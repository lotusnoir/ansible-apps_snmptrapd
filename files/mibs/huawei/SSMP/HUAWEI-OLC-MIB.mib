--
-- HUAWEI-OLC-MIB.mib
-- MIB generated by MG-SOFT Visual MIB Builder Version 4.0 Build 341
-- Thursday, May 15, 2008 at 10:02:27
--  

	HUAWEI-OLC-MIB DEFINITIONS ::= BEGIN
 
		IMPORTS
			huaweiUtility			
				FROM HUAWEI-MIB			
			Unsigned32, OBJECT-TYPE, MODULE-IDENTITY			
				FROM SNMPv2-SMI;
	
	
		-- 1.3.6.1.4.1.2011.6.127
		hwOverLoadControl MODULE-IDENTITY 
			LAST-UPDATED "200805070947Z"		-- May 07, 2008 at 09:47 GMT
			ORGANIZATION 
				"Fix-Net Dept, Huawei Technologies Co.,Ltd."
			CONTACT-INFO 
				"Floor 5, Block 4, R&D Building,
				Huawei Longgang Production Base,
				Shenzhen,  P.R.C.
				http://www.huawei.com
				Zip:518057
				"
			DESCRIPTION 
				"CPU overload-control mib."
			::= { huaweiUtility 127 }

		
	
--
-- Type definitions
--
	
--  Type definitions
-- 
		Time ::= OCTET STRING

	
--
-- Node definitions
--
	
		-- 1.3.6.1.4.1.2011.6.127.1
		hwOverLoadControlQueue OBJECT IDENTIFIER ::= { hwOverLoadControl 1 }

		
		-- 1.3.6.1.4.1.2011.6.127.1.1
		hwOverLoadControlCosQueueMappingMask OBJECT-TYPE
			SYNTAX Unsigned32
			MAX-ACCESS read-write
			STATUS current
			DESCRIPTION
				"Indicate how the cos map to the queue ID.			
				Every four bits indicate the queue ID corresponding to one cos value.
				The range of the queue ID is from 0 to 7.    
				
			    bit value:                bit31                              bit0
				                             0000 0000 0000 0000 0000 0000 0000 0000
			    cos value:	         cos7 cos6 cos5 cos4 cos3 cos2 cos1 cos0"
			DEFVAL { 1985229328 }
			::= { hwOverLoadControlQueue 1 }

		
		-- 1.3.6.1.4.1.2011.6.127.1.2
		hwOverLoadControlQueueWeight OBJECT IDENTIFIER ::= { hwOverLoadControlQueue 2 }

		
		-- 1.3.6.1.4.1.2011.6.127.1.2.1
		hwOverLoadControlQueue0Weight OBJECT-TYPE
			SYNTAX Unsigned32 (1..93)
			MAX-ACCESS read-write
			STATUS current
			DESCRIPTION
				"WRR weight of NO.0 queue."
			DEFVAL { 12 }
			::= { hwOverLoadControlQueueWeight 1 }

		
		-- 1.3.6.1.4.1.2011.6.127.1.2.2
		hwOverLoadControlQueue1Weight OBJECT-TYPE
			SYNTAX Unsigned32 (1..93)
			MAX-ACCESS read-write
			STATUS current
			DESCRIPTION
				"WRR weight of NO.1 queue."
			DEFVAL { 12 }
			::= { hwOverLoadControlQueueWeight 2 }

		
		-- 1.3.6.1.4.1.2011.6.127.1.2.3
		hwOverLoadControlQueue2Weight OBJECT-TYPE
			SYNTAX Unsigned32 (1..93)
			MAX-ACCESS read-write
			STATUS current
			DESCRIPTION
				"WRR weight of NO.2 queue."
			DEFVAL { 12 }
			::= { hwOverLoadControlQueueWeight 3 }

		
		-- 1.3.6.1.4.1.2011.6.127.1.2.4
		hwOverLoadControlQueue3Weight OBJECT-TYPE
			SYNTAX Unsigned32 (1..93)
			MAX-ACCESS read-write
			STATUS current
			DESCRIPTION
				"WRR weight of NO.3 queue."
			DEFVAL { 12 }
			::= { hwOverLoadControlQueueWeight 4 }

		
		-- 1.3.6.1.4.1.2011.6.127.1.2.5
		hwOverLoadControlQueue4Weight OBJECT-TYPE
			SYNTAX Unsigned32 (1..93)
			MAX-ACCESS read-write
			STATUS current
			DESCRIPTION
				"WRR weight of NO.4 queue."
			DEFVAL { 12 }
			::= { hwOverLoadControlQueueWeight 5 }

		
		-- 1.3.6.1.4.1.2011.6.127.1.2.6
		hwOverLoadControlQueue5Weight OBJECT-TYPE
			SYNTAX Unsigned32 (1..93)
			MAX-ACCESS read-write
			STATUS current
			DESCRIPTION
				"WRR weight of NO.5 queue."
			DEFVAL { 12 }
			::= { hwOverLoadControlQueueWeight 6 }

		
		-- 1.3.6.1.4.1.2011.6.127.1.2.7
		hwOverLoadControlQueue6Weight OBJECT-TYPE
			SYNTAX Unsigned32 (1..93)
			MAX-ACCESS read-write
			STATUS current
			DESCRIPTION
				"WRR weight of NO.6 queue."
			DEFVAL { 12 }
			::= { hwOverLoadControlQueueWeight 7 }

		
		-- 1.3.6.1.4.1.2011.6.127.1.2.8
		hwOverLoadControlQueue7Weight OBJECT-TYPE
			SYNTAX Unsigned32 (1..93)
			MAX-ACCESS read-write
			STATUS current
			DESCRIPTION
				"WRR weight of NO.7 queue."
			DEFVAL { 16 }
			::= { hwOverLoadControlQueueWeight 8 }

		
		-- 1.3.6.1.4.1.2011.6.127.1.3
		hwOverLoadControlQueueParaTable OBJECT-TYPE
			SYNTAX SEQUENCE OF HwOverLoadControlQueueParaEntry
			MAX-ACCESS not-accessible
			STATUS current
			DESCRIPTION
				"Olc wrr queues parameter table."
			::= { hwOverLoadControlQueue 3 }

		
		-- 1.3.6.1.4.1.2011.6.127.1.3.1
		hwOverLoadControlQueueParaEntry OBJECT-TYPE
			SYNTAX HwOverLoadControlQueueParaEntry
			MAX-ACCESS not-accessible
			STATUS current
			DESCRIPTION
				"Olc wrr queues parameter table entry."
			INDEX { hwOverLoadControlQueueID }
			::= { hwOverLoadControlQueueParaTable 1 }

		
		HwOverLoadControlQueueParaEntry ::=
			SEQUENCE { 
				hwOverLoadControlQueueID
					Unsigned32,
				hwOverLoadControlQueueMsgNum
					Unsigned32,
				hwOverLoadControlQueueDiscardCount
					Counter32,
				hwOverLoadControlQueueSuppressCount
					Counter32
			 }

		-- 1.3.6.1.4.1.2011.6.127.1.3.1.1
		hwOverLoadControlQueueID OBJECT-TYPE
			SYNTAX Unsigned32 (0..7)
			MAX-ACCESS not-accessible
			STATUS current
			DESCRIPTION
				"Olc wrr queue ID."
			::= { hwOverLoadControlQueueParaEntry 1 }

		
		-- 1.3.6.1.4.1.2011.6.127.1.3.1.2
		hwOverLoadControlQueueMsgNum OBJECT-TYPE
			SYNTAX Unsigned32
			MAX-ACCESS read-only
			STATUS current
			DESCRIPTION
				"Olc wrr queue message number, the number of message currently buffered in the queue."
			::= { hwOverLoadControlQueueParaEntry 2 }

		
		-- 1.3.6.1.4.1.2011.6.127.1.3.1.3
		hwOverLoadControlQueueDiscardCount OBJECT-TYPE
			SYNTAX Counter32
			MAX-ACCESS read-only
			STATUS current
			DESCRIPTION
				"Olc wrr queue discard-count, the count of messages discarded because the queue is full."
			::= { hwOverLoadControlQueueParaEntry 3 }

		
		-- 1.3.6.1.4.1.2011.6.127.1.3.1.4
		hwOverLoadControlQueueSuppressCount OBJECT-TYPE
			SYNTAX Counter32
			MAX-ACCESS read-only
			STATUS current
			DESCRIPTION
				"Olc queue suppress count, the count of queue suppressed because the system is busy."
			::= { hwOverLoadControlQueueParaEntry 4 }

		
		-- 1.3.6.1.4.1.2011.6.127.2
		hwOverLoadControlPara OBJECT IDENTIFIER ::= { hwOverLoadControl 2 }

		
		-- 1.3.6.1.4.1.2011.6.127.2.1
		hwOverLoadControlThreshold1 OBJECT-TYPE
			SYNTAX Unsigned32 (30..99)
			MAX-ACCESS read-write
			STATUS current
			DESCRIPTION
				"Olc system leakbucket threshold1, the target CPU userate of the CPU overload-control."
			DEFVAL { 80 }
			::= { hwOverLoadControlPara 1 }

		
		-- 1.3.6.1.4.1.2011.6.127.2.2
		hwOverLoadControlThreshold2 OBJECT-TYPE
			SYNTAX Unsigned32 (31..100)
			MAX-ACCESS read-write
			STATUS current
			DESCRIPTION
				"Olc system leakbucket threshold2, the max CPU userate of the CPU overload-control."
			DEFVAL { 90 }
			::= { hwOverLoadControlPara 2 }

		
		-- 1.3.6.1.4.1.2011.6.127.2.3
		hwOverLoadControlAdjustFactor OBJECT-TYPE
			SYNTAX Unsigned32 (1..1000)
			MAX-ACCESS read-write
			STATUS current
			DESCRIPTION
				"Olc system leakbucket adjust factor, means how long(units:second) can CPU overload be controlled."
			DEFVAL { 20 }
			::= { hwOverLoadControlPara 3 }

		
	
	END

--
-- HUAWEI-OLC-MIB.mib
--
