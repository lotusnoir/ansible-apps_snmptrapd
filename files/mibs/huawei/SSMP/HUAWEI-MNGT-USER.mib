-- ============================================================================
-- Copyright (C) by  HUAWEI TECHNOLOGIES. All rights reserved.
--
-- Description:  
-- Reference:  
-- Version: V3.00
-- History: 
-- -- 06-11-21 Extracted from HUAWEI-DEVICE-MIB.mib 
-- ============================================================================
HUAWEI-MNGT-MIB DEFINITIONS ::= BEGIN

IMPORTS 

			TimeTicks, IpAddress, Integer32, OBJECT-TYPE, MODULE-IDENTITY, 
			NOTIFICATION-TYPE			
				FROM SNMPv2-SMI	
			DisplayString, DateAndTime, TruthValue, RowStatus	
				FROM SNMPv2-TC
			HWFrameType, HWPCBType, HWSubPCBType, HWPortType		
				FROM HUAWEI-TC-MIB	
			huaweiUtility			
				FROM HUAWEI-MIB	
			hwDev
		    	FROM HUAWEI-DEVICE-MIB;


		hwCliUserMgmt OBJECT IDENTIFIER ::= { hwDev 10 }

		hwCliUserParaTable OBJECT-TYPE
			SYNTAX SEQUENCE OF HwCliUserParaEntry
			MAX-ACCESS not-accessible
			STATUS current
			DESCRIPTION
           "
           "
			::= { hwCliUserMgmt 1 }
		
		hwCliUserParaEntry OBJECT-TYPE
			SYNTAX HwCliUserParaEntry
			MAX-ACCESS not-accessible
			STATUS current
			DESCRIPTION
				
           "
				CLI user parameters configuration table entity.
				
           "
			INDEX { IMPLIED hwCliUserName }
			::= { hwCliUserParaTable 1 }
		
		HwCliUserParaEntry ::=
			SEQUENCE { 
				hwCliUserName
					OCTET STRING,
				hwCliUserPassword
					OCTET STRING,
				hwCliUserLevel
					INTEGER,
				hwCliUserLogins
					INTEGER,
				hwCliUserDecr
					OCTET STRING,
				hwCliUserRowStatus
					RowStatus,
				hwCliUserprofile
					OCTET STRING,
				hwCliUserAccessType
					Unsigned32,
				hwCliUserTimeout
					INTEGER
			 }

		hwCliUserName OBJECT-TYPE
			SYNTAX OCTET STRING (SIZE (1..34))
			MAX-ACCESS not-accessible
			STATUS current
			DESCRIPTION
				
           "
				Name of the CLI user.
           "
			::= { hwCliUserParaEntry 1 }
		
		hwCliUserPassword OBJECT-TYPE
			SYNTAX OCTET STRING (SIZE (0..32))
			MAX-ACCESS read-create
			STATUS current
			DESCRIPTION
				
           "
				password of the CLI user.
           "      
			::= { hwCliUserParaEntry 2 }
		
		hwCliUserLevel OBJECT-TYPE
			SYNTAX INTEGER
				{
				common(1),
				operator(2),
				administrator(3),
				super(4),
				guest(5),
				custom(6)
				}
			MAX-ACCESS read-create
			STATUS current
			DESCRIPTION
				
           "
				Level of CLI user(1:common,2:operator,3:administrator,4:super,5:guest,6:custom).
				
           "
			::= { hwCliUserParaEntry 3 }
		
		hwCliUserLogins OBJECT-TYPE
			SYNTAX INTEGER (0..16)
			MAX-ACCESS read-create
			STATUS current
			DESCRIPTION
				
           "
				The num of user can login in one time.
				
           "
			::= { hwCliUserParaEntry 4 }
		
		hwCliUserDecr OBJECT-TYPE
			SYNTAX OCTET STRING (SIZE (0..100))
			MAX-ACCESS read-create
			STATUS current
			DESCRIPTION
				
           "
				Description of CLI user. 
				
           "
			::= { hwCliUserParaEntry 5 }
		
		hwCliUserRowStatus OBJECT-TYPE
			SYNTAX RowStatus
			MAX-ACCESS read-create
			STATUS current
			DESCRIPTION
				
           "
				Operation status of CLI user,the CLI user 
				can be added,deleted and modified.
				
           "
			::= { hwCliUserParaEntry 6 }
		
		hwCliUserprofile OBJECT-TYPE
			SYNTAX OCTET STRING (SIZE (1..15))
			MAX-ACCESS read-create
			STATUS current
			DESCRIPTION
				
           "the index of userprofile that cli 
				user belongs to 
           "
			::= { hwCliUserParaEntry 7 }
		
		hwCliUserAccessType OBJECT-TYPE
			SYNTAX Unsigned32
			MAX-ACCESS read-create
			STATUS current
			DESCRIPTION
				
           "
				Access-Type of user: Command Line(CLI)(0x1) ,OSS(0x2) ,WEB(0x4) 
           "
			DEFVAL { 1 }
			::= { hwCliUserParaEntry 8 }
		
		hwCliUserTimeout OBJECT-TYPE
			SYNTAX INTEGER (1..120)
			MAX-ACCESS read-create
			STATUS current
			DESCRIPTION
				
           "
				Timeout of CLI user
				
           "
			::= { hwCliUserParaEntry 9 }
			
			
		hwCliClientTable OBJECT-TYPE
			SYNTAX SEQUENCE OF HwCliClientEntry
			MAX-ACCESS not-accessible
			STATUS current
			DESCRIPTION
				
           "
           "
			::= { hwCliUserMgmt 2 }
		
		hwCliClientEntry OBJECT-TYPE
			SYNTAX HwCliClientEntry
			MAX-ACCESS not-accessible
			STATUS current
			DESCRIPTION
				
           "
				CLI user parameters configuration table entity.
           "
			INDEX { hwCliClientID }
			::= { hwCliClientTable 1 }
		
		HwCliClientEntry ::=
			SEQUENCE { 
				hwCliClientID
					INTEGER,
				hwCliClientUserName
					OCTET STRING,
				hwCliClientType
					INTEGER,
				hwCliClientIp
					IpAddress,
				hwCliClientLoginTime
					DateAndTime,
				hwCliClientAdminStatus
					INTEGER,
				hwCliUserIdleTimeOut
					Integer32
			 }

		hwCliClientID OBJECT-TYPE
			SYNTAX INTEGER (1..255)
			MAX-ACCESS not-accessible
			STATUS current
			DESCRIPTION
				
           "
				Client ID(1..255).
				
           "
			::= { hwCliClientEntry 1 }
		
		hwCliClientUserName OBJECT-TYPE
			SYNTAX OCTET STRING (SIZE (1..34))
			MAX-ACCESS read-only
			STATUS current
			DESCRIPTION
				
           "
				User name of client.
				
           "
			::= { hwCliClientEntry 2 }
		
		hwCliClientType OBJECT-TYPE
			SYNTAX INTEGER
				{
				serial(1),
				telnet(2),
				proxy(3)
				}
			MAX-ACCESS read-only
			STATUS current
			DESCRIPTION
				
           "
				Type of client(1:serial,2:telnet,3:proxy).
				
           "
			::= { hwCliClientEntry 3 }
		
		hwCliClientIp OBJECT-TYPE
			SYNTAX IpAddress
			MAX-ACCESS read-only
			STATUS current
			DESCRIPTION
				
           "
				The IP address of client.
           "
			::= { hwCliClientEntry 4 }
		
		hwCliClientLoginTime OBJECT-TYPE
			SYNTAX DateAndTime
			MAX-ACCESS read-only
			STATUS current
			DESCRIPTION
				
           "
				Login time of Client. 
				
           "
			::= { hwCliClientEntry 5 }
		
		hwCliClientAdminStatus OBJECT-TYPE
			SYNTAX INTEGER
				{
				disconnect(1)
				}
			MAX-ACCESS read-write
			STATUS current
			DESCRIPTION
				
           "
				admin status of client, can disconnect client.
				
           "
			::= { hwCliClientEntry 6 }
			
		hwCliUserIdleTimeOut OBJECT-TYPE
			SYNTAX Integer32
			MAX-ACCESS read-write
			STATUS current
			DESCRIPTION
				
           "					
           "
			::= { hwCliClientEntry 7 }
		
		
		hwSysMaxLoginNum OBJECT-TYPE
			SYNTAX Integer32
			MAX-ACCESS read-write
			STATUS current
			DESCRIPTION
				
           " The system max login number.
           "
			::= { hwCliUserMgmt 3 }
		
		hwTelnetMaxSessionNum OBJECT-TYPE
			SYNTAX Integer32
			MAX-ACCESS read-write
			STATUS current
			DESCRIPTION
				
           "
				The max number of Simultaneous Telnet sessions
				
           "
			::= { hwCliUserMgmt 4 }
		
		hwCliUserProfileParaTable OBJECT-TYPE
			SYNTAX SEQUENCE OF HwCliUserProfileParaEntry
			MAX-ACCESS not-accessible
			STATUS current
			DESCRIPTION 
           "
           "
			::= { hwCliUserMgmt 5 }
		
		hwCliUserProfileParaEntry OBJECT-TYPE
			SYNTAX HwCliUserProfileParaEntry
			MAX-ACCESS not-accessible
			STATUS current
			DESCRIPTION
				
           "user profile parameters. 
				 
           "
			INDEX { hwCliUserProfileName }
			::= { hwCliUserProfileParaTable 1 }
		
		HwCliUserProfileParaEntry ::=
			SEQUENCE { 
				hwCliUserProfileName
					OCTET STRING,
				hwCliUserNameAvailableInterval
					Unsigned32,
				hwCliUserPwdAvailableInterval
					Unsigned32,
				hwCliUserLoginTime
					DateAndTime,
				hwCliUserLogoutTime
					DateAndTime,
				hwCliUserProfileRowStatus
					RowStatus
			 }

		hwCliUserProfileName OBJECT-TYPE
			SYNTAX OCTET STRING
			MAX-ACCESS not-accessible
			STATUS current
			DESCRIPTION
				
           "the name of the user profile
           "
			::= { hwCliUserProfileParaEntry 1 }
		
		
		hwCliUserNameAvailableInterval OBJECT-TYPE
			SYNTAX Unsigned32 (0..999)
			UNITS 
           "day
           "
			MAX-ACCESS read-create
			STATUS current
			DESCRIPTION
				
           "available period of cli username
           "
			DEFVAL { 30 }
			::= { hwCliUserProfileParaEntry 4 }
		
		hwCliUserPwdAvailableInterval OBJECT-TYPE
			SYNTAX Unsigned32 (0..999)
			UNITS 
           "day
           "
			MAX-ACCESS read-create
			STATUS current
			DESCRIPTION
				
           "available period of cli userpassword
           "
			DEFVAL { 30 }
			::= { hwCliUserProfileParaEntry 5 }
		
		hwCliUserLoginTime OBJECT-TYPE
			SYNTAX DateAndTime
			MAX-ACCESS read-create
			STATUS current
			DESCRIPTION
				
           "earliest time that cli user be able to log in
           "
			::= { hwCliUserProfileParaEntry 6 }
		
		hwCliUserLogoutTime OBJECT-TYPE
			SYNTAX DateAndTime
			MAX-ACCESS read-create
			STATUS current
			DESCRIPTION
				
           "latest time that cli user be able to log in
           "
			::= { hwCliUserProfileParaEntry 7 }
		
		hwCliUserProfileRowStatus OBJECT-TYPE
			SYNTAX RowStatus
			MAX-ACCESS read-create
			STATUS current
			DESCRIPTION 
           "
           "
			::= { hwCliUserProfileParaEntry 10 }			 	
		

		hwCliSysPara OBJECT IDENTIFIER ::= { hwCliUserMgmt 6 }
		
		hwCliSyslockInterval OBJECT-TYPE
			SYNTAX INTEGER (1..65535)
			MAX-ACCESS read-write
			STATUS current
			DESCRIPTION
				
           "
           Lock Interval
           "
			DEFVAL { 15 }
			::= { hwCliSysPara 1 }
		
		hwCliSyslockCondition OBJECT-TYPE
			SYNTAX INTEGER (1..15)
			MAX-ACCESS read-write
			STATUS current
			DESCRIPTION
				
           "
           Lock Condition
           "
			DEFVAL { 3 }
			::= { hwCliSysPara 2 }
		
		hwCliSysLoginModifyPwd OBJECT-TYPE
			SYNTAX INTEGER
				{
				enable(0),
				disable(1)
				}
			MAX-ACCESS read-write
			STATUS current
			DESCRIPTION
				
           "
           the switch to control if user can to change the password , 0 means user can change the password at
           first login , 1 means not 
           "
			DEFVAL { disable }
			::= { hwCliSysPara 3 }
		
		hwCliSysLockType OBJECT-TYPE
			SYNTAX INTEGER
				{
				none(0),
				user(1),
				ip(2),
				all(3)
				}
			MAX-ACCESS read-write
			STATUS current
			DESCRIPTION
				
           "
           Lock type , 0: no lock 1: lock user 2: lock ip 3: lock user and ip
           "
			DEFVAL { none }
			::= { hwCliSysPara 4 }
			
		hwCliSysSecurityMode OBJECT-TYPE
			SYNTAX INTEGER
				{
				enable(1),
				disable(2)
				}
			MAX-ACCESS read-write
			STATUS current
			DESCRIPTION
				"
				 Security mode switch.
				     "
			DEFVAL { disable }
			::= { hwCliSysPara 5 }

			
		hwSysManFirewall OBJECT IDENTIFIER ::= { hwDev 12 }

		hwFirewallSwitchTable OBJECT-TYPE
			SYNTAX SEQUENCE OF HwFirewallSwitchEntry
			MAX-ACCESS not-accessible
			STATUS current
			DESCRIPTION
				
           "
				Firewall switch table.
				
           "
			::= { hwSysManFirewall 1 }
		
		hwFirewallSwitchEntry OBJECT-TYPE
			SYNTAX HwFirewallSwitchEntry
			MAX-ACCESS not-accessible
			STATUS current
			DESCRIPTION
				
           "
				Firewall switch table entity.
				
           "
			INDEX { hwFirewallProtocolType }
			::= { hwFirewallSwitchTable 1 }
		
		HwFirewallSwitchEntry ::=
			SEQUENCE { 
				hwFirewallProtocolType
					INTEGER,
				hwFirewallSwitch
					INTEGER
			 }
			
		
	 	hwFirewallProtocolType OBJECT-TYPE
			 SYNTAX INTEGER
			        {
			           telnet(1),
			           ssh(2),
			           snmp(3)
			        }
			 MAX-ACCESS not-accessible
			 STATUS current
			 DESCRIPTION
				
           "
				 Protocol type of the firewall:
				  1.telnet
				  2.ssh
				  3.snmp
				
           "
			 ::= { hwFirewallSwitchEntry 1 }

		hwFirewallSwitch	 OBJECT-TYPE
			SYNTAX  INTEGER
			        {
			          enable(1),
			          disable(2)
			        }
			MAX-ACCESS read-write
			STATUS current
			DESCRIPTION
				
           "
				The switch of the firewall:
				 1.enable
				 2.disable
				
           "
			DEFVAL { disable }
			::= { hwFirewallSwitchEntry 2 }

		hwAccessIpTable OBJECT-TYPE
			SYNTAX SEQUENCE OF HwAccessIpEntry
			MAX-ACCESS not-accessible
			STATUS current
			DESCRIPTION
				
           "
				Access Ip table.
				
           "
			::= { hwSysManFirewall 2 }
		
		hwAccessIpEntry OBJECT-TYPE
			SYNTAX HwAccessIpEntry
			MAX-ACCESS not-accessible
			STATUS current
			DESCRIPTION
				
           "
				Access Ip table entity.
				
           "
			INDEX { hwFirewallProtocolType, hwAccessIpStartAddr }
			::= { hwAccessIpTable 1 }
		
		HwAccessIpEntry ::=
			SEQUENCE { 
				hwAccessIpStartAddr
					IpAddress,
				hwAccessIpEndAddr
					IpAddress,
				hwAccessIpRowStatus
					RowStatus
			 }
			
		
		   hwAccessIpStartAddr OBJECT-TYPE
			    SYNTAX IpAddress
			    MAX-ACCESS not-accessible
			    STATUS current
			    DESCRIPTION
				
           "
				 Start IP address of one record in access Ip table.
				
           "
			   ::= { hwAccessIpEntry 1 }
			    
		   hwAccessIpEndAddr OBJECT-TYPE
			    SYNTAX IpAddress
			    MAX-ACCESS read-create
			    STATUS current
			    DESCRIPTION
				
           "
				 End IP address of one record in access Ip table.
				
           "
			   ::= { hwAccessIpEntry 2 }	
			   
		   hwAccessIpRowStatus  OBJECT-TYPE
			    SYNTAX RowStatus
			    MAX-ACCESS read-create
			    STATUS current
			    DESCRIPTION
				
           "
				 Operation status of row.
				
           "
			    ::= { hwAccessIpEntry 3 }
		   
		   	   		    

 			
		hwRefuseIpTable OBJECT-TYPE
			SYNTAX SEQUENCE OF HwRefuseIpEntry
			MAX-ACCESS not-accessible
			STATUS current
			DESCRIPTION
				
           "
				Refuse Ip table.
				
           "
			::= { hwSysManFirewall 3 }
		
		hwRefuseIpEntry OBJECT-TYPE
			SYNTAX HwRefuseIpEntry
			MAX-ACCESS not-accessible
			STATUS current
			DESCRIPTION
				
           "
				Refuse Ip table entity.
				
           "
			INDEX { hwFirewallProtocolType, hwRefuseIpStartAddr }
			::= { hwRefuseIpTable 1 }
		
		HwRefuseIpEntry ::=
			SEQUENCE { 
				hwRefuseIpStartAddr
					IpAddress,
				hwRefuseIpEndAddr
					IpAddress,
				hwRefuseIpRowStatus
					RowStatus
			 }
			

		
		   hwRefuseIpStartAddr OBJECT-TYPE
			    SYNTAX IpAddress
			    MAX-ACCESS not-accessible
			    STATUS current
			    DESCRIPTION
				
           "
				 Start IP address of one record in refuse Ip table.
				
           "
			   ::= { hwRefuseIpEntry 1}
			    
		   hwRefuseIpEndAddr OBJECT-TYPE
			    SYNTAX IpAddress
			    MAX-ACCESS read-create
			    STATUS current
			    DESCRIPTION
				
           "
				 End IP address of one record in refuse Ip table.
				
           "
			   ::= { hwRefuseIpEntry 2}	
			   
		   hwRefuseIpRowStatus  OBJECT-TYPE
			    SYNTAX RowStatus
			    MAX-ACCESS read-create
			    STATUS current
			    DESCRIPTION
				
           "
				 Operation status of row.
				
           "
			    ::= { hwRefuseIpEntry 3 }
			    
			    
			    
		hwSysManSourceInterface OBJECT IDENTIFIER ::= { hwDev 19 }
					
		hwSysManSourceInterfaceTable OBJECT-TYPE
			SYNTAX SEQUENCE OF HwSysManSourceInterfaceEntry
			MAX-ACCESS not-accessible
			STATUS current
			DESCRIPTION
				"
				Sys man source interface table.
				"
			::= { hwSysManSourceInterface 1 }
		
		hwSysManSourceInterfaceEntry OBJECT-TYPE
			SYNTAX HwSysManSourceInterfaceEntry
			MAX-ACCESS not-accessible
			STATUS current
			DESCRIPTION
				"
				Sys man source interface table entity.
				" 
			INDEX { hwSysManProtocolType }
			::= { hwSysManSourceInterfaceTable 1 }
		
		HwSysManSourceInterfaceEntry ::=
			SEQUENCE { 
				hwSysManProtocolType
					INTEGER,
				hwSourceInterfaceType
					INTEGER,
				hwSourceInterfaceNumber
					Integer32
			 }			

		
		   hwSysManProtocolType OBJECT-TYPE
			    SYNTAX INTEGER 
					    {
						trap(1),
						syslog(2),
						tftp(3),
						ftp(4),
						sftp(5),
						telnet(6),
						ping(7),
						tracert(8),
						license(9)
						}
			    MAX-ACCESS read-only
			    STATUS current
			    DESCRIPTION
				"
				 Sys man protocol type.
				"
			    ::= { hwSysManSourceInterfaceEntry 1}
			    
		   hwSourceInterfaceType OBJECT-TYPE
			    SYNTAX INTEGER
			    		{
						auto(1),
						loopback(2),
						meth(3),
						vlanif(4)
						}
			    MAX-ACCESS read-write
			    STATUS current
			    DESCRIPTION
				"
				 Source interface type.
				"
			    DEFVAL { 1 }
			    ::= { hwSysManSourceInterfaceEntry 2}	
			   
		   hwSourceInterfaceNumber  OBJECT-TYPE
			    SYNTAX Integer32
			    MAX-ACCESS read-write
			    STATUS current
			    DESCRIPTION
				"
				 Source interface number.
				"
			    ::= { hwSysManSourceInterfaceEntry 3 }
		
		hwConfigLock OBJECT IDENTIFIER ::= { hwDev 23 }
		
		hwConfigLockState OBJECT-TYPE
			SYNTAX INTEGER
				{
				locked(1),
				unlocked(2)
				}
			MAX-ACCESS read-only
			STATUS current
			DESCRIPTION
				"The state of config lock: locked or unlocked."
			::= { hwConfigLock 1 }
		
		hwConfigUnlockInterval OBJECT-TYPE
			SYNTAX INTEGER (1..255)
			MAX-ACCESS read-write
			STATUS current
			DESCRIPTION
				"The interval to automatically unlock config:  1 to 255 minutes.
				Default: 5 minutes."
			DEFVAL { 5 }
			::= { hwConfigLock 2 }
		
		hwConfigLockUserType OBJECT-TYPE
			SYNTAX INTEGER
				{
				nms(1),
				series(2),
				telnet(3),
				web(4),
				xml(5)
				}
			MAX-ACCESS read-only
			STATUS current
			DESCRIPTION
				"The user type of lock: nms, series, telnet, web, xml.
				"
			::= { hwConfigLock 3 }
		
		hwConfigLockUserName OBJECT-TYPE
			SYNTAX OCTET STRING
			MAX-ACCESS read-only
			STATUS current
			DESCRIPTION
				"The user name of lock.
				"
			::= { hwConfigLock 4 }
		
		hwConfigLockUserIPAddr OBJECT-TYPE
			SYNTAX IpAddress
			MAX-ACCESS read-only
			STATUS current
			DESCRIPTION
				"The user IP address of lock."
			::= { hwConfigLock 5 }
		
		hwConfigLockOperate OBJECT-TYPE
			SYNTAX INTEGER
				{
				lock(1),
				unlock(2)
				}
			MAX-ACCESS read-write
			STATUS current
			DESCRIPTION
				"The operation to lock or unlock the config."
			::= { hwConfigLock 6 }
		
	
END						

--
-- HUAWEI-MNGT-MIB.mib
--
