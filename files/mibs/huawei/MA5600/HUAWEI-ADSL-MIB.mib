-- ============================================================================
-- Copyright (C) by  HUAWEI TECHNOLOGIES. All rights reserved.
--
-- Description:  
-- Reference:  
-- Version: V3.09
-- History:
-- lichengyuan hwXdslPortTable add hwXdslPortStateChangeTrapEnable
-- lichengyuan add hwXdslPortStatStatisticTable
-- zhuweihui 2006-02-13 hwadslLineExtConfProfileTable add two leaves
-- tangjiecheng 2006-02-15  hwXdslPortTable add hwXdslPortFarEndRunState 
-- laizhansong add hwAdslLineLatestActParaTable add hwAdslPortActRateMonitorTrap
-- machi 2006-11-17 hwXdslPortTable add hwXdslPortUpCnt,hwXdslPortUpCntAdminStatus,hwXdslPortLastUpTime,
-- hwXdslPortLastDownTime,hwXdslPortClearUpCntTime,hwXdslPortRetrainCnt,hwXdslPortLastRetrainReason
-- liuxiong add hwAdslPortPerformanceStatTable   
-- zhouxinru add hwAdslPortRateChangeTrapParaTable add hwXdslSysManagementParaTable and hwAdslPortRateChangeTrap
-- jiaweimei hwadslLineExtConfProfileTable add hwadsl2L2ModeIntervalPowerValue and hwadsl2L2ModeTotalPowerValue
-- jingjie hwXdslPortTable add hwXdslPortUpThreshold and hwXdslPortDownThreshold
-- guozhiguo(00108754)hwadslLineExtConfProfileTable,adslAtucChanTable,adslAturChanTable,adslAtucChanPerfDataTable, 
-- adslAturChanPerfDataTable,adslAtucChanIntervalTable,adslAturChanIntervalTable add PHY-R leaves
-- lvfengtao add hwAdslAtucCurrSignalAtn in adslAtucPhysTable; add hwAdslAturCurrSignalAtn in adslAturPhysTable; add hwAdslAtucPerfFailInits,
-- hwAdslAtucPerfCurr15MinFailInits,hwAdslAtucPerfCurr1DayFailInits,hwAdslAtucPerfPrev1DayFailInits in adslAtucPerfDataTable and also he added 
-- hwAdslAtucIntervalFailInits in adslAtucIntervalTable, additionly he update the mib to V3.16.
-- liuyaning 2008-3-31 add hwAdsl2SCStatusTable,include eight leaves: hwAdsl2SCStatusDirection,hwAdsl2SCStatusSnr,hwAdsl2SCStatusBitsAlloc,hwAdsl2SCStatusGainAlloc,hwAdsl2SCStatusLog ,
-- hwAdsl2SCStatusQln,hwAdsl2SCStatusSnrMargin add hwAdsl2SCStatusTxPSD;add leaves hwadsl2TSSiPsdMaskUs,hwadsl2TSSiPsdMaskDs add hwAdslExtPcbDs
-- to hwadslLineExtConfProfileTable;add leaves hwadslAtucChanRsSize,hwadslAtucChanCodeGain add hwadslAtucChanPcb to adslAtucChanTable;add hwadslAturChanRsSize
-- add hwadslAturChanCodeGain to adslAturChanTable; add hwadslLineDynamicProfile to adslLineTable; added hwxdslDynamicProfTable,hwXdslPortIopCaptureTable,hwXdslDynamicInfoCollectTable
-- for N2510 and IOP, additionly update the mib to V3.17.
-- liuyaning 2008-4-21 modify leafe hwAdsl2SCStatusTxPSD,additionly update the mib to V3.18.
-- wangyuzhou 2008-04-25 delete leaves hwxdslDynamicProfPcbDs and hwAdslExtPcbDs,modify leafe hwxdslDynamicProfVdsl2CarMaskUS and hwxdslDynamicProfVdsl2CarMaskDS to hwxdslDynamicProfCarMaskUS and hwxdslDynamicProfCarMaskDS update the mib to V3.18.
-- liuyaning 2008-07-25 modify leaves hwadslAtucChanCodeGain,hwadslAturChanCodeGain,hwAdsl2SCStatusTxPSD,hwXdslPortIopCaptureOperStatus,update the mib to V3.20.
-- ============================================================================
	HUAWEI-ADSL-MIB DEFINITIONS ::= BEGIN

		IMPORTS 
			adslMibObjects, adslLineConfProfileEntry, adslLineConfProfileName, adslLineEntry, adslAturChanEntry, adslAtucChanEntry, adslAtucChanPerfDataEntry, adslAturChanPerfDataEntry, adslAtucChanIntervalEntry, adslAturChanIntervalEntry, adslTraps, adslAturPhysEntry, adslAtucPhysEntry, adslAtucPerfDataEntry, adslAtucIntervalEntry
				FROM ADSL-LINE-MIB			
			ifIndex			
				FROM IF-MIB			
			ifType
				FROM RFC1213-MIB	
			hwFrameIndex, hwSlotIndex,hwSubslotIndex,hwPortIndex,hwIasConfigChangeTrapID
                FROM HUAWEI-DEVICE-MIB
			hwAlarmId,hwAlarmTime,hwAlarmSn,hwCauseId,hwTrapType
                FROM HUAWEI-TC-MIB 		
			Integer32, Unsigned32, Gauge32, OBJECT-TYPE			
				FROM SNMPv2-SMI			
			RowStatus, DateAndTime			
				FROM SNMPv2-TC
			PhysAddress, TEXTUAL-CONVENTION			
				FROM SNMPv2-TC
            		Adsl2TransmissionModeType,
            		Adsl2PsdMaskDs, 
            		Adsl2PsdMaskUs        
                		FROM HUAWEI-ADSL2-LINE-TC-MIB	
			adslLineExtEntry
				FROM ADSL-LINE-EXT-MIB
			PerfIntervalCount
				FROM PerfHist-TC-MIB
			hwExtSrvFlowDescInfo
				FROM HUAWEI-ETHERLIKE-EXT-MIB 
			sysName
				FROM SNMPv2-MIB
            Adsl2SymbolProtection
				FROM HUAWEI-ADSL2-LINE-TC-MIB
			SnmpAdminString  
			  FROM SNMP-FRAMEWORK-MIB;


			                       
  	HWADSLSYMBOLPROTECTION ::= TEXTUAL-CONVENTION
		     STATUS current
		     DESCRIPTION  ""
		     SYNTAX INTEGER {
		       noProtection(0),
		       halfSymbol(1),
		       singleSymbol(2),
		       twoSymbols(4),
		       threeSymbols(6),
		       fourSymbols(8),
		       fiveSymbols(10),
		       sixSymbols(12),
		       sevenSymbols(14),
		       eightSymbols(16),
		       nineSymbols(18),
		       tenSymbols(20),
		       elevenSymbols(22),
		       twelveSymbols(24),
		       thirteenSymbols(26),
		       fourteenSymbols(28),
		       fifteenSymbols(30),
		       sixteenSymbols(32),
		       null(65535)
   		 }
   	HWADSLTRANSMISSIONMODETYPE ::= TEXTUAL-CONVENTION
		     STATUS current
		     DESCRIPTION  " 
		     0 Unknown
		     1 G992.1-Annex A
		     2 G992.2-Annex A
		     3 T1.413
		     4 G992.3-Annex A
		     5 G992.5-Annex A 
		     6 G992.3-Annex L
		     "
		     SYNTAX INTEGER {
		       none(0),
		       q9921gdmt(1),
		       q9922glite(2),
		       ansit1413(3),
		       q9923adsl2a(4),
		       q9925adsl2plus(5),
		       q9923adsl2l(6)   		 
	       }
       HWADSL2ANNEXMSCOPE ::= TEXTUAL-CONVENTION
		     STATUS current
		     DESCRIPTION  ""
		     SYNTAX INTEGER { 
                     ToneIndex7to32(1),                                                           
                     ToneIndex7to36(2),                                                           
                     ToneIndex7to40(3),                                                           
                     ToneIndex7to44(4),                                                             
                     ToneIndex7to48(5),
                     ToneIndex7to52(6),  
                     ToneIndex7to56(7),                                                           
                     ToneIndex7to60(8),                                                           
                     ToneIndex7to64(9)
                     }

    PortDateAndTime ::= TEXTUAL-CONVENTION
    DISPLAY-HINT "2d-1d-1d,1d:1d:1d.2d"
    STATUS       current
    DESCRIPTION
            "A date-time specification of Xdsl Port.

             field  octets  contents                  range
             -----  ------  --------                  -----
               1      1-2   year                      0..65536
               2       3    month                     1..12
               3       4    day                       1..31
               4       5    hour                      0..23
               5       6    minutes                   0..59
               6       7    seconds                   0..59
               7       8-9  mili-seconds              0..999

            For example, Tuesday May 26, 1992 at 1:30:15:999 would be
            displayed as:

                             1992-5-26,13:30:15.999

           "
    SYNTAX       OCTET STRING (SIZE (9 | 9))
   	
--
-- Node definitions
--
	   	
   	hwadslAturChanCurrINP OBJECT-TYPE
             SYNTAX      Gauge32
             UNITS       "DMT Symbol"
             MAX-ACCESS  read-only
             STATUS      current
             DESCRIPTION
                 "
                 Indicates Impulse Noise Protection on upstream direction.
                 The value multiply 1/10000 is the real value .
                 
                 "
         ::= { adslAturChanEntry 65536 }
         
	hwadslAturChanRsSymbols OBJECT-TYPE
	             SYNTAX      Gauge32
	             UNITS        "byte"
	             MAX-ACCESS  read-only
	             STATUS      current
	             DESCRIPTION
	                 "
	                 Indicates Reed-Solomon symbols on upstream direction.
	                 The value multiply 1/10000 is the real value .

	                 "
	         ::= { adslAturChanEntry 65537 }
	hwadslAturChanRsRedundancy OBJECT-TYPE
	             SYNTAX      Gauge32
	             UNITS        "byte"
	             MAX-ACCESS  read-only
	             STATUS      current
	             DESCRIPTION
	                 "Indicates Reed-Solomon redundancy on upstream direction."
	         ::= { adslAturChanEntry 65538 }
	hwadslAturChanRsDepth OBJECT-TYPE
	             SYNTAX      Gauge32
	             UNITS        "byte"
	             MAX-ACCESS  read-only
	             STATUS      current
	             DESCRIPTION
	                 "Indicates Reed-Solomon depth on upstream direction."
	         ::= { adslAturChanEntry 65539 }  
	
	hwadslAturChanSymbolLength OBJECT-TYPE
	             SYNTAX      Gauge32
	             UNITS        "bit"
	             MAX-ACCESS  read-only
	             STATUS      current
	             DESCRIPTION
	                 "Indicates the Bit Number of the DMT Symbol on upstream direction ."
	         ::= { adslAturChanEntry 65540 }
	
	hwadslAturChanPhyRrrcBits OBJECT-TYPE
            SYNTAX      Gauge32
            MAX-ACCESS  read-only
            STATUS      current
            DESCRIPTION
                "The bits in the channel that used to retransmission on upstream direction."
            ::= { adslAturChanEntry 65541 }
    
        hwadslAturChanPhyRtxQueue OBJECT-TYPE
            SYNTAX      Gauge32
            MAX-ACCESS  read-only
            STATUS      current
            DESCRIPTION
                "Queues in send buffer on upstream direction."
            ::= { adslAturChanEntry 65542 }
	        	         	         
	hwadslAturChanRsSize OBJECT-TYPE
	             SYNTAX      Gauge32
	             UNITS        "byte"
	             MAX-ACCESS  read-only
	             STATUS      current
	             DESCRIPTION
	                "Indicates Reed-Solomon Codeword Size on upstream direction.
	                 It ranges from 0 to 255."
	         ::= { adslAturChanEntry 65543 }  
	         
	hwadslAturChanCodeGain OBJECT-TYPE
	             SYNTAX      Gauge32
	             MAX-ACCESS  read-only
	             STATUS      current
	             DESCRIPTION
	                  "Indicates Code Gain on upstream direction.
	                 It ranges from 0 to 16 units of 0.5 dB (physical values
 	                 are 0 to 8 dB)"
	        ::= { adslAturChanEntry 65544 } 
	
	hwadslAturTransmissionCapabilities OBJECT-TYPE       
	    SYNTAX      Adsl2TransmissionModeType
	    MAX-ACCESS  read-only
	    STATUS      current
	    DESCRIPTION
            "The ATU transmission system capability list of the different
             coding types.  It is coded in a bit-map representation with 1
             or more bits set.  A bit set to '1' means that the ATU
             supports the respective coding.  The value may be derived
             from the handshaking procedures defined in G.994.1. "
            ::= { adslAturPhysEntry 65535 }         

-- adslAturPhysTable
		-- 1.3.6.1.2.1.10.94.1.1.3.1.65536
		hwAdslAturCurrSignalAtn OBJECT-TYPE
			SYNTAX Gauge32 (0..630)
			UNITS "tenth dB"
			MAX-ACCESS read-only
			STATUS current
			DESCRIPTION
				"The signal attenuation value on ATUR."
			::= { adslAturPhysEntry 65536 }
	hwadslAtucChanCurrINP OBJECT-TYPE
	             SYNTAX      Gauge32
	             UNITS       "DMT Symbol"
	             MAX-ACCESS  read-only
	             STATUS      current
	             DESCRIPTION
	                 "
	                 Indicates Impulse Noise Protection on downstream direction.
	                 The value multiply 1/10000 is the real value .

	                 "
	         ::= { adslAtucChanEntry 65536 }
	         

	         
	hwadslAtucChanRsSymbols OBJECT-TYPE
	             SYNTAX      Gauge32
	             UNITS        "byte"
	             MAX-ACCESS  read-only
	             STATUS      current
	             DESCRIPTION
	                 "
	                 Indicates Reed-Solomon symbols on downstream direction.
	                 The value multiply 1/10000 is the real value .

	                 "
	         ::= { adslAtucChanEntry 65537 }
	         
	hwadslAtucChanRsRedundancy OBJECT-TYPE
	             SYNTAX      Gauge32
	             UNITS        "byte"
	             MAX-ACCESS  read-only
	             STATUS      current
	             DESCRIPTION
	                 "Indicates Reed-Solomon redundancy on downstream direction."
	         ::= { adslAtucChanEntry 65538 }
	hwadslAtucChanRsDepth OBJECT-TYPE
	             SYNTAX      Gauge32
	             UNITS        "byte"
	             MAX-ACCESS  read-only
	             STATUS      current
	             DESCRIPTION
	                 "Indicates Reed-Solomon depth on downstream direction."
	         ::= { adslAtucChanEntry 65539 } 
	         
	hwadslAtucChanSymbolLength OBJECT-TYPE
	             SYNTAX      Gauge32
	             UNITS        "bit"
	             MAX-ACCESS  read-only
	             STATUS      current
	             DESCRIPTION
	                 "Indicates the Bit Number of the DMT Symbol on downstream direction ."
	         ::= { adslAtucChanEntry 65540 }
	         
	         
	hwadslAtucChanPhyRrrcBits OBJECT-TYPE
            SYNTAX      Gauge32
            MAX-ACCESS  read-only
            STATUS      current
            DESCRIPTION
                "The bits in the channel that used to retransmission on downstream direction."
            ::= { adslAtucChanEntry 65541 }
    
        hwadslAtucChanPhyRtxQueue OBJECT-TYPE
            SYNTAX      Gauge32
            MAX-ACCESS  read-only
            STATUS      current
            DESCRIPTION
                "Queues in send buffer on downstream direction."
            ::= { adslAtucChanEntry 65542 }

        hwadslAtucChanRsSize OBJECT-TYPE
	              SYNTAX      Gauge32
	              UNITS        "byte"
	              MAX-ACCESS  read-only
	              STATUS      current
	              DESCRIPTION
	                   "Indicates Reed-Solomon Codeword Size on downstream direction .
	                  It ranges from 0 to 255."
	          ::= { adslAtucChanEntry 65543 }    
	          
	    hwadslAtucChanCodeGain OBJECT-TYPE
	              SYNTAX      Gauge32
	              MAX-ACCESS  read-only
	              STATUS      current
	              DESCRIPTION
	                   "Indicates Code Gain on downstream direction.
	                  It ranges from 0 to 16 units of 0.5 dB (physical values
 	                  are 0 to 8 dB)"
	          ::= { adslAtucChanEntry 65544 }
        
            hwadslAtucChanPcb OBJECT-TYPE
	              SYNTAX      Gauge32
	              UNITS        "tenth dB"
	              MAX-ACCESS  read-only
	              STATUS      current
	              DESCRIPTION
	                    "Indicates Power Cut-back on downstream direction.
	                  It ranges from 0 to 400 units of 0.1 dB (physical values
 	                  are 0 to 40 dB)"
	          ::= { adslAtucChanEntry 65545 }

		hwAdslAtucConfDownBitSwap OBJECT-TYPE
			SYNTAX INTEGER
				{
				enabled(1),
				disabled(2)
				}
			MAX-ACCESS read-create
			STATUS current
			DESCRIPTION
				"
				Enables and disables the down bitswap of a template.
				"
			DEFVAL { 1 }
			::= { adslLineConfProfileEntry 65536 }
		
		hwAdslAtucConfUpBitSwap OBJECT-TYPE
			SYNTAX INTEGER
				{
				enabled(1),
				disabled(2)
				}
			MAX-ACCESS read-create
			STATUS current
			DESCRIPTION
				"
				Enables and disables the up bitswap of a template.
				"
			DEFVAL { 1 }
			::= { adslLineConfProfileEntry 65537 }
		
		hwAdslTrellionsModeEnable OBJECT-TYPE
			SYNTAX INTEGER
				{
				enabled(1),
				disabled(2)
				}
			MAX-ACCESS read-create
			STATUS current
			DESCRIPTION
				"
				Enables and disables the Trellions mode. This
				object is defaulted enabled(1).
				"
			DEFVAL { 1 }
			::= { adslLineConfProfileEntry 65538 }
		
		hwAdslTransmissionMode OBJECT-TYPE
			SYNTAX INTEGER
				{
				all(1),
				fullRate(2),
				gliteOnly(3),
				t1413Only(4),
				gdmtOnly(5),
				ghs(6),
				g992Dot1(7),
				g992Dot2(8),
				g992Dot3(9),
				g992Dot4(10),
				g992Dot5(11),
				adslAllOnly(12),
				adslAndAdsl2(13)
				}
			MAX-ACCESS read-create
			STATUS current
			DESCRIPTION
				"Indicates the transmission mode of this channel.
				
				all(1)  	All (G992.1, G992.2, T1.413)(Default)
				fullRate(2)	Full rate(G992.1 or T1.413)
				gliteOnly(3)	G992.2(g.lite) only	
				t1413Only(4)	T1.413 only
				gdmtOnly(5)	G992.1,G992.3,G992.5,(g.dmt) only
				ghs(6)		g.hs (G992.1,G992.2,G992.3,G992.4,G992.5,G992.5 is prior)
				g992Dot1(7)	G992.1
				g992Dot2(8)	G992.2
				g992Dot3(9)	G992.3
				g992Dot4(10)	G992.4
				g992Dot5(11)	G992.5
				adslAllOnly(12) ADSL ALL ONLY
				adslAndAdsl2(13) G.992.1,G.992.3,T1.413
				"
			DEFVAL { 1 }
			::= { adslLineConfProfileEntry 65539 }
		
		hwAdslLinePvcTable OBJECT-TYPE
			SYNTAX SEQUENCE OF HwAdslLinePvcEntry
			MAX-ACCESS not-accessible
			STATUS current
			DESCRIPTION
				"
				This table include ADSL PVC Information .
				"
			::= { adslMibObjects 65536 }
		
		hwAdslLinePvcEntry OBJECT-TYPE
			SYNTAX HwAdslLinePvcEntry
			MAX-ACCESS not-accessible
			STATUS current
			DESCRIPTION
				"An entry of hwAdslLinePvcTable."
			INDEX { ifIndex, hwAdsllinePvcVpi, hwAdslLinePvcVci }
			::= { hwAdslLinePvcTable 1 }
		
		HwAdslLinePvcEntry ::=
			SEQUENCE { 
				hwAdsllinePvcVpi
					INTEGER,
				hwAdslLinePvcVci
					INTEGER,
				hwAdslLinePvcVlanId
					INTEGER,
				hwAdslLinePvcPriority
					INTEGER,
				hwAdslLinePvcDsBand
					INTEGER,
				hwAdslLinePvcUsBand
					INTEGER,
				hwAdslLinePvcMCastEnable
					INTEGER,
				hwAdslLinePvcIGMPEnable
					INTEGER,
				hwAdslLinePvcIndex
					INTEGER,
				hwAdslLinePvcConnectType
					INTEGER,	
				hwAdslLinePvcRowStatus
					RowStatus
			 }

		hwAdsllinePvcVpi OBJECT-TYPE
			SYNTAX INTEGER (0..255)
			MAX-ACCESS read-only
			STATUS current
			DESCRIPTION
				"The VPI of the adsl line"
			::= { hwAdslLinePvcEntry 1 }
		
		hwAdslLinePvcVci OBJECT-TYPE
			SYNTAX INTEGER (0..511)
			MAX-ACCESS read-only
			STATUS current
			DESCRIPTION
				"The VCI of the adsl line"
			::= { hwAdslLinePvcEntry 2 }
			
		hwAdslLinePvcVlanId OBJECT-TYPE
			SYNTAX INTEGER (1..4000)
			MAX-ACCESS read-write
			STATUS current
			DESCRIPTION
				"The VLAN ID of the adsl line PVC"
			::= { hwAdslLinePvcEntry 3 }
		
		hwAdslLinePvcPriority OBJECT-TYPE
			SYNTAX INTEGER (0..7)
			MAX-ACCESS read-write
			STATUS current
			DESCRIPTION
				"The Priority value of the adsl line PVC"
			DEFVAL { 0 }
			::= { hwAdslLinePvcEntry 4 }
		
		hwAdslLinePvcDsBand OBJECT-TYPE
			SYNTAX INTEGER (0..450)
			MAX-ACCESS read-write
			STATUS current
			DESCRIPTION
				"The down stream band of the adsl line PVC"
			DEFVAL { 0 }
			::= { hwAdslLinePvcEntry 5 }
		
		hwAdslLinePvcUsBand OBJECT-TYPE
			SYNTAX INTEGER (0..450)
			MAX-ACCESS read-write
			STATUS current
			DESCRIPTION
				"The up stream band of the adsl line PVC"
			::= { hwAdslLinePvcEntry 6 }
		
		hwAdslLinePvcMCastEnable OBJECT-TYPE
			SYNTAX INTEGER
				{
				enable(1),
				disable(2)
				}
			MAX-ACCESS read-write
			STATUS current
			DESCRIPTION
				"This object allows the adsl line PVC to support multicast."
			DEFVAL { 2 }
			::= { hwAdslLinePvcEntry 7 }
		
		hwAdslLinePvcIGMPEnable OBJECT-TYPE
			SYNTAX INTEGER
				{
				enable(1),
				disable(2)
				}
			MAX-ACCESS read-write
			STATUS current
			DESCRIPTION
				"This object allows the adsl line PVC to support IGMP."
			DEFVAL { 2 }
			::= { hwAdslLinePvcEntry 8 }
		
		hwAdslLinePvcIndex OBJECT-TYPE
			SYNTAX INTEGER (1..8)
			MAX-ACCESS read-write
			STATUS current
			DESCRIPTION
				"The index of the adsl line PVC"
			::= { hwAdslLinePvcEntry 9 }
		
		hwAdslLinePvcConnectType OBJECT-TYPE
			SYNTAX INTEGER 
				{
				auto(0),
				llc1483B(1),
	                        pppoaLLC(2),
	                        pppoaVcmux(3),
	                        ipoaLLc(4),
	                        ipoaVcmux(5)
				}
			MAX-ACCESS read-only
			STATUS current
			DESCRIPTION
				"The Connected type of the adsl line PVC"
			::= { hwAdslLinePvcEntry 10 }
		
		hwAdslLinePvcRowStatus OBJECT-TYPE
			SYNTAX RowStatus
			MAX-ACCESS read-create
			STATUS current
			DESCRIPTION
				"Row status.Add or delete a table item."
			::= { hwAdslLinePvcEntry 11 }
    ---------------------------------------------------------------------------
     --    adsl extend profile (insert to adslLineTable)
    ---------------------------------------------------------------------------          
	        hwadslLineExtConfProfile OBJECT-TYPE
	             SYNTAX      SnmpAdminString (SIZE (1..32))
	             MAX-ACCESS  read-write
	             STATUS      current
	             DESCRIPTION
	                 "The value of this object identifies the row
	                 in the ADSL Extend Line Configuration Profile Table,
	                 (adslLineExtConfProfileTable), which applies to this
	                 ADSL line, and channels if applicable.
	                 
	                 NULL - indicates that there is no extend line profile 
	                 bound to this port."
	         ::= { adslLineEntry 65536 }	
	         
	        hwadslLineDynamicProfile OBJECT-TYPE
	             SYNTAX      SnmpAdminString (SIZE (1..32))
	             MAX-ACCESS  read-write
	             STATUS      current
	             DESCRIPTION
	                 "The value of this object identifies the row
	                 in the ADSL Dynamic Profile Table,which applies to this
	                 ADSL line, and channels if applicable.
	                 
	                 NULL - indicates that there is no Dynamic profile 
	                 bound to this port."
	         ::= { adslLineEntry 65537 }
		
		hwAdslLineBitAllocationTable OBJECT-TYPE
			SYNTAX SEQUENCE OF HwAdslLineBitAllocationEntry
			MAX-ACCESS not-accessible
			STATUS current
			DESCRIPTION
				"The hwAdslLineBitAllocationTable contains the detailed bit-allocation
				information for the current link. This information can be used to determine 
				whether a given sub-carrier loop has sufficient margin to support ADSL data 
				rates, and possibly to determine whether certain specific types of interfe-
				rence or line attenuation exist.The bit allocation information are only va-
				lid when the ATU-C is in the C-ACTIVE state."
			::= { adslMibObjects 65537 }
		
		hwAdslLineBitAllocationEntry OBJECT-TYPE
			SYNTAX HwAdslLineBitAllocationEntry
			MAX-ACCESS not-accessible
			STATUS current
			DESCRIPTION
				"
				An entry of hwAdslLineBitAllocationTable.
				"
			INDEX { ifIndex }
			::= { hwAdslLineBitAllocationTable 1 }
		
		HwAdslLineBitAllocationEntry ::=
			SEQUENCE { 
				hwAdslLineDownStreamBitsPerFrame
					Integer32,
				hwAdslLineUpStreamBitsPerFrame
					Integer32,
				hwAdslLineDownStreamBitAllocLow
					OCTET STRING,
				hwAdslLineDownStreamBitAllocHigh
					OCTET STRING,
				hwAdslLineUpStreamBitAlloc
					OCTET STRING
			 }

		hwAdslLineDownStreamBitsPerFrame OBJECT-TYPE
			SYNTAX Integer32
			MAX-ACCESS read-only
			STATUS current
			DESCRIPTION
				"
				Number of bits required per frame in the downstream data path for the 
				current configuration.
				"
			::= { hwAdslLineBitAllocationEntry 1 }
		
		hwAdslLineUpStreamBitsPerFrame OBJECT-TYPE
			SYNTAX Integer32
			MAX-ACCESS read-only
			STATUS current
			DESCRIPTION
				"
				Number of bits required per frame in the upstream data path for the 
				current configuration. 
				"
			::= { hwAdslLineBitAllocationEntry 2 }
		
		hwAdslLineDownStreamBitAllocLow OBJECT-TYPE
			SYNTAX OCTET STRING (SIZE (256))
			MAX-ACCESS read-only
			STATUS current
			DESCRIPTION
			"
			when used to Adsl board
				This object contains the first 128 downstream sub-carrier bit allocations 
				(sub-carrier # 1-128). This object is 64 bytes in length, where each byte
				contains 2 sub-carrier values. 
				
				 Byte 1 - 64           Downstream bit allocation (first 128 sub-carriers),  
				                       one byte for two sub-carriers. 
				                       			      
				   1        Bits 4 - 7 # bits in 1st downstream sub-carrier 
				   1        Bits 0 - 3 # bits in 2nd downstream sub-carrier 
				             ...
				   64       Bits 4 - 7 # bits in 127th downstream sub-carrier 
				   64       Bits 0 - 3 # bits in 128th downstream sub-carrier
				
			when used to Adsl2+ board
			        This object contains the first 256 downstream sub-carrier bit allocations 
				(sub-carrier # 1-256). This object is 256 bytes in length, where each byte
				contains 1 sub-carrier values. 
				
				 Byte 1 - 256          Downstream bit allocation (first 256 sub-carriers),  
				                       one byte for one sub-carriers. 
				                       			      
				   1        Bits 0 - 7 # bits in 1st downstream sub-carrier				    
				             ...
				   255      Bits 0 - 7 # bits in 255th downstream sub-carrier 
				   256      Bits 0 - 7 # bits in 256th downstream sub-carrier
			"
			::= { hwAdslLineBitAllocationEntry 3 }
		
		hwAdslLineDownStreamBitAllocHigh OBJECT-TYPE
			SYNTAX OCTET STRING (SIZE (256))
			MAX-ACCESS read-only
			STATUS current
			DESCRIPTION
			"
			when used to Adsl board
				This object contains the second 128 downstream sub-carrier bit allocations 
				(sub-carrier # 129-256). This object is 64 bytes in length, where each byte
				contains 2 sub-carrier values. 
				
				 Byte 1 - 64           Downstream bit allocation (second 128 sub-carriers),  
				                       one byte for two sub-carriers. 
				                      			      
				   1        Bits 4 - 7 # bits in 129th downstream sub-carrier 
				   1        Bits 0 - 3 # bits in 130th downstream sub-carrier 
				             ...
				   64       Bits 4 - 7 # bits in 255th downstream sub-carrier 
				   64       Bits 0 - 3 # bits in 256th downstream sub-carrier

		       when used to Adsl2+ board
			        This object contains the second 256 downstream sub-carrier bit allocations 
				(sub-carrier # 257-512). This object is 256 bytes in length, where each byte
				contains 1 sub-carrier values. 
				
				 Byte 1 - 256          Downstream bit allocation (second 256 sub-carriers),  
				                       one byte for one sub-carriers. 
				                       			      
				   1        Bits 0 - 7 # bits in 1st downstream sub-carrier				    
				             ...
				   255      Bits 0 - 7 # bits in 255th downstream sub-carrier 
				   256      Bits 0 - 7 # bits in 256th downstream sub-carrier
			"				
			::= { hwAdslLineBitAllocationEntry 4 }
		
		hwAdslLineUpStreamBitAlloc OBJECT-TYPE
			SYNTAX OCTET STRING (SIZE (64))
			MAX-ACCESS read-only
			STATUS current
			DESCRIPTION
			"
			when used to Adsl board
				This Object contains 64 upstream sub-carrier bit allocations (sub-carrier # 1-64).
				This Object is 32 bytes in length, where each byte contains 2 sub-carrier values.
				
				  Byte 1-32         	Upstream bit allocation information, total: 32 bytes,
				                        one byte for two sub-carriers.
				
				   1      Bits 7 - 4  # bits in 1st upstream sub-carrier
				   1      Bits 3 - 0  # bits in 2nd upstream sub-carrier
				           ...
				   32     Bits 7 - 4  # bits in 63rd upstream sub-carrier
				   32     Bits 3 - 0  # bits in 64th upstream sub-carrier
					
			when used to Adsl2+ board
			This Object contains 64 upstream sub-carrier bit allocations (sub-carrier # 1-64).
				This Object is 64 bytes in length, where each byte contains 1 sub-carrier values.
				
				  Byte 1-64         	Upstream bit allocation information, total: 64 bytes,
				                        one byte for one sub-carriers.
				
				   1      Bits 7 - 0  # bits in 1st upstream sub-carrier				  
				           ...				   
				   64     Bits 7 - 0  # bits in 64th upstream sub-carrier
				
			"
			::= { hwAdslLineBitAllocationEntry 5 }
		
		hwXdslPortTable OBJECT-TYPE
			SYNTAX SEQUENCE OF HwXdslPortEntry
			MAX-ACCESS not-accessible
			STATUS current
			DESCRIPTION
				"
				This table includes xDSL(e.g. adsl,g.shdsl,vdsl...)port information.
			        "
			::= { adslMibObjects 65538 }
		
		hwXdslPortEntry OBJECT-TYPE
			SYNTAX HwXdslPortEntry
			MAX-ACCESS not-accessible
			STATUS current
			DESCRIPTION
				"
				An entry of hwXdslPortTable.
				"
			INDEX { ifIndex }
			::= { hwXdslPortTable 1 }
		
		HwXdslPortEntry ::=
			SEQUENCE { 
				hwXdslPortMaxMacLearn
					INTEGER,
				hwXdslPortRateMonitorThreshold
				    INTEGER,
				hwXdslPortUpThresholdTxRate
				    Gauge32,
				hwXdslPortDownThresholdTxRate
				    Gauge32,
				hwXdslPortRateMonitorAlarmEnable
				    INTEGER,
				hwXdslPortUpTime
				    Counter32,
				hwXdslPortNTEPowerStatus
				    INTEGER,
				hwXdslPortCurrentUpRate
				    INTEGER ,
				hwXdslPortCurrentDownRate
				    INTEGER ,
				hwXdslPortFarEndRunState 
				    INTEGER,
				hwXdslPortPowerState 
				    INTEGER,
				hwXdslPortUpCnt
				    Unsigned32 ,
			        hwXdslPortUpCntAdminStatus
				    INTEGER ,
				hwXdslPortLastUpTime 
				    PortDateAndTime ,
				hwXdslPortLastDownTime
				    PortDateAndTime ,    
				hwXdslPortClearUpCntTime
     			            PortDateAndTime ,
     			        hwXdslPortRetrainCnt 
     			            Unsigned32 ,
     			        hwXdslPortLastRetrainReason
     			            Unsigned32,
     			        hwXdslPortLoopFlag 	
     			            INTEGER,
     			        hwXdslPortUpThreshold
     			            INTEGER,
     			        hwXdslPortDownThreshold
     			            INTEGER			    
			 }

		hwXdslPortMaxMacLearn OBJECT-TYPE
			SYNTAX INTEGER (0..255)
			MAX-ACCESS read-write
			STATUS current
			DESCRIPTION
				"
				Set Max MAC count on the XDSL port.
				"
			DEFVAL { 255 }
			::= { hwXdslPortEntry 1 }
		
		hwXdslPortRateMonitorThreshold OBJECT-TYPE
			SYNTAX INTEGER (0..100)
			MAX-ACCESS read-write
			STATUS current
			DESCRIPTION
				"Set Port monitoring rate threshold percent. Including upstream and downstream.
				"
			DEFVAL { 0 }
			::= { hwXdslPortEntry 2 }

		hwXdslPortUpThresholdTxRate  OBJECT-TYPE
		      SYNTAX Gauge32
			  UNITS "bps"
		      MAX-ACCESS read-write
		      STATUS current
		      DESCRIPTION
		       "
		        Set Port monitoring upstream rate threshold value.
		       "	
		        DEFVAL { 0 }
		       ::= { hwXdslPortEntry 4 } 
		       
		hwXdslPortDownThresholdTxRate  OBJECT-TYPE
		      SYNTAX Gauge32
			  UNITS "bps"
		      MAX-ACCESS read-write
		      STATUS current
		      DESCRIPTION
		      "
		       Set Port monitoring downstream rate threshold value.
		      "	
		        DEFVAL { 0 }
		       ::= { hwXdslPortEntry 5 }
		             		
		hwXdslPortRateMonitorAlarmEnable  OBJECT-TYPE
		      SYNTAX INTEGER
				{
				enabled(1),
				disabled(2)
				}
		      MAX-ACCESS read-write
		      STATUS current
		      DESCRIPTION
		      "
		       Enables/Disables port rate monitor alarm.
		      "	
		       ::= { hwXdslPortEntry 6 }


                hwXdslPortUpTime OBJECT-TYPE
			SYNTAX Counter32
			MAX-ACCESS read-only
			STATUS current
			DESCRIPTION
				"Up time(UNIT:Second)."
 			::= { hwXdslPortEntry 7 }
 		
 		hwXdslPortNTEPowerStatus OBJECT-TYPE      
		SYNTAX INTEGER
				{
					on(1),
					off(2),
					unknown(3)
				}
			MAX-ACCESS read-only
			STATUS current
		DESCRIPTION
		      "NTE power status "	      
                DEFVAL { 2 }
		      ::= { hwXdslPortEntry 8 }
		hwXdslPortCurrentUpRate  OBJECT-TYPE
		      SYNTAX INTEGER (0..30000)
		      MAX-ACCESS accessible-for-notify
		      STATUS current
		      DESCRIPTION
		       "
		        Xdsl Port Current Upstream Value.
		       "	
		        DEFVAL { 0 }
		       ::= { hwXdslPortEntry 500 }
		hwXdslPortCurrentDownRate  OBJECT-TYPE
		      SYNTAX INTEGER (0..30000)
		      MAX-ACCESS accessible-for-notify
		      STATUS current
		      DESCRIPTION
		      "
		       Xdsl Port Current Downstream Value.
		      "	
		        DEFVAL { 0 }
		       ::= { hwXdslPortEntry 501 }      		
		hwXdslPortFarEndRunState OBJECT-TYPE      
		SYNTAX INTEGER
				{
					unknown(1),
					noModem(2),
					handshake(3),
					showtime(4)
					
				}
			MAX-ACCESS read-only
			STATUS current
		DESCRIPTION
		      "
		       Xdsl port far end Run state.
		      "	      
        DEFVAL { 1 }
		      ::= { hwXdslPortEntry 600 }
	        hwXdslPortPowerState OBJECT-TYPE      
		SYNTAX INTEGER
				{
				    L0(1),
				    L2(2),
				    L3(3)				
				}
		      MAX-ACCESS read-only
		      STATUS current
		      DESCRIPTION
		      "
		        Xdsl port power state.
		      "	      
                      DEFVAL { 1 }
		      ::= { hwXdslPortEntry 601 }  
     			          
        hwXdslPortUpCnt OBJECT-TYPE
	        SYNTAX Unsigned32
	        MAX-ACCESS read-only
	        STATUS current
	        DESCRIPTION
	            " 
	            The up counts of Xdsl port
	            "   
	        ::= { hwXdslPortEntry 700 }  	    
		
	hwXdslPortUpCntAdminStatus   OBJECT-TYPE
	 	    SYNTAX INTEGER
	           {
                      reset(0)      -- reset line up count
                   }
	        MAX-ACCESS read-write
	        STATUS current
	        DESCRIPTION
	            " 
	            Admin the up counts of Xdsl port
	            "   
	        ::= { hwXdslPortEntry 701 } 
	                
	hwXdslPortLastUpTime OBJECT-TYPE
			SYNTAX PortDateAndTime
			MAX-ACCESS read-only
			STATUS current
			DESCRIPTION
			        "
			        Last Up time of a Xdsl port.
			        "
			::= { hwXdslPortEntry 702 }   
			     
	hwXdslPortLastDownTime OBJECT-TYPE
			SYNTAX PortDateAndTime
			MAX-ACCESS read-only
			STATUS current
			DESCRIPTION
			        "
			        Last Down time of a Xdsl port.
			        "
			::= { hwXdslPortEntry 703 }  
	           
        hwXdslPortClearUpCntTime OBJECT-TYPE
			SYNTAX PortDateAndTime
			MAX-ACCESS read-only
			STATUS current
			DESCRIPTION
				" 
				The time when up counts of a Xdsl port is cleared.
				"
			::= { hwXdslPortEntry 704 }
       
       hwXdslPortRetrainCnt  OBJECT-TYPE
			SYNTAX Unsigned32
			MAX-ACCESS read-only
			STATUS current
			DESCRIPTION
				" 
				The retrain counts of Xdsl Line.
				"
			::= { hwXdslPortEntry 705 }
	
       hwXdslPortLastRetrainReason OBJECT-TYPE
			SYNTAX Unsigned32
			MAX-ACCESS read-only
			STATUS current
			DESCRIPTION
				" 
				The last retrain reson of Xdsl Line, coded as bit mask. 
				Only one bit can be set valid, all bits set valid means invalid retrain reason.
				"
			::= { hwXdslPortEntry 706 }
			
	hwXdslPortLoopFlag OBJECT-TYPE
		 SYNTAX INTEGER
			{
				FALSE(0),
				TRUE(1)
			}	
			MAX-ACCESS read-only
			STATUS current
			DESCRIPTION
			"Loop flag.
				
				FALSE(0): no loop
				TRUE (1): loop
			"
			::= { hwXdslPortEntry 800 }		      

		hwXdslPortUpThreshold OBJECT-TYPE
			SYNTAX INTEGER (0..100)
			MAX-ACCESS read-write
			STATUS current
			DESCRIPTION
				"Set Port monitoring upstream rate threshold percent value.
				"
			DEFVAL { 0 }
			::= { hwXdslPortEntry 810 }

		hwXdslPortDownThreshold OBJECT-TYPE
			SYNTAX INTEGER (0..100)
			MAX-ACCESS read-write
			STATUS current
			DESCRIPTION
				"Set Port monitoring downstream rate threshold percent value.
				"
			DEFVAL { 0 }
                        ::= { hwXdslPortEntry 811 }


--
-- hwAdslLinePreActParaTable
--		
		hwAdslLinePreActParaTable OBJECT-TYPE
			SYNTAX SEQUENCE OF HwAdslLinePreActParaEntry
			MAX-ACCESS not-accessible
			STATUS current
			DESCRIPTION
				"This table provides one row for each ADSL PORT.
				Each row contains the preactived Parameters,
				including:hwAdslAtucPrevSnrMgn,hwAdslAturPrevSnrMgn,
				hwAdslAtucPrevAttainableRate and hwAdslAturPrevAttainableRate
				 "
			::= { adslMibObjects 65539 }
		
		hwAdslLinePreActParaEntry OBJECT-TYPE
			SYNTAX HwAdslLinePreActParaEntry
			MAX-ACCESS not-accessible
			STATUS current
			DESCRIPTION
				"An entry in the hwAdslLinePreActParaTable"
			INDEX { ifIndex }
			::= { hwAdslLinePreActParaTable 1 }
		
		HwAdslLinePreActParaEntry ::=
			SEQUENCE { 
				hwAdslAtucPrevSnrMgn
					Integer32,
				hwAdslAturPrevSnrMgn
					Integer32,
				hwAdslAtucPrevAttainableRate
					Unsigned32,
				hwAdslAturPrevAttainableRate
					Unsigned32,
				hwAdslAtucPreAtn
					Gauge32,
				hwAdslAturPreAtn
					Gauge32,
			        hwAdslPreActiveTime
			                DateAndTime
			 }

		hwAdslAtucPrevSnrMgn OBJECT-TYPE
			SYNTAX Integer32
			UNITS "tenth dB"
			MAX-ACCESS read-only
			STATUS current
			DESCRIPTION
				" Noise Margin as seen by this ATU-C at the 
				time of the last adslAtucRateChangeTrap event. "
			::= { hwAdslLinePreActParaEntry 1 }
		
		hwAdslAturPrevSnrMgn OBJECT-TYPE
			SYNTAX Integer32
			UNITS "tenth dB"
			MAX-ACCESS read-only
			STATUS current
			DESCRIPTION
				" Noise Margin as seen by this ATU-R at 
				the time of the last adslAtucRateChangeTrap event. "
			::= { hwAdslLinePreActParaEntry 2 }
		
		hwAdslAtucPrevAttainableRate OBJECT-TYPE
			SYNTAX Unsigned32
			UNITS "bps"
			MAX-ACCESS read-only
			STATUS current
			DESCRIPTION
				"Indicates the maximum attainable data rate 
				by the ATU-C at the time of the last 
				adslAtucRateChangeTrap event."
			::= { hwAdslLinePreActParaEntry 3 }
		
		hwAdslAturPrevAttainableRate OBJECT-TYPE
			SYNTAX Unsigned32
			UNITS "bps"
			MAX-ACCESS read-only
			STATUS current
			DESCRIPTION
				"Indicates the maximum attainable data rate 
				by the ATU-R at the time of the last 
				adslAtucRateChangeTrap event."
			::= { hwAdslLinePreActParaEntry 4 }
		
		hwAdslAtucPreAtn OBJECT-TYPE
			SYNTAX Gauge32
			UNITS "tenth dB"
			MAX-ACCESS read-only
			STATUS current
			DESCRIPTION
				"Measured difference in the total power 
				transmitted as seen by this ATU-C at the time 
				of the last adslAtucRateChangeTrap event. in tenth dB"
			::= { hwAdslLinePreActParaEntry 5 }
		
		hwAdslAturPreAtn OBJECT-TYPE
			SYNTAX Gauge32
			UNITS "tenth dB"
			MAX-ACCESS read-only
			STATUS current
			DESCRIPTION
				"Measured difference in the total power 
				transmitted as seen by this ATU-R at the time of the 
				last adslAtucRateChangeTrap event. in tenth dB"
			::= { hwAdslLinePreActParaEntry 6 }

       hwAdslPreActiveTime OBJECT-TYPE
                        SYNTAX      DateAndTime
                        MAX-ACCESS  read-only
                        STATUS      current
			DESCRIPTION
				"
				The last time at that the port was activated.
				"
			::= { hwAdslLinePreActParaEntry 7 }	

    ---------------------------------------------------------------------------
    -- hwPortThreePriorityTable
    ---------------------------------------------------------------------------    
        hwPortThreePriorityTable OBJECT-TYPE
		    SYNTAX SEQUENCE OF HwPortThreePriorityEntry
		    MAX-ACCESS not-accessible
		    STATUS obsolete
		    DESCRIPTION
		    	"
			    Adsl port three priority table.
			    "
		    ::= { adslMibObjects 65540 }
	
	    hwPortThreePriorityEntry OBJECT-TYPE
		    SYNTAX HwPortThreePriorityEntry
		    MAX-ACCESS not-accessible
		    STATUS obsolete
		    DESCRIPTION
			    "
			    Adsl port three priority table.
			    "
		    INDEX { ifIndex }
		    ::= { hwPortThreePriorityTable 1 }
	
	    HwPortThreePriorityEntry ::=
		    SEQUENCE
    		    {
	    		    hwPortThreePriorityEnable    INTEGER
		        }
		 
	    hwPortThreePriorityEnable OBJECT-TYPE
		    SYNTAX INTEGER
		        {
		            enable(1),
		            disable(2)
		        }
		    MAX-ACCESS read-write
		    STATUS obsolete
		    DESCRIPTION
			    "     
			    Three Priority status of the interface.
			    "
		    ::= { hwPortThreePriorityEntry 1 }    
		    
     --------------------------------------------------------
     -- hwSlotMacMaxNoLimitTable
     --------------------------------------------------------
     hwSlotMacMaxNoLimitTable OBJECT-TYPE
		    SYNTAX SEQUENCE OF HwSlotMacMaxNoLimitEntry
		    MAX-ACCESS not-accessible
		    STATUS obsolete
		    DESCRIPTION
		    	"
			    Max mac learning no limit table.
			    "
		    ::= { adslMibObjects 65541 }
	
	    hwSlotMacMaxNoLimitEntry OBJECT-TYPE
		    SYNTAX HwSlotMacMaxNoLimitEntry
		    MAX-ACCESS not-accessible
		    STATUS obsolete
		    DESCRIPTION
			    "
			    Max mac learning no limit table.
			    "
		    INDEX { hwFrameIndex, hwSlotIndex }
		    ::= { hwSlotMacMaxNoLimitTable 1 }
	
	    HwSlotMacMaxNoLimitEntry ::=
		    SEQUENCE
    		    {
	    		    hwSlotMacMaxNoLimitEnable    INTEGER
		        }
		 
	    hwSlotMacMaxNoLimitEnable OBJECT-TYPE
		    SYNTAX INTEGER
		        {
		            enable(1),
		            disable(2)
		        }
		    MAX-ACCESS read-write
		    STATUS obsolete
		    DESCRIPTION
			    "     
			    enable:  Don't limit the max NO. of learning mac addresses in the slot
			    disable: limit the max NO. of learning mac addresses in the slot
			    "
		    ::= { hwSlotMacMaxNoLimitEntry 1 } 

--
--  hwXdslPortStateStatisticTable
--
                hwXdslPortStateStatisticTable OBJECT-TYPE
			SYNTAX SEQUENCE OF HwXdslPortStateStatisticEntry
			MAX-ACCESS not-accessible
			STATUS current
			DESCRIPTION
				"
				XDSL port state staticstic table.
				"
			::= { adslMibObjects 65542 }
		
		hwXdslPortStateStatisticEntry OBJECT-TYPE
			SYNTAX HwXdslPortStateStatisticEntry
			MAX-ACCESS not-accessible
			STATUS current
			DESCRIPTION
				"An entry in the hwXdslPortStateStatisticTable"
			INDEX {        
			      ifType,
			      hwFrameIndex,
			      hwSlotIndex 
			      }
			::= { hwXdslPortStateStatisticTable 1 }
		
		HwXdslPortStateStatisticEntry ::=
			SEQUENCE{
				hwXdslPortStatePortNumber
					Unsigned32,
				hwXdslPortStateBitmapList
					OCTET STRING,
				hwXdslTotalOfActivatedPorts
					Unsigned32,
				hwXdslTotalOfDeactivatedPorts
					Unsigned32,	
				hwXdslTotalOfActivatingPorts
					Unsigned32,
				hwXdslTotalOfTestingPorts
					Unsigned32,										
				hwXdslTotalOfBlockedPorts
					Unsigned32,
				hwXdslTotalOfLocalLoopbackPorts
					Unsigned32,					
				hwXdslTotalOfRemoteLoopbackPorts
					Unsigned32, 
				hwXdslTotalOfFailedPorts
					Unsigned32,									
				hwXdslTotalOfUnknownPorts
					Unsigned32
				    }

		hwXdslPortStatePortNumber OBJECT-TYPE
			SYNTAX Unsigned32
			MAX-ACCESS read-only
			STATUS current
			DESCRIPTION   
				" 
				This Object is Port Number of One Slot;
				"
			::= { hwXdslPortStateStatisticEntry 1 }
			
		hwXdslPortStateBitmapList OBJECT-TYPE
			SYNTAX OCTET STRING 
			MAX-ACCESS read-only
			STATUS current
			DESCRIPTION
				"
				The type of port status:
				 2  failed;
				 8  testing;
				 9  activated;
				10  activating; 
				11  deactivated;
				18  localloopback;
				19  remoteloopback;
				20  blocked;  
				37  utopialoopback;
				38  afeloopback; 
				39  hybridloopback; 
				255 unknown;
				hwXdslPortStateBitmapList describes the states of all ports. 
				every byte describe the current state of every port.
				The length is equal to the value of the hwXdslPortStatePortNumber.
				"
			::= { hwXdslPortStateStatisticEntry 2 }
			
		hwXdslTotalOfActivatedPorts OBJECT-TYPE
			SYNTAX Unsigned32
			MAX-ACCESS read-only
			STATUS current
			DESCRIPTION
				" 
				The total of the activated ports.
				"
			::= { hwXdslPortStateStatisticEntry 3 }
		
		hwXdslTotalOfDeactivatedPorts OBJECT-TYPE
			SYNTAX Unsigned32			
			MAX-ACCESS read-only
			STATUS current
			DESCRIPTION
				"
				The total of the deactivated ports.
				"
			::= { hwXdslPortStateStatisticEntry 4 }
		
		hwXdslTotalOfActivatingPorts OBJECT-TYPE
			SYNTAX Unsigned32			
			MAX-ACCESS read-only
			STATUS current
			DESCRIPTION
				"
				The total of the activating ports.
				"
			::= { hwXdslPortStateStatisticEntry 5 }
			
		hwXdslTotalOfTestingPorts OBJECT-TYPE
			SYNTAX Unsigned32			
			MAX-ACCESS read-only
			STATUS current
			DESCRIPTION
				"
				The total of the Testing ports.
				"
			::= { hwXdslPortStateStatisticEntry 6 }				
		
		hwXdslTotalOfBlockedPorts OBJECT-TYPE
			SYNTAX Unsigned32			
			MAX-ACCESS read-only
			STATUS current
			DESCRIPTION
				"
				The total of the blocked ports.
				"
			::= { hwXdslPortStateStatisticEntry 7 }
		
		hwXdslTotalOfLocalLoopbackPorts OBJECT-TYPE
			SYNTAX Unsigned32			
			MAX-ACCESS read-only
			STATUS current
			DESCRIPTION
				"
				The total of the testing ports.
				"
			::= { hwXdslPortStateStatisticEntry 8 }
		
		hwXdslTotalOfRemoteLoopbackPorts OBJECT-TYPE
			SYNTAX Unsigned32			
			MAX-ACCESS read-only
			STATUS current
			DESCRIPTION
				"
				The total of the testing ports.
				"
			::= { hwXdslPortStateStatisticEntry 9 }
			
		hwXdslTotalOfFailedPorts OBJECT-TYPE
			SYNTAX Unsigned32			
			MAX-ACCESS read-only
			STATUS current
			DESCRIPTION
				"
				The total of the failed ports.
				"
			::= { hwXdslPortStateStatisticEntry 10 }
		
		hwXdslTotalOfUnknownPorts OBJECT-TYPE
			SYNTAX Unsigned32			
			MAX-ACCESS read-only
			STATUS current
			DESCRIPTION
				"
				The total of the testing ports.
				"
			::= { hwXdslPortStateStatisticEntry 11 }									               
			

    ---------------------------------------------------------------------------
    --    adsl line extending table: hwadslLineExtConfProfileTable 
    ---------------------------------------------------------------------------        
		hwadslLineExtConfProfileTable OBJECT-TYPE
			SYNTAX SEQUENCE OF HwadslLineExtConfProfileEntry
			MAX-ACCESS not-accessible
			STATUS current
			DESCRIPTION
				"This table contains information on the ADSL extend line
                 configuration.  One entry in this table reflects a
                 extend line profile defined by a manager which can be used to
                 configure the ADSL line. "
			::= { adslMibObjects 65543 }
		
		hwadslLineExtConfProfileEntry OBJECT-TYPE
			SYNTAX HwadslLineExtConfProfileEntry
			MAX-ACCESS not-accessible
			STATUS current
			DESCRIPTION
				"An entry in the hwadslLineExtConfProfileTable"
			INDEX {IMPLIED hwadslLineExtConfProfileName}
			::= { hwadslLineExtConfProfileTable 1 }
		
		HwadslLineExtConfProfileEntry ::=
			SEQUENCE { 
				hwadslLineExtConfProfileName
					SnmpAdminString,
				hwadslLineDisableToneSection1Begin	
					INTEGER,
				hwadslLineDisableToneSection1End	
					INTEGER,
				hwadslLineDisableToneSection1Flag	
					INTEGER,	
				hwadslLineDisableToneSection2Begin	
					INTEGER,
				hwadslLineDisableToneSection2End	
					INTEGER,
				hwadslLineDisableToneSection2Flag	
					INTEGER,	
				hwadslLineDisableToneSection3Begin	
					INTEGER,
				hwadslLineDisableToneSection3End	
					INTEGER,
				hwadslLineDisableToneSection3Flag	
					INTEGER,	
				hwadslLineDisableToneSection4Begin	
					INTEGER,
				hwadslLineDisableToneSection4End	
					INTEGER,
				hwadslLineDisableToneSection4Flag	
					INTEGER,	
				hwadsl2ChConfProfMinProtectionDs
					HWADSLSYMBOLPROTECTION,
				hwadsl2ChConfProfMinProtectionUs
					HWADSLSYMBOLPROTECTION,	
				hwAdslExtDsMinTrainSnrMgn
			                INTEGER,                 
				hwAdslExtUsMinTrainSnrMgn   
			                INTEGER,
				hwAdslExtDsMaxPsd	       	
					INTEGER,
				hwadsl2TSSiPsdMaskDs
				        Adsl2PsdMaskDs,	
			        hwadsl2TranMissionStardardMask	
					Unsigned32,	
		                hwadsl2TransMissionAnnexMask 
					Unsigned32,
				hwadsl2TransMissionAnnexMScope	
				        HWADSL2ANNEXMSCOPE,
				hwadsl2L2ModeState
				        INTEGER,
				hwadsl2L2ModeMinDataRate
				        INTEGER,
				hwadsl2L2ModeMaxDataRate
				        INTEGER,
				hwadsl2L2ModePayloadRateThreshold
				        INTEGER,
				hwadsl2L2ModeGuardTime
				        INTEGER,
				hwadsl2L2ModeIntervalTime
				        INTEGER,				
				hwadsl2L2ModeIntervalPowerValue        
				        INTEGER,
                                hwadsl2L2ModeTotalPowerValue				        
				        INTEGER,
		                hwadslExtUsPhyRcontrol
		                    INTEGER,
		                hwadslExtUsINPmax
		                    Adsl2SymbolProtection,
		                hwadslExtUsMinRtxRatio
		                    INTEGER,
		                hwadslExtUsMinRSoverhead
		                    INTEGER,
		                hwadslExtDsPhyRcontrol
		                    INTEGER,
		                hwadslExtDsINPmax
		                    Adsl2SymbolProtection,
		                hwadslExtDsMinRtxRatio
		                    INTEGER,
		                hwadslExtDsMinRSoverhead
		                    INTEGER,
				hwadsl2TSSiPsdMaskUs
				        Adsl2PsdMaskUs,       
				hwadslLineExtConfProfileRowStatus
					RowStatus

			 }

		hwadslLineExtConfProfileName OBJECT-TYPE
	                 SYNTAX          SnmpAdminString (SIZE (1..32))
	                 MAX-ACCESS      read-create
	                 STATUS          current
	                 DESCRIPTION
	                 "This object is used by the hwadslLineExtConfProfileTable
	                 in order to identify a row of this table."
	         	 ::= { hwadslLineExtConfProfileEntry 1 }
		
		hwadslLineDisableToneSection1Begin OBJECT-TYPE
			SYNTAX INTEGER(0..511)
			MAX-ACCESS read-create
			STATUS current
			DESCRIPTION
			"The begin index of section1."
			::= { hwadslLineExtConfProfileEntry 2 }
		
		hwadslLineDisableToneSection1End OBJECT-TYPE
			SYNTAX INTEGER(0..511)
			MAX-ACCESS read-create
			STATUS current
			DESCRIPTION
			"The end index of section1."
			::= { hwadslLineExtConfProfileEntry 3 }
			
		hwadslLineDisableToneSection1Flag OBJECT-TYPE
			SYNTAX INTEGER {
			  enabled(1),
			  disabled(2)
			}
			MAX-ACCESS read-create
			STATUS current
			DESCRIPTION
			"The enable flag of section1."
			::= { hwadslLineExtConfProfileEntry 4 }
			
		hwadslLineDisableToneSection2Begin OBJECT-TYPE
			SYNTAX INTEGER(0..511)
			MAX-ACCESS read-create
			STATUS current
			DESCRIPTION
			"The begin index of section2."
			::= { hwadslLineExtConfProfileEntry 5 }
		
		hwadslLineDisableToneSection2End OBJECT-TYPE
			SYNTAX INTEGER(0..511)
			MAX-ACCESS read-create
			STATUS current
			DESCRIPTION
			"The end index of section2."
			::= { hwadslLineExtConfProfileEntry 6 }
			
		hwadslLineDisableToneSection2Flag OBJECT-TYPE
			SYNTAX INTEGER {
			  enabled(1),
			  disabled(2)
			}
			MAX-ACCESS read-create
			STATUS current
			DESCRIPTION
			"The enable flag of section2."
			::= { hwadslLineExtConfProfileEntry 7 }
				
		hwadslLineDisableToneSection3Begin OBJECT-TYPE
			SYNTAX INTEGER(0..511)
			MAX-ACCESS read-create
			STATUS current
			DESCRIPTION
			"The begin index of section3."
			::= { hwadslLineExtConfProfileEntry 8 }
		
		hwadslLineDisableToneSection3End OBJECT-TYPE
			SYNTAX INTEGER(0..511)
			MAX-ACCESS read-create
			STATUS current
			DESCRIPTION
			"The end index of section3."
			::= { hwadslLineExtConfProfileEntry 9 }

		hwadslLineDisableToneSection3Flag OBJECT-TYPE
			SYNTAX INTEGER {
			  enabled(1),
			  disabled(2)
			}
			MAX-ACCESS read-create
			STATUS current
			DESCRIPTION
			"The enable flag of the third section."
			::= { hwadslLineExtConfProfileEntry 10 }
			
		hwadslLineDisableToneSection4Begin OBJECT-TYPE
			SYNTAX INTEGER(0..511)
			MAX-ACCESS read-create
			STATUS current
			DESCRIPTION
			"The begin index of the fourth section."
			::= { hwadslLineExtConfProfileEntry 11 }
		
		hwadslLineDisableToneSection4End OBJECT-TYPE
			SYNTAX INTEGER(0..511)
			MAX-ACCESS read-create
			STATUS current
			DESCRIPTION
			"The end index of the fourth section."
			::= { hwadslLineExtConfProfileEntry 12 }
		
		hwadslLineDisableToneSection4Flag OBJECT-TYPE
			SYNTAX INTEGER {
			  enabled(1),
			  disabled(2)
			}
			MAX-ACCESS read-create
			STATUS current
			DESCRIPTION
			"The enable flag of the fourth section."
			::= { hwadslLineExtConfProfileEntry 13 }
			
		hwadsl2ChConfProfMinProtectionDs  OBJECT-TYPE
		     SYNTAX      HWADSLSYMBOLPROTECTION
		     MAX-ACCESS  read-write
		     STATUS      current
		     DESCRIPTION
		     "Minimum Impulse Noise Protection on Downstream direction. The 
		     minimum impulse noise protection for the bearer channel, expressed
		     in symbols. The parameter can take the following values:
		       noProtection(0),
		       halfSymbol(1),
		       singleSymbol(2),
		       twoSymbols(4),
		       threeSymbols(6),
		       fourSymbols(8),
		       fiveSymbols(10),
		       sixSymbols(12),
		       sevenSymbols(14),
		       eightSymbols(16),
		       nineSymbols(18),
		       tenSymbols(20),
		       elevenSymbols(22),
		       twelveSymbols(24),
		       thirteenSymbols(26),
		       fourteenSymbols(28),
		       fifteenSymbols(30),
		       sixteenSymbols(32),
		       null(65535)
		     
		     The value multiply 1/2 is the real value of Noise Protection values.
		     
		     "
		     ::= { hwadslLineExtConfProfileEntry 14 }
		
		hwadsl2ChConfProfMinProtectionUs  OBJECT-TYPE
		     SYNTAX      HWADSLSYMBOLPROTECTION
		     MAX-ACCESS  read-write
		     STATUS      current
		     DESCRIPTION
		     " 
		     Minimum Impulse Noise Protection on Upstream direction. The 
		     minimum impulse noise protection for the bearer channel, expressed
		     in symbols. The parameter can take the following values:
		       noProtection(0),
		       halfSymbol(1),
		       singleSymbol(2),
		       twoSymbols(4),
		       threeSymbols(6),
		       fourSymbols(8),
		       fiveSymbols(10),
		       sixSymbols(12),
		       sevenSymbols(14),
		       eightSymbols(16),
		       nineSymbols(18),
		       tenSymbols(20),
		       elevenSymbols(22),
		       twelveSymbols(24),
		       thirteenSymbols(26),
		       fourteenSymbols(28),
		       fifteenSymbols(30),
		       sixteenSymbols(32),
		     null(65535),
		     
		     The value multiply 1/2 is the real value of Noise Protection values.
		     "
		     ::= { hwadslLineExtConfProfileEntry 15 }
		     
		hwAdslExtDsMinTrainSnrMgn OBJECT-TYPE
		     SYNTAX      INTEGER  (0..310)
		     UNITS       "tenth dB"
		     MAX-ACCESS  read-create
		     STATUS      current
		     DESCRIPTION
		     "Maximum Tranning Margin in downstream"
		     DEFVAL { 30 }
		     ::= { hwadslLineExtConfProfileEntry 16 }		              
		              
		hwAdslExtUsMinTrainSnrMgn OBJECT-TYPE
		     SYNTAX      INTEGER  (0..310)
		     UNITS       "tenth dB"
		     MAX-ACCESS  read-create
		     STATUS      current
		     DESCRIPTION
		     "Maximum Tranning Margin in upstream"
		     DEFVAL { 30 }
		     ::= { hwadslLineExtConfProfileEntry 17 }		              
		              
		hwAdslExtDsMaxPsd  OBJECT-TYPE
		     SYNTAX      INTEGER  (-52..-40)
		     UNITS       "dBm/Hz"
		     MAX-ACCESS  read-create
		     STATUS      current
		     DESCRIPTION
		     "Maximum PSD margin in downstream"
		     DEFVAL { -40 }
		     ::= { hwadslLineExtConfProfileEntry 18 }
			
		hwadsl2TSSiPsdMaskDs   OBJECT-TYPE
  		    SYNTAX      Adsl2PsdMaskDs
  		    MAX-ACCESS  read-write
  		    STATUS      current
 		     DESCRIPTION
 		       "The downstream PSD mask applicable at the U-C2 reference
 		        point.
 		       This parameter is used only for G992.3 or G992.5 and it may impose PSD
 		       restrictions (breakpoints) in addition to the Limit PSD mask
 		       defined in G992.5.
 		       This is a string of 32 pairs of values in the following
  		      structure:
 		       Octets 0+1 - Index of 1st sub-carrier used in the context
		                     of a first breakpoint.
  		      Octet 2    - The PSD reduction for the sub-carrier indicated in
  		                   octets 0 and 1.
  		      Octets 3-5 - Same, for a 2nd breakpoint.
  		      Octets 6-8 - Same, for a 3rd breakpoint.
  		      This architecture continues until octets 94-95, which are
  		      associated with a 32nd breakpoint.
   		     Each subcarrier index is an unsigned number in the range 1 and
   		     NSCds.  Each PSD reduction value is in the range 0 (0dBm/Hz) to
		    255 (-127.5dBm/Hz) with steps of 0.5dBm/Hz.  Valid values are
       		in the range 0 to 190 (0 to -95dBm/Hz).
       		When the number of breakpoints is less than 32, all remaining
       		octets are set to the value 0.  Note that the content of this
       		object should be correlated with the sub-carriers mask and with
       		the RFI setup. "
      		REFERENCE    "ITU-T G.997.1, paragraph 7.3.1.2"
        		::= { hwadslLineExtConfProfileEntry 19 }   
		 
		hwadsl2TranMissionStardardMask OBJECT-TYPE
			SYNTAX Unsigned32
			MAX-ACCESS read-write
			STATUS current
			DESCRIPTION
			"
			The tranmission stardard mask . 
			The Mask bit and the corresponding Tranmission Standard:
			0x 1       1       1       1       1       1   
			 ETSI  T1.413  G992.5  G992.3  G992.2  G992.1
			The Default BitMask: 0X1E .      
     		"
			::= { hwadslLineExtConfProfileEntry 20 }
			 
			
		hwadsl2TransMissionAnnexMask OBJECT-TYPE
			SYNTAX Unsigned32
			MAX-ACCESS read-write
			STATUS current
			DESCRIPTION
			"
			The transMission annex Mask.  
			The Mask bit and the corresponding Tranmission Annex:
			0x   1           1       1           1         
			Annex .M  Annex .L  Annex .B  Annex .A				
			The Default BitMask:  0X0E . 
			"
			::= { hwadslLineExtConfProfileEntry 21 }
			
		hwadsl2TransMissionAnnexMScope  OBJECT-TYPE
		     SYNTAX      HWADSL2ANNEXMSCOPE
		     MAX-ACCESS  read-create
		     STATUS      current
		     DESCRIPTION
		     " 
		     Annex M expand scope:
		     1-Tone Index(7~32)                                                           
                     2-Tone Index(7~36)                                                           
                     3-Tone Index(7~40)                                                           
                     4-Tone Index(7~44)                                                             
                     5-Tone Index(7~48)
                     6-Tone Index(7~52)  
                     7-Tone Index(7~56)                                                           
                     8-Tone Index(7~60)                                                           
                     9-Tone Index(7~64) 
		     "
		     ::= { hwadslLineExtConfProfileEntry 22 }
		
		hwadsl2L2ModeState OBJECT-TYPE
			SYNTAX INTEGER {
			  disabled(1),
			  enabled(2),
			  forced(3)
			}
			MAX-ACCESS read-create
			STATUS current
			DESCRIPTION
			"
			The state of L2 power management mode.
			"
			  DEFVAL { 1 }
			 ::= { hwadslLineExtConfProfileEntry 23 }
			
		hwadsl2L2ModeMinDataRate  OBJECT-TYPE
		      SYNTAX INTEGER (128..16384)
		      UNITS "bps"
		      MAX-ACCESS read-create
		      STATUS current
		      DESCRIPTION
		      "
		      Minimum Data Rate in L2 Mode.
		      "	
		        DEFVAL { 256 }
		       ::= { hwadslLineExtConfProfileEntry 24 } 
		       
	        hwadsl2L2ModeMaxDataRate  OBJECT-TYPE
		      SYNTAX INTEGER (128..16384)
		      UNITS "bps"
		      MAX-ACCESS read-create
		      STATUS current
		      DESCRIPTION
		      "
		      Maximum Data Rate in L2 Mode.
		      "	
		        DEFVAL { 1024 }
		       ::= { hwadslLineExtConfProfileEntry 25 }
		       
		hwadsl2L2ModePayloadRateThreshold  OBJECT-TYPE
		      SYNTAX INTEGER (128..16384)
		      UNITS "bps"
		      MAX-ACCESS read-create
		      STATUS current
		      DESCRIPTION
		      "
		      Threshold for the Payload Rate Ratio.
		      "	
		        DEFVAL { 128 }
		       ::= { hwadslLineExtConfProfileEntry 26 }
		
		hwadsl2L2ModeGuardTime  OBJECT-TYPE
		      SYNTAX INTEGER (0..255)
		      UNITS "s"
		      MAX-ACCESS read-create
		      STATUS current
		      DESCRIPTION
		      "
		      Guard Time before entering L2 Mode.
		      "	
		        DEFVAL { 255 }
		       ::= { hwadslLineExtConfProfileEntry 27 }
		       
		hwadsl2L2ModeIntervalTime  OBJECT-TYPE
		      SYNTAX INTEGER (0..255)
		      UNITS "s"
		      MAX-ACCESS read-create
		      STATUS current
		      DESCRIPTION
		      "
		      The minimum interval between two records of L2 mode.
		      "
		        DEFVAL { 30 }
		       ::= { hwadslLineExtConfProfileEntry 28 }

		hwadsl2L2ModeIntervalPowerValue  OBJECT-TYPE
		        SYNTAX INTEGER (0..31)
		        UNITS "db"
		        MAX-ACCESS read-create
		        STATUS current
		        DESCRIPTION
		        "
		        Maximum aggregate transmit power reduction per L2 request or L2 power trim.
		        "
		          DEFVAL { 3 }
		         ::= { hwadslLineExtConfProfileEntry 29 }

		hwadsl2L2ModeTotalPowerValue  OBJECT-TYPE
		        SYNTAX INTEGER (0..31)
		        UNITS "db"
		        MAX-ACCESS read-create
		        STATUS current
		        DESCRIPTION
		        "
		        Total maximum aggregate transmit power reduction in L2.
		        "
		          DEFVAL { 9 }
		         ::= { hwadslLineExtConfProfileEntry 30 }
		         
    	hwadslExtUsPhyRcontrol OBJECT-TYPE
            SYNTAX      INTEGER
            {
                enable(1),
                disable(2)
            }
            MAX-ACCESS  read-write
            STATUS      current
            DESCRIPTION
                "To enable or disable the PHY-R function on upstream direction."
            DEFVAL { 2 }
            ::= { hwadslLineExtConfProfileEntry 31 }
    
        hwadslExtUsINPmax OBJECT-TYPE
            SYNTAX      Adsl2SymbolProtection
            UNITS       "DMT Symbol"
            MAX-ACCESS  read-write
            STATUS      current
            DESCRIPTION
                "
                Maximum Impulse Noise Protection on upstream direction.
                The parameter can take the following values:
                noProtection(1),
                halfSymbol(2),
                singleSymbol(3),
                twoSymbols(4),
                threeSymbols(5),
                fourSymbols(6),
                fiveSymbols(7),
                sixSymbols(8),
                sevenSymbols(9),
                eightSymbols(10),
                nineSymbols(11),
                tenSymbols(12),
                elevenSymbols(13),
                twelveSymbols(14),
                thirteeSymbols(15),
                fourteenSymbols(16),
                fifteenSymbols(17),
                sixteenSymbols(18)
                
                The value multiply 1/2 is the real value of Noise Protection values.
    		    "
    		DEFVAL { 1 }
            ::= { hwadslLineExtConfProfileEntry 32 }
    
        hwadslExtUsMinRtxRatio OBJECT-TYPE
            SYNTAX      INTEGER (0..255)
            UNITS       "1/256"
            MAX-ACCESS  read-write
            STATUS      current
            DESCRIPTION
                "Minimum rtxratio on upstream direction."
            DEFVAL { 0 }
            ::= { hwadslLineExtConfProfileEntry 33 }
    
        hwadslExtUsMinRSoverhead OBJECT-TYPE
            SYNTAX      INTEGER (0..128)
            UNITS       "1/256"
            MAX-ACCESS  read-write
            STATUS      current
            DESCRIPTION
                "The minimum value of R/N on upstream direction."
            DEFVAL { 0 }
            ::= { hwadslLineExtConfProfileEntry 34 }
            
        hwadslExtDsPhyRcontrol OBJECT-TYPE
            SYNTAX      INTEGER
            {
                enable(1),
                disable(2)
            }
            MAX-ACCESS  read-write
            STATUS      current
            DESCRIPTION
                "To enable or disable the PHY-R function on downstream direction."
            DEFVAL { 2 }
            ::= { hwadslLineExtConfProfileEntry 35 }
    
        hwadslExtDsINPmax OBJECT-TYPE
            SYNTAX      Adsl2SymbolProtection
            UNITS       "DMT Symbol"
            MAX-ACCESS  read-write
            STATUS      current
            DESCRIPTION
                "
                Maximum Impulse Noise Protection on downstream direction.
                The parameter can take the following values:
                noProtection(1),
                halfSymbol(2),
                singleSymbol(3),
                twoSymbols(4),
                threeSymbols(5),
                fourSymbols(6),
                fiveSymbols(7),
                sixSymbols(8),
                sevenSymbols(9),
                eightSymbols(10),
                nineSymbols(11),
                tenSymbols(12),
                elevenSymbols(13),
                twelveSymbols(14),
                thirteeSymbols(15),
                fourteenSymbols(16),
                fifteenSymbols(17),
                sixteenSymbols(18)
                
                The value multiply 1/2 is the real value of Noise Protection values.
    		    "
    		DEFVAL { 1 }
            ::= { hwadslLineExtConfProfileEntry 36 }
    
        hwadslExtDsMinRtxRatio OBJECT-TYPE
            SYNTAX      INTEGER (0..255)
            UNITS       "1/256"
            MAX-ACCESS  read-write
            STATUS      current
            DESCRIPTION
                "Minimum rtxratio on downstream direction."
            DEFVAL { 0 }
            ::= { hwadslLineExtConfProfileEntry 37 }
    
        hwadslExtDsMinRSoverhead OBJECT-TYPE
            SYNTAX      INTEGER (0..128)
            UNITS       "1/256"
            MAX-ACCESS  read-write
            STATUS      current
            DESCRIPTION
                "The minimum value of R/N on downstream direction."
            DEFVAL { 0 }
            ::= { hwadslLineExtConfProfileEntry 38 }
        	  
        hwadsl2TSSiPsdMaskUs OBJECT-TYPE
  		    SYNTAX      Adsl2PsdMaskUs
  		    MAX-ACCESS  read-write
  		    STATUS      current
 		     DESCRIPTION
 		       "The upstream PSD mask applicable at the U-C2 reference
 		        point.
 		       This parameter is used only for G992.3 or G992.5 and it may impose PSD
 		       restrictions (breakpoints) in addition to the Limit PSD mask
 		       defined in G992.5.
 		       This is a string of 32 pairs of values in the following
  		      structure:
 		       Octets 0+1 - Index of 1st sub-carrier used in the context
		                     of a first breakpoint.
  		      Octet 2    - The PSD reduction for the sub-carrier indicated in
  		                   octets 0 and 1.
  		      Octets 3-5 - Same, for a 2nd breakpoint.
  		      Octets 6-8 - Same, for a 3rd breakpoint.
  		      This architecture continues until octets 9-11, which are
  		      associated with a fourth breakpoint.
   		     Each subcarrier index is an unsigned number in the range 1 and
   		     NSCus.  Each PSD reduction value is in the range 0 (0dBm/Hz) to
		    255 (-127.5dBm/Hz) with steps of 0.5dBm/Hz.  Valid values are
       		in the range 0 to 190 (0 to -95dBm/Hz).
       		When the number of breakpoints is less than 4, all remaining
       		octets are set to the value 0.  Note that the content of this
       		object should be correlated with the sub-carriers mask and with
       		the RFI setup. "
      		REFERENCE    "ITU-T G.997.1, paragraph 7.3.1.2"
        		::= { hwadslLineExtConfProfileEntry 39 }         
			
		hwadslLineExtConfProfileRowStatus OBJECT-TYPE
	             SYNTAX          RowStatus
	             MAX-ACCESS      read-create
	             STATUS          current
	             DESCRIPTION
	                 "This object is used to create a new row or modify or
	                 delete an existing row in this table.
	                 A profile activated by setting this object to
	                 `active'.  When `active' is set, the system
	                 will validate the profile.
	
	                 Before a profile can be deleted or taken out of
	                 service, (by setting this object to `destroy' or
	                 `outOfService') it must be first unreferenced
	                 from all associated lines.
	
	                 If the implementator of this MIB has chosen not
	                 to implement `dynamic assignment' of profiles, this
	                 object's MIN-ACCESS is read-only and its value
	                 is always to be `active'."
	         ::= { hwadslLineExtConfProfileEntry 65535 }


    ---------------------------------------------------------------------------
    -- 
    ---------------------------------------------------------------------------    
		hwAdslLineLatestActParaTable OBJECT-TYPE
			SYNTAX SEQUENCE OF HwAdslLineLatestActParaEntry
			MAX-ACCESS not-accessible
			STATUS current
			DESCRIPTION
				"This table provides one row for each ADSL PORT.
				Each row contains the latest actived Parameters
				 "
			::= { adslMibObjects 65544 }
		
		hwAdslLineLatestActParaEntry OBJECT-TYPE
			SYNTAX HwAdslLineLatestActParaEntry
			MAX-ACCESS not-accessible
			STATUS current
			DESCRIPTION
				"An entry in the hwAdslLineLatestActParaTable"
			INDEX { ifIndex }
			::= { hwAdslLineLatestActParaTable 1 }
		
		HwAdslLineLatestActParaEntry ::=
			SEQUENCE {
			    hwAdslLineLatestActiveTime
			        DateAndTime,
			    hwAdslLineLatestDeactiveTime
			        DateAndTime, 
                hwAdslAtucLatestTxRate
				    Gauge32,
                hwAdslAturLatestTxRate
				    Gauge32,
				hwAdslAtucLatestSnrMgn
					INTEGER,
				hwAdslAturLatestSnrMgn
					INTEGER,
				hwAdslAtucLatestAtn
					Gauge32,
				hwAdslAturLatestAtn
					Gauge32,
				hwAdslAtucLatestAttainableRate
					Gauge32,
				hwAdslAturLatestAttainableRate
					Gauge32,
                hwAdslAtucLatestConfTxRate
                    Gauge32,
                hwAdslAturLatestConfTxRate
                    Gauge32,
				hwAdslAtucLatestInterleaveDelay
				    Gauge32,
				hwAdslAturLatestInterleaveDelay
				    Gauge32,
			    hwAdslAtucLatestTargetSnrMgn
			        INTEGER,
			    hwAdslAturLatestTargetSnrMgn
			        INTEGER,
			    hwAdslAtucLatestTxRateThreshold 
			        Gauge32,
			    hwAdslAturLatestTxRateThreshold	
			        Gauge32			    
			 }

  		hwAdslLineLatestActiveTime OBJECT-TYPE
    		SYNTAX      DateAndTime
   			MAX-ACCESS  read-only
    		STATUS      current
            DESCRIPTION
                "Actual time when latest actived"
    	::= { hwAdslLineLatestActParaEntry 1 }

  		hwAdslLineLatestDeactiveTime OBJECT-TYPE
    		SYNTAX      DateAndTime
    		MAX-ACCESS  read-only
    		STATUS      current
            DESCRIPTION
                "Actual time when latest deactived. If port is actived, the value is invalid."
    	::= { hwAdslLineLatestActParaEntry 2 }

        hwAdslAtucLatestTxRate  OBJECT-TYPE
            SYNTAX      Gauge32
            UNITS       "bps"
            MAX-ACCESS  read-only
            STATUS      current
            DESCRIPTION
                "Actual transmit rate on this channel when latest actived."
        ::= { hwAdslLineLatestActParaEntry 3 }

        hwAdslAturLatestTxRate  OBJECT-TYPE
            SYNTAX      Gauge32
            UNITS       "bps"
            MAX-ACCESS  read-only
            STATUS      current
            DESCRIPTION
                "Actual transmit rate on this channel when latest actived."
        ::= { hwAdslLineLatestActParaEntry 4 }

		hwAdslAtucLatestSnrMgn OBJECT-TYPE
			SYNTAX INTEGER
			UNITS "tenth dB"
			MAX-ACCESS read-only
			STATUS current
			DESCRIPTION
				" Noise Margin as seen by this ATU-C at the time of the last adslAtucRateChangeTrap event. in tenth dB"
			::= { hwAdslLineLatestActParaEntry 5 }
		
		hwAdslAturLatestSnrMgn OBJECT-TYPE
			SYNTAX INTEGER
			UNITS "tenth dB"
			MAX-ACCESS read-only
			STATUS current
			DESCRIPTION
				" Noise Margin as seen by this ATU-R at the time of the last adslAtucRateChangeTrap event. in tenth dB"
			::= { hwAdslLineLatestActParaEntry 6 }
		
		hwAdslAtucLatestAtn OBJECT-TYPE
			SYNTAX Gauge32
			UNITS "tenth dB"
			MAX-ACCESS read-only
			STATUS current
			DESCRIPTION
				"Measured difference in the total power transmitted as seen by this ATU-C at the time of the last adslAtucRateChangeTrap event. in tenth dB"
			::= { hwAdslLineLatestActParaEntry 7 }
		
		hwAdslAturLatestAtn OBJECT-TYPE
			SYNTAX Gauge32
			UNITS "tenth dB"
			MAX-ACCESS read-only
			STATUS current
			DESCRIPTION
				"Measured difference in the total power transmitted as seen by this ATU-R at the time of the last adslAtucRateChangeTrap event. in tenth dB"
			::= { hwAdslLineLatestActParaEntry 8 }
        
		hwAdslAtucLatestAttainableRate OBJECT-TYPE
			SYNTAX Gauge32
			UNITS "bps"
			MAX-ACCESS read-only
			STATUS current
			DESCRIPTION
				"Indicates the maximum attainable data rate by the ATU-C at the time of the last adslAtucRateChangeTrap event."
			::= { hwAdslLineLatestActParaEntry 9 }
		
		hwAdslAturLatestAttainableRate OBJECT-TYPE
			SYNTAX Gauge32
			UNITS "bps"
			MAX-ACCESS read-only
			STATUS current
			DESCRIPTION
				"Indicates the maximum attainable data rate by the ATU-R at the time of the last adslAtucRateChangeTrap event."
			::= { hwAdslLineLatestActParaEntry 10 } 
			
         hwAdslAtucLatestConfTxRate  OBJECT-TYPE
             SYNTAX      Gauge32
             UNITS       "bps"
             MAX-ACCESS  read-only
             STATUS      current
             DESCRIPTION
                 "Configured transmit rate for ADSL port,
                 in bps.  See adslAtucConfRateChanRatio for information
                 regarding RADSL mode and ATUR transmit rate for
                 ATUC receive rates."
         ::= { hwAdslLineLatestActParaEntry 11 }

         hwAdslAturLatestConfTxRate  OBJECT-TYPE
             SYNTAX      Gauge32
             UNITS       "bps"
             MAX-ACCESS  read-only
             STATUS      current
             DESCRIPTION
                 "Configured receive rate for ADSL port,
                 in bps.  See adslAtucConfRateChanRatio for information
                 regarding RADSL mode and ATUR transmit rate for
                 ATUC receive rates."
         ::= { hwAdslLineLatestActParaEntry 12 }

         hwAdslAtucLatestInterleaveDelay OBJECT-TYPE
             SYNTAX      Gauge32
             UNITS       "milli-seconds"
             MAX-ACCESS  read-only
             STATUS      current
             DESCRIPTION
                 "Interleave Delay for this channel when latest actived."
         ::= { hwAdslLineLatestActParaEntry 13 }

         hwAdslAturLatestInterleaveDelay OBJECT-TYPE
             SYNTAX      Gauge32
             UNITS       "milli-seconds"
             MAX-ACCESS  read-only
             STATUS      current
             DESCRIPTION
                 "Interleave Delay for this channel when latest actived."
         ::= { hwAdslLineLatestActParaEntry 14 }

        hwAdslAtucLatestTargetSnrMgn OBJECT-TYPE
             SYNTAX      INTEGER (0..310)
             UNITS       "tenth dB"
             MAX-ACCESS  read-only
             STATUS      current
             DESCRIPTION
                 "Port Signal/Noise Margin."
         ::= { hwAdslLineLatestActParaEntry 15 }

        hwAdslAturLatestTargetSnrMgn OBJECT-TYPE
             SYNTAX      INTEGER (0..310)
             UNITS       "tenth dB"
             MAX-ACCESS  read-only
             STATUS      current
             DESCRIPTION
                 "Port Signal/Noise Margin."
         ::= { hwAdslLineLatestActParaEntry 16 }

		hwAdslAtucLatestTxRateThreshold OBJECT-TYPE
			SYNTAX Gauge32
			UNITS "bps"
			MAX-ACCESS read-only
			STATUS      current
			DESCRIPTION
				"Port down stream threshold.
				"
			::= { hwAdslLineLatestActParaEntry 17 }      
           
		hwAdslAturLatestTxRateThreshold OBJECT-TYPE
			SYNTAX Gauge32
			UNITS "bps"
			MAX-ACCESS read-only
			STATUS      current
			DESCRIPTION
				"Port up stream threshold.
				"
			::= { hwAdslLineLatestActParaEntry 18 } 
--
--  hwXdslPortPerformanceStatTable
--
        hwXdslPortPerformanceStatTable OBJECT-TYPE
			SYNTAX SEQUENCE OF HwXdslPortPerformanceStatEntry
			MAX-ACCESS not-accessible
			STATUS current
			DESCRIPTION
				"
				XDSL port performance staticstic table.
				"
			::= { adslMibObjects 65545 }
		
		hwXdslPortPerformanceStatEntry OBJECT-TYPE
			SYNTAX HwXdslPortPerformanceStatEntry
			MAX-ACCESS not-accessible
			STATUS current
			DESCRIPTION
				"An entry in the hwXdslPortPerformanceStatTable"
			INDEX {        
			      ifIndex,
			      hwXdslPort15minutesPerformanceInterval 
			      }
			::= { hwXdslPortPerformanceStatTable 1 }
		
		HwXdslPortPerformanceStatEntry ::=
			SEQUENCE{
			    hwXdslPort15minutesPerformanceInterval
					INTEGER,
				hwXdslPort15minutesPerformanceInBytes
					Counter32,
				hwXdslPort15minutesPerformanceOutBytes
					Counter32,
			        hwXdslPortSyncSuccNumber
			                Counter32,
			        hwXdslPortSyncFailNumber
			                Counter32,
			        hwXdslPortAtucCodeViolation
			                Counter32,
			        hwXdslPortAturCodeViolation
			                Counter32,
			        hwXdslPortAtucFecSeconds
			                Counter32,
			        hwXdslPortAturFecSeconds
			                Counter32,			                
				hwXdslPortCurrent15minutesStatTime
					Counter32
				    }       
	    
	    hwXdslPort15minutesPerformanceInterval OBJECT-TYPE
			SYNTAX INTEGER(0..96)
			MAX-ACCESS not-accessible
			STATUS current
			DESCRIPTION   
				" 
				The index of the interval which is queried.
				"  
			DEFVAL { 0 }
			::= { hwXdslPortPerformanceStatEntry 1 }


		hwXdslPort15minutesPerformanceInBytes OBJECT-TYPE
			SYNTAX Counter32
			MAX-ACCESS read-only
			STATUS current
			DESCRIPTION   
				" 
				Read the receive bytes of xDSL port during 15 minutes.
				"  
			DEFVAL { 0 }
			::= { hwXdslPortPerformanceStatEntry 2 }
			
		hwXdslPort15minutesPerformanceOutBytes OBJECT-TYPE
			SYNTAX Counter32 
			MAX-ACCESS read-only
			STATUS current
			DESCRIPTION
				"
				Read the transmit bytes of xDSL port during 15 minutes.
				" 
			DEFVAL { 0 }
			::= { hwXdslPortPerformanceStatEntry 3 }
	        
	        hwXdslPortSyncSuccNumber OBJECT-TYPE
			SYNTAX Counter32 
			MAX-ACCESS read-only
			STATUS current
			DESCRIPTION
				"
				Number of Successful re-syncs.
				" 
			DEFVAL { 0 }
			::= { hwXdslPortPerformanceStatEntry 4 }
		
		hwXdslPortSyncFailNumber OBJECT-TYPE
			SYNTAX Counter32 
			MAX-ACCESS read-only
			STATUS current
			DESCRIPTION
				"
				Initialisation failure.
				" 
			DEFVAL { 0 }
			::= { hwXdslPortPerformanceStatEntry 5 }
			
	        hwXdslPortAtucCodeViolation OBJECT-TYPE
			SYNTAX Counter32 
			MAX-ACCESS read-only
			STATUS current
			DESCRIPTION
				"
				ATUC code violation.
				" 
			DEFVAL { 0 }
			::= { hwXdslPortPerformanceStatEntry 6 }
			
		hwXdslPortAturCodeViolation OBJECT-TYPE
			SYNTAX Counter32 
			MAX-ACCESS read-only
			STATUS current
			DESCRIPTION
				"
				ATUR code violation.
				" 
			DEFVAL { 0 }
			::= { hwXdslPortPerformanceStatEntry 7 }
			
		hwXdslPortAtucFecSeconds OBJECT-TYPE
			SYNTAX Counter32 
			MAX-ACCESS read-only
			STATUS current
			DESCRIPTION
				"
				ATUC FEC seconds.
				" 
			DEFVAL { 0 }
			::= { hwXdslPortPerformanceStatEntry 8 }	
		
		hwXdslPortAturFecSeconds OBJECT-TYPE
			SYNTAX Counter32 
			MAX-ACCESS read-only
			STATUS current
			DESCRIPTION
				"
				ATUR FEC seconds.
				" 
			DEFVAL { 0 }
			::= { hwXdslPortPerformanceStatEntry 9 }
			
		hwXdslPortCurrent15minutesStatTime OBJECT-TYPE
			SYNTAX Counter32
			MAX-ACCESS read-only
			STATUS current
			DESCRIPTION
				" 
				Read the Stat. time of current 15 minutes.
				"  
			DEFVAL { 0 }
			::= { hwXdslPortPerformanceStatEntry 10 }
------------------------------------------------
---add for atuc phy
------------------------------------------------
         hwAdslAtucCurrTransMode OBJECT-TYPE
             SYNTAX      HWADSLTRANSMISSIONMODETYPE
             MAX-ACCESS  read-only
             STATUS      current
             DESCRIPTION
                 "A set of ADSL line transmission modes"
         ::= { adslAtucPhysEntry 65536 }

-- adslAtucPhysTable
		-- 1.3.6.1.2.1.10.94.1.1.2.1.65537
		hwAdslAtucCurrSignalAtn OBJECT-TYPE
			SYNTAX Gauge32 (0..630)
			UNITS "tenth dB"
			MAX-ACCESS read-only
			STATUS current
			DESCRIPTION
				"The signal attenuation value on ATUC."
			::= { adslAtucPhysEntry 65537 }
		
        hwadsl2LineTransAtucActual OBJECT-TYPE
             SYNTAX      Adsl2TransmissionModeType
             MAX-ACCESS  read-only
             STATUS      current
             DESCRIPTION
                 "The actual transmission mode of the ATU-C.
                  During ADSL line initialization, the ADSL
                  Transceiver Unit - Remote terminal end (ATU-R)
                  will determine the mode used for the link.
                  This value will be limited a single transmission
                  mode that is a subset of those modes enabled
                  by the ATU-C and denoted by
                  adslLineTransAtucConfig. After an initialization
                  has occurred, its mode is saved as the 'Current'
                  mode and is persistence should the link go
                  down. This object returns 0 (i.e. BITS with no
                  mode bit set) if the mode is not known."
             REFERENCE "Section 7.3.2 ITU G.997.1 "
         ::= { adslLineExtEntry 65555 }
         
--
--  ADSL Port Performance Statistics FEC,HEC,CRC
--
--  adslAtucChanPerfDataTable
         hwadslAtucChanFecBlks  OBJECT-TYPE
             SYNTAX      Counter32
             MAX-ACCESS  read-only
             STATUS      current
             DESCRIPTION
                 "Count of all blocks received with FEC anomalies
                 since agent reset."
         ::= { adslAtucChanPerfDataEntry 65536 }
         
         hwadslAtucChanHecBlks  OBJECT-TYPE
             SYNTAX      Counter32
             MAX-ACCESS  read-only
             STATUS      current
             DESCRIPTION
                 "Count of all blocks received with HEC anomalies
                 since agent reset."
         ::= { adslAtucChanPerfDataEntry 65537 }
         
         hwadslAtucChanCrcBlks  OBJECT-TYPE
             SYNTAX      Counter32
             MAX-ACCESS  read-only
             STATUS      current
             DESCRIPTION
                 "Count of all blocks received with CRC anomalies
                 since agent reset."
         ::= { adslAtucChanPerfDataEntry 65538 }
         
         hwadslAtucChanPerfCurr15MinFecBlks  OBJECT-TYPE
             SYNTAX      Counter32
             MAX-ACCESS  read-only
             STATUS      current
             DESCRIPTION
                 "Count of all blocks received with FEC anomalies
                  on this channel within the current 15 minute
                 interval."
         ::= { adslAtucChanPerfDataEntry 65539 }
         
         hwadslAtucChanPerfCurr15MinHecBlks  OBJECT-TYPE
             SYNTAX      Counter32
             MAX-ACCESS  read-only
             STATUS      current
             DESCRIPTION
                 "Count of all blocks received with HEC anomalies
                  on this channel within the current 15 minute
                 interval."
         ::= { adslAtucChanPerfDataEntry 65540 }
         
         hwadslAtucChanPerfCurr15MinCrcBlks  OBJECT-TYPE
             SYNTAX      Counter32
             MAX-ACCESS  read-only
             STATUS      current
             DESCRIPTION
                 "Count of all blocks received with CRC anomalies
                  on this channel within the current 15 minute
                 interval."
         ::= { adslAtucChanPerfDataEntry 65541 }
         
         hwadslAtucChanPerfCurr1DayFecBlks  OBJECT-TYPE
             SYNTAX      Counter32
             MAX-ACCESS  read-only
             STATUS      current
             DESCRIPTION
                 "Count of all blocks received with FEC anomalies
                 on this channel during the current day as
                 measured by adslAtucChanPerfCurr1DayTimeElapsed."
         ::= { adslAtucChanPerfDataEntry 65542 }
         
         hwadslAtucChanPerfCurr1DayHecBlks  OBJECT-TYPE
             SYNTAX      Counter32
             MAX-ACCESS  read-only
             STATUS      current
             DESCRIPTION
                 "Count of all blocks received with HEC anomalies
                 on this channel during the current day as
                 measured by adslAtucChanPerfCurr1DayTimeElapsed."
         ::= { adslAtucChanPerfDataEntry 65543 }
         
         hwadslAtucChanPerfCurr1DayCrcBlks  OBJECT-TYPE
             SYNTAX      Counter32
             MAX-ACCESS  read-only
             STATUS      current
             DESCRIPTION
                 "Count of all blocks received with CRC anomalies
                 on this channel during the current day as
                 measured by adslAtucChanPerfCurr1DayTimeElapsed."
         ::= { adslAtucChanPerfDataEntry 65544 }
         
         hwadslAtucChanPerfPrev1DayFecBlks  OBJECT-TYPE
             SYNTAX      Counter32
             MAX-ACCESS  read-only
             STATUS      current
             DESCRIPTION
                 "Count of all blocks received with FEC anomalies
                 on this channel within the most recent previous
                 1-day period."
         ::= { adslAtucChanPerfDataEntry 65545 }
         
         hwadslAtucChanPerfPrev1DayHecBlks  OBJECT-TYPE
             SYNTAX      Counter32
             MAX-ACCESS  read-only
             STATUS      current
             DESCRIPTION
                 "Count of all blocks received with HEC anomalies
                 on this channel within the most recent previous
                 1-day period."
         ::= { adslAtucChanPerfDataEntry 65546 }
         
         hwdslAtucChanPerfPrev1DayCrcBlks  OBJECT-TYPE
             SYNTAX      Counter32
             MAX-ACCESS  read-only
             STATUS      current
             DESCRIPTION
                 "Count of all blocks received with CRC anomalies
                 on this channel within the most recent previous
                 1-day period."
         ::= { adslAtucChanPerfDataEntry 65547 }
         
--  adslAturChanPerfDataTable
         hwadslAturChanFecBlks  OBJECT-TYPE
             SYNTAX      Counter32
             MAX-ACCESS  read-only
             STATUS      current
             DESCRIPTION
                 "Count of all blocks received with FEC anomalies
                 since agent reset."
         ::= { adslAturChanPerfDataEntry 65536 }
         
         hwadslAturChanHecBlks  OBJECT-TYPE
             SYNTAX      Counter32
             MAX-ACCESS  read-only
             STATUS      current
             DESCRIPTION
                 "Count of all blocks received with HEC anomalies
                 since agent reset."
         ::= { adslAturChanPerfDataEntry 65537 }
         
         hwadslAturChanCrcBlks  OBJECT-TYPE
             SYNTAX      Counter32
             MAX-ACCESS  read-only
             STATUS      current
             DESCRIPTION
                 "Count of all blocks received with CRC anomalies
                 since agent reset."
         ::= { adslAturChanPerfDataEntry 65538 }
         
         hwadslAturChanPerfCurr15MinFecBlks  OBJECT-TYPE
             SYNTAX      Counter32
             MAX-ACCESS  read-only
             STATUS      current
             DESCRIPTION
                 "Count of all blocks received with FEC anomalies
                  on this channel within the current 15 minute
                 interval."
         ::= { adslAturChanPerfDataEntry 65539 }
         
         hwadslAturChanPerfCurr15MinHecBlks  OBJECT-TYPE
             SYNTAX      Counter32
             MAX-ACCESS  read-only
             STATUS      current
             DESCRIPTION
                 "Count of all blocks received with HEC anomalies
                  on this channel within the current 15 minute
                 interval."
         ::= { adslAturChanPerfDataEntry 65540 }
         
         hwadslAturChanPerfCurr15MinCrcBlks  OBJECT-TYPE
             SYNTAX      Counter32
             MAX-ACCESS  read-only
             STATUS      current
             DESCRIPTION
                 "Count of all blocks received with CRC anomalies
                  on this channel within the current 15 minute
                 interval."
         ::= { adslAturChanPerfDataEntry 65541 }
         
         hwadslAturChanPerfCurr1DayFecBlks  OBJECT-TYPE
             SYNTAX      Counter32
             MAX-ACCESS  read-only
             STATUS      current
             DESCRIPTION
                 "Count of all blocks received with FEC anomalies
                 on this channel during the current day as
                 measured by adslAturChanPerfCurr1DayTimeElapsed."
         ::= { adslAturChanPerfDataEntry 65542 }
         
         hwadslAturChanPerfCurr1DayHecBlks  OBJECT-TYPE
             SYNTAX      Counter32
             MAX-ACCESS  read-only
             STATUS      current
             DESCRIPTION
                 "Count of all blocks received with HEC anomalies
                 on this channel during the current day as
                 measured by adslAturChanPerfCurr1DayTimeElapsed."
         ::= { adslAturChanPerfDataEntry 65543 }
         
         hwadslAturChanPerfCurr1DayCrcBlks  OBJECT-TYPE
             SYNTAX      Counter32
             MAX-ACCESS  read-only
             STATUS      current
             DESCRIPTION
                 "Count of all blocks received with CRC anomalies
                 on this channel during the current day as
                 measured by adslAturChanPerfCurr1DayTimeElapsed."
         ::= { adslAturChanPerfDataEntry 65544 }
         
         hwadslAturChanPerfPrev1DayFecBlks  OBJECT-TYPE
             SYNTAX      Counter32
             MAX-ACCESS  read-only
             STATUS      current
             DESCRIPTION
                 "Count of all blocks received with FEC anomalies
                 on this channel within the most recent previous
                 1-day period."
         ::= { adslAturChanPerfDataEntry 65545 }
         
         hwadslAturChanPerfPrev1DayHecBlks  OBJECT-TYPE
             SYNTAX      Counter32
             MAX-ACCESS  read-only
             STATUS      current
             DESCRIPTION
                 "Count of all blocks received with HEC anomalies
                 on this channel within the most recent previous
                 1-day period."
         ::= { adslAturChanPerfDataEntry 65546 }
         
         hwadslAturChanPerfPrev1DayCrcBlks  OBJECT-TYPE
             SYNTAX      Counter32
             MAX-ACCESS  read-only
             STATUS      current
             DESCRIPTION
                 "Count of all blocks received with CRC anomalies
                 on this channel within the most recent previous
                 1-day period."
         ::= { adslAturChanPerfDataEntry 65547 }
         
--  adslAtucChanIntervalTable
         hwadslAtucChanIntervalFecBlks OBJECT-TYPE
             SYNTAX      PerfIntervalCount
             MAX-ACCESS  read-only
             STATUS      current
             DESCRIPTION
                 "Count of all blocks received with FRC anomalies
                 on this channel during this interval."
         ::= { adslAtucChanIntervalEntry 65536 }
         
         hwadslAtucChanIntervalHecBlks OBJECT-TYPE
             SYNTAX      PerfIntervalCount
             MAX-ACCESS  read-only
             STATUS      current
             DESCRIPTION
                 "Count of all blocks received with HRC anomalies
                 on this channel during this interval."
         ::= { adslAtucChanIntervalEntry 65537 }
         
         hwadslAtucChanIntervalCrcBlks OBJECT-TYPE
             SYNTAX      PerfIntervalCount
             MAX-ACCESS  read-only
             STATUS      current
             DESCRIPTION
                 "Count of all blocks received with CRC anomalies
                 on this channel during this interval."
         ::= { adslAtucChanIntervalEntry 65538 }
         
--  adslAturChanIntervalTable
         hwadslAturChanIntervalFecBlks OBJECT-TYPE
             SYNTAX      PerfIntervalCount
             MAX-ACCESS  read-only
             STATUS      current
             DESCRIPTION
                 "Count of all blocks received with FRC anomalies
                 on this channel during this interval."
         ::= { adslAturChanIntervalEntry 65536 }
         
         hwadslAturChanIntervalHecBlks OBJECT-TYPE
             SYNTAX      PerfIntervalCount
             MAX-ACCESS  read-only
             STATUS      current
             DESCRIPTION
                 "Count of all blocks received with HRC anomalies
                 on this channel during this interval."
         ::= { adslAturChanIntervalEntry 65537 }
         
         hwadslAturChanIntervalCrcBlks OBJECT-TYPE
             SYNTAX      PerfIntervalCount
             MAX-ACCESS  read-only
             STATUS      current
             DESCRIPTION
                 "Count of all blocks received with CRC anomalies
                 on this channel during this interval."
         ::= { adslAturChanIntervalEntry 65538 }
	
--  hwAdslPortPerformanceStatTable
--
        hwAdslPortPerformanceStatTable OBJECT-TYPE
			SYNTAX SEQUENCE OF HwAdslPortPerformanceStatEntry
			MAX-ACCESS not-accessible
			STATUS current
			DESCRIPTION
				"
				ADSL port performance staticstic table.
				"
			::= { adslMibObjects 65546 }
		
		hwAdslPortPerformanceStatEntry OBJECT-TYPE
			SYNTAX HwAdslPortPerformanceStatEntry
			MAX-ACCESS not-accessible
			STATUS current
			DESCRIPTION
				"An entry in the hwAdslPortPerformanceStatTable"
			INDEX {        
			      ifIndex,
			      hwAdslPort15minutesPerformanceInterval 
			      }
			::= { hwAdslPortPerformanceStatTable 1 }
		
		HwAdslPortPerformanceStatEntry ::=
			SEQUENCE{
			        hwAdslPort15minutesPerformanceInterval
					INTEGER,
				hwAdslPort15minutesPerformanceInBytes
					Counter32,
				hwAdslPort15minutesPerformanceOutBytes
					Counter32,
			        hwAdslPortSyncSuccNumber
			                Counter32,
			        hwAdslPortSyncFailNumber
			                Counter32,
			        hwAdslPortAtucCodeViolation
			                Counter32,
			        hwAdslPortAturCodeViolation
			                Counter32,
			        hwAdslPortAtucFecSeconds
			                Counter32,
			        hwAdslPortAturFecSeconds
			                Counter32,			                
				hwAdslPortCurrent15minutesTimeElapse
					Counter32,
			        hwAdslPortAtucHecDropCellsCnt
			                Counter32,
			        hwAdslPortAturHecDropCellsCnt
			                Counter32,
			        hwAdslLineConfProfile      
			                SnmpAdminString,
			        hwAdslPort15minUpTime
				        Counter32,
				hwAdslAtucCurrAtn                 
				        Gauge32,
				hwAdslAtucCurrSnrMgn
				        INTEGER,
				hwAdslAtucCurrAttainableRate
				        Gauge32,
				hwAdslAtucChanCurrTxRate 
				        Gauge32,
				hwAdslAturCurrAtn                 
				        Gauge32,
				hwAdslAturCurrSnrMgn
				        INTEGER,
				hwAdslAturCurrAttainableRate      
				        Gauge32,				        
				hwAdslAturChanCurrTxRate
				        Gauge32,
                                hwAdslAtucIntervalESs             
                                        PerfIntervalCount,	
                                hwAdslAtucIntervalLofs            
                                        PerfIntervalCount,
                                hwAdslAtucIntervalLols            
                                        PerfIntervalCount,
                                hwAdslAtucIntervalLoss           
                                        PerfIntervalCount,
                                hwAdslAtucIntervalLprs           
                                        PerfIntervalCount,
                                hwAdslAturIntervalESs             
                                        PerfIntervalCount,
                                hwAdslAturIntervalLofs            
                                        PerfIntervalCount,
                                hwAdslAturIntervalLoss            
                                        PerfIntervalCount,
                                hwAdslAturIntervalLprs            
                                        PerfIntervalCount,
                                hwAdslAtucChanIntervalReceivedBlks    
                                        PerfIntervalCount,
                                hwAdslAtucChanIntervalTransmittedBlks 
                                        PerfIntervalCount,
                                hwAdslAtucChanIntervalCorrectedBlks   
                                        PerfIntervalCount,
                                hwAdslAtucChanIntervalUncorrectBlks  
                                        PerfIntervalCount,
                                hwAdslAturChanIntervalReceivedBlks        
                                        PerfIntervalCount,
                                hwAdslAturChanIntervalTransmittedBlks      
                                        PerfIntervalCount,
                                hwAdslAturChanIntervalCorrectedBlks        
                                        PerfIntervalCount,
                                hwAdslAturChanIntervalUncorrectBlks        
                                        PerfIntervalCount,
                                hwAdslAtucIntervalSesL             
                                        PerfIntervalCount,
                                hwAdslAtucIntervalUasL             
                                        PerfIntervalCount,
                                hwAdslAturIntervalSesL             
                                        PerfIntervalCount,
                                hwAdslAturIntervalUasL            
                                        PerfIntervalCount
				    }       
	                        
	    hwAdslPort15minutesPerformanceInterval OBJECT-TYPE
			SYNTAX INTEGER(0..96)
			MAX-ACCESS not-accessible
			STATUS current
			DESCRIPTION   
				" 
				The index of the interval which is queried.
				"  
			DEFVAL { 0 }
			::= { hwAdslPortPerformanceStatEntry 1 }


		hwAdslPort15minutesPerformanceInBytes OBJECT-TYPE
			SYNTAX Counter32
			MAX-ACCESS read-only
			STATUS current
			DESCRIPTION   
				" 
				Read the receive bytes of xDSL port during 15 minutes.
				"  
			DEFVAL { 0 }
			::= { hwAdslPortPerformanceStatEntry 2 }
			
		hwAdslPort15minutesPerformanceOutBytes OBJECT-TYPE
			SYNTAX Counter32 
			MAX-ACCESS read-only
			STATUS current
			DESCRIPTION
				"
				Read the transmit bytes of xDSL port during 15 minutes.
				" 
			DEFVAL { 0 }
			::= { hwAdslPortPerformanceStatEntry 3 }
	        
	        hwAdslPortSyncSuccNumber OBJECT-TYPE
			SYNTAX Counter32 
			MAX-ACCESS read-only
			STATUS current
			DESCRIPTION
				"
				Number of Successful re-syncs.
				" 
			DEFVAL { 0 }
			::= { hwAdslPortPerformanceStatEntry 4 }
		
		hwAdslPortSyncFailNumber OBJECT-TYPE
			SYNTAX Counter32 
			MAX-ACCESS read-only
			STATUS current
			DESCRIPTION
				"
				Initialisation failure.
				" 
			DEFVAL { 0 }
			::= { hwAdslPortPerformanceStatEntry 5 }
			
	        hwAdslPortAtucCodeViolation OBJECT-TYPE
			SYNTAX Counter32 
			MAX-ACCESS read-only
			STATUS current
			DESCRIPTION
				"
				ATUC code violation.
				" 
			DEFVAL { 0 }
			::= { hwAdslPortPerformanceStatEntry 6 }
			
		hwAdslPortAturCodeViolation OBJECT-TYPE
			SYNTAX Counter32 
			MAX-ACCESS read-only
			STATUS current
			DESCRIPTION
				"
				ATUR code violation.
				" 
			DEFVAL { 0 }
			::= { hwAdslPortPerformanceStatEntry 7 }
			
		hwAdslPortAtucFecSeconds OBJECT-TYPE
			SYNTAX Counter32 
			MAX-ACCESS read-only
			STATUS current
			DESCRIPTION
				"
				ATUC FEC seconds.
				" 
			DEFVAL { 0 }
			::= { hwAdslPortPerformanceStatEntry 8 }	
		
		hwAdslPortAturFecSeconds OBJECT-TYPE
			SYNTAX Counter32 
			MAX-ACCESS read-only
			STATUS current
			DESCRIPTION
				"
				ATUR FEC seconds.
				" 
			DEFVAL { 0 }
			::= { hwAdslPortPerformanceStatEntry 9 }
			
		hwAdslPortCurrent15minutesTimeElapse OBJECT-TYPE
			SYNTAX Counter32
			MAX-ACCESS read-only
			STATUS current
			DESCRIPTION
				" 
				Read the Stat. time of current 15 minutes.
				"  
			DEFVAL { 0 }
			::= { hwAdslPortPerformanceStatEntry 10 }
				
		hwAdslPortAtucHecDropCellsCnt OBJECT-TYPE
			SYNTAX Counter32
			MAX-ACCESS read-only
			STATUS current
			DESCRIPTION
				" 
				ATUC cells discarded with HEC Errors.
				"  
			DEFVAL { 0 }
			::= { hwAdslPortPerformanceStatEntry 11 }
			
		hwAdslPortAturHecDropCellsCnt OBJECT-TYPE
			SYNTAX Counter32
			MAX-ACCESS read-only
			STATUS current
			DESCRIPTION
				" 
				ATUR cells discarded with HEC Errors.
				"  
			DEFVAL { 0 }
			::= { hwAdslPortPerformanceStatEntry 12 }
			
	        hwAdslLineConfProfile OBJECT-TYPE
                        SYNTAX      SnmpAdminString (SIZE (1..32))
                        MAX-ACCESS  read-only
                        STATUS      current
                        DESCRIPTION
                            "The value of this object identifies the row
                            in the ADSL Line Configuration Profile Table,
                            (adslLineConfProfileTable), which applies for this
                            ADSL line, and channels if applicable.
                        
                            For `dynamic' mode, in the case which the
                            configuration profile has not been set, the
                            value will be set to `DEFVAL'.
                        
                            If the implementator of this MIB has chosen not
                            to implement `dynamic assignment' of profiles, this
                            object's MIN-ACCESS is read-only."
                        ::= { hwAdslPortPerformanceStatEntry 13 }

                hwAdslPort15minUpTime OBJECT-TYPE
			SYNTAX Counter32
			MAX-ACCESS read-only
			STATUS current
			DESCRIPTION
				"Up time in the interval (UNIT:Second)."
 			::= { hwAdslPortPerformanceStatEntry 14 }
 			
 	        hwAdslAtucCurrAtn  OBJECT-TYPE
                        SYNTAX      Gauge32(0..630)
                        UNITS       "tenth dB"
                        MAX-ACCESS  read-only
                        STATUS      current
                        DESCRIPTION
                            "Measured difference in the total power transmitted by
                            the peer ATU and the total power received by this ATU."
                        ::= { hwAdslPortPerformanceStatEntry 15 }
                        
                hwAdslAtucCurrSnrMgn OBJECT-TYPE
                        SYNTAX      INTEGER (-640..640)
                        UNITS       "tenth dB"
                        MAX-ACCESS  read-only
                        STATUS      current
                        DESCRIPTION
                            "Noise Margin as seen by this ATU with respect to its
                            received signal in tenth dB."
                        ::= { hwAdslPortPerformanceStatEntry 16 }
                        
                hwAdslAtucCurrAttainableRate OBJECT-TYPE
                        SYNTAX      Gauge32
                        UNITS       "bps"
                        MAX-ACCESS  read-only
                        STATUS      current
                        DESCRIPTION
                            "Indicates the maximum currently attainable data rate
                            by the ATU.  This value will be equal or greater than
                            the current line rate."
                        ::= { hwAdslPortPerformanceStatEntry 17 }
                        
                hwAdslAtucChanCurrTxRate  OBJECT-TYPE
                        SYNTAX      Gauge32
                        UNITS       "bps"
                        MAX-ACCESS  read-only
                        STATUS      current
                        DESCRIPTION
                            "Actual transmit rate on this channel."
                        ::= { hwAdslPortPerformanceStatEntry 18 } 
                        
                hwAdslAturCurrAtn OBJECT-TYPE
                        SYNTAX      Gauge32(0..630)
                        UNITS       "tenth dB"
                        MAX-ACCESS  read-only
                        STATUS      current
                        DESCRIPTION
                            "Measured difference in the total power transmitted by
                            the peer ATU and the total power received by this ATU."
                        ::= { hwAdslPortPerformanceStatEntry 19 }
                        
                hwAdslAturCurrSnrMgn OBJECT-TYPE
                        SYNTAX      INTEGER (-640..640)
                        UNITS       "tenth dB"
                        MAX-ACCESS  read-only
                        STATUS      current
                        DESCRIPTION
                            "Noise Margin as seen by this ATU with respect to its
                            received signal in tenth dB."
                        ::= { hwAdslPortPerformanceStatEntry 20 }
                        
                hwAdslAturCurrAttainableRate OBJECT-TYPE
                        SYNTAX      Gauge32
                        UNITS       "bps"
                        MAX-ACCESS  read-only
                        STATUS      current
                        DESCRIPTION
                            "Indicates the maximum currently attainable data rate
                            by the ATU.  This value will be equal or greater than
                            the current line rate."
                        ::= { hwAdslPortPerformanceStatEntry 21 }
                        
                hwAdslAturChanCurrTxRate  OBJECT-TYPE
                        SYNTAX      Gauge32
                        UNITS       "bps"
                        MAX-ACCESS  read-only
                        STATUS      current
                        DESCRIPTION
                            "Actual transmit rate on this channel."
                        ::= { hwAdslPortPerformanceStatEntry 22 }
                        
                hwAdslAtucIntervalESs OBJECT-TYPE
                        SYNTAX      PerfIntervalCount
                        UNITS       "seconds"
                        MAX-ACCESS  read-only
                        STATUS      current
                        DESCRIPTION
                            "Count of Errored Seconds in the interval.
                            The errored second parameter is a count of
                            one-second intervals containing one or more crc
                            anomalies, or one or more los or sef defects."
                        ::= { hwAdslPortPerformanceStatEntry 23 }
                        
                hwAdslAtucIntervalLofs OBJECT-TYPE
                        SYNTAX      PerfIntervalCount
                        UNITS       "seconds"
                        MAX-ACCESS  read-only
                        STATUS      current
                        DESCRIPTION
                            "Count of seconds in the interval when there was Loss
                            of Framing."
                        ::= { hwAdslPortPerformanceStatEntry 24 }
                        
                hwAdslAtucIntervalLols  OBJECT-TYPE
                        SYNTAX      PerfIntervalCount
                        UNITS       "seconds"
                        MAX-ACCESS  read-only
                        STATUS      current
                        DESCRIPTION
                            "Count of seconds in the interval when there was Loss
                            of Link."
                        ::= { hwAdslPortPerformanceStatEntry 25 }
                        
                hwAdslAtucIntervalLoss  OBJECT-TYPE
                        SYNTAX      PerfIntervalCount
                        UNITS       "seconds"
                        MAX-ACCESS  read-only
                        STATUS      current
                        DESCRIPTION
                            "Count of seconds in the interval when there was Loss
                            of Signal."
                        ::= { hwAdslPortPerformanceStatEntry 26 }
                        
                hwAdslAtucIntervalLprs  OBJECT-TYPE
                        SYNTAX      PerfIntervalCount
                        UNITS       "seconds"
                        MAX-ACCESS  read-only
                        STATUS      current
                        DESCRIPTION
                            "Count of seconds in the interval when there was Loss
                            of Power."
                        ::= { hwAdslPortPerformanceStatEntry 27 }
               
                hwAdslAturIntervalESs OBJECT-TYPE
                        SYNTAX      PerfIntervalCount
                        UNITS       "seconds"
                        MAX-ACCESS  read-only
                        STATUS      current
                        DESCRIPTION
                            "Count of Errored Seconds in the interval.
                            The errored second parameter is a count of
                            one-second intervals containing one or more crc
                            anomalies, or one or more los or sef defects."
                        ::= { hwAdslPortPerformanceStatEntry 28 } 
                        
                hwAdslAturIntervalLofs OBJECT-TYPE
                        SYNTAX      PerfIntervalCount
                        UNITS       "seconds"
                        MAX-ACCESS  read-only
                        STATUS      current
                        DESCRIPTION
                            "Count of seconds in the interval when there was
                            Loss of Framing."
                        ::= { hwAdslPortPerformanceStatEntry 29 }

                hwAdslAturIntervalLoss  OBJECT-TYPE
                        SYNTAX      PerfIntervalCount
                        UNITS       "seconds"
                        MAX-ACCESS  read-only
                        STATUS      current
                        DESCRIPTION
                            "Count of seconds in the interval when there was
                            Loss of Signal."
                        ::= { hwAdslPortPerformanceStatEntry 30 }

                hwAdslAturIntervalLprs  OBJECT-TYPE
                        SYNTAX      PerfIntervalCount
                        UNITS       "seconds"
                        MAX-ACCESS  read-only
                        STATUS      current
                        DESCRIPTION
                            "Count of seconds in the interval when there was
                            Loss of Power."
                        ::= { hwAdslPortPerformanceStatEntry 31 }  
                        
                hwAdslAtucChanIntervalReceivedBlks OBJECT-TYPE
                        SYNTAX      PerfIntervalCount
                        MAX-ACCESS  read-only
                        STATUS      current
                        DESCRIPTION
                            "Count of all encoded blocks received on this channel
                            during this interval."
                        ::= { hwAdslPortPerformanceStatEntry 32 }

                hwAdslAtucChanIntervalTransmittedBlks  OBJECT-TYPE
                        SYNTAX      PerfIntervalCount
                        MAX-ACCESS  read-only
                        STATUS      current
                        DESCRIPTION
                            "Count of all encoded blocks transmitted on this
                            channel during this interval."
                        ::= { hwAdslPortPerformanceStatEntry 33 }

                hwAdslAtucChanIntervalCorrectedBlks  OBJECT-TYPE
                        SYNTAX      PerfIntervalCount
                        MAX-ACCESS  read-only
                        STATUS      current
                        DESCRIPTION
                            "Count of all blocks received with errors that were
                            corrected on this channel during this interval."
                        ::= { hwAdslPortPerformanceStatEntry 34 }

                hwAdslAtucChanIntervalUncorrectBlks  OBJECT-TYPE
                        SYNTAX      PerfIntervalCount
                        MAX-ACCESS  read-only
                        STATUS      current
                        DESCRIPTION
                            "Count of all blocks received with uncorrectable
                            errors on this channel during this interval."
                        ::= { hwAdslPortPerformanceStatEntry 35 }  
                        
                hwAdslAturChanIntervalReceivedBlks OBJECT-TYPE
                        SYNTAX      PerfIntervalCount
                        MAX-ACCESS  read-only
                        STATUS      current
                        DESCRIPTION
                            "Count of all encoded blocks received on this channel
                            during this interval."
                        ::= { hwAdslPortPerformanceStatEntry 36 }
                   
                hwAdslAturChanIntervalTransmittedBlks  OBJECT-TYPE
                        SYNTAX      PerfIntervalCount
                        MAX-ACCESS  read-only
                        STATUS      current
                        DESCRIPTION
                            "Count of all encoded blocks transmitted on this
                            channel during this interval."
                        ::= { hwAdslPortPerformanceStatEntry 37 }
                   
                hwAdslAturChanIntervalCorrectedBlks  OBJECT-TYPE
                        SYNTAX      PerfIntervalCount
                        MAX-ACCESS  read-only
                        STATUS      current
                        DESCRIPTION
                            "Count of all blocks received with errors that were
                            corrected on this channel during this interval."
                        ::= { hwAdslPortPerformanceStatEntry 38 }

                hwAdslAturChanIntervalUncorrectBlks  OBJECT-TYPE
                        SYNTAX      PerfIntervalCount
                        MAX-ACCESS  read-only
                        STATUS      current
                        DESCRIPTION
                            "Count of all blocks received with uncorrectable
                            errors on this channel during this interval."
                        ::= { hwAdslPortPerformanceStatEntry 39 } 
                        
                hwAdslAtucIntervalSesL OBJECT-TYPE
                        SYNTAX      PerfIntervalCount
                        UNITS       "seconds"
                        MAX-ACCESS  read-only
                        STATUS      current
                        DESCRIPTION
                            "For the each interval, adslAtucIntervalSesL
                             reports the number of seconds during which
                             there have been severely errored seconds-line."
                        ::= { hwAdslPortPerformanceStatEntry 40 }

                hwAdslAtucIntervalUasL OBJECT-TYPE
                        SYNTAX      PerfIntervalCount
                        UNITS       "seconds"
                        MAX-ACCESS  read-only
                        STATUS      current
                        DESCRIPTION
                            "For the each interval, adslAtucIntervalUasL
                             reports the number of seconds during which
                             there have been unavailable seconds-line."
                        ::= { hwAdslPortPerformanceStatEntry 41 }
                
                hwAdslAturIntervalSesL OBJECT-TYPE
                        SYNTAX      PerfIntervalCount
                        UNITS       "seconds"
                        MAX-ACCESS  read-only
                        STATUS      current
                        DESCRIPTION
                            "For the each interval, adslAturIntervalSesL
                             reports the number of seconds during which
                             there have been severely errored seconds-line."
                        ::= { hwAdslPortPerformanceStatEntry 42 }

                hwAdslAturIntervalUasL OBJECT-TYPE
                        SYNTAX      PerfIntervalCount
                        UNITS       "seconds"
                        MAX-ACCESS  read-only
                        STATUS      current
                        DESCRIPTION
                            "For the each interval, adslAturIntervalUasL
                             reports the number of seconds during which
                             there have been unavailable seconds-line."
                        ::= { hwAdslPortPerformanceStatEntry 43 }

		
		
--  hwAdslPortRateChangeTrapParaTable
--
        hwAdslPortRateChangeTrapParaTable OBJECT-TYPE
			SYNTAX SEQUENCE OF HwAdslPortRateChangeTrapParaEntry
			MAX-ACCESS not-accessible
			STATUS current
			DESCRIPTION
				"
				ADSL line rate change trap parameter table.
				"
			::= { adslMibObjects 65547 }
		
		hwAdslPortRateChangeTrapParaEntry OBJECT-TYPE
			SYNTAX HwAdslPortRateChangeTrapParaEntry
			MAX-ACCESS not-accessible
			STATUS current
			DESCRIPTION
				"An entry in the hwAdslPortRateChangeTrapParaTable"
			INDEX { ifIndex }
			::= { hwAdslPortRateChangeTrapParaTable 1 }
		
		HwAdslPortRateChangeTrapParaEntry ::=
			SEQUENCE{
				hwAdslPortRateChangeTrapIPIAID
					OCTET STRING,      
				hwAdslPortRateChangeTrapMUXID     
					OCTET STRING,
				hwAdslPortRateChangeTrapTimeStamp
					Counter32,      
				hwAdslPortRateChangeTrapDSLineRate  
					Gauge32,  
			        hwAdslPortRateChangeTrapUSLineRate  
					Gauge32,
				hwAdslPortRateChangeTrapEventType
					OCTET STRING,
				hwAdslPortRateChangeTrapDslType
			        OCTET STRING
				    }       
		
		hwAdslPortRateChangeTrapIPIAID OBJECT-TYPE
			SYNTAX OCTET STRING (SIZE (0..63))
		    MAX-ACCESS accessible-for-notify
		    STATUS current
			DESCRIPTION
				"The IPIAID of Line rate change trap."
 			::= { hwAdslPortRateChangeTrapParaEntry 1 }    
 					
 		hwAdslPortRateChangeTrapMUXID OBJECT-TYPE
			SYNTAX OCTET STRING (SIZE (0..20))
		    MAX-ACCESS accessible-for-notify
		    STATUS current
			DESCRIPTION
				"The MUXID of Line rate change trap."
 			::= { hwAdslPortRateChangeTrapParaEntry 2 }

  		hwAdslPortRateChangeTrapTimeStamp OBJECT-TYPE
			SYNTAX Counter32
			MAX-ACCESS accessible-for-notify
			STATUS current
			DESCRIPTION
				"The time stamp of Line rate change trap.
				Standard Unix format; as the number of seconds since 1/1/1970 (UNIT:Second)."
 			::= { hwAdslPortRateChangeTrapParaEntry 3 } 
 				
 		hwAdslPortRateChangeTrapDSLineRate OBJECT-TYPE
			SYNTAX Gauge32
			MAX-ACCESS accessible-for-notify
			STATUS current
			DESCRIPTION
				"Down stream line rate after line rate change."
 			::= { hwAdslPortRateChangeTrapParaEntry 4 }   
 			 		
 		hwAdslPortRateChangeTrapUSLineRate OBJECT-TYPE
			SYNTAX Gauge32
			MAX-ACCESS accessible-for-notify
			STATUS current
			DESCRIPTION
				"Up stream line rate after line rate change."
 			::= { hwAdslPortRateChangeTrapParaEntry 5 }
   
	    hwAdslPortRateChangeTrapEventType OBJECT-TYPE
			SYNTAX OCTET STRING (SIZE (0..2))
			MAX-ACCESS accessible-for-notify
			STATUS current
			DESCRIPTION
				"The change direct of line rate stream."
 			::= { hwAdslPortRateChangeTrapParaEntry 6 }	
 			
 	    hwAdslPortRateChangeTrapDslType OBJECT-TYPE
			SYNTAX OCTET STRING (SIZE (0..5))
			MAX-ACCESS accessible-for-notify
			STATUS current
			DESCRIPTION
				"Line rate change port's DSL type."
 			::= { hwAdslPortRateChangeTrapParaEntry 7 } 
 			    	    
--  hwXdslSysManagementParaTable 
--    
        hwXdslSysManagementParaTable OBJECT IDENTIFIER ::= { adslMibObjects 65548 }			 
		hwAdslPortRateChangeTrapConfig OBJECT-TYPE
			SYNTAX INTEGER
				{
				enabled(1),
				disabled(2)
				}			
			MAX-ACCESS read-write
			STATUS current
			DESCRIPTION
				"Enable/Disable ADSL port line-rate change trap feature"
			::= { hwXdslSysManagementParaTable 1 }

--


-- adslAtucPerfDataTable
		-- 1.3.6.1.2.1.10.94.1.1.6.1.65535
		hwAdslAtucPerfFailInits OBJECT-TYPE
			SYNTAX Counter32
			MAX-ACCESS read-only
			STATUS current
			DESCRIPTION
				"Count of the line initialization failed attempts since agent reset."
			::= { adslAtucPerfDataEntry 65535 }
		
		-- 1.3.6.1.2.1.10.94.1.1.6.1.65536
		hwAdslAtucPerfCurr15MinFailInits OBJECT-TYPE
			SYNTAX Counter32
			MAX-ACCESS read-only
			STATUS current
			DESCRIPTION
				"Count of the line initialization failed attempts in the current 15 minute interval. "
			::= { adslAtucPerfDataEntry 65536 }
		
		-- 1.3.6.1.2.1.10.94.1.1.6.1.65537
		hwAdslAtucPerfCurr1DayFailInits OBJECT-TYPE
			SYNTAX Counter32
			MAX-ACCESS read-only
			STATUS current
			DESCRIPTION
				"Count of the line initialization failed attempts in the day as measured by adslAtucPerfCurr1DayTimeElapsed.
				"
			::= { adslAtucPerfDataEntry 65537 }
		
		-- 1.3.6.1.2.1.10.94.1.1.6.1.65538
		hwAdslAtucPerfPrev1DayFailInits OBJECT-TYPE
			SYNTAX Counter32
			MAX-ACCESS read-only
			STATUS current
			DESCRIPTION
				"Count of the line initialization failed attempts in the most recent previous 1-day period."
			::= { adslAtucPerfDataEntry 65538 }
		
-- adslAtucIntervalTable
		-- 1.3.6.1.2.1.10.94.1.1.8.1.65535
		hwAdslAtucIntervalFailInits OBJECT-TYPE
			SYNTAX Counter32
			MAX-ACCESS read-only
			STATUS current
			DESCRIPTION
				"Count of the line initialization failed attempts during the interval."
			::= { adslAtucIntervalEntry 65535 }
		
-- adslAtucChanPerfDataTable

        hwadslAtucChanRtxCW OBJECT-TYPE
            SYNTAX      Gauge32
            UNITS       ""
            MAX-ACCESS  read-only
            STATUS      current
            DESCRIPTION
                "Count of units request retransmission since agent reset."
            ::= { adslAtucChanPerfDataEntry 65548 }
    
        hwadslAtucChanRtxCorrectedCW OBJECT-TYPE
            SYNTAX      Gauge32
            UNITS       ""
            MAX-ACCESS  read-only
            STATUS      current
            DESCRIPTION
                "Count of units corrected by retransmission since agent reset."
            ::= { adslAtucChanPerfDataEntry 65549 }
    
        hwadslAtucChanRtxUncorrectedCW OBJECT-TYPE
            SYNTAX      Gauge32
            UNITS       ""
            MAX-ACCESS  read-only
            STATUS      current
            DESCRIPTION
                "Count of units uncorrected by retransmission since agent reset."
            ::= { adslAtucChanPerfDataEntry 65550 }
    
        hwadslAtucChanPerfCurr15MinRtxCW OBJECT-TYPE
            SYNTAX      Gauge32
            UNITS       ""
            MAX-ACCESS  read-only
            STATUS      current
            DESCRIPTION
                "
                Count of units request retransmission on this
                channel within the current 15 minute interval.
                "
            ::= { adslAtucChanPerfDataEntry 65551 }
    
        hwadslAtucChanPerfCurr15MinRtxCorrectedCW OBJECT-TYPE
            SYNTAX      Gauge32
            UNITS       ""
            MAX-ACCESS  read-only
            STATUS      current
            DESCRIPTION
                "
                Count of units corrected by retransmission on this
                channel within the current 15 minute interval.
                "
            ::= { adslAtucChanPerfDataEntry 65552 }
    
        hwadslAtucChanPerfCurr15MinRtxUncorrectedCW OBJECT-TYPE
            SYNTAX      Gauge32
            UNITS       ""
            MAX-ACCESS  read-only
            STATUS      current
            DESCRIPTION
                "Count of units uncorrected by retransmission on
                this channel within the current 15 minute interval.
                "
            ::= { adslAtucChanPerfDataEntry 65553 }
    
        hwadslAtucChanPerfCurr1DayRtxCW OBJECT-TYPE
            SYNTAX      Gauge32
            UNITS       ""
            MAX-ACCESS  read-only
            STATUS      current
            DESCRIPTION
                "
                Count of units request retransmission on
                this channel during the current day.
                "
            ::= { adslAtucChanPerfDataEntry 65554 }
    
        hwadslAtucChanPerfCurr1DayRtxCorrectedCW OBJECT-TYPE
            SYNTAX      Gauge32
            UNITS       ""
            MAX-ACCESS  read-only
            STATUS      current
            DESCRIPTION
                "
                Count of units corrected by retransmission
                on this channel during the current day.
                "
            ::= { adslAtucChanPerfDataEntry 65555 }
    
        hwadslAtucChanPerfCurr1DayRtxUncorrectedCW OBJECT-TYPE
            SYNTAX      Gauge32
            UNITS       ""
            MAX-ACCESS  read-only
            STATUS      current
            DESCRIPTION
                "
                Count of units uncorrected by retransmission
                on this channel during the current day.
                "
            ::= { adslAtucChanPerfDataEntry 65556 }
    
        hwadslAtucChanPerfPrev1DayRtxCW OBJECT-TYPE
            SYNTAX      Gauge32
            UNITS       ""
            MAX-ACCESS  read-only
            STATUS      current
            DESCRIPTION
                "
                Count of units request retransmission on this channel
                within the most recent previous 1-day period.
                "
            ::= { adslAtucChanPerfDataEntry 65557 }
    
        hwadslAtucChanPerfPrev1DayRtxCorrectedCW OBJECT-TYPE
            SYNTAX      Gauge32
            UNITS       ""
            MAX-ACCESS  read-only
            STATUS      current
            DESCRIPTION
                "
                Count of units corrected by retransmission on this
                channel within the most recent previous 1-day period.
                "
            ::= { adslAtucChanPerfDataEntry 65558 }
    
        hwadslAtucChanPerfPrev1DayRtxUncorrectedCW OBJECT-TYPE
            SYNTAX      Gauge32
            UNITS       ""
            MAX-ACCESS  read-only
            STATUS      current
            DESCRIPTION
                "
                Count of units uncorrected by retransmission on this
                channel within the most recent previous 1-day period.
                "
            ::= { adslAtucChanPerfDataEntry 65559 }

-- adslAturChanPerfDataTable

        hwadslAturChanRtxCW OBJECT-TYPE
            SYNTAX      Gauge32
            UNITS       ""
            MAX-ACCESS  read-only
            STATUS      current
            DESCRIPTION
                "Count of units request retransmission since agent reset."
            ::= { adslAturChanPerfDataEntry 65548 }
    
        hwadslAturChanRtxCorrectedCW OBJECT-TYPE
            SYNTAX      Gauge32
            UNITS       ""
            MAX-ACCESS  read-only
            STATUS      current
            DESCRIPTION
                "Count of units corrected by retransmission since agent reset."
            ::= { adslAturChanPerfDataEntry 65549 }
    
        hwadslAturChanRtxUncorrectedCW OBJECT-TYPE
            SYNTAX      Gauge32
            UNITS       ""
            MAX-ACCESS  read-only
            STATUS      current
            DESCRIPTION
                "Count of units uncorrected by retransmission since agent reset."
            ::= { adslAturChanPerfDataEntry 65550 }
    
        hwadslAturChanPerfCurr15MinRtxCW OBJECT-TYPE
            SYNTAX      Gauge32
            UNITS       ""
            MAX-ACCESS  read-only
            STATUS      current
            DESCRIPTION
                "
                Count of units request retransmission on this
                channel within the current 15 minute interval.
                "
            ::= { adslAturChanPerfDataEntry 65551 }
    
        hwadslAturChanPerfCurr15MinRtxCorrectedCW OBJECT-TYPE
            SYNTAX      Gauge32
            UNITS       ""
            MAX-ACCESS  read-only
            STATUS      current
            DESCRIPTION
                "
                Count of units corrected by retransmission on
                this channel within the current 15 minute interval.
                "
            ::= { adslAturChanPerfDataEntry 65552 }
    
        hwadslAturChanPerfCurr15MinRtxUncorrectedCW OBJECT-TYPE
            SYNTAX      Gauge32
            UNITS       ""
            MAX-ACCESS  read-only
            STATUS      current
            DESCRIPTION
                "
                Count of units uncorrected by retransmission on
                this channel within the current 15 minute interval.
                "
            ::= { adslAturChanPerfDataEntry 65553 }
    
        hwadslAturChanPerfCurr1DayRtxCW OBJECT-TYPE
            SYNTAX      Gauge32
            UNITS       ""
            MAX-ACCESS  read-only
            STATUS      current
            DESCRIPTION
                "
                Count of units request retransmission on
                this channel during the current day.
                "
            ::= { adslAturChanPerfDataEntry 65554 }
    
        hwadslAturChanPerfCurr1DayRtxCorrectedCW OBJECT-TYPE
            SYNTAX      Gauge32
            UNITS       ""
            MAX-ACCESS  read-only
            STATUS      current
            DESCRIPTION
                "
                Count of units corrected by retransmission
                on this channel during the current day.
                "
            ::= { adslAturChanPerfDataEntry 65555 }
    
        hwadslAturChanPerfCurr1DayRtxUncorrectedCW OBJECT-TYPE
            SYNTAX      Gauge32
            UNITS       ""
            MAX-ACCESS  read-only
            STATUS      current
            DESCRIPTION
                "
                Count of units uncorrected by retransmission
                on this channel during the current day.
                "
            ::= { adslAturChanPerfDataEntry 65556 }
    
        hwadslAturChanPerfPrev1DayRtxCW OBJECT-TYPE
            SYNTAX      Gauge32
            UNITS       ""
            MAX-ACCESS  read-only
            STATUS      current
            DESCRIPTION
                "
                Count of units request retransmission on this
                channel within the most recent previous 1-day period.
                "
            ::= { adslAturChanPerfDataEntry 65557 }
    
        hwadslAturChanPerfPrev1DayRtxCorrectedCW OBJECT-TYPE
            SYNTAX      Gauge32
            UNITS       ""
            MAX-ACCESS  read-only
            STATUS      current
            DESCRIPTION
                "
                Count of units corrected by retransmission on this
                channel within the most recent previous 1-day period.
                "
            ::= { adslAturChanPerfDataEntry 65558 }
    
        hwadslAturChanPerfPrev1DayRtxUncorrectedCW OBJECT-TYPE
            SYNTAX      Gauge32
            UNITS       ""
            MAX-ACCESS  read-only
            STATUS      current
            DESCRIPTION
                "
                Count of units uncorrected by retransmission on this
                channel within the most recent previous 1-day period.
                "
            ::= { adslAturChanPerfDataEntry 65559 }

-- adslAtucChanIntervalTable

        hwadslAtucChanIntervalRtxCW OBJECT-TYPE
            SYNTAX      Gauge32
            UNITS       ""
            MAX-ACCESS  read-only
            STATUS      current
            DESCRIPTION
                "Count of units request retransmission on this channel during this interval."
            ::= { adslAtucChanIntervalEntry 65539 }
    
        hwadslAtucChanIntervalRtxCorrectedCW OBJECT-TYPE
            SYNTAX      Gauge32
            UNITS       ""
            MAX-ACCESS  read-only
            STATUS      current
            DESCRIPTION
                "Count of units corrected by retransmission on this channel during this interval."
            ::= { adslAtucChanIntervalEntry 65540 }
    
        hwadslAtucChanIntervalRtxUncorrectedCW OBJECT-TYPE
            SYNTAX      Gauge32
            UNITS       ""
            MAX-ACCESS  read-only
            STATUS      current
            DESCRIPTION
                "Count of units uncorrected by retransmission on this channel during this interval."
            ::= { adslAtucChanIntervalEntry 65541 }
        
-- adslAturChanIntervalTable

        hwadslAturChanIntervalRtxCW OBJECT-TYPE
            SYNTAX      Gauge32
            UNITS       ""
            MAX-ACCESS  read-only
            STATUS      current
            DESCRIPTION
                "Count of units request retransmission on this channel during this interval."
            ::= { adslAturChanIntervalEntry 65539 }
    
        hwadslAturChanIntervalRtxCorrectedCW OBJECT-TYPE
            SYNTAX      Gauge32
            UNITS       ""
            MAX-ACCESS  read-only
            STATUS      current
            DESCRIPTION
                "Count of units corrected by retransmission on this channel during this interval."
            ::= { adslAturChanIntervalEntry 65540 }
    
        hwadslAturChanIntervalRtxUncorrectedCW OBJECT-TYPE
            SYNTAX      Gauge32
            UNITS       ""
            MAX-ACCESS  read-only
            STATUS      current
            DESCRIPTION
                "Count of units uncorrected by retransmission on this channel during this interval."
            ::= { adslAturChanIntervalEntry 65541 }    

--
-- end PHY-R
--
--hwAdsl2SCStatusTable
--
--
		hwAdsl2SCStatusTable OBJECT-TYPE 	
			SYNTAX SEQUENCE OF HwAdsl2SCStatusEntry
			MAX-ACCESS not-accessible
			STATUS current
			DESCRIPTION
				"
				The table adsl2SCStatusTable contains status parameters
                                of the ADSL2 sub-carriers.
				"
		 ::= { adslMibObjects 65549 }

		hwAdsl2SCStatusEntry OBJECT-TYPE
			SYNTAX HwAdsl2SCStatusEntry
			MAX-ACCESS not-accessible
			STATUS current
			DESCRIPTION
				"The table Adsl2SCStatusEntry contains status parameters
                                 of the ADSL2 sub-carriers.
                                 One index of this table is an interface index where the
 	                         interface has an ifType of adsl2plus. A second index of this
 	                         table is the transmission direction.."
			INDEX {        
			      ifIndex,
			      hwAdsl2SCStatusDirection 
			      }
			::= { hwAdsl2SCStatusTable 1 }

                HwAdsl2SCStatusEntry ::=
			SEQUENCE {      
			      hwAdsl2SCStatusDirection       
			            INTEGER,
			      hwAdsl2SCStatusSnr             
			            OCTET STRING,
			      hwAdsl2SCStatusBitsAlloc       
			            OCTET STRING,
			      hwAdsl2SCStatusGainAlloc      
			            OCTET STRING,
			      hwAdsl2SCStatusLog             
			            OCTET STRING, 
			      hwAdsl2SCStatusQln             
			            OCTET STRING,	
			      hwAdsl2SCStatusSnrMargin       
			            OCTET STRING,
			      hwAdsl2SCStatusTxPSD          
			            OCTET STRING
			      }   
			
		hwAdsl2SCStatusDirection  OBJECT-TYPE
                        SYNTAX INTEGER
		        {   
		        	upstream(1),
		        	downstream(2)	
		        }
               MAX-ACCESS  not-accessible
               STATUS      current
               DESCRIPTION
	               "The direction of the sub-carrier is either
	               upstream or downstream."
               ::= { hwAdsl2SCStatusEntry 1 } 
               
               hwAdsl2SCStatusSnr  OBJECT-TYPE
	               SYNTAX OCTET STRING  (SIZE(0..512))
	               MAX-ACCESS  read-only
	               STATUS      current
	               DESCRIPTION
	               "The SNR Margin per sub-carrier, expressing the ratio between
	                the received signal power and received noise power per
	                subscriber.  It is an array of 512 octets, designed for
	                supporting up to 512 (downstream) sub-carriers.
	                The number of utilized octets on downstream direction depends
	                on NSCds, and on upstream direction it depends on NSCus.  This
	                value is referred to here as NSC.
	                Octet i (0 <= i < NSC) is set to a value in the range 0 to
	                254 to indicate that the respective downstream or upstream sub-
	                carrier i has SNR of: (-32 + Adsl2SubcarrierSnr(i)/2) in dB
	                (i.e., -32 to 95dB).
	                The special value 255 means that no measurement could be done
	                for the subcarrier because it is out of the PSD mask passband
	                or that the noise PSD is out of range to be represented.
	                Each value in this array is 8 bits wide."
               ::= { hwAdsl2SCStatusEntry 2 }  
               
               hwAdsl2SCStatusBitsAlloc  OBJECT-TYPE
	               SYNTAX OCTET STRING  (SIZE(0..256))
	               MAX-ACCESS  read-only
	               STATUS      current
	               DESCRIPTION
	               "The bits allocation per sub-carrier.  An array of 256 octets
	                (512 nibbles), designed for supporting up to 512 (downstream)
	                sub-carriers.
	                The number of utilized nibbles on downstream direction depends
	                on NSCds, and on upstream direction it depends on NSCus.  This
	                value is referred to here as NSC.
	                Nibble i (0 <= i < NSC) is set to a value in the range 0
	                to 15 to indicate that the respective downstream or upstream
	                sub-carrier i has the same amount of bits allocation."
               ::= { hwAdsl2SCStatusEntry 3 }  
               
               hwAdsl2SCStatusGainAlloc  OBJECT-TYPE
	               SYNTAX OCTET STRING  (SIZE(0..1024))
	               MAX-ACCESS  read-only
	               STATUS      current
	               DESCRIPTION
	               "The gain allocation per sub-carrier.  An array of 512 16-bits
	               values, designed for supporting up to 512 (downstream) sub-
	               carriers.
	               The number of utilized octets on downstream direction depends
	               on NSCds, and on upstream direction it depends on NSCus.  This
	               value is referred to here as NSC.
	               Value i (0 <= i < NSC) is in the range 0 to 4093 to indicate
	               that the respective downstream or upstream sub-carrier i has the
	               same amount of gain value.
	               The gain value is represented as a multiple of 1/512 on a
	               linear scale.  Each value in this array is 16 bits wide and is
	               stored in big endian format."
               ::= { hwAdsl2SCStatusEntry 4 }     
               
               hwAdsl2SCStatusLog  OBJECT-TYPE
	               SYNTAX OCTET STRING  (SIZE(0..1024))
	               MAX-ACCESS  read-only
	               STATUS      current
	               DESCRIPTION
	               "An array of up to 512 real H(f) logarithmic representation
	                values in dB for the respective transmission direction.  It is
	                designed to support up to 512 (downstream) sub-carriers.
	                The number of utilized values on downstream direction depends
	                on NSCds, and on upstream direction it depends on NSCus.  This
	                value is referred to here as NSC.
	                Each array entry represents the real Hlog(f = i*Df) value for a
	                particular sub-carrier index i, (0 <= i < NSC).
	                The real Hlog(f) value is represented as (6-m(i)/10), with m(i)
	                in the range 0 to 1022.  A special value m=1023 indicates that
	                no measurement could be done for the subcarrier because it is
	                out of the passband or that the attenuation is out of range to
	                be represented.  This parameter is applicable in loop
	                diagnostic procedure and initialization.
	                Each value in this array is 16 bits wide and is stored
	                in big endian format."
               ::= { hwAdsl2SCStatusEntry 5 }     
               
               hwAdsl2SCStatusQln  OBJECT-TYPE
	               SYNTAX OCTET STRING  (SIZE(0..512))
	               MAX-ACCESS  read-only
	               STATUS      current
	               DESCRIPTION
	               "An array of up to 512 real Quiet Line Noise values in dBm/Hz
	               for the respective transmission direction.  It is designed for
	               up to 512 (downstream) sub-carriers.
	               The number of utilized values on downstream direction depends
	               on NSCds, and on upstream direction it depends on NSCus.  This
	               value is referred to here as NSC.
	               Each array entry represents the QLN(f = i*Df) value for a
	               particular sub-carrier index i, (0 <= i < NSC).
	               The QLN(f) is represented as ( -23-n(i)/2), with n(i) in the
	               range 0 to 254.  A special value n(i)=255 indicates that no
	               measurement could be done for the subcarrier because it is out
	               of the passband or that the noise PSD is out of range to be
	               represented.
	               This parameter is applicable in loop diagnostic procedure and
	               initialization.  Each value in this array is 8 bits wide."
               ::= { hwAdsl2SCStatusEntry 6 }  
               
               hwAdsl2SCStatusSnrMargin  OBJECT-TYPE
	               SYNTAX OCTET STRING  (SIZE(0..1024))
	               MAX-ACCESS  read-only
	               STATUS      current
	               DESCRIPTION
	               "SNR Margin is the maximum increase in dB of the noise power
	                 received at the ATU (ATU-R on downstream direction and ATU-C
	                 on upstream direction), such that the BER requirements are met
	                 for all bearer channels received at the ATU.  It ranges from
	                 -640 to 630 units of 0.1 dB (physical values are -64 to
	                 63 dB).
	                 "
               ::= { hwAdsl2SCStatusEntry 7 }   
               
               hwAdsl2SCStatusTxPSD  OBJECT-TYPE
	               SYNTAX OCTET STRING  (SIZE(0..1024))
	               MAX-ACCESS  read-only
	               STATUS      current
	               DESCRIPTION
	               "The PSD MASK per sub-carrier.An array of 512 16-bits
 	                values, designed for supporting up to 512 (downstream) sub-carriers. 
 	                It ranges from -1400 to -300 units of 0.1 dBm/Hz (physical values
 	                are -140 to -30 dBm/Hz)"
               ::= { hwAdsl2SCStatusEntry 8 }

--hwxdslDynamicProfTable
--
--
    hwxdslDynamicProfTable   OBJECT-TYPE
         SYNTAX          SEQUENCE OF HwxdslDynamicProfEntry
         MAX-ACCESS      not-accessible
         STATUS          current
         DESCRIPTION
             "This table includes common parameters of the xdsl Dynamic profile."
         ::= { adslMibObjects 65550  }
            
    hwxdslDynamicProfEntry   OBJECT-TYPE
             SYNTAX          HwxdslDynamicProfEntry
             MAX-ACCESS      not-accessible
             STATUS          current
             DESCRIPTION     "An entry in hwxdslDynamicProfTable."
             INDEX           {  hwxdslDynamicProfProfileName }
         ::= { hwxdslDynamicProfTable 1 }
         
    HwxdslDynamicProfEntry ::=
             SEQUENCE {
             hwxdslDynamicProfProfileName           SnmpAdminString,
             hwxdslDynamicProfXtuTransSysEna        BITS,
             hwxdslDynamicProfBitSwapDS             INTEGER,
             hwxdslDynamicProfBitSwapUS             INTEGER,
             hwxdslDynamicProfTargetSnrmDs          Unsigned32,
             hwxdslDynamicProfTargetSnrmUs          Unsigned32,  
             hwxdslDynamicProfMaxSnrmDs             Unsigned32,
             hwxdslDynamicProfMaxSnrmUs             Unsigned32,
             hwxdslDynamicProfMinSnrmDs             Unsigned32,
             hwxdslDynamicProfMinSnrmUs             Unsigned32,             
             hwxdslDynamicProfCh1MinProtectionDs    INTEGER,
             hwxdslDynamicProfCh1MinProtectionUs    INTEGER,
             hwxdslDynamicProfCh1MaxDelayDs         Unsigned32,
             hwxdslDynamicProfCh1MaxDelayUs         Unsigned32,
             hwxdslDynamicProfCh2MinProtectionDs    INTEGER,
             hwxdslDynamicProfCh2MinProtectionUs    INTEGER,
             hwxdslDynamicProfCh2MaxDelayDs         Unsigned32,
             hwxdslDynamicProfCh2MaxDelayUs         Unsigned32,
             hwxdslDynamicProfPmMode                BITS,
             hwxdslDynamicProfL0Time                Unsigned32,
             hwxdslDynamicProfL2Time                Unsigned32,
             hwxdslDynamicProfL2Atpr                Unsigned32,
             hwxdslDynamicProfL2Atprt               Unsigned32,
             hwxdslDynamicProfDpboEPsd              OCTET STRING,
             hwxdslDynamicProfDpboEsEL              Unsigned32,
             hwxdslDynamicProfDpboEscm              OCTET STRING,
             hwxdslDynamicProfDpboMus               Unsigned32,
             hwxdslDynamicProfDpboFMin              Unsigned32,
             hwxdslDynamicProfDpboFMax              Unsigned32,
             hwxdslDynamicProfUpboPsdBand           OCTET STRING,
             hwxdslDynamicProfUpboKLF               INTEGER,
             hwxdslDynamicProfUpboKL                Unsigned32,
             hwxdslDynamicProfRfiBands              SnmpAdminString,
             hwxdslDynamicProfToneBlackOut          SnmpAdminString,
             hwxdslDynamicProfCarMaskDS             OCTET STRING,
             hwxdslDynamicProfCarMaskUS             OCTET STRING,
             hwxdslDynamicProfXdslMode              INTEGER,
             hwxdslDynamicProfMaxNomPsdDs           Integer32,
             hwxdslDynamicProfMaxNomPsdUs           Integer32,
             hwxdslDynamicProfMaxNomAtpDs           Unsigned32,
             hwxdslDynamicProfMaxNomAtpUs           Unsigned32,
             hwxdslDynamicProfPsdMaskDs             OCTET STRING,
             hwxdslDynamicProfPsdMaskUs             OCTET STRING,
             hwxdslDynamicProfLimitMask             INTEGER,
             hwxdslDynamicProfClassMask             INTEGER,             
             hwxdslDynamicProfBandOptUsage            INTEGER,
             hwxdslDynamicProfVirtualNoiseModeDs    INTEGER,
             hwxdslDynamicProfVirtualNoiseModeUs    INTEGER,
             hwxdslDynamicProfVirtualNoiseDs        OCTET STRING,
             hwxdslDynamicProfVirtualNoiseUs        OCTET STRING,
             hwxdslDynamicProfRowStatus             RowStatus             
             }
             
    hwxdslDynamicProfProfileName OBJECT-TYPE
             SYNTAX      SnmpAdminString(SIZE(1..32))
             MAX-ACCESS  not-accessible
             STATUS      current
             DESCRIPTION
                 "The name of xdsl Dynamic Profile."
         ::= { hwxdslDynamicProfEntry 1 }
         
    hwxdslDynamicProfXtuTransSysEna OBJECT-TYPE
             SYNTAX   BITS {
				                     ansit1413(0),
				                     etsi(1),
				                     g9921PotsNonOverlapped(2),
				                     g9921PotsOverlapped(3),
				                     g9921IsdnNonOverlapped(4),
				                     g9921isdnOverlapped(5),
				                     g9921tcmIsdnNonOverlapped(6),
				                     g9921tcmIsdnOverlapped(7),
				                     g9922potsNonOverlapeed(8),
				                     g9922potsOverlapped(9),
				                     g9922tcmIsdnNonOverlapped(10),
				                     g9922tcmIsdnOverlapped(11),
				                     g9921tcmIsdnSymmetric(12),
				                     reserved1(13),
				                     reserved2(14),
				                     reserved3(15),
				                     reserved4(16),
				                     reserved5(17),
				                     g9923PotsNonOverlapped(18),
				                     g9923PotsOverlapped(19),
				                     g9923IsdnNonOverlapped(20),
				                     g9923isdnOverlapped(21),
				                     reserved6(22),
				                     reserved7(23),
				                     g9924potsNonOverlapeed(24),
				                     g9924potsOverlapped(25),
				                     reserved8(26),
				                     reserved9(27),
				                     g9923AnnexIAllDigNonOverlapped(28),
				                     g9923AnnexIAllDigOverlapped(29),
				                     g9923AnnexJAllDigNonOverlapped(30),
				                     g9923AnnexJAllDigOverlapped(31),
				                     g9924AnnexIAllDigNonOverlapped(32),
				                     g9924AnnexIAllDigOverlapped(33),
				                     g9923AnnexLMode1NonOverlapped(34),
				                     g9923AnnexLMode2NonOverlapped(35),
				                     g9923AnnexLMode3Overlapped(36),
				                     g9923AnnexLMode4Overlapped(37),
				                     g9923AnnexMPotsNonOverlapped(38),
				                     g9923AnnexMPotsOverlapped(39),
				                     g9925PotsNonOverlapped(40),
				                     g9925PotsOverlapped(41),
				                     g9925IsdnNonOverlapped(42),
				                     g9925isdnOverlapped(43),
				                     reserved10(44),
				                     reserved11(45),
				                     g9925AnnexIAllDigNonOverlapped(46),
				                     g9925AnnexIAllDigOverlapped(47),
				                     g9925AnnexJAllDigNonOverlapped(48),
				                     g9925AnnexJAllDigOverlapped(49),
				                     g9925AnnexMPotsNonOverlapped(50),
				                     g9925AnnexMPotsOverlapped(51),
				                     reserved12(52),
				                     reserved13(53),
				                     reserved14(54),
				                     reserved15(55),
				                     reserved16(56),
				                     reserved17(57),
				                     reserved18(58),
				                     reserved19(59),
				                     reserved20(60),
				                     reserved21(61),
				                     reserved22(62),
				                     reserved23(63),
						     reserved24(64),
						     reserved25(65),
						     reserved26(66),
						     reserved27(67),
						     reserved28(68),
						     reserved29(69),
						     reserved30(70),
						     reserved31(71),
						     g9932AnnexAPots(72),
						     g9932AnnexAIsdn(73),
						     g9932AnnexBPots(74),
						     g9932AnnexBIsdn(75),
						     g9932AnnexCPots(76),
						     g9932AnnexCIsdn(77),
						     reserved32(78),
						     reserved33(79)
				                  }     				                  
		     MAX-ACCESS  read-create
             STATUS      current
             DESCRIPTION
                 "xTU Transmission System Enabling (ATSE).  A list of the
 	               different coding types enabled in this profile.  It is coded
 	               in a bit-map representation with 1 or more bits set.  A bit
 	               set to  '1' means that the XTUs may apply the respective
 	               coding for the XDSL line.  A bit set to '0' means that
 	               the XTUs cannot apply the respective coding for the XDSL
 	               line.  All 'reserved' bits should be set to '0'.
                "
         ::= { hwxdslDynamicProfEntry 2 }
         
    hwxdslDynamicProfBitSwapDS OBJECT-TYPE
             SYNTAX      INTEGER {
             disable(1),
             enable(2)
             }
             MAX-ACCESS  read-create
             STATUS      current
             DESCRIPTION
                 "Enables or disables the bit swap downstream of a line."
         ::= { hwxdslDynamicProfEntry 3 }
         
    hwxdslDynamicProfBitSwapUS OBJECT-TYPE
             SYNTAX      INTEGER {
             disable(1),
             enable(2)
             }
             MAX-ACCESS  read-create
             STATUS      current
             DESCRIPTION
                 "Enables or disables the bit swap upstream of a line."
         ::= { hwxdslDynamicProfEntry 4 }
         
    hwxdslDynamicProfTargetSnrmDs OBJECT-TYPE
             SYNTAX      Unsigned32(0..310)
             UNITS       "0.1 dB"
             MAX-ACCESS  read-create
             STATUS      current
             DESCRIPTION
                     "The target Noise Margin the xTU-R receiver shall achieve,
                      relative to the BER requirement for each of the downstream
                      bearer channels, to successfully complete initialization.
                      The target noise margin ranges from 0 to 310 units of 0.1 dB
                      (Physical values are 0 to 31 dB)."
         ::= { hwxdslDynamicProfEntry 5 }
         
    hwxdslDynamicProfTargetSnrmUs OBJECT-TYPE
             SYNTAX      Unsigned32(0..310)
             UNITS       "0.1 dB"
             MAX-ACCESS  read-create
             STATUS      current
             DESCRIPTION
                     "The target Noise Margin the xTU-C receiver shall achieve,
                      relative to the BER requirement for each of the downstream
                      bearer channels, to successfully complete initialization.
                      The target noise margin ranges from 0 to 310 units of 0.1 dB
                      (Physical values are 0 to 31 dB)."
         ::= { hwxdslDynamicProfEntry 6 }
         
    hwxdslDynamicProfMaxSnrmDs OBJECT-TYPE
             SYNTAX      Unsigned32(0..310)
             UNITS       "0.1 dB"
             MAX-ACCESS  read-create
             STATUS      current
             DESCRIPTION
                     "The maximum Noise Margin the xTU-R receiver shall achieve,
                      relative to the BER requirement for each of the downstream
                      bearer channels, to successfully complete initialization.
                      The target noise margin ranges from 0 to 310 units of 0.1 dB
                      (Physical values are 0 to 31 dB)."
         ::= { hwxdslDynamicProfEntry 7 }
         
    hwxdslDynamicProfMaxSnrmUs OBJECT-TYPE
             SYNTAX      Unsigned32(0..310)
             UNITS       "0.1 dB"
             MAX-ACCESS  read-create
             STATUS      current
             DESCRIPTION
                     "The maximum Noise Margin the xTU-C receiver shall achieve,
                      relative to the BER requirement for each of the downstream
                      bearer channels, to successfully complete initialization.
                      The target noise margin ranges from 0 to 310 units of 0.1 dB
                      (Physical values are 0 to 31 dB)."
         ::= { hwxdslDynamicProfEntry 8 }       
           
    hwxdslDynamicProfMinSnrmDs OBJECT-TYPE
             SYNTAX      Unsigned32(0..310)
             UNITS       "0.1 dB"
             MAX-ACCESS  read-create
             STATUS      current
             DESCRIPTION
                     "The minimum Noise Margin the xTU-R receiver shall achieve,
                      relative to the BER requirement for each of the downstream
                      bearer channels, to successfully complete initialization.
                      The target noise margin ranges from 0 to 310 units of 0.1 dB
                      (Physical values are 0 to 31 dB)."
         ::= { hwxdslDynamicProfEntry 9 }                      
         
    hwxdslDynamicProfMinSnrmUs OBJECT-TYPE
             SYNTAX      Unsigned32(0..310)
             UNITS       "0.1 dB"
             MAX-ACCESS  read-create
             STATUS      current
             DESCRIPTION
                     "The minimum Noise Margin the xTU-C receiver shall achieve,
                      relative to the BER requirement for each of the downstream
                      bearer channels, to successfully complete initialization.
                      The target noise margin ranges from 0 to 310 units of 0.1 dB
                      (Physical values are 0 to 31 dB)."
         ::= { hwxdslDynamicProfEntry 10 }         
        
    hwxdslDynamicProfCh1MinProtectionDs OBJECT-TYPE
             SYNTAX      INTEGER {
                          noProtection (1),
                          halfSymbol (2),
                          singleSymbol (3),
                          twoSymbols (4),
                          threeSymbols (5),
                          fourSymbols (6),
                          fiveSymbols (7),
                          sixSymbols (8),
                          sevenSymbols (9),
                          eightSymbols (10),
                          nineSymbols (11),
                          tenSymbols (12),
                          elevenSymbols (13),
                          twelveSymbols (14),
                          thirteenSymbols (15),
                          fourteenSymbols (16),
                          fifteenSymbols (17),
                          sixteenSymbols (18)
                        }             
             MAX-ACCESS  read-create
             STATUS      current
             DESCRIPTION
                 "Minimum Impulse Noise Protection on Downstream direction.  The
                  minimum impulse noise protection for the bearer channel,
                  expressed in symbols.  The parameter can take the following
                  values: noProtection (i.e., INP not required), halfSymbol
                  (i.e., INP length is 1/2 symbol) and 1-16 symbols in steps
                  of 1 symbol."
             REFERENCE    "ITU-T G.997.1, paragraph 7.3.2.3"
         ::= { hwxdslDynamicProfEntry 11 }
         
     hwxdslDynamicProfCh1MinProtectionUs OBJECT-TYPE
             SYNTAX      INTEGER {
                          noProtection (1),
                          halfSymbol (2),
                          singleSymbol (3),
                          twoSymbols (4),
                          threeSymbols (5),
                          fourSymbols (6),
                          fiveSymbols (7),
                          sixSymbols (8),
                          sevenSymbols (9),
                          eightSymbols (10),
                          nineSymbols (11),
                          tenSymbols (12),
                          elevenSymbols (13),
                          twelveSymbols (14),
                          thirteenSymbols (15),
                          fourteenSymbols (16),
                          fifteenSymbols (17),
                          sixteenSymbols (18)
                        }             
             MAX-ACCESS  read-create
             STATUS      current
             DESCRIPTION
                 "Minimum Impulse Noise Protection on Upstream direction.  The
                  minimum impulse noise protection for the bearer channel,
                  expressed in symbols.  The parameter can take the following
                  values: noProtection (i.e., INP not required), halfSymbol
                  (i.e., INP length is 1/2 symbol) and 1-16 symbols in steps
                  of 1 symbol."
             REFERENCE    "ITU-T G.997.1, paragraph 7.3.2.3"
         ::= { hwxdslDynamicProfEntry 12 }
         
     hwxdslDynamicProfCh1MaxDelayDs OBJECT-TYPE
             SYNTAX      Unsigned32(0..200)
             UNITS       "milliseconds"
             MAX-ACCESS  read-create
             STATUS      current
             DESCRIPTION
                 "Maximum Interleave Delay on Downstream direction.  The maximum
                  one-way interleaving delay introduced by the PMS-TC on
                  Downstream direction.  The XTUs shall choose the S (factor) and
                  D (depth) values such that the actual one-way interleaving
                  delay is as close as possible to, but less than or equal to, 
                  hwxdslDynamicProfCh1MaxDelayDs.  The delay is coded in ms, 
                  with the value 0 indicating no delay bound is being imposed."
             REFERENCE    "ITU-T G.997.1, paragraph 7.3.2.2"
         ::= { hwxdslDynamicProfEntry 13 }
         
     hwxdslDynamicProfCh1MaxDelayUs OBJECT-TYPE
             SYNTAX      Unsigned32(0..200)
             UNITS       "milliseconds"
             MAX-ACCESS  read-create
             STATUS      current
             DESCRIPTION
                 "Maximum Interleave Delay on Upstream direction.  The maximum
                  one-way interleaving delay introduced by the PMS-TC on
                  Upstream direction.  The XTUs shall choose the S (factor) and
                  D (depth) values such that the actual one-way interleaving
                  delay is as close as possible to, but less than or equal to, 
                  hwxdslDynamicProfCh1MaxDelayUs.  The delay is coded in ms, 
                  with the value 0 indicating no delay bound is being imposed."
             REFERENCE    "ITU-T G.997.1, paragraph 7.3.2.2"
         ::= { hwxdslDynamicProfEntry 14 }
                  
     hwxdslDynamicProfCh2MinProtectionDs OBJECT-TYPE
             SYNTAX      INTEGER {
                          noProtection (1),
                          halfSymbol (2),
                          singleSymbol (3),
                          twoSymbols (4),
                          threeSymbols (5),
                          fourSymbols (6),
                          fiveSymbols (7),
                          sixSymbols (8),
                          sevenSymbols (9),
                          eightSymbols (10),
                          nineSymbols (11),
                          tenSymbols (12),
                          elevenSymbols (13),
                          twelveSymbols (14),
                          thirteenSymbols (15),
                          fourteenSymbols (16),
                          fifteenSymbols (17),
                          sixteenSymbols (18)
                        }             
             MAX-ACCESS  read-create
             STATUS      current
             DESCRIPTION
                 "Minimum Impulse Noise Protection on Downstream direction.  The
                  minimum impulse noise protection for the bearer channel,
                  expressed in symbols.  The parameter can take the following
                  values: noProtection (i.e., INP not required), halfSymbol
                  (i.e., INP length is 1/2 symbol) and 1-16 symbols in steps
                  of 1 symbol."
             REFERENCE    "ITU-T G.997.1, paragraph 7.3.2.3"
         ::= { hwxdslDynamicProfEntry 15 }
         
     hwxdslDynamicProfCh2MinProtectionUs OBJECT-TYPE
             SYNTAX      INTEGER {
                          noProtection (1),
                          halfSymbol (2),
                          singleSymbol (3),
                          twoSymbols (4),
                          threeSymbols (5),
                          fourSymbols (6),
                          fiveSymbols (7),
                          sixSymbols (8),
                          sevenSymbols (9),
                          eightSymbols (10),
                          nineSymbols (11),
                          tenSymbols (12),
                          elevenSymbols (13),
                          twelveSymbols (14),
                          thirteenSymbols (15),
                          fourteenSymbols (16),
                          fifteenSymbols (17),
                          sixteenSymbols (18)
                        }             
             MAX-ACCESS  read-create
             STATUS      current
             DESCRIPTION
                 "Minimum Impulse Noise Protection on Upstream direction.  The
                  minimum impulse noise protection for the bearer channel,
                  expressed in symbols.  The parameter can take the following
                  values: noProtection (i.e., INP not required), halfSymbol
                  (i.e., INP length is 1/2 symbol) and 1-16 symbols in steps
                  of 1 symbol."
             REFERENCE    "ITU-T G.997.1, paragraph 7.3.2.3"
         ::= { hwxdslDynamicProfEntry 16 }

     hwxdslDynamicProfCh2MaxDelayDs OBJECT-TYPE
             SYNTAX      Unsigned32(0..200)
             UNITS       "milliseconds"
             MAX-ACCESS  read-create
             STATUS      current
             DESCRIPTION
                 "Maximum Interleave Delay on Downstream direction.  The maximum
                  one-way interleaving delay introduced by the PMS-TC on
                  Downstream direction.  The XTUs shall choose the S (factor) and
                  D (depth) values such that the actual one-way interleaving
                  delay is as close as possible to, but less than or equal to, 
                  hwxdslDynamicProfCh2MaxDelayDs.  The delay is coded in ms, 
                  with the value 0 indicating no delay bound is being imposed."
             REFERENCE    "ITU-T G.997.1, paragraph 7.3.2.2"
         ::= { hwxdslDynamicProfEntry 17 }
         
     hwxdslDynamicProfCh2MaxDelayUs OBJECT-TYPE
             SYNTAX      Unsigned32(0..200)
             UNITS       "milliseconds"
             MAX-ACCESS  read-create
             STATUS      current
             DESCRIPTION
                 "Maximum Interleave Delay on Upstream direction.  The maximum
                  one-way interleaving delay introduced by the PMS-TC on
                  Upstream direction.  The XTUs shall choose the S (factor) and
                  D (depth) values such that the actual one-way interleaving
                  delay is as close as possible to, but less than or equal to, 
                  hwxdslDynamicProfCh2MaxDelayUs.  The delay is coded in ms, 
                  with the value 0 indicating no delay bound is being imposed."
             REFERENCE    "ITU-T G.997.1, paragraph 7.3.2.2"
         ::= { hwxdslDynamicProfEntry 18 }
         
     hwxdslDynamicProfPmMode OBJECT-TYPE
             SYNTAX BITS {
                              allowTransitionsToIdle(0),
                              allowTransitionsToLowPower(1)
                         }
             MAX-ACCESS  read-create
             STATUS      current
             DESCRIPTION
                 "Power management state Enabling.  Defines the power states the
                  xTU-C or xTU-R may autonomously transition to on this line.
                  The various bit positions are: allowTransitionsToIdle (0) and
                  allowTransitionsToLowPower (1).  A bit with a '1' value means
                  that the xTU is allowed to transit into the respective state
                  and a '0' value means that the xTU is not allowed
                  to transit into the respective state."
             REFERENCE    "ITU-T G.997.1, paragraph 7.3.1.1.4"
         ::= { hwxdslDynamicProfEntry 19 }
         
    hwxdslDynamicProfL0Time OBJECT-TYPE
             SYNTAX Unsigned32 (0..255)
             MAX-ACCESS  read-create
             STATUS      current
             DESCRIPTION
                 "This minimum time (in seconds) between an Exit from the L2
                  state and the next Entry into the L2 state.  It ranges from 0
                  to 255 seconds."
             REFERENCE    "ITU-T G.997.1, paragraph 7.3.1.1.5"
         ::= { hwxdslDynamicProfEntry 20 }
         
    hwxdslDynamicProfL2Time OBJECT-TYPE
             SYNTAX Unsigned32 (0..255)
             MAX-ACCESS  read-create
             STATUS      current
             DESCRIPTION
                 "This minimum time (in seconds) between an Entry into the
                 L2 state and the first Power Trim in the L2 state and between
                 two consecutive Power Trims in the L2 State.
                 It ranges from 0 to 255 seconds."
             REFERENCE    "ITU-T G.997.1, paragraph 7.3.1.1.6"
         ::= { hwxdslDynamicProfEntry 21 }
         
     hwxdslDynamicProfL2Atpr  OBJECT-TYPE
            SYNTAX      Unsigned32 (0..31)
            UNITS       "dB"
            MAX-ACCESS  read-create
            STATUS      current
            DESCRIPTION
                 "The maximum aggregate transmit power reduction (in dB) that
                  can be performed at transition of L0 to L2 state or through a
                  single Power Trim in the L2 state.
                  It ranges from 0 dB to 31 dB."
            REFERENCE    "ITU-T G.997.1 (amendment 1), 7.3.1.1.7"
         ::= { hwxdslDynamicProfEntry 22 }

     hwxdslDynamicProfL2Atprt  OBJECT-TYPE
            SYNTAX      Unsigned32 (0..31)
            UNITS       "dB"
            MAX-ACCESS  read-create
            STATUS      current
            DESCRIPTION
                 "The total maximum aggregate transmit power reduction
                 (in dB) that can be performed in an L2 state. This is the
                 sum of all reductions of L2 Request (i.e., at transition of
                 L0 to L2 state) and Power Trims."
            REFERENCE    "ITU-T G.997.1 (amendment 1), 7.3.1.1.9"
         ::= { hwxdslDynamicProfEntry 23 }    
         
     hwxdslDynamicProfDpboEPsd  OBJECT-TYPE
            SYNTAX      OCTET STRING (SIZE(0..48))
            MAX-ACCESS  read-create
            STATUS      current
            DESCRIPTION
                 "This parameter defines the PSD mask that is assumed to be permitted at the exchange. 
                 This parameter shall use the same format as PSDMASKds.The maximum number of breakpoints 
                 for DPBOEPSD is 16.
                 This is a string of 16 pairs of values in the following
                 structure:
                 Octets 0+1 - Index of 1st sub-carrier used in the context
                              of a first breakpoint.
                 Octet 2    - The PSD reduction for the sub-carrier indicated in
                             octets 0 and 1.
                 Octets 3-5 - Same, for a 2nd breakpoint.
                 Octets 6-8 - Same, for a 3rd breakpoint.
                 This architecture continues until octets 45-47, which are
                 associated with a 16th breakpoint.
                 Each subcarrier index is an unsigned number in the range 1 and
                 NSCds.  Each PSD reduction value is in the range 0 (0dBm/Hz) to
                 255 (-127.5dBm/Hz) with steps of 0.5dBm/Hz.  Valid values are
                 in the range 0 to 190 (0 to -95dBm/Hz).
                 When the number of breakpoints is less than 16, all remaining
                 octets are set to the value 0xff. "
            REFERENCE    "ITU-T G.997.1(200604), paragraph 7.3.1.2.13"         
         ::= { hwxdslDynamicProfEntry 24 }     
         
     hwxdslDynamicProfDpboEsEL  OBJECT-TYPE
            SYNTAX      Unsigned32 (0..511)
            UNITS       "0.5dB"
            MAX-ACCESS  read-create
            STATUS      current
            DESCRIPTION
                 "This configuration parameter defines the assumed electrical length of 
                  cables (E-side cables) connecting exchange based DSL services to a remote
                  flexibility point (cabinet), that hosts the xTU-C that is subject to 
                  spectrally shaped downstream power back-off depending on this length. 
                  For this parameter the electrical length is defined as the loss (in dB) 
                  of an equivalent length of hypothetical cable at a reference frequency 
                  defined by the network operator or in spectrum management regulations. 
                  DPBOESEL shall be coded as an unsigned integer representing an electrical 
                  length from 0 dB (coded as 0) to 255.5 dB (coded as 511) in steps of 0.5 dB. 
                  All values in the range are valid.If DPBOESEL is set to zero, the DPBO in 
                  this section shall be disabled."
            REFERENCE    "ITU-T G.997.1(200604), paragraph 7.3.1.2.13"
         ::= { hwxdslDynamicProfEntry 25 }        
      
    hwxdslDynamicProfDpboEscm  OBJECT-TYPE
            SYNTAX      OCTET STRING (SIZE(0..6)) 
            MAX-ACCESS  read-create
            STATUS      current
            DESCRIPTION
                 "This configuration parameter defines a cable model in terms of three scalars 
                  DPBOESCMA, DPBOESCMB and DPBOESCMC that shall be used to describe the frequency
                  dependent loss of E-side cables.Parameters DPBOESCMA, DPBOESCMB, DPBOESCMC shall be
                  coded as unsigned integers representing a scalar value from -1 (coded as 0) to 1.5 
                  (coded as 640) in step of 1/256. All values in the range are valid.
                  Octets 0+1 DPBOESCMA
        	      Octets 2+3 DPBOESCMB
                  Octets 4+5 DPBOESCMC"
             REFERENCE    "ITU-T G.997.1(200604), paragraph 7.3.1.2.13"          
         ::= { hwxdslDynamicProfEntry 26 }      
         
     hwxdslDynamicProfDpboMus  OBJECT-TYPE
            SYNTAX      Unsigned32 (0..255)
            UNITS       "0.5dBm/Hz"
            MAX-ACCESS  read-create
            STATUS      current
            DESCRIPTION
                 "DPBOMUS defines the assumed Minimum Usable receive Signal PSD (in dBm/Hz) for 
                  exchange based services, used to modify parameter DPBOFMAX defined below. It 
                  shall be coded as an unsigned integer representing a PSD level from 0 dBm/Hz 
                  (coded as 0) to -127.5 dBm/Hz (coded as 255) in steps of 0.5 dBm/Hz. 
                  All values in the range are valid." 
            REFERENCE    "ITU-T G.997.1(200604), paragraph 7.3.1.2.13"                      
         ::= { hwxdslDynamicProfEntry 27 }   

     hwxdslDynamicProfDpboFMin  OBJECT-TYPE
            SYNTAX      Unsigned32 (0..2048)
            UNITS       "4.3125 KHz"
            MAX-ACCESS  read-create
            STATUS      current
            DESCRIPTION
                 "DPBOFMIN defines the minimum frequency from which the DPBO shall be applied. 
                  It shall be coded as a 16 bits unsigned integer representing a frequency in 
                  multiple of 4.3125 KHz. The range of valid values is from 0 kHz (coded as 0)
                  to 8832 kHz (coded as 2048)."  
            REFERENCE    "ITU-T G.997.1(200604), paragraph 7.3.1.2.13"            
      ::= { hwxdslDynamicProfEntry 28 }      
      
     hwxdslDynamicProfDpboFMax  OBJECT-TYPE
            SYNTAX      Unsigned32 (32..6956)
            UNITS       "4.3125 KHz"
            MAX-ACCESS  read-create
            STATUS      current
            DESCRIPTION
                 "DPBOFMAX defines the maximum frequency at which DPBO may be applied. It shall be
                  coded as a 16 bits unsigned integer representing a frequency in multiple of 4.3125 KHz. 
                  The range of valid values is from 138 kHz (coded as 32) to 29997.75 kHz (coded as 6956)."  
            REFERENCE    "ITU-T G.997.1(200604), paragraph 7.3.1.2.13"                      
      ::= { hwxdslDynamicProfEntry 29 }      

     hwxdslDynamicProfUpboPsdBand  OBJECT-TYPE
            SYNTAX      OCTET STRING (SIZE(0..16))  
            MAX-ACCESS  read-create
            STATUS      current
            DESCRIPTION
                 "This parameter defines the UPBO reference PSD used to compute the upstream power back-off
                  for each upstream band except US0. A UPBOPSD defined for each band ahsll consist of two 
                  parameters [a, b]. Parameter a shall be coded as an unsigned 12-bit number from 40 dBm/Hz
                  (coded as 0) to 80.95 dBm/Hz (coded as 4095) in steps of 0.01 dBm/Hz; and b shall be coded
                  as an unsigned 12 bit number from 0 (coded as 0) to 40.95 dBm/Hz (coded as 4095) in steps 
                  of 0.01 dBm/Hz. The UPBO reference PSD at the frequency f expressed in MHz shall be equal 
                  to -a-b√f. The set of parameter values a = 40 dBm/Hz, b = 0 dBm/Hz is a special configuration
                  to disable UPBO in the respective upstream band.
                  Octets 0+1 -   a[0]
            	  Octets 2+3 -   b[0]
            	  Octets 4+5 -   a[1]
            	  Octets 6+7 -   b[1]
            	  Octets 8+9 -   a[2]
            	  Octets 10+11 - b[2]
            	  Octets 12+13 - a[3]
            	  Octets 14+15 - b[3]"
            REFERENCE    "ITU-T G.997.1(200604), paragraph 7.3.1.2.14"                                
         ::= { hwxdslDynamicProfEntry 30 }      

	 hwxdslDynamicProfUpboKLF  OBJECT-TYPE
            SYNTAX INTEGER {
                     forced(1),
                     auto(2)}             
            MAX-ACCESS  read-create
            STATUS      current
            DESCRIPTION
                 "This parameter is a flag that forces the VTU-R to use the electrical loop length of the CO-MIB
                  (UPBOKL) to compute the UPBO. The value shall be forced if the flag is set to 1. Otherwise, the
                  electrical loop length shall be autonomously selected by the VTU-O."  
            REFERENCE    "ITU-T G.997.1(200604), paragraph 7.3.1.2.14"    
         ::= { hwxdslDynamicProfEntry 31 }          

	 hwxdslDynamicProfUpboKL  OBJECT-TYPE
            SYNTAX      Unsigned32 (0..1280)
            UNITS       "0.1 dB"
            MAX-ACCESS  read-create
            STATUS      current
            DESCRIPTION
                 "This parameter defines the electrical loop length expressed in dB at 1MHz, kl0, configured by
                  the CO-MIB. The value shall be coded as an unsigned 16 bit number in the range 0 (coded as 0) 
                  to 128 dB (coded as 1280) in steps of 0.1 dB."
            REFERENCE    "ITU-T G.997.1(200604), paragraph 7.3.1.2.14"                                          
         ::= { hwxdslDynamicProfEntry 32 }        
      
     hwxdslDynamicProfRfiBands  OBJECT-TYPE
            SYNTAX      SnmpAdminString(SIZE(0..159))
            MAX-ACCESS  read-create
            STATUS      current
            DESCRIPTION
                  "The subset of PSD mask breakpoints that shall be
                  used to notch an RFI band.
                  It is a string of bands consist of begin tone index
                  and end tone index.
                  for example :0-10,20-50,100-4095
                  It can contain as most as 16 bands."
            REFERENCE    "ITU-T G.997.1(200604), paragraph 7.3.1.2.10"
         ::= { hwxdslDynamicProfEntry 33 }
      
     hwxdslDynamicProfToneBlackOut  OBJECT-TYPE
            SYNTAX      SnmpAdminString(SIZE(0..79))
            MAX-ACCESS  read-create
            STATUS      current
            DESCRIPTION
                  "The subset of subcarriermask that shall be
                  used to mask the subcarriers.
                  It is a string of bands consist of begin tone index
                  and end tone index.
                  for example :0-10,20-50,100-4095
                  It can contain as most as 8 bands."
            REFERENCE    "ITU-T G.997.1(200604), paragraph 7.3.1.2.8"
         ::= { hwxdslDynamicProfEntry 34 }                   
         
     hwxdslDynamicProfCarMaskDS  OBJECT-TYPE
            SYNTAX      OCTET STRING (SIZE(0..64))
            MAX-ACCESS  read-create
            STATUS      current
            DESCRIPTION
                 "Sub-carriers mask.  A bitmap of 512 bits that allows masking
                  up to 512 downstream sub-carriers, depending on NSCds.  If bit
                  i (0 &lt;= i &lt; NSCds) is set to '1', the respective
                  downstream sub-carrier i is masked, and if set to '0', the
                  respective sub-carrier is unmasked.  Note that there should
                  always be unmasked sub-carriers (i.e., the object cannot be
                  all 1's).  Also note that if NSCds &lt; 512, all bits
                  i (NSCds i &lt;= 512) should be set to '1'."
            REFERENCE    "ITU-T G.997.1, paragraph 7.3.1.2.6"
         ::= { hwxdslDynamicProfEntry 35 }

     hwxdslDynamicProfCarMaskUS  OBJECT-TYPE
            SYNTAX      OCTET STRING (SIZE(0..8))
            MAX-ACCESS  read-create
            STATUS      current
            DESCRIPTION
                 "Sub-carriers mask.  A bitmap of 64 bits that allows masking
                  up to 64 downstream sub-carriers, depending on NSCds.  If
                  bit i (0 &lt;= i &lt; NSCus) is set to '1', the respective
                  upstream sub-carrier i is masked, and if set to '0', the
                  respective sub-carrier is unmasked.  Note that there
                  should always be unmasked sub-carriers (i.e., the object
                  cannot be all 1's).  Also note that if NSCus &lt;
                  64, all bits i (NSCus &lt; i &lt;= 64) should be set to '1'."
            REFERENCE    "ITU-T G.997.1, paragraph 7.3.1.2.7"
         ::= { hwxdslDynamicProfEntry 36 }
                  
     hwxdslDynamicProfXdslMode    OBJECT-TYPE
            SYNTAX    INTEGER {
                     defMode (1),
                     adsl (2),
                     adsl2Pots (3),
                     adsl2Isdn (4),
                     adsl2PlusPots (5),
                     adsl2PlusIsdn (6),
                     adsl2ReachExtended (7),                     
                     g9923PotsNonOverlapped(8),
                     g9923PotsOverlapped(9),
                     g9923IsdnNonOverlapped(10),
                     g9923isdnOverlapped(11),
                     g9924potsNonOverlapped(14),
                     g9924potsOverlapped(15),
                     g9923AnnexIAllDigNonOverlapped(18),
                     g9923AnnexIAllDigOverlapped(19),
                     g9923AnnexJAllDigNonOverlapped(20),
                     g9923AnnexJAllDigOverlapped(21),
                     g9924AnnexIAllDigNonOverlapped(22),
                     g9924AnnexIAllDigOverlapped(23),
                     g9923AnnexLMode1NonOverlapped(24),
                     g9923AnnexLMode2NonOverlapped(25),
                     g9923AnnexLMode3Overlapped(26),
                     g9923AnnexLMode4Overlapped(27),
                     g9923AnnexMPotsNonOverlapped(28),
                     g9923AnnexMPotsOverlapped(29),
                     g9925PotsNonOverlapped(30),
                     g9925PotsOverlapped(31),
                     g9925IsdnNonOverlapped(32),
                     g9925isdnOverlapped(33),
                     g9925AnnexIAllDigNonOverlapped(36),
                     g9925AnnexIAllDigOverlapped(37),
                     g9925AnnexJAllDigNonOverlapped(38),
                     g9925AnnexJAllDigOverlapped(39),
                     g9925AnnexMPotsNonOverlapped(40),
                     g9925AnnexMPotsOverlapped(41),
                     vdsl2Pots (42),
                     vdsl2Isdn (43)
                     }
            MAX-ACCESS  read-create
            STATUS      current
            DESCRIPTION
                 "The XDSL Mode is a way of categorizing the various XDSL
                  transmission modes into groups, each group (XDSL Mode) shares
                  the same PSD configuration."
            REFERENCE    "DSL Forum TR-90, paragraph 5.1.8"
         ::= { hwxdslDynamicProfEntry 37 }
     
    hwxdslDynamicProfMaxNomPsdDs OBJECT-TYPE
             SYNTAX      Integer32(-600..-300)
             UNITS       "0.1 dB"
             MAX-ACCESS  read-create
             STATUS      current
             DESCRIPTION
                 "The maximum nominal transmit PSD in the downstream
                  direction during initialization and Showtime.  It ranges from
                  -600 to -300 units of 0.1 dBm/Hz.  (physical values are -60 to
                  -30 dBm/Hz).  "
         ::= { hwxdslDynamicProfEntry 38 }
         
    hwxdslDynamicProfMaxNomPsdUs OBJECT-TYPE
             SYNTAX      Integer32(-600..-300)
             UNITS       "0.1 dB"
             MAX-ACCESS  read-create
             STATUS      current
             DESCRIPTION
                 "The maximum nominal transmit PSD in the upstream
                  direction during initialization and Showtime.  It ranges from
                  -600 to -300 units of 0.1 dBm/Hz.  (physical values are -60 to
                  -30 dBm/Hz).  "
         ::= { hwxdslDynamicProfEntry 39 }
         
    hwxdslDynamicProfMaxNomAtpDs  OBJECT-TYPE
              SYNTAX      Unsigned32 (0..255)
              UNITS       "0.1 dBm"
              MAX-ACCESS  read-create
              STATUS      current
              DESCRIPTION
                 "The maximum nominal aggregate transmit power in the
                  downstream direction during initialization and Showtime.  It
                  ranges from 0 to 255 units of 0.1 dBm (physical values are 0
                  to 25.5 dBm)."
              REFERENCE    "ITU-T G.997.1, paragraph 7.3.1.2"
        ::= { hwxdslDynamicProfEntry 40 }

    hwxdslDynamicProfMaxNomAtpUs  OBJECT-TYPE
              SYNTAX      Unsigned32 (0..255)
              UNITS       "0.1 dBm"
              MAX-ACCESS  read-create
              STATUS      current
              DESCRIPTION
                 "The maximum nominal aggregate transmit power in the
                  upstream direction during initialization and Showtime.  It
                  ranges from 0 to 255 units of 0.1 dBm (physical values are 0
                  to 25.5 dBm)."
              REFERENCE    "ITU-T G.997.1, paragraph 7.3.1.2"
        ::= { hwxdslDynamicProfEntry 41 }
                     
     hwxdslDynamicProfPsdMaskDs   OBJECT-TYPE
            SYNTAX      OCTET STRING (SIZE(0..96))
            MAX-ACCESS  read-create
            STATUS      current
            DESCRIPTION
                "This configuration parameter defines the downstream PSD mask 
                applicable at the U C2 reference point.
                This MIB PSD mask may impose PSD restrictions in addition 
                to the Limit PSD mask defined in the relevant Recommendation 
                (e.g., G.992.5, G.993.2).
                This is a string of 32 pairs of values in the following
                structure:
                Octets 0+1 - Index of 1st sub-carrier used in the context
                             of a first breakpoint.
                Octet 2    - The PSD reduction for the sub-carrier indicated in
                             octets 0 and 1.
                Octets 3-5 - Same, for a 2nd breakpoint.
                Octets 6-8 - Same, for a 3rd breakpoint.
                This architecture continues until octets 94-95, which are
                associated with a 32nd breakpoint.
                Each subcarrier index is an unsigned number in the range 0 and
                (NSCds - 1).  Each PSD reduction value is in the range 0 (0dBm/Hz) to
                255 (-127.5dBm/Hz) with steps of 0.5dBm/Hz.  Valid values are
                in the range 0 to 190 (0 to -95dBm/Hz).
                When the number of breakpoints is less than 32, all remaining
                octets are set to the value 0xff.  Note that the content of this
                object should be correlated with the sub-carriers mask and with
                the RFI setup. "
            REFERENCE    "ITU-T G.997.1(200604), paragraph 7.3.1.2.9"
         ::= { hwxdslDynamicProfEntry 42 }
        
     hwxdslDynamicProfPsdMaskUs   OBJECT-TYPE
            SYNTAX      OCTET STRING (SIZE(0..48))
            MAX-ACCESS  read-create
            STATUS      current
            DESCRIPTION
                "This configuration parameter defines the upstream PSD 
                mask applicable at the U R2 reference point. This MIB 
                PSD mask may impose PSD restrictions in addition to the 
                Limit PSD mask defined in the relevant Recommendations 
                (e.g., ITU-T Recommendations G.992.3, G.993.2).
                This is a string of 16 pairs of values in the following
                structure:
                Octets 0+1 - Index of 1st sub-carrier used in the context
                             of a first breakpoint.
                Octet 2    - The PSD reduction for the sub-carrier indicated in
                             octets 0 and 1.
                Octets 3-5 - Same, for a 2nd breakpoint.
                Octets 45-47 - Same, for a 3rd breakpoint.
                This architecture continues until octets 45-47, which are
                associated with a 16th breakpoint.
                Each subcarrier index is an unsigned number in the range 0 and
                (NSCus - 1).  Each PSD reduction value is in the range 0 (0dBm/Hz) to
                255 (-127.5dBm/Hz) with steps of 0.5dBm/Hz.  Valid values are
                in the range 0 to 190 (0 to -95dBm/Hz).
                When the number of breakpoints is less than 16, all remaining
                octets are set to the value 0xff.  Note that the content of this
                object should be correlated with the sub-carriers mask and with
                the RFI setup. "
            REFERENCE    "ITU-T G.997.1(200604), paragraph 7.3.1.2.12"
         ::= { hwxdslDynamicProfEntry 43 }                  
         
     hwxdslDynamicProfLimitMask  OBJECT-TYPE
            SYNTAX      INTEGER {
                        			Profile8a (1),
                        			Profile8b (2),
                        			Profile8c (3),
                        			Profile8d (4),
                        			Profile12a (5),
                        			Profile12b (6),
                        			Profile17a (7),
                        			Profile30a (8)
                               }
            MAX-ACCESS  read-create
            STATUS      current
            DESCRIPTION
                "This configuration parameter contains the G.993.2 
                profiles to be allowed by the near-end xTU on this line."
                REFERENCE    "ITU-T G.997.1(200604), paragraph 7.3.1.1.11"
       ::= { hwxdslDynamicProfEntry 44 }
         
     hwxdslDynamicProfClassMask  OBJECT-TYPE
            SYNTAX    INTEGER {
                        			AnnexA998-D-32              (1),
                        			AnnexA998-D-64              (2),
                        			AnnexB997-M1c-A-7           (3),
                        			AnnexB997-M1x-M-8           (4),
                        			AnnexB997-M1x-M             (5),
                        			AnnexB997-M2x-M-8           (6),
                        			AnnexB997-M2x-A             (7),
                        			AnnexB997-M2x-M             (8),
                        			AnnexB998-M1x-A             (9),
                        			AnnexB998-M1x-B             (10),
                        			AnnexB998-M1x-NUS0          (11),
                        			AnnexB998-M2x-A             (12),
                        			AnnexB998-M2x-M             (13),
                        			AnnexB998-M2x-B             (14),
                        			AnnexB998-M2x-NUS0          (15),
                        			AnnexBHPE17-M1              (16),
                        			AnnexBHPE30-M1              (17),
                        			AnnexB997E17-M2x-NUS0       (18),
                        			AnnexB997E30-M2x-NUS0       (19),
                        			AnnexB998E17-M2x-NUS0       (20),
                        			AnnexB998E17-M2x-NUS0-M     (21),
                        			AnnexB998ADE17-M2x-NUS0-M   (22),
                        			AnnexB998ADE17-M2x-B        (23),
                        			AnnexB998E30-M2x-NUS0       (24),
                        			AnnexB998E30-M2x-NUS0-M     (25),
                        			AnnexB998ADE30-M2x-NUS0-M   (26),
                        			AnnexB998ADE17-M2x-A        (27),
                        			AnnexB998ADE30-M2x-NUS0-A   (28)
                              }
            MAX-ACCESS  read-create
            STATUS      current
            DESCRIPTION
                "In order to reduce the number of configuration possibilities, 
                the limit PSD masks are grouped in the following PSD mask classes:
                 -  Class 998 Annex A: D-32, D-64.
                 -  Class 997-M1c Annex B: 997-M1c-A-7.
                 -  Class 997-M1x Annex B: 997-M1x-M-8, 997-M1x-M.
                 -  Class 997-M2x Annex B: 997-M2x-M-8, 997-M2x-A, 997-M2x-M.
                 -  Class 998-M1x Annex B: 998-M1x-A, 998-M1x-B, 998-M1x-NUS0.
                 -  Class 998-M2x Annex B: 998-M2x-A, 998-M2x-M, 998-M2x-B, 998-M2x-NUS0.
                 -  Class HPE17 Annex B: HPE17-M1.
                 -  Class HPE30 Annex B: HPE30-M1.
                 -  Class 997E17-M2x Annex B: 997E17-M2x-NUS0.
                 -  Class 997E30-M2x Annex B: 997E30-M2x-NUS0.
                 -  Class 998E17-M2x Annex B: 998E17-M2x-NUS0, 998E17-M2x-NUS0-M.
                 -  Class 998ADE17-M2x Annex B: 998ADE17-M2x-NUS0-M, 998ADE17-M2x-A, 998ADE17-M2x-B.
                 -  Class 998E30-M2x Annex B: 998E30-M2x-NUS0, 998E30-M2x-NUS0-M.
                 -  Class 998ADE30-M2x Annex B: 998ADE30-M2x-NUS0-M, 998ADE30-M2x-NUS0-A.
                 "
            REFERENCE    "ITU-T G.997.1(200604), paragraph 7.3.1.1.12"
         ::= { hwxdslDynamicProfEntry 45 }
         
     hwxdslDynamicProfBandOptUsage  OBJECT-TYPE
            SYNTAX      INTEGER {
                                     disable(1),
                                     enable(2)
                                }
            MAX-ACCESS  read-create
            STATUS      current
            DESCRIPTION
                 "Defines the VDSL link use of the optional frequency
                  range [25kHz - 138kHz] (Opt).
        		  disable(1)     indicates Opt is unused
        		  enable(2)      indicates Opt usage is for upstream
        		  Huawei defined."
      ::= { hwxdslDynamicProfEntry 46 }
      
     hwxdslDynamicProfVirtualNoiseModeDs  OBJECT-TYPE
            SYNTAX      INTEGER {
                                     disable(1),
                                     enable(2)
                                }
            MAX-ACCESS  read-create
            STATUS      current
            DESCRIPTION
                 "Defines the Virtual Noise of downsteam.
        		  disable(1)      unused
        		  enable(2)        used
        		  Huawei defined."
      ::= { hwxdslDynamicProfEntry 47 }
      
      hwxdslDynamicProfVirtualNoiseModeUs  OBJECT-TYPE
            SYNTAX      INTEGER {
                                     disable(1),
                                     enable(2)
                                }
            MAX-ACCESS  read-create
            STATUS      current
            DESCRIPTION
                 "Defines the Virtual Noise of upstream.
        		  disable(1)      unused
        		  enable(2)        used
        		  Huawei defined."
      ::= { hwxdslDynamicProfEntry 48 }
      
      hwxdslDynamicProfVirtualNoiseDs  OBJECT-TYPE
            SYNTAX      OCTET STRING (SIZE(0..96))
            MAX-ACCESS  read-create
            STATUS      current
            DESCRIPTION
                 "The Virtual Noise of downsteam.
                 This is a string of 32 pairs of values in the following
                structure:
                Octets 0+1 - Index of 1st sub-carrier used in the context
                             of a first breakpoint.
                Octet 2    - The PSD reduction for the sub-carrier indicated in
                             octets 0 and 1.
                Octets 3-5 - Same, for a 2nd breakpoint.
                Octets 6-8 - Same, for a 3rd breakpoint.
                This architecture continues until octets 94-95, which are
                associated with a 32nd breakpoint.
                Each subcarrier index is an unsigned number in the range 0 and
                (NSCds - 1).  Each PSD reduction value is in the range 0 (0dBm/Hz) to
                255 (127.5dBm/Hz) with steps of 0.5dBm/Hz.
        		  "
      ::= { hwxdslDynamicProfEntry 49 }
      
      hwxdslDynamicProfVirtualNoiseUs  OBJECT-TYPE
            SYNTAX      OCTET STRING(SIZE(0..48))
            MAX-ACCESS  read-create
            STATUS      current
            DESCRIPTION
                 "The Virtual Noise of upsteam.
                 This is a string of 16 pairs of values in the following
                structure:
                Octets 0+1 - Index of 1st sub-carrier used in the context
                             of a first breakpoint.
                Octet 2    - The PSD reduction for the sub-carrier indicated in
                             octets 0 and 1.
                Octets 3-5 - Same, for a 2nd breakpoint.
                Octets 6-8 - Same, for a 3rd breakpoint.
                This architecture continues until octets 45-47, which are
                associated with a 16th breakpoint.
                Each subcarrier index is an unsigned number in the range 0 and
                (NSCds - 1).  Each PSD reduction value is in the range 0 (0dBm/Hz) to
                255 (127.5dBm/Hz) with steps of 0.5dBm/Hz.
        		  "
      ::= { hwxdslDynamicProfEntry 50 }
      
     hwxdslDynamicProfRowStatus  OBJECT-TYPE
      SYNTAX      RowStatus
      MAX-ACCESS  read-create
      STATUS      current
      DESCRIPTION
         "This object is used to create a new row or to modify or
         delete an existing row in this table.

         A profile is activated by setting this object to 'active'.
         When 'active' is set, the system will validate the profile.

         Before a profile can be deleted or taken out of service
         (by setting this object to 'destroy' or 'outOfService'),
         it must be first unreferenced from all associated
         templates."
      ::= { hwxdslDynamicProfEntry 51 }
      
      
--hwXdslPortIopCaptureTable
--
--    
              hwXdslPortIopCaptureTable OBJECT-TYPE 	
			SYNTAX SEQUENCE OF HwXdslPortIopCaptureEntry
			MAX-ACCESS not-accessible
			STATUS current
			DESCRIPTION
				"
				The table hwXdslPortIopCaptureTable implement xDSL port IOP information capture.
				"
		 ::= { adslMibObjects 65551 }

		hwXdslPortIopCaptureEntry OBJECT-TYPE
			SYNTAX HwXdslPortIopCaptureEntry
			MAX-ACCESS not-accessible
			STATUS current
			DESCRIPTION
				"The table hwXdslPortIopCaptureEntry implement xDSL port IOP information capture.
                                 The index of this table is an interface index where the
                                 interface has an ifType of adsl2plus."
			INDEX{        
			         ifIndex
			     }
			::= { hwXdslPortIopCaptureTable 1 }

                HwXdslPortIopCaptureEntry ::=
			SEQUENCE{      
			           hwXdslPortIopCaptureOperType
			              INTEGER,
                                   hwXdslPortIopCaptureOperStatus 
			              INTEGER
			        }  
			    
                hwXdslPortIopCaptureOperType OBJECT-TYPE
	             SYNTAX INTEGER
		        {   
		        	start(1),
		        	stop(2)	
		        }
	               MAX-ACCESS  read-write
	               STATUS      current
	               DESCRIPTION
		                 "start or stop IOP information capture of Xdsl port."
	        ::= { hwXdslPortIopCaptureEntry 1 }  
	        
	        hwXdslPortIopCaptureOperStatus OBJECT-TYPE  
	                SYNTAX INTEGER
			        {   
			        	no-capture(1),
					capturing(2),
					iop-generate(3),
					captured(4)
			        }    
			MAX-ACCESS read-only
			STATUS     current
			DESCRIPTION
			  "port IOP capture status "	      
	       ::= { hwXdslPortIopCaptureEntry 2 }
	        
--hwXdslDynamicInfoCollectTable
--
--   
              hwXdslDynamicInfoCollectTable OBJECT-TYPE 	
			SYNTAX SEQUENCE OF HwXdslDynamicInfoCollectEntry
			MAX-ACCESS not-accessible
			STATUS current
			DESCRIPTION
				"
				The table hwXdslDynamicInfoCollectTable implement xDSL port Dynamic information collect.
				"
		 ::= { adslMibObjects 65552 }

		hwXdslDynamicInfoCollectEntry OBJECT-TYPE
			SYNTAX HwXdslDynamicInfoCollectEntry
			MAX-ACCESS not-accessible
			STATUS current
			DESCRIPTION
				"The table HwXdslDynamicInfoCollectEntry implement xDSL port Dynamic information capture.
                                 The index of this table is an interface index where the
                                 interface has an ifType of adsl2plus."
			INDEX{        
			         hwFrameIndex, 
			         hwSlotIndex
			     }
			::= { hwXdslDynamicInfoCollectTable 1 }

            HwXdslDynamicInfoCollectEntry ::=
			SEQUENCE{      
					hwXdslDynamicInfoCollect
						INTEGER,
					hwXdslDynamicInfoCollectStatus
						INTEGER,
					hwXdslDynamicInfoCollectTime
			              		DateAndTime
			        }  
			    
            hwXdslDynamicInfoCollect OBJECT-TYPE
	             SYNTAX INTEGER
		        {   
		        	start(1)
		        }
	               MAX-ACCESS  read-write
	               STATUS      current
	               DESCRIPTION
		                 "start Dynamic information collecting of Xdsl port."
	        ::= { hwXdslDynamicInfoCollectEntry 1 }  
	        
	        hwXdslDynamicInfoCollectStatus OBJECT-TYPE  
	                SYNTAX INTEGER
			        {   
			        	no-collect(1),
					collecting(2),
					collected(3)
			        }    
			MAX-ACCESS read-only
			STATUS     current
			DESCRIPTION
			  "board Dynamic infomation collecting status "	      
	       ::= { hwXdslDynamicInfoCollectEntry 2 }
	       
	       hwXdslDynamicInfoCollectTime OBJECT-TYPE
			SYNTAX DateAndTime
			MAX-ACCESS read-only
			STATUS current
			DESCRIPTION				
		           " date and time of the Dynamic infomation file.
		           "
			::= { hwXdslDynamicInfoCollectEntry 3 }
--
--ADSL traps description
--
    	hwAdslTraps OBJECT IDENTIFIER ::= { adslTraps 65536 }
    	hwAdslGeneralTraps OBJECT IDENTIFIER ::= { hwAdslTraps 1 }
    	hwAdslGeneralTrapsOIDs OBJECT IDENTIFIER ::= { hwAdslGeneralTraps 0 }

	    hwAdslPortActRateMonitorTrap NOTIFICATION-TYPE
            OBJECTS { hwFrameIndex,hwSlotIndex,hwPortIndex,
                    hwAdslAtucLatestTxRate,hwAdslAturLatestTxRate,
                    hwAdslAtucLatestTxRateThreshold,hwAdslAturLatestTxRateThreshold,
                    hwAdslLineLatestActiveTime,hwAdslAtucLatestSnrMgn,hwAdslAturLatestSnrMgn,
                    hwAdslAtucLatestAtn,hwAdslAturLatestAtn,hwAdslAtucLatestAttainableRate,hwAdslAturLatestAttainableRate,
                    hwAdslAtucLatestConfTxRate,hwAdslAturLatestConfTxRate,hwAdslAtucLatestInterleaveDelay,
                    hwAdslAturLatestInterleaveDelay,hwAdslAtucLatestTargetSnrMgn,hwAdslAturLatestTargetSnrMgn,
                    hwSubslotIndex,hwAlarmId,hwAlarmTime,hwAlarmSn,hwCauseId,hwTrapType } 
            STATUS current
            DESCRIPTION
                "  If ADSL act rate is lower than threshold, hwTrapType is 1. Otherwise, hwTrapType is 2."
            ::= { hwAdslGeneralTrapsOIDs 1 }

	    hwAdslPortRateChangeTrap NOTIFICATION-TYPE
            OBJECTS { hwFrameIndex,hwSlotIndex,hwPortIndex,hwIasConfigChangeTrapID,
                      hwAdslPortRateChangeTrapIPIAID,hwAdslPortRateChangeTrapMUXID,
                      hwXdslPortRateChangeTrapTimeStamp,hwAdslPortRateChangeTrapDSLineRate,
            	      hwAdslPortRateChangeTrapUSLineRate,hwAdslPortRateChangeTrapEventType,hwAdslPortRateChangeTrapDslType} 
            STATUS current
            DESCRIPTION
                "  ADSL act rate is change trap."
            ::= { hwAdslGeneralTrapsOIDs 2 }                
	END
