-- ==================================================================
-- Copyright (C) 2002 by  HUAWEI TECHNOLOGIES. All rights reserved.
-- 
-- Description: HUAWEI MSTP MIB
-- Reference:
-- Version: V1.0                                
-- History:
-- ==================================================================
-- ==================================================================
-- 
-- Varibles and types be imported
--
-- ==================================================================
-- ------------------------------------------------------------------
-- ------------------------------------------------------------------
HUAWEI-IPDSLAM-MSTP-MIB  DEFINITIONS ::= BEGIN

IMPORTS

    MODULE-IDENTITY,OBJECT-TYPE,Counter32, OBJECT-IDENTITY, NOTIFICATION-TYPE
        FROM SNMPv2-SMI
    TEXTUAL-CONVENTION,RowStatus
        FROM SNMPv2-TC            
    BridgeId
        FROM BRIDGE-MIB
    hwDatacomm 
        FROM HUAWEI-MIB;
    
    hwL2Mgmt  OBJECT IDENTIFIER ::= { hwDatacomm 42 }
    hwMstp MODULE-IDENTITY
	LAST-UPDATED "200504191936Z"		
	ORGANIZATION 
	"Huawei Technologies co.,Ltd."
	CONTACT-INFO 
	    "VRP Team Huawei Technologies co.,Ltd.
	    Huawei Bld.,NO.3 Xinxi Rd., 
	    Shang-Di Information Industry Base,
	    Hai-Dian District Beijing P.R. China
	    http://www.huawei.com
            Zip:100085
	    "
	DESCRIPTION
	    "This module include the information about MSTP protocol in the bridge.
	     The information can be read and some of them can be set."
	::= { hwL2Mgmt 4 }

    HwMSTPEnabledStatus ::= TEXTUAL-CONVENTION
    STATUS      current
    DESCRIPTION
        "A simple status value for the object."
    SYNTAX      INTEGER { enabled(1), disabled(2) }    

  hwMstpObjects OBJECT IDENTIFIER ::= {  hwMstp 1  }
  
  hwMstpStatus OBJECT-TYPE 
    SYNTAX      HwMSTPEnabledStatus
    MAX-ACCESS  read-write
    STATUS      current
    DESCRIPTION
      "Whether the Bridge MSTP is enabled.
      Enable indicate that MSTP enable in the bridge;
      Disabled indicate that MSTP disable in the bridge"
    DEFVAL      { 2 }
    ::= { hwMstpObjects 1 }

  hwMstpForceVersion OBJECT-TYPE 
    SYNTAX      INTEGER{stp(0),rstp(2),mstp(3)}
    MAX-ACCESS  read-write
    STATUS      current
    DESCRIPTION
      " The mode of this Bridge spanning-tree protocol.
        At present,the bridge hold out STP compatible mode and MSTP .
        User can set the mode by command line."
    DEFVAL      { mstp}
    ::= { hwMstpObjects 2 }

  hwMstpDiameter OBJECT-TYPE 
    SYNTAX      INTEGER(2..7)
    MAX-ACCESS  read-write
    STATUS      current
    DESCRIPTION
      "The diameter of Bridge.
       It stands for the scope of the network.
       It  affects the time that include hello time,
       forward delay time,maxage.Every bridge can set
       the diameter of Bridge,and it is effective when
       the bridge is root bridge.Effective in the CIST"
    DEFVAL      { 7}
    ::= { hwMstpObjects 3 }

  hwMstpBridgeMaxHops OBJECT-TYPE 
    SYNTAX      INTEGER(1..40)
    MAX-ACCESS  read-write
    STATUS      current
    DESCRIPTION
      "The maximum value of the  Bridge hops.
       It can limit the scope of the bridge network.
       It is effective when the bridge is root bridge.
       The BPDU that the bridge receives from 
       the Designed bridge will be dropped 
       when the hops in the BPDU is zero ."
    DEFVAL      { 20}
    ::= { hwMstpObjects 4 }

  hwMstpMasterBridgeID OBJECT-TYPE 
    SYNTAX      BridgeId
    MAX-ACCESS  read-only
    STATUS      current
    DESCRIPTION
      "The Bridge Identifier of the current Master Bridge.
       It is the root Bridge Identifier of the instance 0 in the region "
    ::= { hwMstpObjects 5 }

  hwMstpMasterPathCost OBJECT-TYPE 
    SYNTAX      INTEGER
    MAX-ACCESS  read-only
    STATUS      current
    DESCRIPTION
      "The CIST path cost from the transmitting Bridge to the Master Bridge."
    DEFVAL      { 0}
    ::= { hwMstpObjects 6 }

  hwMstpBpduGuard OBJECT-TYPE 
    SYNTAX      HwMSTPEnabledStatus
    MAX-ACCESS  read-write
    STATUS      current
    DESCRIPTION
      "Whether the Bridge BPDU Guard function is enabled. If the function 
      is enabled, the port will shutdown when received BPDU and the port 
      is configured as portfast.The purpose of the function is to prevent the bridge from
      BPDU attacking."
    DEFVAL      { disabled}
    ::= { hwMstpObjects 7 }

  hwMstpAdminFormatSelector OBJECT-TYPE --read only
    SYNTAX      INTEGER
    MAX-ACCESS  read-only
    STATUS      current
    DESCRIPTION
      "The administrative Configuration Identifier Format Selector in use 
      by the Bridge. This has a value of 0 indicate the format specified 
      in the Standard of IEEE 802.1s."
    DEFVAL      { 0}
    ::= { hwMstpObjects 8 }

  hwMstpAdminRegionName OBJECT-TYPE  
    SYNTAX      OCTET STRING(SIZE(1..32))
    MAX-ACCESS  read-write
    STATUS      current
    DESCRIPTION
      "This MSTP administrative region name.
       It changes to hwMstpOperRegionName 
       when user use the activing command 
       to active the configuration of the region."
    ::= { hwMstpObjects 9 }

  hwMstpAdminRevisionLevel OBJECT-TYPE 
    SYNTAX      INTEGER(0..65535)
    MAX-ACCESS  read-write
    STATUS      current
    DESCRIPTION
      "This MSTP administrative revision level.
      It changes to hwMstpOperRevisionLevel 
       when user use the activing command 
       to active the configuration of the region."
    DEFVAL      { 0}
    ::= { hwMstpObjects 10 }

  hwMstpOperFormatSelector OBJECT-TYPE 
    SYNTAX      INTEGER
    MAX-ACCESS  read-only
    STATUS      current
    DESCRIPTION
      "The operative Configuration Identifier Format Selector in use by the 
      Bridge. This has a value of 0 indicate the format specified in the 
      Standard of IEEE 802.1s."
    DEFVAL      { 0}
    ::= { hwMstpObjects 11 }

  hwMstpOperRegionName OBJECT-TYPE 
    SYNTAX      OCTET STRING( SIZE(0..32) )
    MAX-ACCESS  read-only
    STATUS      current
    DESCRIPTION
      "This MSTP operative region name.
      It can be used to determine whether
      the region is the same region with
      the mapping between vlan and instance
      and hwMstpOperRevisionLevel."
    ::= { hwMstpObjects 12 }

  hwMstpOperRevisionLevel OBJECT-TYPE 
    SYNTAX      INTEGER(0..65535)
    MAX-ACCESS  read-only
    STATUS      current
    DESCRIPTION
      "This MSTP operative revision level.
      It can be used to determine whether
      the region is the same region with
      the mapping between vlan and instance
      and hwMstpOperRegionName."
    DEFVAL      { 0}
    ::= { hwMstpObjects 13 }

  hwMstpRegionConfActive OBJECT-TYPE  
    SYNTAX      INTEGER{enable(1),disable(2)}
    MAX-ACCESS  read-write
    STATUS      current
    DESCRIPTION
      "Active the region configuration.
      Generally,the value of the hwMstpRegionConfActive is disable,
      but the value will be set as enable if Net Manager want to 
      active the configure of the region in the bridge.And then 
      all manager configuration will change to operable configuration.
      The value of hwMstpRegionConfActive is only disable when it is read.
      It is only enable when it is set."
    DEFVAL      { disable }
    ::= { hwMstpObjects 14 }

  hwMstpDefaultVlanAllo OBJECT-TYPE 
    SYNTAX      INTEGER{enable(1),unused(65535)}
    MAX-ACCESS  read-write
    STATUS      current
    DESCRIPTION
      "Set default configuration about VLAN allocation and all VLANs 
      are mapped to CIST.
      The value of hwMstpDefaultVlanAllo is only unused(65535) when it is read.
      It is only enable(1) when it is set."
    ::= { hwMstpObjects 15 }

  hwMstpDefaultRegionName OBJECT-TYPE 
    SYNTAX      INTEGER{reset(1),unused(65535)}
    MAX-ACCESS  read-write
    STATUS      current
    DESCRIPTION
      "Set default region name.
      The value of hwMstpDefaultRegionName is only unused(65535) when it is read.
      It is only reset(1) when it is set."
    ::= { hwMstpObjects 16 }

  hwMstpPathCostStandard  OBJECT-TYPE 
    SYNTAX      INTEGER{dot1d-1998(1),dot1t(2),legacy(3)}
    MAX-ACCESS  read-write
    STATUS      current
    DESCRIPTION
      "Path cost standard of the bridge. Value dot1d-1998 is 
	     IEEE 802.1d standard in 1998, value dot1t is IEEE 802.1t standard, 
	     and value legacy is a private legacy standard.The default path cost standard is 2(IEEE 802.1t standard)."
	  ::= { hwMstpObjects 17 }
    
  hwMstpTimeFactor  OBJECT-TYPE 
    SYNTAX      INTEGER (1..10)
    MAX-ACCESS  read-write
    STATUS      current
    DESCRIPTION
      "Time factor of the Bridge. Time factor can rapily check whether  the message which the port has received
       is timeout.The default value is three times of the hello time ."
    ::= { hwMstpObjects 21 }
    
  hwMstpMD5KEY  OBJECT-TYPE 
    SYNTAX      OCTET STRING (SIZE(0..16))
    MAX-ACCESS  read-write
    STATUS      current
    DESCRIPTION
      "The Region Configuration Digest,a 16 Octet signature of type HMAC-MD5
       Created from the MST Configuration Table. The default value of MD5key is
       0x13AC06A62E47FD51F95D2BA243CD0346."
     ::= { hwMstpObjects 22 }
     
-- TABLE: hwMstpVIDAllocationTable ------
  hwMstpVIDAllocationTable OBJECT-TYPE
    SYNTAX      SEQUENCE OF HwMstpVIDAllocationEntry
    MAX-ACCESS  not-accessible
    STATUS      current
    DESCRIPTION
      "The table includes the information of the vlan with relation to the instance of MSTP."
    ::= { hwMstpObjects 18 }

  hwMstpVIDAllocationEntry OBJECT-TYPE
    SYNTAX      HwMstpVIDAllocationEntry
    MAX-ACCESS  not-accessible
    STATUS      current
    DESCRIPTION
      "The table includes the information of the vlan with relation to the instance of MSTP.
      The index of the table is vlanid.Default, the vlan is in the CIST."
    INDEX { hwMstpVID }
    ::= { hwMstpVIDAllocationTable 1 }

  HwMstpVIDAllocationEntry ::=
    SEQUENCE
    {
      hwMstpVID	INTEGER,
      hwMstpAdminMstID	INTEGER,
      hwMstpOperMstID	INTEGER
    }

  hwMstpVID OBJECT-TYPE
    SYNTAX      INTEGER(1..4094)
    MAX-ACCESS  not-accessible
    STATUS      current
    DESCRIPTION
        "VLAN Identifier"
    ::={ hwMstpVIDAllocationEntry 1 }

  hwMstpAdminMstID OBJECT-TYPE
    SYNTAX      INTEGER(0..48)
    MAX-ACCESS  read-only
    STATUS      current
    DESCRIPTION
        "Administrative Multiple spanning-tree instance Identifier.
         The relation between vlan and Multiple spanning-tree instance 
         is set by operation in the region,
         but it isn't effective if the configuraion isn't actived."
    ::={ hwMstpVIDAllocationEntry 2 }

  hwMstpOperMstID OBJECT-TYPE
    SYNTAX      INTEGER(0..48)
    MAX-ACCESS  read-only
    STATUS      current
    DESCRIPTION
        "Operative Multiple spanning-tree instance Identifier.
        The relation between vlan and Multiple spanning-tree instance
        is effective in the bridge."
    ::={ hwMstpVIDAllocationEntry 3 }

-- TABLE: hwMstpInstanceTable ------
  hwMstpInstanceTable OBJECT-TYPE
    SYNTAX      SEQUENCE OF HwMstpInstanceEntry
    MAX-ACCESS  not-accessible
    STATUS      current
    DESCRIPTION
      "The table includes the information of  the instance."
    ::= { hwMstpObjects 19 }

  hwMstpInstanceEntry OBJECT-TYPE
    SYNTAX      HwMstpInstanceEntry
    MAX-ACCESS  not-accessible
    STATUS      current
    DESCRIPTION
      "The table includes the information of  the instance.
      The index of the table is Multiple spanning-tree instance Identifier."
    INDEX { hwMstpInstanceID }
    ::= { hwMstpInstanceTable 1 }

  HwMstpInstanceEntry ::=
    SEQUENCE
    {
      hwMstpInstanceID	INTEGER,
      hwMstpiBridgeID	BridgeId,
      hwMstpiBridgePriority	INTEGER,
      hwMstpiDesignedRoot	BridgeId,
      hwMstpiRootPathCost	INTEGER,
      hwMstpiRootPort	INTEGER,
      hwMstpiRootType	INTEGER,
      hwMstpiRemainingHops	INTEGER,
      hwMstpiAdminMappedVlanListLow OCTET STRING,
      hwMstpiAdminMappedVlanListHigh OCTET STRING,
      hwMstpiOperMappedVlanListLow OCTET STRING,
      hwMstpiOperMappedVlanListHigh OCTET STRING,
      hwMstpiRowStatus  RowStatus
    }

  hwMstpInstanceID OBJECT-TYPE
    SYNTAX      INTEGER(0..48) 
    MAX-ACCESS  not-accessible
    STATUS      current
    DESCRIPTION
        "Multiple spanning-tree instance Identifier"
    ::={ hwMstpInstanceEntry 1 }

  hwMstpiBridgeID OBJECT-TYPE 
    SYNTAX      BridgeId
    MAX-ACCESS  read-only
    STATUS      current
    DESCRIPTION
        "The Bridge Identifier for the spanning tree instance 
        identified by MSTID"
    ::={ hwMstpInstanceEntry 2 }

  hwMstpiBridgePriority OBJECT-TYPE 
    SYNTAX      INTEGER(0..61440)
    MAX-ACCESS  read-create
    STATUS      current
    DESCRIPTION
        "The Bridge Priority for the spanning tree instance 
        identified by MSTID. Step of 4096.For example,
        we can set the Priority of the bridge such as 0,4096,8192 etc.
        It can be used to determined whether the bridge is the root of
        the spanning tree. "
    DEFVAL      { 32768 }
    ::={ hwMstpInstanceEntry 3 }

  hwMstpiDesignedRoot OBJECT-TYPE 
    SYNTAX      BridgeId
    MAX-ACCESS  read-only
    STATUS      current
    DESCRIPTION
        "The Bridge Identifier of the Root Bridge for the spanning 
        tree instance identified by MSTID"
    ::={ hwMstpInstanceEntry 4 }

  hwMstpiRootPathCost OBJECT-TYPE 
    SYNTAX      INTEGER
    MAX-ACCESS  read-only
    STATUS      current
    DESCRIPTION
        "The path cost from the transmitting Bridge to the Root Bridge 
        for the spanning tree instance  identified by MSTID."
    ::={ hwMstpInstanceEntry 5 }

  hwMstpiRootPort OBJECT-TYPE 
    SYNTAX      INTEGER
    MAX-ACCESS  read-only
    STATUS      current
    DESCRIPTION
        "The Root Port for the spanning tree instance identified by the MSTID."
    ::={ hwMstpInstanceEntry 6 }

  hwMstpiRootType OBJECT-TYPE 
    SYNTAX      INTEGER{normal(0), secondary(1), primary(2)}
    MAX-ACCESS  read-create
    STATUS      current
    DESCRIPTION
        "Config this Bridge as a primary root or seconary root / cancel 
        the root for this spanning tree instance  identified by MSTID.
        The current value of the hwMstpiRootType is the value 
        that was set resently."
    DEFVAL      { normal }
    ::={ hwMstpInstanceEntry 7 }

  hwMstpiRemainingHops OBJECT-TYPE 
    SYNTAX      INTEGER
    MAX-ACCESS  read-only
    STATUS      current
    DESCRIPTION
        "The remaining hops of the spanning tree instance  identified by MSTID."
    ::={ hwMstpInstanceEntry 8 }
    
  hwMstpiAdminMappedVlanListLow  OBJECT-TYPE 
    SYNTAX  OCTET STRING (SIZE(0..256))
    MAX-ACCESS read-create
    STATUS current
    DESCRIPTION 
        " The lower part of administrative Vlan list mapped to the spanning 
        tree instance identified by MSTID."
    ::= { hwMstpInstanceEntry 9 }

  hwMstpiAdminMappedVlanListHigh  OBJECT-TYPE 
    SYNTAX  OCTET STRING (SIZE(0..256))
    MAX-ACCESS read-create
    STATUS current
    DESCRIPTION 
        " The higher part of administrative Vlan  list mapped to the spanning 
        tree instance identified by MSTID."
    ::= { hwMstpInstanceEntry 10 }
    
  hwMstpiOperMappedVlanListLow  OBJECT-TYPE 
    SYNTAX  OCTET STRING (SIZE(0..256))
    MAX-ACCESS read-only
    STATUS current
    DESCRIPTION 
        " The lower part of operative Vlan list mapped to the spanning 
        tree instance identified by MSTID."
    ::= { hwMstpInstanceEntry 11 }

  hwMstpiOperMappedVlanListHigh  OBJECT-TYPE 
    SYNTAX  OCTET STRING (SIZE(0..256))
    MAX-ACCESS read-only
    STATUS current
    DESCRIPTION 
        " The higher part of operative Vlan list mapped to the spanning 
        tree instance identified by MSTID."
    ::= { hwMstpInstanceEntry 12 }  
    
  hwMstpiRowStatus  OBJECT-TYPE
    SYNTAX  RowStatus
    MAX-ACCESS  read-create
    STATUS      current
    DESCRIPTION
          "To band MSTI and Vlan List."
    ::= { hwMstpInstanceEntry 13 }


-- TABLE: hwMstpPortTable ------
  hwMstpPortTable OBJECT-TYPE
    SYNTAX      SEQUENCE OF HwMstpPortEntry
    MAX-ACCESS  not-accessible
    STATUS      current
    DESCRIPTION
      "The table includes the information of the port 
      of the multiple spanning tree instance."
    ::= { hwMstpObjects 20 }

  hwMstpPortEntry OBJECT-TYPE
    SYNTAX      HwMstpPortEntry
    MAX-ACCESS  not-accessible
    STATUS      current
    DESCRIPTION
      "The table includes the information of the port 
      of the multiple spanning tree instance.The index
      of the table is the aggregation of mutiple spanning
      tree instance identifier and port index."
    INDEX { hwMstpInstanceID, hwMstpiPortIndex }
    ::= { hwMstpPortTable 1 }

  HwMstpPortEntry ::=
    SEQUENCE
    {
      hwMstpiPortIndex	INTEGER,
      hwMstpiPortState	INTEGER,
      hwMstpiPortPriority	INTEGER,
      hwMstpiPortPathCost	INTEGER,
      hwMstpiDesignatedRoot	BridgeId,
      hwMstpiDesignatedCost	INTEGER,
      hwMstpiDesignatedBridge	BridgeId,
      hwMstpiDesignatedPort	OCTET STRING,
      hwMstpiStpPortEdgeport	HwMSTPEnabledStatus,
      hwMstpiStpPortPointToPoint	INTEGER,
      hwMstpiStpMcheck	INTEGER,
      hwMstpiStpTransLimit	INTEGER,
      hwMstpiStpRXStpBPDU	Counter32,
      hwMstpiStpTXStpBPDU	Counter32,
      hwMstpiStpRXTCNBPDU	Counter32,
      hwMstpiStpTXTCNBPDU	Counter32,
      hwMstpiStpRXRSTPBPDU	Counter32,
      hwMstpiStpTXRSTPBPDU	Counter32,
      hwMstpiStpRXMSTPBPDU	Counter32,
      hwMstpiStpTXMSTPBPDU	Counter32,
      hwMstpiStpClearStatistics	INTEGER,
      hwMstpiStpDefaultPortCost	INTEGER,
      hwMstpiStpStatus	HwMSTPEnabledStatus,
      hwMstpiPortRootGuard	HwMSTPEnabledStatus,
      hwMstpiPortLoopGuard  HwMSTPEnabledStatus
    }

  hwMstpiPortIndex OBJECT-TYPE
    SYNTAX      INTEGER
    MAX-ACCESS  not-accessible
    STATUS      current
    DESCRIPTION
        "The index of the Bridge Port"
    ::={ hwMstpPortEntry 1 }
      
  hwMstpiPortState OBJECT-TYPE 
    SYNTAX      INTEGER{disabled(1),discarding(2),learning(4),forwarding(5)}
    MAX-ACCESS  read-only
    STATUS      current
    DESCRIPTION
        "The current state of the Port (i.e., Disabled, Discarding , 
        Learning, Forwarding)"
    ::={ hwMstpPortEntry 2 }

  hwMstpiPortPriority OBJECT-TYPE 
    SYNTAX      INTEGER(0..240)
    MAX-ACCESS  read-write
    STATUS      current
    DESCRIPTION
        "The value of the priority field which is contained in the 
        first (in network byte order)  four bits of the (2 octet long) Port ID.  
        The other octet of the Port ID is given by the value of mstiPortIndex. 
        And step of 16.It is the priority of the port in the multiple spanning tree instance,
        and it can be used to determine the role of the port in the multiple spanning tree ."
    DEFVAL      { 128 }
    ::={ hwMstpPortEntry 3 }

  hwMstpiPortPathCost OBJECT-TYPE 
    SYNTAX      INTEGER(1..200000000)
    MAX-ACCESS  read-write
    STATUS      current
    DESCRIPTION
        "the path cost of paths with which the package passes the port.
         The range of path cost is 1..65535 for 802.1d standard,
         is 1..200000000 for 802.1t standard,and is 1..200000  
         for the legacy standard. "
    ::={ hwMstpPortEntry 4 }

  hwMstpiDesignatedRoot OBJECT-TYPE 
    SYNTAX      BridgeId
    MAX-ACCESS  read-only
    STATUS      current
    DESCRIPTION
        "The Bridge Identifier of the Root Bridge for the port of the Spanning
         Tree instance identified by the MSTID"
    ::={ hwMstpPortEntry 5 }
 
  hwMstpiDesignatedCost OBJECT-TYPE 
    SYNTAX      INTEGER
    MAX-ACCESS  read-only
    STATUS      current
    DESCRIPTION
        "The path cost of the Designated Port of the segment connected to 
        this port.  This value is compared to the Root Path Cost field 
        in received bridge PDUs."
    ::={ hwMstpPortEntry 6}

  hwMstpiDesignatedBridge OBJECT-TYPE 
    SYNTAX      BridgeId
    MAX-ACCESS  read-only
    STATUS      current
    DESCRIPTION
        "The Bridge Identifier of the bridge which this port considers to 
        be the Designated Bridge for this port's segment."
    ::={ hwMstpPortEntry 7 }

  hwMstpiDesignatedPort OBJECT-TYPE 
    SYNTAX      OCTET STRING(SIZE (2))
    MAX-ACCESS  read-only
    STATUS      current
    DESCRIPTION
        "The Port Identifier of the port on the Designated Bridge 
        for this port's segment."
    ::={ hwMstpPortEntry 8 }
 
  hwMstpiStpPortEdgeport OBJECT-TYPE
    SYNTAX      HwMSTPEnabledStatus
    MAX-ACCESS  read-write
    STATUS      current
    DESCRIPTION
        " Whether the port fast is enabled. 
          When the port is the edge port,it can change to forwarding state .
          We can set the value.Disable indicates that we make the port not 
          to be a edge port.Enable indicates that we make the port to be a 
          edge port."
    DEFVAL      { disabled }
    ::={ hwMstpPortEntry 9 }
  
  hwMstpiStpPortPointToPoint OBJECT-TYPE
    SYNTAX      INTEGER{forceTrue (1),forceFalse (2),auto  (3)}
    MAX-ACCESS  read-write
    STATUS      current
    DESCRIPTION
        " Whether the port connects the point to point link.
          If user set the port as a point to point port,
          the port is a point to point port in all instance of the MSTP.
          If user set the port as a point to point port but the port isn't,
          the mstp may import temporary loop.So user can use the default.
         "
    DEFVAL      { auto }
    ::={ hwMstpPortEntry 10 }

  hwMstpiStpMcheck OBJECT-TYPE
    SYNTAX      INTEGER{enable(1),unused(65535)}
    MAX-ACCESS  read-write
    STATUS      current
    DESCRIPTION
        " Forcing the state machine to send MST BPDUs in this manner 
        can be used to test whether all legacy Bridges on a given LAN 
        have been removed.The value of hwMstpiStpMcheck is unused(65535) 
        when it is read.The value of hwMstpiStpMcheck must be enable(1) when it is set."
    ::={ hwMstpPortEntry 11 }

  hwMstpiStpTransLimit OBJECT-TYPE
    SYNTAX      INTEGER(1..255)
    MAX-ACCESS  read-write
    STATUS      current
    DESCRIPTION
        "The value used by the Port Transmit state machine to limit 
        the maximum transmission rate. "
    DEFVAL      { 3 }
    ::={ hwMstpPortEntry 12 }

  hwMstpiStpRXStpBPDU OBJECT-TYPE
    SYNTAX      Counter32
    MAX-ACCESS  read-only
    STATUS      current
    DESCRIPTION
        "The number of received Config BPDU. Effective in CIST."
    ::={ hwMstpPortEntry 13 }

  hwMstpiStpTXStpBPDU OBJECT-TYPE
    SYNTAX      Counter32
    MAX-ACCESS  read-only
    STATUS      current
    DESCRIPTION
        "The number of transmitted Config BPDU. Effective in CIST."
    ::={ hwMstpPortEntry 14 }

  hwMstpiStpRXTCNBPDU OBJECT-TYPE
    SYNTAX      Counter32
    MAX-ACCESS  read-only
    STATUS      current
    DESCRIPTION
        "The number of received TCN BPDU. Effective in CIST."
    ::={ hwMstpPortEntry 15 }

  hwMstpiStpTXTCNBPDU OBJECT-TYPE
    SYNTAX      Counter32
    MAX-ACCESS  read-only
    STATUS      current
    DESCRIPTION
        "The number of transmitted TCN BPDU. Effective in CIST."
    ::={ hwMstpPortEntry 16 }

  hwMstpiStpRXRSTPBPDU OBJECT-TYPE
    SYNTAX      Counter32
    MAX-ACCESS  read-only
    STATUS      current
    DESCRIPTION
        "The number of received RST BPDU. Effective in CIST."
    ::={ hwMstpPortEntry 17 }

  hwMstpiStpTXRSTPBPDU OBJECT-TYPE
    SYNTAX      Counter32
    MAX-ACCESS  read-only
    STATUS      current
    DESCRIPTION
        "The number of transmitted RST BPDU. Effective in CIST."
    ::={ hwMstpPortEntry 18 }

  hwMstpiStpRXMSTPBPDU OBJECT-TYPE
    SYNTAX      Counter32
    MAX-ACCESS  read-only
    STATUS      current
    DESCRIPTION
        "The number of received MST BPDU. Effective in CIST."
    ::={ hwMstpPortEntry 19 }

  hwMstpiStpTXMSTPBPDU OBJECT-TYPE
    SYNTAX      Counter32
    MAX-ACCESS  read-only
    STATUS      current
    DESCRIPTION
        "The number of transmitted MST BPDU. Effective in CIST."
    ::={ hwMstpPortEntry 20 }

  hwMstpiStpClearStatistics OBJECT-TYPE 
    SYNTAX      INTEGER{clear(1),unused(65535)}
    MAX-ACCESS  read-write
    STATUS      current
    DESCRIPTION
        "Clear the spanning tree statistic. Effective in CIST.
        The value of hwMstpiStpClearStatistics is unused(65535) when it is read.
        The value of hwMstpiStpClearStatistics must be clear(1) when it is set."
    ::={ hwMstpPortEntry 21 }

  hwMstpiStpDefaultPortCost OBJECT-TYPE
    SYNTAX      INTEGER{reset(1),unused(65535)}     
    MAX-ACCESS  read-write
    STATUS      current
    DESCRIPTION
        "Set default Port path cost.
        The value of hwMstpiStpDefaultPortCost is unused(65535) when it is read.
        The value of  hwMstpiStpDefaultPortCost must be reset(1) when it is set."
    ::={ hwMstpPortEntry 22}

  hwMstpiStpStatus OBJECT-TYPE 
    SYNTAX      HwMSTPEnabledStatus
    MAX-ACCESS  read-write
    STATUS      current
    DESCRIPTION
        "Whether the spanning tree protocol is enabled on this port. 
        Effective in CIST."
    DEFVAL      { enabled}
    ::={ hwMstpPortEntry 23 }

  hwMstpiPortRootGuard OBJECT-TYPE 
    SYNTAX      HwMSTPEnabledStatus
    MAX-ACCESS  read-write
    STATUS      current
    DESCRIPTION
        "Whether the root guard is enabled. 
         The function is to prevent the port from receiving the BPDU 
         ,the priority of which is above the priority of the port."
    DEFVAL      { disabled }
    ::={ hwMstpPortEntry 24 }

  hwMstpiPortLoopGuard OBJECT-TYPE 
    SYNTAX      HwMSTPEnabledStatus
    MAX-ACCESS  read-write
    STATUS      current
    DESCRIPTION
        "Whether the loop protection is enabled. "
    DEFVAL      { disabled }
    ::={ hwMstpPortEntry 25 }
    
 hwMstpTraps OBJECT-IDENTITY
     STATUS      current
     DESCRIPTION "Definition point for Mstp notifications."
     ::= { hwMstp 2 }

 hwMstpiPortStateForwarding NOTIFICATION-TYPE
     OBJECTS  { hwMstpInstanceID , hwMstpiPortIndex}
     STATUS   current
     DESCRIPTION
         "The SNMP trap that is generated when a port turns into 
         forwarding state form other state."
     ::= { hwMstpTraps 1 }

  hwMstpiPortStateDiscarding NOTIFICATION-TYPE
     OBJECTS  { hwMstpInstanceID , hwMstpiPortIndex}
     STATUS   current
     DESCRIPTION
         "The SNMP trap that is generated when a port turns into 
         discarding state form forwarding state."
     ::= { hwMstpTraps 2 }
     

  hwMstpiBridgeLostRootPrimary NOTIFICATION-TYPE --
     OBJECTS  { hwMstpInstanceID }
     STATUS   current
     DESCRIPTION
         "The SNMP trap that is generated when the bridge is no longer 
         the root bridge of the instance. Another switch with higher 
         priority has already been the root bridge of the instance."   
     ::= { hwMstpTraps 3 }
     
  hwMstpiPortRootGuarded NOTIFICATION-TYPE --
     OBJECTS  { hwMstpInstanceID , hwMstpiPortIndex}
     STATUS   current
     DESCRIPTION
         "The SNMP trap that is generated when a root-guard port 
         receives a superior message on the relevant instance."
     ::= { hwMstpTraps 4 }

  hwMstpiPortBpduGuarded NOTIFICATION-TYPE
     OBJECTS  { hwMstpiPortIndex }
     STATUS   current
     DESCRIPTION
         "The SNMP trap that is generated when an edged port of 
         the BPDU-guard switch receives BPDU packets."
     ::= { hwMstpTraps 5 }
     
  hwMstpiPortLoopGuarded NOTIFICATION-TYPE
     OBJECTS  { hwMstpInstanceID , hwMstpiPortIndex}
     STATUS   current
     DESCRIPTION
         "The SNMP trap that is generated when an Alternate-Port 
         or Root-Port is aged out."
     ::= { hwMstpTraps 6 }
     
-- -------------------------------------------------------------
-- HUAWEI MSTP MIB - Conformance Information
-- -------------------------------------------------------------     

  hwMstpConformance OBJECT IDENTIFIER ::= { hwMstp 3 }
      
-- -------------------------------------------------------------
-- units of conformance
-- -------------------------------------------------------------

  hwMstpGroups OBJECT IDENTIFIER ::= { hwMstpConformance 1 }
  
  hwMstpBridgeInfoGroup OBJECT-GROUP
  OBJECTS {
        	hwMstpStatus,
		hwMstpForceVersion,
		hwMstpDiameter,
		hwMstpBridgeMaxHops,
		hwMstpMasterBridgeID,
		hwMstpMasterPathCost,
		hwMstpBpduGuard,
		hwMstpAdminFormatSelector,
		hwMstpAdminRegionName,
		hwMstpAdminRevisionLevel,
		hwMstpOperFormatSelector,
		hwMstpOperRegionName,
		hwMstpOperRevisionLevel,
		hwMstpRegionConfActive,
		hwMstpDefaultVlanAllo,
		hwMstpDefaultRegionName,
		hwMstpPathCostStandard,
		hwMstpTimeFactor,
		hwMstpMD5KEY
    	  }
    STATUS      current
    DESCRIPTION
        "A collection of objects indicating the necessary
        capabilites of the bridge device which is running the multi spanning tree protocol."
    ::= { hwMstpGroups 1 }
    
  hwMstpVlanInfoGroup  OBJECT-GROUP
  OBJECTS {
        	hwMstpVID,
      		hwMstpAdminMstID,
      		hwMstpOperMstID
    	  }
    STATUS      current
    DESCRIPTION
        "A collection of objects describes 
        the attribute of the vlan in the multi spanning tree protocol.
        They are necessary to find the relation 
        between vlan and instance by the vlan identifier."
    ::= { hwMstpGroups 2 }
    
  hwMstpInstanceInfoGroup  OBJECT-GROUP
  OBJECTS {
        	hwMstpInstanceID,
      		hwMstpiBridgeID,
      		hwMstpiBridgePriority,
      		hwMstpiDesignedRoot,
      		hwMstpiRootPathCost,
      		hwMstpiRootPort,
      		hwMstpiRootType,
      		hwMstpiRemainingHops,
      		hwMstpiAdminMappedVlanListLow,
      		hwMstpiAdminMappedVlanListHigh,
      		hwMstpiOperMappedVlanListLow,
      		hwMstpiOperMappedVlanListHigh
    	  }
    STATUS      current
    DESCRIPTION
        "A collection of objects describes 
        the attribute of the instance in the multi spanning tree protocol."
    ::= { hwMstpGroups 3 }
    
  hwMstpPortInfoGroup  OBJECT-GROUP
  OBJECTS {
        	hwMstpiPortIndex,
      		hwMstpiPortState,
      		hwMstpiPortPriority,
     		hwMstpiPortPathCost,
     		hwMstpiDesignatedRoot,
      		hwMstpiDesignatedCost,
      		hwMstpiDesignatedBridge,
      		hwMstpiDesignatedPort,
      		hwMstpiStpPortEdgeport,
      		hwMstpiStpPortPointToPoint,
      		hwMstpiStpMcheck,
     	 	hwMstpiStpTransLimit,
      		hwMstpiStpRXStpBPDU,
      		hwMstpiStpTXStpBPDU,
      		hwMstpiStpRXTCNBPDU,
      		hwMstpiStpTXTCNBPDU,
      		hwMstpiStpRXRSTPBPDU,
      		hwMstpiStpTXRSTPBPDU,
      		hwMstpiStpRXMSTPBPDU,
      		hwMstpiStpTXMSTPBPDU,
      		hwMstpiStpClearStatistics,
      		hwMstpiStpDefaultPortCost,
      		hwMstpiStpStatus,
      		hwMstpiPortRootGuard,
      		hwMstpiPortLoopGuard
    	  }
    STATUS      current
    DESCRIPTION
        "A collection of objects is necessary to show the 
         information of the port in the bridge in the multi 
         spanning tree protocol."
    ::= { hwMstpGroups 4 }
    
hwMstpCompliances OBJECT IDENTIFIER
    ::= { hwMstpConformance 2 }
    
  
-- -------------------------------------------------------------
-- compliance statements
-- -------------------------------------------------------------
    hwMstpCompliance MODULE-COMPLIANCE
    STATUS  current
    DESCRIPTION
        "The compliance statement for device support of Priority
        and Multicast Filtering extended bridging services."

    MODULE
        MANDATORY-GROUPS { hwMstpBridgeInfoGroup, 
        		   hwMstpVlanInfoGroup,
        		   hwMstpInstanceInfoGroup,
        		   hwMstpPortInfoGroup
        		   }
       ::= { hwMstpCompliances 1 }    

END
