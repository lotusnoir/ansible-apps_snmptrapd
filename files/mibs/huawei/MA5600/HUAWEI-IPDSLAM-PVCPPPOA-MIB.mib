HUAWEI-IPDSLAM-PVCPPPOA-MIB DEFINITIONS ::= BEGIN

IMPORTS
	OBJECT-TYPE, MODULE-IDENTITY		
		FROM SNMPv2-SMI	       		
	huaweiUtility			
		FROM HUAWEI-MIB    
	TruthValue
                FROM SNMPv2-TC;  
		 
				
hwIpDslamPvcPPPoA MODULE-IDENTITY
	LAST-UPDATED "200407070900Z"
	ORGANIZATION "Fix-Net Dept, Huawei Technologies Co.,Ltd."
	CONTACT-INFO 
		"Floor 5 ,Block 4, R&D Building,
		Huawei Longgang Production Base,
		Shenzhen,   P.R.C.
		http://www.huawei.com
		Zip:518057
		"
	DESCRIPTION 
		"huawei ipdslam PVC protocol table."
    ::= { huaweiUtility 44 }
    	                                      

--  ------------------------------------------------------------------------
-- System Management Parameter
-- ------------------------------------------------------------------------ 
hwIpDslamPPPoASwitch OBJECT-TYPE
	      SYNTAX  TruthValue
	      MAX-ACCESS  read-write
	      STATUS      current
	      DESCRIPTION
	         "
	         The global switch of PPPoA2E.
          	 "	      
          DEFVAL 	  { false}
	      ::= { hwIpDslamPvcPPPoA 1 }   
	
hwIpDslamPPPoAMacMode OBJECT-TYPE
	      SYNTAX INTEGER
		      {
			multi-mac(1),
			single-mac(2)
	 	      }
	      MAX-ACCESS  read-write
	      STATUS      current
	      DESCRIPTION
	         "
	         The MAC distribution mode of PPPoA2E.
          	 "	      
          DEFVAL 	  {multi-mac}
	      ::= { hwIpDslamPvcPPPoA 2 }
	      
hwIpDslamPPPoAUserId OBJECT-TYPE
	      SYNTAX INTEGER
		      {
			host-uniq(1),
			relay-session-id(2)
	 	      }
	      MAX-ACCESS  read-write
	      STATUS      current
	      DESCRIPTION
	         "
	         The selection of user identifier in PPPoE of PPPoA2E.
          	 "	      
          DEFVAL 	  {host-uniq}
	      ::= { hwIpDslamPvcPPPoA 3 }	
	      
hwIpDslamPPPoAMRUSwitch OBJECT-TYPE
	      SYNTAX  TruthValue
	      MAX-ACCESS  read-write
	      STATUS      current
	      DESCRIPTION
	         "
	         The global switch of PPPoA2E MRU negotiation function.
          	 "	      
          DEFVAL 	  { false}
	      ::= { hwIpDslamPvcPPPoA 4 }  	
	      
END
