--
-- HUAWEI-LICENSE-MIB.mib
-- MIB generated by MG-SOFT Visual MIB Builder Version 2.5 Build 225
-- Thursday, October 25, 2007 at 16:08:12
--

	HUAWEI-LICENSE-MIB DEFINITIONS ::= BEGIN

		IMPORTS 
			huaweiUtility			
				FROM HUAWEI-MIB			
			IpAddress, Unsigned32, OBJECT-TYPE, MODULE-IDENTITY			
				FROM SNMPv2-SMI;
	
	
		hwLicense MODULE-IDENTITY
			LAST-UPDATED "200304280900Z"
			ORGANIZATION
				"Fix-Net Dep, Huawei Technologies Co.,Ltd."
			CONTACT-INFO
				"Floot 5 ,Block 4, R&D Building,
				Huawei Longgang Production Base,
				Shenzhen,   P.R.C.
				http://www.huawei.com
				Zip:518057
				"
			DESCRIPTION
				"huawei license  mib."
			REVISION "200302280900Z"
			DESCRIPTION
				"V1.00  initialized  by IAS 
				"
			::= { huaweiUtility 114 }
		
	
--
-- Type definitions
--
	
		Time ::= OCTET STRING
		
	
--
-- Node definitions
--
	
		hwLicensePara OBJECT IDENTIFIER ::= { hwLicense 1 }
		
		hwLicSpecialtySwitch OBJECT-TYPE
			SYNTAX INTEGER
				{
				on(1),
				off(2)
				}
			MAX-ACCESS read-write
			STATUS current
			DESCRIPTION
				"Special license switch. When you query the switch status, 1 stands for on and 2 for off. The switch status can be set as
				
				1 only. That is, the switch can be switched on but cannot be switched off.
				"
			::= { hwLicensePara 1 }
		
		hwLicESN OBJECT-TYPE
			SYNTAX IpAddress
			MAX-ACCESS read-write
			STATUS current
			DESCRIPTION
				"
				Serial number of the device, used for identifying the device uniquely.
				
				"
			::= { hwLicensePara 2 }
		
		hwLicFirstServerIP OBJECT-TYPE
			SYNTAX IpAddress
			MAX-ACCESS read-write
			STATUS current
			DESCRIPTION
				"IP address of the license primary server.
				
				"
			::= { hwLicensePara 3 }
		
		hwLicSecondServerIP OBJECT-TYPE
			SYNTAX IpAddress
			MAX-ACCESS read-write
			STATUS current
			DESCRIPTION
				"
				IP address of the license secondary server."
			::= { hwLicensePara 4 }
		
		hwLicServerPort OBJECT-TYPE
			SYNTAX Unsigned32 (1024..65535)
			MAX-ACCESS read-write
			STATUS current
			DESCRIPTION
				"Port number of the license server."
			::= { hwLicensePara 5 }
		
		hwLicBasicSwitch OBJECT-TYPE
			SYNTAX INTEGER
				{
				on(1),
				off(2)
				}
			MAX-ACCESS read-write
			STATUS current
			DESCRIPTION
				"Basic license switch. When you query the switch status, 1 stands for on and 2 for off. The switch status can be set as
				
				1 only. That is, the switch can be switched on but cannot be switched off.
				."
			::= { hwLicensePara 6 }
		
		hwLicResTable OBJECT-TYPE
			SYNTAX SEQUENCE OF HwLicResEntry
			MAX-ACCESS not-accessible
			STATUS current
			DESCRIPTION
				"Description."
			::= { hwLicense 2 }
		
		hwLicResEntry OBJECT-TYPE
			SYNTAX HwLicResEntry
			MAX-ACCESS not-accessible
			STATUS current
			DESCRIPTION
				"Description."
			INDEX { hwLicFeatureName, IMPLIED hwLicResName }
			::= { hwLicResTable 1 }
		
		HwLicResEntry ::=
			SEQUENCE { 
				hwLicFeatureName
					OCTET STRING,
				hwLicResName
					OCTET STRING,
				hwLicResAuthNum
					Unsigned32,
				hwLicResUsedNum
					Unsigned32,
				hwLicResDesc
					OCTET STRING
			 }

		hwLicFeatureName OBJECT-TYPE
			SYNTAX OCTET STRING
			MAX-ACCESS read-only
			STATUS current
			DESCRIPTION
				"Feature name."
			::= { hwLicResEntry 1 }
		
		hwLicResName OBJECT-TYPE
			SYNTAX OCTET STRING
			MAX-ACCESS read-only
			STATUS current
			DESCRIPTION
				"Resource name."
			::= { hwLicResEntry 2 }
		
		hwLicResAuthNum OBJECT-TYPE
			SYNTAX Unsigned32
			MAX-ACCESS read-only
			STATUS current
			DESCRIPTION
				"Authorization quantity."
			::= { hwLicResEntry 3 }
		
		hwLicResUsedNum OBJECT-TYPE
			SYNTAX Unsigned32
			MAX-ACCESS read-only
			STATUS current
			DESCRIPTION
				"Usage quantity."
			::= { hwLicResEntry 4 }
		
		hwLicResDesc OBJECT-TYPE
			SYNTAX OCTET STRING
			MAX-ACCESS read-only
			STATUS current
			DESCRIPTION
				"Resource description."
			::= { hwLicResEntry 5 }
		
		hwLicFuncTable OBJECT-TYPE
			SYNTAX SEQUENCE OF HwLicFuncEntry
			MAX-ACCESS not-accessible
			STATUS current
			DESCRIPTION
				"Description."
			::= { hwLicense 3 }
		
		hwLicFuncEntry OBJECT-TYPE
			SYNTAX HwLicFuncEntry
			MAX-ACCESS not-accessible
			STATUS current
			DESCRIPTION
				"Description."
			INDEX { hwLicFeatureName, IMPLIED hwLicFuncName }
			::= { hwLicFuncTable 1 }
		
		HwLicFuncEntry ::=
			SEQUENCE { 
				hwLicFuncName
					OCTET STRING,
				hwLicFuncAuth
					INTEGER,
				hwLicFuncDesc
					OCTET STRING
			 }

		hwLicFuncName OBJECT-TYPE
			SYNTAX OCTET STRING
			MAX-ACCESS read-only
			STATUS current
			DESCRIPTION
				"Function name."
			::= { hwLicFuncEntry 1 }
		
		hwLicFuncAuth OBJECT-TYPE
			SYNTAX INTEGER
				{
				disable(1),
				enable(2)
				}
			MAX-ACCESS read-only
			STATUS current
			DESCRIPTION
				"Function Authorization."
			::= { hwLicFuncEntry 2 }
		
		hwLicFuncDesc OBJECT-TYPE
			SYNTAX OCTET STRING
			MAX-ACCESS read-only
			STATUS current
			DESCRIPTION
				"Function description."
			::= { hwLicFuncEntry 3 }
		
	
	END

--
-- HUAWEI-LICENSE-MIB.mib
--
