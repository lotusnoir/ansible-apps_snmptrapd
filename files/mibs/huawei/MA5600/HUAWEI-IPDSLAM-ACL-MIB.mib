--
-- HUAWEI-ACL-MIB.my
-- MIB generated by MG-SOFT Visual MIB Builder Version 3.0 Build 253
-- Sunday, January 16, 2005 at 15:28:35
--

--  HUAWEI-ACL-MIB.my
-- MIB generated by MG-SOFT Visual MIB Builder Version 3.0 Build 253
-- Tuesday, January 04, 2005 at 16:11:30
-- 
--  ====================================================================
-- Copyright (C) 2003 by  HUAWEI TECHNOLOGIES. All rights reserved.
-- 
-- Description: Huawei Acl MIB Definition
-- Reference: Huawei Enterprise MIB
-- Version: V2.0
-- History:
--   Wang Ning,2002-11-29,Reunification version based on the  Fix-Net MIBs baseline by the MIB Standard community.
-- Version: V2.1
-- History:
--   Yang Hongjie,2003-04-11,Reunification version based on V2.0.
-- =====================================================================

	HUAWEI-ACL-MIB DEFINITIONS ::= BEGIN
 
		IMPORTS
			huaweiMgmt			
				FROM HUAWEI-MIB			
			IpAddress, Integer32, Counter32, OBJECT-TYPE, MODULE-IDENTITY			
				FROM SNMPv2-SMI			
			RowStatus, TruthValue, MacAddress			
				FROM SNMPv2-TC;
	
	
--   November 29, 2002 at 09:00 GMT
-- November 29, 2002 at 09:00 GMT
		hwAcl MODULE-IDENTITY 
			LAST-UPDATED "200211290900Z"		-- November 29, 2002 at 09:00 GMT
			ORGANIZATION 
				"Huawei Technologies Co., Ltd."
			CONTACT-INFO 
				"R&D BeiJing, Huawei Technologies co.,Ltd.
				Huawei Bld.,NO.3 Xinxi Rd., 
				Shang-Di Information Industry Base,
				Hai-Dian District Beijing P.R. China
				Zip:100085 
				Http://www.huawei.com                                       
				E-mail:support@huawei.com"
			DESCRIPTION 
				"The HUAWEI-ACL-MIB contains objects to
				Configure ACL-module."
			::= { huaweiMgmt 1 }
		
	
	
--
-- Node definitions
--
	
--  Node definitions
-- 
-- Node definitions
-- 
-- 1.3.6.1.4.1.2011.5.1.1
-- 1.3.6.1.4.1.2011.5.1.1
		-- 1.3.6.1.4.1.2011.5.1.1
		hwAclMibObjects OBJECT IDENTIFIER ::= { hwAcl 1 }
		
--    1.3.6.1.4.1.2011.5.1.1.2
-- 1.3.6.1.4.1.2011.5.1.1.2
-- 1.3.6.1.4.1.2011.5.1.1.2
		-- 1.3.6.1.4.1.2011.5.1.1.2
		hwAclNumGroupTable OBJECT-TYPE
			SYNTAX SEQUENCE OF HwAclNumGroupEntry
			MAX-ACCESS not-accessible
			STATUS current
			DESCRIPTION
				"The table of ACL group information including
				match order, step, description and so on"
			::= { hwAclMibObjects 2 }
		
--    1.3.6.1.4.1.2011.5.1.1.2.1
-- 1.3.6.1.4.1.2011.5.1.1.2.1
-- 1.3.6.1.4.1.2011.5.1.1.2.1
		-- 1.3.6.1.4.1.2011.5.1.1.2.1
		hwAclNumGroupEntry OBJECT-TYPE
			SYNTAX HwAclNumGroupEntry
			MAX-ACCESS not-accessible
			STATUS current
			DESCRIPTION
				"An entry containing characters of a number-acl group "
			INDEX { hwAclNumGroupAclNum }
			::= { hwAclNumGroupTable 1 }
		
		HwAclNumGroupEntry ::=
			SEQUENCE { 
				hwAclNumGroupAclNum
					Integer32,
				hwAclNumGroupMatchOrder
					INTEGER,
				hwAclNumGroupSubitemNum
					Counter32,
				hwAclNumGroupStep
					Integer32,
				hwAclNumGroupDescription
					OCTET STRING,
				hwAclNumGroupCountClear
					INTEGER,
				hwAclNumGroupRowStatus
					RowStatus
			 }

--    1.3.6.1.4.1.2011.5.1.1.2.1.1
-- 1.3.6.1.4.1.2011.5.1.1.2.1.1
-- 1.3.6.1.4.1.2011.5.1.1.2.1.1
		-- 1.3.6.1.4.1.2011.5.1.1.2.1.1
		hwAclNumGroupAclNum OBJECT-TYPE
			SYNTAX Integer32 (2000..5999)
			MAX-ACCESS not-accessible
			STATUS current
			DESCRIPTION
				"The index of number-acl group, identifying an ACL.
				The object specifies the range of an ACL number. 
				The basic ACL is represented by the number 
				in the range 2000 through 2999. The advanced ACL is 
				represented by the number in the range 3000 through 
				3999. The interface-based ACL is represented by the 
				number in the range 2000 to 5999."
			::= { hwAclNumGroupEntry 1 }
		
--    1.3.6.1.4.1.2011.5.1.1.2.1.2
-- 1.3.6.1.4.1.2011.5.1.1.2.1.2
-- 1.3.6.1.4.1.2011.5.1.1.2.1.2
		-- 1.3.6.1.4.1.2011.5.1.1.2.1.2
		hwAclNumGroupMatchOrder OBJECT-TYPE
			SYNTAX INTEGER
				{
				config(1),
				auto(2)
				}
			MAX-ACCESS read-only
			STATUS current
			DESCRIPTION
				"The object indicates the match order of rules. 
				'config' means matching ACL rules in the configuration sequence,
				'auto' means matches ACL rules following the 'Depth-first' principle."
			DEFVAL { config }
			::= { hwAclNumGroupEntry 2 }
		
--    1.3.6.1.4.1.2011.5.1.1.2.1.3
-- 1.3.6.1.4.1.2011.5.1.1.2.1.3
-- 1.3.6.1.4.1.2011.5.1.1.2.1.3
		-- 1.3.6.1.4.1.2011.5.1.1.2.1.3
		hwAclNumGroupSubitemNum OBJECT-TYPE
			SYNTAX Counter32
			MAX-ACCESS read-only
			STATUS current
			DESCRIPTION
				"The total number of the rules in the acl group."
			::= { hwAclNumGroupEntry 3 }
		
--   1.3.6.1.4.1.2011.5.1.1.2.1.4
-- 1.3.6.1.4.1.2011.5.1.1.2.1.4
		-- 1.3.6.1.4.1.2011.5.1.1.2.1.4
		hwAclNumGroupStep OBJECT-TYPE
			SYNTAX Integer32 (1..20)
			MAX-ACCESS read-create
			STATUS current
			DESCRIPTION
				"The object indicates the step value of number acl.
				Step here refers to the difference between each ID. 
				For instance, given the step is set to 5, 
				the IDs are the multiples of 5 beginning with 0.
				The ACL IDs change along with the step. When the step is 5, 
				the ACL IDs are 0, 5, 10, and 15 and so on. 
				However, when the step is set to 2, the IDs turn to 0, 2, 4, 
				and 6 and so on."
			DEFVAL { 5 }
			::= { hwAclNumGroupEntry 4 }
		
--   1.3.6.1.4.1.2011.5.1.1.2.1.5
-- 1.3.6.1.4.1.2011.5.1.1.2.1.5
		-- 1.3.6.1.4.1.2011.5.1.1.2.1.5
		hwAclNumGroupDescription OBJECT-TYPE
			SYNTAX OCTET STRING (SIZE (0..127))
			MAX-ACCESS read-create
			STATUS current
			DESCRIPTION
				"The object indicates the description of this acl group.
				The object describes the usage of an ACL with a word or a sentence."
			::= { hwAclNumGroupEntry 5 }
		
--    1.3.6.1.4.1.2011.5.1.1.4.1.11
-- 1.3.6.1.4.1.2011.5.1.1.2.1.6
-- 1.3.6.1.4.1.2011.5.1.1.2.1.6
		-- 1.3.6.1.4.1.2011.5.1.1.2.1.6
		hwAclNumGroupCountClear OBJECT-TYPE
			SYNTAX INTEGER
				{
				cleared(1),
				nouse(2)
				}
			MAX-ACCESS read-create
			STATUS current
			DESCRIPTION
				"Reset the statistics of ACL group."
			::= { hwAclNumGroupEntry 6 }
		
--    1.3.6.1.4.1.2011.5.1.1.3.1.6
-- 1.3.6.1.4.1.2011.5.1.1.2.1.7
-- 1.3.6.1.4.1.2011.5.1.1.2.1.7
		-- 1.3.6.1.4.1.2011.5.1.1.2.1.7
		hwAclNumGroupRowStatus OBJECT-TYPE
			SYNTAX RowStatus
			MAX-ACCESS read-create
			STATUS current
			DESCRIPTION
				"RowStatus，Now support three value:CreateAndGo,Active,Destroy."
			::= { hwAclNumGroupEntry 7 }
		
--   1.3.6.1.4.1.2011.5.1.1.4
-- 1.3.6.1.4.1.2011.5.1.1.4
		-- 1.3.6.1.4.1.2011.5.1.1.4
		hwAclBasicRuleTable OBJECT-TYPE
			SYNTAX SEQUENCE OF HwAclBasicRuleEntry
			MAX-ACCESS not-accessible
			STATUS current
			DESCRIPTION
				"Configure the rule for basic acl group"
			::= { hwAclMibObjects 4 }
		
--   1.3.6.1.4.1.2011.5.1.1.4.1
-- 1.3.6.1.4.1.2011.5.1.1.4.1
		-- 1.3.6.1.4.1.2011.5.1.1.4.1
		hwAclBasicRuleEntry OBJECT-TYPE
			SYNTAX HwAclBasicRuleEntry
			MAX-ACCESS not-accessible
			STATUS current
			DESCRIPTION
				"Define the index of hwAclBasicRuleTable"
			INDEX { hwAclBasicAclNum, hwAclBasicSubitem }
			::= { hwAclBasicRuleTable 1 }
		
		HwAclBasicRuleEntry ::=
			SEQUENCE { 
				hwAclBasicAclNum
					Integer32,
				hwAclBasicSubitem
					Integer32,
				hwAclBasicAct
					INTEGER,
				hwAclBasicSrcIp
					IpAddress,
				hwAclBasicSrcWild
					IpAddress,
				hwAclBasicTimeRangeIndex
					Integer32,
				hwAclBasicFragments
					TruthValue,
				hwAclBasicLog
					TruthValue,
				hwAclBasicEnable
					TruthValue,
				hwAclBasicCount
					Counter32,
				hwAclBasicCountClear
					INTEGER,
				hwAclBasicRowStatus
					RowStatus
			 }

--   1.3.6.1.4.1.2011.5.1.1.4.1.1
-- 1.3.6.1.4.1.2011.5.1.1.4.1.1
		-- 1.3.6.1.4.1.2011.5.1.1.4.1.1
		hwAclBasicAclNum OBJECT-TYPE
			SYNTAX Integer32 (2000..2999)
			MAX-ACCESS not-accessible
			STATUS current
			DESCRIPTION
				"The index of basic acl group"
			::= { hwAclBasicRuleEntry 1 }
		
--   1.3.6.1.4.1.2011.5.1.1.4.1.2
-- 1.3.6.1.4.1.2011.5.1.1.4.1.2
		-- 1.3.6.1.4.1.2011.5.1.1.4.1.2
		hwAclBasicSubitem OBJECT-TYPE
			SYNTAX Integer32 (0..4294967295)
			MAX-ACCESS not-accessible
			STATUS current
			DESCRIPTION
				"The sub-index of basic acl group"
			::= { hwAclBasicRuleEntry 2 }
		
--   1.3.6.1.4.1.2011.5.1.1.4.1.3
-- 1.3.6.1.4.1.2011.5.1.1.4.1.3
		-- 1.3.6.1.4.1.2011.5.1.1.4.1.3
		hwAclBasicAct OBJECT-TYPE
			SYNTAX INTEGER
				{
				permit(1),
				deny(2)
				}
			MAX-ACCESS read-create
			STATUS current
			DESCRIPTION
				"The Action of basic acl rule"
			::= { hwAclBasicRuleEntry 3 }
		
--   1.3.6.1.4.1.2011.5.1.1.4.1.4
-- 1.3.6.1.4.1.2011.5.1.1.4.1.4
		-- 1.3.6.1.4.1.2011.5.1.1.4.1.4
		hwAclBasicSrcIp OBJECT-TYPE
			SYNTAX IpAddress
			MAX-ACCESS read-create
			STATUS current
			DESCRIPTION
				"Source IP-address of basic acl rule"
			::= { hwAclBasicRuleEntry 4 }
		
--   1.3.6.1.4.1.2011.5.1.1.4.1.5
-- 1.3.6.1.4.1.2011.5.1.1.4.1.5
		-- 1.3.6.1.4.1.2011.5.1.1.4.1.5
		hwAclBasicSrcWild OBJECT-TYPE
			SYNTAX IpAddress
			MAX-ACCESS read-create
			STATUS current
			DESCRIPTION
				"Source IP-address wild of basic acl rule"
			::= { hwAclBasicRuleEntry 5 }
		
--   1.3.6.1.4.1.2011.5.1.1.4.1.6
-- 1.3.6.1.4.1.2011.5.1.1.4.1.6
		-- 1.3.6.1.4.1.2011.5.1.1.4.1.6
		hwAclBasicTimeRangeIndex OBJECT-TYPE
			SYNTAX Integer32 (0..256)
			MAX-ACCESS read-create
			STATUS current
			DESCRIPTION
				"The Time-range of basic acl rule"
			DEFVAL { 0 }
			::= { hwAclBasicRuleEntry 6 }
		
--   1.3.6.1.4.1.2011.5.1.1.4.1.7
-- 1.3.6.1.4.1.2011.5.1.1.4.1.7
		-- 1.3.6.1.4.1.2011.5.1.1.4.1.7
		hwAclBasicFragments OBJECT-TYPE
			SYNTAX TruthValue
			MAX-ACCESS read-create
			STATUS current
			DESCRIPTION
				"The flag of matching fragmented packet"
			::= { hwAclBasicRuleEntry 7 }
		
--   1.3.6.1.4.1.2011.5.1.1.4.1.8
-- 1.3.6.1.4.1.2011.5.1.1.4.1.8
		-- 1.3.6.1.4.1.2011.5.1.1.4.1.8
		hwAclBasicLog OBJECT-TYPE
			SYNTAX TruthValue
			MAX-ACCESS read-create
			STATUS current
			DESCRIPTION
				"The flag of log"
			::= { hwAclBasicRuleEntry 8 }
		
--   1.3.6.1.4.1.2011.5.1.1.4.1.9
-- 1.3.6.1.4.1.2011.5.1.1.4.1.9
		-- 1.3.6.1.4.1.2011.5.1.1.4.1.9
		hwAclBasicEnable OBJECT-TYPE
			SYNTAX TruthValue
			MAX-ACCESS read-only
			STATUS current
			DESCRIPTION
				"The flag of valid or invalid"
			::= { hwAclBasicRuleEntry 9 }
		
--   1.3.6.1.4.1.2011.5.1.1.4.1.10
-- 1.3.6.1.4.1.2011.5.1.1.4.1.10
		-- 1.3.6.1.4.1.2011.5.1.1.4.1.10
		hwAclBasicCount OBJECT-TYPE
			SYNTAX Counter32
			MAX-ACCESS read-only
			STATUS current
			DESCRIPTION
				"The count of matched by basic rule"
			::= { hwAclBasicRuleEntry 10 }
		
--   1.3.6.1.4.1.2011.5.1.1.4.1.11
-- 1.3.6.1.4.1.2011.5.1.1.4.1.11
		-- 1.3.6.1.4.1.2011.5.1.1.4.1.11
		hwAclBasicCountClear OBJECT-TYPE
			SYNTAX INTEGER
				{
				cleared(1),
				nouse(2)
				}
			MAX-ACCESS read-create
			STATUS current
			DESCRIPTION
				"Reset the value of count"
			::= { hwAclBasicRuleEntry 11 }
		
--   1.3.6.1.4.1.2011.5.1.1.4.1.12
-- 1.3.6.1.4.1.2011.5.1.1.4.1.12
		-- 1.3.6.1.4.1.2011.5.1.1.4.1.12
		hwAclBasicRowStatus OBJECT-TYPE
			SYNTAX RowStatus
			MAX-ACCESS read-create
			STATUS current
			DESCRIPTION
				"RowStatus，Now support three state:CreateAndGo,Active,Destroy."
			::= { hwAclBasicRuleEntry 12 }
		
--   1.3.6.1.4.1.2011.5.1.1.5
-- 1.3.6.1.4.1.2011.5.1.1.5
		-- 1.3.6.1.4.1.2011.5.1.1.5
		hwAclAdvancedRuleTable OBJECT-TYPE
			SYNTAX SEQUENCE OF HwAclAdvancedRuleEntry
			MAX-ACCESS not-accessible
			STATUS current
			DESCRIPTION
				"Configure the rule for advanced acl group"
			::= { hwAclMibObjects 5 }
		
--   1.3.6.1.4.1.2011.5.1.1.5.1
-- 1.3.6.1.4.1.2011.5.1.1.5.1
		-- 1.3.6.1.4.1.2011.5.1.1.5.1
		hwAclAdvancedRuleEntry OBJECT-TYPE
			SYNTAX HwAclAdvancedRuleEntry
			MAX-ACCESS not-accessible
			STATUS current
			DESCRIPTION
				"Define the index of hwAclAdvancedRuleTable"
			INDEX { hwAclAdvancedAclNum, hwAclAdvancedSubitem }
			::= { hwAclAdvancedRuleTable 1 }
		
		HwAclAdvancedRuleEntry ::=
			SEQUENCE { 
				hwAclAdvancedAclNum
					Integer32,
				hwAclAdvancedSubitem
					Integer32,
				hwAclAdvancedAct
					INTEGER,
				hwAclAdvancedProtocol
					Integer32,
				hwAclAdvancedSrcIp
					IpAddress,
				hwAclAdvancedSrcWild
					IpAddress,
				hwAclAdvancedSrcOp
					INTEGER,
				hwAclAdvancedSrcPort1
					Integer32,
				hwAclAdvancedSrcPort2
					Integer32,
				hwAclAdvancedDestIp
					IpAddress,
				hwAclAdvancedDestWild
					IpAddress,
				hwAclAdvancedDestOp
					INTEGER,
				hwAclAdvancedDestPort1
					Integer32,
				hwAclAdvancedDestPort2
					Integer32,
				hwAclAdvancedPrecedence
					INTEGER,
				hwAclAdvancedTos
					Integer32,
				hwAclAdvancedDscp
					Integer32,
				hwAclAdvancedEstablish
					TruthValue,
				hwAclAdvancedTimeRangeIndex
					Integer32,
				hwAclAdvancedIcmpType
					Integer32,
				hwAclAdvancedIcmpCode
					Integer32,
				hwAclAdvancedFragments
					TruthValue,
				hwAclAdvancedLog
					TruthValue,
				hwAclAdvancedEnable
					TruthValue,
				hwAclAdvancedCount
					Counter32,
				hwAclAdvancedCountClear
					INTEGER,
				hwAclAdvancedRowStatus
					RowStatus
			 }

--   1.3.6.1.4.1.2011.5.1.1.5.1.1
-- 1.3.6.1.4.1.2011.5.1.1.5.1.1
		-- 1.3.6.1.4.1.2011.5.1.1.5.1.1
		hwAclAdvancedAclNum OBJECT-TYPE
			SYNTAX Integer32 (3000..3999)
			MAX-ACCESS not-accessible
			STATUS current
			DESCRIPTION
				"The index of advanced acl group"
			::= { hwAclAdvancedRuleEntry 1 }
		
--   1.3.6.1.4.1.2011.5.1.1.5.1.2
-- 1.3.6.1.4.1.2011.5.1.1.5.1.2
		-- 1.3.6.1.4.1.2011.5.1.1.5.1.2
		hwAclAdvancedSubitem OBJECT-TYPE
			SYNTAX Integer32 (0..4294967295)
			MAX-ACCESS not-accessible
			STATUS current
			DESCRIPTION
				"The sub-index of advanced acl group"
			::= { hwAclAdvancedRuleEntry 2 }
		
--   1.3.6.1.4.1.2011.5.1.1.5.1.3
-- 1.3.6.1.4.1.2011.5.1.1.5.1.3
		-- 1.3.6.1.4.1.2011.5.1.1.5.1.3
		hwAclAdvancedAct OBJECT-TYPE
			SYNTAX INTEGER
				{
				permit(1),
				deny(2)
				}
			MAX-ACCESS read-create
			STATUS current
			DESCRIPTION
				"The action of advanced acl group"
			::= { hwAclAdvancedRuleEntry 3 }
		
--   1.3.6.1.4.1.2011.5.1.1.5.1.4
-- 1.3.6.1.4.1.2011.5.1.1.5.1.4
		-- 1.3.6.1.4.1.2011.5.1.1.5.1.4
		hwAclAdvancedProtocol OBJECT-TYPE
			SYNTAX Integer32 (0..255|256)
			MAX-ACCESS read-create
			STATUS current
			DESCRIPTION
				"The protocol-type of advanced acl group
				GRE tunneling(47)
				Internet Control Message Protocol(1)
				Any IP protocol(0)
				IP in IP tunneling(4)
				Transmission Control Protocol (6)
				User Datagram Protocol (17)   
				协议类型不方便定义为枚举类型，这里没有列出的也可以
				下发。"
			DEFVAL { 0 }
			::= { hwAclAdvancedRuleEntry 4 }
		
--   1.3.6.1.4.1.2011.5.1.1.5.1.5
-- 1.3.6.1.4.1.2011.5.1.1.5.1.5
		-- 1.3.6.1.4.1.2011.5.1.1.5.1.5
		hwAclAdvancedSrcIp OBJECT-TYPE
			SYNTAX IpAddress
			MAX-ACCESS read-create
			STATUS current
			DESCRIPTION
				"Source IP-address of advanced acl group"
			::= { hwAclAdvancedRuleEntry 5 }
		
--   1.3.6.1.4.1.2011.5.1.1.5.1.6
-- 1.3.6.1.4.1.2011.5.1.1.5.1.6
		-- 1.3.6.1.4.1.2011.5.1.1.5.1.6
		hwAclAdvancedSrcWild OBJECT-TYPE
			SYNTAX IpAddress
			MAX-ACCESS read-create
			STATUS current
			DESCRIPTION
				"Source IP-address wild of advanced acl group"
			::= { hwAclAdvancedRuleEntry 6 }
		
--   1.3.6.1.4.1.2011.5.1.1.5.1.7
-- 1.3.6.1.4.1.2011.5.1.1.5.1.7
		-- 1.3.6.1.4.1.2011.5.1.1.5.1.7
		hwAclAdvancedSrcOp OBJECT-TYPE
			SYNTAX INTEGER
				{
				lt(1),
				eq(2),
				gt(3),
				neq(4),
				invalid(0),
				range(5)
				}
			MAX-ACCESS read-create
			STATUS current
			DESCRIPTION
				"Source Port operation symbol of advanced acl group"
			::= { hwAclAdvancedRuleEntry 7 }
		
--   1.3.6.1.4.1.2011.5.1.1.5.1.8
-- 1.3.6.1.4.1.2011.5.1.1.5.1.8
		-- 1.3.6.1.4.1.2011.5.1.1.5.1.8
		hwAclAdvancedSrcPort1 OBJECT-TYPE
			SYNTAX Integer32 (0..65535|65536)
			MAX-ACCESS read-create
			STATUS current
			DESCRIPTION
				"The fourth layer sourec port1"
			::= { hwAclAdvancedRuleEntry 8 }
		
--   1.3.6.1.4.1.2011.5.1.1.5.1.9
-- 1.3.6.1.4.1.2011.5.1.1.5.1.9
		-- 1.3.6.1.4.1.2011.5.1.1.5.1.9
		hwAclAdvancedSrcPort2 OBJECT-TYPE
			SYNTAX Integer32 (0..65535|65536)
			MAX-ACCESS read-create
			STATUS current
			DESCRIPTION
				"The fourth layer source port2"
			::= { hwAclAdvancedRuleEntry 9 }
		
--   1.3.6.1.4.1.2011.5.1.1.5.1.10
-- 1.3.6.1.4.1.2011.5.1.1.5.1.10
		-- 1.3.6.1.4.1.2011.5.1.1.5.1.10
		hwAclAdvancedDestIp OBJECT-TYPE
			SYNTAX IpAddress
			MAX-ACCESS read-create
			STATUS current
			DESCRIPTION
				"Destination IP-address of advanced acl group"
			::= { hwAclAdvancedRuleEntry 10 }
		
--   1.3.6.1.4.1.2011.5.1.1.5.1.11
-- 1.3.6.1.4.1.2011.5.1.1.5.1.11
		-- 1.3.6.1.4.1.2011.5.1.1.5.1.11
		hwAclAdvancedDestWild OBJECT-TYPE
			SYNTAX IpAddress
			MAX-ACCESS read-create
			STATUS current
			DESCRIPTION
				"Destination IP-address wild of advanced acl group"
			::= { hwAclAdvancedRuleEntry 11 }
		
--   1.3.6.1.4.1.2011.5.1.1.5.1.12
-- 1.3.6.1.4.1.2011.5.1.1.5.1.12
		-- 1.3.6.1.4.1.2011.5.1.1.5.1.12
		hwAclAdvancedDestOp OBJECT-TYPE
			SYNTAX INTEGER
				{
				lt(1),
				eq(2),
				gt(3),
				neq(4),
				invalid(0),
				range(5)
				}
			MAX-ACCESS read-create
			STATUS current
			DESCRIPTION
				"Destination Port operation symbol of advanced acl group"
			::= { hwAclAdvancedRuleEntry 12 }
		
--   1.3.6.1.4.1.2011.5.1.1.5.1.13
-- 1.3.6.1.4.1.2011.5.1.1.5.1.13
		-- 1.3.6.1.4.1.2011.5.1.1.5.1.13
		hwAclAdvancedDestPort1 OBJECT-TYPE
			SYNTAX Integer32 (0..65535|65536)
			MAX-ACCESS read-create
			STATUS current
			DESCRIPTION
				"The fourth layer destination port1"
			::= { hwAclAdvancedRuleEntry 13 }
		
--   1.3.6.1.4.1.2011.5.1.1.5.1.14
-- 1.3.6.1.4.1.2011.5.1.1.5.1.14
		-- 1.3.6.1.4.1.2011.5.1.1.5.1.14
		hwAclAdvancedDestPort2 OBJECT-TYPE
			SYNTAX Integer32 (0..65535|65536)
			MAX-ACCESS read-create
			STATUS current
			DESCRIPTION
				"The fourth layer destination port2"
			::= { hwAclAdvancedRuleEntry 14 }
		
--   1.3.6.1.4.1.2011.5.1.1.5.1.15
-- 1.3.6.1.4.1.2011.5.1.1.5.1.15
		-- 1.3.6.1.4.1.2011.5.1.1.5.1.15
		hwAclAdvancedPrecedence OBJECT-TYPE
			SYNTAX INTEGER
				{
				routine(0),
				priority(1),
				immediate(2),
				flash(3),
				flash-override(4),
				critical(5),
				internet(6),
				network(7),
				invalid(255)
				}
			MAX-ACCESS read-create
			STATUS current
			DESCRIPTION
				"The value of IP-packet's precedence
				critical              Specify critical precedence(5)
				flash                 Specify flash precedence(3)
				flash-override        Specify flash-override precedence(4)
				immediate             Specify immediate precedence(2)
				internet              Specify internetwork control precedence(6)
				network               Specify network control precedence(7)
				priority              Specify priority precedence(1)
				routine               Specify routine precedence(0) "
			::= { hwAclAdvancedRuleEntry 15 }
		
--   1.3.6.1.4.1.2011.5.1.1.5.1.16
-- 1.3.6.1.4.1.2011.5.1.1.5.1.16
		-- 1.3.6.1.4.1.2011.5.1.1.5.1.16
		hwAclAdvancedTos OBJECT-TYPE
			SYNTAX Integer32 (0..15 | 255)
			MAX-ACCESS read-create
			STATUS current
			DESCRIPTION
				"The value of IP-packet's TOS
				max-reliability       Match packets with max reliable TOS(2)
				max-throughput        Match packets with max throughput TOS(4)
				min-delay             Match packets with min delay TOS(8)
				min-monetary-cost     Match packets with min monetary cost TOS(1)
				normal                Match packets with normal TOS(0)
				不方便定义为枚举类型，这里没有列出的也可以下发。"
			::= { hwAclAdvancedRuleEntry 16 }
		
--   1.3.6.1.4.1.2011.5.1.1.5.1.17
-- 1.3.6.1.4.1.2011.5.1.1.5.1.17
		-- 1.3.6.1.4.1.2011.5.1.1.5.1.17
		hwAclAdvancedDscp OBJECT-TYPE
			SYNTAX Integer32 (0..63 | 255)
			MAX-ACCESS read-create
			STATUS current
			DESCRIPTION
				"The value of frame
				af1                   Specify Assured Forwarding 1 service(10)
				af2                   Specify Assured Forwarding 2 service(18)
				af3                   Specify Assured Forwarding 3 service(26)
				af4                   Specify Assured Forwarding 4 service(34)
				be                    Specify Best Effort service(0)
				cs1                   Specify Class Seletor 1 service(8)
				cs2                   Specify Class Seletor 2 service(16)
				cs3                   Specify Class Seletor 3 service(24)
				cs4                   Specify Class Seletor 4 service(32)
				cs5                   Specify Class Seletor 5 service(40)
				cs6                   Specify Class Seletor 6 service(48)
				cs7                   Specify Class Seletor 7 service(56)
				ef                    Specify Expedited Forwarding service(46)  "
			::= { hwAclAdvancedRuleEntry 17 }
		
--   1.3.6.1.4.1.2011.5.1.1.5.1.18
-- 1.3.6.1.4.1.2011.5.1.1.5.1.18
		-- 1.3.6.1.4.1.2011.5.1.1.5.1.18
		hwAclAdvancedEstablish OBJECT-TYPE
			SYNTAX TruthValue
			MAX-ACCESS read-create
			STATUS current
			DESCRIPTION
				"Establish flag"
			DEFVAL { False }
			::= { hwAclAdvancedRuleEntry 18 }
		
--   1.3.6.1.4.1.2011.5.1.1.5.1.19
-- 1.3.6.1.4.1.2011.5.1.1.5.1.19
		-- 1.3.6.1.4.1.2011.5.1.1.5.1.19
		hwAclAdvancedTimeRangeIndex OBJECT-TYPE
			SYNTAX Integer32 (0..256)
			MAX-ACCESS read-create
			STATUS current
			DESCRIPTION
				"The Time-range of advanced acl rule
				(0) invalid"
			::= { hwAclAdvancedRuleEntry 19 }
		
--   1.3.6.1.4.1.2011.5.1.1.5.1.20
-- 1.3.6.1.4.1.2011.5.1.1.5.1.20
		-- 1.3.6.1.4.1.2011.5.1.1.5.1.20
		hwAclAdvancedIcmpType OBJECT-TYPE
			SYNTAX Integer32 (0..255|256)
			MAX-ACCESS read-create
			STATUS current
			DESCRIPTION
				"The type of ICMP packet
				(255) invalid"
			::= { hwAclAdvancedRuleEntry 20 }
		
--   1.3.6.1.4.1.2011.5.1.1.5.1.21
-- 1.3.6.1.4.1.2011.5.1.1.5.1.21
		-- 1.3.6.1.4.1.2011.5.1.1.5.1.21
		hwAclAdvancedIcmpCode OBJECT-TYPE
			SYNTAX Integer32 (0..255|256)
			MAX-ACCESS read-create
			STATUS current
			DESCRIPTION
				"The code of ICMP packet
				(255) invalid"
			::= { hwAclAdvancedRuleEntry 21 }
		
--   1.3.6.1.4.1.2011.5.1.1.5.1.22
-- 1.3.6.1.4.1.2011.5.1.1.5.1.22
		-- 1.3.6.1.4.1.2011.5.1.1.5.1.22
		hwAclAdvancedFragments OBJECT-TYPE
			SYNTAX TruthValue
			MAX-ACCESS read-create
			STATUS current
			DESCRIPTION
				"The flag of matching fragmented packet"
			::= { hwAclAdvancedRuleEntry 22 }
		
--   1.3.6.1.4.1.2011.5.1.1.5.1.23
-- 1.3.6.1.4.1.2011.5.1.1.5.1.23
		-- 1.3.6.1.4.1.2011.5.1.1.5.1.23
		hwAclAdvancedLog OBJECT-TYPE
			SYNTAX TruthValue
			MAX-ACCESS read-create
			STATUS current
			DESCRIPTION
				"The flag of log"
			::= { hwAclAdvancedRuleEntry 23 }
		
--   1.3.6.1.4.1.2011.5.1.1.5.1.24
-- 1.3.6.1.4.1.2011.5.1.1.5.1.24
		-- 1.3.6.1.4.1.2011.5.1.1.5.1.24
		hwAclAdvancedEnable OBJECT-TYPE
			SYNTAX TruthValue
			MAX-ACCESS read-only
			STATUS current
			DESCRIPTION
				"The flag of valid or invalid"
			::= { hwAclAdvancedRuleEntry 24 }
		
--   1.3.6.1.4.1.2011.5.1.1.5.1.25
-- 1.3.6.1.4.1.2011.5.1.1.5.1.25
		-- 1.3.6.1.4.1.2011.5.1.1.5.1.25
		hwAclAdvancedCount OBJECT-TYPE
			SYNTAX Counter32
			MAX-ACCESS read-only
			STATUS current
			DESCRIPTION
				"The count of matched by advanced rule"
			::= { hwAclAdvancedRuleEntry 25 }
		
--   1.3.6.1.4.1.2011.5.1.1.5.1.26
-- 1.3.6.1.4.1.2011.5.1.1.5.1.26
		-- 1.3.6.1.4.1.2011.5.1.1.5.1.26
		hwAclAdvancedCountClear OBJECT-TYPE
			SYNTAX INTEGER
				{
				cleared(1),
				nouse(2)
				}
			MAX-ACCESS read-create
			STATUS current
			DESCRIPTION
				"Reset the value of count"
			::= { hwAclAdvancedRuleEntry 26 }
		
--   1.3.6.1.4.1.2011.5.1.1.5.1.27
-- 1.3.6.1.4.1.2011.5.1.1.5.1.27
		-- 1.3.6.1.4.1.2011.5.1.1.5.1.27
		hwAclAdvancedRowStatus OBJECT-TYPE
			SYNTAX RowStatus
			MAX-ACCESS read-create
			STATUS current
			DESCRIPTION
				"RowStatus，Now support three state:CreateAndGo,Active,Destroy."
			::= { hwAclAdvancedRuleEntry 27 }
		
--   1.3.6.1.4.1.2011.5.1.1.7
-- 1.3.6.1.4.1.2011.5.1.1.7
		-- 1.3.6.1.4.1.2011.5.1.1.7
		hwAclLinkTable OBJECT-TYPE
			SYNTAX SEQUENCE OF HwAclLinkEntry
			MAX-ACCESS not-accessible
			STATUS current
			DESCRIPTION
				"Create link acl"
			::= { hwAclMibObjects 7 }
		
--   1.3.6.1.4.1.2011.5.1.1.7.1
-- 1.3.6.1.4.1.2011.5.1.1.7.1
		-- 1.3.6.1.4.1.2011.5.1.1.7.1
		hwAclLinkEntry OBJECT-TYPE
			SYNTAX HwAclLinkEntry
			MAX-ACCESS not-accessible
			STATUS current
			DESCRIPTION
				"The entry of the link acl table."
			INDEX { hwAclLinkAclNum, hwAclLinkSubitem }
			::= { hwAclLinkTable 1 }
		
		HwAclLinkEntry ::=
			SEQUENCE { 
				hwAclLinkAclNum
					Integer32,
				hwAclLinkSubitem
					Integer32,
				hwAclLinkAct
					INTEGER,
				hwAclLinkProtocol
					Integer32,
				hwAclLinkFormatType
					INTEGER,
				hwAclLinkVlanTag
					INTEGER,
				hwAclLinkVlanPri
					INTEGER,
				hwAclLinkSrcVlanId
					Integer32,
				hwAclLinkSrcMac
					MacAddress,
				hwAclLinkSrcMacWild
					MacAddress,
				hwAclLinkSrcIfIndex
					Integer32,
				hwAclLinkSrcAny
					TruthValue,
				hwAclLinkDestVlanId
					Integer32,
				hwAclLinkDestMac
					MacAddress,
				hwAclLinkDestMacWild
					MacAddress,
				hwAclLinkDestIfIndex
					Integer32,
				hwAclLinkDestAny
					TruthValue,
				hwAclLinkTimeRangeIndex
					Integer32,
				hwAclLinkEnable
					TruthValue,
				hwAclLinkRowStatus
					RowStatus
			 }

--   1.3.6.1.4.1.2011.5.1.1.7.1.1
-- 1.3.6.1.4.1.2011.5.1.1.7.1.1
		-- 1.3.6.1.4.1.2011.5.1.1.7.1.1
		hwAclLinkAclNum OBJECT-TYPE
			SYNTAX Integer32 (4000..4999)
			MAX-ACCESS not-accessible
			STATUS current
			DESCRIPTION
				"The num of the link acl"
			::= { hwAclLinkEntry 1 }
		
--   1.3.6.1.4.1.2011.5.1.1.7.1.2
-- 1.3.6.1.4.1.2011.5.1.1.7.1.2
		-- 1.3.6.1.4.1.2011.5.1.1.7.1.2
		hwAclLinkSubitem OBJECT-TYPE
			SYNTAX Integer32 (0..4294967295)
			MAX-ACCESS not-accessible
			STATUS current
			DESCRIPTION
				"The subitem of the link acl"
			::= { hwAclLinkEntry 2 }
		
--   1.3.6.1.4.1.2011.5.1.1.7.1.3
-- 1.3.6.1.4.1.2011.5.1.1.7.1.3
		-- 1.3.6.1.4.1.2011.5.1.1.7.1.3
		hwAclLinkAct OBJECT-TYPE
			SYNTAX INTEGER
				{
				permit(1),
				deny(2)
				}
			MAX-ACCESS read-create
			STATUS current
			DESCRIPTION
				"The action of the link acl"
			::= { hwAclLinkEntry 3 }
		
--   1.3.6.1.4.1.2011.5.1.1.7.1.4
-- 1.3.6.1.4.1.2011.5.1.1.7.1.4
		-- 1.3.6.1.4.1.2011.5.1.1.7.1.4
		hwAclLinkProtocol OBJECT-TYPE
		SYNTAX Integer32 (1..65535|65536)
			MAX-ACCESS read-create
			STATUS current
			DESCRIPTION
				"L2 protocol"  
			DEFVAL { 65536 }
			::= { hwAclLinkEntry 4 } 
					
--   1.3.6.1.4.1.2011.5.1.1.7.1.5
-- 1.3.6.1.4.1.2011.5.1.1.7.1.5
		-- 1.3.6.1.4.1.2011.5.1.1.7.1.5
		hwAclLinkFormatType OBJECT-TYPE
			SYNTAX INTEGER
				{
				invalid(0),
				ethernetII(1),
				snap(2),
				ieee802Dot3And2(3),
				ieee802Dot4(4)
				}
			MAX-ACCESS read-only
			STATUS current
			DESCRIPTION
				"Format type"
			::= { hwAclLinkEntry 5 }
		
--   1.3.6.1.4.1.2011.5.1.1.7.1.6
-- 1.3.6.1.4.1.2011.5.1.1.7.1.6
		-- 1.3.6.1.4.1.2011.5.1.1.7.1.6
		hwAclLinkVlanTag OBJECT-TYPE
			SYNTAX INTEGER
				{
				tagged(1),
				untagged(2),
				invalid(0)
				}
			MAX-ACCESS read-only
			STATUS current
			DESCRIPTION
				"Have vlan tag or not"
			::= { hwAclLinkEntry 6 }
		
--   1.3.6.1.4.1.2011.5.1.1.7.1.7
-- 1.3.6.1.4.1.2011.5.1.1.7.1.7
		-- 1.3.6.1.4.1.2011.5.1.1.7.1.7
		hwAclLinkVlanPri OBJECT-TYPE
			SYNTAX INTEGER
				{
				best-effort(0),
				background(1),
				spare(2),
				excellent-effort(3),
				controlled-load(4),
				video(5),
				voice(6),
				network-management(7),
				invalid(255)
				}
			MAX-ACCESS read-create
			STATUS current
			DESCRIPTION
				"Vlan priority
				background            Specify background priority(1)
				best-effort           Specify best-effort priority(0)
				controlled-load       Specify controlled-load priority(4)
				excellent-effort      Specify excellent-effort priority(3)
				network-management    Specify network-management priority(7)
				spare                 Specify spare priority(2)
				video                 Specify video priority(5)
				voice                 Specify voice priority(6)   "
			::= { hwAclLinkEntry 7 }
		
--   1.3.6.1.4.1.2011.5.1.1.7.1.8
-- 1.3.6.1.4.1.2011.5.1.1.7.1.8
		-- 1.3.6.1.4.1.2011.5.1.1.7.1.8
		hwAclLinkSrcVlanId OBJECT-TYPE
			SYNTAX Integer32 (0..4093)
			MAX-ACCESS read-create
			STATUS current
			DESCRIPTION
				"Source vlan ID
				(0) invalid"
			::= { hwAclLinkEntry 8 }
		
--   1.3.6.1.4.1.2011.5.1.1.7.1.9
-- 1.3.6.1.4.1.2011.5.1.1.7.1.9
		-- 1.3.6.1.4.1.2011.5.1.1.7.1.9
		hwAclLinkSrcMac OBJECT-TYPE
			SYNTAX MacAddress
			MAX-ACCESS read-create
			STATUS current
			DESCRIPTION
				"Source mac"
			::= { hwAclLinkEntry 9 }
		
--   1.3.6.1.4.1.2011.5.1.1.7.1.10
-- 1.3.6.1.4.1.2011.5.1.1.7.1.10
		-- 1.3.6.1.4.1.2011.5.1.1.7.1.10
		hwAclLinkSrcMacWild OBJECT-TYPE
			SYNTAX MacAddress
			MAX-ACCESS read-create
			STATUS current
			DESCRIPTION
				"Source mac wild"
			::= { hwAclLinkEntry 10 }
		
--   1.3.6.1.4.1.2011.5.1.1.7.1.11
-- 1.3.6.1.4.1.2011.5.1.1.7.1.11
		-- 1.3.6.1.4.1.2011.5.1.1.7.1.11
		hwAclLinkSrcIfIndex OBJECT-TYPE
			SYNTAX Integer32 (0..2147483647)
			MAX-ACCESS read-only
			STATUS current
			DESCRIPTION
				"Source IfIndex
				(0) invalid"
			::= { hwAclLinkEntry 11 }
		
--   1.3.6.1.4.1.2011.5.1.1.7.1.12
-- 1.3.6.1.4.1.2011.5.1.1.7.1.12
		-- 1.3.6.1.4.1.2011.5.1.1.7.1.12
		hwAclLinkSrcAny OBJECT-TYPE
			SYNTAX TruthValue
			MAX-ACCESS read-create
			STATUS current
			DESCRIPTION
				"Source any"
			::= { hwAclLinkEntry 12 }
		
--   1.3.6.1.4.1.2011.5.1.1.7.1.13
-- 1.3.6.1.4.1.2011.5.1.1.7.1.13
		-- 1.3.6.1.4.1.2011.5.1.1.7.1.13
		hwAclLinkDestVlanId OBJECT-TYPE
			SYNTAX Integer32 (0..4093)
			MAX-ACCESS read-only
			STATUS current
			DESCRIPTION
				"Destination vlan ID
				(0) invalid"
			::= { hwAclLinkEntry 13 }
		
--   1.3.6.1.4.1.2011.5.1.1.7.1.14
-- 1.3.6.1.4.1.2011.5.1.1.7.1.14
		-- 1.3.6.1.4.1.2011.5.1.1.7.1.14
		hwAclLinkDestMac OBJECT-TYPE
			SYNTAX MacAddress
			MAX-ACCESS read-create
			STATUS current
			DESCRIPTION
				"Destination mac"
			::= { hwAclLinkEntry 14 }
		
--   1.3.6.1.4.1.2011.5.1.1.7.1.15
-- 1.3.6.1.4.1.2011.5.1.1.7.1.15
		-- 1.3.6.1.4.1.2011.5.1.1.7.1.15
		hwAclLinkDestMacWild OBJECT-TYPE
			SYNTAX MacAddress
			MAX-ACCESS read-create
			STATUS current
			DESCRIPTION
				"Destination mac wild"
			::= { hwAclLinkEntry 15 }
		
--   1.3.6.1.4.1.2011.5.1.1.7.1.16
-- 1.3.6.1.4.1.2011.5.1.1.7.1.16
		-- 1.3.6.1.4.1.2011.5.1.1.7.1.16
		hwAclLinkDestIfIndex OBJECT-TYPE
			SYNTAX Integer32 (0..2147483647)
			MAX-ACCESS read-only
			STATUS current
			DESCRIPTION
				"Destination IfIndex"
			::= { hwAclLinkEntry 16 }
		
--   1.3.6.1.4.1.2011.5.1.1.7.1.17
-- 1.3.6.1.4.1.2011.5.1.1.7.1.17
		-- 1.3.6.1.4.1.2011.5.1.1.7.1.17
		hwAclLinkDestAny OBJECT-TYPE
			SYNTAX TruthValue
			MAX-ACCESS read-create
			STATUS current
			DESCRIPTION
				"Destination any"
			::= { hwAclLinkEntry 17 }
		
--   1.3.6.1.4.1.2011.5.1.1.7.1.18
-- 1.3.6.1.4.1.2011.5.1.1.7.1.18
		-- 1.3.6.1.4.1.2011.5.1.1.7.1.18
		hwAclLinkTimeRangeIndex OBJECT-TYPE
			SYNTAX Integer32 (0..256)
			MAX-ACCESS read-create
			STATUS current
			DESCRIPTION
				"The name index of the timerange"
			::= { hwAclLinkEntry 18 }
		
--   1.3.6.1.4.1.2011.5.1.1.7.1.19
-- 1.3.6.1.4.1.2011.5.1.1.7.1.19
		-- 1.3.6.1.4.1.2011.5.1.1.7.1.19
		hwAclLinkEnable OBJECT-TYPE
			SYNTAX TruthValue
			MAX-ACCESS read-only
			STATUS current
			DESCRIPTION
				"Is enable or not"
			::= { hwAclLinkEntry 19 }
		
--   1.3.6.1.4.1.2011.5.1.1.7.1.20
-- 1.3.6.1.4.1.2011.5.1.1.7.1.20
		-- 1.3.6.1.4.1.2011.5.1.1.7.1.20
		hwAclLinkRowStatus OBJECT-TYPE
			SYNTAX RowStatus
			MAX-ACCESS read-create
			STATUS current
			DESCRIPTION
				"RowStatus，Now support three state:CreateAndGo,Active,Destroy."
			::= { hwAclLinkEntry 20 }
		
--   1.3.6.1.4.1.2011.5.1.1.8
-- 1.3.6.1.4.1.2011.5.1.1.8
		-- 1.3.6.1.4.1.2011.5.1.1.8
		hwAclUserTable OBJECT-TYPE
			SYNTAX SEQUENCE OF HwAclUserEntry
			MAX-ACCESS not-accessible
			STATUS current
			DESCRIPTION
				"Create user acl"
			::= { hwAclMibObjects 8 }
		
--   1.3.6.1.4.1.2011.5.1.1.8.1
-- 1.3.6.1.4.1.2011.5.1.1.8.1
		-- 1.3.6.1.4.1.2011.5.1.1.8.1
		hwAclUserEntry OBJECT-TYPE
			SYNTAX HwAclUserEntry
			MAX-ACCESS not-accessible
			STATUS current
			DESCRIPTION
				"The entry of user acl table."
			INDEX { hwAclUserAclNum, hwAclUserSubitem }
			::= { hwAclUserTable 1 }
		
		HwAclUserEntry ::=
			SEQUENCE { 
				hwAclUserAclNum
					Integer32,
				hwAclUserSubitem
					Integer32,
				hwAclUserAct
					INTEGER,
				hwAclUserFormatType
					INTEGER,
				hwAclUserVlanTag
					INTEGER,
				hwAclUserRuleStr
					OCTET STRING,
				hwAclUserRuleMask
					OCTET STRING,
				hwAclUserRowOffset
					Integer32,
				hwAclUserTimeRangeIndex
					Integer32,
				hwAclUserEnable
					TruthValue,
				hwAclUserRowStatus
					RowStatus
			 }

--   1.3.6.1.4.1.2011.5.1.1.8.1.1
-- 1.3.6.1.4.1.2011.5.1.1.8.1.1
		-- 1.3.6.1.4.1.2011.5.1.1.8.1.1
		hwAclUserAclNum OBJECT-TYPE
			SYNTAX Integer32 (5000..5999)
			MAX-ACCESS not-accessible
			STATUS current
			DESCRIPTION
				"The num of the user acl"
			::= { hwAclUserEntry 1 }
		
--   1.3.6.1.4.1.2011.5.1.1.8.1.2
-- 1.3.6.1.4.1.2011.5.1.1.8.1.2
		-- 1.3.6.1.4.1.2011.5.1.1.8.1.2
		hwAclUserSubitem OBJECT-TYPE
			SYNTAX Integer32 (0..4294967295)
			MAX-ACCESS not-accessible
			STATUS current
			DESCRIPTION
				"The subitem of the user acl"
			::= { hwAclUserEntry 2 }
		
--   1.3.6.1.4.1.2011.5.1.1.8.1.3
-- 1.3.6.1.4.1.2011.5.1.1.8.1.3
		-- 1.3.6.1.4.1.2011.5.1.1.8.1.3
		hwAclUserAct OBJECT-TYPE
			SYNTAX INTEGER
				{
				permit(1),
				deny(2)
				}
			MAX-ACCESS read-create
			STATUS current
			DESCRIPTION
				"The action of the user acl"
			::= { hwAclUserEntry 3 }
		
--   1.3.6.1.4.1.2011.5.1.1.8.1.4
-- 1.3.6.1.4.1.2011.5.1.1.8.1.4
		-- 1.3.6.1.4.1.2011.5.1.1.8.1.4
		hwAclUserFormatType OBJECT-TYPE
			SYNTAX INTEGER
				{
				invalid(0),
				ethernetII(1),
				snap(2),
				ieee802Dot2And3(3),
				ieee802Dot4(4)
				}
			MAX-ACCESS read-only
			STATUS current
			DESCRIPTION
				"Format type"
			DEFVAL { invalid }
			::= { hwAclUserEntry 4 }
		
--   1.3.6.1.4.1.2011.5.1.1.8.1.5
-- 1.3.6.1.4.1.2011.5.1.1.8.1.5
		-- 1.3.6.1.4.1.2011.5.1.1.8.1.5
		hwAclUserVlanTag OBJECT-TYPE
			SYNTAX INTEGER
				{
				tagged(1),
				untagged(2),
				invalid(0)
				}
			MAX-ACCESS read-only
			STATUS current
			DESCRIPTION
				"Have vlan tag or not"
			DEFVAL { invalid }
			::= { hwAclUserEntry 5 }
		
--   1.3.6.1.4.1.2011.5.1.1.8.1.6
-- 1.3.6.1.4.1.2011.5.1.1.8.1.6
		-- 1.3.6.1.4.1.2011.5.1.1.8.1.6
		hwAclUserRuleStr OBJECT-TYPE
			SYNTAX OCTET STRING (SIZE (1..80))
			MAX-ACCESS read-create
			STATUS current
			DESCRIPTION
				"Rule string"
			::= { hwAclUserEntry 6 }
		
--   1.3.6.1.4.1.2011.5.1.1.8.1.7
-- 1.3.6.1.4.1.2011.5.1.1.8.1.7
		-- 1.3.6.1.4.1.2011.5.1.1.8.1.7
		hwAclUserRuleMask OBJECT-TYPE
			SYNTAX OCTET STRING (SIZE (1..80))
			MAX-ACCESS read-create
			STATUS current
			DESCRIPTION
				"Rule mask"
			::= { hwAclUserEntry 7 }
		
-- 1.3.6.1.4.1.2011.5.1.1.8.1.8
		-- 1.3.6.1.4.1.2011.5.1.1.8.1.8
		hwAclUserRowOffset OBJECT-TYPE
			SYNTAX Integer32 (0..79)
			MAX-ACCESS read-only
			STATUS current
			DESCRIPTION
				"Description."
			::= { hwAclUserEntry 8 }
		
--   1.3.6.1.4.1.2011.5.1.1.8.1.9
-- 1.3.6.1.4.1.2011.5.1.1.8.1.9
		-- 1.3.6.1.4.1.2011.5.1.1.8.1.9
		hwAclUserTimeRangeIndex OBJECT-TYPE
			SYNTAX Integer32 (0..256)
			MAX-ACCESS read-create
			STATUS current
			DESCRIPTION
				"The name index of the timerange"
			::= { hwAclUserEntry 9 }
		
--   1.3.6.1.4.1.2011.5.1.1.8.1.10
-- 1.3.6.1.4.1.2011.5.1.1.8.1.10
		-- 1.3.6.1.4.1.2011.5.1.1.8.1.10
		hwAclUserEnable OBJECT-TYPE
			SYNTAX TruthValue
			MAX-ACCESS read-only
			STATUS current
			DESCRIPTION
				"Is enable or not"
			::= { hwAclUserEntry 10 }
		
--   1.3.6.1.4.1.2011.5.1.1.8.1.11
-- 1.3.6.1.4.1.2011.5.1.1.8.1.11
		-- 1.3.6.1.4.1.2011.5.1.1.8.1.11
		hwAclUserRowStatus OBJECT-TYPE
			SYNTAX RowStatus
			MAX-ACCESS read-create
			STATUS current
			DESCRIPTION
				"RowStatus，Now support three state:CreateAndGo,Active,Destroy."
			::= { hwAclUserEntry 11 }
		
--   1.3.6.1.4.1.2011.5.1.1.9
-- 1.3.6.1.4.1.2011.5.1.1.9
		-- 1.3.6.1.4.1.2011.5.1.1.9
		hwAclActiveTable OBJECT-TYPE
			SYNTAX SEQUENCE OF HwAclActiveEntry
			MAX-ACCESS not-accessible
			STATUS current
			DESCRIPTION
				"Active acl"
			::= { hwAclMibObjects 9 }
		
--   1.3.6.1.4.1.2011.5.1.1.9.1
-- 1.3.6.1.4.1.2011.5.1.1.9.1
		-- 1.3.6.1.4.1.2011.5.1.1.9.1
		hwAclActiveEntry OBJECT-TYPE
			SYNTAX HwAclActiveEntry
			MAX-ACCESS not-accessible
			STATUS current
			DESCRIPTION
				"The entry of active acl table."
			INDEX { hwAclActiveAclIndex, hwAclActiveIfIndex, hwAclActiveDirection }
			::= { hwAclActiveTable 1 }
		
		HwAclActiveEntry ::=
			SEQUENCE { 
				hwAclActiveAclIndex
					Integer32,
				hwAclActiveIfIndex
					Integer32,
				hwAclActiveDirection
					INTEGER,
				hwAclActiveUserAclNum
					Integer32,
				hwAclActiveUserAclSubitem
					Integer32,
				hwAclActiveIpAclNum
					Integer32,
				hwAclActiveIpAclSubitem
					Integer32,
				hwAclActiveLinkAclNum
					Integer32,
				hwAclActiveLinkAclSubitem
					Integer32,
				hwAclActiveRuntime
					TruthValue,
				hwAclActiveRowStatus
					RowStatus
			 }

--   1.3.6.1.4.1.2011.5.1.1.9.1.1
-- 1.3.6.1.4.1.2011.5.1.1.9.1.1
		-- 1.3.6.1.4.1.2011.5.1.1.9.1.1
		hwAclActiveAclIndex OBJECT-TYPE
			SYNTAX Integer32 (0..2999)
			MAX-ACCESS not-accessible
			STATUS current
			DESCRIPTION
				"Acl index"
			::= { hwAclActiveEntry 1 }
		
--   1.3.6.1.4.1.2011.5.1.1.9.1.2
-- 1.3.6.1.4.1.2011.5.1.1.9.1.2
		-- 1.3.6.1.4.1.2011.5.1.1.9.1.2
		hwAclActiveIfIndex OBJECT-TYPE
			SYNTAX Integer32 (0..2147483647)
			MAX-ACCESS not-accessible
			STATUS current
			DESCRIPTION
				"IfIndex"
			::= { hwAclActiveEntry 2 }
		
--   1.3.6.1.4.1.2011.5.1.1.9.1.3
-- 1.3.6.1.4.1.2011.5.1.1.9.1.3
		-- 1.3.6.1.4.1.2011.5.1.1.9.1.3
		hwAclActiveDirection OBJECT-TYPE
			SYNTAX INTEGER
				{
				input(1),
				output(2),
				invalid(0)
				}
			MAX-ACCESS not-accessible
			STATUS current
			DESCRIPTION
				"Direction"
			::= { hwAclActiveEntry 3 }
		
--   1.3.6.1.4.1.2011.5.1.1.9.1.4
-- 1.3.6.1.4.1.2011.5.1.1.9.1.4
		-- 1.3.6.1.4.1.2011.5.1.1.9.1.4
		hwAclActiveUserAclNum OBJECT-TYPE
			SYNTAX Integer32 (0 | 5000..5999)
			MAX-ACCESS read-create
			STATUS current
			DESCRIPTION
				"The num of the user acl"
			::= { hwAclActiveEntry 4 }
		
--   1.3.6.1.4.1.2011.5.1.1.9.1.5
-- 1.3.6.1.4.1.2011.5.1.1.9.1.5
		-- 1.3.6.1.4.1.2011.5.1.1.9.1.5
		hwAclActiveUserAclSubitem OBJECT-TYPE
			SYNTAX Integer32 (0,4294967295)
			MAX-ACCESS read-create
			STATUS current
			DESCRIPTION
				"The subitem of the user acl"
			::= { hwAclActiveEntry 5 }
		
--   1.3.6.1.4.1.2011.5.1.1.9.1.6
-- 1.3.6.1.4.1.2011.5.1.1.9.1.6
		-- 1.3.6.1.4.1.2011.5.1.1.9.1.6
		hwAclActiveIpAclNum OBJECT-TYPE
			SYNTAX Integer32 (0 | 2000..3999)
			MAX-ACCESS read-create
			STATUS current
			DESCRIPTION
				"The num of the IP acl"
			::= { hwAclActiveEntry 6 }
		
--   1.3.6.1.4.1.2011.5.1.1.9.1.7
-- 1.3.6.1.4.1.2011.5.1.1.9.1.7
		-- 1.3.6.1.4.1.2011.5.1.1.9.1.7
		hwAclActiveIpAclSubitem OBJECT-TYPE
			SYNTAX Integer32 (0,4294967295)
			MAX-ACCESS read-create
			STATUS current
			DESCRIPTION
				"The subitem of the IP acl"
			::= { hwAclActiveEntry 7 }
		
--   1.3.6.1.4.1.2011.5.1.1.9.1.8
-- 1.3.6.1.4.1.2011.5.1.1.9.1.8
		-- 1.3.6.1.4.1.2011.5.1.1.9.1.8
		hwAclActiveLinkAclNum OBJECT-TYPE
			SYNTAX Integer32 (0 | 4000..4999)
			MAX-ACCESS read-create
			STATUS current
			DESCRIPTION
				"The num of the link acl"
			::= { hwAclActiveEntry 8 }
		
--   1.3.6.1.4.1.2011.5.1.1.9.1.9
-- 1.3.6.1.4.1.2011.5.1.1.9.1.9
		-- 1.3.6.1.4.1.2011.5.1.1.9.1.9
		hwAclActiveLinkAclSubitem OBJECT-TYPE
			SYNTAX Integer32 (0,4294967295)
			MAX-ACCESS read-create
			STATUS current
			DESCRIPTION
				"The subitem of the link acl"
			::= { hwAclActiveEntry 9 }
		
--   1.3.6.1.4.1.2011.5.1.1.9.1.10
-- 1.3.6.1.4.1.2011.5.1.1.9.1.10
		-- 1.3.6.1.4.1.2011.5.1.1.9.1.10
		hwAclActiveRuntime OBJECT-TYPE
			SYNTAX TruthValue
			MAX-ACCESS read-only
			STATUS current
			DESCRIPTION
				"Is run or not"
			::= { hwAclActiveEntry 10 }
		
--   1.3.6.1.4.1.2011.5.1.1.9.1.11
-- 1.3.6.1.4.1.2011.5.1.1.9.1.11
		-- 1.3.6.1.4.1.2011.5.1.1.9.1.11
		hwAclActiveRowStatus OBJECT-TYPE
			SYNTAX RowStatus
			MAX-ACCESS read-create
			STATUS current
			DESCRIPTION
				"RowStatus，Now support three state:CreateAndGo,Active,Destroy."
			::= { hwAclActiveEntry 11 }
		
	
	END

--
-- HUAWEI-ACL-MIB.my
--
