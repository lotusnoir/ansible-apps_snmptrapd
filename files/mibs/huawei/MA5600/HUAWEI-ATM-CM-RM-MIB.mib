--
-- HUAWEI-ATM-CM-RM-MIB.mib
-- MIB generated by MG-SOFT Visual MIB Builder Version 2.5 Build 225
-- Monday, Dec 10, 2003 at 08:03:05
--

   HUAWEI-ATM-CM-RM-MIB DEFINITIONS ::= BEGIN

   IMPORTS 		
     ifIndex			
	    FROM IF-MIB
     Unsigned32, Counter32, OBJECT-TYPE			
	    FROM SNMPv2-SMI
     hwFrameIndex, hwSlotIndex
            FROM HUAWEI-DEVICE-MIB 
     hwAtmCmRm
	    FROM HUAWEI-MIB;

--
-- Node definitions
--	
	
   hwAtmPortBandWidthTable OBJECT-TYPE
     SYNTAX      SEQUENCE OF HwAtmPortBandWidthEntry
     MAX-ACCESS  not-accessible
     STATUS      current
     DESCRIPTION
        "BandWidth Resource table"
     ::= { hwAtmCmRm 1 }
     
   hwAtmPortBandWidthEntry OBJECT-TYPE
     SYNTAX      HwAtmPortBandWidthEntry
     MAX-ACCESS  not-accessible
     STATUS      current
     DESCRIPTION
      "BandWidth Resource table"
     INDEX {  
              ifIndex
           }
     ::= { hwAtmPortBandWidthTable 1 }
     
   HwAtmPortBandWidthEntry ::=
     SEQUENCE
     {
       hwAtmPortBandWidthValue     INTEGER
     }
  
   hwAtmPortBandWidthValue OBJECT-TYPE
    SYNTAX      INTEGER(1..32)
    MAX-ACCESS  read-write
    STATUS      current
    DESCRIPTION
        "The bandwidth value of the port"
    DEFVAL      { 0 }
    ::={ hwAtmPortBandWidthEntry 1 }



   
   hwApmBandWidthTable OBJECT-TYPE
     SYNTAX      SEQUENCE OF HwApmBandWidthEntry
     MAX-ACCESS  not-accessible
     STATUS      current
     DESCRIPTION
        "BandWidth Resource table"
     ::= { hwAtmCmRm 2 }
     
   hwApmBandWidthEntry OBJECT-TYPE
     SYNTAX      HwApmBandWidthEntry
     MAX-ACCESS  not-accessible
     STATUS      current
     DESCRIPTION
      "BandWidth Resource table"
     INDEX {  
              hwFrameIndex,
              hwSlotIndex,
              hwApmBandWidthType
           }
     ::= { hwApmBandWidthTable 1 }
     
   HwApmBandWidthEntry ::=
     SEQUENCE
     {
       hwApmBandWidthType    INTEGER,
       hwApmBandWidthValue   INTEGER
     }  

   hwApmBandWidthType OBJECT-TYPE
    SYNTAX      INTEGER{vpring(1),relay(2),inner(3)}
    MAX-ACCESS  not-accessible
    STATUS      current
    DESCRIPTION
        "BandWidth Value"
    ::={ hwApmBandWidthEntry 1 }
    
   hwApmBandWidthValue OBJECT-TYPE
    SYNTAX      INTEGER(1..32)
    MAX-ACCESS  read-write
    STATUS      current
    DESCRIPTION
        "The bandwidth value of the apm"
    DEFVAL      { 0 }
    ::={ hwApmBandWidthEntry 2 }
    
		
END
