--  =================================================================
-- Copyright (C) by  HUAWEI TECHNOLOGIES. All rights reserved.
-- 
-- Description:     HUAWEI-IPDSLAM-PPPOE-MIB.mib
-- Reference:      
-- Version: V1.00 
-- date     :2006-04-04 ,
-- =================================================================

	HUAWEI-IPDSLAM-PPPOE-MIB DEFINITIONS ::= BEGIN
 
		IMPORTS			
			huaweiUtility			
				FROM HUAWEI-MIB						
			Unsigned32, OBJECT-TYPE, MODULE-IDENTITY			
				FROM SNMPv2-SMI			
			TruthValue, RowStatus			
				FROM SNMPv2-TC;
	
	
		hwIpDslamPPPoE MODULE-IDENTITY 
			LAST-UPDATED "200604041428Z"
			ORGANIZATION 
				"Fix-Net Dept, Huawei Technologies Co.,Ltd."
			CONTACT-INFO 
				"Block 4, R&D Building,
				Huawei Longgang Production Base,
				Shenzhen,  P.R.C.
				http://www.huawei.com
				Zip: 518057
				"
			DESCRIPTION 
				"
				huawei HUAWEI-IPDSLAM-PPPOE-MIB.
				"
			::= { huaweiUtility 107 }

	
--  ------------------------------------------------------------------------
-- System Management Parameter
-- ------------------------------------------------------------------------ 
		hwIpDslamPPPoEMacMode OBJECT-TYPE
			SYNTAX INTEGER
				{
				multi-mac(1),
				single-mac(2)
				}
			MAX-ACCESS read-write
			STATUS current
			DESCRIPTION
				"
				The MAC distribution mode of PPPoE.
				"
			DEFVAL { multi-mac }
			::= { hwIpDslamPPPoE 1 }
					
	END
