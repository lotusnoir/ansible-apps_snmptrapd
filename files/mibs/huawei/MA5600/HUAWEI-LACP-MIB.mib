--
-- HUAWEI-LACP-MIB.mib
-- MIB generated by MG-SOFT Visual MIB Builder Version 3.0 Build 253
-- Wednesday, May 24, 2006 at 14:28:42
--
HUAWEI-LACP-MIB DEFINITIONS ::= BEGIN
 
		IMPORTS 
			dot1dStpPortEntry			
				FROM BRIDGE-MIB			
			huaweiMgmt			
				FROM HUAWEI-MIB			
			Counter32, OBJECT-TYPE, MODULE-IDENTITY			
				FROM SNMPv2-SMI			
			MacAddress, TruthValue, RowStatus, DisplayString, TEXTUAL-CONVENTION			
				FROM SNMPv2-TC
			--huaweiDatacomm			
			--	FROM HUAWEI-DATACOMM-OID-MIB			
			OBJECT-GROUP, MODULE-COMPLIANCE			
				FROM SNMPv2-CONF;  
				
			--	IMPORTS
			--huaweiDatacomm			
			--	FROM HUAWEI-DATACOMM-OID-MIB			
			--OBJECT-GROUP, MODULE-COMPLIANCE			
			--	FROM SNMPv2-CONF			
			--Integer32, OBJECT-TYPE, MODULE-IDENTITY			
			--	FROM SNMPv2-SMI			
			--TruthValue, DateAndTime, RowStatus			
			--	FROM SNMPv2-TC
		
	    hwLacpExt MODULE-IDENTITY
			LAST-UPDATED "200604260900Z"           -- April 28, 2006 at 21:00 GMT
			ORGANIZATION "Fix-Net Dept, Huawei Technologies Co.,Ltd."
			CONTACT-INFO 
				"Floor 5 ,Block 4, R&D Building,
				Huawei Longgang Production Base,
				Shenzhen,  P.R.C.
				http://www.huawei.com
				Zip:518057
				"
			DESCRIPTION 
				"
				huawei lacp mib.
				"
			REVISION "200604280900Z"
			DESCRIPTION
				"
				V1.00	
				reunification version based on the  Fix-Net MIBs baseline by the MIB Standard community.
				"
			::= { huaweiMgmt 102 }
	    
	
	
--
-- Node definitions
--
	
		-- 1.3.6.1.4.1.2011.5.102.1
		hwLacpMibObjects OBJECT IDENTIFIER ::= { hwLacpExt 1 }
		
		-- 1.3.6.1.4.1.2011.5.102.1.1
		hwAggLinkTable OBJECT-TYPE
			SYNTAX SEQUENCE OF HwAggLinkEntry
			MAX-ACCESS not-accessible
			STATUS current
			DESCRIPTION
				"A table of aggregated link objects"
			::= { hwLacpMibObjects 1 }
		
		-- 1.3.6.1.4.1.2011.5.102.1.1.1
		hwAggLinkEntry OBJECT-TYPE
			SYNTAX HwAggLinkEntry
			MAX-ACCESS not-accessible
			STATUS current
			DESCRIPTION
				"Entry of table."
			INDEX { hwAggLinkNumber }
			::= { hwAggLinkTable 1 }
		
		HwAggLinkEntry ::=
			SEQUENCE { 
				hwAggLinkNumber
					Integer32,
				hwAggLinkName
					DisplayString,
				hwAggLinkMode
					INTEGER,
				hwAggLinkPortList
					INTEGER,
				hwAggLinkState
					RowStatus,
				hwAggPortListSelectedPorts
					INTEGER,
				hwAggPortListSamePartnerPorts
					INTEGER,
				hwAggLinkShareType
					INTEGER,
				hwAggLinkProtectType
					INTEGER,
				hwAggLinkSelectPorts
					Integer32,
				hwAggLinkUnselectPorts
					Integer32,
				hwAggLinkMasterPort
					Integer32
			 }

		-- 1.3.6.1.4.1.2011.5.102.1.1.1.1
		hwAggLinkNumber OBJECT-TYPE
			SYNTAX Integer32 (1..728)
			MAX-ACCESS accessible-for-notify
			STATUS current
			DESCRIPTION
				"Description."
			::= { hwAggLinkEntry 1 }
		
		-- 1.3.6.1.4.1.2011.5.102.1.1.1.2
		hwAggLinkName OBJECT-TYPE
			SYNTAX DisplayString (SIZE (0..32))
			MAX-ACCESS read-create
			STATUS current
			DESCRIPTION
				"Description."
			::= { hwAggLinkEntry 2 }
		
		-- 1.3.6.1.4.1.2011.5.102.1.1.1.3
		hwAggLinkMode OBJECT-TYPE
			SYNTAX INTEGER
				{
				manual(1),
				static(2),
				dynamic(3)
				}
			MAX-ACCESS read-create
			STATUS current
			DESCRIPTION
				"Type of aggregation. 1 => Manual 
				aggregation, no LACP 2 => Membership 
				specified by user, LACP is used to 
				validate 3 => Completely dynamic 
				aggregation detected by LACP"
			::= { hwAggLinkEntry 3 }
		
		-- 1.3.6.1.4.1.2011.5.102.1.1.1.4
		hwAggLinkPortList OBJECT-TYPE
			SYNTAX INTEGER
			MAX-ACCESS read-create
			STATUS current
			DESCRIPTION
				"List of ports in this AL, by bridge port number. 
				If the type is manual or static, you can update 
				this list to your hearts content. If, however, 
				the AL is dynamic, then the system will maintain it.
				 You are NOT permitted to set the value of this to all 
				zeroes."
			::= { hwAggLinkEntry 4 }
		
		-- 1.3.6.1.4.1.2011.5.102.1.1.1.5
		hwAggLinkState OBJECT-TYPE
			SYNTAX RowStatus
			MAX-ACCESS read-create
			STATUS current
			DESCRIPTION
				"RowStatus"
			::= { hwAggLinkEntry 5 }
		
		-- 1.3.6.1.4.1.2011.5.102.1.1.1.6
		hwAggPortListSelectedPorts OBJECT-TYPE
			SYNTAX INTEGER
			MAX-ACCESS read-only
			STATUS current
			DESCRIPTION
				"A PortList of physical ports that have selected
				to this aggregator, but which have not yet attached."
			::= { hwAggLinkEntry 6 }
		
		-- 1.3.6.1.4.1.2011.5.102.1.1.1.7
		hwAggPortListSamePartnerPorts OBJECT-TYPE
			SYNTAX INTEGER
			MAX-ACCESS read-only
			STATUS current
			DESCRIPTION
				"PortList of physical ports that the same Actor 
				SystemID and partner systemID as this aggregator,
				 but have differing actor and partner keys."
			::= { hwAggLinkEntry 7 }
		
		-- 1.3.6.1.4.1.2011.5.102.1.1.1.8
		hwAggLinkShareType OBJECT-TYPE
			SYNTAX INTEGER
				{
				loadsharing(1),
				nonloadsharing(2)
				}
			MAX-ACCESS read-only
			STATUS current
			DESCRIPTION
				"链路的负载分担类型，loadsharing表示负载分担 nonloadsharing表示非负载分担"
			::= { hwAggLinkEntry 8 }
		
		-- 1.3.6.1.4.1.2011.5.102.1.1.1.9
		hwAggLinkProtectType OBJECT-TYPE
			SYNTAX INTEGER
				{
				backupprotect(1),
				nonbackupprotect(2)
				}
			MAX-ACCESS read-only
			STATUS current
			DESCRIPTION
				"链路的保护类型,backupprotect表示备份保护聚合,nonbackupprotect表示非备份保护聚合"
			::= { hwAggLinkEntry 9 }
		
		-- 1.3.6.1.4.1.2011.5.102.1.1.1.10
		hwAggLinkSelectPorts OBJECT-TYPE
			SYNTAX Integer32 (0..65535)
			MAX-ACCESS read-only
			STATUS current
			DESCRIPTION
				"聚合组中已经选择的端口数"
			::= { hwAggLinkEntry 10 }
		
		-- 1.3.6.1.4.1.2011.5.102.1.1.1.11
		hwAggLinkUnselectPorts OBJECT-TYPE
			SYNTAX Integer32 (0..65535)
			MAX-ACCESS read-only
			STATUS current
			DESCRIPTION
				"聚合组中未选择的端口数"
			::= { hwAggLinkEntry 11 }
		
		-- 1.3.6.1.4.1.2011.5.102.1.1.1.12
		hwAggLinkMasterPort OBJECT-TYPE
			SYNTAX Integer32
			MAX-ACCESS read-only
			STATUS current
			DESCRIPTION
				"聚合组中的主端口号"
			::= { hwAggLinkEntry 12 }
		
		-- 1.3.6.1.4.1.2011.5.102.1.2
		hwAggPortTable OBJECT-TYPE
			SYNTAX SEQUENCE OF HwAggPortEntry
			MAX-ACCESS not-accessible
			STATUS current
			DESCRIPTION
				"A table of aggregated link objects"
			::= { hwLacpMibObjects 2 }
		
		-- 1.3.6.1.4.1.2011.5.102.1.2.1
		hwAggPortEntry OBJECT-TYPE
			SYNTAX HwAggPortEntry
			MAX-ACCESS not-accessible
			STATUS current
			DESCRIPTION
				"Entry of table."
			INDEX { hwAggPortIndex }
			::= { hwAggPortTable 1 }
		
		HwAggPortEntry ::=
			SEQUENCE { 
				hwAggPortIndex
					Gauge32,
				hwAggPortNotAttachedReason
					Integer32,
				hwAggPortLacpState
					TruthValue,
				hwAggPortNotAttachedString
					DisplayString,
				hwAggPortRole
					INTEGER,
				hwAggPortType
					INTEGER,
				hwAggPortStatus
					INTEGER
			 }

		-- 1.3.6.1.4.1.2011.5.102.1.2.1.1
		hwAggPortIndex OBJECT-TYPE
			SYNTAX Gauge32
			MAX-ACCESS not-accessible
			STATUS current
			DESCRIPTION
				"port index"
			::= { hwAggPortEntry 1 }
		
		-- 1.3.6.1.4.1.2011.5.102.1.2.1.2
		hwAggPortNotAttachedReason OBJECT-TYPE
			SYNTAX Integer32 (0..4)
			MAX-ACCESS read-write
			STATUS current
			DESCRIPTION
				"reason why this port is selected for an aggregator
				but not attached,-- 1 - all active ports are already
				in-use for this aggregator.-- 2 - all aggregation 
				resources are already in-use.-- 3 - the port's 
				configuration is not appropriate. -- 4 - the port's 
				partner is not appropriate"
			::= { hwAggPortEntry 2 }
		
		-- 1.3.6.1.4.1.2011.5.102.1.2.1.3
		hwAggPortLacpState OBJECT-TYPE
			SYNTAX TruthValue
			MAX-ACCESS read-write
			STATUS current
			DESCRIPTION
				"Control lacp enble or disable"
			::= { hwAggPortEntry 3 }
		
		-- 1.3.6.1.4.1.2011.5.102.1.2.1.4
		hwAggPortNotAttachedString OBJECT-TYPE
			SYNTAX DisplayString (SIZE (0..255))
			MAX-ACCESS read-write
			STATUS current
			DESCRIPTION
				"the reason  string why this 
				port is selected for an aggregator 
				but not attached"
			::= { hwAggPortEntry 4 }
		
		-- 1.3.6.1.4.1.2011.5.102.1.2.1.5
		hwAggPortRole OBJECT-TYPE
			SYNTAX INTEGER
				{
				selected(1),
				unselected(2)
				}
			MAX-ACCESS read-only
			STATUS current
			DESCRIPTION
				"端口角色,selected表示已选择,unselected表示未选择"
			::= { hwAggPortEntry 5 }
		
		-- 1.3.6.1.4.1.2011.5.102.1.2.1.6
		hwAggPortType OBJECT-TYPE
			SYNTAX INTEGER
				{
				mastport(1),
				nonmastPort(2)
				}
			MAX-ACCESS read-only
			STATUS current
			DESCRIPTION
				"端口类型，mastport表示主用端口，nonmastport表示备用端口"
			::= { hwAggPortEntry 6 }
		
		-- 1.3.6.1.4.1.2011.5.102.1.2.1.7
		hwAggPortStatus OBJECT-TYPE
			SYNTAX INTEGER
				{
				fowarding(1),
				block(2)
				}
			MAX-ACCESS read-only
			STATUS current
			DESCRIPTION
				"端口状态，fowarding表示转发，block表示阻塞"
			::= { hwAggPortEntry 7 }
		
		
		-- 1.3.6.1.4.1.2011.5.102.1.5
		hwAggResourceAllocationValue OBJECT-TYPE
			SYNTAX INTEGER
			MAX-ACCESS read-only
			STATUS current
			DESCRIPTION
				"The priority value calculated to decide 
				which aggregations have first call on the
				load-sharing aggregation resources in the hardware."
			DEFVAL { "0" }
			::= { hwLacpMibObjects 3 }     
					-- 1.3.6.1.4.1.2011.5.102.1.3
		hwAggShortPeriod OBJECT-TYPE
			SYNTAX INTEGER (0..10)
			MAX-ACCESS read-write
			STATUS current
			DESCRIPTION
				"the number of short timeouts
				短周期时间值"
			::= { hwLacpMibObjects 4 }
		
		-- 1.3.6.1.4.1.2011.5.102.1.4
		hwAggLongPeriod OBJECT-TYPE
			SYNTAX INTEGER (0 | 20..40)
			MAX-ACCESS read-write
			STATUS current
			DESCRIPTION
				"the number of long timeouts
				长周期时间值"
			::= { hwLacpMibObjects 5 }

		
		-- 1.3.6.1.4.1.2011.5.102.2
		hwLacpMibNotifications OBJECT IDENTIFIER ::= { hwLacpExt 2 }
		
		-- 1.3.6.1.4.1.2011.5.102.2.1
		hwAggSpeedChangedNotification NOTIFICATION-TYPE
			OBJECTS { hwAggLinkNumber }
			STATUS current
			DESCRIPTION 
				"This event will be triggered whenever an aggregation changes its speed."
			::= { hwLacpMibNotifications 1 }
		
		-- 1.3.6.1.4.1.2011.5.102.2.4
		hwAggPortInactiveNotification NOTIFICATION-TYPE
			OBJECTS { hwAggLinkNumber }
			STATUS current
			DESCRIPTION 
				"This event will be triggered whenever any port in aggrerator is made inactive"
			::= { hwLacpMibNotifications 4 }
		
		-- 1.3.6.1.4.1.2011.5.102.4
		hwLacpMibConformance OBJECT IDENTIFIER ::= { hwLacpExt 4 }
		
		-- 1.3.6.1.4.1.2011.5.102.4.1
		hwLacpMibCompliances OBJECT IDENTIFIER ::= { hwLacpMibConformance 1 }
		
		-- 1.3.6.1.4.1.2011.5.102.4.1.1
		hwLacpMibCompliance MODULE-COMPLIANCE
			STATUS current
			DESCRIPTION 
				"The compliance statement for SNMP entities which implement
				the Lacp MIB"
			MODULE -- this module
				MANDATORY-GROUPS { hwLacpMibObjectGroup, hwLacpMibNotificationGroup }
			::= { hwLacpMibCompliances 1 }
		
		-- 1.3.6.1.4.1.2011.5.102.4.2
		hwLacpMibGroup OBJECT IDENTIFIER ::= { hwLacpMibConformance 2 }
		
		-- 1.3.6.1.4.1.2011.5.102.4.2.1
		hwLacpMibObjectGroup OBJECT-GROUP
			OBJECTS { hwAggLinkName, hwAggLinkMode, hwAggLinkPortList, hwAggLinkState, hwAggPortListSelectedPorts, 
				hwAggPortListSamePartnerPorts, hwAggLinkShareType, hwAggLinkProtectType, hwAggLinkSelectPorts, hwAggLinkUnselectPorts, 
				hwAggLinkMasterPort, hwAggLinkUndoActorSystemPriority, hwAggPortNotAttachedReason, hwAggPortLacpState, hwAggPortNotAttachedString, 
				hwAggPortRole, hwAggPortType, hwAggPortStatus, hwAggPortUndoActorPortPriority,  hwAggResourceAllocationValue, hwAggShortPeriod, 
				hwAggLongPeriod}
			STATUS current
			DESCRIPTION 
				"The collection of objects which are used to represent Lacp objects."
			::= { hwLacpMibGroup 1 }
		
		-- 1.3.6.1.4.1.2011.5.102.4.2.2
		hwLacpMibNotificationGroup NOTIFICATION-GROUP
			NOTIFICATIONS { hwAggSpeedChangedNotification, hwAggPortInactiveNotification }
			STATUS current
			DESCRIPTION 
				"The collection of objects which are used to represent notifications."
			::= { hwLacpMibGroup 2 }
		
	
	END

--
-- HUAWEI-LACP-MIB.mib
--
