-- =================================================================
-- Copyright (C) 2003 by  HUAWEI TECHNOLOGIES. All rights reserved.
--
-- Description:     HUAWEI-DSLAM-NTV-MIB
-- Reference:      
-- Version: V1.00 
-- History:
-- author   :HaoFeng
-- date     :03-04-21
-- modify   :03-06-03
-- =================================================================

HUAWEI-DSLAM-NTV-MIB DEFINITIONS ::= BEGIN
IMPORTS	
       MODULE-IDENTITY, OBJECT-TYPE, OBJECT-IDENTITY, IpAddress, Integer32,Unsigned32
                        FROM SNMPv2-SMI
                        
        huaweiUtility
                        FROM HUAWEI-MIB
       ifIndex, InterfaceIndex          
                        FROM IF-MIB                                                
        RowStatus, DateAndTime, TruthValue
            FROM SNMPv2-TC;                        
                        
                        

hwDslamNtv MODULE-IDENTITY
			LAST-UPDATED "0304280900Z"
			ORGANIZATION 
			"Huawei Technologies co.,Ltd."
			CONTACT-INFO 
			"Administration Building
                         Huawei Technologies Co., Ltd.
                         Bantian, Longgang District 
                         Shenzhen, P. R. China
                         Postal Code: 518129
                         http://www.huawei.com
			"

			DESCRIPTION
			"
			huawei DSLAM NTV mib.
			"
			REVISION "0211290900Z"
			DESCRIPTION
			"It was initailized by FixNet Mib Group .
			"

   ::= { huaweiUtility 28} 
        
    DisplayString ::= OCTET STRING
    
    PortList ::= TEXTUAL-CONVENTION
			STATUS current
			DESCRIPTION
				"
				Every sequence 16 octet group altogether represents ports of 
				one slot:
				  octet0  -- octet15  represents ports of slot0,
				  octet16 -- octet31  represents ports of slot1,
				  ......
				  octet112-- octet127 represents ports of slot7.
				
				Each octet specifies a set of eight ports, 
				with the first octet of a 16 octet group specifying ports 0 
				through 7 of the slot, the second octet of a 16 octet group
				specifying ports 8 through 15 of the slot, etc.
				Within each octet, the most significant bit represents 
				the lowest numbered port, and the least significant bit 
				represents the highest numbered port:
				   ________________________________________________
				  |bit in octet0:  7   6   5   4   3   2   1   0   |
				  |port in slot0:  0   1   2   3   4   5   6   7   |
				  |________________________________________________|
				   ......
				   ________________________________________________              
				  |bit in octet15: 7   6   5   4   3   2   1   0   |
				  |port in slot0: 120 121 122 123 124 125 126 127  |                  
				  |________________________________________________|                    
				  
				  
				   ________________________________________________
				  |bit in octet16: 7   6   5   4   3   2   1   0   |
				  |port in slot1:  0   1   2   3   4   5   6   7   |
				  |________________________________________________|
				  ......              
				   ________________________________________________
				  |bit in octet31: 7   6   5   4   3   2   1   0   |  
				  |port in slot1: 120 121 122 123 124 125 126 127  |  
				  |________________________________________________|
				  ......
				  ......
				
				Thus, each port of the DSLAN is represented by a single bit 
				within the value of this object. If that bit has a value of 
				'1' then that port is included in the set of ports; the port 
				is not included if its bit has a value of '0'."
			SYNTAX OCTET STRING (SIZE (0..128))

    
    -- ------------------------------------------------------------------------
    --       System Management Parameter
    -- ------------------------------------------------------------------------ 
   hwDslamNtvMode   OBJECT-TYPE
       SYNTAX   INTEGER{
                         hmcp(1),
                         igmp-snooping(2),
                         igmp-proxy(3),
                         tv-off(4),
                         oam-group-control(5)
                       }
       MAX-ACCESS   read-write
       STATUS       current
       DESCRIPTION
           "NTV mode.
           HMCP and IGMP mode switch, supporting IGMP V1 and IGMP V2 and IGMP V3."
   ::= { hwDslamNtv 1 }
   
   hwDslamNtvVpi   OBJECT-TYPE
       SYNTAX       Integer32(0..255)
       MAX-ACCESS   read-write
       STATUS       current
       DESCRIPTION
           "Multicast vpi.
           System multicast vpi. Value ranges from 0 to 255.If it is changed,all the vpi of multicast pvcs are changed."
       DEFVAL { 0 }
   ::= { hwDslamNtv 2 }
   
   hwDslamNtvVci   OBJECT-TYPE
       SYNTAX       Integer32(32..255)
       MAX-ACCESS   read-write
       STATUS       current
       DESCRIPTION
           "Multicast vci.
           System multicast vci. Value from 0 to 65535.If it is changed,all the vci of multicast pvc are changed."
       DEFVAL { 35 }
   ::= { hwDslamNtv 3 }
   
   hwDslamNtvQueryInterval   OBJECT-TYPE
       SYNTAX       Unsigned32 (30..5000)
       UNITS        "seconds"
       MAX-ACCESS   read-write
       STATUS       current
       DESCRIPTION
           "Query interval.
           The frequency at which IGMP Host-Query packets are transmitted on this interface."
       DEFVAL { 125 }    
   ::= { hwDslamNtv 4 }
   
   hwDslamNtvQuerier   OBJECT-TYPE
       SYNTAX       IpAddress
       MAX-ACCESS   read-write
       STATUS       current
       DESCRIPTION
           "NTV Querier.
           The address of the IGMP Querier on the IP subnet to which this interface is attached.
           In fact it is the system IP address.
           "
   ::= { hwDslamNtv 5 }   
   
   hwDslamNtvQueryMaxResponseTime   OBJECT-TYPE
       SYNTAX       Integer32 (1..255)
       UNITS        "0.1s"
       MAX-ACCESS   read-write
       STATUS       current
       DESCRIPTION
           "Max response time.
           The maximum general query response time advertised in IGMPv2 queries in the system."
      DEFVAL { 100 }    
   ::= { hwDslamNtv 6 }      

   hwDslamNtvLeaveDelay   OBJECT-TYPE
       SYNTAX       Integer32(5..2550)
       UNITS        "0.1s"
       MAX-ACCESS   read-write
       STATUS       current
       DESCRIPTION
           "Leave delay."
   ::= { hwDslamNtv 7 }
   
   hwDslamNtvMaxChannelNum   OBJECT-TYPE
       SYNTAX       Integer32(1..1024)
       MAX-ACCESS   read-only
       STATUS       current
       DESCRIPTION
				"The max channel number that the system supports."
   ::= { hwDslamNtv 8 }   

   hwDslamNtvSnoopingAdminStatus        OBJECT-TYPE
           SYNTAX       TruthValue
           MAX-ACCESS   read-write
           STATUS       current
           DESCRIPTION
               "Snooping administer state.
                The administrative true(enable)/ false(disable) state for IGMP Snooping.
		used to enable/disable IGMP Snooping to control whether MAC multicast 
		forwarding table is created and maintained on Layer 2."
   ::= { hwDslamNtv 9 }   
    
   hwDslamNtvLastChange   OBJECT-TYPE
       SYNTAX   INTEGER{
                         changed(1),
		         unchanged(2)
		       }
       MAX-ACCESS   read-only
       STATUS       current
       DESCRIPTION
           "NTV feature configure state.
           The value of sysUpTime at the time when the system entered its current operational state. 
           If the currentstate was entered prior to the last re-initializationof the local 
           network management subsystem, then this object contains a zero value."
   ::= { hwDslamNtv 10 }
   
   hwDslamNtvUpportInterface   OBJECT-TYPE
       SYNTAX       InterfaceIndex
       MAX-ACCESS   read-write
       STATUS       current
       DESCRIPTION
           "IfIndex of Main Up Port."
   ::= { hwDslamNtv 11 } 
   
   hwDslamNtvUpportVlanId   OBJECT-TYPE
       SYNTAX       Integer32(1..4093)
       MAX-ACCESS   read-write
       STATUS       current
       DESCRIPTION
           "VlanId of Main Up Port."
   ::= { hwDslamNtv 12 }
   
   hwDslamNtvRobustness        OBJECT-TYPE
       SYNTAX       Integer32(1..10)
       MAX-ACCESS   read-write
       STATUS       current
       DESCRIPTION
           "Config robustness-variable.
            The Robustness Variable allows tuning for the 
            expected packet loss on a subnet.If a subnet is 
            expected to be lossy, the Robustness Variable may be 
				increased."
           DEFVAL { 2 }
    ::= { hwDslamNtv 13}
       
   -- -------------------------------------------------------------------------   
   --        Port Management Table
   -- -------------------------------------------------------------------------       
    hwDslamNtvUserTable    OBJECT-TYPE
        SYNTAX          SEQUENCE OF HwDslamNtvUserEntry
        MAX-ACCESS      not-accessible
        STATUS          current
        DESCRIPTION
            "NTV port management table.One port has a user group."
    ::= { hwDslamNtv 16 }
    
    hwDslamNtvUserEntry    OBJECT-TYPE
        SYNTAX          HwDslamNtvUserEntry
        MAX-ACCESS      not-accessible
        STATUS          current
        DESCRIPTION
            "NTV port management entry"
    INDEX   { 
               hwDslamNtvUserIndex
            }
    ::= { hwDslamNtvUserTable  1 }

		HwDslamNtvUserEntry ::=
			SEQUENCE { 
				hwDslamNtvUserAuthority
					INTEGER,
				hwDslamNtvUserRightProfile
					Integer32,
				hwDslamNtvUserRowStatus
					RowStatus,
				hwDslamNtvUserOperStatus
					INTEGER,
				hwDslamNtvUserAdminStatus
					INTEGER,
				hwDslamNtvUserMaxChannel
					Integer32,
				hwDslamNtvUserWatchingChannel1
				        BITS,
				hwDslamNtvUserWatchingChannel2
				        BITS,
				hwDslamNtvUserEnableLog
					TruthValue,
				hwDslamNtvUserVpi
					Integer32,
				hwDslamNtvUserVci
					Integer32,
				hwDslamNtvUserVlan
					Integer32,
                hwDslamNtvUserFlowType         
                    INTEGER,
                hwDslamNtvUserFlowPara	     
                    Integer32,
                hwDslamNtvUserMode
                    INTEGER,
                hwDslamNtvUserAuthFailProcess
                    INTEGER,
                hwDslamNtvUserUsedBandwidth
                    Integer32,
                hwDslamNtvUserUsdBwthPcntToPortRate
                    INTEGER,
                hwDslamNtvUserIfIndex
                    Integer32,
                hwDslamNtvUserIndex
                    Integer32,
                hwDslamNtvUserMatchPara
                    Integer32,
                hwDslamNtvUserMaxBandWidth
                    Integer32,
                hwDslamNtvUserQuickLeaveTime
	                Integer32,
	            hwDslamNtvUserVideoVpi
	                Integer32,   
	            hwDslamNtvUserVideoVci
	                Integer32,  
	            hwDslamNtvUserVideoFlowType
	                INTEGER,          
	            hwDslamNtvUserVideoFlowPara      
	                Integer32,
	            hwDslamNtvUserQuickLeaveMode
	                INTEGER, 	                	                      
	            hwDslamNtvReceiveGlobalLeave
	                INTEGER,
	            hwDslamNtvUserFlowMode
	                INTEGER,
	            hwDslamNtvUserFlowID
	                Integer32,
	            hwDslamNtvUserVideoFlowID
	                Integer32,
	            hwDslamNtvUserVideoTagMode
	                INTEGER,
	            hwDslamNtvUserVideoTagPara
	                INTEGER,
	            hwDslamNtvUserAncpVideoBandwidth
	                Integer32,
	            hwDslamNtvUserAncpMcastBandwidth
	                Integer32}
			 
    hwDslamNtvUserAuthority        OBJECT-TYPE
           SYNTAX      INTEGER
           	           {
                           auth(1),
                           noauth(2)
                       }           
           MAX-ACCESS  read-create
           STATUS      current
           DESCRIPTION
               "User authority.
               For an authorized user, it must have a right profile and it can watch the program in the
               right profile only. For an unauthorized user, it needn't have a right profile and it can watch
				any program even not included in the program table."
    ::= { hwDslamNtvUserEntry 1}
              
    hwDslamNtvUserRightProfile        OBJECT-TYPE
           SYNTAX       Integer32(1..1024)
           MAX-ACCESS   read-create
           STATUS       current
           DESCRIPTION
               "Right profile.
               The index of user right profile.When user select the right profile,it can watch the program in the
               right profile only."
    ::= { hwDslamNtvUserEntry 2}
    
    hwDslamNtvUserRowStatus      OBJECT-TYPE
           SYNTAX       RowStatus
           MAX-ACCESS   read-create
           STATUS       current
           DESCRIPTION
               "Row status.
				Add or delete a table item."
    ::= { hwDslamNtvUserEntry 3}
    
    hwDslamNtvUserOperStatus    OBJECT-TYPE
           SYNTAX   INTEGER
                    {
                       online(1),
                       offline(2),
                       block(3)
                    }  
           MAX-ACCESS   read-only
           STATUS       current
           DESCRIPTION
               "Operational state.
               The current operational state of the user.If hwDslamNtvUserAdminStatus is block(1) then
               hwDslamNtvUserOperStatus should be block(3).If hwDslamNtvUserAdminStatus is unblock(2) 
               and the user are watching program then hwDslamNtvUserOperStatus should
               be online(1).If the user are not watching program then hwDslamNtvUserOperStatus should
				be offline(2)."
    ::= { hwDslamNtvUserEntry 4}
    
    hwDslamNtvUserAdminStatus     OBJECT-TYPE
           SYNTAX      INTEGER
           	           {
                           block(1),
                           unblock(2)
                       }
           MAX-ACCESS  read-create
           STATUS      current
           DESCRIPTION
				"Administerial state. Only several states offen used are described here.If there is any more,please extend it."
    ::= { hwDslamNtvUserEntry 5}
    
    hwDslamNtvUserMaxChannel        OBJECT-TYPE
           SYNTAX      Integer32(0..255)
           MAX-ACCESS  read-create
           STATUS      current
           DESCRIPTION
               "User max channel.
				The max channel number that a user can watch at the same time."
           DEFVAL { 8 }
    ::= { hwDslamNtvUserEntry 6}
       
    hwDslamNtvUserWatchingChannel1        OBJECT-TYPE
           SYNTAX   BITS
           	    {
                       channel1(0),
                       channel2(1),
                       channel3(2),
                       channel4(3),
                       channel5(4),
                       channel6(5),
                       channel7(6),
                       channel8(7),
                       channel9(8),
                       channel10(9),
                       channel11(10),
                       channel12(11),
                       channel13(12),
                       channel14(13),
                       channel15(14),
                       channel16(15),
                       channel17(16),
                       channel18(17),
                       channel19(18),
                       channel20(19),
                       channel21(20),
                       channel22(21),
                       channel23(22),
                       channel24(23),
                       channel25(24),
                       channel26(25),
                       channel27(26),
                       channel28(27),
                       channel29(28),
                       channel30(29),
                       channel31(30),
                       channel32(31),
                       channel33(32),
                       channel34(33),
                       channel35(34),
                       channel36(35),
                       channel37(36),
                       channel38(37),
                       channel39(38),
                       channel40(39),
                       channel41(40),
                       channel42(41),
                       channel43(42),
                       channel44(43),
                       channel45(44),
                       channel46(45),
                       channel47(46),
                       channel48(47),
                       channel49(48),
                       channel50(49),
                       channel51(50),
                       channel52(51),
                       channel53(52),
                       channel54(53),
                       channel55(54),
                       channel56(55),
                       channel57(56),
                       channel58(57),
                       channel59(58),
                       channel60(59),
                       channel61(60),
                       channel62(61),
                       channel63(62),
                       channel64(63),
                       channel65(64),
                       channel66(65),
                       channel67(66),
                       channel68(67),
                       channel69(68),
                       channel70(69),
                       channel71(70),
                       channel72(71),
                       channel73(72),
                       channel74(73),
                       channel75(74),
                       channel76(75),
                       channel77(76),
                       channel78(77),
                       channel79(78),
                       channel80(79),
                       channel81(80),
                       channel82(81),
                       channel83(82),
                       channel84(83),
                       channel85(84),
                       channel86(85),
                       channel87(86),
                       channel88(87),
                       channel89(88),
                       channel90(89),
                       channel91(90),
                       channel92(91),
                       channel93(92),
                       channel94(93),
                       channel95(94),
                       channel96(95),
                       channel97(96),
                       channel98(97),
                       channel99(98),
                       channel100(99),
                       channel101(100),
                       channel102(101),
                       channel103(102),
                       channel104(103),
                       channel105(104),
                       channel106(105),
                       channel107(106),
                       channel108(107),
                       channel109(108),
                       channel110(109),
                       channel111(110),
                       channel112(111),
                       channel113(112),
                       channel114(113),
                       channel115(114),
                       channel116(115),
                       channel117(116),
                       channel118(117),
                       channel119(118),
                       channel120(119),
                       channel121(120),
                       channel122(121),
                       channel123(122),
                       channel124(123),
                       channel125(124),
                       channel126(125),
                       channel127(126),
                       channel128(127)                       
                    }           
           MAX-ACCESS   read-only
           STATUS       current
           DESCRIPTION
               "User watching channel.
               The channels that a user is watching."
    ::= { hwDslamNtvUserEntry 7}   
    
    hwDslamNtvUserWatchingChannel2        OBJECT-TYPE
           SYNTAX   BITS
           	    {
                       channel129(0),
                       channel130(1),
                       channel131(2),
                       channel132(3),
                       channel133(4),
                       channel134(5),
                       channel135(6),
                       channel136(7),
                       channel137(8),
                       channel138(9),
                       channel139(10),
                       channel140(11),
                       channel141(12),
                       channel142(13),
                       channel143(14),
                       channel144(15),
                       channel145(16),
                       channel146(17),
                       channel147(18),
                       channel148(19),
                       channel149(20),
                       channel150(21),
                       channel151(22),
                       channel152(23),
                       channel153(24),
                       channel154(25),
                       channel155(26),
                       channel156(27),
                       channel157(28),
                       channel158(29),
                       channel159(30),
                       channel160(31),
                       channel161(32),
                       channel162(33),
                       channel163(34),
                       channel164(35),
                       channel165(36),
                       channel166(37),
                       channel167(38),
                       channel168(39),
                       channel169(40),
                       channel170(41),
                       channel171(42),
                       channel172(43),
                       channel173(44),
                       channel174(45),
                       channel175(46),
                       channel176(47),
                       channel177(48),
                       channel178(49),
                       channel179(50),
                       channel180(51),
                       channel181(52),
                       channel182(53),
                       channel183(54),
                       channel184(55),
                       channel185(56),
                       channel186(57),
                       channel187(58),
                       channel188(59),
                       channel189(60),
                       channel190(61),
                       channel191(62),
                       channel192(63),
                       channel193(64),
                       channel194(65),
                       channel195(66),
                       channel196(67),
                       channel197(68),
                       channel198(69),
                       channel199(70),
                       channel200(71),
                       channel201(72),
                       channel202(73),
                       channel203(74),
                       channel204(75),
                       channel205(76),
                       channel206(77),
                       channel207(78),
                       channel208(79),
                       channel209(80),
                       channel210(81),
                       channel211(82),
                       channel212(83),
                       channel213(84),
                       channel214(85),
                       channel215(86),
                       channel216(87),
                       channel217(88),
                       channel218(89),
                       channel219(90),
                       channel220(91),
                       channel221(92),
                       channel222(93),
                       channel223(94),
                       channel224(95),
                       channel225(96),
                       channel226(97),
                       channel227(98),
                       channel228(99),
                       channel229(100),
                       channel230(101),
                       channel231(102),
                       channel232(103),
                       channel233(104),
                       channel234(105),
                       channel235(106),
                       channel236(107),
                       channel237(108),
                       channel238(109),
                       channel239(110),
                       channel240(111),
                       channel241(112),
                       channel242(113),
                       channel243(114),
                       channel244(115),
                       channel245(116),
                       channel246(117),
                       channel247(118),
                       channel248(119),
                       channel249(120),
                       channel250(121),
                       channel251(122),
                       channel252(123),
                       channel253(124),
                       channel254(125),
                       channel255(126),
                       channel256(127)
                    }
           MAX-ACCESS   read-only
           STATUS       current
           DESCRIPTION
               "User watching channel.
               The channels that a user is watching."
    ::= { hwDslamNtvUserEntry 8}          		
		
		hwDslamNtvUserEnableLog OBJECT-TYPE
			SYNTAX TruthValue				
			MAX-ACCESS read-create
			STATUS current
			DESCRIPTION
				"Log switch.
				When the log switch is true(1), the system will record the events of starting or stopping watching programs of the user.
				When the log switch is false(2), the system will stop recording."
			DEFVAL { 1 }
			::= { hwDslamNtvUserEntry 9 }
		
		hwDslamNtvUserVpi OBJECT-TYPE
			SYNTAX Integer32
			MAX-ACCESS read-create
			STATUS current
			DESCRIPTION
				"the VPI of PVC which carries IGMP messages."
			::= { hwDslamNtvUserEntry 10 }

		hwDslamNtvUserVci OBJECT-TYPE
			SYNTAX Integer32
			MAX-ACCESS read-create
			STATUS current
			DESCRIPTION
				"the VCI of PVC which carries IGMP messages.
				This value is the ICID of the PVC which carries IGMP messages."
			::= { hwDslamNtvUserEntry 11 }

		hwDslamNtvUserVlan OBJECT-TYPE
			SYNTAX Integer32
			MAX-ACCESS read-create
			STATUS current
			DESCRIPTION
				"the VLAN which carries IGMP messages."
			::= { hwDslamNtvUserEntry 12 }
			
		hwDslamNtvUserFlowType OBJECT-TYPE
	                SYNTAX INTEGER
			{
			by-uservlan(1),
			by-encap(2),
			by-8021p(3),
			by-uservlan-ethertype(4)
			}
			MAX-ACCESS read-write
			STATUS current
			DESCRIPTION
			"the type of flow,Default:by_uservlan.
			 The subscriber with the flow type of VLAN and EtherType added in this way is not supported. Add the subscriber by the flow ID.
			"
			DEFVAL { 1 }
			::= { hwDslamNtvUserEntry 17 }
	
		hwDslamNtvUserFlowPara OBJECT-TYPE
			SYNTAX Integer32
			MAX-ACCESS read-write
			STATUS current
			DESCRIPTION
			"the parameter of flow.Default:1"
			DEFVAL { 1 }
			::= { hwDslamNtvUserEntry 18 }
			
		hwDslamNtvUserMode    OBJECT-TYPE
                        SYNTAX    INTEGER
		        {
		        snooping(0),
                        discard(1),
		        forwarding(2)
		        }
		    MAX-ACCESS    read-write
		    STATUS        current
		    DESCRIPTION
		        "the status of the user port mode."
			::= { hwDslamNtvUserEntry 19 }
			
		hwDslamNtvUserAuthFailProcess    OBJECT-TYPE
		    SYNTAX    INTEGER
		        {
		        discard(0),
		        forward(1)
		        }
		    MAX-ACCESS    read-write
		    STATUS        current
		    DESCRIPTION
		        "the process mode for the user when his authorization failed"
			::= { hwDslamNtvUserEntry 20 }  
			
		hwDslamNtvUserUsedBandwidth OBJECT-TYPE
			SYNTAX Integer32
			MAX-ACCESS read-only
			STATUS current
			DESCRIPTION
			"the user used bandwidth"
			::= { hwDslamNtvUserEntry 21 }
                                                
		hwDslamNtvUserUsdBwthPcntToPortRate OBJECT-TYPE
			SYNTAX INTEGER
			MAX-ACCESS read-only
			STATUS current
			DESCRIPTION
			"the percentage of user used bandwidth to port rate"
			::= { hwDslamNtvUserEntry 22 }			

		hwDslamNtvUserIfIndex OBJECT-TYPE
			SYNTAX Integer32
			MAX-ACCESS read-write
			STATUS current
			DESCRIPTION
			"the user ifindex,"
			::= { hwDslamNtvUserEntry 23 }	

		hwDslamNtvUserIndex OBJECT-TYPE
			SYNTAX Integer32
			MAX-ACCESS read-only
			STATUS current
			DESCRIPTION
			"the user inner index"
			::= { hwDslamNtvUserEntry 24 }	

		hwDslamNtvUserMatchPara OBJECT-TYPE
			SYNTAX Integer32
			MAX-ACCESS read-write
			STATUS current
			DESCRIPTION
			"the GemPortID of GPON port"
			::= { hwDslamNtvUserEntry 25 }	
		
		hwDslamNtvUserMaxBandWidth OBJECT-TYPE
			SYNTAX Integer32
			MAX-ACCESS read-write
			STATUS current
			DESCRIPTION
			"the max bandwidth a user can use"
			::= { hwDslamNtvUserEntry 26 }
			
		hwDslamNtvUserQuickLeaveTime  OBJECT-TYPE
			SYNTAX       Integer32(0..20)
                        UNITS        "0.1s"
			MAX-ACCESS read-write
			STATUS current
			DESCRIPTION
			"the aging time of user when quick leaved"
			::= { hwDslamNtvUserEntry 30 }   
			
       hwDslamNtvUserVideoVpi OBJECT-TYPE
			SYNTAX Integer32
			MAX-ACCESS read-create
			STATUS current
			DESCRIPTION
				"the VPI of PVC which carries multicast video."
			::= { hwDslamNtvUserEntry 31 }

		hwDslamNtvUserVideoVci OBJECT-TYPE
			SYNTAX Integer32
			MAX-ACCESS read-create
			STATUS current
			DESCRIPTION
				"the VCI of PVC which carries multicast video."
			::= { hwDslamNtvUserEntry 32 }
		
		hwDslamNtvUserVideoFlowType OBJECT-TYPE
	        SYNTAX INTEGER
			{
			by-uservlan(1),
			by-encap(2),
			by-8021p(3),
			by-uservlan-ethertype(4)
			}
			MAX-ACCESS read-write
			STATUS current
			DESCRIPTION
			"the type of flow,Default:by_uservlan.
			 The subscriber with the flow type of VLAN and EtherType added in this way is not supported. Add the subscriber by the flow ID.
			"
			DEFVAL { 1 }
			::= { hwDslamNtvUserEntry 33 }
	
		hwDslamNtvUserVideoFlowPara OBJECT-TYPE
			SYNTAX Integer32
			MAX-ACCESS read-write
			STATUS current
			DESCRIPTION
			"the parameter of flow.Default:1"
			DEFVAL { 1 }
			::= { hwDslamNtvUserEntry 34 }    
			
    	hwDslamNtvUserQuickLeaveMode OBJECT-TYPE
			SYNTAX INTEGER{immediate(1),mac-based(2),disable(3)}
			MAX-ACCESS read-write
			STATUS current
			DESCRIPTION
			"Quick Leave.
               When Quick Leave is normal,IGMP-Proxy make user 
               offline as soon as receiveing Leave packet instead 
	       of sending  specific queries.
	       When Quick Leave is mac-based,IGMP-Proxy make user 
               offline as soon as receiveing Leave packet instead 
	       of sending specific queries when all user have send 
	       Leave packet of one program in one port."
           DEFVAL { 2 }
			::= { hwDslamNtvUserEntry 35 }    
			
        hwDslamNtvReceiveGlobalLeave OBJECT-TYPE
			SYNTAX INTEGER{enable(1),disable(2)}
			MAX-ACCESS read-write
			STATUS current
			DESCRIPTION
			"
			The switch of receiving global leave from BTV user.
			"
			::= { hwDslamNtvUserEntry 36 } 			  
        
			 
        hwDslamNtvUserFlowMode OBJECT-TYPE
            SYNTAX      INTEGER{ptm(1),atm(2)}           
            MAX-ACCESS  read-write
            STATUS      current
            DESCRIPTION
            "User FlowMode.
            For an Vdsl or SHDSL user, it must have a mode that is ptm or atm."
            ::= { hwDslamNtvUserEntry 37 }                                                          
	
        hwDslamNtvUserFlowID OBJECT-TYPE
			SYNTAX      Integer32
			MAX-ACCESS  read-create
			STATUS      current
			DESCRIPTION
				"User Flow ID"
			::= { hwDslamNtvUserEntry 38 }
            
        hwDslamNtvUserVideoFlowID OBJECT-TYPE
			SYNTAX      Integer32
			MAX-ACCESS  read-create
			STATUS      current
			DESCRIPTION
				"User Video Flow ID"
			::= { hwDslamNtvUserEntry 39 }
			
	hwDslamNtvUserVideoTagMode OBJECT-TYPE
		         SYNTAX      INTEGER{untagged(1),mvlan(2),vlan(3)}           
		         MAX-ACCESS  read-write
		         STATUS      current
		         DESCRIPTION
		         	"Video tag mode."
		         DEFVAL { 1 }
		         ::= { hwDslamNtvUserEntry 40 }  
		         
	hwDslamNtvUserVideoTagPara OBJECT-TYPE
		         SYNTAX      INTEGER           
		         MAX-ACCESS  read-write
		         STATUS      current
		         DESCRIPTION
		         	"Video tag para."
		         ::= { hwDslamNtvUserEntry 41 }  
    
	hwDslamNtvUserAncpVideoBandwidth OBJECT-TYPE
		         SYNTAX      Integer32  
		         UNITS       "kbps"         
		         MAX-ACCESS  read-only
		         STATUS      current
		         DESCRIPTION
		         	"The video bandwidth which is allocated by ANCP server.
		         	 It include VOD bandwidth and muticast bandwidth"
		         ::= { hwDslamNtvUserEntry 42 }  

	hwDslamNtvUserAncpMcastBandwidth OBJECT-TYPE
		         SYNTAX      Integer32   
		         UNITS       "kbps"        
		         MAX-ACCESS  read-only
		         STATUS      current
		         DESCRIPTION
		         	"The muticast bandwidth which is allocated by ANCP server."
		         ::= { hwDslamNtvUserEntry 43 }  
            
   -- -------------------------------------------------------------------------   
   --        Channel Management Table
   -- -------------------------------------------------------------------------       
    hwDslamNtvChannelTable    OBJECT-TYPE
        SYNTAX             SEQUENCE OF HwDslamNtvChannelEntry
        MAX-ACCESS         not-accessible
        STATUS             current
        DESCRIPTION
            "Channel management table"
    ::= { hwDslamNtv 17 }
    
    hwDslamNtvChannelEntry    OBJECT-TYPE
        SYNTAX         HwDslamNtvChannelEntry
        MAX-ACCESS         not-accessible
        STATUS         current
        DESCRIPTION
            "Channel management entity"
        INDEX   { 
                    hwDslamNtvChannelIndex
                }
    ::= { hwDslamNtvChannelTable  1 }

   HwDslamNtvChannelEntry    ::= SEQUENCE  {
            hwDslamNtvChannelIndex        Integer32,
            hwDslamNtvChannelFrame        Integer32,
            hwDslamNtvChannelSlot         Integer32,
            hwDslamNtvChannelPort         Integer32,
            hwDslamNtvProgramIPAddr       IpAddress,
            hwDslamNtvChannelType         INTEGER,
            hwDslamNtvChannelRowStatus    RowStatus,
            hwDslamNtvChannelAttrib       INTEGER,
            hwDslamNtvChannelUserCount    Integer32
          }
   
    hwDslamNtvChannelIndex        OBJECT-TYPE
           SYNTAX       Integer32(1..256)
           MAX-ACCESS   read-only
           STATUS       current
           DESCRIPTION
               "Channel index."
    ::= { hwDslamNtvChannelEntry 1}
    
    hwDslamNtvChannelFrame        OBJECT-TYPE
           SYNTAX       Integer32 (0..255)
           MAX-ACCESS   read-create
           STATUS       current
           DESCRIPTION
               "Channel frame.
               The frame ID of channel that indicates which frame the channel is on."

    ::= { hwDslamNtvChannelEntry 2}
    
    hwDslamNtvChannelSlot        OBJECT-TYPE
           SYNTAX       Integer32 (0..255)
           MAX-ACCESS   read-create
           STATUS       current
           DESCRIPTION
               "Channel slot.
               The slot ID of channel that indicates which slot the channel is on."
    ::= { hwDslamNtvChannelEntry 3}        

    hwDslamNtvChannelPort        OBJECT-TYPE
           SYNTAX       Integer32 (0..255)
           MAX-ACCESS   read-create
           STATUS       current
           DESCRIPTION
               "Channel port.
               The port ID of channel that indicates which port the channel is on."
    ::= { hwDslamNtvChannelEntry 4}        

    hwDslamNtvProgramIPAddr         OBJECT-TYPE
           SYNTAX       IpAddress
           MAX-ACCESS   read-create
           STATUS       current
           DESCRIPTION
               "Program IP address.
               This address is the same as hwDslamNtvProgramIP in hwDslamNtvProgramTable."
    ::= { hwDslamNtvChannelEntry 5}
    
    hwDslamNtvChannelType        OBJECT-TYPE
           SYNTAX       INTEGER
                        {
                            contral(1),
                            service(2)
                        }
           MAX-ACCESS   read-create
           STATUS       current
           DESCRIPTION
               "Channel type."
    ::= { hwDslamNtvChannelEntry 6}    
    
    hwDslamNtvChannelRowStatus        OBJECT-TYPE
           SYNTAX       RowStatus
           MAX-ACCESS   read-create
           STATUS       current
           DESCRIPTION
               "Row status.
               Add or delete a table item."
    ::= { hwDslamNtvChannelEntry 7}
    
    hwDslamNtvChannelAttrib        OBJECT-TYPE
           SYNTAX   INTEGER
                    {
                      free(1),
                      used(2)
                    }
           MAX-ACCESS   read-only
           STATUS   current
           DESCRIPTION
               "Channel state.
               The state of channel being used.If the user count is 0,t he value of the node is free(1).
               If the user count isn't 0, the value of the node is used(2)."
    ::= { hwDslamNtvChannelEntry 8}
    
    hwDslamNtvChannelUserCount        OBJECT-TYPE
           SYNTAX       Integer32
           MAX-ACCESS   read-only
           STATUS       current
           DESCRIPTION
               "User Count.
               Number of the users who are watching the channel."
    ::= { hwDslamNtvChannelEntry 9}
    
   -- -------------------------------------------------------------------------   
   --        Program Management Table
   -- -------------------------------------------------------------------------       
    hwDslamNtvProgramTable    OBJECT-TYPE
        SYNTAX          SEQUENCE OF HwDslamNtvProgramEntry
        MAX-ACCESS      not-accessible
        STATUS          current
        DESCRIPTION
            "Program management table"
    ::= { hwDslamNtv 18 }
    
    hwDslamNtvProgramEntry    OBJECT-TYPE
        SYNTAX          HwDslamNtvProgramEntry
        MAX-ACCESS      not-accessible
        STATUS          current
        DESCRIPTION
            "Program source management entity."
        INDEX { 
                  hwDslamNtvProgramIndex
              }
    ::= { hwDslamNtvProgramTable  1 }

   HwDslamNtvProgramEntry    ::= SEQUENCE  {
            hwDslamNtvProgramIndex             Integer32,
            hwDslamNtvProgramIP                IpAddress,
            hwDslamNtvProgramRowStatus         RowStatus,
            hwDslamNtvProgramName              DisplayString,
            hwDslamNtvProfileMask              BITS,   
            hwDslamNtvProgramUserCount         Integer32,
            hwDslamNtvProgramUpport            InterfaceIndex, 
            hwDslamNtvProgramUpportVlan        Integer32, 
            hwDslamNtvProgramHostFun           TruthValue,  
            hwDslamNtvProgramPrejoin           TruthValue,
            hwDslamNtvProgramWatchingPortList1 PortList,
            hwDslamNtvProgramWatchingPortList2 PortList,
            hwDslamNtvProgramSourceIP          IpAddress,
            hwDslamNtvProgramLogAttr           TruthValue,
            hwDslamNtvProgramAcrossVlan        TruthValue,
            hwDslamNtvProgramUnsolicited       TruthValue,
            hwDslamNtvProgramBandWidth         Integer32,
            hwDslamNtvProgramWatchingCount     Integer32,
            hwDslamNtvProgramIpCascadePortList Integer32,
            hwDslamNtvProgramPreviewMaxTime    Integer32,
            hwDslamNtvProgramPreviewInterval   Integer32,
            hwDslamNtvProgramPreviewCount      Integer32,
            hwDslamNtvProgramPriority          Integer32,
            hwDslamNtvProgramHostIP            IpAddress,
            hwDslamNtvProgramLastReporterIP    IpAddress,
            hwDslamNtvProgramFoundElapse       OCTET STRING,
            hwDslamNtvProgramExpireTime        OCTET STRING,
            hwDslamNtvProgramBTVUserPortList   OCTET STRING,
            hwDslamNtvPreviewProfileID      Integer32,
            hwDslamNtvProgramGrade          INTEGER(0..255),
            hwDslamNtvProgramNewIpCascadePortList OCTET STRING,
            hwDslamNtvProgramMAC              DisplayString,
            hwDslamNtvProgramBTVUserPortList2   OCTET STRING
          }
                                    
    hwDslamNtvProgramIndex        OBJECT-TYPE
           SYNTAX       Integer32(1..1024)
           MAX-ACCESS   read-only
           STATUS       current
           DESCRIPTION
				"Program index."
    ::= { hwDslamNtvProgramEntry 1}   
   
    hwDslamNtvProgramIP        OBJECT-TYPE
           SYNTAX       IpAddress
           MAX-ACCESS   read-create
           STATUS       current
           DESCRIPTION
               "Program IP address.
               This address is the same as hwDslamNtvProgramIPAddr in hwDslamNtvChannelTable.It isn't the program
				source IP address."
    ::= { hwDslamNtvProgramEntry 2}
    
    hwDslamNtvProgramRowStatus        OBJECT-TYPE
           SYNTAX       RowStatus
           MAX-ACCESS   read-create
           STATUS       current
           DESCRIPTION
               "Row status.
				Add or delete a table item."
    ::= { hwDslamNtvProgramEntry 3}
    
    hwDslamNtvProgramName        OBJECT-TYPE
           SYNTAX       DisplayString (SIZE (1..16))
           MAX-ACCESS   read-create
           STATUS       current
           DESCRIPTION
               "Program name.
				Enery name is different from others."
    ::= { hwDslamNtvProgramEntry 4}
    
    hwDslamNtvProfileMask        OBJECT-TYPE
           SYNTAX   BITS
           	    {
                       profile1(0),
                       profile2(1),
                       profile3(2),
                       profile4(3),
                       profile5(4),
                       profile6(5),
                       profile7(6),
                       profile8(7),
                       profile9(8),
                       profile10(9),
                       profile11(10),
                       profile12(11),
                       profile13(12),
                       profile14(13),
                       profile15(14),
                       profile16(15),
                       profile17(16),
                       profile18(17),
                       profile19(18),
                       profile20(19),
                       profile21(20),
                       profile22(21),
                       profile23(22),
                       profile24(23),
                       profile25(24),
                       profile26(25),
                       profile27(26),
                       profile28(27),
                       profile29(28),
                       profile30(29),
                       profile31(30),
                       profile32(31),
                       profile33(32),
                       profile34(33),
                       profile35(34),
                       profile36(35),
                       profile37(36),
                       profile38(37),
                       profile39(38),
                       profile40(39),
                       profile41(40),
                       profile42(41),
                       profile43(42),
                       profile44(43),
                       profile45(44),
                       profile46(45),
                       profile47(46),
                       profile48(47),
                       profile49(48),
                       profile50(49),
                       profile51(50),
                       profile52(51),
                       profile53(52),
                       profile54(53),
                       profile55(54),
                       profile56(55),
                       profile57(56),
                       profile58(57),
                       profile59(58),
                       profile60(59),
                       profile61(60),
                       profile62(61),
                       profile63(62),
                       profile64(63),
                       profile65(64),
                       profile66(65),
                       profile67(66),
                       profile68(67),
                       profile69(68),
                       profile70(69),
                       profile71(70),
                       profile72(71),
                       profile73(72),
                       profile74(73),
                       profile75(74),
                       profile76(75),
                       profile77(76),
                       profile78(77),
                       profile79(78),
                       profile80(79),
                       profile81(80),
                       profile82(81),
                       profile83(82),
                       profile84(83),
                       profile85(84),
                       profile86(85),
                       profile87(86),
                       profile88(87),
                       profile89(88),
                       profile90(89),
                       profile91(90),
                       profile92(91),
                       profile93(92),
                       profile94(93),
                       profile95(94),
                       profile96(95),
                       profile97(96),
                       profile98(97),
                       profile99(98),
                       profile100(99),
                       profile101(100),
                       profile102(101),
                       profile103(102),
                       profile104(103),
                       profile105(104),
                       profile106(105),
                       profile107(106),
                       profile108(107),
                       profile109(108),
                       profile110(109),
                       profile111(110),
                       profile112(111),
                       profile113(112),
                       profile114(113),
                       profile115(114),
                       profile116(115),
                       profile117(116),
                       profile118(117),
                       profile119(118),
                       profile120(119),
                       profile121(120),
                       profile122(121),
                       profile123(122),
                       profile124(123),
                       profile125(124),
                       profile126(125),
                       profile127(126),
                       profile128(127)                       
                    }
           MAX-ACCESS   read-create
           STATUS       current
           DESCRIPTION
               "Right profile mask.
               Right profile mask of program source. If program is included in the right profile,the mask is 1.
               If program isn't included in the right profile,the mask is 0."
    ::= { hwDslamNtvProgramEntry 5}
    
    hwDslamNtvProgramUserCount        OBJECT-TYPE
           SYNTAX       Integer32
           MAX-ACCESS   read-only
           STATUS       current
           DESCRIPTION
               "User count.
               Count of the user which can watch the program."
    ::= { hwDslamNtvProgramEntry 6}
    
    hwDslamNtvProgramUpport   OBJECT-TYPE
       SYNTAX       InterfaceIndex
       MAX-ACCESS   read-create
       STATUS       current
       DESCRIPTION
				"IfIndex of Slave Up Port."
   ::= { hwDslamNtvProgramEntry 7 }
   
   hwDslamNtvProgramUpportVlan   OBJECT-TYPE
       SYNTAX       Integer32(1..4093)
       MAX-ACCESS   read-create
       STATUS       current
       DESCRIPTION
				"VlanId of Slave Up Port."
   ::= { hwDslamNtvProgramEntry 8 }
   
   hwDslamNtvProgramHostFun     OBJECT-TYPE
           SYNTAX      TruthValue
           MAX-ACCESS  read-create
           STATUS      current
           DESCRIPTION
               "Host funtion of program.
               Only the host funtion of a program is true,can the IGMP-Proxy 
				send IGMP packets to Up Port."
           DEFVAL { 1 }
    ::= { hwDslamNtvProgramEntry 9}   
    
   hwDslamNtvProgramPrejoin     OBJECT-TYPE
           SYNTAX      TruthValue
           MAX-ACCESS  read-create
           STATUS      current
           DESCRIPTION
               "Prejoin funtion of program
               When the prejoin funtion of a program is true,IGMP-Proxy 
               immediately send IGMP join packet of the program to Up Port
				whether user join or not."
           DEFVAL { 2 }
    ::= { hwDslamNtvProgramEntry 10} 
    
    hwDslamNtvProgramWatchingPortList1 OBJECT-TYPE
	   SYNTAX       PortList
	   MAX-ACCESS   read-only
	   STATUS       current
	   DESCRIPTION
		"Port list of slot0 to slot7 who are watching the program."
    ::= { hwDslamNtvProgramEntry 11 }
    
    hwDslamNtvProgramWatchingPortList2 OBJECT-TYPE
	   SYNTAX       PortList
	   MAX-ACCESS   read-only
	   STATUS       current
	   DESCRIPTION
		"Port list of slot8 to slot15 who are watching the program."
    ::= { hwDslamNtvProgramEntry 12 }
       
    hwDslamNtvProgramSourceIP        OBJECT-TYPE
           SYNTAX       IpAddress
           MAX-ACCESS   read-create
           STATUS       current
           DESCRIPTION
               "IP address of multicast-source."
    ::= { hwDslamNtvProgramEntry 13}        
 
    hwDslamNtvProgramLogAttr OBJECT-TYPE
           SYNTAX TruthValue
           MAX-ACCESS read-create
           STATUS current
           DESCRIPTION
				"Program log attribute."
           DEFVAL { 1 }
           ::= { hwDslamNtvProgramEntry 14 }

  hwDslamNtvProgramAcrossVlan OBJECT-TYPE
           SYNTAX TruthValue
           MAX-ACCESS read-create
           STATUS current
           DESCRIPTION
				"Program is transfered by across VLAN."
           DEFVAL { 1 }
           ::= { hwDslamNtvProgramEntry 15 }

   hwDslamNtvProgramUnsolicited OBJECT-TYPE
           SYNTAX TruthValue
           MAX-ACCESS read-create
           STATUS current
           DESCRIPTION
				"Program is reported unsolicited."
           DEFVAL { 1 }
           ::= { hwDslamNtvProgramEntry 16 }

   hwDslamNtvProgramBandWidth OBJECT-TYPE
           SYNTAX Integer32
           MAX-ACCESS read-create
           STATUS current
           DESCRIPTION
				"Program bit rate."
           ::= { hwDslamNtvProgramEntry 17 }

   hwDslamNtvProgramWatchingCount OBJECT-TYPE
           SYNTAX Integer32
           MAX-ACCESS read-only
           STATUS current
           DESCRIPTION
				"Count of users which are watching this program."
           ::= { hwDslamNtvProgramEntry 18 }

   hwDslamNtvProgramIpCascadePortList OBJECT-TYPE
           SYNTAX Integer32
           MAX-ACCESS read-only
           STATUS current
           DESCRIPTION
               "IP cascade port list, 16bits. List of the IP cascade port which can watch the program."
           ::= { hwDslamNtvProgramEntry 19 }
           
   hwDslamNtvProgramPreviewMaxTime OBJECT-TYPE
           SYNTAX Integer32 (10..6000)
           UNITS  "second"
           MAX-ACCESS read-write
           STATUS current
           DESCRIPTION
				"The max time of per preview."
           DEFVAL { 120 }
           ::= { hwDslamNtvProgramEntry 20 }
		
   hwDslamNtvProgramPreviewInterval OBJECT-TYPE
           SYNTAX Integer32 (0..7650)
           UNITS  "second"
           MAX-ACCESS read-write
           STATUS current
           DESCRIPTION
				"The interval time of preview the same program."
           DEFVAL { 120 }
           ::= { hwDslamNtvProgramEntry 21 }
		
   hwDslamNtvProgramPreviewCount OBJECT-TYPE
           SYNTAX Integer32 (1..255)
           MAX-ACCESS read-write
           STATUS current
           DESCRIPTION
				"The times of preview."
           DEFVAL { 8 }
           ::= { hwDslamNtvProgramEntry 22 }

   hwDslamNtvProgramPriority OBJECT-TYPE
           SYNTAX Integer32 (0..7)
           MAX-ACCESS read-write
           STATUS current
           DESCRIPTION
				"The priority of program."
           DEFVAL { 7 }
           ::= { hwDslamNtvProgramEntry 23 }

   hwDslamNtvProgramHostIP OBJECT-TYPE
           SYNTAX IpAddress
           MAX-ACCESS read-write
           STATUS current
           DESCRIPTION
               "The hostip address of program."
           ::= { hwDslamNtvProgramEntry 24 }

    hwDslamNtvProgramLastReporterIP OBJECT-TYPE
    	   SYNTAX IpAddress
    	   MAX-ACCESS read-only
    	   STATUS current
    	   DESCRIPTION
    		"The last host ip address of the igmp report message for the multicast group."
    	   ::= { hwDslamNtvProgramEntry 25 }
    hwDslamNtvProgramFoundElapse OBJECT-TYPE
    	   SYNTAX OCTET STRING
    	   MAX-ACCESS read-only
    	   STATUS current
    	   DESCRIPTION
    		"Elapse time since the igmp group is founded."
    	   ::= { hwDslamNtvProgramEntry 26 }
    
    hwDslamNtvProgramExpireTime OBJECT-TYPE
    	   SYNTAX OCTET STRING
    	   MAX-ACCESS read-only
    	   STATUS current
    	   DESCRIPTION
    		"The remain time that the igmp group to be deleted."
    	   ::= { hwDslamNtvProgramEntry 27 }
                                 
    hwDslamNtvProgramBTVUserPortList OBJECT-TYPE
    	   SYNTAX OCTET STRING
    	   MAX-ACCESS read-only
    	   STATUS current
    	   DESCRIPTION
    		"BTV user list. List of the BTV user who is watching the program."
    	   ::= { hwDslamNtvProgramEntry 28 }
    	       	   
    hwDslamNtvPreviewProfileID  OBJECT-TYPE
    	   SYNTAX  Integer32
    	   MAX-ACCESS read-write
    	   STATUS current
    	   DESCRIPTION
    		"The index of preview profile"
    	   ::= { hwDslamNtvProgramEntry 29 }
   
    hwDslamNtvProgramGrade  OBJECT-TYPE
           SYNTAX  INTEGER(0..255)      
           MAX-ACCESS read-write
    	   STATUS current
    	   DESCRIPTION
    		"The program's grade "
    	   ::= { hwDslamNtvProgramEntry 30 }   
    
   hwDslamNtvProgramNewIpCascadePortList OBJECT-TYPE
           SYNTAX OCTET STRING
           MAX-ACCESS read-only
           STATUS current
           DESCRIPTION
               "IP cascade port list, 2048bits. List of the IP cascade port which can watch the program."
           ::= { hwDslamNtvProgramEntry 31 }
           
    hwDslamNtvProgramMAC        OBJECT-TYPE
           SYNTAX       DisplayString 
           MAX-ACCESS   read-only
           STATUS       current
           DESCRIPTION
               "Program mac address."
    ::= { hwDslamNtvProgramEntry 32}   
    
    hwDslamNtvProgramBTVUserPortList2 OBJECT-TYPE
    	   SYNTAX OCTET STRING
    	   MAX-ACCESS read-only
    	   STATUS current
    	   DESCRIPTION
    		"BTV user list2. List of the BTV user who is watching the program."
    	   ::= { hwDslamNtvProgramEntry 33 }
           	                                                           
   -- -------------------------------------------------------------------------   
   --        Right Profile Management Table
   -- -------------------------------------------------------------------------       
    hwDslamNtvRightProfileTable    OBJECT-TYPE
        SYNTAX          SEQUENCE OF HwDslamNtvRightProfileEntry
        MAX-ACCESS      not-accessible
        STATUS          current
        DESCRIPTION
            "Right profile management table"
    ::= { hwDslamNtv 19 }
    
    hwDslamNtvRightProfileEntry    OBJECT-TYPE
        SYNTAX         HwDslamNtvRightProfileEntry
        MAX-ACCESS         not-accessible
        STATUS         current
    DESCRIPTION
    "Right profile management entity"
    INDEX   { 
               hwDslamNtvRightProfileIndex
            }
    ::= { hwDslamNtvRightProfileTable  1 }

    HwDslamNtvRightProfileEntry    ::= SEQUENCE  {
            hwDslamNtvRightProfileIndex           Integer32,
            hwDslamNtvRightProfileName            DisplayString,
            hwDslamNtvRightProfileRowStatus       RowStatus,
            hwDslamNtvProgramMask1                BITS,
            hwDslamNtvProgramMask2                BITS,
            hwDslamNtvRightProfileCount           Integer32,
            hwDslamNtvRightProfilePortList1       PortList,
            hwDslamNtvRightProfilePortList2       PortList,
            hwDslamNtvProgramMask3                BITS,
            hwDslamNtvProgramMask4                BITS,
            hwDslamNtvProgramMask5                BITS,
            hwDslamNtvProgramMask6                BITS,
            hwDslamNtvProgramMask7                BITS,
            hwDslamNtvProgramMask8                BITS,
            hwDslamNtvProgramMask9                BITS,
            hwDslamNtvProgramMask10               BITS,
            hwDslamNtvProgramMask11               BITS,
            hwDslamNtvProgramMask12               BITS,
            hwDslamNtvProgramMask13               BITS,
            hwDslamNtvProgramMask14               BITS,
            hwDslamNtvProgramMask15               BITS,
            hwDslamNtvProgramMask16               BITS,
            hwDslamNtvProgramMask17               BITS,
            hwDslamNtvProgramMask18               BITS,
            hwDslamNtvProgramMask19               BITS,
            hwDslamNtvProgramMask20               BITS,
            hwDslamNtvProgramMask21               BITS,
            hwDslamNtvProgramMask22               BITS,
            hwDslamNtvProgramMask23               BITS,
            hwDslamNtvProgramMask24               BITS,
            hwDslamNtvProgramMask25               BITS,
            hwDslamNtvProgramMask26               BITS,
            hwDslamNtvProgramMask27               BITS,
            hwDslamNtvProgramMask28               BITS,
            hwDslamNtvProgramMask29               BITS,
            hwDslamNtvProgramMask30               BITS,
            hwDslamNtvProgramMask31               BITS,
            hwDslamNtvProgramMask32               BITS,
            hwDslamNtvRightProfileUserRefCount    Integer32
          }
   
    hwDslamNtvRightProfileIndex        OBJECT-TYPE
           SYNTAX       Integer32
           MAX-ACCESS   read-only
           STATUS       current
           DESCRIPTION
				"Right profile index in profile-based.Or user's ifindex in user-based."
    ::= { hwDslamNtvRightProfileEntry 1}   

    hwDslamNtvRightProfileName      OBJECT-TYPE
           SYNTAX       DisplayString (SIZE (1..16))
           MAX-ACCESS   read-write
           STATUS       current
           DESCRIPTION
				"Right profile name."
    ::= { hwDslamNtvRightProfileEntry 2}
   
    hwDslamNtvRightProfileRowStatus    OBJECT-TYPE
           SYNTAX       RowStatus
           MAX-ACCESS   read-create
           STATUS       current
           DESCRIPTION
               "Row status.
				Add or delete a table item."
    ::= { hwDslamNtvRightProfileEntry 3}   
   
    hwDslamNtvProgramMask1        OBJECT-TYPE
           SYNTAX   BITS
           	    {
                       program1(0),
                       program2(1),
                       program3(2),
                       program4(3),
                       program5(4),
                       program6(5),
                       program7(6),
                       program8(7),
                       program9(8),
                       program10(9),
                       program11(10),
                       program12(11),
                       program13(12),
                       program14(13),
                       program15(14),
                       program16(15),
                       program17(16),
                       program18(17),
                       program19(18),
                       program20(19),
                       program21(20),
                       program22(21),
                       program23(22),
                       program24(23),
                       program25(24),
                       program26(25),
                       program27(26),
                       program28(27),
                       program29(28),
                       program30(29),
                       program31(30),
                       program32(31),
                       program33(32),
                       program34(33),
                       program35(34),
                       program36(35),
                       program37(36),
                       program38(37),
                       program39(38),
                       program40(39),
                       program41(40),
                       program42(41),
                       program43(42),
                       program44(43),
                       program45(44),
                       program46(45),
                       program47(46),
                       program48(47),
                       program49(48),
                       program50(49),
                       program51(50),
                       program52(51),
                       program53(52),
                       program54(53),
                       program55(54),
                       program56(55),
                       program57(56),
                       program58(57),
                       program59(58),
                       program60(59),
                       program61(60),
                       program62(61),
                       program63(62),
                       program64(63),
                       program65(64),
                       program66(65),
                       program67(66),
                       program68(67),
                       program69(68),
                       program70(69),
                       program71(70),
                       program72(71),
                       program73(72),
                       program74(73),
                       program75(74),
                       program76(75),
                       program77(76),
                       program78(77),
                       program79(78),
                       program80(79),
                       program81(80),
                       program82(81),
                       program83(82),
                       program84(83),
                       program85(84),
                       program86(85),
                       program87(86),
                       program88(87),
                       program89(88),
                       program90(89),
                       program91(90),
                       program92(91),
                       program93(92),
                       program94(93),
                       program95(94),
                       program96(95),
                       program97(96),
                       program98(97),
                       program99(98),
                       program100(99),
                       program101(100),
                       program102(101),
                       program103(102),
                       program104(103),
                       program105(104),
                       program106(105),
                       program107(106),
                       program108(107),
                       program109(108),
                       program110(109),
                       program111(110),
                       program112(111),
                       program113(112),
                       program114(113),
                       program115(114),
                       program116(115),
                       program117(116),
                       program118(117),
                       program119(118),
                       program120(119),
                       program121(120),
                       program122(121),
                       program123(122),
                       program124(123),
                       program125(124),
                       program126(125),
                       program127(126),
                       program128(127)                       
                    }
           MAX-ACCESS   read-write
           STATUS       current
           DESCRIPTION
               "Program mask.
               Program source mask of right profile. If right profile includes the program, the mask is 1.
               Two bits indicate one program's right.
               So if the profile has the corresponding program watch right, the two masks should be 01.
               If the profile has the corresponding program preview right, the two masks should be 10.
               If the profile has the corresponding program forbidden right, the two masks should be 11.
               If the profile has not the corresponding program right, the two masks should be 00."
    ::= { hwDslamNtvRightProfileEntry 4}
    
    hwDslamNtvProgramMask2        OBJECT-TYPE
           SYNTAX   BITS
           	    {
                       program129(0),
                       program130(1),
                       program131(2),
                       program132(3),
                       program133(4),
                       program134(5),
                       program135(6),
                       program136(7),
                       program137(8),
                       program138(9),
                       program139(10),
                       program140(11),
                       program141(12),
                       program142(13),
                       program143(14),
                       program144(15),
                       program145(16),
                       program146(17),
                       program147(18),
                       program148(19),
                       program149(20),
                       program150(21),
                       program151(22),
                       program152(23),
                       program153(24),
                       program154(25),
                       program155(26),
                       program156(27),
                       program157(28),
                       program158(29),
                       program159(30),
                       program160(31),
                       program161(32),
                       program162(33),
                       program163(34),
                       program164(35),
                       program165(36),
                       program166(37),
                       program167(38),
                       program168(39),
                       program169(40),
                       program170(41),
                       program171(42),
                       program172(43),
                       program173(44),
                       program174(45),
                       program175(46),
                       program176(47),
                       program177(48),
                       program178(49),
                       program179(50),
                       program180(51),
                       program181(52),
                       program182(53),
                       program183(54),
                       program184(55),
                       program185(56),
                       program186(57),
                       program187(58),
                       program188(59),
                       program189(60),
                       program190(61),
                       program191(62),
                       program192(63),
                       program193(64),
                       program194(65),
                       program195(66),
                       program196(67),
                       program197(68),
                       program198(69),
                       program199(70),
                       program200(71),
                       program201(72),
                       program202(73),
                       program203(74),
                       program204(75),
                       program205(76),
                       program206(77),
                       program207(78),
                       program208(79),
                       program209(80),
                       program210(81),
                       program211(82),
                       program212(83),
                       program213(84),
                       program214(85),
                       program215(86),
                       program216(87),
                       program217(88),
                       program218(89),
                       program219(90),
                       program220(91),
                       program221(92),
                       program222(93),
                       program223(94),
                       program224(95),
                       program225(96),
                       program226(97),
                       program227(98),
                       program228(99),
                       program229(100),
                       program230(101),
                       program231(102),
                       program232(103),
                       program233(104),
                       program234(105),
                       program235(106),
                       program236(107),
                       program237(108),
                       program238(109),
                       program239(110),
                       program240(111),
                       program241(112),
                       program242(113),
                       program243(114),
                       program244(115),
                       program245(116),
                       program246(117),
                       program247(118),
                       program248(119),
                       program249(120),
                       program250(121),
                       program251(122),
                       program252(123),
                       program253(124),
                       program254(125),
                       program255(126),
                       program256(127)
                    }           
           MAX-ACCESS   read-write
           STATUS       current
           DESCRIPTION
               "Program mask.
               Program source mask of right profile. If right profile includes the program, the mask is 1.
               Two bits indicate one program's right.
               So if the profile has the corresponding program watch right, the two masks should be 01.
               If the profile has the corresponding program preview right, the two masks should be 10.
               If the profile has the corresponding program forbidden right, the two masks should be 11.
               If the profile has not the corresponding program right, the two masks should be 00."
    ::= { hwDslamNtvRightProfileEntry 5}
    
    hwDslamNtvRightProfileCount        OBJECT-TYPE
           SYNTAX       Integer32
           MAX-ACCESS   read-only
           STATUS       current
           DESCRIPTION
               "Right profile count.
               Count of the users who can watch the program in the right profile."
    ::= { hwDslamNtvRightProfileEntry 6}
    
    hwDslamNtvRightProfilePortList1 OBJECT-TYPE
	   SYNTAX       PortList
	   MAX-ACCESS   read-only
	   STATUS       current
	   DESCRIPTION
		"Port list of slot0 to slot7 who can watch the program in the right profile."
    ::= { hwDslamNtvRightProfileEntry 7 }
    
    hwDslamNtvRightProfilePortList2 OBJECT-TYPE
	   SYNTAX       PortList
	   MAX-ACCESS   read-only
	   STATUS       current
	   DESCRIPTION
		"Port list of slot8 to slot15 who can watch the program in the right profile."
    ::= { hwDslamNtvRightProfileEntry 8 }

   hwDslamNtvProgramMask3 OBJECT-TYPE
			SYNTAX BITS
				{
				program257(0),
				program258(1),
				program259(2),
				program260(3),
				program261(4),
				program262(5),
				program263(6),
				program264(7),
				program265(8),
				program266(9),
				program267(10),
				program268(11),
				program269(12),
				program270(13),
				program271(14),
				program272(15),
				program273(16),
				program274(17),
				program275(18),
				program276(19),
				program277(20),
				program278(21),
				program279(22),
				program280(23),
				program281(24),
				program282(25),
				program283(26),
				program284(27),
				program285(28),
				program286(29),
				program287(30),
				program288(31),
				program289(32),
				program290(33),
				program291(34),
				program292(35),
				program293(36),
				program294(37),
				program295(38),
				program296(39),
				program297(40),
				program298(41),
				program299(42),
				program300(43),
				program301(44),
				program302(45),
				program303(46),
				program304(47),
				program305(48),
				program306(49),
				program307(50),
				program308(51),
				program309(52),
				program310(53),
				program311(54),
				program312(55),
				program313(56),
				program314(57),
				program315(58),
				program316(59),
				program317(60),
				program318(61),
				program319(62),
				program320(63),
				program321(64),
				program322(65),
				program323(66),
				program324(67),
				program325(68),
				program326(69),
				program327(70),
				program328(71),
				program329(72),
				program330(73),
				program331(74),
				program332(75),
				program333(76),
				program334(77),
				program335(78),
				program336(79),
				program337(80),
				program338(81),
				program339(82),
				program340(83),
				program341(84),
				program342(85),
				program343(86),
				program344(87),
				program345(88),
				program346(89),
				program347(90),
				program348(91),
				program349(92),
				program350(93),
				program351(94),
				program352(95),
				program353(96),
				program354(97),
				program355(98),
				program356(99),
				program357(100),
				program358(101),
				program359(102),
				program360(103),
				program361(104),
				program362(105),
				program363(106),
				program364(107),
				program365(108),
				program366(109),
				program367(110),
				program368(111),
				program369(112),
				program370(113),
				program371(114),
				program372(115),
				program373(116),
				program374(117),
				program375(118),
				program376(119),
				program377(120),
				program378(121),
				program379(122),
				program380(123),
				program381(124),
				program382(125),
				program383(126),
				program384(127)
				}
			MAX-ACCESS read-write
			STATUS current
			DESCRIPTION
				"Program mask.
				Program source mask of right profile. If right profile include the program, the mask is 1.
                Two bits indicate one program's right.
                So if the profile has the corresponding program watch right, the two masks should be 01.
                If the profile has the corresponding program preview right, the two masks should be 10.
                If the profile has the corresponding program forbidden right, the two masks should be 11.
				            If the profile has not the corresponding program right, the two masks should be 00."
			::= { hwDslamNtvRightProfileEntry 9 }
		
		
		hwDslamNtvProgramMask4 OBJECT-TYPE
			SYNTAX BITS
				{
				program385(0),
				program386(1),
				program387(2),
				program388(3),
				program389(4),
				program390(5),
				program391(6),
				program392(7),
				program393(8),
				program394(9),
				program395(10),
				program396(11),
				program397(12),
				program398(13),
				program399(14),
				program400(15),
				program401(16),
				program402(17),
				program403(18),
				program404(19),
				program405(20),
				program406(21),
				program407(22),
				program408(23),
				program409(24),
				program410(25),
				program411(26),
				program412(27),
				program413(28),
				program414(29),
				program415(30),
				program416(31),
				program417(32),
				program418(33),
				program419(34),
				program420(35),
				program421(36),
				program422(37),
				program423(38),
				program424(39),
				program425(40),
				program426(41),
				program427(42),
				program428(43),
				program429(44),
				program430(45),
				program431(46),
				program432(47),
				program433(48),
				program434(49),
				program435(50),
				program436(51),
				program437(52),
				program438(53),
				program439(54),
				program440(55),
				program441(56),
				program442(57),
				program443(58),
				program444(59),
				program445(60),
				program446(61),
				program447(62),
				program448(63),
				program449(64),
				program450(65),
				program451(66),
				program452(67),
				program453(68),
				program454(69),
				program455(70),
				program456(71),
				program457(72),
				program458(73),
				program459(74),
				program460(75),
				program461(76),
				program462(77),
				program463(78),
				program464(79),
				program465(80),
				program466(81),
				program467(82),
				program468(83),
				program469(84),
				program470(85),
				program471(86),
				program472(87),
				program473(88),
				program474(89),
				program475(90),
				program476(91),
				program477(92),
				program478(93),
				program479(94),
				program480(95),
				program481(96),
				program482(97),
				program483(98),
				program484(99),
				program485(100),
				program486(101),
				program487(102),
				program488(103),
				program489(104),
				program490(105),
				program491(106),
				program492(107),
				program493(108),
				program494(109),
				program495(110),
				program496(111),
				program497(112),
				program498(113),
				program499(114),
				program500(115),
				program501(116),
				program502(117),
				program503(118),
				program504(119),
				program505(120),
				program506(121),
				program507(122),
				program508(123),
				program509(124),
				program510(125),
				program511(126),
				program512(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 10 }
		
		
		hwDslamNtvProgramMask5 OBJECT-TYPE
			SYNTAX BITS
				{
				program513(0),
				program514(1),
				program515(2),
				program516(3),
				program517(4),
				program518(5),
				program519(6),
				program520(7),
				program521(8),
				program522(9),
				program523(10),
				program524(11),
				program525(12),
				program526(13),
				program527(14),
				program528(15),
				program529(16),
				program530(17),
				program531(18),
				program532(19),
				program533(20),
				program534(21),
				program535(22),
				program536(23),
				program537(24),
				program538(25),
				program539(26),
				program540(27),
				program541(28),
				program542(29),
				program543(30),
				program544(31),
				program545(32),
				program546(33),
				program547(34),
				program548(35),
				program549(36),
				program550(37),
				program551(38),
				program552(39),
				program553(40),
				program554(41),
				program555(42),
				program556(43),
				program557(44),
				program558(45),
				program559(46),
				program560(47),
				program561(48),
				program562(49),
				program563(50),
				program564(51),
				program565(52),
				program566(53),
				program567(54),
				program568(55),
				program569(56),
				program570(57),
				program571(58),
				program572(59),
				program573(60),
				program574(61),
				program575(62),
				program576(63),
				program577(64),
				program578(65),
				program579(66),
				program580(67),
				program581(68),
				program582(69),
				program583(70),
				program584(71),
				program585(72),
				program586(73),
				program587(74),
				program588(75),
				program589(76),
				program590(77),
				program591(78),
				program592(79),
				program593(80),
				program594(81),
				program595(82),
				program596(83),
				program597(84),
				program598(85),
				program599(86),
				program600(87),
				program601(88),
				program602(89),
				program603(90),
				program604(91),
				program605(92),
				program606(93),
				program607(94),
				program608(95),
				program609(96),
				program610(97),
				program611(98),
				program612(99),
				program613(100),
				program614(101),
				program615(102),
				program616(103),
				program617(104),
				program618(105),
				program619(106),
				program620(107),
				program621(108),
				program622(109),
				program623(110),
				program624(111),
				program625(112),
				program626(113),
				program627(114),
				program628(115),
				program629(116),
				program630(117),
				program631(118),
				program632(119),
				program633(120),
				program634(121),
				program635(122),
				program636(123),
				program637(124),
				program638(125),
				program639(126),
				program640(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 11 }
		
		
		hwDslamNtvProgramMask6 OBJECT-TYPE
			SYNTAX BITS
				{
				program641(0),
				program642(1),
				program643(2),
				program644(3),
				program645(4),
				program646(5),
				program647(6),
				program648(7),
				program649(8),
				program650(9),
				program651(10),
				program652(11),
				program653(12),
				program654(13),
				program655(14),
				program656(15),
				program657(16),
				program658(17),
				program659(18),
				program660(19),
				program661(20),
				program662(21),
				program663(22),
				program664(23),
				program665(24),
				program666(25),
				program667(26),
				program668(27),
				program669(28),
				program670(29),
				program671(30),
				program672(31),
				program673(32),
				program674(33),
				program675(34),
				program676(35),
				program677(36),
				program678(37),
				program679(38),
				program680(39),
				program681(40),
				program682(41),
				program683(42),
				program684(43),
				program685(44),
				program686(45),
				program687(46),
				program688(47),
				program689(48),
				program690(49),
				program691(50),
				program692(51),
				program693(52),
				program694(53),
				program695(54),
				program696(55),
				program697(56),
				program698(57),
				program699(58),
				program700(59),
				program701(60),
				program702(61),
				program703(62),
				program704(63),
				program705(64),
				program706(65),
				program707(66),
				program708(67),
				program709(68),
				program710(69),
				program711(70),
				program712(71),
				program713(72),
				program714(73),
				program715(74),
				program716(75),
				program717(76),
				program718(77),
				program719(78),
				program720(79),
				program721(80),
				program722(81),
				program723(82),
				program724(83),
				program725(84),
				program726(85),
				program727(86),
				program728(87),
				program729(88),
				program730(89),
				program731(90),
				program732(91),
				program733(92),
				program734(93),
				program735(94),
				program736(95),
				program737(96),
				program738(97),
				program739(98),
				program740(99),
				program741(100),
				program742(101),
				program743(102),
				program744(103),
				program745(104),
				program746(105),
				program747(106),
				program748(107),
				program749(108),
				program750(109),
				program751(110),
				program752(111),
				program753(112),
				program754(113),
				program755(114),
				program756(115),
				program757(116),
				program758(117),
				program759(118),
				program760(119),
				program761(120),
				program762(121),
				program763(122),
				program764(123),
				program765(124),
				program766(125),
				program767(126),
				program768(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 12 }
		
		
		hwDslamNtvProgramMask7 OBJECT-TYPE
			SYNTAX BITS
				{
				program769(0),
				program770(1),
				program771(2),
				program772(3),
				program773(4),
				program774(5),
				program775(6),
				program776(7),
				program777(8),
				program778(9),
				program779(10),
				program780(11),
				program781(12),
				program782(13),
				program783(14),
				program784(15),
				program785(16),
				program786(17),
				program787(18),
				program788(19),
				program789(20),
				program790(21),
				program791(22),
				program792(23),
				program793(24),
				program794(25),
				program795(26),
				program796(27),
				program797(28),
				program798(29),
				program799(30),
				program800(31),
				program801(32),
				program802(33),
				program803(34),
				program804(35),
				program805(36),
				program806(37),
				program807(38),
				program808(39),
				program809(40),
				program810(41),
				program811(42),
				program812(43),
				program813(44),
				program814(45),
				program815(46),
				program816(47),
				program817(48),
				program818(49),
				program819(50),
				program820(51),
				program821(52),
				program822(53),
				program823(54),
				program824(55),
				program825(56),
				program826(57),
				program827(58),
				program828(59),
				program829(60),
				program830(61),
				program831(62),
				program832(63),
				program833(64),
				program834(65),
				program835(66),
				program836(67),
				program837(68),
				program838(69),
				program839(70),
				program840(71),
				program841(72),
				program842(73),
				program843(74),
				program844(75),
				program845(76),
				program846(77),
				program847(78),
				program848(79),
				program849(80),
				program850(81),
				program851(82),
				program852(83),
				program853(84),
				program854(85),
				program855(86),
				program856(87),
				program857(88),
				program858(89),
				program859(90),
				program860(91),
				program861(92),
				program862(93),
				program863(94),
				program864(95),
				program865(96),
				program866(97),
				program867(98),
				program868(99),
				program869(100),
				program870(101),
				program871(102),
				program872(103),
				program873(104),
				program874(105),
				program875(106),
				program876(107),
				program877(108),
				program878(109),
				program879(110),
				program880(111),
				program881(112),
				program882(113),
				program883(114),
				program884(115),
				program885(116),
				program886(117),
				program887(118),
				program888(119),
				program889(120),
				program890(121),
				program891(122),
				program892(123),
				program893(124),
				program894(125),
				program895(126),
				program896(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 13 }
		
		
		hwDslamNtvProgramMask8 OBJECT-TYPE
			SYNTAX BITS
				{
				program897(0),
				program898(1),
				program899(2),
				program900(3),
				program901(4),
				program902(5),
				program903(6),
				program904(7),
				program905(8),
				program906(9),
				program907(10),
				program908(11),
				program909(12),
				program910(13),
				program911(14),
				program912(15),
				program913(16),
				program914(17),
				program915(18),
				program916(19),
				program917(20),
				program918(21),
				program919(22),
				program920(23),
				program921(24),
				program922(25),
				program923(26),
				program924(27),
				program925(28),
				program926(29),
				program927(30),
				program928(31),
				program929(32),
				program930(33),
				program931(34),
				program932(35),
				program933(36),
				program934(37),
				program935(38),
				program936(39),
				program937(40),
				program938(41),
				program939(42),
				program940(43),
				program941(44),
				program942(45),
				program943(46),
				program944(47),
				program945(48),
				program946(49),
				program947(50),
				program948(51),
				program949(52),
				program950(53),
				program951(54),
				program952(55),
				program953(56),
				program954(57),
				program955(58),
				program956(59),
				program957(60),
				program958(61),
				program959(62),
				program960(63),
				program961(64),
				program962(65),
				program963(66),
				program964(67),
				program965(68),
				program966(69),
				program967(70),
				program968(71),
				program969(72),
				program970(73),
				program971(74),
				program972(75),
				program973(76),
				program974(77),
				program975(78),
				program976(79),
				program977(80),
				program978(81),
				program979(82),
				program980(83),
				program981(84),
				program982(85),
				program983(86),
				program984(87),
				program985(88),
				program986(89),
				program987(90),
				program988(91),
				program989(92),
				program990(93),
				program991(94),
				program992(95),
				program993(96),
				program994(97),
				program995(98),
				program996(99),
				program997(100),
				program998(101),
				program999(102),
				program1000(103),
				program1001(104),
				program1002(105),
				program1003(106),
				program1004(107),
				program1005(108),
				program1006(109),
				program1007(110),
				program1008(111),
				program1009(112),
				program1010(113),
				program1011(114),
				program1012(115),
				program1013(116),
				program1014(117),
				program1015(118),
				program1016(119),
				program1017(120),
				program1018(121),
				program1019(122),
				program1020(123),
				program1021(124),
				program1022(125),
				program1023(126),
				program1024(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 14 }
		
		
		hwDslamNtvProgramMask9 OBJECT-TYPE
			SYNTAX BITS
				{
				program1025(0),
				program1026(1),
				program1027(2),
				program1028(3),
				program1029(4),
				program1030(5),
				program1031(6),
				program1032(7),
				program1033(8),
				program1034(9),
				program1035(10),
				program1036(11),
				program1037(12),
				program1038(13),
				program1039(14),
				program1040(15),
				program1041(16),
				program1042(17),
				program1043(18),
				program1044(19),
				program1045(20),
				program1046(21),
				program1047(22),
				program1048(23),
				program1049(24),
				program1050(25),
				program1051(26),
				program1052(27),
				program1053(28),
				program1054(29),
				program1055(30),
				program1056(31),
				program1057(32),
				program1058(33),
				program1059(34),
				program1060(35),
				program1061(36),
				program1062(37),
				program1063(38),
				program1064(39),
				program1065(40),
				program1066(41),
				program1067(42),
				program1068(43),
				program1069(44),
				program1070(45),
				program1071(46),
				program1072(47),
				program1073(48),
				program1074(49),
				program1075(50),
				program1076(51),
				program1077(52),
				program1078(53),
				program1079(54),
				program1080(55),
				program1081(56),
				program1082(57),
				program1083(58),
				program1084(59),
				program1085(60),
				program1086(61),
				program1087(62),
				program1088(63),
				program1089(64),
				program1090(65),
				program1091(66),
				program1092(67),
				program1093(68),
				program1094(69),
				program1095(70),
				program1096(71),
				program1097(72),
				program1098(73),
				program1099(74),
				program1100(75),
				program1101(76),
				program1102(77),
				program1103(78),
				program1104(79),
				program1105(80),
				program1106(81),
				program1107(82),
				program1108(83),
				program1109(84),
				program1110(85),
				program1111(86),
				program1112(87),
				program1113(88),
				program1114(89),
				program1115(90),
				program1116(91),
				program1117(92),
				program1118(93),
				program1119(94),
				program1120(95),
				program1121(96),
				program1122(97),
				program1123(98),
				program1124(99),
				program1125(100),
				program1126(101),
				program1127(102),
				program1128(103),
				program1129(104),
				program1130(105),
				program1131(106),
				program1132(107),
				program1133(108),
				program1134(109),
				program1135(110),
				program1136(111),
				program1137(112),
				program1138(113),
				program1139(114),
				program1140(115),
				program1141(116),
				program1142(117),
				program1143(118),
				program1144(119),
				program1145(120),
				program1146(121),
				program1147(122),
				program1148(123),
				program1149(124),
				program1150(125),
				program1151(126),
				program1152(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 15 }
		
		
		hwDslamNtvProgramMask10 OBJECT-TYPE
			SYNTAX BITS
				{
				program1153(0),
				program1154(1),
				program1155(2),
				program1156(3),
				program1157(4),
				program1158(5),
				program1159(6),
				program1160(7),
				program1161(8),
				program1162(9),
				program1163(10),
				program1164(11),
				program1165(12),
				program1166(13),
				program1167(14),
				program1168(15),
				program1169(16),
				program1170(17),
				program1171(18),
				program1172(19),
				program1173(20),
				program1174(21),
				program1175(22),
				program1176(23),
				program1177(24),
				program1178(25),
				program1179(26),
				program1180(27),
				program1181(28),
				program1182(29),
				program1183(30),
				program1184(31),
				program1185(32),
				program1186(33),
				program1187(34),
				program1188(35),
				program1189(36),
				program1190(37),
				program1191(38),
				program1192(39),
				program1193(40),
				program1194(41),
				program1195(42),
				program1196(43),
				program1197(44),
				program1198(45),
				program1199(46),
				program1200(47),
				program1201(48),
				program1202(49),
				program1203(50),
				program1204(51),
				program1205(52),
				program1206(53),
				program1207(54),
				program1208(55),
				program1209(56),
				program1210(57),
				program1211(58),
				program1212(59),
				program1213(60),
				program1214(61),
				program1215(62),
				program1216(63),
				program1217(64),
				program1218(65),
				program1219(66),
				program1220(67),
				program1221(68),
				program1222(69),
				program1223(70),
				program1224(71),
				program1225(72),
				program1226(73),
				program1227(74),
				program1228(75),
				program1229(76),
				program1230(77),
				program1231(78),
				program1232(79),
				program1233(80),
				program1234(81),
				program1235(82),
				program1236(83),
				program1237(84),
				program1238(85),
				program1239(86),
				program1240(87),
				program1241(88),
				program1242(89),
				program1243(90),
				program1244(91),
				program1245(92),
				program1246(93),
				program1247(94),
				program1248(95),
				program1249(96),
				program1250(97),
				program1251(98),
				program1252(99),
				program1253(100),
				program1254(101),
				program1255(102),
				program1256(103),
				program1257(104),
				program1258(105),
				program1259(106),
				program1260(107),
				program1261(108),
				program1262(109),
				program1263(110),
				program1264(111),
				program1265(112),
				program1266(113),
				program1267(114),
				program1268(115),
				program1269(116),
				program1270(117),
				program1271(118),
				program1272(119),
				program1273(120),
				program1274(121),
				program1275(122),
				program1276(123),
				program1277(124),
				program1278(125),
				program1279(126),
				program1280(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 16 }
		
--  1.3.6.1.4.1.2011.6.28.19.1.17
		hwDslamNtvProgramMask11 OBJECT-TYPE
			SYNTAX BITS
				{
				program1281(0),
				program1282(1),
				program1283(2),
				program1284(3),
				program1285(4),
				program1286(5),
				program1287(6),
				program1288(7),
				program1289(8),
				program1290(9),
				program1291(10),
				program1292(11),
				program1293(12),
				program1294(13),
				program1295(14),
				program1296(15),
				program1297(16),
				program1298(17),
				program1299(18),
				program1300(19),
				program1301(20),
				program1302(21),
				program1303(22),
				program1304(23),
				program1305(24),
				program1306(25),
				program1307(26),
				program1308(27),
				program1309(28),
				program1310(29),
				program1311(30),
				program1312(31),
				program1313(32),
				program1314(33),
				program1315(34),
				program1316(35),
				program1317(36),
				program1318(37),
				program1319(38),
				program1320(39),
				program1321(40),
				program1322(41),
				program1323(42),
				program1324(43),
				program1325(44),
				program1326(45),
				program1327(46),
				program1328(47),
				program1329(48),
				program1330(49),
				program1331(50),
				program1332(51),
				program1333(52),
				program1334(53),
				program1335(54),
				program1336(55),
				program1337(56),
				program1338(57),
				program1339(58),
				program1340(59),
				program1341(60),
				program1342(61),
				program1343(62),
				program1344(63),
				program1345(64),
				program1346(65),
				program1347(66),
				program1348(67),
				program1349(68),
				program1350(69),
				program1351(70),
				program1352(71),
				program1353(72),
				program1354(73),
				program1355(74),
				program1356(75),
				program1357(76),
				program1358(77),
				program1359(78),
				program1360(79),
				program1361(80),
				program1362(81),
				program1363(82),
				program1364(83),
				program1365(84),
				program1366(85),
				program1367(86),
				program1368(87),
				program1369(88),
				program1370(89),
				program1371(90),
				program1372(91),
				program1373(92),
				program1374(93),
				program1375(94),
				program1376(95),
				program1377(96),
				program1378(97),
				program1379(98),
				program1380(99),
				program1381(100),
				program1382(101),
				program1383(102),
				program1384(103),
				program1385(104),
				program1386(105),
				program1387(106),
				program1388(107),
				program1389(108),
				program1390(109),
				program1391(110),
				program1392(111),
				program1393(112),
				program1394(113),
				program1395(114),
				program1396(115),
				program1397(116),
				program1398(117),
				program1399(118),
				program1400(119),
				program1401(120),
				program1402(121),
				program1403(122),
				program1404(123),
				program1405(124),
				program1406(125),
				program1407(126),
				program1408(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 17 }
		
		
		hwDslamNtvProgramMask12 OBJECT-TYPE
			SYNTAX BITS
				{
				program1409(0),
				program1410(1),
				program1411(2),
				program1412(3),
				program1413(4),
				program1414(5),
				program1415(6),
				program1416(7),
				program1417(8),
				program1418(9),
				program1419(10),
				program1420(11),
				program1421(12),
				program1422(13),
				program1423(14),
				program1424(15),
				program1425(16),
				program1426(17),
				program1427(18),
				program1428(19),
				program1429(20),
				program1430(21),
				program1431(22),
				program1432(23),
				program1433(24),
				program1434(25),
				program1435(26),
				program1436(27),
				program1437(28),
				program1438(29),
				program1439(30),
				program1440(31),
				program1441(32),
				program1442(33),
				program1443(34),
				program1444(35),
				program1445(36),
				program1446(37),
				program1447(38),
				program1448(39),
				program1449(40),
				program1450(41),
				program1451(42),
				program1452(43),
				program1453(44),
				program1454(45),
				program1455(46),
				program1456(47),
				program1457(48),
				program1458(49),
				program1459(50),
				program1460(51),
				program1461(52),
				program1462(53),
				program1463(54),
				program1464(55),
				program1465(56),
				program1466(57),
				program1467(58),
				program1468(59),
				program1469(60),
				program1470(61),
				program1471(62),
				program1472(63),
				program1473(64),
				program1474(65),
				program1475(66),
				program1476(67),
				program1477(68),
				program1478(69),
				program1479(70),
				program1480(71),
				program1481(72),
				program1482(73),
				program1483(74),
				program1484(75),
				program1485(76),
				program1486(77),
				program1487(78),
				program1488(79),
				program1489(80),
				program1490(81),
				program1491(82),
				program1492(83),
				program1493(84),
				program1494(85),
				program1495(86),
				program1496(87),
				program1497(88),
				program1498(89),
				program1499(90),
				program1500(91),
				program1501(92),
				program1502(93),
				program1503(94),
				program1504(95),
				program1505(96),
				program1506(97),
				program1507(98),
				program1508(99),
				program1509(100),
				program1510(101),
				program1511(102),
				program1512(103),
				program1513(104),
				program1514(105),
				program1515(106),
				program1516(107),
				program1517(108),
				program1518(109),
				program1519(110),
				program1520(111),
				program1521(112),
				program1522(113),
				program1523(114),
				program1524(115),
				program1525(116),
				program1526(117),
				program1527(118),
				program1528(119),
				program1529(120),
				program1530(121),
				program1531(122),
				program1532(123),
				program1533(124),
				program1534(125),
				program1535(126),
				program1536(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 18 }
		
		
		hwDslamNtvProgramMask13 OBJECT-TYPE
			SYNTAX BITS
				{
				program1537(0),
				program1538(1),
				program1539(2),
				program1540(3),
				program1541(4),
				program1542(5),
				program1543(6),
				program1544(7),
				program1545(8),
				program1546(9),
				program1547(10),
				program1548(11),
				program1549(12),
				program1550(13),
				program1551(14),
				program1552(15),
				program1553(16),
				program1554(17),
				program1555(18),
				program1556(19),
				program1557(20),
				program1558(21),
				program1559(22),
				program1560(23),
				program1561(24),
				program1562(25),
				program1563(26),
				program1564(27),
				program1565(28),
				program1566(29),
				program1567(30),
				program1568(31),
				program1569(32),
				program1570(33),
				program1571(34),
				program1572(35),
				program1573(36),
				program1574(37),
				program1575(38),
				program1576(39),
				program1577(40),
				program1578(41),
				program1579(42),
				program1580(43),
				program1581(44),
				program1582(45),
				program1583(46),
				program1584(47),
				program1585(48),
				program1586(49),
				program1587(50),
				program1588(51),
				program1589(52),
				program1590(53),
				program1591(54),
				program1592(55),
				program1593(56),
				program1594(57),
				program1595(58),
				program1596(59),
				program1597(60),
				program1598(61),
				program1599(62),
				program1600(63),
				program1601(64),
				program1602(65),
				program1603(66),
				program1604(67),
				program1605(68),
				program1606(69),
				program1607(70),
				program1608(71),
				program1609(72),
				program1610(73),
				program1611(74),
				program1612(75),
				program1613(76),
				program1614(77),
				program1615(78),
				program1616(79),
				program1617(80),
				program1618(81),
				program1619(82),
				program1620(83),
				program1621(84),
				program1622(85),
				program1623(86),
				program1624(87),
				program1625(88),
				program1626(89),
				program1627(90),
				program1628(91),
				program1629(92),
				program1630(93),
				program1631(94),
				program1632(95),
				program1633(96),
				program1634(97),
				program1635(98),
				program1636(99),
				program1637(100),
				program1638(101),
				program1639(102),
				program1640(103),
				program1641(104),
				program1642(105),
				program1643(106),
				program1644(107),
				program1645(108),
				program1646(109),
				program1647(110),
				program1648(111),
				program1649(112),
				program1650(113),
				program1651(114),
				program1652(115),
				program1653(116),
				program1654(117),
				program1655(118),
				program1656(119),
				program1657(120),
				program1658(121),
				program1659(122),
				program1660(123),
				program1661(124),
				program1662(125),
				program1663(126),
				program1664(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 19 }
		
		
		hwDslamNtvProgramMask14 OBJECT-TYPE
			SYNTAX BITS
				{
				program1665(0),
				program1666(1),
				program1667(2),
				program1668(3),
				program1669(4),
				program1670(5),
				program1671(6),
				program1672(7),
				program1673(8),
				program1674(9),
				program1675(10),
				program1676(11),
				program1677(12),
				program1678(13),
				program1679(14),
				program1680(15),
				program1681(16),
				program1682(17),
				program1683(18),
				program1684(19),
				program1685(20),
				program1686(21),
				program1687(22),
				program1688(23),
				program1689(24),
				program1690(25),
				program1691(26),
				program1692(27),
				program1693(28),
				program1694(29),
				program1695(30),
				program1696(31),
				program1697(32),
				program1698(33),
				program1699(34),
				program1700(35),
				program1701(36),
				program1702(37),
				program1703(38),
				program1704(39),
				program1705(40),
				program1706(41),
				program1707(42),
				program1708(43),
				program1709(44),
				program1710(45),
				program1711(46),
				program1712(47),
				program1713(48),
				program1714(49),
				program1715(50),
				program1716(51),
				program1717(52),
				program1718(53),
				program1719(54),
				program1720(55),
				program1721(56),
				program1722(57),
				program1723(58),
				program1724(59),
				program1725(60),
				program1726(61),
				program1727(62),
				program1728(63),
				program1729(64),
				program1730(65),
				program1731(66),
				program1732(67),
				program1733(68),
				program1734(69),
				program1735(70),
				program1736(71),
				program1737(72),
				program1738(73),
				program1739(74),
				program1740(75),
				program1741(76),
				program1742(77),
				program1743(78),
				program1744(79),
				program1745(80),
				program1746(81),
				program1747(82),
				program1748(83),
				program1749(84),
				program1750(85),
				program1751(86),
				program1752(87),
				program1753(88),
				program1754(89),
				program1755(90),
				program1756(91),
				program1757(92),
				program1758(93),
				program1759(94),
				program1760(95),
				program1761(96),
				program1762(97),
				program1763(98),
				program1764(99),
				program1765(100),
				program1766(101),
				program1767(102),
				program1768(103),
				program1769(104),
				program1770(105),
				program1771(106),
				program1772(107),
				program1773(108),
				program1774(109),
				program1775(110),
				program1776(111),
				program1777(112),
				program1778(113),
				program1779(114),
				program1780(115),
				program1781(116),
				program1782(117),
				program1783(118),
				program1784(119),
				program1785(120),
				program1786(121),
				program1787(122),
				program1788(123),
				program1789(124),
				program1790(125),
				program1791(126),
				program1792(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 20 }
		
		
		hwDslamNtvProgramMask15 OBJECT-TYPE
			SYNTAX BITS
				{
				program1793(0),
				program1794(1),
				program1795(2),
				program1796(3),
				program1797(4),
				program1798(5),
				program1799(6),
				program1800(7),
				program1801(8),
				program1802(9),
				program1803(10),
				program1804(11),
				program1805(12),
				program1806(13),
				program1807(14),
				program1808(15),
				program1809(16),
				program1810(17),
				program1811(18),
				program1812(19),
				program1813(20),
				program1814(21),
				program1815(22),
				program1816(23),
				program1817(24),
				program1818(25),
				program1819(26),
				program1820(27),
				program1821(28),
				program1822(29),
				program1823(30),
				program1824(31),
				program1825(32),
				program1826(33),
				program1827(34),
				program1828(35),
				program1829(36),
				program1830(37),
				program1831(38),
				program1832(39),
				program1833(40),
				program1834(41),
				program1835(42),
				program1836(43),
				program1837(44),
				program1838(45),
				program1839(46),
				program1840(47),
				program1841(48),
				program1842(49),
				program1843(50),
				program1844(51),
				program1845(52),
				program1846(53),
				program1847(54),
				program1848(55),
				program1849(56),
				program1850(57),
				program1851(58),
				program1852(59),
				program1853(60),
				program1854(61),
				program1855(62),
				program1856(63),
				program1857(64),
				program1858(65),
				program1859(66),
				program1860(67),
				program1861(68),
				program1862(69),
				program1863(70),
				program1864(71),
				program1865(72),
				program1866(73),
				program1867(74),
				program1868(75),
				program1869(76),
				program1870(77),
				program1871(78),
				program1872(79),
				program1873(80),
				program1874(81),
				program1875(82),
				program1876(83),
				program1877(84),
				program1878(85),
				program1879(86),
				program1880(87),
				program1881(88),
				program1882(89),
				program1883(90),
				program1884(91),
				program1885(92),
				program1886(93),
				program1887(94),
				program1888(95),
				program1889(96),
				program1890(97),
				program1891(98),
				program1892(99),
				program1893(100),
				program1894(101),
				program1895(102),
				program1896(103),
				program1897(104),
				program1898(105),
				program1899(106),
				program1900(107),
				program1901(108),
				program1902(109),
				program1903(110),
				program1904(111),
				program1905(112),
				program1906(113),
				program1907(114),
				program1908(115),
				program1909(116),
				program1910(117),
				program1911(118),
				program1912(119),
				program1913(120),
				program1914(121),
				program1915(122),
				program1916(123),
				program1917(124),
				program1918(125),
				program1919(126),
				program1920(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 21 }
		
		
		hwDslamNtvProgramMask16 OBJECT-TYPE
			SYNTAX BITS
				{
				program1921(0),
				program1922(1),
				program1923(2),
				program1924(3),
				program1925(4),
				program1926(5),
				program1927(6),
				program1928(7),
				program1929(8),
				program1930(9),
				program1931(10),
				program1932(11),
				program1933(12),
				program1934(13),
				program1935(14),
				program1936(15),
				program1937(16),
				program1938(17),
				program1939(18),
				program1940(19),
				program1941(20),
				program1942(21),
				program1943(22),
				program1944(23),
				program1945(24),
				program1946(25),
				program1947(26),
				program1948(27),
				program1949(28),
				program1950(29),
				program1951(30),
				program1952(31),
				program1953(32),
				program1954(33),
				program1955(34),
				program1956(35),
				program1957(36),
				program1958(37),
				program1959(38),
				program1960(39),
				program1961(40),
				program1962(41),
				program1963(42),
				program1964(43),
				program1965(44),
				program1966(45),
				program1967(46),
				program1968(47),
				program1969(48),
				program1970(49),
				program1971(50),
				program1972(51),
				program1973(52),
				program1974(53),
				program1975(54),
				program1976(55),
				program1977(56),
				program1978(57),
				program1979(58),
				program1980(59),
				program1981(60),
				program1982(61),
				program1983(62),
				program1984(63),
				program1985(64),
				program1986(65),
				program1987(66),
				program1988(67),
				program1989(68),
				program1990(69),
				program1991(70),
				program1992(71),
				program1993(72),
				program1994(73),
				program1995(74),
				program1996(75),
				program1997(76),
				program1998(77),
				program1999(78),
				program2000(79),
				program2001(80),
				program2002(81),
				program2003(82),
				program2004(83),
				program2005(84),
				program2006(85),
				program2007(86),
				program2008(87),
				program2009(88),
				program2010(89),
				program2011(90),
				program2012(91),
				program2013(92),
				program2014(93),
				program2015(94),
				program2016(95),
				program2017(96),
				program2018(97),
				program2019(98),
				program2020(99),
				program2021(100),
				program2022(101),
				program2023(102),
				program2024(103),
				program2025(104),
				program2026(105),
				program2027(106),
				program2028(107),
				program2029(108),
				program2030(109),
				program2031(110),
				program2032(111),
				program2033(112),
				program2034(113),
				program2035(114),
				program2036(115),
				program2037(116),
				program2038(117),
				program2039(118),
				program2040(119),
				program2041(120),
				program2042(121),
				program2043(122),
				program2044(123),
				program2045(124),
				program2046(125),
				program2047(126),
				program2048(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 22 }
		
		
		hwDslamNtvProgramMask17 OBJECT-TYPE
			SYNTAX BITS
				{
				program2049(0),
				program2050(1),
				program2051(2),
				program2052(3),
				program2053(4),
				program2054(5),
				program2055(6),
				program2056(7),
				program2057(8),
				program2058(9),
				program2059(10),
				program2060(11),
				program2061(12),
				program2062(13),
				program2063(14),
				program2064(15),
				program2065(16),
				program2066(17),
				program2067(18),
				program2068(19),
				program2069(20),
				program2070(21),
				program2071(22),
				program2072(23),
				program2073(24),
				program2074(25),
				program2075(26),
				program2076(27),
				program2077(28),
				program2078(29),
				program2079(30),
				program2080(31),
				program2081(32),
				program2082(33),
				program2083(34),
				program2084(35),
				program2085(36),
				program2086(37),
				program2087(38),
				program2088(39),
				program2089(40),
				program2090(41),
				program2091(42),
				program2092(43),
				program2093(44),
				program2094(45),
				program2095(46),
				program2096(47),
				program2097(48),
				program2098(49),
				program2099(50),
				program2100(51),
				program2101(52),
				program2102(53),
				program2103(54),
				program2104(55),
				program2105(56),
				program2106(57),
				program2107(58),
				program2108(59),
				program2109(60),
				program2110(61),
				program2111(62),
				program2112(63),
				program2113(64),
				program2114(65),
				program2115(66),
				program2116(67),
				program2117(68),
				program2118(69),
				program2119(70),
				program2120(71),
				program2121(72),
				program2122(73),
				program2123(74),
				program2124(75),
				program2125(76),
				program2126(77),
				program2127(78),
				program2128(79),
				program2129(80),
				program2130(81),
				program2131(82),
				program2132(83),
				program2133(84),
				program2134(85),
				program2135(86),
				program2136(87),
				program2137(88),
				program2138(89),
				program2139(90),
				program2140(91),
				program2141(92),
				program2142(93),
				program2143(94),
				program2144(95),
				program2145(96),
				program2146(97),
				program2147(98),
				program2148(99),
				program2149(100),
				program2150(101),
				program2151(102),
				program2152(103),
				program2153(104),
				program2154(105),
				program2155(106),
				program2156(107),
				program2157(108),
				program2158(109),
				program2159(110),
				program2160(111),
				program2161(112),
				program2162(113),
				program2163(114),
				program2164(115),
				program2165(116),
				program2166(117),
				program2167(118),
				program2168(119),
				program2169(120),
				program2170(121),
				program2171(122),
				program2172(123),
				program2173(124),
				program2174(125),
				program2175(126),
				program2176(127)
				}
			MAX-ACCESS read-write
			STATUS current
			DESCRIPTION
				"Program mask.
				Program source mask of right profile. If right profile include the program, the mask is 1.
				If right profile doesn't include the program,the mask is 0.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 23 }
		
		
		hwDslamNtvProgramMask18 OBJECT-TYPE
			SYNTAX BITS
				{
				program2177(0),
				program2178(1),
				program2179(2),
				program2180(3),
				program2181(4),
				program2182(5),
				program2183(6),
				program2184(7),
				program2185(8),
				program2186(9),
				program2187(10),
				program2188(11),
				program2189(12),
				program2190(13),
				program2191(14),
				program2192(15),
				program2193(16),
				program2194(17),
				program2195(18),
				program2196(19),
				program2197(20),
				program2198(21),
				program2199(22),
				program2200(23),
				program2201(24),
				program2202(25),
				program2203(26),
				program2204(27),
				program2205(28),
				program2206(29),
				program2207(30),
				program2208(31),
				program2209(32),
				program2210(33),
				program2211(34),
				program2212(35),
				program2213(36),
				program2214(37),
				program2215(38),
				program2216(39),
				program2217(40),
				program2218(41),
				program2219(42),
				program2220(43),
				program2221(44),
				program2222(45),
				program2223(46),
				program2224(47),
				program2225(48),
				program2226(49),
				program2227(50),
				program2228(51),
				program2229(52),
				program2230(53),
				program2231(54),
				program2232(55),
				program2233(56),
				program2234(57),
				program2235(58),
				program2236(59),
				program2237(60),
				program2238(61),
				program2239(62),
				program2240(63),
				program2241(64),
				program2242(65),
				program2243(66),
				program2244(67),
				program2245(68),
				program2246(69),
				program2247(70),
				program2248(71),
				program2249(72),
				program2250(73),
				program2251(74),
				program2252(75),
				program2253(76),
				program2254(77),
				program2255(78),
				program2256(79),
				program2257(80),
				program2258(81),
				program2259(82),
				program2260(83),
				program2261(84),
				program2262(85),
				program2263(86),
				program2264(87),
				program2265(88),
				program2266(89),
				program2267(90),
				program2268(91),
				program2269(92),
				program2270(93),
				program2271(94),
				program2272(95),
				program2273(96),
				program2274(97),
				program2275(98),
				program2276(99),
				program2277(100),
				program2278(101),
				program2279(102),
				program2280(103),
				program2281(104),
				program2282(105),
				program2283(106),
				program2284(107),
				program2285(108),
				program2286(109),
				program2287(110),
				program2288(111),
				program2289(112),
				program2290(113),
				program2291(114),
				program2292(115),
				program2293(116),
				program2294(117),
				program2295(118),
				program2296(119),
				program2297(120),
				program2298(121),
				program2299(122),
				program2300(123),
				program2301(124),
				program2302(125),
				program2303(126),
				program2304(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 24 }
		
		
		hwDslamNtvProgramMask19 OBJECT-TYPE
			SYNTAX BITS
				{
				program2305(0),
				program2306(1),
				program2307(2),
				program2308(3),
				program2309(4),
				program2310(5),
				program2311(6),
				program2312(7),
				program2313(8),
				program2314(9),
				program2315(10),
				program2316(11),
				program2317(12),
				program2318(13),
				program2319(14),
				program2320(15),
				program2321(16),
				program2322(17),
				program2323(18),
				program2324(19),
				program2325(20),
				program2326(21),
				program2327(22),
				program2328(23),
				program2329(24),
				program2330(25),
				program2331(26),
				program2332(27),
				program2333(28),
				program2334(29),
				program2335(30),
				program2336(31),
				program2337(32),
				program2338(33),
				program2339(34),
				program2340(35),
				program2341(36),
				program2342(37),
				program2343(38),
				program2344(39),
				program2345(40),
				program2346(41),
				program2347(42),
				program2348(43),
				program2349(44),
				program2350(45),
				program2351(46),
				program2352(47),
				program2353(48),
				program2354(49),
				program2355(50),
				program2356(51),
				program2357(52),
				program2358(53),
				program2359(54),
				program2360(55),
				program2361(56),
				program2362(57),
				program2363(58),
				program2364(59),
				program2365(60),
				program2366(61),
				program2367(62),
				program2368(63),
				program2369(64),
				program2370(65),
				program2371(66),
				program2372(67),
				program2373(68),
				program2374(69),
				program2375(70),
				program2376(71),
				program2377(72),
				program2378(73),
				program2379(74),
				program2380(75),
				program2381(76),
				program2382(77),
				program2383(78),
				program2384(79),
				program2385(80),
				program2386(81),
				program2387(82),
				program2388(83),
				program2389(84),
				program2390(85),
				program2391(86),
				program2392(87),
				program2393(88),
				program2394(89),
				program2395(90),
				program2396(91),
				program2397(92),
				program2398(93),
				program2399(94),
				program2400(95),
				program2401(96),
				program2402(97),
				program2403(98),
				program2404(99),
				program2405(100),
				program2406(101),
				program2407(102),
				program2408(103),
				program2409(104),
				program2410(105),
				program2411(106),
				program2412(107),
				program2413(108),
				program2414(109),
				program2415(110),
				program2416(111),
				program2417(112),
				program2418(113),
				program2419(114),
				program2420(115),
				program2421(116),
				program2422(117),
				program2423(118),
				program2424(119),
				program2425(120),
				program2426(121),
				program2427(122),
				program2428(123),
				program2429(124),
				program2430(125),
				program2431(126),
				program2432(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 25 }
		
		
		hwDslamNtvProgramMask20 OBJECT-TYPE
			SYNTAX BITS
				{
				program2433(0),
				program2434(1),
				program2435(2),
				program2436(3),
				program2437(4),
				program2438(5),
				program2439(6),
				program2440(7),
				program2441(8),
				program2442(9),
				program2443(10),
				program2444(11),
				program2445(12),
				program2446(13),
				program2447(14),
				program2448(15),
				program2449(16),
				program2450(17),
				program2451(18),
				program2452(19),
				program2453(20),
				program2454(21),
				program2455(22),
				program2456(23),
				program2457(24),
				program2458(25),
				program2459(26),
				program2460(27),
				program2461(28),
				program2462(29),
				program2463(30),
				program2464(31),
				program2465(32),
				program2466(33),
				program2467(34),
				program2468(35),
				program2469(36),
				program2470(37),
				program2471(38),
				program2472(39),
				program2473(40),
				program2474(41),
				program2475(42),
				program2476(43),
				program2477(44),
				program2478(45),
				program2479(46),
				program2480(47),
				program2481(48),
				program2482(49),
				program2483(50),
				program2484(51),
				program2485(52),
				program2486(53),
				program2487(54),
				program2488(55),
				program2489(56),
				program2490(57),
				program2491(58),
				program2492(59),
				program2493(60),
				program2494(61),
				program2495(62),
				program2496(63),
				program2497(64),
				program2498(65),
				program2499(66),
				program2500(67),
				program2501(68),
				program2502(69),
				program2503(70),
				program2504(71),
				program2505(72),
				program2506(73),
				program2507(74),
				program2508(75),
				program2509(76),
				program2510(77),
				program2511(78),
				program2512(79),
				program2513(80),
				program2514(81),
				program2515(82),
				program2516(83),
				program2517(84),
				program2518(85),
				program2519(86),
				program2520(87),
				program2521(88),
				program2522(89),
				program2523(90),
				program2524(91),
				program2525(92),
				program2526(93),
				program2527(94),
				program2528(95),
				program2529(96),
				program2530(97),
				program2531(98),
				program2532(99),
				program2533(100),
				program2534(101),
				program2535(102),
				program2536(103),
				program2537(104),
				program2538(105),
				program2539(106),
				program2540(107),
				program2541(108),
				program2542(109),
				program2543(110),
				program2544(111),
				program2545(112),
				program2546(113),
				program2547(114),
				program2548(115),
				program2549(116),
				program2550(117),
				program2551(118),
				program2552(119),
				program2553(120),
				program2554(121),
				program2555(122),
				program2556(123),
				program2557(124),
				program2558(125),
				program2559(126),
				program2560(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 26 }
		
		
		hwDslamNtvProgramMask21 OBJECT-TYPE
			SYNTAX BITS
				{
				program2561(0),
				program2562(1),
				program2563(2),
				program2564(3),
				program2565(4),
				program2566(5),
				program2567(6),
				program2568(7),
				program2569(8),
				program2570(9),
				program2571(10),
				program2572(11),
				program2573(12),
				program2574(13),
				program2575(14),
				program2576(15),
				program2577(16),
				program2578(17),
				program2579(18),
				program2580(19),
				program2581(20),
				program2582(21),
				program2583(22),
				program2584(23),
				program2585(24),
				program2586(25),
				program2587(26),
				program2588(27),
				program2589(28),
				program2590(29),
				program2591(30),
				program2592(31),
				program2593(32),
				program2594(33),
				program2595(34),
				program2596(35),
				program2597(36),
				program2598(37),
				program2599(38),
				program2600(39),
				program2601(40),
				program2602(41),
				program2603(42),
				program2604(43),
				program2605(44),
				program2606(45),
				program2607(46),
				program2608(47),
				program2609(48),
				program2610(49),
				program2611(50),
				program2612(51),
				program2613(52),
				program2614(53),
				program2615(54),
				program2616(55),
				program2617(56),
				program2618(57),
				program2619(58),
				program2620(59),
				program2621(60),
				program2622(61),
				program2623(62),
				program2624(63),
				program2625(64),
				program2626(65),
				program2627(66),
				program2628(67),
				program2629(68),
				program2630(69),
				program2631(70),
				program2632(71),
				program2633(72),
				program2634(73),
				program2635(74),
				program2636(75),
				program2637(76),
				program2638(77),
				program2639(78),
				program2640(79),
				program2641(80),
				program2642(81),
				program2643(82),
				program2644(83),
				program2645(84),
				program2646(85),
				program2647(86),
				program2648(87),
				program2649(88),
				program2650(89),
				program2651(90),
				program2652(91),
				program2653(92),
				program2654(93),
				program2655(94),
				program2656(95),
				program2657(96),
				program2658(97),
				program2659(98),
				program2660(99),
				program2661(100),
				program2662(101),
				program2663(102),
				program2664(103),
				program2665(104),
				program2666(105),
				program2667(106),
				program2668(107),
				program2669(108),
				program2670(109),
				program2671(110),
				program2672(111),
				program2673(112),
				program2674(113),
				program2675(114),
				program2676(115),
				program2677(116),
				program2678(117),
				program2679(118),
				program2680(119),
				program2681(120),
				program2682(121),
				program2683(122),
				program2684(123),
				program2685(124),
				program2686(125),
				program2687(126),
				program2688(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00."
			::= { hwDslamNtvRightProfileEntry 27 }
		
		
		hwDslamNtvProgramMask22 OBJECT-TYPE
			SYNTAX BITS
				{
				program2689(0),
				program2690(1),
				program2691(2),
				program2692(3),
				program2693(4),
				program2694(5),
				program2695(6),
				program2696(7),
				program2697(8),
				program2698(9),
				program2699(10),
				program2700(11),
				program2701(12),
				program2702(13),
				program2703(14),
				program2704(15),
				program2705(16),
				program2706(17),
				program2707(18),
				program2708(19),
				program2709(20),
				program2710(21),
				program2711(22),
				program2712(23),
				program2713(24),
				program2714(25),
				program2715(26),
				program2716(27),
				program2717(28),
				program2718(29),
				program2719(30),
				program2720(31),
				program2721(32),
				program2722(33),
				program2723(34),
				program2724(35),
				program2725(36),
				program2726(37),
				program2727(38),
				program2728(39),
				program2729(40),
				program2730(41),
				program2731(42),
				program2732(43),
				program2733(44),
				program2734(45),
				program2735(46),
				program2736(47),
				program2737(48),
				program2738(49),
				program2739(50),
				program2740(51),
				program2741(52),
				program2742(53),
				program2743(54),
				program2744(55),
				program2745(56),
				program2746(57),
				program2747(58),
				program2748(59),
				program2749(60),
				program2750(61),
				program2751(62),
				program2752(63),
				program2753(64),
				program2754(65),
				program2755(66),
				program2756(67),
				program2757(68),
				program2758(69),
				program2759(70),
				program2760(71),
				program2761(72),
				program2762(73),
				program2763(74),
				program2764(75),
				program2765(76),
				program2766(77),
				program2767(78),
				program2768(79),
				program2769(80),
				program2770(81),
				program2771(82),
				program2772(83),
				program2773(84),
				program2774(85),
				program2775(86),
				program2776(87),
				program2777(88),
				program2778(89),
				program2779(90),
				program2780(91),
				program2781(92),
				program2782(93),
				program2783(94),
				program2784(95),
				program2785(96),
				program2786(97),
				program2787(98),
				program2788(99),
				program2789(100),
				program2790(101),
				program2791(102),
				program2792(103),
				program2793(104),
				program2794(105),
				program2795(106),
				program2796(107),
				program2797(108),
				program2798(109),
				program2799(110),
				program2800(111),
				program2801(112),
				program2802(113),
				program2803(114),
				program2804(115),
				program2805(116),
				program2806(117),
				program2807(118),
				program2808(119),
				program2809(120),
				program2810(121),
				program2811(122),
				program2812(123),
				program2813(124),
				program2814(125),
				program2815(126),
				program2816(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00.
				"
			::= { hwDslamNtvRightProfileEntry 28 }
		
		
		hwDslamNtvProgramMask23 OBJECT-TYPE
			SYNTAX BITS
				{
				program2817(0),
				program2818(1),
				program2819(2),
				program2820(3),
				program2821(4),
				program2822(5),
				program2823(6),
				program2824(7),
				program2825(8),
				program2826(9),
				program2827(10),
				program2828(11),
				program2829(12),
				program2830(13),
				program2831(14),
				program2832(15),
				program2833(16),
				program2834(17),
				program2835(18),
				program2836(19),
				program2837(20),
				program2838(21),
				program2839(22),
				program2840(23),
				program2841(24),
				program2842(25),
				program2843(26),
				program2844(27),
				program2845(28),
				program2846(29),
				program2847(30),
				program2848(31),
				program2849(32),
				program2850(33),
				program2851(34),
				program2852(35),
				program2853(36),
				program2854(37),
				program2855(38),
				program2856(39),
				program2857(40),
				program2858(41),
				program2859(42),
				program2860(43),
				program2861(44),
				program2862(45),
				program2863(46),
				program2864(47),
				program2865(48),
				program2866(49),
				program2867(50),
				program2868(51),
				program2869(52),
				program2870(53),
				program2871(54),
				program2872(55),
				program2873(56),
				program2874(57),
				program2875(58),
				program2876(59),
				program2877(60),
				program2878(61),
				program2879(62),
				program2880(63),
				program2881(64),
				program2882(65),
				program2883(66),
				program2884(67),
				program2885(68),
				program2886(69),
				program2887(70),
				program2888(71),
				program2889(72),
				program2890(73),
				program2891(74),
				program2892(75),
				program2893(76),
				program2894(77),
				program2895(78),
				program2896(79),
				program2897(80),
				program2898(81),
				program2899(82),
				program2900(83),
				program2901(84),
				program2902(85),
				program2903(86),
				program2904(87),
				program2905(88),
				program2906(89),
				program2907(90),
				program2908(91),
				program2909(92),
				program2910(93),
				program2911(94),
				program2912(95),
				program2913(96),
				program2914(97),
				program2915(98),
				program2916(99),
				program2917(100),
				program2918(101),
				program2919(102),
				program2920(103),
				program2921(104),
				program2922(105),
				program2923(106),
				program2924(107),
				program2925(108),
				program2926(109),
				program2927(110),
				program2928(111),
				program2929(112),
				program2930(113),
				program2931(114),
				program2932(115),
				program2933(116),
				program2934(117),
				program2935(118),
				program2936(119),
				program2937(120),
				program2938(121),
				program2939(122),
				program2940(123),
				program2941(124),
				program2942(125),
				program2943(126),
				program2944(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00.
				"
			::= { hwDslamNtvRightProfileEntry 29 }
		
		
		hwDslamNtvProgramMask24 OBJECT-TYPE
			SYNTAX BITS
				{
				program2945(0),
				program2946(1),
				program2947(2),
				program2948(3),
				program2949(4),
				program2950(5),
				program2951(6),
				program2952(7),
				program2953(8),
				program2954(9),
				program2955(10),
				program2956(11),
				program2957(12),
				program2958(13),
				program2959(14),
				program2960(15),
				program2961(16),
				program2962(17),
				program2963(18),
				program2964(19),
				program2965(20),
				program2966(21),
				program2967(22),
				program2968(23),
				program2969(24),
				program2970(25),
				program2971(26),
				program2972(27),
				program2973(28),
				program2974(29),
				program2975(30),
				program2976(31),
				program2977(32),
				program2978(33),
				program2979(34),
				program2980(35),
				program2981(36),
				program2982(37),
				program2983(38),
				program2984(39),
				program2985(40),
				program2986(41),
				program2987(42),
				program2988(43),
				program2989(44),
				program2990(45),
				program2991(46),
				program2992(47),
				program2993(48),
				program2994(49),
				program2995(50),
				program2996(51),
				program2997(52),
				program2998(53),
				program2999(54),
				program3000(55),
				program3001(56),
				program3002(57),
				program3003(58),
				program3004(59),
				program3005(60),
				program3006(61),
				program3007(62),
				program3008(63),
				program3009(64),
				program3010(65),
				program3011(66),
				program3012(67),
				program3013(68),
				program3014(69),
				program3015(70),
				program3016(71),
				program3017(72),
				program3018(73),
				program3019(74),
				program3020(75),
				program3021(76),
				program3022(77),
				program3023(78),
				program3024(79),
				program3025(80),
				program3026(81),
				program3027(82),
				program3028(83),
				program3029(84),
				program3030(85),
				program3031(86),
				program3032(87),
				program3033(88),
				program3034(89),
				program3035(90),
				program3036(91),
				program3037(92),
				program3038(93),
				program3039(94),
				program3040(95),
				program3041(96),
				program3042(97),
				program3043(98),
				program3044(99),
				program3045(100),
				program3046(101),
				program3047(102),
				program3048(103),
				program3049(104),
				program3050(105),
				program3051(106),
				program3052(107),
				program3053(108),
				program3054(109),
				program3055(110),
				program3056(111),
				program3057(112),
				program3058(113),
				program3059(114),
				program3060(115),
				program3061(116),
				program3062(117),
				program3063(118),
				program3064(119),
				program3065(120),
				program3066(121),
				program3067(122),
				program3068(123),
				program3069(124),
				program3070(125),
				program3071(126),
				program3072(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00.
				"
			::= { hwDslamNtvRightProfileEntry 30 }
		
		
		hwDslamNtvProgramMask25 OBJECT-TYPE
			SYNTAX BITS
				{
				program3073(0),
				program3074(1),
				program3075(2),
				program3076(3),
				program3077(4),
				program3078(5),
				program3079(6),
				program3080(7),
				program3081(8),
				program3082(9),
				program3083(10),
				program3084(11),
				program3085(12),
				program3086(13),
				program3087(14),
				program3088(15),
				program3089(16),
				program3090(17),
				program3091(18),
				program3092(19),
				program3093(20),
				program3094(21),
				program3095(22),
				program3096(23),
				program3097(24),
				program3098(25),
				program3099(26),
				program3100(27),
				program3101(28),
				program3102(29),
				program3103(30),
				program3104(31),
				program3105(32),
				program3106(33),
				program3107(34),
				program3108(35),
				program3109(36),
				program3110(37),
				program3111(38),
				program3112(39),
				program3113(40),
				program3114(41),
				program3115(42),
				program3116(43),
				program3117(44),
				program3118(45),
				program3119(46),
				program3120(47),
				program3121(48),
				program3122(49),
				program3123(50),
				program3124(51),
				program3125(52),
				program3126(53),
				program3127(54),
				program3128(55),
				program3129(56),
				program3130(57),
				program3131(58),
				program3132(59),
				program3133(60),
				program3134(61),
				program3135(62),
				program3136(63),
				program3137(64),
				program3138(65),
				program3139(66),
				program3140(67),
				program3141(68),
				program3142(69),
				program3143(70),
				program3144(71),
				program3145(72),
				program3146(73),
				program3147(74),
				program3148(75),
				program3149(76),
				program3150(77),
				program3151(78),
				program3152(79),
				program3153(80),
				program3154(81),
				program3155(82),
				program3156(83),
				program3157(84),
				program3158(85),
				program3159(86),
				program3160(87),
				program3161(88),
				program3162(89),
				program3163(90),
				program3164(91),
				program3165(92),
				program3166(93),
				program3167(94),
				program3168(95),
				program3169(96),
				program3170(97),
				program3171(98),
				program3172(99),
				program3173(100),
				program3174(101),
				program3175(102),
				program3176(103),
				program3177(104),
				program3178(105),
				program3179(106),
				program3180(107),
				program3181(108),
				program3182(109),
				program3183(110),
				program3184(111),
				program3185(112),
				program3186(113),
				program3187(114),
				program3188(115),
				program3189(116),
				program3190(117),
				program3191(118),
				program3192(119),
				program3193(120),
				program3194(121),
				program3195(122),
				program3196(123),
				program3197(124),
				program3198(125),
				program3199(126),
				program3200(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00.
				"
			::= { hwDslamNtvRightProfileEntry 31 }
		
		
		hwDslamNtvProgramMask26 OBJECT-TYPE
			SYNTAX BITS
				{
				program3201(0),
				program3202(1),
				program3203(2),
				program3204(3),
				program3205(4),
				program3206(5),
				program3207(6),
				program3208(7),
				program3209(8),
				program3210(9),
				program3211(10),
				program3212(11),
				program3213(12),
				program3214(13),
				program3215(14),
				program3216(15),
				program3217(16),
				program3218(17),
				program3219(18),
				program3220(19),
				program3221(20),
				program3222(21),
				program3223(22),
				program3224(23),
				program3225(24),
				program3226(25),
				program3227(26),
				program3228(27),
				program3229(28),
				program3230(29),
				program3231(30),
				program3232(31),
				program3233(32),
				program3234(33),
				program3235(34),
				program3236(35),
				program3237(36),
				program3238(37),
				program3239(38),
				program3240(39),
				program3241(40),
				program3242(41),
				program3243(42),
				program3244(43),
				program3245(44),
				program3246(45),
				program3247(46),
				program3248(47),
				program3249(48),
				program3250(49),
				program3251(50),
				program3252(51),
				program3253(52),
				program3254(53),
				program3255(54),
				program3256(55),
				program3257(56),
				program3258(57),
				program3259(58),
				program3260(59),
				program3261(60),
				program3262(61),
				program3263(62),
				program3264(63),
				program3265(64),
				program3266(65),
				program3267(66),
				program3268(67),
				program3269(68),
				program3270(69),
				program3271(70),
				program3272(71),
				program3273(72),
				program3274(73),
				program3275(74),
				program3276(75),
				program3277(76),
				program3278(77),
				program3279(78),
				program3280(79),
				program3281(80),
				program3282(81),
				program3283(82),
				program3284(83),
				program3285(84),
				program3286(85),
				program3287(86),
				program3288(87),
				program3289(88),
				program3290(89),
				program3291(90),
				program3292(91),
				program3293(92),
				program3294(93),
				program3295(94),
				program3296(95),
				program3297(96),
				program3298(97),
				program3299(98),
				program3300(99),
				program3301(100),
				program3302(101),
				program3303(102),
				program3304(103),
				program3305(104),
				program3306(105),
				program3307(106),
				program3308(107),
				program3309(108),
				program3310(109),
				program3311(110),
				program3312(111),
				program3313(112),
				program3314(113),
				program3315(114),
				program3316(115),
				program3317(116),
				program3318(117),
				program3319(118),
				program3320(119),
				program3321(120),
				program3322(121),
				program3323(122),
				program3324(123),
				program3325(124),
				program3326(125),
				program3327(126),
				program3328(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10. 
               If the profile has the corresponding program forbidden right, the two masks should be 11.
				           If the profile has not the corresponding program right, the two masks should be 00.
				"
			::= { hwDslamNtvRightProfileEntry 32 }
		
		
		hwDslamNtvProgramMask27 OBJECT-TYPE
			SYNTAX BITS
				{
				program3329(0),
				program3330(1),
				program3331(2),
				program3332(3),
				program3333(4),
				program3334(5),
				program3335(6),
				program3336(7),
				program3337(8),
				program3338(9),
				program3339(10),
				program3340(11),
				program3341(12),
				program3342(13),
				program3343(14),
				program3344(15),
				program3345(16),
				program3346(17),
				program3347(18),
				program3348(19),
				program3349(20),
				program3350(21),
				program3351(22),
				program3352(23),
				program3353(24),
				program3354(25),
				program3355(26),
				program3356(27),
				program3357(28),
				program3358(29),
				program3359(30),
				program3360(31),
				program3361(32),
				program3362(33),
				program3363(34),
				program3364(35),
				program3365(36),
				program3366(37),
				program3367(38),
				program3368(39),
				program3369(40),
				program3370(41),
				program3371(42),
				program3372(43),
				program3373(44),
				program3374(45),
				program3375(46),
				program3376(47),
				program3377(48),
				program3378(49),
				program3379(50),
				program3380(51),
				program3381(52),
				program3382(53),
				program3383(54),
				program3384(55),
				program3385(56),
				program3386(57),
				program3387(58),
				program3388(59),
				program3389(60),
				program3390(61),
				program3391(62),
				program3392(63),
				program3393(64),
				program3394(65),
				program3395(66),
				program3396(67),
				program3397(68),
				program3398(69),
				program3399(70),
				program3400(71),
				program3401(72),
				program3402(73),
				program3403(74),
				program3404(75),
				program3405(76),
				program3406(77),
				program3407(78),
				program3408(79),
				program3409(80),
				program3410(81),
				program3411(82),
				program3412(83),
				program3413(84),
				program3414(85),
				program3415(86),
				program3416(87),
				program3417(88),
				program3418(89),
				program3419(90),
				program3420(91),
				program3421(92),
				program3422(93),
				program3423(94),
				program3424(95),
				program3425(96),
				program3426(97),
				program3427(98),
				program3428(99),
				program3429(100),
				program3430(101),
				program3431(102),
				program3432(103),
				program3433(104),
				program3434(105),
				program3435(106),
				program3436(107),
				program3437(108),
				program3438(109),
				program3439(110),
				program3440(111),
				program3441(112),
				program3442(113),
				program3443(114),
				program3444(115),
				program3445(116),
				program3446(117),
				program3447(118),
				program3448(119),
				program3449(120),
				program3450(121),
				program3451(122),
				program3452(123),
				program3453(124),
				program3454(125),
				program3455(126),
				program3456(127)
				}
			MAX-ACCESS read-write
			STATUS current
			DESCRIPTION
				"Program mask.
				Program source mask of right profile. 
               Two bits indicate one program's right.
               So if the profile has the corresponding program watch right, the two masks should be 01.
               If the profile has the corresponding program preview right, the two masks should be 10.
               If the profile has the corresponding program forbidden right, the two masks should be 11.
				           If the profile has not the corresponding program right, the two masks should be 00.
				"
			::= { hwDslamNtvRightProfileEntry 33 }
		
		
		hwDslamNtvProgramMask28 OBJECT-TYPE
			SYNTAX BITS
				{
				program3457(0),
				program3458(1),
				program3459(2),
				program3460(3),
				program3461(4),
				program3462(5),
				program3463(6),
				program3464(7),
				program3465(8),
				program3466(9),
				program3467(10),
				program3468(11),
				program3469(12),
				program3470(13),
				program3471(14),
				program3472(15),
				program3473(16),
				program3474(17),
				program3475(18),
				program3476(19),
				program3477(20),
				program3478(21),
				program3479(22),
				program3480(23),
				program3481(24),
				program3482(25),
				program3483(26),
				program3484(27),
				program3485(28),
				program3486(29),
				program3487(30),
				program3488(31),
				program3489(32),
				program3490(33),
				program3491(34),
				program3492(35),
				program3493(36),
				program3494(37),
				program3495(38),
				program3496(39),
				program3497(40),
				program3498(41),
				program3499(42),
				program3500(43),
				program3501(44),
				program3502(45),
				program3503(46),
				program3504(47),
				program3505(48),
				program3506(49),
				program3507(50),
				program3508(51),
				program3509(52),
				program3510(53),
				program3511(54),
				program3512(55),
				program3513(56),
				program3514(57),
				program3515(58),
				program3516(59),
				program3517(60),
				program3518(61),
				program3519(62),
				program3520(63),
				program3521(64),
				program3522(65),
				program3523(66),
				program3524(67),
				program3525(68),
				program3526(69),
				program3527(70),
				program3528(71),
				program3529(72),
				program3530(73),
				program3531(74),
				program3532(75),
				program3533(76),
				program3534(77),
				program3535(78),
				program3536(79),
				program3537(80),
				program3538(81),
				program3539(82),
				program3540(83),
				program3541(84),
				program3542(85),
				program3543(86),
				program3544(87),
				program3545(88),
				program3546(89),
				program3547(90),
				program3548(91),
				program3549(92),
				program3550(93),
				program3551(94),
				program3552(95),
				program3553(96),
				program3554(97),
				program3555(98),
				program3556(99),
				program3557(100),
				program3558(101),
				program3559(102),
				program3560(103),
				program3561(104),
				program3562(105),
				program3563(106),
				program3564(107),
				program3565(108),
				program3566(109),
				program3567(110),
				program3568(111),
				program3569(112),
				program3570(113),
				program3571(114),
				program3572(115),
				program3573(116),
				program3574(117),
				program3575(118),
				program3576(119),
				program3577(120),
				program3578(121),
				program3579(122),
				program3580(123),
				program3581(124),
				program3582(125),
				program3583(126),
				program3584(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00.
				"
			::= { hwDslamNtvRightProfileEntry 34 }
		
		
		hwDslamNtvProgramMask29 OBJECT-TYPE
			SYNTAX BITS
				{
				program3585(0),
				program3586(1),
				program3587(2),
				program3588(3),
				program3589(4),
				program3590(5),
				program3591(6),
				program3592(7),
				program3593(8),
				program3594(9),
				program3595(10),
				program3596(11),
				program3597(12),
				program3598(13),
				program3599(14),
				program3600(15),
				program3601(16),
				program3602(17),
				program3603(18),
				program3604(19),
				program3605(20),
				program3606(21),
				program3607(22),
				program3608(23),
				program3609(24),
				program3610(25),
				program3611(26),
				program3612(27),
				program3613(28),
				program3614(29),
				program3615(30),
				program3616(31),
				program3617(32),
				program3618(33),
				program3619(34),
				program3620(35),
				program3621(36),
				program3622(37),
				program3623(38),
				program3624(39),
				program3625(40),
				program3626(41),
				program3627(42),
				program3628(43),
				program3629(44),
				program3630(45),
				program3631(46),
				program3632(47),
				program3633(48),
				program3634(49),
				program3635(50),
				program3636(51),
				program3637(52),
				program3638(53),
				program3639(54),
				program3640(55),
				program3641(56),
				program3642(57),
				program3643(58),
				program3644(59),
				program3645(60),
				program3646(61),
				program3647(62),
				program3648(63),
				program3649(64),
				program3650(65),
				program3651(66),
				program3652(67),
				program3653(68),
				program3654(69),
				program3655(70),
				program3656(71),
				program3657(72),
				program3658(73),
				program3659(74),
				program3660(75),
				program3661(76),
				program3662(77),
				program3663(78),
				program3664(79),
				program3665(80),
				program3666(81),
				program3667(82),
				program3668(83),
				program3669(84),
				program3670(85),
				program3671(86),
				program3672(87),
				program3673(88),
				program3674(89),
				program3675(90),
				program3676(91),
				program3677(92),
				program3678(93),
				program3679(94),
				program3680(95),
				program3681(96),
				program3682(97),
				program3683(98),
				program3684(99),
				program3685(100),
				program3686(101),
				program3687(102),
				program3688(103),
				program3689(104),
				program3690(105),
				program3691(106),
				program3692(107),
				program3693(108),
				program3694(109),
				program3695(110),
				program3696(111),
				program3697(112),
				program3698(113),
				program3699(114),
				program3700(115),
				program3701(116),
				program3702(117),
				program3703(118),
				program3704(119),
				program3705(120),
				program3706(121),
				program3707(122),
				program3708(123),
				program3709(124),
				program3710(125),
				program3711(126),
				program3712(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00.
				"
			::= { hwDslamNtvRightProfileEntry 35 }
		
		
		hwDslamNtvProgramMask30 OBJECT-TYPE
			SYNTAX BITS
				{
				program3713(0),
				program3714(1),
				program3715(2),
				program3716(3),
				program3717(4),
				program3718(5),
				program3719(6),
				program3720(7),
				program3721(8),
				program3722(9),
				program3723(10),
				program3724(11),
				program3725(12),
				program3726(13),
				program3727(14),
				program3728(15),
				program3729(16),
				program3730(17),
				program3731(18),
				program3732(19),
				program3733(20),
				program3734(21),
				program3735(22),
				program3736(23),
				program3737(24),
				program3738(25),
				program3739(26),
				program3740(27),
				program3741(28),
				program3742(29),
				program3743(30),
				program3744(31),
				program3745(32),
				program3746(33),
				program3747(34),
				program3748(35),
				program3749(36),
				program3750(37),
				program3751(38),
				program3752(39),
				program3753(40),
				program3754(41),
				program3755(42),
				program3756(43),
				program3757(44),
				program3758(45),
				program3759(46),
				program3760(47),
				program3761(48),
				program3762(49),
				program3763(50),
				program3764(51),
				program3765(52),
				program3766(53),
				program3767(54),
				program3768(55),
				program3769(56),
				program3770(57),
				program3771(58),
				program3772(59),
				program3773(60),
				program3774(61),
				program3775(62),
				program3776(63),
				program3777(64),
				program3778(65),
				program3779(66),
				program3780(67),
				program3781(68),
				program3782(69),
				program3783(70),
				program3784(71),
				program3785(72),
				program3786(73),
				program3787(74),
				program3788(75),
				program3789(76),
				program3790(77),
				program3791(78),
				program3792(79),
				program3793(80),
				program3794(81),
				program3795(82),
				program3796(83),
				program3797(84),
				program3798(85),
				program3799(86),
				program3800(87),
				program3801(88),
				program3802(89),
				program3803(90),
				program3804(91),
				program3805(92),
				program3806(93),
				program3807(94),
				program3808(95),
				program3809(96),
				program3810(97),
				program3811(98),
				program3812(99),
				program3813(100),
				program3814(101),
				program3815(102),
				program3816(103),
				program3817(104),
				program3818(105),
				program3819(106),
				program3820(107),
				program3821(108),
				program3822(109),
				program3823(110),
				program3824(111),
				program3825(112),
				program3826(113),
				program3827(114),
				program3828(115),
				program3829(116),
				program3830(117),
				program3831(118),
				program3832(119),
				program3833(120),
				program3834(121),
				program3835(122),
				program3836(123),
				program3837(124),
				program3838(125),
				program3839(126),
				program3840(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00.
				"
			::= { hwDslamNtvRightProfileEntry 36 }
		
		
		hwDslamNtvProgramMask31 OBJECT-TYPE
			SYNTAX BITS
				{
				program3841(0),
				program3842(1),
				program3843(2),
				program3844(3),
				program3845(4),
				program3846(5),
				program3847(6),
				program3848(7),
				program3849(8),
				program3850(9),
				program3851(10),
				program3852(11),
				program3853(12),
				program3854(13),
				program3855(14),
				program3856(15),
				program3857(16),
				program3858(17),
				program3859(18),
				program3860(19),
				program3861(20),
				program3862(21),
				program3863(22),
				program3864(23),
				program3865(24),
				program3866(25),
				program3867(26),
				program3868(27),
				program3869(28),
				program3870(29),
				program3871(30),
				program3872(31),
				program3873(32),
				program3874(33),
				program3875(34),
				program3876(35),
				program3877(36),
				program3878(37),
				program3879(38),
				program3880(39),
				program3881(40),
				program3882(41),
				program3883(42),
				program3884(43),
				program3885(44),
				program3886(45),
				program3887(46),
				program3888(47),
				program3889(48),
				program3890(49),
				program3891(50),
				program3892(51),
				program3893(52),
				program3894(53),
				program3895(54),
				program3896(55),
				program3897(56),
				program3898(57),
				program3899(58),
				program3900(59),
				program3901(60),
				program3902(61),
				program3903(62),
				program3904(63),
				program3905(64),
				program3906(65),
				program3907(66),
				program3908(67),
				program3909(68),
				program3910(69),
				program3911(70),
				program3912(71),
				program3913(72),
				program3914(73),
				program3915(74),
				program3916(75),
				program3917(76),
				program3918(77),
				program3919(78),
				program3920(79),
				program3921(80),
				program3922(81),
				program3923(82),
				program3924(83),
				program3925(84),
				program3926(85),
				program3927(86),
				program3928(87),
				program3929(88),
				program3930(89),
				program3931(90),
				program3932(91),
				program3933(92),
				program3934(93),
				program3935(94),
				program3936(95),
				program3937(96),
				program3938(97),
				program3939(98),
				program3940(99),
				program3941(100),
				program3942(101),
				program3943(102),
				program3944(103),
				program3945(104),
				program3946(105),
				program3947(106),
				program3948(107),
				program3949(108),
				program3950(109),
				program3951(110),
				program3952(111),
				program3953(112),
				program3954(113),
				program3955(114),
				program3956(115),
				program3957(116),
				program3958(117),
				program3959(118),
				program3960(119),
				program3961(120),
				program3962(121),
				program3963(122),
				program3964(123),
				program3965(124),
				program3966(125),
				program3967(126),
				program3968(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00.
				"
			::= { hwDslamNtvRightProfileEntry 37 }
		
		
		hwDslamNtvProgramMask32 OBJECT-TYPE
			SYNTAX BITS
				{
				program3969(0),
				program3970(1),
				program3971(2),
				program3972(3),
				program3973(4),
				program3974(5),
				program3975(6),
				program3976(7),
				program3977(8),
				program3978(9),
				program3979(10),
				program3980(11),
				program3981(12),
				program3982(13),
				program3983(14),
				program3984(15),
				program3985(16),
				program3986(17),
				program3987(18),
				program3988(19),
				program3989(20),
				program3990(21),
				program3991(22),
				program3992(23),
				program3993(24),
				program3994(25),
				program3995(26),
				program3996(27),
				program3997(28),
				program3998(29),
				program3999(30),
				program4000(31),
				program4001(32),
				program4002(33),
				program4003(34),
				program4004(35),
				program4005(36),
				program4006(37),
				program4007(38),
				program4008(39),
				program4009(40),
				program4010(41),
				program4011(42),
				program4012(43),
				program4013(44),
				program4014(45),
				program4015(46),
				program4016(47),
				program4017(48),
				program4018(49),
				program4019(50),
				program4020(51),
				program4021(52),
				program4022(53),
				program4023(54),
				program4024(55),
				program4025(56),
				program4026(57),
				program4027(58),
				program4028(59),
				program4029(60),
				program4030(61),
				program4031(62),
				program4032(63),
				program4033(64),
				program4034(65),
				program4035(66),
				program4036(67),
				program4037(68),
				program4038(69),
				program4039(70),
				program4040(71),
				program4041(72),
				program4042(73),
				program4043(74),
				program4044(75),
				program4045(76),
				program4046(77),
				program4047(78),
				program4048(79),
				program4049(80),
				program4050(81),
				program4051(82),
				program4052(83),
				program4053(84),
				program4054(85),
				program4055(86),
				program4056(87),
				program4057(88),
				program4058(89),
				program4059(90),
				program4060(91),
				program4061(92),
				program4062(93),
				program4063(94),
				program4064(95),
				program4065(96),
				program4066(97),
				program4067(98),
				program4068(99),
				program4069(100),
				program4070(101),
				program4071(102),
				program4072(103),
				program4073(104),
				program4074(105),
				program4075(106),
				program4076(107),
				program4077(108),
				program4078(109),
				program4079(110),
				program4080(111),
				program4081(112),
				program4082(113),
				program4083(114),
				program4084(115),
				program4085(116),
				program4086(117),
				program4087(118),
				program4088(119),
				program4089(120),
				program4090(121),
				program4091(122),
				program4092(123),
				program4093(124),
				program4094(125),
				program4095(126),
				program4096(127)
				}
			MAX-ACCESS read-write
			STATUS current
			DESCRIPTION
				"Program mask.
				Program source mask of right profile. If right profile include the program, the mask is 1.
               Two bits indicate one program's right.
               So if the profile has the corresponding program watch right, the two masks should be 01.
               If the profile has the corresponding program preview right, the two masks should be 10.
               If the profile has the corresponding program forbidden right, the two masks should be 11.
				           If the profile has not the corresponding program right, the two masks should be 00.
				"
			::= { hwDslamNtvRightProfileEntry 38 }
		
        hwDslamNtvRightProfileUserRefCount OBJECT-TYPE
			SYNTAX Integer32
			MAX-ACCESS read-only
			STATUS current
			DESCRIPTION
				"User references of the profile in profile-based."
			::= { hwDslamNtvRightProfileEntry 39 }
   -- -------------------------------------------------------------------------   
   --        Traffic Statistics Table
   -- -------------------------------------------------------------------------    
   hwDslamNtvChannelTrafficTable    OBJECT-TYPE
        SYNTAX          SEQUENCE OF HwDslamNtvChannelTrafficEntry
        MAX-ACCESS      not-accessible
        STATUS          current
    DESCRIPTION
    "Traffic statistics table"
    ::= { hwDslamNtv 20 }
    
    hwDslamNtvChannelTrafficEntry    OBJECT-TYPE
        SYNTAX             HwDslamNtvChannelTrafficEntry
        MAX-ACCESS         not-accessible
        STATUS             current
    DESCRIPTION
    "Traffic statistics entity"
    INDEX   { 
               hwDslamNtvChannelIndex
            }
    ::= { hwDslamNtvChannelTrafficTable  1 }


   HwDslamNtvChannelTrafficEntry    ::= SEQUENCE  {
            hwDslamNtvAdminStatus          INTEGER,
            hwDslamNtvTrafficValue        Integer32
          }

    hwDslamNtvAdminStatus       OBJECT-TYPE
           SYNTAX       INTEGER
           {
               up(1),
               down(2)
           }
           MAX-ACCESS   read-write
           STATUS       current
           DESCRIPTION
               "Administerial state.
               The Administerial state of video multicast traffic statistics."
    ::= { hwDslamNtvChannelTrafficEntry 1}
    
    hwDslamNtvTrafficValue        OBJECT-TYPE
           SYNTAX       Integer32
           UNITS        "kbps"           
           MAX-ACCESS   read-only
           STATUS       current
           DESCRIPTION
               "Traffic Value.
               The value of video multicast traffic statistics."
    ::= { hwDslamNtvChannelTrafficEntry 2}       

   -- -------------------------------------------------------------------------   
   --        Port IGMP Parameter Config Table
   -- -------------------------------------------------------------------------       
    hwDslamNtvIgmpConfigTable    OBJECT-TYPE
        SYNTAX          SEQUENCE OF HwDslamNtvIgmpConfigEntry
        MAX-ACCESS      not-accessible
        STATUS          current
        DESCRIPTION
				"Port IGMP Parameter config table."
    ::= { hwDslamNtv 21 }
    
    hwDslamNtvIgmpConfigEntry    OBJECT-TYPE
        SYNTAX          HwDslamNtvIgmpConfigEntry
        MAX-ACCESS      not-accessible
        STATUS          current
        DESCRIPTION
            "Port IGMP Parameter config entry"
    INDEX   { 
               hwDslamNtvUserIndex
            }
    ::= { hwDslamNtvIgmpConfigTable  1 }

   HwDslamNtvIgmpConfigEntry    ::= SEQUENCE  {
            hwDslamNtvIgmpQuickLeave              TruthValue,
            
          }
    
    hwDslamNtvIgmpQuickLeave        OBJECT-TYPE
           SYNTAX      TruthValue    
           MAX-ACCESS  read-write
           STATUS      current
           DESCRIPTION
               "Quick Leave.
               When Quick Leave is true,IGMP-Proxy make user 
               offline as soon as receiveing Leave packet instead 
				of sending  specific queries."
           DEFVAL { 2 }
    ::= { hwDslamNtvIgmpConfigEntry 1}

        
    
    -- -------------------------------------------------------------------------   
   --        Program Log Statistics Table
   -- -------------------------------------------------------------------------    
   hwDslamNtvProgramLogTable    OBJECT-TYPE
        SYNTAX          SEQUENCE OF HwDslamNtvProgramLogEntry
        MAX-ACCESS      not-accessible
        STATUS          current
        DESCRIPTION
            "Program Log statistics table"
    ::= { hwDslamNtv 22 }
    
    hwDslamNtvProgramLogEntry    OBJECT-TYPE
        SYNTAX             HwDslamNtvProgramLogEntry
        MAX-ACCESS         not-accessible
        STATUS             current
        DESCRIPTION
            "Program Log statistics entity"
    INDEX   { 
               hwDslamNtvProgramLogStartTime,
               hwDslamNtvProgramLogEndTime,
               hwDslamNtvProgramLogIP
            }
    ::= { hwDslamNtvProgramLogTable  1 }

   HwDslamNtvProgramLogEntry    ::= SEQUENCE  {
            hwDslamNtvProgramLogStartTime     DateAndTime,
            hwDslamNtvProgramLogEndTime       DateAndTime,
            hwDslamNtvProgramLogIP            IpAddress,
            hwDslamNtvProgramLogUserNum       Integer32, 
            hwDslamNtvProgramLogTotalTime     Integer32
          }

    hwDslamNtvProgramLogStartTime       OBJECT-TYPE
           SYNTAX       DateAndTime
           MAX-ACCESS   read-only
           STATUS       current
           DESCRIPTION
               "Start time.
               Start time of the program log Statistics."
    ::= { hwDslamNtvProgramLogEntry 1}
    
    hwDslamNtvProgramLogEndTime       OBJECT-TYPE
           SYNTAX       DateAndTime
           MAX-ACCESS   read-only
           STATUS       current
           DESCRIPTION
               "End time.
               End time of the program log Statistics."
    ::= { hwDslamNtvProgramLogEntry 2}  
    
    hwDslamNtvProgramLogIP        OBJECT-TYPE
           SYNTAX       IpAddress
           MAX-ACCESS   read-only
           STATUS       current
           DESCRIPTION
               "Program IP address."
    ::= { hwDslamNtvProgramLogEntry 3}     
    
    hwDslamNtvProgramLogUserNum        OBJECT-TYPE
           SYNTAX       Integer32
           MAX-ACCESS   read-only
           STATUS       current
           DESCRIPTION
               "Total user number."
    ::= { hwDslamNtvProgramLogEntry 4}    
    
    hwDslamNtvProgramLogTotalTime        OBJECT-TYPE
           SYNTAX       Integer32
           MAX-ACCESS   read-only
           STATUS       current
           DESCRIPTION
               "Total time."
    ::= { hwDslamNtvProgramLogEntry 5} 

   -- -------------------------------------------------------------------------   
   --        Upport Management Table
   -- -------------------------------------------------------------------------       
    hwDslamNtvUpportTable    OBJECT-TYPE
        SYNTAX          SEQUENCE OF HwDslamNtvUpportEntry
        MAX-ACCESS      not-accessible
        STATUS          current
        DESCRIPTION
            "Upport management table"
    ::= { hwDslamNtv 23 }
    
    hwDslamNtvUpportEntry    OBJECT-TYPE
        SYNTAX          HwDslamNtvUpportEntry
        MAX-ACCESS      not-accessible
        STATUS          current
        DESCRIPTION
            "Upport management entity."
        INDEX { 
                  hwDslamNtvUpportTblIndex
              }
    ::= { hwDslamNtvUpportTable  1 }

   HwDslamNtvUpportEntry    ::= SEQUENCE  {
            hwDslamNtvUpportTblIndex         Integer32,
            hwDslamNtvUpportTblRowStatus     RowStatus, 
            hwDslamNtvUpportTblInter         Integer32, 
            hwDslamNtvUpportTblVlan          Integer32,
            hwDslamNtvUpportTblHostIP        IpAddress,
            hwDslamNtvUpportTblRouterVersion  INTEGER,
            hwDslamNtvUpportTblAllocBandwidth INTEGER,
            hwDslamNtvUpportTblUsedBandwidth  DisplayString,     
            hwDslamNtvUpportTblPortSpeed      INTEGER,
            hwDslamNtvUpportTblMFSResult      Integer32         
          }
                                    
    hwDslamNtvUpportTblIndex        OBJECT-TYPE
           SYNTAX       Integer32(1..1024)
           MAX-ACCESS   read-create
           STATUS       current
           DESCRIPTION
				"Upport index."
    ::= { hwDslamNtvUpportEntry 1}   
    
    hwDslamNtvUpportTblRowStatus        OBJECT-TYPE
           SYNTAX       RowStatus
           MAX-ACCESS   read-create
           STATUS       current
           DESCRIPTION
               "Row status.
				Add or delete a table item."
    ::= { hwDslamNtvUpportEntry 2}   
    
    hwDslamNtvUpportTblInter   OBJECT-TYPE
       SYNTAX       Integer32
       MAX-ACCESS   read-create
       STATUS       current
       DESCRIPTION
				"Up Port.Frame/Slot/Port"
   ::= { hwDslamNtvUpportEntry 3 }
   
   hwDslamNtvUpportTblVlan   OBJECT-TYPE
       SYNTAX       Integer32(1..4093)
       MAX-ACCESS   read-create
       STATUS       current
       DESCRIPTION
				"VlanId of Up Port."
   ::= { hwDslamNtvUpportEntry 4 }
    
    hwDslamNtvUpportTblHostIP        OBJECT-TYPE
           SYNTAX       IpAddress
           MAX-ACCESS   read-create
           STATUS       current
           DESCRIPTION
               "IGMP host IP address.
				If IP address of Upport-interface is not configue, IGMP-host-IP-address will be used to send IGMP packets."
    ::= { hwDslamNtvUpportEntry 5}

    hwDslamNtvUpportTblRouterVersion  OBJECT-TYPE
           SYNTAX       INTEGER (1..3)
           MAX-ACCESS   read-only
           STATUS       current
           DESCRIPTION
				"the current IGMP Version of  up port.It is include V1/V2/V3 version."
    ::= { hwDslamNtvUpportEntry 6}

    hwDslamNtvUpportTblAllocBandwidth OBJECT-TYPE
           SYNTAX       INTEGER (1..100)
           MAX-ACCESS   read-create
           STATUS       current
           DESCRIPTION
               "the uplink port alloc multicast bandwidth. unit:kbps"
    ::= { hwDslamNtvUpportEntry 7}
    
    hwDslamNtvUpportTblUsedBandwidth OBJECT-TYPE
           SYNTAX       DisplayString
           MAX-ACCESS   read-only
           STATUS       current
           DESCRIPTION
               "it has been used multicase bandwidth of up port. unit:kbps"
    ::= { hwDslamNtvUpportEntry 8}  
    
    hwDslamNtvUpportTblPortSpeed OBJECT-TYPE
           SYNTAX       INTEGER
           MAX-ACCESS   read-only
           STATUS       current
           DESCRIPTION
               "The ethernet port speed. unit:kbps"
               ::= { hwDslamNtvUpportEntry 9}
               
    hwDslamNtvUpportTblMFSResult OBJECT-TYPE
	  SYNTAX Integer32
	  MAX-ACCESS read-only
	  STATUS current
	  DESCRIPTION
	  "
	  Get the Multicast Flow Statics result of an appointed uplink port."
	  ::= { hwDslamNtvUpportEntry 10 } 

   -- -------------------------------------------------------------------------   
   --        IP cascade  Table
   -- -------------------------------------------------------------------------       
    hwDslamNtvIpCascadeTable    OBJECT-TYPE
        SYNTAX          SEQUENCE OF HwDslamNtvIpCascadeEntry
        MAX-ACCESS      not-accessible
        STATUS          current
        DESCRIPTION
            "IP cascade  Table"
    ::= { hwDslamNtv 24 }
    
    hwDslamNtvIpCascadeEntry    OBJECT-TYPE
        SYNTAX          HwDslamNtvIpCascadeEntry
        MAX-ACCESS      not-accessible
        STATUS          current
        DESCRIPTION
            "IP cascade entity."
        INDEX { 
                  hwDslamntvIpCascadePortIndex
              }
    ::= { hwDslamNtvIpCascadeTable  1 }

   HwDslamNtvIpCascadeEntry    ::= SEQUENCE  {
            hwDslamntvIpCascadePortIndex             INTEGER,
            hwDslamNtvIpCascadePortRowStatus         RowStatus, 
            hwDslamntvIpCascadePortFrameSlotPort     INTEGER, 
            hwDslamntvIpCascadeProgramWatchingCount  Integer32,     
            hwDslamntvIpCascadePortStaticJoin        TruthValue,
            hwDslamntvIpCascadePortQuickLeave        TruthValue,
            hwDslamntvIpCascadePortMode		     INTEGER,
            hwDslamntvIpCascadePortProcAfterMismatch INTEGER,
            hwDslamNtvIpCascadePortMatchPara         Integer32,
            hwDslamntvIpCascadePortControlWord       TruthValue,
            hwDslamNtvIpCascadePortMatchPara2        Integer32
          }
                                    
    hwDslamntvIpCascadePortIndex        OBJECT-TYPE
           SYNTAX       INTEGER(1..2048)
			MAX-ACCESS read-only
           STATUS       current
           DESCRIPTION
				"IP cascade port index."
    ::= { hwDslamNtvIpCascadeEntry 1}   
    
    hwDslamNtvIpCascadePortRowStatus        OBJECT-TYPE
           SYNTAX       RowStatus
           MAX-ACCESS   read-create
           STATUS       current
           DESCRIPTION
               "Row status.
				Add or delete a table item."
    ::= { hwDslamNtvIpCascadeEntry 2}   

    hwDslamntvIpCascadePortFrameSlotPort   OBJECT-TYPE
           SYNTAX       INTEGER
           MAX-ACCESS   read-create
           STATUS       current
           DESCRIPTION
				"Combination of the IP cascade port's frame/slot/port."
    ::= { hwDslamNtvIpCascadeEntry 3}   
    
    hwDslamntvIpCascadeProgramWatchingCount   OBJECT-TYPE
       SYNTAX       Integer32
       MAX-ACCESS   read-only
       STATUS       current
       DESCRIPTION
				"Count of the IP cascade port watching program."
   ::= { hwDslamNtvIpCascadeEntry 4 }
   
   hwDslamntvIpCascadePortStaticJoin   OBJECT-TYPE
 	   SYNTAX TruthValue
 	   MAX-ACCESS read-create
 	   STATUS current
 	   DESCRIPTION
 	       "StaticJoin attribute of the IP cascade port."
 	::= { hwDslamNtvIpCascadeEntry 5 }
		
   hwDslamntvIpCascadePortQuickLeave   OBJECT-TYPE
       SYNTAX TruthValue
       MAX-ACCESS read-create
       STATUS current
       DESCRIPTION
           "QuickLeave attribute of the IP cascade port."
    ::= { hwDslamNtvIpCascadeEntry 6 }

	    hwDslamntvIpCascadePortMode   OBJECT-TYPE
            SYNTAX INTEGER
		        {
		        snooping(0),
                        discard(1),
		        forwarding(2)
		        }
            MAX-ACCESS read-create
            STATUS current
            DESCRIPTION
                "snooping mode of the IP cascade port."
            ::= { hwDslamNtvIpCascadeEntry 7 }

   hwDslamntvIpCascadePortProcAfterMismatch   OBJECT-TYPE
            SYNTAX INTEGER
		        {
		        transparent(0),
                        discard(1)
		        }
            MAX-ACCESS read-create
            STATUS current
            DESCRIPTION
                "The process mode of the IP cascade port while matching IGMP unsuccessfully."
            ::= { hwDslamNtvIpCascadeEntry 8 }
            
   hwDslamNtvIpCascadePortMatchPara OBJECT-TYPE
		SYNTAX Integer32
		MAX-ACCESS read-write
		STATUS current
		DESCRIPTION
			"the GemPortID of GPON port
			"
		::= { hwDslamNtvIpCascadeEntry 9 }   
		
	hwDslamntvIpCascadePortControlWord OBJECT-TYPE
       SYNTAX TruthValue
       MAX-ACCESS read-create
       STATUS current
       DESCRIPTION
           "Should find out the VLAN that the packet carried from the cascade port."
    ::= { hwDslamNtvIpCascadeEntry 10 }

   hwDslamNtvIpCascadePortMatchPara2 OBJECT-TYPE
		SYNTAX Integer32
		MAX-ACCESS read-write
		STATUS current
		DESCRIPTION
			"the Gem Index of GPON port
			"
		::= { hwDslamNtvIpCascadeEntry 11 }   

  -- -------------------------------------------------------------------------   
   --        User Run State Table
   -- -------------------------------------------------------------------------       	
    hwDslamNtvUserRunStateTable OBJECT-TYPE
        SYNTAX SEQUENCE OF HwDslamNtvUserRunStateEntry
        MAX-ACCESS not-accessible
        STATUS current
        DESCRIPTION
            "NTV user run state table.One port has a user group."
    ::= { hwDslamNtv 25 }

    hwDslamNtvUserRunStateEntry OBJECT-TYPE
        SYNTAX HwDslamNtvUserRunStateEntry
        MAX-ACCESS not-accessible
        STATUS current
        DESCRIPTION
            "NTV user run state entry"
        INDEX { 
        		hwDslamNtvUserIndex,
        		hwDslamNtvUserRunStateProgramIndex
         	  }
    ::= { hwDslamNtvUserRunStateTable 1 }

    HwDslamNtvUserRunStateEntry ::=
        SEQUENCE { 
                    hwDslamNtvUserRunStateProgramIndex		Integer32,
                    hwDslamNtvUserRunStateProgramStatus		INTEGER
                 }

    hwDslamNtvUserRunStateProgramIndex OBJECT-TYPE
        SYNTAX Integer32 (1..2048)
        MAX-ACCESS read-only
        STATUS current
        DESCRIPTION
				"Program index."
    ::= { hwDslamNtvUserRunStateEntry 1 }
				
    hwDslamNtvUserRunStateProgramStatus OBJECT-TYPE
        SYNTAX INTEGER { watch(1),preview(2),invalid(3) }
        MAX-ACCESS read-create
        STATUS current
        DESCRIPTION
            "the status of the corresponding program above.
             If the this value is 1(watch), it means the corresponding program is being watched.
             If the this value is 2(preview), it means the corresponding program is being previewed.
				If the this value is 3(invalid), it means the corresponding program is invalid."
    ::= { hwDslamNtvUserRunStateEntry 2 }

    -- -----------------------------------------------------------------------
    -- user profile table
    -- ------------------------------------------------------------------------ 
    hwDslamNtvUserProfileTable    OBJECT-TYPE
        SYNTAX          SEQUENCE OF HwDslamNtvUserProfileEntry
        MAX-ACCESS      not-accessible
        STATUS          current
        DESCRIPTION
            "User Profile table"
    ::= { hwDslamNtv 26 }
    
    hwDslamNtvUserProfileEntry    OBJECT-TYPE
        SYNTAX          HwDslamNtvUserProfileEntry
        MAX-ACCESS      not-accessible
        STATUS          current
        DESCRIPTION
            "User Profile entity."
        INDEX { 
                  hwDslamNtvUserIndex,
                  hwDslamNtvUserProfileIndex
              }
    ::= { hwDslamNtvUserProfileTable  1 }
    
    HwDslamNtvUserProfileEntry    ::= SEQUENCE  {
            hwDslamNtvUserProfileIndex            Integer32,
            hwDslamNtvUserProfileTblRowStatus     RowStatus
        }

    hwDslamNtvUserProfileIndex        OBJECT-TYPE
           SYNTAX       Integer32(1..1024)
           MAX-ACCESS   read-only
           STATUS       current
           DESCRIPTION
               "Right profile index.
               The index of user right profile.When user select the right profile,it can watch the program in the
				right profile only"
    ::= { hwDslamNtvUserProfileEntry 1}
    
    hwDslamNtvUserProfileTblRowStatus      OBJECT-TYPE
           SYNTAX       RowStatus
           MAX-ACCESS   read-create
           STATUS       current
           DESCRIPTION
               "Row status.
				Add or delete a table item."
    ::= { hwDslamNtvUserProfileEntry 2} 
    
    
    
   -- -------------------------------------------------------------------------   
   --        User attribute Profile Management Table
   -- -------------------------------------------------------------------------       
    hwDslamNtvAttrProfileTable    OBJECT-TYPE
        SYNTAX          SEQUENCE OF HwDslamNtvAttrProfileEntry
        MAX-ACCESS      not-accessible
        STATUS          current
        DESCRIPTION
            "User Attribute profile management table"
    ::= { hwDslamNtv 27 }
    
    hwDslamNtvAttrProfileEntry    OBJECT-TYPE
        SYNTAX         HwDslamNtvAttrProfileEntry
        MAX-ACCESS         not-accessible
        STATUS         current
    DESCRIPTION
    "User Attribute profile management entity"
    INDEX   { 
               hwDslamNtvAttrProfileIndex
            }
    ::= { hwDslamNtvAttrProfileTable  1 }

    HwDslamNtvAttrProfileEntry    ::= SEQUENCE  {
            hwDslamNtvAttrProfileIndex           Integer32,
            hwDslamNtvAttrProfileName            DisplayString,
            hwDslamNtvAttrProfileQuickLeave      TruthValue,
            hwDslamNtvAttrProfileAuthorization   Integer32,
            hwDslamNtvAttrProfileMaxBandwidth    Integer32,
            hwDslamNtvAttrProfileMaxGroups       Integer32,
            hwDslamNtvAttrProfileEnableLog       Integer32,
            hwDslamNtvAttrProfileAuthFailCut     Integer32,
            hwDslamNtvAttrProfilePacketMode      Integer32
        }

    hwDslamNtvAttrProfileIndex        OBJECT-TYPE
           SYNTAX       Integer32
           MAX-ACCESS   read-only
           STATUS       current
           DESCRIPTION
               "The user attribute profile index"
    ::= { hwDslamNtvAttrProfileEntry 1}

    hwDslamNtvAttrProfileName		OBJECT-TYPE
           SYNTAX       DisplayString
           MAX-ACCESS   read-create
           STATUS       current
           DESCRIPTION
               "The user attribute profile name,It is the keywords of attribute profile"
    ::= { hwDslamNtvAttrProfileEntry 2}

    hwDslamNtvAttrProfileQuickLeave	OBJECT-TYPE
           SYNTAX       TruthValue
           MAX-ACCESS   read-create
           STATUS       current
           DESCRIPTION
               "When the user send igmp leave packet,if the value is true(1),then the multicast table is delete,
               and the system donot send the special query packet to user.if the value is false(2),then the system need 
               send the special query packet to user."
    ::= { hwDslamNtvAttrProfileEntry 3}

    hwDslamNtvAttrProfileAuthorization	OBJECT-TYPE
           SYNTAX       Integer32
           MAX-ACCESS   read-create
           STATUS       current
           DESCRIPTION
               "The user's authorization ,{ auth(0),no-auth(1) }"
    ::= { hwDslamNtvAttrProfileEntry 4}

    hwDslamNtvAttrProfileMaxBandwidth	OBJECT-TYPE
           SYNTAX       Integer32
           MAX-ACCESS   read-create
           STATUS       current
           DESCRIPTION
               "The user  permit the max bandwidth to traffic multicast"
    ::= { hwDslamNtvAttrProfileEntry 5}

    hwDslamNtvAttrProfileMaxGroups	OBJECT-TYPE
           SYNTAX       Integer32
           MAX-ACCESS   read-create
           STATUS       current
           DESCRIPTION
               "The max channel number that a user can watch at the same time."
    ::= { hwDslamNtvAttrProfileEntry 6}

    hwDslamNtvAttrProfileEnableLog	OBJECT-TYPE
           SYNTAX       Integer32
           MAX-ACCESS   read-create
           STATUS       current
           DESCRIPTION
               "Log switch. When the log switch is on(1), 
                the system will record the events of starting or stopping watching programs of the user.
                When the log switch is off(2), the system will stop recording."
    ::= { hwDslamNtvAttrProfileEntry 7}

    hwDslamNtvAttrProfileAuthFailCut	OBJECT-TYPE
           SYNTAX       Integer32
           MAX-ACCESS   read-create
           STATUS       current
           DESCRIPTION
               "When the user authorization fail,if the value is discard(0), the user's igmp packet is discard,
               and if the value is forward(1),the user's igmp packet is send to upper router }"
    ::= { hwDslamNtvAttrProfileEntry 8}

    hwDslamNtvAttrProfilePacketMode	OBJECT-TYPE
           SYNTAX       Integer32
           MAX-ACCESS   read-only
           STATUS       current
           DESCRIPTION
               "The packet proccess mode when receive the user's igmp packet,if snooping(0),then config the user multicast
               table,and send this igmp packet to upper router. if discard(1), then discard the user's igmp packet.
               if forwarding(2),the send user's igmp packet to upper router,donot config user multicast table"
    ::= { hwDslamNtvAttrProfileEntry 9}

    -- ------------------------------------------------------------------------
    --       System Management Parameter
    -- ------------------------------------------------------------------------ 
    hwDslamNtvSourceCheck        OBJECT-TYPE
           SYNTAX       TruthValue
           MAX-ACCESS   read-write
           STATUS       current
           DESCRIPTION
               "Source-IP-check administer state.
                The true(enable)/ false(disable) state for Source-IP-check.
		Used to enable/disable Source-IP-check to control whether source-IP 
		must be match when forwarding multicast data."
    ::= { hwDslamNtv 31} 
    
    hwDslamNtvDefaultSource        OBJECT-TYPE
           SYNTAX       IpAddress
           MAX-ACCESS   read-write
           STATUS       current
           DESCRIPTION
               "Default multicast-source for program.
               The program which is not bind to multicast-source when added to 
               program room will be bind to this default source."
    ::= { hwDslamNtv 32}
     
    hwDslamNtvReportInterval   OBJECT-TYPE
       SYNTAX       Integer32(1..5000)
       UNITS        "seconds"
       MAX-ACCESS   read-write
       STATUS       current
       DESCRIPTION
           "Unsolicited report interval.
           The frequency at which Unsolicited IGMP Host-Report packets 
				are transmitted to up-device."
       DEFVAL { 10 }
   ::= { hwDslamNtv 33 }

    hwDslamNtvUpportWorkMode   OBJECT-TYPE
       SYNTAX       INTEGER { program(1),mstp(2),broadcast(3),protect(4),default(5),query-detect(6) }
       MAX-ACCESS   read-write
       STATUS       current
       DESCRIPTION
		   "Upport work mode."
   ::= { hwDslamNtv 34 }

    hwDslamNtvV1RouterTimerout   OBJECT-TYPE
       SYNTAX       Integer32(1..5000)
       UNITS        "seconds"
       MAX-ACCESS   read-write
       STATUS       current
       DESCRIPTION
           "The Version 1 Router Present Timeout is how long a host must wait
            after hearing a Version 1 Query before it may send any IGMPv2
				messages."
       DEFVAL { 400 }
   ::= { hwDslamNtv 35 }

    hwDslamNtvLastMemberQueryCount   OBJECT-TYPE
       SYNTAX       Integer32(1..10)
       MAX-ACCESS   read-write
       STATUS       current
       DESCRIPTION
           "The Last Member Query Count is the number of Group-Specific Queries
            sent before the router assumes there are no local members.  Default:
				the Robustness Variable."
       DEFVAL { 2 }
   ::= { hwDslamNtv 36 }

    hwDslamNtvLastMemberQueryInterval   OBJECT-TYPE
       SYNTAX       Integer32(1..50000)
       UNITS        "0.1s"
       MAX-ACCESS   read-write
       STATUS       current
       DESCRIPTION
           "The Last Member Query Interval is the Max Response Time inserted into
            Group-Specific Queries sent in response to Leave Group messages, and
            is also the amount of time between Group-Specific Query messages.
				Default: 10 (1 second)."
       DEFVAL { 10 }
   ::= { hwDslamNtv 37 }

   hwDslamNtvLastMemberQueryResponse OBJECT-TYPE
			SYNTAX Integer32 (1..255)
			UNITS "0.1s"
			MAX-ACCESS read-write
			STATUS current
			DESCRIPTION
				"The Last Member Query Response is the Max Responst Time that the reciever should response to the Last Member IGMPv2 Query"
			DEFVAL { 8 }
			::= { hwDslamNtv 38 }	

   hwDslamNtvAuthorizeSwitch OBJECT-TYPE
       SYNTAX      TruthValue
       MAX-ACCESS  read-write
       STATUS      current
       DESCRIPTION
           "The system authorize switch.  
           If the value is true, the authorize switch is on.
		   	If the value is false, the authorize switch is off. "
   ::= { hwDslamNtv 39 }
   
   		hwDslamNtvPreviewSwitch  OBJECT-TYPE
       SYNTAX      TruthValue
       MAX-ACCESS  read-write
       STATUS      current
       DESCRIPTION
           		"The system preview switch.  
           If the value is true, the preview switch is on.
           		If the value is false, the preview switch is off. "
   ::= { hwDslamNtv 40 }

   hwDslamNtvRecognitionTime  OBJECT-TYPE
       SYNTAX      Integer32 (1..120)
       UNITS        "second"
       MAX-ACCESS  read-write
       STATUS      current
       DESCRIPTION
                           "The system recognition time. "
       DEFVAL { 30 }
   ::= { hwDslamNtv 41 }
   
   hwDslamNtvClearPreviewCount  OBJECT-TYPE
       SYNTAX       RowStatus
       MAX-ACCESS   read-write
       STATUS      current
       DESCRIPTION
                          "Clear the count of all user preview ."
   ::= { hwDslamNtv 42 }

   hwDslamNtvTimeClearPreviewCount  OBJECT-TYPE
       SYNTAX       DateAndTime
       MAX-ACCESS   read-write
       STATUS      current
       DESCRIPTION
                           "The time which clear the count of all user have previewed."
   ::= { hwDslamNtv 43 }

   hwDslamNtvRightAssignMode   OBJECT-TYPE
       SYNTAX   INTEGER{  user-based(1), profile-based(2) }
       MAX-ACCESS   read-write
       STATUS       current
       DESCRIPTION
                           "Right assigned mode."
   ::= { hwDslamNtv 44 }

   hwDslamNtvLogReportInterval   OBJECT-TYPE
       SYNTAX   Integer32 (0..12)
       UNITS        "hour"
       MAX-ACCESS   read-write
       STATUS       current
       DESCRIPTION
                           "Log report interval."
   ::= { hwDslamNtv 45 }
   
   hwDslamNtvLogOperation   OBJECT-TYPE
       SYNTAX   INTEGER{  log-report-start(1), log-report-stop(2)  }
       MAX-ACCESS   read-write
       STATUS       current
       DESCRIPTION
                           "Operation to log."
   ::= { hwDslamNtv 46 }

   hwDslamNtvBandwidthManagementSwitch OBJECT-TYPE
       SYNTAX      TruthValue
       MAX-ACCESS  read-write
       STATUS      current
       DESCRIPTION
           "bandwidth management switch."
    ::= { hwDslamNtv 47 }	
 
   hwDslamNtvLogSwitch OBJECT-TYPE
       SYNTAX      TruthValue
       MAX-ACCESS  read-write
       STATUS      current
       DESCRIPTION
           "Global switch of Log"
    ::= { hwDslamNtv 48 }	
  hwDslamNtvFlow8021p OBJECT-TYPE
	SYNTAX Integer32 (0..7)
	MAX-ACCESS read-write
	STATUS current
	DESCRIPTION
		"Default:6
            priority of	802.1p
		"
	DEFVAL { 6 }	
	::= { hwDslamNtv 52 }
	
   hwDslamNtvFlowVlanid  OBJECT-TYPE
	SYNTAX Integer32 (1..4093)
	MAX-ACCESS read-write
	STATUS current
	DESCRIPTION
		"Default:1
		vlan id"
	DEFVAL { 1 }	
	::= { hwDslamNtv 53 }

  hwDslamNtvFlowEncap  OBJECT-TYPE
	SYNTAX INTEGER
		{
		ipoe(1),
		pppoe(2)
		}
	MAX-ACCESS read-write
	STATUS current
	DESCRIPTION
		"Default:ipoe
		encapsulation type"
	DEFVAL { 1 }	
	::= { hwDslamNtv 54 }
	
   hwDslamNtvQuerySwitch   OBJECT-TYPE
       SYNTAX       TruthValue
           MAX-ACCESS   read-write
           STATUS       current
           DESCRIPTION
               "IGMP user querier switch.When enable, device may send igmp query to 
                user sequently, else, just forward query from upper router to user."
    ::= { hwDslamNtv 55} 
    
    hwDslamNtvReportProxySwitch OBJECT-TYPE
       SYNTAX       TruthValue
           MAX-ACCESS   read-write
           STATUS       current
           DESCRIPTION
               "IGMP report Proxy switch.When it's enabled, device will intercepts, 
               absorbs and summarizes IGMP reports coming from IGMP hosts. IGMP 
               reports are relayed upstream only when necessary, i.e. when the 
               first user joins a multicast group, and once only per multicast group
               in response to an IGMP query."
    ::= { hwDslamNtv 56}
    
    hwDslamNtvLeaveProxySwitch    OBJECT-TYPE
        SYNTAX      TruthValue
            MAX-ACCESS    read-write
            STATUS        current
            DESCRIPTION
                "IGMP report Proxy switch.When it's enabled, device will intercepts, 
                absorbs and summarizes IGMP leaves coming from IGMP hosts. IGMP 
                leaves are relayed upstream only when necessary, i.e. when the last
                user quits a multicast group."
    ::= { hwDslamNtv 57}
    
    hwDslamNtvSnoopingUserAgingTime    OBJECT-TYPE
        SYNTAX      Integer32(10..1200)
        UNITS       "1s"
        MAX-ACCESS  read-write
        STATUS      current
        DESCRIPTION
            "The aging time configuration for IGMP over PPPoE user under the IGMP 
            Snooping mode."
        ::= { hwDslamNtv 58}
     
     hwDslamUnkownMulticastTunnelSwitch OBJECT-TYPE
           SYNTAX       TruthValue
           MAX-ACCESS   read-write
           STATUS       current
           DESCRIPTION
               "Unkown multicast tunneling switch."
       DEFVAL { 2 }
       ::= { hwDslamNtv 59}
     
     hwDslamNtvUserAllocBwthPercent  OBJECT-TYPE
          SYNTAX INTEGER (1..100)
	      MAX-ACCESS read-write
	      STATUS current
       	  DESCRIPTION
	       	  "the bandwidth percentage assigned for user. Default:100%"
	   ::= { hwDslamNtv 60 } 
              
     hwDslamNtvMFSTable OBJECT-TYPE
		SYNTAX SEQUENCE OF HwDslamNtvMFSEntry
		MAX-ACCESS not-accessible
		STATUS current
		DESCRIPTION
		"NTV multicast flow statistics table."
		::= { hwDslamNtv 61 }
		
		hwDslamNtvMFSEntry OBJECT-TYPE
		SYNTAX HwDslamNtvMFSEntry
		MAX-ACCESS not-accessible
		STATUS current
		DESCRIPTION
			"NTV multicast flow statistics entry"
		INDEX { hwDslamNtvMFSProgramIndex }
		::= { hwDslamNtvMFSTable 1 }
		
		HwDslamNtvMFSEntry ::= SEQUENCE {
		  hwDslamNtvMFSProgramIndex Integer32,
		  hwDslamNtvMFSResult       Integer32
		  }
		    
		hwDslamNtvMFSProgramIndex OBJECT-TYPE
		SYNTAX Integer32 (1..1024)
		MAX-ACCESS read-only
		STATUS current
		DESCRIPTION
		"Index of the program for multicast flow statistic.	"
		::= { hwDslamNtvMFSEntry 1 }
		
		hwDslamNtvMFSResult OBJECT-TYPE
		SYNTAX Integer32
		MAX-ACCESS read-only
		STATUS current
		DESCRIPTION
		"Get the Multicast Flow Statics result of a indexed program."
		::= { hwDslamNtvMFSEntry 2 }      
	
      hwDslamNtvUserActionReport OBJECT-TYPE
           SYNTAX       TruthValue
           MAX-ACCESS   read-write
           STATUS       current
           DESCRIPTION
               "User Action Report switch."
       DEFVAL { 2 }
       ::= { hwDslamNtv 62}
        
   hwDslamNtvCDRReportInterval   OBJECT-TYPE
       SYNTAX   Integer32 (60..43200)
       UNITS        "second"
       MAX-ACCESS   read-write
       STATUS       current
       DESCRIPTION
                           "CDR report interval."  
       DEFVAL { 600 }      
        ::= { hwDslamNtv 63}
        
    hwDslamNtvCDRReportNumber   OBJECT-TYPE
       SYNTAX   Integer32 (100..200)
       MAX-ACCESS   read-write
       STATUS       current
       DESCRIPTION
                           "CDR report number."     
       DEFVAL { 200 }   
        ::= { hwDslamNtv 64}
        
    hwDslamNtvRightPrioMode   OBJECT-TYPE
       SYNTAX   INTEGER{ w-p-f-i(1), w-f-p-i(2),p-w-f-i(3),p-f-w-i(4),f-w-p-i(5),f-p-w-i(6) }
       MAX-ACCESS   read-write
       STATUS       current
       DESCRIPTION
                           "The index of user right priority."     
       DEFVAL { 6 }   
        ::= { hwDslamNtv 65}
      
       -- -------------------------------------------------------------------------   
   --        Igmp statistic Management Table
   -- -------------------------------------------------------------------------       
    hwDslamNtvIgmpStatisticTable    OBJECT-TYPE
        SYNTAX          SEQUENCE OF HwDslamNtvIgmpStatisticEntry
        MAX-ACCESS      not-accessible
        STATUS          current
        DESCRIPTION
            "Igmp statistic Management Table"
        ::= { hwDslamNtv 66 }
    
    hwDslamNtvIgmpStatisticEntry    OBJECT-TYPE
        SYNTAX         HwDslamNtvIgmpStatisticEntry
        MAX-ACCESS     not-accessible
        STATUS         current
        DESCRIPTION
        "Igmp statistic Management entity"
        INDEX   { 
                   hwDslamNtvIgmpStatisticTypeIndex
                }
        ::= { hwDslamNtvIgmpStatisticTable  1 }

    HwDslamNtvIgmpStatisticEntry    ::= SEQUENCE  {
            hwDslamNtvIgmpStatisticOperMode        INTEGER, 
            hwDslamNtvIgmpStatisticTypeIndex       Integer32,
            hwDslamNtvIgmpStatisticPort            Integer32,
            hwDslamNtvIgmpStatisticMatchPara       Integer32,
            hwDslamNtvIgmpStatisticGenQueryRcv     Integer32,  
            hwDslamNtvIgmpStatisticSpecQueryRcv    Integer32,
            hwDslamNtvIgmpStatisticReportV1Rcv     Integer32,        
            hwDslamNtvIgmpStatisticReportV2Rcv     Integer32,
            hwDslamNtvIgmpStatisticReportV3Rcv     Integer32,
            hwDslamNtvIgmpStatisticErrQueryRcv     Integer32,
            hwDslamNtvIgmpStatisticErrReportRcv    Integer32,
            hwDslamNtvIgmpStatisticLeaveRcv        Integer32,
            hwDslamNtvIgmpStatisticErrLeaveRcv     Integer32,
            hwDslamNtvIgmpStatisticGenQuerySnd     Integer32,
            hwDslamNtvIgmpStatisticSpecQuerySnd    Integer32,
            hwDslamNtvIgmpStatisticReportV1Snd     Integer32,
            hwDslamNtvIgmpStatisticReportV2Snd     Integer32,
            hwDslamNtvIgmpStatisticLeaveSnd        Integer32,
            hwDslamNtvIgmpStatisticSnoopingMsgSnd  Integer32,
            hwDslamNtvIgmpStatisticErrV1ReportRcv  Integer32,                
            hwDslamNtvIgmpStatisticErrV2ReportRcv  Integer32,                
            hwDslamNtvIgmpStatisticErrV3ReportRcv  Integer32,   
            hwDslamNtvIgmpStatisticReportV3Snd     Integer32,                         
            hwDslamNtvIgmpStatisticInvalidRcv      Integer32,    
            hwDslamNtvIgmpStatisticVlan            Integer32,  
            hwDslamNtvIgmpActiveProgramNum         Integer32,   
            hwDslamNtvIgmpActiveUserNum            Integer32,                   
           }
                     
    hwDslamNtvIgmpStatisticOperMode        OBJECT-TYPE
           SYNTAX   INTEGER{ clear-statistic(1) }
           MAX-ACCESS   read-write
           STATUS       current
           DESCRIPTION
               "IGMP statistic operation mode.1-Clear IGMP statistic result."
    ::= { hwDslamNtvIgmpStatisticEntry 1}

    hwDslamNtvIgmpStatisticTypeIndex       OBJECT-TYPE
           SYNTAX   Integer32 (1..3)
           MAX-ACCESS   read-only
           STATUS       current
           DESCRIPTION
               "IGMP statistic type index.1-global IGMP statistic,2-specific port IGMP statistic,3-specific Mulicast VLAN statistic."
    ::= { hwDslamNtvIgmpStatisticEntry 2}

    hwDslamNtvIgmpStatisticPort           OBJECT-TYPE
           SYNTAX   Integer32 
           MAX-ACCESS   read-write
           STATUS       current
           DESCRIPTION
               "The ifindex of IGMP statistic port."
    ::= { hwDslamNtvIgmpStatisticEntry 3}
       
    hwDslamNtvIgmpStatisticMatchPara      OBJECT-TYPE
           SYNTAX   Integer32 
           MAX-ACCESS   read-write
           STATUS       current
           DESCRIPTION
               "the GemPortID of GPON port"
    ::= { hwDslamNtvIgmpStatisticEntry 4}
       
    hwDslamNtvIgmpStatisticGenQueryRcv    OBJECT-TYPE
           SYNTAX   Integer32 
           MAX-ACCESS   read-only
           STATUS       current
           DESCRIPTION
               "The number of general query packet received."
    ::= { hwDslamNtvIgmpStatisticEntry 5}

    hwDslamNtvIgmpStatisticSpecQueryRcv   OBJECT-TYPE
           SYNTAX   Integer32 
           MAX-ACCESS   read-only
           STATUS       current
           DESCRIPTION
               "The number of specific query packet received."
    ::= { hwDslamNtvIgmpStatisticEntry 6}
 
    hwDslamNtvIgmpStatisticReportV1Rcv    OBJECT-TYPE
           SYNTAX   Integer32 
           MAX-ACCESS   read-only
           STATUS       current
           DESCRIPTION
               "The number of report packet of version 1 received."
    ::= { hwDslamNtvIgmpStatisticEntry 7}

    hwDslamNtvIgmpStatisticReportV2Rcv    OBJECT-TYPE
           SYNTAX   Integer32 
           MAX-ACCESS   read-only
           STATUS       current
           DESCRIPTION
               "The number of report packet of version 2 received."
    ::= { hwDslamNtvIgmpStatisticEntry 8}

    hwDslamNtvIgmpStatisticReportV3Rcv    OBJECT-TYPE
           SYNTAX   Integer32 
           MAX-ACCESS   read-only
           STATUS       current
           DESCRIPTION
               "The number of report packet of version 3 received."
    ::= { hwDslamNtvIgmpStatisticEntry 9}

    hwDslamNtvIgmpStatisticErrQueryRcv    OBJECT-TYPE
           SYNTAX   Integer32 
           MAX-ACCESS   read-only
           STATUS       current
           DESCRIPTION
               "The number of error query packet received."
    ::= { hwDslamNtvIgmpStatisticEntry 10}

    hwDslamNtvIgmpStatisticErrReportRcv   OBJECT-TYPE
           SYNTAX   Integer32 
           MAX-ACCESS   read-only
           STATUS       current
           DESCRIPTION
               "The number of error report packet received."
    ::= { hwDslamNtvIgmpStatisticEntry 11}

    hwDslamNtvIgmpStatisticLeaveRcv       OBJECT-TYPE
           SYNTAX   Integer32 
           MAX-ACCESS   read-only
           STATUS       current
           DESCRIPTION
               "The number of leave report packet received."
    ::= { hwDslamNtvIgmpStatisticEntry 12}

    hwDslamNtvIgmpStatisticErrLeaveRcv    OBJECT-TYPE
           SYNTAX   Integer32 
           MAX-ACCESS   read-only
           STATUS       current
           DESCRIPTION
               "The number of error leave report packet received."
    ::= { hwDslamNtvIgmpStatisticEntry 13}

    hwDslamNtvIgmpStatisticGenQuerySnd    OBJECT-TYPE
           SYNTAX   Integer32 
           MAX-ACCESS   read-only
           STATUS       current
           DESCRIPTION
               "The number of general query packet sent out."
    ::= { hwDslamNtvIgmpStatisticEntry 14}

    hwDslamNtvIgmpStatisticSpecQuerySnd    OBJECT-TYPE
           SYNTAX   Integer32 
           MAX-ACCESS   read-only
           STATUS       current
           DESCRIPTION
               "The number of specific query packet sent out."
    ::= { hwDslamNtvIgmpStatisticEntry 15}

    hwDslamNtvIgmpStatisticReportV1Snd    OBJECT-TYPE
           SYNTAX   Integer32 
           MAX-ACCESS   read-only
           STATUS       current
           DESCRIPTION
               "The number of report packet of version 1 sent out."
    ::= { hwDslamNtvIgmpStatisticEntry 16}

    hwDslamNtvIgmpStatisticReportV2Snd    OBJECT-TYPE
           SYNTAX   Integer32 
           MAX-ACCESS   read-only
           STATUS       current
           DESCRIPTION
               "The number of report packet of version 2 sent out."
    ::= { hwDslamNtvIgmpStatisticEntry 17}

    hwDslamNtvIgmpStatisticLeaveSnd    OBJECT-TYPE
           SYNTAX   Integer32 
           MAX-ACCESS   read-only
           STATUS       current
           DESCRIPTION
               "The number of leave packet sent out."
    ::= { hwDslamNtvIgmpStatisticEntry 18}

    hwDslamNtvIgmpStatisticSnoopingMsgSnd   OBJECT-TYPE
           SYNTAX   Integer32 
           MAX-ACCESS   read-only
           STATUS       current
           DESCRIPTION
               "The number of IGMP snooping packet tranmitted."
    ::= { hwDslamNtvIgmpStatisticEntry 19}    

    hwDslamNtvIgmpStatisticErrV1ReportRcv   OBJECT-TYPE
           SYNTAX   Integer32 
           MAX-ACCESS   read-only
           STATUS       current
           DESCRIPTION
               "The number of error V1 report packet received."
    ::= { hwDslamNtvIgmpStatisticEntry 20}    

    hwDslamNtvIgmpStatisticErrV2ReportRcv   OBJECT-TYPE
           SYNTAX   Integer32 
           MAX-ACCESS   read-only
           STATUS       current
           DESCRIPTION
               "The number of error V2 report packet received."
    ::= { hwDslamNtvIgmpStatisticEntry 21}

    hwDslamNtvIgmpStatisticErrV3ReportRcv   OBJECT-TYPE
           SYNTAX   Integer32 
           MAX-ACCESS   read-only
           STATUS       current
           DESCRIPTION
               "The number of error V3 report packet received."
    ::= { hwDslamNtvIgmpStatisticEntry 22}  

    hwDslamNtvIgmpStatisticReportV3Snd    OBJECT-TYPE
           SYNTAX   Integer32 
           MAX-ACCESS   read-only
           STATUS       current
           DESCRIPTION
               "The number of report packet of version 3 sent out."
    ::= { hwDslamNtvIgmpStatisticEntry 23}

    hwDslamNtvIgmpStatisticInvalidRcv    OBJECT-TYPE
           SYNTAX   Integer32 
           MAX-ACCESS   read-only
           STATUS       current
           DESCRIPTION
               "The number of invalid IGMP packet received."
    ::= { hwDslamNtvIgmpStatisticEntry 24}

    hwDslamNtvIgmpStatisticVlan           OBJECT-TYPE
           SYNTAX   Integer32 
           MAX-ACCESS   read-write
           STATUS       current
           DESCRIPTION
               "The ID of IGMP statistic Mvlan."
    ::= { hwDslamNtvIgmpStatisticEntry 25}
    
    hwDslamNtvIgmpActiveProgramNum    OBJECT-TYPE
           SYNTAX   Integer32 
           MAX-ACCESS   read-only
           STATUS       current
           DESCRIPTION
               "The number of actived program in Mvlan."
    ::= { hwDslamNtvIgmpStatisticEntry 26}
    
    hwDslamNtvIgmpActiveUserNum    OBJECT-TYPE
           SYNTAX   Integer32 
           MAX-ACCESS   read-only
           STATUS       current
           DESCRIPTION
               "The number of actived user in Mvlan."
    ::= { hwDslamNtvIgmpStatisticEntry 27}
    
   
    -- ------------------------------------------------------------------------
    --       System Management Parameter
    -- ------------------------------------------------------------------------ 
   hwDslamNtvIgmpEncap   OBJECT-TYPE
       SYNTAX   INTEGER{ all(0), ppp(1), ip(2) }
       MAX-ACCESS   read-write
       STATUS       current
       DESCRIPTION
           "IGMP packet encapsulation. 0-all, 1-IGMP over PPP, 2-IGMP over IP."
   ::= { hwDslamNtv 67 }
   
   hwDslamNtvIgmpEcho   OBJECT-TYPE
       SYNTAX   INTEGER{ true(1), false(2) }
       MAX-ACCESS   read-write
       STATUS       current
       DESCRIPTION
           "IGMP echo switch. 1-enable, 2-disable."
   ::= { hwDslamNtv 68 } 
   
   
   ----------------------------------------------------------------
   --   multicast flow statistics table
   ----------------------------------------------------------------
   hwDslamNtvUpPortMFSTable OBJECT-TYPE
   SYNTAX SEQUENCE OF HwDslamNtvUpPortMFSEntry
   MAX-ACCESS not-accessible
   STATUS current
   DESCRIPTION
   "NTV multicast flow statistics table of uplink port."
   ::= { hwDslamNtv 69 }
   
   hwDslamNtvUpPortMFSEntry OBJECT-TYPE
   SYNTAX HwDslamNtvUpPortMFSEntry
   MAX-ACCESS not-accessible
   STATUS current
   DESCRIPTION
   	"NTV multicast flow statistics entry of uplink port"
   INDEX { hwDslamNtvUpPortMFSIndex }
   ::= { hwDslamNtvUpPortMFSTable 1 }
   
   HwDslamNtvUpPortMFSEntry ::= SEQUENCE {
     hwDslamNtvUpPortMFSIndex Integer32,
     hwDslamNtvUpPortMFSResult       Integer32
     }
       
   hwDslamNtvUpPortMFSIndex OBJECT-TYPE
   SYNTAX Integer32 (1..1024)
   MAX-ACCESS read-only
   STATUS current
   DESCRIPTION
   "Index of the upport for multicast flow statistic."
   ::= { hwDslamNtvUpPortMFSEntry 1 }
   
   hwDslamNtvUpPortMFSResult OBJECT-TYPE
   SYNTAX Integer32
   MAX-ACCESS read-only
   STATUS current
   DESCRIPTION
   "
   Get the Multicast Flow Statics result of an indexed upport."
   ::= { hwDslamNtvUpPortMFSEntry 2 }   
   
   
   hwDslamNtvDefaultUpport   OBJECT-TYPE
       SYNTAX   INTEGER
       MAX-ACCESS   read-write
       STATUS       current
       DESCRIPTION
                           "Default upport."     
   ::= { hwDslamNtv 70}
   
    hwDslamNtvCDRReport   OBJECT-TYPE
       SYNTAX   INTEGER { fail(1), all(2) }
       MAX-ACCESS   write-only
       STATUS       current
       DESCRIPTION
                           "Re-transmit the multicast CDR log."     
   ::= { hwDslamNtv 71}
       
    -- ------------------------------------------------------------------------
    --       System Management Parameter --Added by l52111
    -- ------------------------------------------------------------------------           
   hwDslamNtvV3QueryMaxResponseTime   OBJECT-TYPE
       SYNTAX       Integer32 (1..31744)
       UNITS        "0.1s"
       MAX-ACCESS   read-write
       STATUS       current
       DESCRIPTION
           "Max response time.
           The maximum general query response time advertised in IGMPv3 queries in the system."
      DEFVAL { 100 }    
   ::= { hwDslamNtv 72 }        
   
   hwDslamNtvLastMemberV3QueryResponse OBJECT-TYPE
			SYNTAX Integer32 (1..31744)
			UNITS "0.1s"
			MAX-ACCESS read-write
			STATUS current
			DESCRIPTION
				"The Last Member Query Response is the Max Responst Time that the receiver should response to the Last Member IGMPv3 Query."
			DEFVAL { 8 }
   ::= { hwDslamNtv 73 }	
 
   
   ---------------------------------------------------------------- 
   --    added by c58452 2006-09-01
   ----------------------------------------------------------------
       hwDslamNtvSnoopingProcess        OBJECT-TYPE
           SYNTAX       INTEGER{ firstmatch(1),discard(2)}
           MAX-ACCESS   read-write
           STATUS       current
           DESCRIPTION
		               "The process of different (S，G) matching different multicast snooping vlan in IGMPv3 Report.
		               :1-firstmatch   2-discard."
   ::= { hwDslamNtv 74} 
   
   
   -- -------------------------------------------------------------------------   
   --        preview profile Management Table
   -- -------------------------------------------------------------------------       
    hwDslamNtvPreviewProfileTable    OBJECT-TYPE
        SYNTAX          SEQUENCE OF HwDslamNtvPreviewProfileEntry 
        MAX-ACCESS      not-accessible                     
        STATUS          current                                      
        DESCRIPTION
            "preview profile management table"
    ::= { hwDslamNtv 75 }
    
    hwDslamNtvPreviewProfileEntry    OBJECT-TYPE
        SYNTAX          HwDslamNtvPreviewProfileEntry
        MAX-ACCESS      not-accessible
        STATUS          current
        DESCRIPTION
            " preview profile management entity."
        INDEX { 
                  hwDslamNtvPreviewProfileIndex
              }
              ::= { hwDslamNtvPreviewProfileTable  1 }

   HwDslamNtvPreviewProfileEntry    ::= SEQUENCE  {
            hwDslamNtvPreviewProfileIndex         Integer32,
            hwDslamNtvPreviewRowStatus            RowStatus,
            hwDslamNtvPreviewDuration             Integer32,
            hwDslamNtvPreviewTimes                Integer32,
            hwDslamNtvPreviewInterval             Integer32,
            hwDslamNtvProgramRefCount             Integer32
         }
                                    
    hwDslamNtvPreviewProfileIndex         OBJECT-TYPE
           SYNTAX          Integer32 (0..31)
           MAX-ACCESS      read-only
           STATUS          current
           DESCRIPTION
				   "preview profile index."
    ::= { hwDslamNtvPreviewProfileEntry 1}   
    
    hwDslamNtvPreviewRowStatus        OBJECT-TYPE
           SYNTAX       RowStatus
           MAX-ACCESS   read-create
           STATUS       current
           DESCRIPTION
               "Row status.
				Add or delete a table item."
    ::= { hwDslamNtvPreviewProfileEntry 2}
   
    hwDslamNtvPreviewDuration        OBJECT-TYPE
           SYNTAX        Integer32 (10..6000 )
           UNITS         "second"
           MAX-ACCESS    read-write
           STATUS         current
           DESCRIPTION
				"The preview duration."
           DEFVAL {120}
    ::= { hwDslamNtvPreviewProfileEntry 3}

    hwDslamNtvPreviewTimes        OBJECT-TYPE
           SYNTAX      Integer32 (1..255 )
           MAX-ACCESS  read-write
           STATUS      current
           DESCRIPTION
				"The times of preview." 
        DEFVAL {8 }
    ::= { hwDslamNtvPreviewProfileEntry 4}
    
    hwDslamNtvPreviewInterval      OBJECT-TYPE
           SYNTAX      Integer32 (0..7650)
           UNITS        "second"
           MAX-ACCESS  read-write
           STATUS       current
           DESCRIPTION
				"The interval time of preview the same program."
        DEFVAL {120 }   
    ::= { hwDslamNtvPreviewProfileEntry 5}
    
        hwDslamNtvProgramRefCount        OBJECT-TYPE
           SYNTAX       Integer32
           MAX-ACCESS   read-only
           STATUS       current
           DESCRIPTION
               " Count of programs which reference the preview profile."
      ::= { hwDslamNtvPreviewProfileEntry 6}
 
        
   ----------------------------------------------------------------
   --   multicast vlan table
   ----------------------------------------------------------------
   hwDslamNtvMVLANTable OBJECT-TYPE
   SYNTAX SEQUENCE OF HwDslamNtvMVLANEntry
   MAX-ACCESS not-accessible
   STATUS current
   DESCRIPTION
   "NTV MVLAN table "
   ::= { hwDslamNtv 76 }
   
   hwDslamNtvMVLANEntry OBJECT-TYPE
   SYNTAX HwDslamNtvMVLANEntry
   MAX-ACCESS not-accessible
   STATUS current
   DESCRIPTION
   	"NTV MVLAN"
   INDEX { hwDslamNtvMVLANIndex }
   ::= { hwDslamNtvMVLANTable 1 }
   
   HwDslamNtvMVLANEntry ::= SEQUENCE {
     hwDslamNtvMVLANIndex                         Integer32,
     hwDslamNtvMVLANLogSwitch                     INTEGER{ enable(1),disable(2)},
     hwDslamNtvMVLANIGMPPriority                  Integer32 (0..7),
     hwDslamNtvMVLANGlobalLeaveSendSwitch         INTEGER{ enable(1),disable(2)},
     hwDslamNtvMVLANIgmpMode                      INTEGER{igmp_proxy(1),igmp_snooping(2),tv_off(3)},
     hwDslamNtvMVLANIgmpVer                       INTEGER{igmpv2(1),igmpv3(2)},
     hwDslamNtvMVLANMatchMode                     INTEGER{ enable(1),disable(2)},
     hwDslamNtvMVLANDynStartIP                    IpAddress,
     hwDslamNtvMVLANDynEndIP                      IpAddress,
     hwDslamNtvMVLANSnoopingReportSwitch          INTEGER{ enable(1),disable(2)},
     hwDslamNtvMVLANSnoopingLeaveSwitch           INTEGER{ enable(1),disable(2)},     
     hwDslamNtvMVLANUnsoliReportTime              Integer32 (10..5000),
     hwDslamNtvMVLANRowstatus                     RowStatus,
     hwDslamNtvDefaultUplinkPort                  Integer32,     
     hwDslamNtvVlanID                             Integer32,
     hwDslamNtvMVLANProgramMask1                  BITS,
     hwDslamNtvMVLANProgramMask2                  BITS,
     hwDslamNtvMVLANProgramMask3                  BITS,
     hwDslamNtvMVLANProgramMask4                  BITS,
     hwDslamNtvMVLANProgramMask5                  BITS,
     hwDslamNtvMVLANProgramMask6                  BITS,
     hwDslamNtvMVLANProgramMask7                  BITS,
     hwDslamNtvMVLANProgramMask8                  BITS
     }
       
   hwDslamNtvMVLANIndex OBJECT-TYPE
   SYNTAX Integer32 (1..256)
   MAX-ACCESS read-only
   STATUS current
   DESCRIPTION
   "Index of  MVLAN.
   "
   ::= { hwDslamNtvMVLANEntry 1 }
   
   hwDslamNtvMVLANLogSwitch OBJECT-TYPE
   SYNTAX INTEGER{ enable(1),disable(2)}
   MAX-ACCESS read-write
   STATUS current
   DESCRIPTION
   "
   the log switch
   "
DEFVAL { 2 }
   ::= { hwDslamNtvMVLANEntry 2 }   

hwDslamNtvMVLANIGMPPriority OBJECT-TYPE
   SYNTAX  Integer32 (0..7)
   MAX-ACCESS read-write
   STATUS current
   DESCRIPTION
   "
   the priority of IGMP packets.
   "
DEFVAL { 6 }
   ::= { hwDslamNtvMVLANEntry 3 }   

    
hwDslamNtvMVLANGlobalLeaveSendSwitch OBJECT-TYPE
   SYNTAX  INTEGER{ enable(1),disable(2)}
   MAX-ACCESS read-write
   STATUS current
   DESCRIPTION
   "
   the switch of Global-Leave sending.
   "
DEFVAL { 2 }
   ::= { hwDslamNtvMVLANEntry 4 } 

hwDslamNtvMVLANIgmpMode OBJECT-TYPE
   SYNTAX  INTEGER {igmp-proxy(1),igmp-snooping(2),tv-off(3)}
   MAX-ACCESS read-write
   STATUS current
   DESCRIPTION
   "
   igmp working mode.
   "
DEFVAL { 3 }
   ::= { hwDslamNtvMVLANEntry 5 } 
   
hwDslamNtvMVLANIgmpVer OBJECT-TYPE
   SYNTAX  INTEGER{ igmpv2(1),igmpv3(2)}
   MAX-ACCESS read-write
   STATUS current
   DESCRIPTION
   "
    igmp version.
   "
DEFVAL { 2 }
   ::= { hwDslamNtvMVLANEntry 6 } 
   
hwDslamNtvMVLANMatchMode OBJECT-TYPE
   SYNTAX  INTEGER{ enable(1),disable(2) }
   MAX-ACCESS read-write
   STATUS current
   DESCRIPTION
   "
    program match mode.
   "
DEFVAL { 1 }
   ::= { hwDslamNtvMVLANEntry 7 } 
   
hwDslamNtvMVLANDynStartIP OBJECT-TYPE
   SYNTAX  IpAddress
   MAX-ACCESS read-write
   STATUS current
   DESCRIPTION
   "
    started IP of the dynamic created program.
   "
   ::= { hwDslamNtvMVLANEntry 8 } 

hwDslamNtvMVLANDynEndIP OBJECT-TYPE
   SYNTAX  IpAddress
   MAX-ACCESS read-write
   STATUS current
   DESCRIPTION
   "
    ended IP of the dynamic created program.
   "
   ::= { hwDslamNtvMVLANEntry 9 } 
   
hwDslamNtvMVLANSnoopingReportSwitch OBJECT-TYPE
   SYNTAX  INTEGER{ enable(1),disable(2)}
   MAX-ACCESS read-write
   STATUS current
   DESCRIPTION
   "
    The proxy switch of the report packet under snooping mode.
   "
DEFVAL { 2 }
   ::= { hwDslamNtvMVLANEntry 10 } 
   
hwDslamNtvMVLANSnoopingLeaveSwitch OBJECT-TYPE
   SYNTAX  INTEGER{ enable(1),disable(2)}
   MAX-ACCESS read-write
   STATUS current
   DESCRIPTION
   "
    The proxy switch of the leave packet under snooping mode.
   "
DEFVAL { 2 }
   ::= { hwDslamNtvMVLANEntry 11 }    
 
   
hwDslamNtvMVLANUnsoliReportTime OBJECT-TYPE
   SYNTAX  Integer32 (10..5000)
   MAX-ACCESS read-write
   STATUS current
   DESCRIPTION
   "
    The interval on which users send report unsolicited.
   "
DEFVAL { 10 }
   ::= { hwDslamNtvMVLANEntry 12 } 

           
    hwDslamNtvMVLANRowstatus        OBJECT-TYPE
           SYNTAX       RowStatus
           MAX-ACCESS   read-create
           STATUS       current
           DESCRIPTION
                         "Row status.
		        Add or delete a table item."
    ::= { hwDslamNtvMVLANEntry 13 }
    
    hwDslamNtvDefaultUplinkPort        OBJECT-TYPE
           SYNTAX       Integer32
           MAX-ACCESS   read-write
           STATUS       current
           DESCRIPTION
                         "Default uplink port."
    ::= { hwDslamNtvMVLANEntry 14 }  
     
   
   
      hwDslamNtvVlanID  OBJECT-TYPE
       SYNTAX     Integer32(1..4093)
       MAX-ACCESS   read-write
       STATUS       current
       DESCRIPTION
           "MVlan ID."
   ::= { hwDslamNtvMVLANEntry 15 }
   
   hwDslamNtvMVLANProgramMask1        OBJECT-TYPE
           SYNTAX   BITS
           	    {
                       program1(0),
                       program2(1),
                       program3(2),
                       program4(3),
                       program5(4),
                       program6(5),
                       program7(6),
                       program8(7),
                       program9(8),
                       program10(9),
                       program11(10),
                       program12(11),
                       program13(12),
                       program14(13),
                       program15(14),
                       program16(15),
                       program17(16),
                       program18(17),
                       program19(18),
                       program20(19),
                       program21(20),
                       program22(21),
                       program23(22),
                       program24(23),
                       program25(24),
                       program26(25),
                       program27(26),
                       program28(27),
                       program29(28),
                       program30(29),
                       program31(30),
                       program32(31),
                       program33(32),
                       program34(33),
                       program35(34),
                       program36(35),
                       program37(36),
                       program38(37),
                       program39(38),
                       program40(39),
                       program41(40),
                       program42(41),
                       program43(42),
                       program44(43),
                       program45(44),
                       program46(45),
                       program47(46),
                       program48(47),
                       program49(48),
                       program50(49),
                       program51(50),
                       program52(51),
                       program53(52),
                       program54(53),
                       program55(54),
                       program56(55),
                       program57(56),
                       program58(57),
                       program59(58),
                       program60(59),
                       program61(60),
                       program62(61),
                       program63(62),
                       program64(63),
                       program65(64),
                       program66(65),
                       program67(66),
                       program68(67),
                       program69(68),
                       program70(69),
                       program71(70),
                       program72(71),
                       program73(72),
                       program74(73),
                       program75(74),
                       program76(75),
                       program77(76),
                       program78(77),
                       program79(78),
                       program80(79),
                       program81(80),
                       program82(81),
                       program83(82),
                       program84(83),
                       program85(84),
                       program86(85),
                       program87(86),
                       program88(87),
                       program89(88),
                       program90(89),
                       program91(90),
                       program92(91),
                       program93(92),
                       program94(93),
                       program95(94),
                       program96(95),
                       program97(96),
                       program98(97),
                       program99(98),
                       program100(99),
                       program101(100),
                       program102(101),
                       program103(102),
                       program104(103),
                       program105(104),
                       program106(105),
                       program107(106),
                       program108(107),
                       program109(108),
                       program110(109),
                       program111(110),
                       program112(111),
                       program113(112),
                       program114(113),
                       program115(114),
                       program116(115),
                       program117(116),
                       program118(117),
                       program119(118),
                       program120(119),
                       program121(120),
                       program122(121),
                       program123(122),
                       program124(123),
                       program125(124),
                       program126(125),
                       program127(126),
                       program128(127)                       
                    }
           MAX-ACCESS   read-only
           STATUS       current
           DESCRIPTION
               "Program mask.               
               Program mask of multicast vlan. One bit indicate one program.If the multicast vlan includes the program, the bit value is 1.
               "
    ::= { hwDslamNtvMVLANEntry 16}
    
    hwDslamNtvMVLANProgramMask2        OBJECT-TYPE
           SYNTAX   BITS
           	    {
                       program129(0),
                       program130(1),
                       program131(2),
                       program132(3),
                       program133(4),
                       program134(5),
                       program135(6),
                       program136(7),
                       program137(8),
                       program138(9),
                       program139(10),
                       program140(11),
                       program141(12),
                       program142(13),
                       program143(14),
                       program144(15),
                       program145(16),
                       program146(17),
                       program147(18),
                       program148(19),
                       program149(20),
                       program150(21),
                       program151(22),
                       program152(23),
                       program153(24),
                       program154(25),
                       program155(26),
                       program156(27),
                       program157(28),
                       program158(29),
                       program159(30),
                       program160(31),
                       program161(32),
                       program162(33),
                       program163(34),
                       program164(35),
                       program165(36),
                       program166(37),
                       program167(38),
                       program168(39),
                       program169(40),
                       program170(41),
                       program171(42),
                       program172(43),
                       program173(44),
                       program174(45),
                       program175(46),
                       program176(47),
                       program177(48),
                       program178(49),
                       program179(50),
                       program180(51),
                       program181(52),
                       program182(53),
                       program183(54),
                       program184(55),
                       program185(56),
                       program186(57),
                       program187(58),
                       program188(59),
                       program189(60),
                       program190(61),
                       program191(62),
                       program192(63),
                       program193(64),
                       program194(65),
                       program195(66),
                       program196(67),
                       program197(68),
                       program198(69),
                       program199(70),
                       program200(71),
                       program201(72),
                       program202(73),
                       program203(74),
                       program204(75),
                       program205(76),
                       program206(77),
                       program207(78),
                       program208(79),
                       program209(80),
                       program210(81),
                       program211(82),
                       program212(83),
                       program213(84),
                       program214(85),
                       program215(86),
                       program216(87),
                       program217(88),
                       program218(89),
                       program219(90),
                       program220(91),
                       program221(92),
                       program222(93),
                       program223(94),
                       program224(95),
                       program225(96),
                       program226(97),
                       program227(98),
                       program228(99),
                       program229(100),
                       program230(101),
                       program231(102),
                       program232(103),
                       program233(104),
                       program234(105),
                       program235(106),
                       program236(107),
                       program237(108),
                       program238(109),
                       program239(110),
                       program240(111),
                       program241(112),
                       program242(113),
                       program243(114),
                       program244(115),
                       program245(116),
                       program246(117),
                       program247(118),
                       program248(119),
                       program249(120),
                       program250(121),
                       program251(122),
                       program252(123),
                       program253(124),
                       program254(125),
                       program255(126),
                       program256(127)
                    }           
           MAX-ACCESS   read-only
           STATUS       current
           DESCRIPTION
               "Program mask.               
               Program mask of multicast vlan. One bit indicate one program.If the multicast vlan includes the program, the bit value is 1.
               "
    ::= { hwDslamNtvMVLANEntry 17 }
    
    
   hwDslamNtvMVLANProgramMask3 OBJECT-TYPE
			SYNTAX BITS
				{
				program257(0),
				program258(1),
				program259(2),
				program260(3),
				program261(4),
				program262(5),
				program263(6),
				program264(7),
				program265(8),
				program266(9),
				program267(10),
				program268(11),
				program269(12),
				program270(13),
				program271(14),
				program272(15),
				program273(16),
				program274(17),
				program275(18),
				program276(19),
				program277(20),
				program278(21),
				program279(22),
				program280(23),
				program281(24),
				program282(25),
				program283(26),
				program284(27),
				program285(28),
				program286(29),
				program287(30),
				program288(31),
				program289(32),
				program290(33),
				program291(34),
				program292(35),
				program293(36),
				program294(37),
				program295(38),
				program296(39),
				program297(40),
				program298(41),
				program299(42),
				program300(43),
				program301(44),
				program302(45),
				program303(46),
				program304(47),
				program305(48),
				program306(49),
				program307(50),
				program308(51),
				program309(52),
				program310(53),
				program311(54),
				program312(55),
				program313(56),
				program314(57),
				program315(58),
				program316(59),
				program317(60),
				program318(61),
				program319(62),
				program320(63),
				program321(64),
				program322(65),
				program323(66),
				program324(67),
				program325(68),
				program326(69),
				program327(70),
				program328(71),
				program329(72),
				program330(73),
				program331(74),
				program332(75),
				program333(76),
				program334(77),
				program335(78),
				program336(79),
				program337(80),
				program338(81),
				program339(82),
				program340(83),
				program341(84),
				program342(85),
				program343(86),
				program344(87),
				program345(88),
				program346(89),
				program347(90),
				program348(91),
				program349(92),
				program350(93),
				program351(94),
				program352(95),
				program353(96),
				program354(97),
				program355(98),
				program356(99),
				program357(100),
				program358(101),
				program359(102),
				program360(103),
				program361(104),
				program362(105),
				program363(106),
				program364(107),
				program365(108),
				program366(109),
				program367(110),
				program368(111),
				program369(112),
				program370(113),
				program371(114),
				program372(115),
				program373(116),
				program374(117),
				program375(118),
				program376(119),
				program377(120),
				program378(121),
				program379(122),
				program380(123),
				program381(124),
				program382(125),
				program383(126),
				program384(127)
				}
			MAX-ACCESS read-only
			STATUS current
			DESCRIPTION
	                        "Program mask.               
               Program mask of multicast vlan. One bit indicate one program.If the multicast vlan includes the program, the bit value is 1.
                                "
			::= { hwDslamNtvMVLANEntry 18 }
		
		
		hwDslamNtvMVLANProgramMask4 OBJECT-TYPE
			SYNTAX BITS
				{
				program385(0),
				program386(1),
				program387(2),
				program388(3),
				program389(4),
				program390(5),
				program391(6),
				program392(7),
				program393(8),
				program394(9),
				program395(10),
				program396(11),
				program397(12),
				program398(13),
				program399(14),
				program400(15),
				program401(16),
				program402(17),
				program403(18),
				program404(19),
				program405(20),
				program406(21),
				program407(22),
				program408(23),
				program409(24),
				program410(25),
				program411(26),
				program412(27),
				program413(28),
				program414(29),
				program415(30),
				program416(31),
				program417(32),
				program418(33),
				program419(34),
				program420(35),
				program421(36),
				program422(37),
				program423(38),
				program424(39),
				program425(40),
				program426(41),
				program427(42),
				program428(43),
				program429(44),
				program430(45),
				program431(46),
				program432(47),
				program433(48),
				program434(49),
				program435(50),
				program436(51),
				program437(52),
				program438(53),
				program439(54),
				program440(55),
				program441(56),
				program442(57),
				program443(58),
				program444(59),
				program445(60),
				program446(61),
				program447(62),
				program448(63),
				program449(64),
				program450(65),
				program451(66),
				program452(67),
				program453(68),
				program454(69),
				program455(70),
				program456(71),
				program457(72),
				program458(73),
				program459(74),
				program460(75),
				program461(76),
				program462(77),
				program463(78),
				program464(79),
				program465(80),
				program466(81),
				program467(82),
				program468(83),
				program469(84),
				program470(85),
				program471(86),
				program472(87),
				program473(88),
				program474(89),
				program475(90),
				program476(91),
				program477(92),
				program478(93),
				program479(94),
				program480(95),
				program481(96),
				program482(97),
				program483(98),
				program484(99),
				program485(100),
				program486(101),
				program487(102),
				program488(103),
				program489(104),
				program490(105),
				program491(106),
				program492(107),
				program493(108),
				program494(109),
				program495(110),
				program496(111),
				program497(112),
				program498(113),
				program499(114),
				program500(115),
				program501(116),
				program502(117),
				program503(118),
				program504(119),
				program505(120),
				program506(121),
				program507(122),
				program508(123),
				program509(124),
				program510(125),
				program511(126),
				program512(127)
				}
			MAX-ACCESS read-only
			STATUS current
			DESCRIPTION
	                        "Program mask.               
               Program mask of multicast vlan. One bit indicate one program.If the multicast vlan includes the program, the bit value is 1.
                                "
			::= { hwDslamNtvMVLANEntry 19 }
		
		
		hwDslamNtvMVLANProgramMask5 OBJECT-TYPE
			SYNTAX BITS
				{
				program513(0),
				program514(1),
				program515(2),
				program516(3),
				program517(4),
				program518(5),
				program519(6),
				program520(7),
				program521(8),
				program522(9),
				program523(10),
				program524(11),
				program525(12),
				program526(13),
				program527(14),
				program528(15),
				program529(16),
				program530(17),
				program531(18),
				program532(19),
				program533(20),
				program534(21),
				program535(22),
				program536(23),
				program537(24),
				program538(25),
				program539(26),
				program540(27),
				program541(28),
				program542(29),
				program543(30),
				program544(31),
				program545(32),
				program546(33),
				program547(34),
				program548(35),
				program549(36),
				program550(37),
				program551(38),
				program552(39),
				program553(40),
				program554(41),
				program555(42),
				program556(43),
				program557(44),
				program558(45),
				program559(46),
				program560(47),
				program561(48),
				program562(49),
				program563(50),
				program564(51),
				program565(52),
				program566(53),
				program567(54),
				program568(55),
				program569(56),
				program570(57),
				program571(58),
				program572(59),
				program573(60),
				program574(61),
				program575(62),
				program576(63),
				program577(64),
				program578(65),
				program579(66),
				program580(67),
				program581(68),
				program582(69),
				program583(70),
				program584(71),
				program585(72),
				program586(73),
				program587(74),
				program588(75),
				program589(76),
				program590(77),
				program591(78),
				program592(79),
				program593(80),
				program594(81),
				program595(82),
				program596(83),
				program597(84),
				program598(85),
				program599(86),
				program600(87),
				program601(88),
				program602(89),
				program603(90),
				program604(91),
				program605(92),
				program606(93),
				program607(94),
				program608(95),
				program609(96),
				program610(97),
				program611(98),
				program612(99),
				program613(100),
				program614(101),
				program615(102),
				program616(103),
				program617(104),
				program618(105),
				program619(106),
				program620(107),
				program621(108),
				program622(109),
				program623(110),
				program624(111),
				program625(112),
				program626(113),
				program627(114),
				program628(115),
				program629(116),
				program630(117),
				program631(118),
				program632(119),
				program633(120),
				program634(121),
				program635(122),
				program636(123),
				program637(124),
				program638(125),
				program639(126),
				program640(127)
				}
			MAX-ACCESS read-only
			STATUS current
			DESCRIPTION
				"Program mask.               
               Program mask of multicast vlan. One bit indicate one program.If the multicast vlan includes the program, the bit value is 1.
                                "
			::= { hwDslamNtvMVLANEntry 20 }
		
		
		hwDslamNtvMVLANProgramMask6 OBJECT-TYPE
			SYNTAX BITS
				{
				program641(0),
				program642(1),
				program643(2),
				program644(3),
				program645(4),
				program646(5),
				program647(6),
				program648(7),
				program649(8),
				program650(9),
				program651(10),
				program652(11),
				program653(12),
				program654(13),
				program655(14),
				program656(15),
				program657(16),
				program658(17),
				program659(18),
				program660(19),
				program661(20),
				program662(21),
				program663(22),
				program664(23),
				program665(24),
				program666(25),
				program667(26),
				program668(27),
				program669(28),
				program670(29),
				program671(30),
				program672(31),
				program673(32),
				program674(33),
				program675(34),
				program676(35),
				program677(36),
				program678(37),
				program679(38),
				program680(39),
				program681(40),
				program682(41),
				program683(42),
				program684(43),
				program685(44),
				program686(45),
				program687(46),
				program688(47),
				program689(48),
				program690(49),
				program691(50),
				program692(51),
				program693(52),
				program694(53),
				program695(54),
				program696(55),
				program697(56),
				program698(57),
				program699(58),
				program700(59),
				program701(60),
				program702(61),
				program703(62),
				program704(63),
				program705(64),
				program706(65),
				program707(66),
				program708(67),
				program709(68),
				program710(69),
				program711(70),
				program712(71),
				program713(72),
				program714(73),
				program715(74),
				program716(75),
				program717(76),
				program718(77),
				program719(78),
				program720(79),
				program721(80),
				program722(81),
				program723(82),
				program724(83),
				program725(84),
				program726(85),
				program727(86),
				program728(87),
				program729(88),
				program730(89),
				program731(90),
				program732(91),
				program733(92),
				program734(93),
				program735(94),
				program736(95),
				program737(96),
				program738(97),
				program739(98),
				program740(99),
				program741(100),
				program742(101),
				program743(102),
				program744(103),
				program745(104),
				program746(105),
				program747(106),
				program748(107),
				program749(108),
				program750(109),
				program751(110),
				program752(111),
				program753(112),
				program754(113),
				program755(114),
				program756(115),
				program757(116),
				program758(117),
				program759(118),
				program760(119),
				program761(120),
				program762(121),
				program763(122),
				program764(123),
				program765(124),
				program766(125),
				program767(126),
				program768(127)
				}
			MAX-ACCESS read-only
			STATUS current
			DESCRIPTION
				"Program mask.               
               Program mask of multicast vlan. One bit indicate one program.If the multicast vlan includes the program, the bit value is 1.
                                "
			::= { hwDslamNtvMVLANEntry 21 }
		
		
		hwDslamNtvMVLANProgramMask7 OBJECT-TYPE
			SYNTAX BITS
				{
				program769(0),
				program770(1),
				program771(2),
				program772(3),
				program773(4),
				program774(5),
				program775(6),
				program776(7),
				program777(8),
				program778(9),
				program779(10),
				program780(11),
				program781(12),
				program782(13),
				program783(14),
				program784(15),
				program785(16),
				program786(17),
				program787(18),
				program788(19),
				program789(20),
				program790(21),
				program791(22),
				program792(23),
				program793(24),
				program794(25),
				program795(26),
				program796(27),
				program797(28),
				program798(29),
				program799(30),
				program800(31),
				program801(32),
				program802(33),
				program803(34),
				program804(35),
				program805(36),
				program806(37),
				program807(38),
				program808(39),
				program809(40),
				program810(41),
				program811(42),
				program812(43),
				program813(44),
				program814(45),
				program815(46),
				program816(47),
				program817(48),
				program818(49),
				program819(50),
				program820(51),
				program821(52),
				program822(53),
				program823(54),
				program824(55),
				program825(56),
				program826(57),
				program827(58),
				program828(59),
				program829(60),
				program830(61),
				program831(62),
				program832(63),
				program833(64),
				program834(65),
				program835(66),
				program836(67),
				program837(68),
				program838(69),
				program839(70),
				program840(71),
				program841(72),
				program842(73),
				program843(74),
				program844(75),
				program845(76),
				program846(77),
				program847(78),
				program848(79),
				program849(80),
				program850(81),
				program851(82),
				program852(83),
				program853(84),
				program854(85),
				program855(86),
				program856(87),
				program857(88),
				program858(89),
				program859(90),
				program860(91),
				program861(92),
				program862(93),
				program863(94),
				program864(95),
				program865(96),
				program866(97),
				program867(98),
				program868(99),
				program869(100),
				program870(101),
				program871(102),
				program872(103),
				program873(104),
				program874(105),
				program875(106),
				program876(107),
				program877(108),
				program878(109),
				program879(110),
				program880(111),
				program881(112),
				program882(113),
				program883(114),
				program884(115),
				program885(116),
				program886(117),
				program887(118),
				program888(119),
				program889(120),
				program890(121),
				program891(122),
				program892(123),
				program893(124),
				program894(125),
				program895(126),
				program896(127)
				}
			MAX-ACCESS read-only
			STATUS current
			DESCRIPTION
				"Program mask.               
               Program mask of multicast vlan. One bit indicate one program.If the multicast vlan includes the program, the bit value is 1.
                                "
			::= { hwDslamNtvMVLANEntry 22 }
		
		
		hwDslamNtvMVLANProgramMask8 OBJECT-TYPE
			SYNTAX BITS
				{
				program897(0),
				program898(1),
				program899(2),
				program900(3),
				program901(4),
				program902(5),
				program903(6),
				program904(7),
				program905(8),
				program906(9),
				program907(10),
				program908(11),
				program909(12),
				program910(13),
				program911(14),
				program912(15),
				program913(16),
				program914(17),
				program915(18),
				program916(19),
				program917(20),
				program918(21),
				program919(22),
				program920(23),
				program921(24),
				program922(25),
				program923(26),
				program924(27),
				program925(28),
				program926(29),
				program927(30),
				program928(31),
				program929(32),
				program930(33),
				program931(34),
				program932(35),
				program933(36),
				program934(37),
				program935(38),
				program936(39),
				program937(40),
				program938(41),
				program939(42),
				program940(43),
				program941(44),
				program942(45),
				program943(46),
				program944(47),
				program945(48),
				program946(49),
				program947(50),
				program948(51),
				program949(52),
				program950(53),
				program951(54),
				program952(55),
				program953(56),
				program954(57),
				program955(58),
				program956(59),
				program957(60),
				program958(61),
				program959(62),
				program960(63),
				program961(64),
				program962(65),
				program963(66),
				program964(67),
				program965(68),
				program966(69),
				program967(70),
				program968(71),
				program969(72),
				program970(73),
				program971(74),
				program972(75),
				program973(76),
				program974(77),
				program975(78),
				program976(79),
				program977(80),
				program978(81),
				program979(82),
				program980(83),
				program981(84),
				program982(85),
				program983(86),
				program984(87),
				program985(88),
				program986(89),
				program987(90),
				program988(91),
				program989(92),
				program990(93),
				program991(94),
				program992(95),
				program993(96),
				program994(97),
				program995(98),
				program996(99),
				program997(100),
				program998(101),
				program999(102),
				program1000(103),
				program1001(104),
				program1002(105),
				program1003(106),
				program1004(107),
				program1005(108),
				program1006(109),
				program1007(110),
				program1008(111),
				program1009(112),
				program1010(113),
				program1011(114),
				program1012(115),
				program1013(116),
				program1014(117),
				program1015(118),
				program1016(119),
				program1017(120),
				program1018(121),
				program1019(122),
				program1020(123),
				program1021(124),
				program1022(125),
				program1023(126),
				program1024(127)
				}
			MAX-ACCESS read-only
			STATUS current
			DESCRIPTION
				"Program mask.               
               Program mask of multicast vlan. One bit indicate one program.If the multicast vlan includes the program, the bit value is 1.
                                "
			::= { hwDslamNtvMVLANEntry 23 }

   ----------------------------------------------------------------
   --   FlowBasedMulticastPolicy ------
   ----------------------------------------------------------------
   hwDslamNtvFlowBasedMulticastPolicyTable OBJECT-TYPE
   SYNTAX SEQUENCE OF HwDslamNtvFlowBasedMulticastPolicyEntry
   MAX-ACCESS not-accessible
   STATUS current
   DESCRIPTION
   "NTV FlowBasedMulticastPolicy table "
   ::= { hwDslamNtv 77 }
   
   hwDslamNtvFlowBasedMulticastPolicyEntry OBJECT-TYPE
   SYNTAX HwDslamNtvFlowBasedMulticastPolicyEntry
   MAX-ACCESS not-accessible
   STATUS current
   DESCRIPTION
   	"hwDslamNtvFlowBasedMulticastPolicy "
   INDEX { 
          hwDslamNtvFlowID
           }
   ::= { hwDslamNtvFlowBasedMulticastPolicyTable 1 }
   
   HwDslamNtvFlowBasedMulticastPolicyEntry ::= SEQUENCE {
     hwDslamNtvFlowID  Integer32,
     hwDslamNtvUnknownMulticastTrafficPolicy  INTEGER{ transparent(2),discard(3)},
     hwDslamNtvIgmpPacketPolicy  INTEGER{ normal(1),transparent(2),discard(3)}
     }
     
   hwDslamNtvFlowID OBJECT-TYPE
   SYNTAX  Integer32 (1..16384)
   MAX-ACCESS read-write
   STATUS current
   DESCRIPTION
   "
   Flow ID. For MA5600T, the index is between 1 and 16384;For MA5606T,the index is between 1 and 1024"
   ::= { hwDslamNtvFlowBasedMulticastPolicyEntry 1 } 

   hwDslamNtvUnknownMulticastTrafficPolicy OBJECT-TYPE
   SYNTAX  INTEGER{ transparent(2),discard(3) }
   MAX-ACCESS read-write
   STATUS current
   DESCRIPTION
   "
   The policy of unknown multicast traffic. "
   DEFVAL { 3 }
   ::= { hwDslamNtvFlowBasedMulticastPolicyEntry 2 } 
   
   hwDslamNtvIgmpPacketPolicy OBJECT-TYPE
   SYNTAX  INTEGER{ normal(1),transparent(2),discard(3) }
   MAX-ACCESS read-write
   STATUS current
   DESCRIPTION
   "
   The policy of igmp packet. "
   DEFVAL { 1 }
   ::= { hwDslamNtvFlowBasedMulticastPolicyEntry 3 } 

    hwDslamNtvV2RouterTimerout   OBJECT-TYPE
       SYNTAX       Integer32(1..5000)
       UNITS        "seconds"
       MAX-ACCESS   read-write
       STATUS       current
       DESCRIPTION
           "The Version 2 Router Present Timeout is how long a host must wait
            after hearing a Version 2 Query before it may send any IGMPv3
				messages."
       DEFVAL { 400 }
   ::= { hwDslamNtv 78 }
   
              
   ----------------------------------------------------------------
   --   MVlanMemberStatusTable --------
   ----------------------------------------------------------------
   hwDslamNtvMVlanMemberStatusTable OBJECT-TYPE
   SYNTAX SEQUENCE OF HwDslamNtvMVlanMemberStatusEntry
   MAX-ACCESS not-accessible
   STATUS current
   DESCRIPTION
   "NTV MVlanMemberStatusTable  "
   ::= { hwDslamNtv 80 }
   
   hwDslamNtvMVlanMemberStatusEntry OBJECT-TYPE
   SYNTAX HwDslamNtvMVlanMemberStatusEntry
   MAX-ACCESS not-accessible
   STATUS current
   DESCRIPTION
   	"hwDslamNtvMVlanMemberStatus "
   INDEX { 
          hwDslamNtvMVLANIndex,
          hwDslamNtvUserIndex
           }
   ::= { hwDslamNtvMVlanMemberStatusTable 1 }
   
   HwDslamNtvMVlanMemberStatusEntry ::= SEQUENCE {
     hwDslamNtvMVlanMemberStatus INTEGER{ enable(1),disable(2) }
     }
     
   hwDslamNtvMVlanMemberStatus OBJECT-TYPE
   SYNTAX  INTEGER{ enable(1),disable(2) }
   MAX-ACCESS read-write
   STATUS current
   DESCRIPTION
   "
   The status of membership between Mvlan and user,the user is a member of Mvlan or not."
   ::= { hwDslamNtvMVlanMemberStatusEntry 1 } 

   hwDslamNtvRouterInterAgingTime   OBJECT-TYPE
       SYNTAX   INTEGER(30..5000)
       MAX-ACCESS   read-write
       STATUS       current
       DESCRIPTION
           "The aging time of router interface.
            Default value: 260s."
       DEFVAL { 260 }     
   ::= { hwDslamNtv 81 }

   -- -------------------------------------------------------------------------   
   --        Allow to be router-interface table
   -- -------------------------------------------------------------------------       

    hwDslamNtvAllowToBeRouterInterTable    OBJECT-TYPE
        SYNTAX          SEQUENCE OF HwDslamNtvAllowToBeRouterInterEntry
        MAX-ACCESS      not-accessible
        STATUS          current
        DESCRIPTION
            "Port table which allow to be router interface."
    ::= { hwDslamNtv 82 }
    
    hwDslamNtvAllowToBeRouterInterEntry    OBJECT-TYPE
        SYNTAX          HwDslamNtvAllowToBeRouterInterEntry
        MAX-ACCESS      not-accessible
        STATUS          current
        DESCRIPTION
            "Allow to be router interface entity."
        INDEX { 
                  hwDslamNtvAllowToBeRouterInterIndex
              }
    ::= { hwDslamNtvAllowToBeRouterInterTable  1 }

   HwDslamNtvAllowToBeRouterInterEntry ::= SEQUENCE  {
            hwDslamNtvAllowToBeRouterInterIndex           Integer32,
            hwDslamNtvAllowToBeRouterInterRowStatus       RowStatus, 
            hwDslamNtvAllowToBeRouterInterFSP             Integer32
          }
                                    
    hwDslamNtvAllowToBeRouterInterIndex        OBJECT-TYPE
           SYNTAX       Integer32(0..128)
                   MAX-ACCESS   read-only
           STATUS       current
           DESCRIPTION
                "Port index which allow to be router interface."
    ::= { hwDslamNtvAllowToBeRouterInterEntry 1}   
    
    hwDslamNtvAllowToBeRouterInterRowStatus     OBJECT-TYPE
           SYNTAX       RowStatus
           MAX-ACCESS   read-create
           STATUS       current
           DESCRIPTION
               "Row status.
                Add or delete a table item."
    ::= { hwDslamNtvAllowToBeRouterInterEntry 2}   

    hwDslamNtvAllowToBeRouterInterFSP   OBJECT-TYPE
           SYNTAX       Integer32
           MAX-ACCESS   read-create
           STATUS       current
           DESCRIPTION
                "Combination of 'frame/slot/port' which allow to be router interface.
                Using 32 bits to express 'frame/slot/port'. The frame and slot both occupied 8 bits, 
                and the port occupied 16 bits. For example, 0/3/7 can expressed as 0x00 03 0007"
    ::= { hwDslamNtvAllowToBeRouterInterEntry 3}   
    
   -- -------------------------------------------------------------------------   
   --        Router interface Table
   -- -------------------------------------------------------------------------       
    hwDslamNtvRouterInterTable    OBJECT-TYPE
        SYNTAX          SEQUENCE OF HwDslamNtvRouterInterEntry
        MAX-ACCESS      not-accessible
        STATUS          current
        DESCRIPTION
             "The table included the router interface learned currently"
        ::=  { hwDslamNtv 83 }
        
    hwDslamNtvRouterInterEntry    OBJECT-TYPE
        SYNTAX          HwDslamNtvRouterInterEntry
        MAX-ACCESS      not-accessible
        STATUS          current
        DESCRIPTION
            "Router interface entity."
        INDEX { 
                  hwDslamNtvRouterInterIndex
              }
    ::= { hwDslamNtvRouterInterTable  1 }

   HwDslamNtvRouterInterEntry    ::= SEQUENCE  {
            hwDslamNtvRouterInterIndex        Integer32,
            hwDslamNtvRouterInterFSP          Integer32, 
            hwDslamNtvRouterInterVlan         Integer32,
            hwDslamNtvRouterInterTimeout      Integer32,
            hwDslamNtvRouterVersion           Integer32
           }
                                    
    hwDslamNtvRouterInterIndex        OBJECT-TYPE
           SYNTAX       Integer32
           MAX-ACCESS   read-only
           STATUS       current
           DESCRIPTION
                "Router interface index. 256 is the max value of the index"
    ::= { hwDslamNtvRouterInterEntry 1}   

    hwDslamNtvRouterInterFSP   OBJECT-TYPE
       SYNTAX       Integer32
       MAX-ACCESS   read-only
       STATUS       current
       DESCRIPTION          
		"Combination of 'frame/slot/port', which is the router interface learned.      
		Using 32 bits to express 'frame/slot/port'. The frame and slot both occupied 8 bits, 
		and the port occupied 16 bits. For example, 0/3/7 can expressed as 0x00030007 "	
   ::= { hwDslamNtvRouterInterEntry 2 }
   
   hwDslamNtvRouterInterVlan   OBJECT-TYPE
       SYNTAX       Integer32
       MAX-ACCESS   read-only
       STATUS       current
       DESCRIPTION
		"Vlan of the router interface"
   ::= { hwDslamNtvRouterInterEntry 3 }
    
   hwDslamNtvRouterInterTimeout   OBJECT-TYPE
       SYNTAX       Integer32
       MAX-ACCESS   read-only
       STATUS       current
       DESCRIPTION
		"The remain time of the router interface before deleted.
		After the system learned router interface, the router interface's aging timer is runing.
	        When it is timeout two times, the router intface will be deleted"
   ::= { hwDslamNtvRouterInterEntry 4 }

    hwDslamNtvRouterVersion  OBJECT-TYPE
           SYNTAX       Integer32 
           MAX-ACCESS   read-only
           STATUS       current
           DESCRIPTION
                "The IGMP Version of  multicast router.
		It is include V1/V2/V3 version."
    ::= { hwDslamNtvRouterInterEntry 5 }    

   -- -------------------------------------------------------------------------   
   --        Virtual upport Table
   -- -------------------------------------------------------------------------       

    hwDslamNtvVUpportTable    OBJECT-TYPE
        SYNTAX          SEQUENCE OF HwDslamNtvVUpportEntry
        MAX-ACCESS      not-accessible
        STATUS          current
        DESCRIPTION
            "Virtual upport management table"
    ::= { hwDslamNtv 84 }
    
    hwDslamNtvVUpportEntry    OBJECT-TYPE
        SYNTAX          HwDslamNtvVUpportEntry
        MAX-ACCESS      not-accessible
        STATUS          current
        DESCRIPTION
            "Virtual upport management entity."
        INDEX { 
                  hwDslamNtvVUpportTblIndex
              }
    ::= { hwDslamNtvVUpportTable  1 }

   HwDslamNtvVUpportEntry    ::= SEQUENCE  {
            hwDslamNtvVUpportTblIndex          Integer32,
            hwDslamNtvVUpportTblRowStatus      RowStatus, 
            hwDslamNtvVUpportTblInter          Integer32, 
            hwDslamNtvVUpportTblVlan           Integer32,
            hwDslamNtvVUpportTblRouterVersion  INTEGER,
          }
                                    
    hwDslamNtvVUpportTblIndex        OBJECT-TYPE
           SYNTAX       Integer32(1..1024)
           MAX-ACCESS   read-create
           STATUS       current
           DESCRIPTION
				"Virtual upport index."
    ::= { hwDslamNtvVUpportEntry 1}   
    
    hwDslamNtvVUpportTblRowStatus        OBJECT-TYPE
           SYNTAX       RowStatus
           MAX-ACCESS   read-create
           STATUS       current
           DESCRIPTION
               "Row status.
				Add or delete a table item."
    ::= { hwDslamNtvVUpportEntry 2}   
    
    hwDslamNtvVUpportTblInter   OBJECT-TYPE
       SYNTAX       Integer32
       MAX-ACCESS   read-create
       STATUS       current
       DESCRIPTION
				"Up Port.Frame/Slot/Port"
   ::= { hwDslamNtvVUpportEntry 3 }
   
   hwDslamNtvVUpportTblVlan   OBJECT-TYPE
       SYNTAX       Integer32(1..4093)
       MAX-ACCESS   read-create
       STATUS       current
       DESCRIPTION
				"VlanId of Up Port."
   ::= { hwDslamNtvVUpportEntry 4 }

    hwDslamNtvVUpportTblRouterVersion  OBJECT-TYPE
           SYNTAX       INTEGER (1..3)
           MAX-ACCESS   read-only
           STATUS       current
           DESCRIPTION
				"the current IGMP Version of  up port.It is include V1/V2/V3 version."
    ::= { hwDslamNtvVUpportEntry 5}

   -- -------------------------------------------------------------------------   
   --        UserQuery Table
   -- -------------------------------------------------------------------------       

    hwDslamNtvUserQueryTable    OBJECT-TYPE
        SYNTAX          SEQUENCE OF HwDslamNtvUserQueryEntry
        MAX-ACCESS      not-accessible
        STATUS          current
        DESCRIPTION
            "User query management table"
    ::= { hwDslamNtv 85 }
    
    hwDslamNtvUserQueryEntry    OBJECT-TYPE
        SYNTAX          HwDslamNtvUserQueryEntry
        MAX-ACCESS      not-accessible
        STATUS          current
        DESCRIPTION
            "User query management entity."
        INDEX { 
                  hwDslamNtvUserQueryIfIndex,
                  hwDslamNtvUserQueryVpi,
                  hwDslamNtvUserQueryVci,
                  hwDslamNtvUserQueryFlowType,
                  hwDslamNtvUserQueryFlowPara,
                  hwDslamNtvUserQueryMatchPara1,
                  hwDslamNtvUserQueryMatchPara2                 
              }
    ::= { hwDslamNtvUserQueryTable  1 }

   HwDslamNtvUserQueryEntry    ::= SEQUENCE  {
   	    hwDslamNtvUserQueryIfIndex      Integer32,
            hwDslamNtvUserQueryVpi          Integer32,
            hwDslamNtvUserQueryVci          Integer32, 
            hwDslamNtvUserQueryFlowType     INTEGER, 
            hwDslamNtvUserQueryFlowPara     Integer32,
            hwDslamNtvUserQueryMatchPara1   Integer32,
            hwDslamNtvUserQueryMatchPara2   Integer32,
            hwDslamNtvUserQueryIndex        Integer32
          }
                                    
    	hwDslamNtvUserQueryIfIndex OBJECT-TYPE
			SYNTAX Integer32
			MAX-ACCESS not-accessible
			STATUS current
			DESCRIPTION
			"the user ifindex."
			::= { hwDslamNtvUserQueryEntry 1 }		
    
        hwDslamNtvUserQueryVpi OBJECT-TYPE
	   SYNTAX Integer32
	   MAX-ACCESS not-accessible
	   STATUS current
	   DESCRIPTION
		"the VPI of PVC which carries IGMP messages."
	      ::= { hwDslamNtvUserQueryEntry 2 }

        hwDslamNtvUserQueryVci OBJECT-TYPE
	  SYNTAX Integer32
	  MAX-ACCESS not-accessible
	  STATUS current
	  DESCRIPTION
		  "the VCI of PVC which carries IGMP messages.
		   This value is the ICID of the PVC which carries IGMP messages."
		::= { hwDslamNtvUserQueryEntry 3 }

    	hwDslamNtvUserQueryFlowType OBJECT-TYPE
	                SYNTAX INTEGER
			{
			by-uservlan(1),
			by-encap(2),
			by-8021p(3),
			by-vlan-ethertype(4),
			singleflow(4294967295)
			}
			MAX-ACCESS not-accessible
			STATUS current
			DESCRIPTION
			"the type of flow"
			::= { hwDslamNtvUserQueryEntry 4 }
	
	hwDslamNtvUserQueryFlowPara OBJECT-TYPE
			SYNTAX Integer32
			MAX-ACCESS not-accessible
			STATUS current
			DESCRIPTION
			"the parameter of flow"
			::= { hwDslamNtvUserQueryEntry 5 }		
			
	hwDslamNtvUserQueryMatchPara1 OBJECT-TYPE
			SYNTAX Integer32
			MAX-ACCESS not-accessible
			STATUS current
			DESCRIPTION
			"the GemPortID of GPON port"
			::= { hwDslamNtvUserQueryEntry 6 }
			
	hwDslamNtvUserQueryMatchPara2 OBJECT-TYPE
			SYNTAX Integer32
			MAX-ACCESS not-accessible
			STATUS current
			DESCRIPTION
			"reserve"
			::= { hwDslamNtvUserQueryEntry 7 }			
			
	hwDslamNtvUserQueryIndex OBJECT-TYPE
			SYNTAX Integer32
			MAX-ACCESS read-only
			STATUS current
			DESCRIPTION
			"the user inner index"
			::= { hwDslamNtvUserQueryEntry 8 }	


   -- -------------------------------------------------------------------------   
   --        upstream mode
   -- -------------------------------------------------------------------------  
    hwDslamNtvUpstreamMode   OBJECT-TYPE
       SYNTAX       INTEGER { igmp(1),pim-ssm(2) }
       MAX-ACCESS   read-write
       STATUS       current
       DESCRIPTION
		   "Upstream work mode."
   ::= { hwDslamNtv 86 }

----------------------------------------------------------------
   --   UserExtendedAttributesTable --------
   ----------------------------------------------------------------
   hwDslamNtvUserExtendedAttributesTable OBJECT-TYPE
   SYNTAX SEQUENCE OF HwDslamNtvUserExtendedAttributesEntry
   MAX-ACCESS not-accessible
   STATUS current
   DESCRIPTION
   "NTV user extended attributes table  "
   ::= { hwDslamNtv 87 }
   
   hwDslamNtvUserExtendedAttributesEntry OBJECT-TYPE
   SYNTAX HwDslamNtvUserExtendedAttributesEntry
   MAX-ACCESS not-accessible
   STATUS current
   DESCRIPTION
   	"hwDslamNtvUserExtendedAttributes "
   INDEX { 
          hwDslamNtvUserInnerIndex
         }
   ::= { hwDslamNtvUserExtendedAttributesTable 1 }
   
   HwDslamNtvUserExtendedAttributesEntry ::= SEQUENCE {
     hwDslamNtvUserInnerIndex Integer32,
     hwDslamNtvUserHdtvWatchLimit INTEGER,
     hwDslamNtvUserSdtvWatchLimit INTEGER,  
     hwDslamNtvUserStreamingVideoWatchLimit INTEGER
     }
        
   hwDslamNtvUserInnerIndex OBJECT-TYPE
			SYNTAX Integer32
			MAX-ACCESS read-only
			STATUS current
			DESCRIPTION
			"the user inner index"
			::= { hwDslamNtvUserExtendedAttributesEntry 1 }	
			
   hwDslamNtvUserHdtvWatchLimit  OBJECT-TYPE
			SYNTAX       INTEGER
			MAX-ACCESS read-write
			STATUS current
			DESCRIPTION
			"The max number of a ntv user can watch HDTV"
			::= { hwDslamNtvUserExtendedAttributesEntry 2 } 
			
   hwDslamNtvUserSdtvWatchLimit  OBJECT-TYPE
			SYNTAX       INTEGER
			MAX-ACCESS read-write
			STATUS current
			DESCRIPTION
			"The max number of a ntv user can watch SDTV"
			::= { hwDslamNtvUserExtendedAttributesEntry 3 } 
			
   hwDslamNtvUserStreamingVideoWatchLimit  OBJECT-TYPE
			SYNTAX       INTEGER
			MAX-ACCESS read-write
			STATUS current
			DESCRIPTION
			"The max number of a ntv user can watch Streaming-Video"
			::= { hwDslamNtvUserExtendedAttributesEntry 4 } 						
			
			
   -- -------------------------------------------------------------------------   
   --        uplink-port version force to V2
   -- -------------------------------------------------------------------------  
    hwDslamNtvVersionForceSwitch   OBJECT-TYPE
       SYNTAX      TruthValue
       MAX-ACCESS  read-write
       STATUS      current
       DESCRIPTION
		   "Force switch upplink-port version to IGMP V2.
		   TRUE(enable) means that upport-port version is force to V2,
		   FALSE(disable) means thhat upport-port version is auto-selected.
		   The default vlaue is ‘enable’" 
   ::= { hwDslamNtv 88 }			
			
   -- ========================================================================
   --   BandwidthCACTable 
   -- ========================================================================
   hwDslamNtvBandwidthCACTable OBJECT-TYPE
   SYNTAX SEQUENCE OF HwDslamNtvBandwidthCACEntry
   MAX-ACCESS not-accessible
   STATUS current
   DESCRIPTION
   "NTV port bandwidth table"
   ::= { hwDslamNtv 89 }
   
   hwDslamNtvBandwidthCACEntry OBJECT-TYPE
   SYNTAX HwDslamNtvBandwidthCACEntry
   MAX-ACCESS not-accessible
   STATUS current
   DESCRIPTION
   	"hwDslamNtvBandwidthCAC "
   INDEX { 
          hwDslamNtvBandwidthCACifIndex
         }
   ::= { hwDslamNtvBandwidthCACTable 1 }
   
   HwDslamNtvBandwidthCACEntry ::= SEQUENCE {
     hwDslamNtvBandwidthCACifIndex InterfaceIndex,
     hwDslamNtvAssignBandwidth Integer32,
     hwDslamNtvUsedBandwidth Integer32  
     }   	
			
	 hwDslamNtvBandwidthCACifIndex OBJECT-TYPE
			SYNTAX InterfaceIndex
			MAX-ACCESS read-only
			STATUS current
			DESCRIPTION
			"The port ifindex"
			::= { hwDslamNtvBandwidthCACEntry 1 }
			
   hwDslamNtvAssignBandwidth  OBJECT-TYPE
			SYNTAX Integer32
			MAX-ACCESS read-write
			STATUS current
			DESCRIPTION
			"The max bandwidth of port(512 ~ 2608857 kbps), 0xFFFFFFFF indicates no limit. Default:716800 kbps"
			::= { hwDslamNtvBandwidthCACEntry 2 } 
			
   hwDslamNtvUsedBandwidth  OBJECT-TYPE
			SYNTAX Integer32
			MAX-ACCESS read-only
			STATUS current
			DESCRIPTION
			"The used bandwidth of port"
			::= { hwDslamNtvBandwidthCACEntry 3 } 
 
-- -------------------------------------------------------------------------   
   --        MVlan igmp statistic Management Table
   -- -------------------------------------------------------------------------       
    hwDslamNtvMVlanIgmpStatTable    OBJECT-TYPE
        SYNTAX          SEQUENCE OF HwDslamNtvMVlanIgmpStatEntry
        MAX-ACCESS      not-accessible
        STATUS          current
        DESCRIPTION
            "MVlan igmp statistic Management Table"
        ::= { hwDslamNtv 90 }
    
    hwDslamNtvMVlanIgmpStatEntry    OBJECT-TYPE
        SYNTAX         HwDslamNtvMVlanIgmpStatEntry
        MAX-ACCESS     not-accessible
        STATUS         current
        DESCRIPTION
        "MVlan igmp statistic Management entity"
        INDEX   { 
                   hwDslamNtvMVlanIgmpStatMVlanIndex
                }
        ::= { hwDslamNtvMVlanIgmpStatTable  1 }

    HwDslamNtvMVlanIgmpStatEntry    ::= SEQUENCE  {
            hwDslamNtvMVlanIgmpStatMVlanIndex      Integer32,
            hwDslamNtvMVlanIgmpStatOperMode        INTEGER,
            hwDslamNtvMVlanIgmpStatGenQueryRcv     Integer32,  
            hwDslamNtvMVlanIgmpStatSpecQueryRcv    Integer32,       
            hwDslamNtvMVlanIgmpStatReportV2Rcv     Integer32,
            hwDslamNtvMVlanIgmpStatErrV2ReportRcv  Integer32,  
            hwDslamNtvMVlanIgmpStatReportV3Rcv     Integer32,
            hwDslamNtvMVlanIgmpStatErrV3ReportRcv  Integer32,   
            hwDslamNtvMVlanIgmpStatLeaveRcv        Integer32,
            hwDslamNtvMVlanIgmpStatGenQuerySnd     Integer32,
            hwDslamNtvMVlanIgmpStatSpecQuerySnd    Integer32,
            hwDslamNtvMVlanIgmpStatReportV2Snd     Integer32,
            hwDslamNtvMVlanIgmpStatReportV3Snd     Integer32,  
            hwDslamNtvMVlanIgmpStatLeaveSnd        Integer32, 
            hwDslamNtvMVlanIgmpActiveProgramNum    Integer32,   
            hwDslamNtvMVlanIgmpActiveUserNum       Integer32,   
            hwDslamNtvMVlanIgmpStatInvalidRcv      Integer32,    
           }
           
    hwDslamNtvMVlanIgmpStatMVlanIndex       OBJECT-TYPE
            SYNTAX Integer32 (1..256)
            MAX-ACCESS read-only
            STATUS current
            DESCRIPTION
            "Index of MVLAN."
    ::= { hwDslamNtvMVlanIgmpStatEntry 1 }
                   
    hwDslamNtvMVlanIgmpStatOperMode        OBJECT-TYPE
           SYNTAX   INTEGER{ clear-statistic(1) }
           MAX-ACCESS   read-write
           STATUS       current
           DESCRIPTION
               "IGMP statistic operation mode.1-Clear IGMP statistic result."
    ::= { hwDslamNtvMVlanIgmpStatEntry 2}
      
    hwDslamNtvMVlanIgmpStatGenQueryRcv    OBJECT-TYPE
           SYNTAX   Integer32 
           MAX-ACCESS   read-only
           STATUS       current
           DESCRIPTION
               "The number of general query packet received."
    ::= { hwDslamNtvMVlanIgmpStatEntry 3}

    hwDslamNtvMVlanIgmpStatSpecQueryRcv   OBJECT-TYPE
           SYNTAX   Integer32 
           MAX-ACCESS   read-only
           STATUS       current
           DESCRIPTION
               "The number of specific query packet received."
    ::= { hwDslamNtvMVlanIgmpStatEntry 4}

    hwDslamNtvMVlanIgmpStatReportV2Rcv    OBJECT-TYPE
           SYNTAX   Integer32 
           MAX-ACCESS   read-only
           STATUS       current
           DESCRIPTION
               "The number of report packet of version 2 received."
    ::= { hwDslamNtvMVlanIgmpStatEntry 5}

    hwDslamNtvMVlanIgmpStatErrV2ReportRcv    OBJECT-TYPE
           SYNTAX   Integer32 
           MAX-ACCESS   read-only
           STATUS       current
           DESCRIPTION
               "The number of error report packet of version 2 received."
    ::= { hwDslamNtvMVlanIgmpStatEntry 6}
    
    hwDslamNtvMVlanIgmpStatReportV3Rcv    OBJECT-TYPE
           SYNTAX   Integer32 
           MAX-ACCESS   read-only
           STATUS       current
           DESCRIPTION
               "The number of report packet of version 3 received."
    ::= { hwDslamNtvMVlanIgmpStatEntry 7}
    
    hwDslamNtvMVlanIgmpStatErrV3ReportRcv    OBJECT-TYPE
           SYNTAX   Integer32 
           MAX-ACCESS   read-only
           STATUS       current
           DESCRIPTION
               "The number of error report packet of version 3 received."
    ::= { hwDslamNtvMVlanIgmpStatEntry 8}
    
    hwDslamNtvMVlanIgmpStatLeaveRcv    OBJECT-TYPE
           SYNTAX   Integer32 
           MAX-ACCESS   read-only
           STATUS       current
           DESCRIPTION
               "The number of leave packet received."
    ::= { hwDslamNtvMVlanIgmpStatEntry 9}
			
    hwDslamNtvMVlanIgmpStatGenQuerySnd    OBJECT-TYPE
           SYNTAX   Integer32 
           MAX-ACCESS   read-only
           STATUS       current
           DESCRIPTION
               "The number of general query packet send out."
    ::= { hwDslamNtvMVlanIgmpStatEntry 10}	
    		
    hwDslamNtvMVlanIgmpStatSpecQuerySnd    OBJECT-TYPE
           SYNTAX   Integer32 
           MAX-ACCESS   read-only
           STATUS       current
           DESCRIPTION
               "The number of specific query packet send out."
    ::= { hwDslamNtvMVlanIgmpStatEntry 11}
    		
    hwDslamNtvMVlanIgmpStatReportV2Snd    OBJECT-TYPE
           SYNTAX   Integer32 
           MAX-ACCESS   read-only
           STATUS       current
           DESCRIPTION
               "The number of report packet of version 2 send out."
    ::= { hwDslamNtvMVlanIgmpStatEntry 12}
    		
    hwDslamNtvMVlanIgmpStatReportV3Snd    OBJECT-TYPE
           SYNTAX   Integer32 
           MAX-ACCESS   read-only
           STATUS       current
           DESCRIPTION
               "The number of report packet of version 3 send out."
    ::= { hwDslamNtvMVlanIgmpStatEntry 13}
    
    hwDslamNtvMVlanIgmpStatLeaveSnd    OBJECT-TYPE
           SYNTAX   Integer32 
           MAX-ACCESS   read-only
           STATUS       current
           DESCRIPTION
               "The number of leave packet send out."
    ::= { hwDslamNtvMVlanIgmpStatEntry 14}
    
    hwDslamNtvMVlanIgmpActiveProgramNum    OBJECT-TYPE
           SYNTAX   Integer32 
           MAX-ACCESS   read-only
           STATUS       current
           DESCRIPTION
               "The number of actived program in Mvlan."
    ::= { hwDslamNtvMVlanIgmpStatEntry 15}
    
    hwDslamNtvMVlanIgmpActiveUserNum    OBJECT-TYPE
           SYNTAX   Integer32 
           MAX-ACCESS   read-only
           STATUS       current
           DESCRIPTION
               "The number of actived user in Mvlan."
    ::= { hwDslamNtvMVlanIgmpStatEntry 16}
    
    hwDslamNtvMVlanIgmpStatInvalidRcv    OBJECT-TYPE
           SYNTAX   Integer32 
           MAX-ACCESS   read-only
           STATUS       current
           DESCRIPTION
               "The number of invalid packet received."
    ::= { hwDslamNtvMVlanIgmpStatEntry 17}
    
-- -------------------------------------------------------------------------   
   --        User igmp statistic Management Table
   -- -------------------------------------------------------------------------       
    hwDslamNtvUserIgmpStatTable    OBJECT-TYPE
        SYNTAX          SEQUENCE OF HwDslamNtvUserIgmpStatEntry
        MAX-ACCESS      not-accessible
        STATUS          current
        DESCRIPTION
            "User igmp statistic Management Table"
        ::= { hwDslamNtv 91 }
    
    hwDslamNtvUserIgmpStatEntry    OBJECT-TYPE
        SYNTAX         HwDslamNtvUserIgmpStatEntry
        MAX-ACCESS     not-accessible
        STATUS         current
        DESCRIPTION
        "User igmp statistic Management entity"
        INDEX   { 
                   hwDslamNtvUserIgmpStatUserIndex
                }
        ::= { hwDslamNtvUserIgmpStatTable  1 }

    HwDslamNtvUserIgmpStatEntry    ::= SEQUENCE  {
            hwDslamNtvUserIgmpStatUserIndex       Integer32,
            hwDslamNtvUserIgmpStatOperMode        INTEGER, 
            hwDslamNtvUserIgmpStatReportV1Rcv     Integer32, 
            hwDslamNtvUserIgmpStatErrV1ReportRcv  Integer32,    
            hwDslamNtvUserIgmpStatReportV2Rcv     Integer32,
            hwDslamNtvUserIgmpStatErrV2ReportRcv  Integer32, 
            hwDslamNtvUserIgmpStatReportV3Rcv    Integer32,
            hwDslamNtvUserIgmpStatErrV3ReportRcv  Integer32,   
            hwDslamNtvUserIgmpStatV2LeaveRcv      Integer32,
            hwDslamNtvUserIgmpStatGenQuerySnd     Integer32,
            hwDslamNtvUserIgmpStatSpecQuerySnd    Integer32,  
            hwDslamNtvUserIgmpStatInvalidRcv      Integer32,    
           }
           
    hwDslamNtvUserIgmpStatUserIndex       OBJECT-TYPE
            SYNTAX Integer32 (1..256)
            MAX-ACCESS read-only
            STATUS current
            DESCRIPTION
            "Index of user."
    ::= { hwDslamNtvUserIgmpStatEntry 1 }
                   
    hwDslamNtvUserIgmpStatOperMode        OBJECT-TYPE
           SYNTAX   INTEGER{ clear-statistic(1) }
           MAX-ACCESS   read-write
           STATUS       current
           DESCRIPTION
               "IGMP statistic operation mode.1-Clear IGMP statistic result."
    ::= { hwDslamNtvUserIgmpStatEntry 2}
   
    hwDslamNtvUserIgmpStatReportV1Rcv    OBJECT-TYPE
           SYNTAX   Integer32 
           MAX-ACCESS   read-only
           STATUS       current
           DESCRIPTION
               "The number of report packet of version v1 received."
    ::= { hwDslamNtvUserIgmpStatEntry 3} 
    
    hwDslamNtvUserIgmpStatErrV1ReportRcv    OBJECT-TYPE
           SYNTAX   Integer32 
           MAX-ACCESS   read-only
           STATUS       current
           DESCRIPTION
               "The number of error report packet of version v1 received."
    ::= { hwDslamNtvUserIgmpStatEntry 4} 
    
    hwDslamNtvUserIgmpStatReportV2Rcv    OBJECT-TYPE
           SYNTAX   Integer32 
           MAX-ACCESS   read-only
           STATUS       current
           DESCRIPTION
               "The number of report packet of version v2 received."
    ::= { hwDslamNtvUserIgmpStatEntry 5} 
    
    hwDslamNtvUserIgmpStatErrV2ReportRcv    OBJECT-TYPE
           SYNTAX   Integer32 
           MAX-ACCESS   read-only
           STATUS       current
           DESCRIPTION
               "The number of error report packet of version v2 received."
    ::= { hwDslamNtvUserIgmpStatEntry 6} 
    
    hwDslamNtvUserIgmpStatReportV3Rcv    OBJECT-TYPE
           SYNTAX   Integer32 
           MAX-ACCESS   read-only
           STATUS       current
           DESCRIPTION
               "The number of report packet of version v3 received."
    ::= { hwDslamNtvUserIgmpStatEntry 7} 
    
    hwDslamNtvUserIgmpStatErrV3ReportRcv    OBJECT-TYPE
           SYNTAX   Integer32 
           MAX-ACCESS   read-only
           STATUS       current
           DESCRIPTION
               "The number of error report packet of version v3 received."
    ::= { hwDslamNtvUserIgmpStatEntry 8} 
        
    hwDslamNtvUserIgmpStatV2LeaveRcv    OBJECT-TYPE
           SYNTAX   Integer32 
           MAX-ACCESS   read-only
           STATUS       current
           DESCRIPTION
               "The number of leave packet of version v2 received."
    ::= { hwDslamNtvUserIgmpStatEntry 9} 
     
    hwDslamNtvUserIgmpStatGenQuerySnd    OBJECT-TYPE
           SYNTAX   Integer32 
           MAX-ACCESS   read-only
           STATUS       current
           DESCRIPTION
               "The number of general query packet send out."
    ::= { hwDslamNtvUserIgmpStatEntry 10} 
    
    hwDslamNtvUserIgmpStatSpecQuerySnd    OBJECT-TYPE
           SYNTAX   Integer32 
           MAX-ACCESS   read-only
           STATUS       current
           DESCRIPTION
               "The number of specific query packet send out."
    ::= { hwDslamNtvUserIgmpStatEntry 11} 
    
    hwDslamNtvUserIgmpStatInvalidRcv    OBJECT-TYPE
           SYNTAX   Integer32 
           MAX-ACCESS   read-only
           STATUS       current
           DESCRIPTION
               "The number of invalid packet received."
    ::= { hwDslamNtvUserIgmpStatEntry 12} 
    
    
      
   -- -----------------------------------------------------------------------
   -- Incremental modify rightprofile table
   -- ------------------------------------------------------------------------ 
   hwDslamNtvIncrementalModifyRightProfileTable    OBJECT-TYPE
       SYNTAX          SEQUENCE OF HwDslamNtvIncrementalModifyRightProfileEntry
       MAX-ACCESS      not-accessible
       STATUS          current
       DESCRIPTION
           "Incremental modify rightprofile table"
   ::= { hwDslamNtv 92 }
   
   hwDslamNtvIncrementalModifyRightProfileEntry    OBJECT-TYPE
       SYNTAX          HwDslamNtvIncrementalModifyRightProfileEntry
       MAX-ACCESS      not-accessible
       STATUS          current
       DESCRIPTION
           "Incremental modify rightprofile entity."
       INDEX { 
                 hwDslamNtvRightProfileIndex
             }
   ::= { hwDslamNtvIncrementalModifyRightProfileTable  1 }
   
   HwDslamNtvIncrementalModifyRightProfileEntry    ::= SEQUENCE  {
           hwDslamNtvIncrementalModifyRightProfileMask      OCTET STRING
       }
   
   hwDslamNtvIncrementalModifyRightProfileMask      OBJECT-TYPE
          SYNTAX       OCTET STRING (SIZE (0..2048))
          MAX-ACCESS   read-write
          STATUS       current
          DESCRIPTION
              "One program has two octets' mask.
               The format of the mask is ( Right bits:[15~14] + Reserve bits:[13~11] + Program Index bits:[10~0] ).
               Right bits(15,14)：00=idle,01=watch,10=preview,11=forbidden .
               The scope of program index is 1~1024.
               The length of the RightProfileMask is the number of programs * 2 octets. "
   ::= { hwDslamNtvIncrementalModifyRightProfileEntry 1} 
   
   
   hwDslamNtvIgmpVersion OBJECT-TYPE
   	SYNTAX  INTEGER{ igmpv2(1),igmpv3(2)}
   	MAX-ACCESS read-write
   	STATUS current
   	DESCRIPTION
   		"
    		igmp version.
   		"
   DEFVAL { 1 }
   ::= { hwDslamNtv 93 }
    
   
   hwDslamNtvIgmpPriority OBJECT-TYPE
   	SYNTAX  INTEGER (0..7)
   	MAX-ACCESS read-write
   	STATUS current
   	DESCRIPTION
   		"
    		igmp priority.
   		"
	DEFVAL { 0 }
   	::= { hwDslamNtv 94 } 


   hwDslamNtvCdrSwitch  OBJECT-TYPE
       SYNTAX      TruthValue
       MAX-ACCESS  read-write
       STATUS      current
       DESCRIPTION
          "The system Cdr switch.  
           If the value is true, the Cdr switch is on.
           If the value is false, the Cdr switch is off. "
   ::= { hwDslamNtv 95 }

   hwDslamNtvInitialUnsolicitedReportInterval  OBJECT-TYPE
       SYNTAX       Integer32(1..10)
       MAX-ACCESS   read-write
       STATUS       current
       DESCRIPTION
           "Unsolicited Report Interval. 
            Value ranges from 1 to 10. If it is changed, the State-Change Report retransmitted intervals are changed."
       DEFVAL { 1 }
   ::= { hwDslamNtv 96 }

	hwDslamNtvQueryMode OBJECT-TYPE
       SYNTAX   INTEGER{
                         with-cvlan(1),
                         with-mvlan(2)
                       }
       MAX-ACCESS   read-write
       STATUS       current
       DESCRIPTION
           "The mode to send query package to EPON user."
       DEFVAL { 1 }
    ::= { hwDslamNtv 97}        
    
    	hwDslamNtvIgmpUpstreamVlanMode OBJECT-TYPE
       SYNTAX   INTEGER{
                         mvlan(1),
                         svlan(2),
                         vlan(3)
                       }
       MAX-ACCESS   read-write
       STATUS       current
       DESCRIPTION
           "The vlan mode of upstream igmp packet."
    ::= { hwDslamNtv 98}        
    
    	hwDslamNtvIgmpUpstreamVlanPara OBJECT-TYPE
       SYNTAX   INTEGER
       MAX-ACCESS   read-write
       STATUS       current
       DESCRIPTION
           "The vlan parameter of upstream igmp packet."
    ::= { hwDslamNtv 99}   
         
        hwDslamNtvEnvironmentModeSwitch OBJECT-TYPE
       SYNTAX   INTEGER{
                         non-mvlan-mode(1),
                         mvlan-mode(2)
                       }
       MAX-ACCESS   read-write
       STATUS       current
       DESCRIPTION
           "The swtich is offered to select a BTV environment between R3&R5. 
           'R3' indicate BTV running under non-mvlan-mode mode,
           Otherwise the BTV running under mvlan-mode mode."
       DEFVAL { 1 }
    ::= { hwDslamNtv 100}      
    
    	hwDslamNtvIgmpGlobalLeaveSendSwitch OBJECT-TYPE
       SYNTAX   INTEGER{
                         enable(1),
                         disable(2)
                       }
       MAX-ACCESS   read-write
       STATUS       current
       DESCRIPTION
           "the switch of Global-Leave sending."
       DEFVAL { 1 }
           
    ::= { hwDslamNtv 101}

		hwDslamNtvForwardMode OBJECT-TYPE
       SYNTAX   INTEGER{
                         mvlan(1),
                         global-ip(2)
                       }
       MAX-ACCESS   read-write
       STATUS       current
       DESCRIPTION
           "The swtich is offered to select a BTV forwarding mode between mvlan and global-ip.
           '1' is mvlan mode. '2' is global-ip mode."
       DEFVAL { 1 }

    ::= { hwDslamNtv 102}
    
       hwDslamNtvSendQueryToOfflineUserSwitch  OBJECT-TYPE
       SYNTAX      TruthValue
       MAX-ACCESS  read-write
       STATUS      current
       DESCRIPTION
           		"The system send query to offline BTV user switch.  
           If the value is true, the switch is on.
           If the value is false, the switch is off. "
   ::= { hwDslamNtv 103 }
      
END
