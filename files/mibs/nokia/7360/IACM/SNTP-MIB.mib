SNTP-MIB DEFINITIONS ::= BEGIN

-- ===========================================================================
--  This specification is published by Alcatel under Non-Disclosure
--  Agreement(s) (NDA) with specific parties and has to be considered as
--  Confidential Information as defined in such NDA.
--  Alcatel reserves the right to revise this document for any reason,
--  including but not limited to conformity with standards promulgated by
--  various agencies, utilisation of advances in the state of the technical
--  areas, or the reflection of changes in the design of any equipment,
--  techniques, or procedures described or referred to herein.
--  The product specifications and other technical or performance information
--  contained herein are subject to change without notice.
--  Updates of this document will be issued under the above NDA's.
--  Alcatel makes no representation or warranty, expressed or implied, with
--  respect to the sufficiency, accuracy, or utility of any information or
--  opinion contained herein. Alcatel expressly advises that any use of for 
--  any purpose or reliance upon this technical reference is at the risk of
--  the user and that Alcatel shall not be liable for any damage or injury
--  incurred by any person arising out of the sufficiency, accuracy, or
--  utility of any information or opinion contained herein.
--  This document is not to be construed as a suggestion to any manufacturer
--  to modify or change any of its products, nor does this document represent
--  any commitment by Alcatel to sell or purchase any product.
--  Nothing contained herein shall be construed as conferring by implication,
--  estoppel, or otherwise any license or right under any patent, whether or
--  not the use of any information herein necessarily employs an invention of
--  any existing or later issued patent.
--  Alcatel reserves the right not to offer any or all of these products and
--  to withdraw any or all of them at any future time.
--  Copyright (C) 2006, Alcatel. All Rights Reserved.
-- ===========================================================================

--  MODULE-IDENTITY
--  LAST-UPDATED   "201103210000Z"
--  ORGANIZATION   "Alcatel"
--  CONTACT-INFO
--
--          Email:  asam.mibsupport@alcatel.be"
--
--  DESCRIPTION
--        "This MIB module defines objects for management of the SNTP
--         client.
--
--  REVISION 201702180000Z
--  DESCRIPTION
--        "Version:  3EC15584EAAA_V5.7.0.0.0
--         Editor:   Meeus Ronny
--         Changes:  ALU02295160 Add support for asamSNTPBootTimeSeconds"
--
--  REVISION 201106070000Z
--  DESCRIPTION
--        "Version:  3EC15584EAAA_V4.3.0.0.0
--         Editor:   Madhusudanan Subramanian
--         Changes:  Removed the asamSNTPServerProxyACLTable"
--
--  REVISION 201103210000Z
--  DESCRIPTION
--        "Version:  3EC15584EAAA_V4.1.0.1.3
--         Editor:   Karel Meijfroidt
--         Changes:  ALU01175199: Updated description of the asamSNTPTimeSeconds
--                   MIB object on request of customer DT"
--
--  REVISION 201103140000Z
--  DESCRIPTION
--        "Version:  3EC15584EAAA_V4.3.0.0.0
--         Editor:   Madhusudanan Subramanian
--         Changes:  ALU00966975: Added SNTP server proxy ACL Table"
--
--  REVISION 200907140000Z
--  DESCRIPTION
--        "Version:  3EC15584EAAA_V4.1.0.0.0
--         Editor:   Selvaraj Palaniyappan
--         Changes:  *ANTmt61831:SNTP MIB Cleanup"
--
--  REVISION 200605180000Z
--  DESCRIPTION
--        "Version:  3EC15584EAAA_V3.2.0.0.0
--         Editor:   Marc Van Vlimmeren
--         Changes:  Updates for PB template conformance"
--
--  REVISION 200503230000Z
--  DESCRIPTION
--        "Version:  3EC15584EAAA_V2.4.0.0.0
--         Editor:   Bart Bogaert
--         Changes:  Implemented BDFhw70643: strict syntax checks (smilint)"
--
--  REVISION 199701130000Z
--  DESCRIPTION
--        "Version:  33EC15584AAAA_V1.0.0.0.0
--         Editor:   Kurt Pynaert
--         Changes:  Initial version"

-- ============================================================================


IMPORTS

    IpAddress
        FROM RFC1155-SMI

    OBJECT-TYPE
	FROM RFC-1212
    
    Gauge
         FROM RFC1155-SMI

    NetworkTimeInSeconds, NetworkTimeInMiliSeconds
        FROM ASAM-TC-MIB

    asam
        FROM SYSTEM-MIB
    
    RowStatus
        FROM SNMPv2-TC

    EqptSlotIndex
        FROM ASAM-EQUIP-MIB
	
    InetAddress, InetAddressType, InetPortNumber
        FROM INET-ADDRESS-MIB
    TruthValue                      
        FROM SNMPv2-TC;

-- ============================================================================
-- Type Definitions
-- ============================================================================

SNTPOperatingMode		::= INTEGER {
				unicast		(1), 
				anycast 	(2),
				multicast	(3)}


SNTPEnableDisable		::= INTEGER {
				enable		(1),
				disable		(2)}

Uint32 ::= Gauge (0 .. 4294967295)

-- ============================================================================
-- Object Definitions
-- ============================================================================

asamSNTPMIB			OBJECT IDENTIFIER ::=	{ asam 13 }

asamSNTPServerIpAddress OBJECT-TYPE
    SYNTAX   IpAddress
    ACCESS   read-write
    STATUS   mandatory
    DESCRIPTION
        "IpAddress of the SNTP Server.
        ALCATEL NOTE:
            ACCESS:      NA           USAGE:       NA
            PERSIST:     YES          INSRVMOD:    YES
            RANGE:       NA           DEFVALUE:    0.0.0.0
            UNITS:       NA           SPARSE:      NA
            DESCR:       NA"
::= {asamSNTPMIB 1}

asamSNTPServerPort OBJECT-TYPE
    SYNTAX   INTEGER (0..65535)
    ACCESS   read-write
    STATUS   mandatory
    DESCRIPTION
        "Port number of the SNTP Server.
        ALCATEL NOTE:
            ACCESS:      NA           USAGE:       NA
            PERSIST:     YES          INSRVMOD:    YES
            RANGE:       NA           DEFVALUE:    123
            UNITS:       NA           SPARSE:      NA
            DESCR:       NA"
::= {asamSNTPMIB 2}

asamSNTPPollingRate OBJECT-TYPE
    SYNTAX   INTEGER (60..864000)
    ACCESS   read-write
    STATUS   mandatory
    DESCRIPTION
        "The polling period.
        ALCATEL NOTE:
            ACCESS:      NA           USAGE:       NA
            PERSIST:     YES          INSRVMOD:    YES
            RANGE:       NA           DEFVALUE:    3600
            UNITS:       seconds      SPARSE:      NA
            DESCR:       NA"
::=	{asamSNTPMIB 3}

asamSNTPEnableDisable OBJECT-TYPE
    SYNTAX   SNTPEnableDisable
    ACCESS   read-write
    STATUS   mandatory
    DESCRIPTION
        "This object manages the functionality of the SNTP cliemt.
        If it is set to enable, the SNTP client becomes active.
        If it is set to disable, the Network Time is not polled.
        ALCATEL NOTE:
            ACCESS:      NA           USAGE:       NA
            PERSIST:     YES          INSRVMOD:    YES
            RANGE:       NA           DEFVALUE:    disable
            UNITS:       NA           SPARSE:      NA
            DESCR:       NA"
::= {asamSNTPMIB 4}

asamSNTPTimeSeconds OBJECT-TYPE
    SYNTAX   Uint32
    ACCESS   read-write
    STATUS   mandatory
    DESCRIPTION
    	"This object gives the network time in seconds. It is the integer part
         of the NTP Timestamp which means the number of standard seconds since
         0h on 1 January 1900. This object is read-write.
         The Network time can be set by the operator by means of this object.
        ALCATEL NOTE:
            ACCESS:      NA           USAGE:       NA
            PERSIST:     NO           INSRVMOD:    YES
            RANGE:       NA           DEFVALUE:    0
            UNITS:       seconds      SPARSE:      NA
            DESCR:       NA"
::= {asamSNTPMIB 5}

asamSNTPTimeFractionOfSeconds OBJECT-TYPE
    SYNTAX   INTEGER (1..4294967295)
    ACCESS   read-write
    STATUS   mandatory
    DESCRIPTION
        "This object gives the milliseconds elapsed in a second.
        This object is read-write. The Network time can be set
        by the Operator by means of this object.
        ALCATEL NOTE:
            ACCESS:      NA           USAGE:       NA
            PERSIST:     NO           INSRVMOD:    YES
            RANGE:       NA           DEFVALUE:    0
            UNITS:       milliseconds SPARSE:      NA
            DESCR:       NA"
::= {asamSNTPMIB 6}

asamSNTPOperatingMode OBJECT-TYPE
    SYNTAX   SNTPOperatingMode
    ACCESS   read-only
    STATUS   mandatory
    DESCRIPTION
        "This object gives the operating mode for the SNTP client.
        ALCATEL NOTE:
            ACCESS:      NA           USAGE:       NA
            PERSIST:     NO           INSRVMOD:    YES
            RANGE:       NA           DEFVALUE:    unicast
            UNITS:       NA           SPARSE:      NA
            DESCR:       NA"
::= {asamSNTPMIB 7}

--
--asamSNTPServerProxyACLTable OBJECT-TYPE
--    SYNTAX  SEQUENCE OF AsamSNTPServerProxyACLEntry
--    ACCESS  not-accessible
--    STATUS  mandatory
--    DESCRIPTION
--        "A list of SNTP server IP addresses per VLAN per LT. 
--         Maximum number of entries is 108"
--::= {asamSNTPMIB 8}
--
--asamSNTPServerProxyACLEntry OBJECT-TYPE
--    SYNTAX  AsamSNTPServerProxyACLEntry
--    ACCESS  not-accessible
--    STATUS  mandatory
--    DESCRIPTION
--        "An SNTP Proxy Vlan entry containing list of SNTP Server 
--         Addresses being proxied on the VLAN-LT combination."
--    INDEX {asamSNTPServerProxyACLVlan,
--           asamSNTPServerProxyACLLim,
--	   asamSNTPServerProxyACLIPAddress}
--::= {asamSNTPServerProxyACLTable 1}
--
--AsamSNTPServerProxyACLEntry ::=
--    SEQUENCE {asamSNTPServerProxyACLVlan INTEGER,
--              asamSNTPServerProxyACLLim EqptSlotIndex,
--              asamSNTPServerProxyACLIPAddress IpAddress,
--              asamSNTPServerProxyACLRowStatus RowStatus}
--
--asamSNTPServerProxyACLVlan  OBJECT-TYPE
--    SYNTAX  INTEGER (0..65535)
--    ACCESS  read-only
--    STATUS  mandatory
--    DESCRIPTION 
--         "A value indicating the VLAN_ID to which this entry belongs."
--::= {asamSNTPServerProxyACLEntry 1}
--
--asamSNTPServerProxyACLLim  OBJECT-TYPE
--    SYNTAX  EqptSlotIndex
--    ACCESS  read-only
--   STATUS  mandatory
--  DESCRIPTION 
--         "A value indicating the LT_ID to which this entry belongs."
--::= {asamSNTPServerProxyACLEntry 2}
--
--asamSNTPServerProxyACLIPAddress  OBJECT-TYPE
--    SYNTAX  IpAddress
--    ACCESS  read-only
--    STATUS  mandatory 
--    DESCRIPTION 
--         "SNTP Server IP to be proxied."
--::= {asamSNTPServerProxyACLEntry 3}
--
--asamSNTPServerProxyACLRowStatus OBJECT-TYPE
--      SYNTAX  RowStatus
--     ACCESS  read-write
--      STATUS  mandatory
--      DESCRIPTION
--         "This object indicates the status of this entry.
--                 ALCATEL NOTE:
--                        ACCESS:     NA       USAGE:      MAND
--                        PERSIST:    NO       INSRVMOD:   NO
--                        RANGE:      1,6      DEFVALUE:   NA
--                        UNITS:      NA       SPARSE:     NA
--                        DESCR:      NA"
--::= {asamSNTPServerProxyACLEntry 4}
--

asamSNTPServerConfTable OBJECT-TYPE
    SYNTAX   SEQUENCE OF AsamSNTPServerConfEntry
    ACCESS   not-accessible
    STATUS   mandatory
    DESCRIPTION
          "	The table listing the SNTP servers with their configurable 
           parameters. This table will have maximum 3 entries corresponding
           to values 1 to 3 for asamSNTPServerConfPriority."
::= { asamSNTPMIB 9 }

asamSNTPBootTimeSeconds OBJECT-TYPE
    SYNTAX   Uint32
    ACCESS   read-only
    STATUS   mandatory
    DESCRIPTION
    	"This object gives the boot time in seconds. It is the integer part
         of the NTP Timestamp which means the number of standard seconds since
         0h on 1 January 1900. This object is read-only.
         At the moment the asamSNTPTimeSeconds field is set for the first time
         the localtime is used to calculate the boottime of the system.
        ALCATEL NOTE:
            ACCESS:      NA           USAGE:       NA
            PERSIST:     NO           INSRVMOD:    YES
            RANGE:       NA           DEFVALUE:    0
            UNITS:       seconds      SPARSE:      NA
            DESCR:       NA"
::= {asamSNTPMIB 10}

asamSNTPServerConfEntry OBJECT-TYPE
    SYNTAX   AsamSNTPServerConfEntry
    ACCESS	 not-accessible
    STATUS   mandatory
    DESCRIPTION
            "An entry representing the configuration of a SNTP server."
    INDEX { asamSNTPServerConfAddrType, asamSNTPServerConfAddress }
::= { asamSNTPServerConfTable 1 }

AsamSNTPServerConfEntry ::=
    SEQUENCE {
		  asamSNTPServerConfAddrType         InetAddressType,
	  asamSNTPServerConfAddress			InetAddress,
	  asamSNTPServerConfPort  			InetPortNumber,
	  asamSNTPServerConfPriority			INTEGER,
	  asamSNTPServerConfIsSyncSource		TruthValue,
	  asamSNTPServerConfRowStatus		    RowStatus
      	 }

asamSNTPServerConfAddrType   OBJECT-TYPE
     SYNTAX   InetAddressType
     ACCESS   not-accessible
     STATUS   mandatory
     DESCRIPTION
	 "The value of asamSNTPServerConfAddrType indicates the address 
              type of the asamSNTPServerConfAddress address.
              ALCATEL NOTE:
                 ACCESS:      NA            USAGE:       NA
                 PERSIST:     YES           INSRVMOD:    NA
                 RANGE:       1 - only ipv4 DEFVALUE:    NA
                 UNITS:       NA            SPARSE:      NA
                 DESCR:       NA"
::= { asamSNTPServerConfEntry 1 }

asamSNTPServerConfAddress   OBJECT-TYPE
     SYNTAX   InetAddress
     ACCESS   not-accessible
     STATUS   mandatory
     DESCRIPTION
	 "The value of asamSNTPServerConfAddress is an index that uniquely
              identifies a node that will provide time to the SNTP client
              of this system. Any update of the scalar object 
              asamSNTPServerIpAddress would get reflected in this object 
              corresponding to the entry with asamSNTPServerConfPriority value 1."
::= { asamSNTPServerConfEntry 2 }

asamSNTPServerConfPort   OBJECT-TYPE
     SYNTAX   InetPortNumber
     ACCESS   read-write
     STATUS   mandatory
     DESCRIPTION
	 "The value of asamSNTPServerConfPort indicates the UDP Port number 
              of the SNTP Server. Any update of the scalar object 
              asamSNTPServerPort would get reflected in this object 
              corresponding to the entry with asamSNTPServerConfPriority value 1."
::= { asamSNTPServerConfEntry 3 }

asamSNTPServerConfPriority   OBJECT-TYPE
     SYNTAX   INTEGER (1..3)
     ACCESS   read-write
     STATUS   mandatory
     DESCRIPTION
	 "The value of asamSNTPServerConfPriority indicates the priority of 
              this SNTP Server among the configured servers. This value is unique 
              across all the entries in this table."
::= { asamSNTPServerConfEntry 4 }

asamSNTPServerConfIsSyncSource   OBJECT-TYPE
     SYNTAX   TruthValue
     ACCESS   read-only
     STATUS   mandatory
     DESCRIPTION
	 "The value of asamSNTPServerConfIsSyncSource indicates whether this
              SNTP Server entry is the current source of time synchronization."
::= { asamSNTPServerConfEntry 5 }

asamSNTPServerConfRowStatus   OBJECT-TYPE
     SYNTAX   RowStatus
     ACCESS   read-write
     STATUS   mandatory
     DESCRIPTION
	 "The asamSNTPServerConfRowStatus is the object used for creating 
              and deleting row entries in this table. Row can be created by using 
              value createAndGo and deleted using value destroy."
::= { asamSNTPServerConfEntry 6 }

END
