LA-MIB DEFINITIONS ::= BEGIN

-- ==============================================================================
-- This specification is published by Alcatel under Non-Disclosure
-- Agreement(s) (NDA) with specific parties and has to be considered as
-- Confidential Information as defined in such NDA.
-- Alcatel reserves the right to revise this document for any reason,
-- including but not limited to conformity with standards promulgated by
-- various agencies, utilisation of advances in the state of the technical
-- areas, or the reflection of changes in the design of any equipment,
-- techniques, or procedures described or referred to herein.
-- The product specifications and other technical or performance information
-- contained herein are subject to change without notice.
-- Updates of this document will be issued under the above NDA's.
-- Alcatel makes no representation or warranty, expressed or implied, with
-- respect to the sufficiency, accuracy, or utility of any information or
-- opinion contained herein. Alcatel expressly advises that any use of for 
-- any purpose or reliance upon this technical reference is at the risk of
-- the user and that Alcatel shall not be liable for any damage or injury
-- incurred by any person arising out of the sufficiency, accuracy, or
-- utility of any information or opinion contained herein.
-- This document is not to be construed as a suggestion to any manufacturer
-- to modify or change any of its products, nor does this document represent
-- any commitment by Alcatel to sell or purchase any product.
-- Nothing contained herein shall be construed as conferring by implication,
-- estoppel, or otherwise any license or right under any patent, whether or
-- not the use of any information herein necessarily employs an invention of
-- any existing or later issued patent.
-- Alcatel reserves the right not to offer any or all of these products and
-- to withdraw any or all of them at any future time.
-- Copyright (C) 2007, Alcatel. All Rights Reserved.
-- ==============================================================================
--
--  MODULE-IDENTITY
--  LAST-UPDATED   "201003100600Z"
--  ORGANIZATION   "Alcatel"
--  CONTACT-INFO
--
--          "Email:  asam.mibsupport@alcatel.be"
--
--  DESCRIPTION   Alcatel proprietary Link Aggregation Control Protocol context-
--                specific variant of the LACP MIB.
-- 
--  REVISION 201003100600Z
--  DESCRIPTION
--        "Version:  3FE62624EAAA_V4.2.0.0.0
--         Editor:   Zhang Xiaofeng
--         Changes:  Implementation for ALU00123173. newly created for NELT-B"
--
--  REVISION "2013-12-08"
--  DESCRIPTION
--        "Version:  3FE62624EAAA_V5.0.0.0
--         Editor:   Durga Prasad Gandi
--         Changes:  updated for NGVR RCR: ALU01744917"
--
--  REVISION "2014-07-22"
--  DESCRIPTION
--        "Version:  3FE62624EAAA_V5.1.0.0
--         Editor:   Durga Prasad Gandi
--         Changes:  updated for NGVR RCR: ALU01949051"

--  REVISION "2015-06-16"
--  DESCRIPTION
--        "Version:  3FE62624EAAA_V5.3.0.0
--         Editor:   Durga Prasad Gandi
--         Changes:  updated for SX RCR: ALU01911436"

--  REVISION "2016-01-07"
--  DESCRIPTION
--        "Version:  3FE62624EAAA_V5.4.0.0
--         Editor:   xguo008
--         Changes:  updated for RCR: ALU02133850"

--  REVISION "2016-07-26"
--  DESCRIPTION
--        "Version:  3FE62624EAAA_V5.5.0.0
--         Editor:   chunyonl
--         Changes:  updated for RCR: ALU02250404"
-- ======================================================================

   IMPORTS  OBJECT-TYPE                     FROM RFC-1212
            AutonomousType                  FROM SNMPv2-TC
            TruthValue                      FROM SNMPv2-TC
            TestAndIncr                     FROM SNMPv2-TC
            RowStatus                       FROM SNMPv2-TC
            TimeStamp                       FROM SNMPv2-TC
            Counter                         FROM RFC1155-SMI
            Gauge                           FROM RFC1155-SMI
            mib-2                           FROM RFC1213-MIB
            DisplayString                   FROM RFC1213-MIB
            IANAifType                      FROM IANAifType-MIB
            ifIndex, InterfaceIndex         FROM ITF-MIB
            InterfaceIndexOrZero            FROM ITF-MIB
            AsamProfilePointer              FROM ASAM-TC-MIB
            asam                            FROM SYSTEM-MIB;


-- asam OBJECT IDENTIFIER ::= { iso(1) identified-organization(3) dod(6)
--                              internet(1) private(4) enterprises(1)
--                              alcatel(637) asd(61) asam(1)}

-- **************************************************************************
-- **   T E X T U A L     C O N V E N T I O N S                            **
-- **************************************************************************

Uint32 ::= Gauge (0 .. 4294967295)

  TosValue ::= INTEGER (0 .. 255)


-- **************************************************************************
-- **   O B J E C T     D E F I N I T I O N S                              **
-- **************************************************************************

lacpMIB      OBJECT IDENTIFIER ::= { asam 89 }

-- **************************************************************************
-- **   S Y S T E M     P R I O R I T Y                        **
-- **   lacpSystemPriority   ::= {lacpMIB 1}
-- **************************************************************************

   lacpSystemPriority OBJECT-TYPE
      SYNTAX INTEGER
      ACCESS read-write
      STATUS mandatory
      DESCRIPTION
         "the LACP system priority, 1 ISAM has only 1 same system priority. default value is 1 (as LANX), 

          ALCATEL NOTE:
            ACCESS:      NA           USAGE:       NA
            PERSIST:     YES          INSRVMOD:    NA
            RANGE:       1..65535     DEFVALUE:    1
            UNITS:       NA           SPARSE:      NA
            DESCR:       NA
		"

      ::= {lacpMIB 1}


-- **************************************************************************
-- **   L A C P     A G G     T A B L E                  **
-- **                                                                      **
-- **   lacpAggTable  ::= {lacpMIB 2}                                  **
-- **************************************************************************

     lacpAggTable  OBJECT-TYPE
        SYNTAX SEQUENCE OF LacpAggEntry
        ACCESS not-accessible
        STATUS mandatory
        DESCRIPTION
           "The LAG attributes table.
         ALCATEL NOTE: 
              SUPPORT:     YES
             	TABLESIZE:   684
            	DESCR:   The table size is the maximum number of physical interfaces: 19*36. 
                         In 7363 MX, the table is supported for four physical uplink interfaces.
                         And table size is for two physical uplink interfaces in 7367 sx variants."

        ::= {lacpMIB 2}

     lacpAggEntry  OBJECT-TYPE
        SYNTAX LacpAggEntry
        ACCESS not-accessible
        STATUS mandatory
        DESCRIPTION
           "An entry containing LAG attribute information.
            Row creation : Entries are created by the NE when planning the board.
            Row deletion : Entries are deleted by the NE when planning the board.
            Index usage : the index is the ifIndex of LAG.
            Note that entries will be presented to the SNMP manager in full
            lexicographical order :  sorted on LAG index."

        INDEX { lacpAggIndex }

        ::= {lacpAggTable 1}

     LacpAggEntry ::= SEQUENCE
     {
        lacpAggIndex                    InterfaceIndex,
        lacpAggMode                     INTEGER,
        lacpAggLoadShareType            INTEGER,
        lacpAggMaxActivePortNum         INTEGER,
        lacpAggPortThreshold            INTEGER
     }


     lacpAggIndex  OBJECT-TYPE
        SYNTAX InterfaceIndex
        ACCESS read-only
        STATUS mandatory
        DESCRIPTION
           "The ifIndex of the LAG

          ALCATEL NOTE:
            ACCESS:      NA           USAGE:       NA
            PERSIST:     YES          INSRVMOD:    NA
            RANGE:       NA           DEFVALUE:    NA
            UNITS:       NA           SPARSE:      NA
            DESCR:       NA
           "
        ::= {lacpAggEntry 1}


   lacpAggMode  OBJECT-TYPE
      SYNTAX INTEGER
      ACCESS read-write
      STATUS mandatory
      DESCRIPTION
         "the LAG mode, '0' for static and '1' for dynamic 

          ALCATEL NOTE:
            ACCESS:      NA           USAGE:       NA
            PERSIST:     YES          INSRVMOD:    NA
            DEFVALUE:    0                            
            RANGE:	0 | 1  -- static (0) and dynamic (1)
            UNITS:       NA           SPARSE:      NA
            DESCR:       NA         "
      ::= {lacpAggEntry 2}


   lacpAggLoadShareType  OBJECT-TYPE
      SYNTAX INTEGER
      ACCESS read-write
      STATUS mandatory
      DESCRIPTION
         "The load sharing type the LAG supported. 
         7 types of type supported, 1 for MAC_SA, 2 for MAC_DA, 
         3 for MAC_SA_DA, 4 for IP_SA, 5 for IP_DA, 6 for IP_SA_DA, 7 for L2_L3_HYBRID_MODEL.
         For the 7363 ISAM MX and the 7367 ISAM SX the lacpAggLoadShareType cannot be written and
         the system supports the default value IP_SA_DA(6), and does not
         allow to modify this value to a different one.
         For FELT-B the default value is L2_L3_HYBRID_MODEL(7) and connot be modified by other value.
  
          ALCATEL NOTE:
            ACCESS:      NA           USAGE:       NA
            PERSIST:     YES          INSRVMOD:    NA
            DEFVALUE:    DEP|
                         1 
                         In case of 7363 ISAM MX and the 7367 ISAM SX : 6
                         In case of FELT-B : 7
            RANGE:	 DEP|
                         1 | 2 | 3 | 4 | 5 | 6 | 7  --  MAC_SA(1),MAC_DA(2),MAC_SA_DA(3),IP_SA(4),IP_DA(5),IP_SA_DA(6),L2_L3_HYBRID_MODEL(7)
                         In case of 7363 ISAM MX and the 7367 ISAM SX : 6 -- IP_SA_DA(6)
                         in case of FELT-B : 7 -- L2_L3_HYBRID_MODEL(7)
            UNITS:       NA           SPARSE:      NA
            DESCR:       NA
         "
      ::= {lacpAggEntry 3}


   lacpAggMaxActivePortNum  OBJECT-TYPE
      SYNTAX INTEGER
      ACCESS read-write
      STATUS mandatory
      DESCRIPTION
         "the max member port number in a LAG.

          ALCATEL NOTE:
            ACCESS:      NA           USAGE:       NA
            PERSIST:     YES          INSRVMOD:    NA
            RANGE:       1..8         DEFVALUE:    NA
            UNITS:       NA           SPARSE:      NA
            DESCR:       range (1..8) with default value 8,
         "
      ::= {lacpAggEntry 4}


   lacpAggPortThreshold  OBJECT-TYPE
      SYNTAX INTEGER
      ACCESS read-write
      STATUS mandatory
      DESCRIPTION
         "lacpAggPortThreshold is a threshold for a Link Aggregation Group.

         when the number of active link in the Link Aggregation Group is less
         than lacpAggPortThreshold, the LAG is set operationally down.

         when the value of lacpAggPortThreshold is set to 0, port threshold
         function is disable.

          ALCATEL NOTE:
            ACCESS:      NA           USAGE:       NA
            PERSIST:     YES          INSRVMOD:    NA
            RANGE:       0..8         DEFVALUE:    NA
            UNITS:       NA           SPARSE:      NA
            DESCR:       range (0..8) with default value 0,
         "
      ::= {lacpAggEntry 5}   





-- **************************************************************************
-- **   L A C P     A G G     P O R T     A S S O C I A T I O N  T A B L E **
-- **                                                                      **
-- **   lacpAggPortTable  ::= {lacpMIB 3}                                  **
-- **************************************************************************

     lacpAggPortAssociationTable  OBJECT-TYPE
        SYNTAX SEQUENCE OF LacpAggPortAssociationEntry
        ACCESS not-accessible
        STATUS mandatory
        DESCRIPTION
           "The LAG port association table.
              SUPPORT:     YES
             	TABLESIZE:   684
            	DESCR:	 The table size is the maximum number of physical interfaces: 19*36. 
                         In 7363 MX, the table is supported for four physical uplink interfaces.
                         And table size is for two physical uplink interfaces in 7367 sx variants."

        ::= {lacpMIB 3}

     lacpAggPortAssociationEntry  OBJECT-TYPE
        SYNTAX LacpAggPortAssociationEntry
        ACCESS not-accessible
        STATUS mandatory
        DESCRIPTION
           "An entry containing LAG port association list
            information.
            Row creation : Entries are created by the NE when planning the board.
            Row deletion : Entries are deleted by the NE when planning the board.
            Index usage : the index is the ifIndex of LAG and port
            Note that entries will be presented to the SNMP manager in full
            lexicographical order :  sorted on LAG index and port index."

        INDEX { lacpAggAssIndex, lacpAggPortIndex }

        ::= {lacpAggPortAssociationTable 1}

     LacpAggPortAssociationEntry ::= SEQUENCE
     {
        lacpAggAssIndex                        InterfaceIndex,
        lacpAggPortIndex                    InterfaceIndex,
        lacpAggPortStatus                   INTEGER,
        lacpAggPortAssociationRowStatus     RowStatus
     }


     lacpAggAssIndex  OBJECT-TYPE
        SYNTAX InterfaceIndex
        ACCESS not-accessible
        STATUS mandatory
        DESCRIPTION
           "The ifIndex of the LAG

          ALCATEL NOTE:
            ACCESS:      NA           USAGE:       NA
            PERSIST:     YES          INSRVMOD:    NA
            RANGE:       NA           DEFVALUE:    NA
            UNITS:       NA           SPARSE:      NA
            DESCR:       NA
           "
        ::= {lacpAggPortAssociationEntry 1}


     lacpAggPortIndex  OBJECT-TYPE
        SYNTAX InterfaceIndex
        ACCESS not-accessible
        STATUS mandatory
        DESCRIPTION
           "The ifIndex of the LA member port

          ALCATEL NOTE:
            ACCESS:      NA           USAGE:       NA
            PERSIST:     YES          INSRVMOD:    NA
            RANGE:       NA           DEFVALUE:    NA
            UNITS:       NA           SPARSE:      NA
            DESCR:       NA"
        ::= {lacpAggPortAssociationEntry 2}


   lacpAggPortStatus  OBJECT-TYPE
      SYNTAX INTEGER
      ACCESS read-only
      STATUS mandatory
      DESCRIPTION
         "the LA member port's status. 1 for active, 0 for standby

          ALCATEL NOTE:
            ACCESS:      NA           USAGE:       NA
            PERSIST:     YES          INSRVMOD:    NA
            RANGE:       0 | 1	-- active (1), standby (0)
            DEFVALUE:    NA           UNITS:       NA
            SPARSE:      NA           DESCR:       NA
         "
      ::= {lacpAggPortAssociationEntry 3}


   lacpAggPortAssociationRowStatus  OBJECT-TYPE
      SYNTAX RowStatus
      ACCESS read-write
      STATUS mandatory
      DESCRIPTION
         "The status of this conceptual row.
          The RowStatus TC requires that this DESCRIPTION clause
          states under which circumstances other objects in this row
          can be modified.  The value of this object has no effect on
          whether other objects in this conceptual row can be
          modified.
          A conceptual row can always be made active.

          ALCATEL NOTE:
            ACCESS:      NA           USAGE:       MAND
            PERSIST:     NO           INSRVMOD:    NA
            DEFVALUE:    NA                              
            RANGE:	1 | 4 | 6	-- active (1), createAndGo (4), destroy (6)
            UNITS:       NA           SPARSE:      NA
            DESCR:       NA         "
      ::= {lacpAggPortAssociationEntry 4}
END
