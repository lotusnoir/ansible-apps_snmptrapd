-- ========================================================================
--  This specification is published by Alcatel under Non-Disclosure
--  Agreement(s) (NDA) with specific parties and has to be considered as
--  Confidential Information as defined in such NDA.
--  Alcatel reserves the right to revise this document for any reason,
--  including but not limited to conformity with standards promulgated by
--  various agencies, utilisation of advances in the state of the
--  technical areas, or the reflection of changes in the design of any 
--  equipment,techniques, or procedures described or referred to herein.
--  The product specifications and other technical or performance
--  information contained herein are subject to change without notice.
--  Updates of this document will be issued under the above NDA's.
--  Alcatel makes no representation or warranty, expressed or implied, 
--  with respect to the sufficiency, accuracy, or utility of any 
--  information or opinion contained herein. Alcatel expressly advises 
--  that any use of for any purpose or reliance upon this technical 
--  reference is at the risk of the user and that Alcatel shall not be 
--  liable for any damage or injury incurred by any person arising out of 
--  the sufficiency, accuracy, or utility of any information or opinion 
--  contained herein.
--  This document is not to be construed as a suggestion to any
--  manufacturer to modify or change any of its products, nor does this
--  document represent any commitment by Alcatel to sell or purchase any
--  product. Nothing contained herein shall be construed as conferring by
--  implication, estoppel, or otherwise any license or right under any 
--  patent, whether or not the use of any information herein necessarily
--  employs an invention of any existing or later issued patent.
--  Alcatel reserves the right not to offer any or all of these products 
--  and to withdraw any or all of them at any future time.
--  Copyright (C) 2004, Alcatel. All Rights Reserved.
-- ========================================================================

IEEE8021-PAE-MIB DEFINITIONS ::= BEGIN

-- IEEE 802.1X MIB converted to SMIv1 Format.

 
IMPORTS
    Counter,iso,
    TimeTicks                 FROM RFC1155-SMI
    OBJECT-TYPE               FROM RFC-1212
    MacAddress, TruthValue    FROM SNMPv2-TC
--    SnmpAdminString           FROM SNMP-FRAMEWORK-MIB
    InterfaceIndex            FROM ITF-MIB;

ieee8021paeMIB OBJECT IDENTIFIER
-- MODULE-IDENTITY
--    LAST-UPDATED "200101160000Z"
--    ORGANIZATION "IEEE 802.1 Working Group"
--    CONTACT-INFO
--        "http://grouper.ieee.org/groups/802/1/index.html"
--    DESCRIPTION
--        "The Port Access Entity module for managing IEEE 
--            802.1X."
::=  { iso(1) std(0) iso8802(8802) ieee802dot1(1) ieee802dot1mibs(1) 1 }

paeMIBObjects OBJECT IDENTIFIER ::=  { ieee8021paeMIB 1 }

-- Textual Conventions 
-- 
PaeControlledDirections ::=
-- TEXTUAL-CONVENTION
--    STATUS mandatory
--    DESCRIPTION
--        "The control mode values for the Authenticator PAE. 
--              Support for in(1) is optional. The MIB is standards
--              compliant with supporting the BOTH option only"
--    SYNTAX
INTEGER {
              both          (0)
           }
PaeControlledPortStatus ::=
-- TEXTUAL-CONVENTION
--    STATUS mandatory
--    DESCRIPTION
--        "The status values of the Authenticator PAE controlled 
--             Port."
--    SYNTAX
INTEGER {
              authorized          (1),
              unauthorized          (2)
           }
PaeControlledPortControl ::=
-- TEXTUAL-CONVENTION
--    STATUS mandatory
--    DESCRIPTION
--        "The control values of the Authenticator PAE controlled 
--             Port."
--    SYNTAX
INTEGER {
              forceUnauthorized          (1),
              auto          (2),
              forceAuthorized          (3)
           }


SnmpAdminString ::= OCTET STRING (SIZE(0..32)) 

-- groups in the PAE MIB 
 
dot1xPaeSystem OBJECT IDENTIFIER ::=  { paeMIBObjects 1 }

dot1xPaeAuthenticator OBJECT IDENTIFIER ::=  { paeMIBObjects 2 }

dot1xPaeSupplicant OBJECT IDENTIFIER ::=  { paeMIBObjects 3 }

-- The PAE System Group 


dot1xPaeSystemAuthControl OBJECT-TYPE
    SYNTAX INTEGER {
              enabled          (1),
              disabled          (2)
           }
    ACCESS read-write
    STATUS mandatory
    DESCRIPTION
        "The administrative enable/disable state for 
               Port Access Control in a System."
    REFERENCE
        "9.6.1, SystemAuthControl"
    ::=  { dot1xPaeSystem 1 }

 

-- The PAE Port Table 

 
dot1xPaePortTable OBJECT-TYPE
    SYNTAX SEQUENCE OF Dot1xPaePortEntry
    ACCESS not-accessible
    STATUS mandatory
    DESCRIPTION
        "A table of system level information for each port 
               supported by the Port Access Entity. An entry appears 
               in this table for each port of this system."
    REFERENCE
        "9.6.."
    ::=  { dot1xPaeSystem 2 }

dot1xPaePortEntry OBJECT-TYPE
    SYNTAX Dot1xPaePortEntry
    ACCESS not-accessible
    STATUS mandatory
    DESCRIPTION
        "The Port number, protocol version, and 
               initialization control for a Port."
    INDEX {dot1xPaePortNumber}
    ::=  { dot1xPaePortTable 1 }

Dot1xPaePortEntry ::= SEQUENCE {
    dot1xPaePortNumber    InterfaceIndex,
    dot1xPaePortProtocolVersion    INTEGER,
    dot1xPaePortCapabilities    OCTET STRING (SIZE (1)),
    dot1xPaePortInitialize    TruthValue,
    dot1xPaePortReauthenticate    TruthValue
    }

dot1xPaePortNumber OBJECT-TYPE
    SYNTAX InterfaceIndex
    ACCESS not-accessible
    STATUS mandatory
    DESCRIPTION
        "The Port number associated with this Port."
    REFERENCE
        "9.6.1, Port number."
    ::=  { dot1xPaePortEntry 1 }

dot1xPaePortProtocolVersion OBJECT-TYPE
    SYNTAX INTEGER
    ACCESS read-only
    STATUS mandatory
    DESCRIPTION
        "The protocol version associated with this Port."
    REFERENCE
        "9.6.1, Protocol version."
    ::=  { dot1xPaePortEntry 2 }


dot1xPaePortCapabilities       OBJECT-TYPE
    SYNTAX        OCTET STRING  (SIZE (1))
--                     {  dot1xPaePortAuthCapable(0), 
--                        *Authenticator functions are supported 
--                        dot1xPaePortSuppCapable(1) 
--                        *Supplicant functions are supported 
--                     } 
    ACCESS    read-only 
    STATUS        mandatory 
    DESCRIPTION 
      "Indicates the PAE functionality that this Port 
     supports and that may be managed through this MIB." 
    REFERENCE 
     "9.6.1, PAE Capabilities." 

    ::= { dot1xPaePortEntry 3 } 

dot1xPaePortInitialize OBJECT-TYPE
    SYNTAX TruthValue
    ACCESS read-write
    STATUS mandatory
    DESCRIPTION
        "The initialization control for this Port. Setting this 
               attribute TRUE causes the Port to be initialized. 
               The attribute value reverts to FALSE once initialization 
               has completed."
    REFERENCE
        "9.6.1.2, Initialize Port."
    ::=  { dot1xPaePortEntry 4 }

dot1xPaePortReauthenticate OBJECT-TYPE
    SYNTAX TruthValue
    ACCESS read-only
    STATUS mandatory
    DESCRIPTION

"The value of the dot1xPaePortReauthenticate constant 
               currently in use by the Authenticator PAE state 
               machine.  The only value allowed for this attribute 
               is FALSE."
    REFERENCE
        "9.4.1.3 Reauthenticator."
    ::=  { dot1xPaePortEntry 5 }

-- The PAE Authenticator Group 


-- The Authenticator Configuration Table 

dot1xAuthConfigTable OBJECT-TYPE
    SYNTAX SEQUENCE OF Dot1xAuthConfigEntry
    ACCESS not-accessible
    STATUS mandatory
    DESCRIPTION
        "A table that contains the configuration objects for the 
               Authenticator PAE associated with each port. 
               An entry appears in this table for each port that may 
               authenticate access to itself."
    REFERENCE
        "9.4.1 Authenticator Configuration."
    ::=  { dot1xPaeAuthenticator 1 }

dot1xAuthConfigEntry OBJECT-TYPE
    SYNTAX Dot1xAuthConfigEntry
    ACCESS not-accessible
    STATUS mandatory
    DESCRIPTION
        "The configuration information for an Authenticator 
               PAE."
    INDEX {dot1xPaePortNumber}
    ::=  { dot1xAuthConfigTable 1 }

Dot1xAuthConfigEntry ::= SEQUENCE {
    dot1xAuthPaeState    INTEGER,
    dot1xAuthBackendAuthState    INTEGER,
    dot1xAuthAdminControlledDirections    PaeControlledDirections,
    dot1xAuthOperControlledDirections    PaeControlledDirections,
    dot1xAuthAuthControlledPortStatus    PaeControlledPortStatus,
    dot1xAuthAuthControlledPortControl    PaeControlledPortControl,
    dot1xAuthQuietPeriod    INTEGER,
    dot1xAuthTxPeriod    INTEGER,
    dot1xAuthSuppTimeout    INTEGER,
    dot1xAuthServerTimeout    INTEGER,
    dot1xAuthMaxReq    INTEGER,
    dot1xAuthReAuthPeriod    INTEGER,
    dot1xAuthReAuthEnabled    TruthValue,
    dot1xAuthKeyTxEnabled    TruthValue
    }

dot1xAuthPaeState OBJECT-TYPE
    SYNTAX INTEGER {
              initialize          (1),
              disconnected          (2),
              connecting          (3),
              authenticating          (4),
              authenticated          (5),
              aborting          (6),
              held          (7),
              forceAuth          (8),
              forceUnauth          (9)
           }
    ACCESS read-only
    STATUS mandatory
    DESCRIPTION
        "The current value of the Authenticator PAE state 
               machine."
    REFERENCE
        "9.4.1, Authenticator PAE stat."
    ::=  { dot1xAuthConfigEntry 1 }

dot1xAuthBackendAuthState OBJECT-TYPE
    SYNTAX INTEGER {
              request          (1),
              response          (2),
              success          (3),
              fail          (4),
              timeout          (5),
              idle          (6),
              initialize          (7)
           }
    ACCESS read-only
    STATUS mandatory
    DESCRIPTION
        "The current state of the Backend Authentication 
               state machine."
    REFERENCE
        "9.4.1, Backend Authentication stat."
    ::=  { dot1xAuthConfigEntry 2 }

dot1xAuthAdminControlledDirections OBJECT-TYPE
    SYNTAX PaeControlledDirections
    ACCESS read-only
    STATUS mandatory
    DESCRIPTION
        "The current value of the administrative controlled 
               directions parameter for the Port.  The only value
               allowed for this attribute is BOTH"
    REFERENCE
        "9.4.1, Admin Control Mod."
    ::=  { dot1xAuthConfigEntry 3 }

dot1xAuthOperControlledDirections OBJECT-TYPE
    SYNTAX PaeControlledDirections
    ACCESS read-only
    STATUS mandatory
    DESCRIPTION
        "The current value of the operational controlled 
               directions parameter for the Port."
    REFERENCE
        "9.4.1, Oper Control Mod."
    ::=  { dot1xAuthConfigEntry 4 }

dot1xAuthAuthControlledPortStatus OBJECT-TYPE
    SYNTAX PaeControlledPortStatus
    ACCESS read-only
    STATUS mandatory
    DESCRIPTION
        "The current value of the controlled Port 
               status parameter for the Port."
    REFERENCE
        "9.4.1, AuthControlledPortStatu."
    ::=  { dot1xAuthConfigEntry 5 }

dot1xAuthAuthControlledPortControl OBJECT-TYPE
    SYNTAX PaeControlledPortControl
    ACCESS read-write
    STATUS mandatory
    DESCRIPTION
        "The current value of the controlled Port 
               control parameter for the Port."
    REFERENCE
        "9.4.1, AuthControlledPortControl."
    ::=  { dot1xAuthConfigEntry 6 }

dot1xAuthQuietPeriod OBJECT-TYPE
    SYNTAX INTEGER
    ACCESS read-write
    STATUS mandatory
    DESCRIPTION
        "The value, in seconds, of the quietPeriod constant 
               currently in use by the Authenticator PAE state 
               machine."
    REFERENCE
        "9.4.1, quietPeriod."
    DEFVAL { 60         }
    ::=  { dot1xAuthConfigEntry 7 }

dot1xAuthTxPeriod OBJECT-TYPE
    SYNTAX INTEGER
    ACCESS read-write
    STATUS mandatory
    DESCRIPTION
        "The value, in seconds, of the txPeriod constant 
               currently in use by the Authenticator PAE state 
               machine."
    REFERENCE
        "9.4.1, txPeriod."
    DEFVAL { 30         }
    ::=  { dot1xAuthConfigEntry 8 }

dot1xAuthSuppTimeout OBJECT-TYPE
    SYNTAX INTEGER
    ACCESS read-write
    STATUS mandatory
    DESCRIPTION
        "The value, in seconds, of the suppTimeout constant 
               currently in use by the Backend Authentication state 
               machine."
    REFERENCE
        "9.4.1, suppTimeout."
    DEFVAL { 30         }
    ::=  { dot1xAuthConfigEntry 9 }

dot1xAuthServerTimeout OBJECT-TYPE
    SYNTAX INTEGER
    ACCESS read-write
    STATUS mandatory
    DESCRIPTION
        "The value, in seconds, of the serverTimeout constant 
               currently in use by the Backend Authentication state 
               machine."
    REFERENCE
        "9.4.1, serverTimeout."
    DEFVAL { 30         }
    ::=  { dot1xAuthConfigEntry 10 }

dot1xAuthMaxReq OBJECT-TYPE
    SYNTAX INTEGER
    ACCESS read-write
    STATUS mandatory
    DESCRIPTION
        "The value of the maxReq constant currently in use by 
               the Backend Authentication state machine."
    REFERENCE
        "9.4.1, maxReq."
    DEFVAL { 2         }
    ::=  { dot1xAuthConfigEntry 11 }

dot1xAuthReAuthPeriod OBJECT-TYPE
    SYNTAX INTEGER
    ACCESS read-write
    STATUS mandatory
    DESCRIPTION
        
"The value of the dot1xAuthReAuthPeriod constant currently
 in use by the Reauthentication timer state machine."
    REFERENCE
        "9.4.1, reAuthPerio."
    DEFVAL { 3600         }
    ::=  { dot1xAuthConfigEntry 12 }

dot1xAuthReAuthEnabled OBJECT-TYPE
    SYNTAX TruthValue
    ACCESS read-write
    STATUS mandatory
    DESCRIPTION

"The value of the dot1xAuthReAuthEnabled constant           currently in use by the Reauthentication timer state              machine. Reauthentication may not be enabled for this port if extdot1xPaePortHandShakeMode is enabled."
    REFERENCE
        "9.4.1, reAuthEnable."
    DEFVAL { false         }
    ::=  { dot1xAuthConfigEntry 13 }

dot1xAuthKeyTxEnabled OBJECT-TYPE
    SYNTAX TruthValue
    ACCESS read-only
    STATUS mandatory
    DESCRIPTION
        "The value of the keyTransmissionEnabled constant 
               currently in use by the Authenticator PAE state 
               machine.  The only value allowed for this attribute 
               is FALSE"
    REFERENCE
        "9.4.1, keyTransmissionEnable."
    ::=  { dot1xAuthConfigEntry 14 }

-- The Authenticator Statistics Table 

 
dot1xAuthStatsTable OBJECT-TYPE
    SYNTAX SEQUENCE OF Dot1xAuthStatsEntry
    ACCESS not-accessible
    STATUS mandatory
    DESCRIPTION
        "A table that contains the statistics objects for the 
               Authenticator PAE associated with each Port. 
               An entry appears in this table for each port that may 
               authenticate access to itself."
    REFERENCE
        "9.4.2 Authenticator Statistic."
    ::=  { dot1xPaeAuthenticator 2 }

dot1xAuthStatsEntry OBJECT-TYPE
    SYNTAX Dot1xAuthStatsEntry
    ACCESS not-accessible
    STATUS mandatory
    DESCRIPTION
        "The statistics information for an Authenticator PAE."
    INDEX {dot1xPaePortNumber}
    ::=  { dot1xAuthStatsTable 1 }

Dot1xAuthStatsEntry ::= SEQUENCE {
    dot1xAuthEapolFramesRx    Counter,
    dot1xAuthEapolFramesTx    Counter,
    dot1xAuthEapolStartFramesRx    Counter,
    dot1xAuthEapolLogoffFramesRx    Counter,
    dot1xAuthEapolRespIdFramesRx    Counter,
    dot1xAuthEapolRespFramesRx    Counter,
    dot1xAuthEapolReqIdFramesTx    Counter,
    dot1xAuthEapolReqFramesTx    Counter,
    dot1xAuthInvalidEapolFramesRx    Counter,
    dot1xAuthEapLengthErrorFramesRx    Counter,
    dot1xAuthLastEapolFrameVersion    INTEGER,
    dot1xAuthLastEapolFrameSource    MacAddress
    }

dot1xAuthEapolFramesRx OBJECT-TYPE
    SYNTAX Counter
    ACCESS read-only
    STATUS mandatory
    DESCRIPTION
        "The number of valid EAPOL frames of any type 
               that have been received by this Authenticator."
    REFERENCE
        "9.4.2, EAPOL frames receive."
    ::=  { dot1xAuthStatsEntry 1 }

dot1xAuthEapolFramesTx OBJECT-TYPE
    SYNTAX Counter
    ACCESS read-only
    STATUS mandatory
    DESCRIPTION
        "The number of EAPOL frames of any type 
               that have been transmitted by this Authenticator."
    REFERENCE
        "9.4.2, EAPOL frames transmitted."
    ::=  { dot1xAuthStatsEntry 2 }

dot1xAuthEapolStartFramesRx OBJECT-TYPE
    SYNTAX Counter
    ACCESS read-only
    STATUS mandatory
    DESCRIPTION
        "The number of EAPOL Start frames that have 
               been received by this Authenticator."
    REFERENCE
        "9.4.2, EAPOL Start frames receive."
    ::=  { dot1xAuthStatsEntry 3 }

dot1xAuthEapolLogoffFramesRx OBJECT-TYPE
    SYNTAX Counter
    ACCESS read-only
    STATUS mandatory
    DESCRIPTION
        "The number of EAPOL Logoff frames that have 
               been received by this Authenticator."
    REFERENCE
        "9.4.2, EAPOL Logoff frames receive."
    ::=  { dot1xAuthStatsEntry 4 }

dot1xAuthEapolRespIdFramesRx OBJECT-TYPE
    SYNTAX Counter
    ACCESS read-only
    STATUS mandatory
    DESCRIPTION
        "The number of EAP Resp/Id frames that have 
               been received by this Authenticator."
    REFERENCE
        "9.4.2, EAPOL Resp/Id frames receive."
    ::=  { dot1xAuthStatsEntry 5 }

dot1xAuthEapolRespFramesRx OBJECT-TYPE
    SYNTAX Counter
    ACCESS read-only
    STATUS mandatory
    DESCRIPTION
        "The number of valid EAP Response frames 
               (other than Resp/Id frames) that have been 
               received by this Authenticator."
    REFERENCE
        "9.4.2, EAPOL Response frames receive."
    ::=  { dot1xAuthStatsEntry 6 }

dot1xAuthEapolReqIdFramesTx OBJECT-TYPE
    SYNTAX Counter
    ACCESS read-only
    STATUS mandatory
    DESCRIPTION
        "The number of EAP Req/Id frames that have been 
               transmitted by this Authenticator."
    REFERENCE
        "9.4.2, EAPOL Req/Id frames transmitted."
    ::=  { dot1xAuthStatsEntry 7 }

dot1xAuthEapolReqFramesTx OBJECT-TYPE
    SYNTAX Counter
    ACCESS read-only
    STATUS mandatory
    DESCRIPTION
        "The number of EAP Request frames 
               (other than Rq/Id frames) that have been 
               transmitted by this Authenticator."
    REFERENCE
        "9.4.2, EAPOL Request frames transmitted."
    ::=  { dot1xAuthStatsEntry 8 }

dot1xAuthInvalidEapolFramesRx OBJECT-TYPE
    SYNTAX Counter
    ACCESS read-only
    STATUS mandatory
    DESCRIPTION
        "The number of EAPOL frames that have been 
               received by this Authenticator in which the 
               frame type is not recognized."
    REFERENCE
        "9.4.2, Invalid EAPOL frames receive."
    ::=  { dot1xAuthStatsEntry 9 }

dot1xAuthEapLengthErrorFramesRx OBJECT-TYPE
    SYNTAX Counter
    ACCESS read-only
    STATUS mandatory
    DESCRIPTION
        "The number of EAPOL frames that have been received 
               by this Authenticator in which the Packet Body 
               Length field is invalid."
    REFERENCE
        "9.4.2, EAP length error frames receive."
    ::=  { dot1xAuthStatsEntry 10 }

dot1xAuthLastEapolFrameVersion OBJECT-TYPE
    SYNTAX INTEGER
    ACCESS read-only
    STATUS mandatory
    DESCRIPTION
        "The protocol version number carried in the 
               most recently received EAPOL frame."
    REFERENCE
        "9.4.2, Last EAPOL frame version."
    ::=  { dot1xAuthStatsEntry 11 }

dot1xAuthLastEapolFrameSource OBJECT-TYPE
    SYNTAX MacAddress
    ACCESS read-only
    STATUS mandatory
    DESCRIPTION
        "The source MAC address carried in the 
               most recently received EAPOL frame."
    REFERENCE
        "9.4.2, Last EAPOL frame source."
    ::=  { dot1xAuthStatsEntry 12 }


-- The Authenticator Diagnostics Table 

dot1xAuthDiagTable OBJECT-TYPE
    SYNTAX SEQUENCE OF Dot1xAuthDiagEntry
    ACCESS not-accessible
    STATUS mandatory
    DESCRIPTION
        "A table that contains the diagnostics objects for the 
               Authenticator PAE associated with each Port. 
               An entry appears in this table for each port that may 
               authenticate access to itself."
    REFERENCE
        "9.4.3 Authenticator Diagnostic."
    ::=  { dot1xPaeAuthenticator 3 }

dot1xAuthDiagEntry OBJECT-TYPE
    SYNTAX Dot1xAuthDiagEntry
    ACCESS not-accessible
    STATUS mandatory
    DESCRIPTION
        "The diagnostics information for an Authenticator PAE."
    INDEX {dot1xPaePortNumber}
    ::=  { dot1xAuthDiagTable 1 }

Dot1xAuthDiagEntry ::= SEQUENCE {
    dot1xAuthEntersConnecting    Counter,
    dot1xAuthEapLogoffsWhileConnecting    Counter,
    dot1xAuthEntersAuthenticating    Counter,
    dot1xAuthAuthSuccessWhileAuthenticating    Counter,
    dot1xAuthAuthTimeoutsWhileAuthenticating    Counter,
    dot1xAuthAuthFailWhileAuthenticating    Counter,
    dot1xAuthAuthReauthsWhileAuthenticating    Counter,
    dot1xAuthAuthEapStartsWhileAuthenticating    Counter,
    dot1xAuthAuthEapLogoffWhileAuthenticating    Counter,
    dot1xAuthAuthReauthsWhileAuthenticated    Counter,
    dot1xAuthAuthEapStartsWhileAuthenticated    Counter,
    dot1xAuthAuthEapLogoffWhileAuthenticated    Counter,
    dot1xAuthBackendResponses    Counter,
    dot1xAuthBackendAccessChallenges    Counter,
    dot1xAuthBackendOtherRequestsToSupplicant    Counter,
    dot1xAuthBackendNonNakResponsesFromSupplicant    Counter,
    dot1xAuthBackendAuthSuccesses    Counter,
    dot1xAuthBackendAuthFails    Counter
    }

dot1xAuthEntersConnecting OBJECT-TYPE
    SYNTAX Counter
    ACCESS read-only
    STATUS mandatory
    DESCRIPTION
        "Counts the number of times that the state machine 
               transitions to the CONNECTING state from any other 
               state."
    REFERENCE
        "9.4.2, 8.5.4.2.."
    ::=  { dot1xAuthDiagEntry 1 }

dot1xAuthEapLogoffsWhileConnecting OBJECT-TYPE
    SYNTAX Counter
    ACCESS read-only
    STATUS mandatory
    DESCRIPTION
        "Counts the number of times that the state machine 
               transitions from CONNECTING to DISCONNECTED as a result 
               of receiving an EAPOL-Logoff message."
    REFERENCE
        "9.4.2, 8.5.4.2.."
    ::=  { dot1xAuthDiagEntry 2 }

dot1xAuthEntersAuthenticating OBJECT-TYPE
    SYNTAX Counter
    ACCESS read-only
    STATUS mandatory
    DESCRIPTION
        "Counts the number of times that the state machine 
               transitions from CONNECTING to AUTHENTICATING, as a 
               result of an EAP-Response/Identity message being 
               received from the Supplicant."
    REFERENCE
        "9.4.2, 8.5.4.2.."
    ::=  { dot1xAuthDiagEntry 3 }

dot1xAuthAuthSuccessWhileAuthenticating OBJECT-TYPE
    SYNTAX Counter
    ACCESS read-only
    STATUS mandatory
    DESCRIPTION
        "Counts the number of times that the state machine 
               transitions from AUTHENTICATING to AUTHENTICATED, as a 
               result of the Backend Authentication state machine 
               indicating successful authentication of the Supplicant 
               (authSuccess = TRUE)."
    REFERENCE
        "9.4.2, 8.5.4.2.."
    ::=  { dot1xAuthDiagEntry 4 }

dot1xAuthAuthTimeoutsWhileAuthenticating OBJECT-TYPE
    SYNTAX Counter
    ACCESS read-only
    STATUS mandatory
    DESCRIPTION
        "Counts the number of times that the state machine 
               transitions from AUTHENTICATING to ABORTING, as a result 
               of the Backend Authentication state machine indicating 
               authentication timeout (authTimeout = TRUE)."
    REFERENCE
        "9.4.2, 8.5.4.2.."
    ::=  { dot1xAuthDiagEntry 5 }

dot1xAuthAuthFailWhileAuthenticating OBJECT-TYPE
    SYNTAX Counter
    ACCESS read-only
    STATUS mandatory
    DESCRIPTION
        "Counts the number of times that the state machine 
               transitions from AUTHENTICATING to HELD, as a result 
               of the Backend Authentication state machine indicating 
               authentication failure (authFail = TRUE)."
    REFERENCE
        "9.4.2, 8.5.4.2.."
    ::=  { dot1xAuthDiagEntry 6 }

dot1xAuthAuthReauthsWhileAuthenticating OBJECT-TYPE
    SYNTAX Counter
    ACCESS read-only
    STATUS mandatory
    DESCRIPTION
        "Counts the number of times that the state machine 
               transitions from AUTHENTICATING to ABORTING, as a result 
               of a reauthentication request (reAuthenticate = TRUE)."
    REFERENCE
        "9.4.2, 8.5.4.2.."
    ::=  { dot1xAuthDiagEntry 7 }

dot1xAuthAuthEapStartsWhileAuthenticating OBJECT-TYPE
    SYNTAX Counter
    ACCESS read-only
    STATUS mandatory
    DESCRIPTION
        "Counts the number of times that the state machine 
               transitions from AUTHENTICATING to ABORTING, as a result 
               of an EAPOL-Start message being received 
               from the Supplicant."
    REFERENCE
        "9.4.2, 8.5.4.2.."
    ::=  { dot1xAuthDiagEntry 8 }

dot1xAuthAuthEapLogoffWhileAuthenticating OBJECT-TYPE
    SYNTAX Counter
    ACCESS read-only
    STATUS mandatory
    DESCRIPTION
        "Counts the number of times that the state machine 
               transitions from AUTHENTICATING to ABORTING, as a result 
               of an EAPOL-Logoff message being received 
               from the Supplicant."
    REFERENCE
        "9.4.2, 8.5.4.2.."
    ::=  { dot1xAuthDiagEntry 9 }

dot1xAuthAuthReauthsWhileAuthenticated OBJECT-TYPE
    SYNTAX Counter
    ACCESS read-only
    STATUS mandatory
    DESCRIPTION
        "Counts the number of times that the state machine 
               transitions from AUTHENTICATED to CONNECTING, as a 
               result of a reauthentication request 
               (reAuthenticate = TRUE)."
    REFERENCE
        "9.4.2, 8.5.4.2.1."
    ::=  { dot1xAuthDiagEntry 10 }

dot1xAuthAuthEapStartsWhileAuthenticated OBJECT-TYPE
    SYNTAX Counter
    ACCESS read-only
    STATUS mandatory
    DESCRIPTION
        "Counts the number of times that the state machine 
               transitions from AUTHENTICATED to CONNECTING, as a 
               result of an EAPOL-Start message being received from the 
               Supplicant."
    REFERENCE
        "9.4.2, 8.5.4.2.1."
    ::=  { dot1xAuthDiagEntry 11 }

dot1xAuthAuthEapLogoffWhileAuthenticated OBJECT-TYPE
    SYNTAX Counter
    ACCESS read-only
    STATUS mandatory
    DESCRIPTION
        "Counts the number of times that the state machine 
               transitions from AUTHENTICATED to DISCONNECTED, as a 
               result of an EAPOL-Logoff message being received from 
               the Supplicant."
    REFERENCE
        "9.4.2, 8.5.4.2.1."
    ::=  { dot1xAuthDiagEntry 12 }

dot1xAuthBackendResponses OBJECT-TYPE
    SYNTAX Counter
    ACCESS read-only
    STATUS mandatory
    DESCRIPTION
        "Counts the number of times that the state machine sends 
               an initial Access-Request packet to the Authentication 
               server (i.e., executes sendRespToServer on entry to the 
               RESPONSE state). Indicates that the Authenticator 
               attempted communication with the Authentication Server."
    REFERENCE
        "9.4.2, 8.5.6.2.."
    ::=  { dot1xAuthDiagEntry 13 }

dot1xAuthBackendAccessChallenges OBJECT-TYPE
    SYNTAX Counter
    ACCESS read-only
    STATUS mandatory
    DESCRIPTION
        "Counts the number of times that the state machine 
               receives an initial Access-Challenge packet from the 
               Authentication server (i.e., aReq becomes TRUE, 
               causing exit from the RESPONSE state). Indicates that 
               the Authentication Server has communication with 
               the Authenticator."
    REFERENCE
        "9.4.2, 8.5.6.2.."
    ::=  { dot1xAuthDiagEntry 14 }

dot1xAuthBackendOtherRequestsToSupplicant OBJECT-TYPE
    SYNTAX Counter
    ACCESS read-only
    STATUS mandatory
    DESCRIPTION
        "Counts the number of times that the state machine 
               sends an EAP-Request packet (other than an Identity, 
               Notification, Failure or Success message) to the 
               Supplicant (i.e., executes txReq on entry to the 
               REQUEST state). Indicates that the Authenticator chose 
               an EAP-method."
    REFERENCE
        "9.4.2, 8.5.6.2.."
    ::=  { dot1xAuthDiagEntry 15 }

dot1xAuthBackendNonNakResponsesFromSupplicant OBJECT-TYPE
    SYNTAX Counter
    ACCESS read-only
    STATUS mandatory
    DESCRIPTION
        "Counts the number of times that the state machine 
               receives a response from the Supplicant to an initial 
               EAP-Request, and the response is something other than 
               EAP-NAK (i.e., rxResp becomes TRUE, causing the state 
               machine to transition from REQUEST to RESPONSE, 
               and the response is not an EAP-NAK). Indicates that 
               the Supplicant can respond to the Authenticator's 
               chosen EAP-method."
    REFERENCE
        "9.4.2, 8.5.6.2.."
    ::=  { dot1xAuthDiagEntry 16 }

dot1xAuthBackendAuthSuccesses OBJECT-TYPE
    SYNTAX Counter
    ACCESS read-only
    STATUS mandatory
    DESCRIPTION
        "Counts the number of times that the state machine 
               receives an EAP-Success message from the Authentication 
               Server (i.e., aSuccess becomes TRUE, causing a 
               transition from RESPONSE to SUCCESS). Indicates that 
               the Supplicant has successfully authenticated to 
               the Authentication Server."
    REFERENCE
        "9.4.2, 8.5.6.2.."
    ::=  { dot1xAuthDiagEntry 17 }

dot1xAuthBackendAuthFails OBJECT-TYPE
    SYNTAX Counter
    ACCESS read-only
    STATUS mandatory
    DESCRIPTION
        "Counts the number of times that the state machine 
               receives an EAP-Failure message from the Authentication 
               Server (i.e., aFail becomes TRUE, causing a transition 
               from RESPONSE to FAIL). Indicates that the Supplicant 
               has not authenticated to the Authentication Server."
    REFERENCE
        "9.4.2, 8.5.6.2.."
    ::=  { dot1xAuthDiagEntry 18 }

 

-- The Authenticator Session Statistics Table 

dot1xAuthSessionStatsTable OBJECT-TYPE
    SYNTAX SEQUENCE OF Dot1xAuthSessionStatsEntry
    ACCESS not-accessible
    STATUS mandatory
    DESCRIPTION
        "A table that contains the session statistics objects 
               for the Authenticator PAE associated with each Port. 
               An entry appears in this table for each port that may 
               authenticate access to itself."
    REFERENCE
        "9.4.."
    ::=  { dot1xPaeAuthenticator 4 }

dot1xAuthSessionStatsEntry OBJECT-TYPE
    SYNTAX Dot1xAuthSessionStatsEntry
    ACCESS not-accessible
    STATUS mandatory
    DESCRIPTION
        "The session statistics information for an Authenticator 
               PAE. This shows the current values being collected for 
               each session that is still in progress, or the final 
               values for the last valid session on each port where 
               there is no session currently active."
    INDEX {dot1xPaePortNumber}
    ::=  { dot1xAuthSessionStatsTable 1 }

Dot1xAuthSessionStatsEntry ::= SEQUENCE {
    dot1xAuthSessionOctetsRx    Counter,
    dot1xAuthSessionOctetsTx    Counter,
    dot1xAuthSessionFramesRx    Counter,
    dot1xAuthSessionFramesTx    Counter,
    dot1xAuthSessionId    SnmpAdminString,
    dot1xAuthSessionAuthenticMethod    INTEGER,
    dot1xAuthSessionTime    TimeTicks,
    dot1xAuthSessionTerminateCause    INTEGER,
    dot1xAuthSessionUserName    SnmpAdminString
    }

dot1xAuthSessionOctetsRx OBJECT-TYPE
    SYNTAX Counter
    ACCESS read-only
    STATUS mandatory
    DESCRIPTION
        "The number of octets received in user data 
               frames on this Port during the session."
    REFERENCE
        "9.4.4, Session Octets Receive."
    ::=  { dot1xAuthSessionStatsEntry 1 }

dot1xAuthSessionOctetsTx OBJECT-TYPE
    SYNTAX Counter
    ACCESS read-only
    STATUS mandatory
    DESCRIPTION
        "The number of octets transmitted in user data 
                frames on this Port during the session."
    REFERENCE
        "9.4.4, Session Octets Transmitted."
    ::=  { dot1xAuthSessionStatsEntry 2 }

dot1xAuthSessionFramesRx OBJECT-TYPE
    SYNTAX Counter
    ACCESS read-only
    STATUS mandatory
    DESCRIPTION
        "The number of user data frames received 
               on this Port during the session."
    REFERENCE
        "9.4.4, Session Frames Receive."
    ::=  { dot1xAuthSessionStatsEntry 3 }

dot1xAuthSessionFramesTx OBJECT-TYPE
    SYNTAX Counter
    ACCESS read-only
    STATUS mandatory
    DESCRIPTION
        "The number of user data frames transmitted 
               on this Port during the session."
    REFERENCE
        "9.4.4, Session Frames Transmitted."
    ::=  { dot1xAuthSessionStatsEntry 4 }

dot1xAuthSessionId OBJECT-TYPE
    SYNTAX SnmpAdminString
    ACCESS read-only
    STATUS mandatory
    DESCRIPTION
        "A unique identifier for the session, in the 
               form of a printable ASCII string of at least 
               three characters."
    REFERENCE
        "9.4.4, Session Identifie."
    ::=  { dot1xAuthSessionStatsEntry 5 }

dot1xAuthSessionAuthenticMethod OBJECT-TYPE
    SYNTAX INTEGER {
              remoteAuthServer          (1),
              localAuthServer          (2)
           }
    ACCESS read-only
    STATUS mandatory
    DESCRIPTION
        "The authentication method used to establish the 
               session."
    REFERENCE
        "9.4.4, Session Authentication Method."
    ::=  { dot1xAuthSessionStatsEntry 6 }

dot1xAuthSessionTime OBJECT-TYPE
    SYNTAX TimeTicks
    ACCESS read-only
    STATUS mandatory
    DESCRIPTION
        "The duration of the session in seconds."
    REFERENCE
        "9.4.4, Session Tim."
    ::=  { dot1xAuthSessionStatsEntry 7 }

dot1xAuthSessionTerminateCause OBJECT-TYPE
    SYNTAX INTEGER {
              supplicantLogoff          (1),
              portFailure          (2),
              supplicantRestart          (3),
              reauthFailed          (4),
              authControlForceUnauth          (5),
              portReInit          (6),
              portAdminDisabled          (7),
			   authControlForceauth		(995),	
			   authServerTerminated	  (996),
			   timeLimitCut			     (997),
			   idleCut					  (998),
              notTerminatedYet          (999)
           }
    ACCESS read-only
    STATUS mandatory
    DESCRIPTION
        "The reason for the session termination."
    REFERENCE
        "9.4.4, Session Terminate Cause."
    ::=  { dot1xAuthSessionStatsEntry 8 }

dot1xAuthSessionUserName OBJECT-TYPE
    SYNTAX SnmpAdminString
    ACCESS read-only
    STATUS mandatory
    DESCRIPTION
        "The User-Name representing the identity of the 
               Supplicant PAE."
    REFERENCE
        "9.4.4, Session User Nam."
    ::=  { dot1xAuthSessionStatsEntry 9 }


END
