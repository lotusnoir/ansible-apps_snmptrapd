-- ============================================================
--  ALCATEL ATM-M4-MIB (Derived from ATM-FORUM-SNMP-M4-MIB) 
-- ============================================================
-- This MIB module is a subset of the ATM-FORUM-SNMP-M4-MIB
-- (as specified in ATM Forum AF-nm-0095 Version 1.0) as
-- implemented in Alcatel's ADSL-1000 System Rel 5.0
-- The following definitions were extracted and adapted to reflect 
-- Alcatel's implementation.
-- Alcatel specific behavior is indicated by comments
-- labeled 'ALCATEL NOTE'.
--

ATM-M4-MIB DEFINITIONS ::= BEGIN

IMPORTS
     OBJECT-TYPE
        FROM RFC-1212
     enterprises
        FROM RFC1155-SMI
     TruthValue, TimeStamp,TestAndIncr,AutonomousType
        FROM SNMPv2-TC
     ifIndex,OwnerString
        FROM ITF-MIB
--     atmVplVpi, 
      atmVclVpi, atmVclVci
        FROM ATM-MIB
;


-- atmfM4MIB MODULE-IDENTITY
--      LAST-UPDATED   "9805140000Z"
--      ORGANIZATION   "The ATM Forum"
--      CONTACT-INFO
--            "The ATM Forum
--             2570 West El Camino Real, Suite 304
--             Mountain View, CA 94040-1313 USA
--             Phone: +1 415-949-6700
--             Fax:   +1 415-949-6705
--             info@atmforum.com"
--      DESCRIPTION
--            "This MIB module is the SNMP version of the ATM Forum's
--             M4 interface (network element view)."
--      REVISION   "9805140000Z"
--      DESCRIPTION
--            "Initial version of MIB module ATM-FORUM-SNMP-M4-MIB."
--     ::= { atmfM4SnmpNEView 1 }

-- ===========================================================================
--  MODULE-IDENTITY
--  LAST-UPDATED "20060605000000Z"
--  ORGANIZATION "Alcatel"
--  CONTACT-INFO
--
--          "Email:  asam.mibsupport@alcatel.be"
--
--  DESCRIPTION  
--       Created from ATM-FORUM-SNMP-M4-MIB (980514000Z)
--       Modified the MIB syntax to confirm with SMIv1
--  
--  REVISION "20060605000000Z"
--  DESCRIPTION
--        "Version: 3EC17924EAAA_E3.2.0.0.0
--         Editor: Rommy VOLDERS
--         Changes:  Open SNMP feature ISAM R3.2"
--
--  REVISION "20060123000000Z"
--  DESCRIPTION
--        "Version: 3EC17924EAAA_E2.0.0.2.1
--         Editor: Bart Bogaert
--         Changes:  Implemented BDFhw70643: strict syntax checks (smilint)"
--
--  date: 29/04/2002   
--  editor: Thierry Caron
--  comment:
--         o Changed the STATUS of the objects of atmfM4VpTestTable and 
--           atmfM4VcTestTable from "optional" to "mandatory"
--         o Changed the ACCESS of atmfM4VpTestObject and atmfM4VcTestObject
--           from "read-write" to "not-accessible" as described in AF-nm-0095
--         o Added ALCATEL NOTE for atmfM4VpTestObject and atmfM4VcTestObject use
--
--  date: 02/07/2001   
--  editor: Hervault Marie-Helene.
--  comment:
--         Key revisions for R5.0 :
--         ========================
--         o New tables atmfM4VpTestTable and atmfM4VcTestTable are added 
--
--
--  date: 11/07/00  -  version: 3ECXXXXXAAAA_R4.2.0
--  editor: Chandrashekhar Menkudle, Murthy N N
--  comment:
--       Created from ATM-FORUM-SNMP-M4-MIB (980514000Z)
--       Modified the MIB syntax to confirm with SMIv1
--
-- ===========================================================================

atmForum                OBJECT IDENTIFIER ::= { enterprises 353 }
atmForumNetworkManagement    OBJECT IDENTIFIER ::= { atmForum 5 }
atmfM4      OBJECT IDENTIFIER ::= { atmForumNetworkManagement 1 }
atmfM4SnmpNEView               OBJECT IDENTIFIER ::= { atmfM4 3 }
atmfM4MIB           OBJECT IDENTIFIER ::= { atmfM4SnmpNEView 1 }
atmfM4MIBObjects    OBJECT IDENTIFIER ::= { atmfM4MIB 1 }
-- atmfM4MIBTraps      OBJECT IDENTIFIER ::= { atmfM4MIB 2 }
-- atmfM4MIBTrapPrefix OBJECT IDENTIFIER ::= { atmfM4MIBTraps 0 }
-- atmfM4MIBConformance OBJECT IDENTIFIER ::= { atmfM4MIB 3 }

--   This MIB module consists of the following tables (Alcatel requirement):
--        (1)  VPL Termination Point Table Extensions
--        (2)  VCL Termination Point Table Extensions
--        (3)  VP 'next VPI' Table
--        (4)  VC 'next VCI' Table
--        (5)  ATM Cell Protocol Monitoring Error Log Table
--        (6)  ATM VP termination Point Test Table
--        (7)  ATM VC termination Point Test Table


--
-- atmfM4VplTable OBJECT-TYPE
--     ::= { atmfM4MIBObjects 9 }
--
-- atmfM4VclTable OBJECT-TYPE
--     ::= { atmfM4MIBObjects 10 }
--

-- atmfM4VpNextVpiTable OBJECT-TYPE
--     ::= { atmfM4MIBObjects 13 }
--

-- atmfM4VcNextVciTable OBJECT-TYPE
--     ::= { atmfM4MIBObjects 14 }
--

-- atmfM4CellProtoErrorTable OBJECT-TYPE
--     ::= { atmfM4MIBObjects 17 }
--


-- atmfM4VpTestTable OBJECT-TYPE
--     ::= { atmfM4MIBObjects 25 }
--

--
-- ATM Forum M4 VC Termination Point Test Table
-- ============================================
--

atmfM4VcTestTable OBJECT-TYPE
     SYNTAX    SEQUENCE OF    AtmfM4VcTestEntry
     ACCESS    not-accessible
     STATUS    mandatory
     DESCRIPTION
          "The ATM Forum M4 VC Termination Point Test table.
          This table allows tests to be run on VCL and VCC
          termination points.

          The operation of this table is entirely analogous to
          that of the ifTestTable in RFC 1573 (which was later
          deprecated in RFC 2233), except that the indexes into
          this table are different."
     ::= { atmfM4MIBObjects 26 }

atmfM4VcTestEntry OBJECT-TYPE
     SYNTAX    AtmfM4VcTestEntry
     ACCESS    not-accessible
     STATUS    mandatory
     DESCRIPTION
          "An entry containing objects for invoking tests on a
          VCL or VCC termination point."
     INDEX          { ifIndex,
                    atmVclVpi,
                    atmVclVci,
                    atmfM4VcTestObject }
     ::= { atmfM4VcTestTable 1 }

AtmfM4VcTestEntry ::= SEQUENCE {
     atmfM4VcTestObject  INTEGER,
     atmfM4VcTestId      TestAndIncr,
     atmfM4VcTestStatus  INTEGER,
     atmfM4VcTestType    AutonomousType,
     atmfM4VcTestResult  INTEGER,
     atmfM4VcTestCode    OBJECT IDENTIFIER,
     atmfM4VcTestOwner   OwnerString
          }

atmfM4VcTestObject OBJECT-TYPE
     SYNTAX    INTEGER {
                    vclTp(1),
                    vccTp(2)
                         }
     ACCESS    not-accessible
     STATUS    mandatory
     DESCRIPTION
          "Specifies whether the test applies to the VCL termination
          point with the specified VPI and VCI values, or to the VCC
          termination point.
          ALCATEL NOTE: A VCL termination point is identified uniquely 
                        by its Ifindex, its VPI value and its VCI value.
                        A VCC termination point is identified uniquely
                        by its Ifindex, its VPI value and its VCI value.
                        In other words, the entry in the AtmfM4VcTestTable
                        indexed by (Ifindex=x, atmVclVpi=y, atmVclVci=z,
                        vclTp) and the entry in the AtmfM4VcTestTable 
                        indexed by (Ifindex=x, atmVplVpi=y, atmVclVci=z, 
                        vccTp) are identical."
     ::= { atmfM4VcTestEntry 1 }

atmfM4VcTestId         OBJECT-TYPE
     SYNTAX   TestAndIncr
     ACCESS   read-write
     STATUS   mandatory    
     DESCRIPTION
          "This object identifies the current invocation of the
          interface's test."
     ::= { atmfM4VcTestEntry 2 }

atmfM4VcTestStatus     OBJECT-TYPE
     SYNTAX   INTEGER { notInUse(1), inUse(2) }
     ACCESS   read-write
     STATUS   mandatory    
     DESCRIPTION
          "This object indicates whether or not some manager
          currently has the necessary 'ownership' required to
          invoke a test on this interface.  A write to this
          object is only successful when it changes its value
          from 'notInUse(1)' to 'inUse(2)'.  After completion of
          a test, the agent resets the value back to
          'notInUse(1)'."
     ::= { atmfM4VcTestEntry 3 }

atmfM4VcTestType       OBJECT-TYPE
     SYNTAX   AutonomousType
     ACCESS   read-write
     STATUS   mandatory    
     DESCRIPTION
          "A control variable used to start and stop operator-
          initiated interface tests.  Most OBJECT IDENTIFIER
          values assigned to tests are defined elsewhere, in
          association with specific types of interface.
          However, this document assigns a value for a full-
          duplex loopback test, and defines the special meanings
          of the subject identifier:

              noTest  OBJECT IDENTIFIER ::= { 0 0 }

          When the value noTest is written to this object, no
          action is taken unless a test is in progress, in which
          case the test is aborted.  Writing any other value to
          this object is only valid when no test is currently in
          progress, in which case the indicated test is
          initiated.

          When read, this object always returns the most recent
          value that atmfM4VcTestType was set to.  If it has not been
          set since the last initialization of the network
          management subsystem on the agent, a value of noTest
          is returned."
     ::= { atmfM4VcTestEntry 4 }

atmfM4VcTestResult  OBJECT-TYPE
     SYNTAX       INTEGER {
                      none(1),          -- no test yet requested
                      success(2),
                      inProgress(3),
                      notSupported(4),
                      unAbleToRun(5),   -- due to state of system
                      aborted(6),
                      failed(7)
                  }
     ACCESS   read-only
     STATUS   mandatory    
     DESCRIPTION
          "This object contains the result of the most recently
          requested test, or the value none(1) if no tests have
          been requested since the last reset.  Note that this
          facility provides no provision for saving the results
          of one test when starting another, as could be
          required if used by multiple managers concurrently."
     ::= { atmfM4VcTestEntry 5 }

atmfM4VcTestCode  OBJECT-TYPE
     SYNTAX   OBJECT IDENTIFIER
     ACCESS   read-only
     STATUS   mandatory    
     DESCRIPTION
          "This object contains a code which contains more
          specific information on the test result, for example
          an error-code after a failed test.  Error codes and
          other values this object may take are specific to the
          type of interface and/or test.  The value may have the
          semantics of either the AutonomousType or
          RowPointer textual conventions as defined in RFC
          1903 [15].  The identifier:

              testCodeUnknown  OBJECT IDENTIFIER ::= { 0 0 }

          is defined for use if no additional result code is
          available."
     ::= { atmfM4VcTestEntry 6 }

atmfM4VcTestOwner      OBJECT-TYPE
     SYNTAX   OwnerString
     ACCESS   read-write
     STATUS   mandatory    
     DESCRIPTION
          "The entity which currently has the 'ownership'
          required to invoke a test on this termination point."
     ::= { atmfM4VcTestEntry 7 }


END
