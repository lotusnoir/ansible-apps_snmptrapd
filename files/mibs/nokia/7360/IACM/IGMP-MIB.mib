IGMP-MIB DEFINITIONS ::= BEGIN

-- =============================================================================
-- This specification is published by Alcatel under Non-Disclosure
-- Agreement(s) (NDA) with specific parties and has to be considered as
-- Confidential Information as defined in such NDA.
-- Alcatel reserves the right to revise this document for any reason,
-- including but not limited to conformity with standards promulgated by
-- various agencies, utilization of advances in the state of the technical
-- areas, or the reflection of changes in the design of any equipment,
-- techniques, or procedures described or referred to herein.
-- The product specifications and other technical or performance
-- information contained herein are subject to change without notice.
-- Updates of this document will be issued under the above NDA's.
-- Alcatel makes no representation or warranty, expressed or implied, with
-- respect to the sufficiency, accuracy, or utility of any information or
-- opinion contained herein. Alcatel expressly advises that any use of for
-- any purpose or reliance upon this technical reference is at the risk of
-- the user and that Alcatel shall not be liable for any damage or injury
-- incurred by any person arising out of the sufficiency, accuracy, or
-- utility of any information or opinion contained herein.
-- This document is not to be construed as a suggestion to any manufacturer
-- to modify or change any of its products, nor does this document
-- represent any commitment by Alcatel to sell or purchase any product.
-- Nothing contained herein shall be construed as conferring by implication,
-- estoppel, or otherwise any license or right under any patent, whether or
-- not the use of any information herein necessarily employs an invention
-- of any existing or later issued patent.
-- Alcatel reserves the right not to offer any or all of these products and
-- to withdraw any or all of them at any future time.
-- Copyright (C) 2006, Alcatel. All Rights Reserved.
-- =============================================================================
--
--  MODULE-IDENTITY
--  LAST-UPDATED   "200705230000Z"
--  ORGANIZATION   "Alcatel"
--  CONTACT-INFO
--
--          Email:  asam.mibsupport@alcatel.be"
--
--
--  DESCRIPTION
--        "This MIB module defines objects for management of
--         IGMP & multicast.
--         The IGMP MIB module is composed of these elements:
--             * Multicast Channel Table,
--             * IGMP Channel Table
--             * Package Table
--             * Module Table
--             * Module Multicast Channel Expansion Table
--             * System variables
--             * General Group Multicast Parameters
--             * Multicast Capacity Parameters
--
-- REVISION Nov 01, 2015
-- DESCRIPTION
--        "Version: 3FE21373EEAA_V5.4.0.0
--        Editor:   Vijayakumar Kanniah
--        Changes:  For ALU02073815 - Supporting unconfigured SSM multicast
--		Added new object igmpSystemUncfgMcastSupport 
--
-- REVISION Jan 24, 2014
-- DESCRIPTION
--        "Version: 3FE21373EBAA_V5.1.0.0
--        Editor:   John Boyle
--        Changes:  For ALU01915837 – Support Display Live Multicast Streams per PON/ONT:
--		Added following 2 tables:
--			multicastPonItf2McGroupAddrTable
--			multicastOntItf2McGroupAddrTable
--

-- REVISION 20130307
-- DESCRIPTION
--        "Version: 3FE20080EAAA_V4.5.0.2.0
--        Editor:   Kupuswamy Ramamurthy
--        Changes: for RCR ALU01438709(7342 Feature Gap: Expanding Configured MC Entries)
--           * Update Row creation and Row deletion for igmpModuleMcastChnlEntry in igmpModuleMcastChnlExpTable table.
--
-- REVISION 20121114
-- DESCRIPTION
--        "Version: 3FE20080EAAA_V4.5.0.1.2
--        Editor:   mahesh katakamsetty
--        Changes: for RCR ALU01808192(FX:Configure IGMP message rate per IGMP control channel)
--           * Update igmpChannelProtocolMaxMsgRate objects access rights to Read-Write in igmpChannelProtocolTable.
--		 By default this Object is in System-Inherited state,which will inherit the value from qosDslControlPktR
--		ate,which will inherit the value from qosDslControlPktRate object.The configuration of this attribute
--		is supported only on GPON LT.for all other LT's this attribute is not supported. 
--
--
-- REVISION 20120920
-- DESCRIPTION
--        "Version: 3FE20080EAAA_V4.5.0.0.0
--        Editor:   mahesh katakamsetty
--        Changes: for RCR ALU01808192(FX:Configure IGMP message rate per IGMP control channel)
--           * Update igmpChannelProtocolMaxMsgRate objects access rights to Read-Write in igmpChannelProtocolTable
--
-- REVISION 20110822
-- DESCRIPTION
--        "Version: 3FE20080EAAA_V4.4.0.0.0
--        Editor:   Mei Yuhua
--        Changes: for RCR ALU01157566. Multicast Cross VLAN translation on FX EPON OLT.
--           * add new table multicastPonTranslationTable
--
-- REVISION 20110414
-- DESCRIPTION
--        "Version: 3FE20080EAAA_V4.3.0.1.0
--        Editor:   Alex Helsen
--        Changes: for RCR ALU01184517 Increase nbr unconfigured
--           * change multicastCapacityMaxNumUnCfg 128 to 1024 
--
-- REVISION 20110112
-- DESCRIPTION
--        "Version: 3FE20080EAAA_V4.3.0.0.0
--        Editor:   Luc Gijselinck
--        Changes: for RCR ALU00459155 Drop non-IGMPv3 packets
--           * add object igmpSystemDiscardLowerVersions
--
-- REVISION 20101223
-- DESCRIPTION
--        "Version: 3FE20080EAAA_V4.3.0.0.0
--         Editor: Madhusudanan Subramanian & Venkatesh Sukumaran
--         Changes:
--             R4.3 RCR ALU00121724. GPON IOP for IGMP CAC and access-rights
--           * Added new table multicastServiceContextProfileTable
--           * Added igmpChannelProtocolServiceContextProfile object to igmpChannelProtocolTable
--           * Added multicastChnlGroupAddrEnd & multicastChnlServiceContextProfile objects 
--              to multicastChnlTable
--           * Modified description of multicastChnlGroupAddr object in multicastChnlTable
--           * Added multicastChannelGroupAddrEnd & multicastChannelServiceContextProfile    
--              objects to multicastChannelTable
--           * Modified description of multicastChannelGroupAddr object in 
--              multicastChannelTable
--           * Added multicastServiceContextProfileIndexNext & 
--              multicastServiceContextProfileMaxIndex to igmpMIB
--           * Added AsamProfileIndex, AsamProfileName, AsamProfileRefCount, 
--              AsamNextProfileIndex, AsamMaxProfileIndex as IMPORTS from ASAM-TC-MIB
--           * Added multicastServiceContextMappingTable
--
--
-- REVISION 20101011
-- DESCRIPTION
--        "Version: 3FE20080EAAA_V4.2.0.0.0
--        Editor:   Udaya S Sivadanam
--        Changes:
--           * add new table multicastTranslationTable
--           * add object igmpChannelProtocolMcastVlanTranslation in igmpChannelProtocolTable
--	 
--
--
-- REVISION 20100512
-- DESCRIPTION
--        "Version: 3FE20080EAAA_V4.2.0.0.0
--        Editor:   Alex Helsen / Luc Gijselinck
--        Changes:
--           * add new table multicastChnltable	      ( add vlanid as key)
--           * add new table igmpModuleMcastChnltable ( add vlanid as key)
--           * add object igmpSystemVlanSelection
--           * make multicastChannelVLANID key in multicastChnlTable
--           * add object igmpPkg2McsrcVlanId ad key to igmpPackage2MulticastSrcTable
--           * add object multicastChannelVLANID as key in igmpModuleMcastChnlExpTable
--           * add object multicastChannelVLANID as key in multicastMonitorTable
--           * add object igmpChannelProtocolMcastVlan in igmpChannelProtocolTable
--	      ==
--
-- REVISION 20100805
-- DESCRIPTION
--        "Version: 3FE20080EAAA_V4.0.10.0.0
--        Editor:   Elvin Taylor
--        Changes:
--           * Changed range to 0..8 and default value to 8 for
--                     igmpChannelProtocolTable.igmpChannelProtocolMulticastChannelPriority
-- REVISION 20100804
-- DESCRIPTION
--        "Version: 3FE20080EAAA_V4.0.10.0.0
--        Editor:   Elvin Taylor
--        Changes:
--           * Changed OID from 37 to 38 for 
--                     igmpChannelProtocolTable.igmpChannelProtocolMulticastChannelPriority
--           * Changed from INSRVMOD=NO to INSRVMOD=YES for
--                     igmpChannelProtocolTable.igmpChannelProtocolMulticastChannelPriority
--           * other editorial changes to the DESCRIPTION based on review comments.
--           * Changed from INSRVMOD=YES to INSRVMOD=NO for igmpSystemOntSignallingEnabled            
--
-- REVISION 20100730
-- DESCRIPTION
--        "Version: 3FE20080EAAA_V4.0.10.0.0
--        Editor:   Elvin Taylor 
--        Changes:
--           * add igmpChannelProtocolTable.igmpChannelProtocolMulticastChannelPriority
--
-- REVISION 20091117
-- DESCRIPTION
--        "Version: 3FE20080EAAA_V4.0.10.0.0
--        Editor:   Tassilo Dietze
--        Changes:
--           * add igmpChannelProtocolTable.igmpChannelProtocolPonBitRateFailJoinCounter
--
-- REVISION 20090930
-- DESCRIPTION
--        "Version: 3FE20080EAAA_V4.0.10.0.0
--        Editor:   Tassilo Dietze
--        Changes:
--           * add igmpChannelProtocolTable. igmpChannelProtocolOntSignallingEnabled
--           * add igmpSystemOntSignalingEnabled
--           * add multicastMonitorTable
-- 
-- REVISION 2009060100001
-- DESCRIPTION 
--        "Version:  3FE20080EAAA_V4.1.FDT918
--         Editor:   Shi Xiong 
--         Changes:
-- 	             add a new IGMP system object igmpSystemForkingAdminStatus 
-- 	             add a new object in the igmp channel protocol table                          
-- REVISION 20070530
-- DESCRIPTION 
--        "Version:  3FE20080EAAA_V3.5.FDT522
--         Editor:   Alex Helsen 
--         Changes:
-- 	     * textual changes in Multicast channel table 
-- REVISION 2007041700001
-- DESCRIPTION  
--        "Version:  3FE20080EAAA_V3.5.0.1.0
--         Editor:   Alex Helsen
--         Changes: 
--               add a new table multicastChanneltable 	(same as multicastSrctable add key )
--               add a new table igmpModuleMcastChannelExpTable (same as igmpModuleMcastSrcExpTable, add key )
--               del table multicastSrctable    
--               del table igmpModuleMcastSrcExpTable
--               add new object igmpChannelProtocolTable.igmpChannelProtocolTxGroupSpecificQueries
--               add new object   			 igmpChannelProtocolDropV3V2reportswrongmode
--               add new object igmpModuleTable.igmpModuleTotalGSQCounter
--		 compress bit-rate objects to one single bit-rate object in the multicastchanneltable
-- REVISION 200705150000Z
-- DESCRIPTION
--        "Version:  3FE20080EAAA_V3.5.0.1.0
--         Editor:   Jia Jungle 
--         Changes:
-- 	     * change the Table size of multicastMcGroupAddrUserItfTable
--           * change the Tbale size of igmpChannelProtocolTable 
--           * remove the literal number of table size       
-- REVISION 200703120000Z
-- DESCRIPTION
--        "Version:  3FE20080EAAA_V3.4.0.0.0
--         Editor:   Kris Van Bos
--         Changes:
--           * Size of multicastSrcTable increased to 4096
--           * Changed description of multicastSrcPkgMembBitmap:
--               the number of packages is restricted
--           * Size of igmpModuleMcastSrcExpTable increased to 4096 * nmbr of slots
--           * Size of igmpMulticastGroup2PackageTable increased to 4096
--           * Size of igmpPackage2MulticastSrcTable increased to 4096
--           * Removed objects from igmpChannelProtocolTable:
--               igmpChannelProtocolBwCacProcessingEnabled
--               igmpChannelProtocolIPAddrAntiSpoofingEnabled
-- REVISION 2007011900001 
-- DESCRIPTION  
--        "Version:  3FE20080EAAA_V3.3.0.0.2
--         Editor:   Liu Li  Alex Helsen
--         Changes:
--                add a new object in igmp channel protocol table : igmpChannelProtocolRowStatus
--                remove IGMP channel table.
--  REVISION 200610190000Z
--  DESCRIPTION
--        "Version:  3FE20080EAAA_V3.3.0.0.0
--         Editor:   Marc Van Vlimmeren, Alex Helsen
--         Changes:
--            * Updates for PB template conformance
--            * AOS improvements and IGMPv3
--               > multicastUserItf2McGroupAddrTable
--                   add    multicastUserItf2McGroupCurrentPreviewNumber
--               > new multicastMcGroupAddr2UserItfTable
--               > new system multicastCDRGenerationMethod
--               > new system multicastCDRGenType
--                      Start-CDR
--                      Stop-CDR
--                      Interim-CDR
--                      max-nbr-review-Exc-CDR
--                      blackout-running-CDR
--                      access-rights-violated-CDR
--                      gen-rat-for-singles
--                      interim-gen-period
--               > new system multicastCDRFileAgingTime
--               > new system multicastCDRSystemPollingCycle
--               > new system igmpSystemProtocolVersionToUser
--               > new system igmpSystemVlanGenV3ProcessingAdminStatus
--               > new system igmpSystemVlanGenV3MaxNumRecordsReport
--               > new igmpVlanSystemTable
--                    igmpV3ProcessingAdminState
--                    igmpV3MaxNumrecordsReport
--               > new igmpChannelProtocolTable
--                    igmpChannelProtocolIndex
--                    igmpChannelProtocolPermPkgBitmap
--                    igmpChannelProtocolMaxMsgRate
--                    igmpChannelProtocolNoPermJoinCounter
--                    igmpChannelProtocolBitRateFailJoinCounter
--                    igmpChannelProtocolInvalidJoinClassDCounter
--                    igmpChannelProtocolNumSecOvrldProtAppl
--                    igmpChannelProtocolClearStats
--                    igmpChannelProtocolMaxNumGroup
--                    igmpChannelProtocolCurrentNumGroup
--                    igmpChannelProtocolNumFailJoinCounter
--                    igmpChannelProtocolSysNumFailJoinCounter
--                    igmpChannelProtocolCurrentPreviewNumber
--                    igmpChannelProtocolPreviewPkgBitmap
--                    igmpChannelProtocolCurrentUncfgGroupNumber
--	                  igmpChannelProtocolBwCacProcessingEnabled
--	                  igmpChannelProtocolIPAddrAntiSpoofingEnabled
--	                  igmpChannelProtocolGMQToUserItfVersion
--                    igmpChannelProtocolTxGeneralQueries
--	   	              igmpChannelProtocolTxGroupSpecificQueries
--                    igmpChannelProtocolRxV1Reports
-- 	                  igmpChannelProtocolRxV2Reports
--	                  igmpChannelProtocolRxV3Reports
--	   	              igmpChannelProtocolRxV2Leaves
--	   	              igmpChannelProtocolRxValidPackets
--	                  igmpChannelProtocolRxInvalidPackets
--                    igmpChannelProtocolRxUnknownTypePackets
--                    igmpChannelProtocolRxBadLengthDrops
--                    igmpChannelProtocolRxBadIpChksmDropsCounter
--                    igmpChannelProtocolRxBadIgmpChksmDropsCounter
--               > new igmpMulticastGroup2PackageTable
--                    igmpPkg2McsrcGroupClassDAddr
--	                  igmpPkg2McsrcGroupSourceIPAddr
--                    igmpPkg2McsrcGroupSourceIndex
--               > update text in
--		               multicastSrcClassDAddr
--                     multicastSrcFastChanChange
--                     multicastSrcPkgMemBitmap
--                     multicastSrcName
--                     multicastSrcAtmSustainBitRate
--                     multicastSrcMaxPreviewDuration
--                     multicastSrcMaxPreviewNumber
--                     multicastSrcPreviewBlackoutDuration
--
--                     igmpChannelCurrentPreviewNumber
--                     igmpChannelCurrentUncfgGroupNumber
--
--                     igmpPreviewRecognitionTime
--
--                     igmpPreviewTimeCounterReset
--                     igmpCDRAdminState
--                     igmpCDRManualRetrievalFlag
--
--                     igmpPackage2MulticastSrcTable
--                     igmpPkg2MscrPackageIndex
--                     igmpPkg2MscrGroupClassDAddr
--              
--                     multicastUserItf2McGroupAddrTable
--                     multicastUserItf2McGroupAddrIfIndex
--                     multicastUserrItf2McGroupAddrVlan
--                     multicastUserItf2McGroupAddrClassDAddr
--                     multicastUserItf2McGroupAddrSrcIPAddr
--                     multicastUserItf2McGroupAddrActualstate
--
--  REVISION 200604050000Z
--  DESCRIPTION
--        "Version:  3FE20080EAAA_Vx.x.x.x.x
--         Editor:   Zhou Lipin
--         Changes:
--           * Modify for IGMP CAC, add guaranteed flag and ethernet rate in
--             Multicast Source Table.
--           * Add counter userSuccessjoinCounter in igmpModuleMcastSrcExpTable
--
--  REVISION 200511160000Z
--  DESCRIPTION
--        "Version:  3FE20080EAAA_Vx.x.x.x.x
--         Editor:   Zheng Dayong
--         Changes:
--            * modify the range of multicastSrcMaxPreviewDuration to 1..6000
--
--  REVISION 200511110000Z
--  DESCRIPTION
--        "Version:  3FE20080EAAA_Vx.x.x.x.x
--         Editor:   Katrien SCHARRE
--         Changes:
--            * add one table to display which multicast streams are watched
--              by a user
--
--  REVISION 200508100000Z
--  DESCRIPTION
--        "Version:  3FE20080EAAA_Vx.x.x.x.x
--         Editor:   Zheng Dayong
--         Changes:
--            * add igmpCDRAdminState and igmpCDRManualRetrievalFlag
--
--  REVISION 200507200000Z
--  DESCRIPTION
--        "Version:  3FE20080EAAA_Vx.x.x.x.x
--         Editor:   Zhang Weihua
--         Changes:
--            * add igmpPreviewCDRGenRecognitionTime to igmp system group
--
--  REVISION 200507180000Z
--  DESCRIPTION
--        "Version:  3FE20080EAAA_Vx.x.x.x.x
--         Editor:   Zheng Dayong
--         Changes:
--            * add preview control to igmpMIB:
--              > IGMP multicast source table
--                     maxPreviewDuration
--                     maxPreviewNumber
--                     previewBlockoutDuration
--              > igmp channel table
--                     igmpChannelCurrentPreviewNumber
--                     igmpChannelPreviewPkgBitmap
--              > igmp system group
--                     igmpPreviewRecognitionTime
--                     igmpPreviewTimeCounterReset
--            * increase multicast limit per port from 4 to 10 in NP LIM.
--              For BRCM LIM the scope is still 4.
--              Counter added in igmp channel table:
--                  igmpChannelCurrentUncfgGroupNumber
--
--  REVISION 200407080000Z
--  DESCRIPTION
--        "Version:  3FE20080EAAA_Vx.x.x.x.x
--         Editor:   Patrick Mensch
--         Changes:
--            *  Changed syntax of igmpModuleCurrentNumRootConnections with
--               OID {igmpModuleEntry 17} from Gauge to Counter.
--            *  Changed syntax of igmpModuleMcastSrcCurrentSubscrIGMPChans with
--               OID {igmpModuleMcastSrcEntry 3} from Gauge to Counter.
--
--  REVISION 200407050000Z
--  DESCRIPTION
--        "Version:  3FE20080EAAA_Vx.x.x.x.x
--         Editor:   Patrick Mensch
--         Changes:
--            *  Changed OID of igmpSystemGroupMembershipInterval to igmpMIB 33
--
--  REVISION 200403040000Z
--  DESCRIPTION
--        "Version:  3FE20080EAAA_Vx.x.x.x.x
--         Editor:   Patrick Mensch
--         Changes:
--            *  Removed multicastCapacityMultEfficiency object from the MIB.
--            *  Editorial changes.
--
--  REVISION 200311130000Z
--  DESCRIPTION
--        "Version:  3FE20080EAAA_Vx.x.x.x.x
--         Editor:   Patrick Mensch
--         Changes:  Initial edition"
--
-- =============================================================================

IMPORTS
    OBJECT-TYPE FROM RFC-1212
    InterfaceIndex
        FROM ITF-MIB
    RowStatus, TruthValue
        FROM SNMPv2-TC
    IpAddress, Gauge, Counter
        FROM RFC1155-SMI
    AtmTrafficDescrParamIndex, AtmServiceCategory, AtmVcIdentifier,
    AtmVpIdentifier
        FROM ATM-TC-MIB
    asam
        FROM SYSTEM-MIB
    NetworkTimeInSeconds, AsamProfilePointer, AsamProfileIndex, AsamProfileName, AsamProfileRefCount,
    AsamNextProfileIndex, AsamMaxProfileIndex
        FROM ASAM-TC-MIB
    VlanId
        FROM Q-BRIDGE-MIB;

-- ===========================================================================
-- iso.org.dod.internet.private.enterprises.alcatel.asd.asam.igmpMIB
-- (1.3.6.1.4.1.637.61.1.29)
-- ===========================================================================

igmpMIB OBJECT IDENTIFIER ::= {asam 29}

-- Threshold for multicast monitoring.

Threshold ::= INTEGER (0..4294967295)


-- ===============================================================================
--  Multicast Source Table
-- ===============================================================================
--
--multicastSrcTable OBJECT-TYPE
--SYNTAX SEQUENCE OF MulticastSrcEntry
--    ACCESS not-accessible
--    STATUS mandatory
--    DESCRIPTION
--        "This table contains management information of pre-configured multicast
--        sources such as group IP address, VLAN ID, package membership
--        bitmap, traffic descriptor, etc. for each multicast source.
--        ALCATEL NOTE:
--            TABLESIZE: 4096
--            DESCR: NA"
--        ::= { igmpMIB 1 }
--
--multicastSrcEntry OBJECT-TYPE
--    SYNTAX MulticastSrcEntry
--    ACCESS not-accessible
--    STATUS mandatory
--    DESCRIPTION
--        "This list contains management information for a pre-configured
--        multicast source.
--        Row creation : An entry is created by operator.
--        Row deletion : An entry is deleted by operator.
--        Index usage : the index is the multicast group IP address.
--        Note that entries will be presented to the SNMP manager in full
--        lexicographical order."
--        INDEX { multicastSrcClassDAddr }
--        ::= {multicastSrcTable 1}
--
--MulticastSrcEntry ::=
--    SEQUENCE {
--        multicastSrcClassDAddr              IpAddress,
--      multicastSrcIfIndex                 InterfaceIndex,
--      multicastSrcAtmVpi                  AtmVpIdentifier,
--      multicastSrcAtmVci                  AtmVcIdentifier,
--        multicastSrcFastChanChange          TruthValue,
--        multicastSrcPkgMembBitmap           OCTET STRING,
--        multicastSrcName                    OCTET STRING,
--      multicastSrcAtmServiceCat           AtmServiceCategory,
--      multicastSrcAtmTrafDescrType        INTEGER,
--        multicastSrcAtmPeakBitRate          INTEGER,
--        multicastSrcAtmSustainBitRate       INTEGER,
--      multicastSrcAtmMbs                  INTEGER,
--      multicastSrcAtmCdvTol               INTEGER,
--      multicastSrcVCLCreationStatus       TruthValue,
--        multicastSrcRowStatus               RowStatus,
--        multicastSrcGuaranteedBWReserve     TruthValue,
--      multicastSrcServiceProfileIndex     AsamProfilePointer,
--      multicastSrcAALProfileIndex         AsamProfilePointer,
--        multicastSrcVLANID                  VlanId,
--        multicastSrcServiceName             OCTET STRING,
--        multicastSrcMaxPreviewDuration      INTEGER,
--        multicastSrcMaxPreviewNumber        INTEGER,
--        multicastSrcPreviewBlackoutDuration INTEGER,
--        multicastSrcEtherPeakBitRate        INTEGER,
--        multicastSrcEtherSustainBitRate     INTEGER
--    }
--
--multicastSrcClassDAddr OBJECT-TYPE
--    SYNTAX IpAddress
--    ACCESS not-accessible
--    STATUS mandatory
--    DESCRIPTION
--        "This index is the multicast group IP address of a multicast stream
--        in network-byte order (big-endian). The class D address must be in
--        the Multicast IP address range 224.0.0.3 to 239.255.255.255 with 
--        exception of the reserved addresses used by the IGMP protocol. 
--        In the meantime, those IP addresses in this table should be 
--        different each other in low-order 23 bits to avoid MAC address 
--        conflict.
--        ALCATEL NOTE:
--            ACCESS:      NA            USAGE:       NA
--            PERSIST:     YES           INSRVMOD:    NA
--            RANGE:       224.0.0.3 .. 239.255.255.255
--                                       DEFVALUE:    NA
--            UNITS:       NA            SPARSE:      NA
--            DESCR:       NA"
--    ::={multicastSrcEntry 1}
--
-- multicastSrcIfIndex OBJECT-TYPE
--      ::={multicastSrcEntry 2 }
--
-- multicastSrcAtmVpi OBJECT-TYPE
--      ::={multicastSrcEntry 3}
--
-- multicastSrcAtmVci OBJECT-TYPE
--      ::={multicastSrcEntry 4}
--
--multicastSrcFastChanChange OBJECT-TYPE
--    SYNTAX TruthValue
--    ACCESS read-write
--    STATUS mandatory
--    DESCRIPTION
--        "This object allows to configure the leave procedure to be applied
--		upon the receipt of a leave request from the end-user for this
--		particular multicast stream.
--		When configured as 'false' then the standard leave procedure
--        is initiated, otherwise , if 'true' then the fast leave with
--        end-user source IP@ & MAC@ tracking is applied.
--        ALCATEL NOTE:
--            ACCESS:      NA            USAGE:       NA
--            PERSIST:     YES           INSRVMOD:    YES
--            RANGE:       NA            DEFVALUE:    NA
--            UNITS:       NA            SPARSE:      NO
--            DESCR:       NA"
--    DEFVAL { true }
--    ::={multicastSrcEntry 5}
--
--multicastSrcPkgMembBitmap OBJECT-TYPE
--    SYNTAX OCTET STRING (SIZE(128))
--    ACCESS read-write
--    STATUS mandatory
--    DESCRIPTION
--        "This object indicates to which package(s) a class D address
--        belongs. A multicast stream can be member of maximum 20 packages or
--        be member of all packages, any value in between is not allowed.
--		Each bit represents a package in the igmpPackageTable.
--        Thus, bit 1 corresponds to package 1, bit 2 corresponds to package 2,
--        and so on.
--        In accordance with the ASAM MIB convention, the bitmap shall
--        function as follows:
--        MSB                            LSB
--        byte 0 :  8  7  6  5  4  3  2  1
--        byte 1 : 16 15 14 13 12 11 10  9
--        byte 2 : 24 23 22 21 20 19 18 17
--        byte 3 : 32 31 30 29 28 27 26 25
--        byte 4 : 40 39 38 37 36 35 34 33
--        byte 5 : 48 47 46 45 44 43 42 41
--        byte 6 : 56 55 54 53 52 51 50 49
--        byte 7 : 64 63 62 61 60 59 58 57
--        ... ... ... ... ... ... ... ...
--
--        byte 127 1024 1023 1022 1021 1020 1019 1018 1017
--        Following the convention, byte 0 shall be the first byte (the
--        left-most, most significant byte).
--        ALCATEL NOTE:
--            ACCESS:      NA            USAGE:       NA
--            PERSIST:     YES           INSRVMOD:    YES
--            RANGE:       NA            DEFVALUE:    NA
--            UNITS:       NA            SPARSE:      NO
--            DESCR:       NA"
--    DEFVAL {'0100000000000000000000000000000000000000000000000000000000000000000000000000000000000000000000000000000000000000000000000000000000000000000000000000000000000000000000000000000000000000000000000000000000000000000000000000000000000000000000000000000000000000'H }
--    ::= {multicastSrcEntry 6}
--
--multicastSrcName OBJECT-TYPE
--    SYNTAX OCTET STRING (SIZE (0..32))
--    ACCESS read-write
--    STATUS mandatory
--    DESCRIPTION
--        "This is a label to make this table more operator friendly.
--        Labels can be used to easily identify multicast streams.
--        ALCATEL NOTE:
--            ACCESS:      NA            USAGE:       NA
--            PERSIST:     YES           INSRVMOD:    YES
--            RANGE:       NA            DEFVALUE:    NA
--            UNITS:       NA            SPARSE:      NO
--            DESCR:       NA"
--    DEFVAL {""}
--    ::= { multicastSrcEntry 7}
--
-- multicastSrcAtmServiceCat OBJECT-TYPE
--      ::= { multicastSrcEntry 8}
--
-- multicastSrcAtmTrafDescrType OBJECT-TYPE
--      ::= {multicastSrcEntry 9}
--
--multicastSrcAtmPeakBitRate OBJECT-TYPE
--    SYNTAX INTEGER (0..100000)
--    ACCESS read-write
--    STATUS mandatory
--    DESCRIPTION
--        "The Peak Bit Rate for the traffic of this multicast stream
--        in the transmit (downstream) direction.
--        This value is measured in units of 1000 bits per second (kbps).
--        ALCATEL NOTE:
--            ACCESS:      NA            USAGE:       NA
--            PERSIST:     YES           INSRVMOD:    NO
--            RANGE:       NA            DEFVALUE:    NA
--            UNITS:       kbps          SPARSE:      NO
--            DESCR:       NA"
--    DEFVAL { 2500 }
--    ::= {multicastSrcEntry 10}
--
--multicastSrcAtmSustainBitRate OBJECT-TYPE
--    SYNTAX INTEGER (0..100000)
--    ACCESS read-write
--    STATUS mandatory
--    DESCRIPTION
--        "The Sustainable Bit Rate of this multicast stream
--        in the transmit (downstream) direction.
--        This value is measured in units of 1000 bits per second (kbps).
--        The default value is derived from the multicastSrcAtmPeakBitRate
--        object as follows:
--        Sustainable Bitrate = 100% of the Peak Bitrate
--        ALCATEL NOTE:
--            ACCESS:      NA            USAGE:       OPT
--            PERSIST:     YES           INSRVMOD:    NO
--            RANGE:       NA            DEFVALUE:    multicastSrcAtmPeakBitRate
--            UNITS:       kbps          SPARSE:      NO
--            DESCR:       NA"
--    ::= {multicastSrcEntry 11}
--
-- multicastSrcAtmMbs OBJECT-TYPE
--      ::= {multicastSrcEntry 12}
--
-- multicastSrcAtmCdvTol OBJECT-TYPE
--      ::= {multicastSrcEntry 13}
--
-- multicastSrcVCLCreationStatus OBJECT-TYPE
--      ::={multicastSrcEntry 14}
--
--multicastSrcRowStatus OBJECT-TYPE
--    SYNTAX RowStatus
--    ACCESS read-write
--    STATUS mandatory
--    DESCRIPTION
--        "This object is used to create a new row or delete an
--        existing row in this table. The possible valid values are:
--            (1) active
--            (4) createdAndGo
--            (6) destroy
--        To create an entry in this table, this object should be set to
--        CreateAndGo. To delete an entry from this table, RowStatus
--        should be set to Destroy value by the SNMP manager.
--        This object does not support the dribble-mode.
--        ALCATEL NOTE:
--            ACCESS:      NA            USAGE:       MAND
--            PERSIST:     NO            INSRVMOD:    YES
--            RANGE:       1|4|6         DEFVALUE:    NA
--            UNITS:       NA            SPARSE:      NA
--            DESCR:       NA"
--    ::= {multicastSrcEntry 15}
--
--multicastSrcGuaranteedBWReserve OBJECT-TYPE
--    SYNTAX TruthValue
--    ACCESS read-write
--    STATUS mandatory
--    DESCRIPTION
--        "This object reserves guaranteed bandwidth for a multicast channel.
--        A value of true means bandwidth is reserved.
--        A value of false means bandwidth is not reserved so there is a
--        probability of blocking. i.e. the multicast source channel may be
--        unavailable for connection.
--        ALCATEL NOTE:
--            ACCESS:      NA            USAGE:       NA
--            PERSIST:     YES           INSRVMOD:    YES
--            RANGE:       NA            DEFVALUE:    NA
--            UNITS:       NA            SPARSE:      NO
--            DESCR:       NA"
--    DEFVAL { false }
--    ::={multicastSrcEntry 16}
--
-- multicastSrcServiceProfileIndex OBJECT-TYPE
--      ::={multicastSrcEntry 17}
--
-- multicastSrcAALProfileIndex OBJECT-TYPE
--      ::={multicastSrcEntry 18}
--
--multicastSrcVLANID OBJECT-TYPE
--    SYNTAX VlanId
--    ACCESS read-write
--    STATUS mandatory
--    DESCRIPTION
--        "This object specifies the VLAN in which the multicast source is.
--        ALCATEL NOTE:
--            ACCESS:      NA            USAGE:       MAND
--            PERSIST:     YES           INSRVMOD:    NO
--            RANGE:       1..4093       DEFVALUE:    NA
--            UNITS:       NA            SPARSE:      NO
--            DESCR:       NA"
--    ::={multicastSrcEntry 19}
--
--multicastSrcServiceName OBJECT-TYPE
--    SYNTAX OCTET STRING (SIZE (0..32))
--    ACCESS read-write
--    STATUS mandatory
--    DESCRIPTION
--        "This is a label to identify the service or service provider which
--        is the originator of this multicast source.
--        ALCATEL NOTE:
--            ACCESS:      NA            USAGE:       NA
--            PERSIST:     YES           INSRVMOD:    YES
--            RANGE:       NA            DEFVALUE:    NA
--            UNITS:       NA            SPARSE:      NO
--            DESCR:       NA"
--    DEFVAL {""}
--    ::= { multicastSrcEntry 20}
--
--multicastSrcMaxPreviewDuration  OBJECT-TYPE
--    SYNTAX INTEGER (1..6000)
--    ACCESS read-write
--    STATUS mandatory
--    DESCRIPTION
--        "This object allows to configure the maximum duration of a
--        preview session for this stream.
--        Upon the receipt of a join request to preview this stream ,
--        the user will be allowed to view this multicast stream for
--		a time period equal to the time configured in this object.
--		Upon expiry of this time period, the IGMP subsystem will
--		autonomously stop this multicast stream and block this stream
--		for the concerend IGMP channel for a period equal to the
--		time configured in the PreviewBlackoutDuration object.
--        ALCATEL NOTE:
--            ACCESS:      NA            USAGE:       NA
--            PERSIST:     YES           INSRVMOD:    NO
--            RANGE:       NA            DEFVALUE:    NA
--            UNITS:       secs          SPARSE:      NO
--            DESCR:       NA"
--    DEFVAL {180}
--    ::= {multicastSrcEntry 21}
--
--
--multicastSrcMaxPreviewNumber  OBJECT-TYPE
--    SYNTAX INTEGER (1..100)
--    ACCESS read-write
--    STATUS mandatory
--    DESCRIPTION
--        "This object allows to configure the maximum number of previews
--		per preview period for this multicast stream at a particular IGMP
--		channel . 
--        ALCATEL NOTE:
--            ACCESS:      NA            USAGE:       NA
--            PERSIST:     YES           INSRVMOD:    NO
--            RANGE:       NA            DEFVALUE:    NA
--            UNITS:       NA            SPARSE:      NO
--            DESCR:       NA"
--    DEFVAL {3}
--   ::= {multicastSrcEntry 22}
--
--
--multicastSrcPreviewBlackoutDuration  OBJECT-TYPE
--    SYNTAX INTEGER (0..7200)
--    ACCESS read-write
--    STATUS mandatory
--    DESCRIPTION
--        "This object allows to configure the Preview Blackout Duration
--        time for this multicast stream.
--        ALCATEL NOTE:
--            ACCESS:      NA            USAGE:       NA
--            PERSIST:     YES           INSRVMOD:    NO
--            RANGE:       NA            DEFVALUE:    NA
--            UNITS:       secs          SPARSE:      NO
--            DESCR:       NA"
--    DEFVAL {0}
--    ::= {multicastSrcEntry 23}
--
--multicastSrcEtherPeakBitRate OBJECT-TYPE
--    SYNTAX INTEGER (0..100000)
--    ACCESS read-write
--    STATUS mandatory
--    DESCRIPTION
--        "The Peak Bit Rate for the traffic of this multicast source
--        in the transmit (downstream) direction.
--        This value is measured in units of 1000 bits per second (kbps) based
--        Ethernet packet.
--        ALCATEL NOTE:
--            ACCESS:      NA            USAGE:       NA
--            PERSIST:     YES           INSRVMOD:    NO
--            RANGE:       NA            DEFVALUE:    NA
--            UNITS:       kbps          SPARSE:      NO
--            DESCR:       NA"
--    DEFVAL { 2125 }
--    ::= {multicastSrcEntry 24}
--
--multicastSrcEtherSustainBitRate OBJECT-TYPE
--    SYNTAX INTEGER (0..100000)
--    ACCESS read-write
--    STATUS mandatory
--    DESCRIPTION
--        "The Sustainable Bit Rate for the traffic of this multicast source
--        in the transmit (downstream) direction.
--        This value is measured in units of 1000 bits per second (kbps) based
--        Ethernet packet. The default value is dependent on the
--        multicastSrcAtmPeakBitRate object as follows:
--        Sustainable Bitrate = 100% of the Ethernet Peak Bitrate
--        ALCATEL NOTE:
--            ACCESS:      NA            USAGE:       MAND
--            PERSIST:     YES           INSRVMOD:    NO
--            RANGE:       NA            DEFVALUE:    multicastSrcEtherPeakBitRate
--            UNITS:       kbps          SPARSE:      NO
--            DESCR:       NA"
--    ::= {multicastSrcEntry 25}


-- ===============================================================================
--  IGMP Channel Table
-- ===============================================================================
--igmpChannelTable OBJECT-TYPE
--        SYNTAX SEQUENCE OF IgmpChannelEntry
--        ACCESS not-accessible
--        STATUS mandatory
--        DESCRIPTION
--                "This table contains multicast capacity parameters as well as
--               statistics and counters related to IGMP&multicast per ADSL
--                bridge port."
--        ::= { igmpMIB 2}

--igmpChannelEntry OBJECT-TYPE
--        SYNTAX IgmpChannelEntry
--        ACCESS not-accessible
--        STATUS mandatory
--        DESCRIPTION
--                "This object contains multicast capacity parameters
--                as well as statistics and counters related to
--                IGMP&multicast of an ADSL bridge port."
--        INDEX { igmpChannelIfIndex, igmpChannelVpi, igmpChannelVci }
--        ::= {igmpChannelTable 1}

--IgmpChannelEntry ::=
--        SEQUENCE {
--              igmpChannelIfIndex                         InterfaceIndex,
--              igmpChannelVpi                             AtmVpIdentifier,
--              igmpChannelVci                             AtmVcIdentifier,
--              igmpChannelMulticastVpi                    AtmVpIdentifier,
--              igmpChannelMulticastMinVci                 AtmVcIdentifier,
--              igmpChannelPermPkgBitmap                   OCTET STRING,
--              igmpChannelMaxMsgRate                      INTEGER,
--              igmpChannelMaxNumOfMcastVCs                INTEGER,
--              igmpChannelMaxTotalMcastBitRate            INTEGER,
--              igmpChannelMcastBitRateUsed                INTEGER,
--              igmpChannelNumMcastVCsUsed                 INTEGER,
--              igmpChannelNoPermJoinCounter               Counter,
--              igmpChannelBitRateFailJoinCounter          Counter,
--              igmpChannelNumVCsFailJoinCounter           Counter,
--              igmpChannelCACFailJoinCounter              Counter,
--              igmpChannelInvalidJoinClassDCounter        Counter,
--              igmpChannelNumSecOvrldProtAppl             Counter,
--              igmpChannelClearStats                      TruthValue,
--              igmpChannelOperStatus                      TruthValue,
--              igmpChannelRowStatus                       RowStatus,
--              igmpChannelMaxNumGroup                     INTEGER,
--              igmpChannelUnusedMcastBitRate              INTEGER,
--              igmpChannelCurrentNumGroup                 Gauge,
--              igmpChannelNumFailJoinCounter              Counter,
--              igmpChannelInternalBitRateFailJoinCounter  Counter,
--              igmpChannelIWFBitRateFailJoinCounter       Counter,
--              igmpChannelUplinkBitRateFailJoinCounter    Counter,
--              igmpChannelSysNumFailJoinCounter           Counter,
--              igmpChannelCurrentPreviewNumber            Counter,
--              igmpChannelPreviewPkgBitmap                OCTETSTRING,
--              igmpChannelCurrentUncfgGroupNumber         Counter, 
--	           igmpChannelBwCacProcessingEnabled          TruthValue,
--	           igmpChannelIPAddrAntiSpoofingEnabled       TruthValue,
--		      igmpChannelGMQToUserItfVersion             INTEGER
--
--        }

--igmpChannelIfIndex OBJECT-TYPE
--        SYNTAX InterfaceIndex
--        ACCESS not-accessible
--        STATUS mandatory
--        DESCRIPTION
--                "This is the IfIndex associated with the access ATM interface which                is carrying
--the IGMP channel, and the multicast egress traffic.
--                "
--        ::={igmpChannelEntry 1}
--
--igmpChannelVpi OBJECT-TYPE
--        SYNTAX AtmVpIdentifier
--        ACCESS not-accessible
--        STATUS mandatory
--        DESCRIPTION
--                "Virtual path identifier for this channel. This object is
--                also one of the indices of this table.
--                The valid range of Vpi values is release-dependent."
--        ::={igmpChannelEntry 2}

--igmpChannelVci OBJECT-TYPE
--        SYNTAX AtmVcIdentifier
--        ACCESS not-accessible
--        STATUS mandatory
--        DESCRIPTION
--                "Virtual channel identifier for this channel. This object is
--                also one of the indices of this table.
--                The valid range of Vci values is release-dependent.
--                "
--        ::={igmpChannelEntry 3}
--
-- igmpChannelMulticastVpi OBJECT-TYPE
--      SYNTAX AtmVpIdentifier
--      ACCESS read-write
--      STATUS mandatory
--      DESCRIPTION
--              "Indicates the ATM Virtual Path Identifier used by all
--              multicast leaf VCLs created using the IGMP channel. The range
--              of values for this parameter is release-dependent. In general,
--              it must be within the ranges specified in the attributes of the
--              Access Profile used by the ATM interface. This Vpi value shall
--              be allocated to all multicast leaf VCLs created using the IGMP
--              channel. It isn't applied in ISAM."
--      ::= {igmpChannelEntry 4}

-- igmpChannelMulticastMinVci OBJECT-TYPE
--      SYNTAX AtmVcIdentifier
--      ACCESS read-write
--      STATUS mandatory
--      DESCRIPTION
--              "This parameter specifies the minimum Vci in a range of vci
--              values that are allocated to multicast leaf VCLs created on
--              the IGMP channel.
--              The maximum Vci is derived from the value of this object
--              and igmpChannelMaxNumOfMcastVCs. i.e.
--              maxVci = (igmpChannelMulticastMinVci +
--              igmpChannelMaxNumOfMcastVCs - 1)
--              It isn't applied in ISAM."
--      ::= {igmpChannelEntry 5}

--igmpChannelPermPkgBitmap OBJECT-TYPE
--        SYNTAX OCTET STRING (SIZE(128))
--        ACCESS read-write
--        STATUS mandatory
--        DESCRIPTION
--                "The purpose of this bitmap is to indicate which packages
--                the user is allowed to join. In accordance with the
--                ASAM MIB convention, the bitmap shall function as follows:
--                MSB                                     LSB
--                byte 0 :  8  7  6  5  4  3  2  1
--                byte 1 : 16 15 14 13 12 11 10  9
--                byte 2 : 24 23 22 21 20 19 18 17
--                byte 3 : 32 31 30 29 28 27 26 25
--                byte 4 : 40 39 38 37 36 35 34 33
--                byte 5 : 48 47 46 45 44 43 42 41
--                byte 6 : 56 55 54 53 52 51 50 49
--                byte 7 : 64 63 62 61 60 59 58 57
--                ... ... ... ... ... ... ... ...

--                byte 127 1024 1023 1022 1021 1020 1019 1018 1017
--                Following the convention, byte 0 shall be the first byte (the
--                left-most, most significant byte).
--                "
--        DEFVAL {'0000000000000000000000000000000000000000000000000000000000000000000000000000000000000000000000000000000000000000000000000000000000000000000000000000000000000000000000000000000000000000000000000000000000000000000000000000000000000000000000000000000000000000'H }
--        ::= {igmpChannelEntry 6}

--igmpChannelMaxMsgRate OBJECT-TYPE
--        SYNTAX INTEGER (0..65535)
--        ACCESS read-only
--        STATUS mandatory
--        DESCRIPTION
--                "This object indicates the maximum messages per second that can be
--                received by the IGMP protocol stack. When the message rate
--                exceeds this value, overload protection will be applied to the
--                IGMP channel.   "
--        DEFVAL { 16 }
--        ::= {igmpChannelEntry 7}

-- igmpChannelMaxNumOfMcastVCs OBJECT-TYPE
--      SYNTAX INTEGER (0..14)
--      ACCESS read-write
--      STATUS mandatory
--      DESCRIPTION
--              "Indicates the maximum number of multicast channels (leaf
--              VCs) allowed on this IGMP channel.
--              The maximum multicast leaf Vci is derived from the value of
--              this object and igmpChannelMulticastMinVci. i.e.
--              maxVci = (igmpChannelMulticastMinVci +
--              igmpChannelMaxNumOfMcastVCs - 1)
--              It isn't applied in ISAM ."
--      DEFVAL { 3 }
-- ::={igmpChannelEntry 8}

-- igmpChannelMaxTotalMcastBitRate OBJECT-TYPE
--         SYNTAX INTEGER (0..100000)
--         ACCESS read-write
--         STATUS mandatory
--         DESCRIPTION
--                 "This object contains the maximum allowed bandwidth
--                 consumption for multicast channels. The multicastSrcAtmPeakBitRate
--                 is used for calculating bandwidth cossumption ADSL port at Phase 1,
--                 which is different from R4.5/5.0 and may lead to incorrect reject,
--   		     but it reduces probability of congestion.
--                 This value is measured in units of 1000 bits per second (kbps).
--                 This object can be modified when igmpChannelCurrentNumGroup = 0,
--                 or igmpChannelMaxNumGroup = 0, or igmpSystemChangeOperStatus = false."
--        DEFVAL { 0 }
--        ::={igmpChannelEntry 9}

-- igmpChannelMcastBitRateUsed OBJECT-TYPE
--      SYNTAX INTEGER
--      ACCESS read-only
--      STATUS mandatory
--      DESCRIPTION
--              "This field is used for tracking bandwidth consumed by
--              multicast channels. In R4.5/5.0, it is defined as follow:
--              1) For multicast channels with VBR service
--              category, the multicastSrcAtmSustainBitRate is used for calculating
--              bandwidth consumption. 2) For CBR, the
--              multicastSrcAtmPeakBitRate is used.
--              This value is measured in units of 1000 bits per second (kbps).
--              It isn't applied in ISAM ."
--      DEFVAL {0}
--      ::={igmpChannelEntry 10}

-- igmpChannelNumMcastVCsUsed OBJECT-TYPE
--      SYNTAX INTEGER
--      ACCESS read-only
--      STATUS mandatory
--      DESCRIPTION
--              "Indicates the number of multicast channels (leaf
--              VCs) currently connected on this channel.
--              It isn't applied in ISAM ."
--      DEFVAL { 0 }
--      ::={igmpChannelEntry 11}


--igmpChannelNoPermJoinCounter OBJECT-TYPE
--        SYNTAX Counter
--        ACCESS read-only
--        STATUS mandatory
--        DESCRIPTION
--                "Indicates the number of times that a permission bitmap failure
--                has occurred. (In other words, a request to join a multicast
--                channel has been attempted for which the IGMP channel has no
--                permission.)"
--        DEFVAL { 0 }
--        ::= {igmpChannelEntry 12}

--igmpChannelBitRateFailJoinCounter OBJECT-TYPE
--        SYNTAX Counter
--        ACCESS read-only
--        STATUS mandatory
--        DESCRIPTION
--                "Indicates the number of times that an IGMP join message failed
--                to trigger a multicast connection because the resultant
--                bandwidth would exceed the maximum total bitrate allowed."
--        DEFVAL { 0 }
--        ::= {igmpChannelEntry 13}

-- igmpChannelNumVCsFailJoinCounter OBJECT-TYPE
--      SYNTAX Counter
--      ACCESS read-only
--      STATUS mandatory
--      DESCRIPTION
--              "Indicates the number of times that an IGMP join message failed
--              to trigger a multicast connection because the resultant
--              number of VCs was higher than the maximum number of multicast
--              VCs allowed. It isn't applied in ISAM ."
--      DEFVAL { 0 }
--      ::= {igmpChannelEntry 14}

-- igmpChannelCACFailJoinCounter OBJECT-TYPE
--      SYNTAX Counter
--      ACCESS read-only
--      STATUS mandatory
--      DESCRIPTION
--              "Indicates the number of times that ATM CAC (connection admission
--              control) failed, causing a join attempt to fail.
--              It isn't applied in ISAM ."
--      DEFVAL { 0 }
--      ::= {igmpChannelEntry 15}

--igmpChannelInvalidJoinClassDCounter OBJECT-TYPE
--        SYNTAX Counter
--        ACCESS read-only
--        STATUS mandatory
--        DESCRIPTION
--                "Indicates the number of times that the IP address:
--                1) it isn't multicast address, or
--                2) it is a reserved multicast address, or
--                3) it isn't in Multicast Source Table, but its low-order
--                   23 bits are same as those of a group IP address in
--                   Multicast Source Table"
--        DEFVAL { 0 }
--        ::= {igmpChannelEntry 16}

--igmpChannelNumSecOvrldProtAppl OBJECT-TYPE
--        SYNTAX Counter
--        ACCESS read-only
--        STATUS mandatory
--        DESCRIPTION
--                "Indicates the number of one second intervals for which overload
--                protection has been applied because the message rate exceeded
--                the peak threshold (igmpChannelMaxMsgRate)."
--        DEFVAL { 0 }
--        ::= {igmpChannelEntry 17}

--igmpChannelClearStats OBJECT-TYPE
--        SYNTAX TruthValue
--        ACCESS read-write
--        STATUS mandatory
--        DESCRIPTION
--                "When this object is set to true, the statistics within this
--                table are cleared. When this object is set to false, the request is
--                ignored."
--        DEFVAL {false}
--        ::={igmpChannelEntry 18}

-- igmpChannelOperStatus OBJECT-TYPE
--      SYNTAX TruthValue
--      ACCESS read-only
--      STATUS mandatory
--      DESCRIPTION
--              "This object indicates the operational status of the IGMP Channel
--              with respect to the servicing of IGMP requests.
--                      (1) True = operational
--              (2) False = not operational
--              It isn't applied in ISAM ."
--      DEFVAL {FALSE}
--      ::={igmpChannelEntry 19}

-- igmpChannelRowStatus OBJECT-TYPE
--      SYNTAX RowStatus
--      ACCESS read-write
--      STATUS mandatory
--      DESCRIPTION
--              "This object is used to create a new row or delete
--              an existing row in this table. The possible valid values are:
--                      (1) active
--                      (4) createdAndGo
--                      (6) destroy
--              To create an entry in this table, this object should be set to
--              CreateAndGo. To delete an entry from this table, RowStatus should be
--              set to Destroy value by the SNMP manager.
--              This object does not support the dribble-mode.
--              It isn't applied in ISAM ."
--      ::={igmpChannelEntry 20}

--igmpChannelMaxNumGroup OBJECT-TYPE
--        SYNTAX INTEGER (0..100)
--       ACCESS read-write
--        STATUS mandatory
--        DESCRIPTION
--                "The Maximum Group Number this port(ADSL, PVC) can support.
--                When it is 0, this port doesn't support IGMP and
--                multicast, and all IGMP messages shouldn't be sent to this
--                port and all IGMP messages from this port should be discarded.
--                It doesn't include the MAC+VLAN entry for GMQ in ISAM R2.1.
--                When modify this object, remove all multicast MAC+VALN entries
--                for multicast stream and stop all multicast streams in this port,
--               if set it to 0, remove MAC+VLAN entry for GMQ for this port.
--                After R2.4, for NP LIM board, this threshold may be increase to 10,
--                for BRCM LIM, it still is 4. "
--        DEFVAL { 0 }
--        ::= { igmpChannelEntry 21 }

-- igmpChannelUnusedMcastBitRate OBJECT-TYPE
--        SYNTAX INTEGER (0..100000)
--        ACCESS read-only
--        STATUS mandatory
--        DESCRIPTION
--                "The Unused Bit Rate for the multicast traffic in the
--                port(ADSL, PVC) (downstream).
--                This value is measured in units of 1000 bits per second (kbps),
--                It is define by:
--                igmpChannelUnusedMcastBitRate = igmpChannelMaxTotalMcastBitRate -
--                SUM( peak/maximum bit rates for all multicast traffic in this port)
--                "
--        DEFVAL { igmpChannelMaxTotalMcastBitRate  }
--        ::= { igmpChannelEntry 22 }

--igmpChannelCurrentNumGroup OBJECT-TYPE
--        SYNTAX Gauge
--        ACCESS read-only
--       STATUS mandatory
--        DESCRIPTION
--                "Indicates the current group number in this port(ADSL, PVC)."
--        DEFVAL { 0 }
--        ::= { igmpChannelEntry 23 }

--igmpChannelNumFailJoinCounter OBJECT-TYPE
--        SYNTAX Counter
--        ACCESS read-only
--        STATUS mandatory
--        DESCRIPTION
--                "Indicates the number of times that a join fails
--                 because the resultant number of simultaneous streams
--                 was higher than the maximum allowed on the port."
--        DEFVAL { 0 }
--        ::= { igmpChannelEntry 24 }

-- igmpChannelInternalBitRateFailJoinCounter OBJECT-TYPE
--      SYNTAX Counter
--      ACCESS read-only
--      STATUS mandatory
--      DESCRIPTION
--              "Indicates the number of times that an IGMP join fails
--              because the bit rate between switch and IWF for multicast
--              isn't enough for this join. As there are two Ethernet port
--              between switch and IWF, and the port selection is based on
--              MAC address: even or odd, checking bit rate should base on
--              the Ethernet port from which multicast stream is sent if
--              Accept this join."
--      DEFVAL { 0 }
--      ::= { igmpChannelEntry 25 }

-- igmpChannelIWFBitRateFailJoinCounter OBJECT-TYPE
--      SYNTAX Counter
--      ACCESS read-only
--      STATUS mandatory
--      DESCRIPTION
--              "Indicates the number of times that an IGMP join fails because
--              the IWF bit rate for multicast isn't enough for this join."
--      DEFVAL { 0 }
--      ::= { igmpChannelEntry 26 }

-- igmpChannelUplinkBitRateFailJoinCounter OBJECT-TYPE
--      SYNTAX Counter
--      ACCESS read-only
--      STATUS mandatory
--      DESCRIPTION
--              "Indicates the number of times that an IGMP join fails because
--              the uplink bit rate for multicast isn't enough for this join.
--              As there are two Ethernet ports for uplink, and the port
--              selection is based on negotiation of IEEE802.3ad, checking
--              bit rate should base on the Ethernet port from which
--              multicast stream is sent if accept this join."
--      DEFVAL { 0 }
--      ::= { igmpChannelEntry 27 }

--igmpChannelSysNumFailJoinCounter OBJECT-TYPE
--        SYNTAX Counter
--        ACCESS read-only
--        STATUS mandatory
--        DESCRIPTION
--                "Indicates the number of times that an IGMP join fails
--                because the resultant number of all/unconfigured
--                groups was higher than the maximum number of
--                all/unconfigured multicast groups allowed."
--        DEFVAL { 0 }
--        ::= { igmpChannelEntry 28 }

--igmpChannelCurrentPreviewNumber  OBJECT-TYPE
--        SYNTAX Counter
--        ACCESS read-only
--        STATUS mandatory
--        DESCRIPTION
--                "This object counts the total number of validated preview 
--		 sessions on this IGMP channel."
--        DEFVAL { 0 }
--        ::= { igmpChannelEntry 29 }

--igmpChannelPreviewPkgBitmap OBJECT-TYPE
--        SYNTAX OCTET STRING (SIZE(128))
--        ACCESS read-write
--        STATUS mandatory
--        DESCRIPTION
--                "The purpose of this bitmap is to indicate which packages
--                the user is allowed to join for preview. In accordance with the
--                ASAM MIB convention, the bitmap shall function as follows:
--                MSB                                     LSB
--                byte 0 :  8  7  6  5  4  3  2  1
--                byte 1 : 16 15 14 13 12 11 10  9
--                byte 2 : 24 23 22 21 20 19 18 17
--                byte 3 : 32 31 30 29 28 27 26 25
--                byte 4 : 40 39 38 37 36 35 34 33
--                byte 5 : 48 47 46 45 44 43 42 41
--                byte 6 : 56 55 54 53 52 51 50 49
--                byte 7 : 64 63 62 61 60 59 58 57
--                ... ... ... ... ... ... ... ...
--
--                byte 127 1024 1023 1022 1021 1020 1019 1018 1017
--                Following the convention, byte 0 shall be the first byte (the
--                left-most, most significant byte).
--                "
--        DEFVAL {'FFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFF'H }
--        ::= {igmpChannelEntry 30}



--igmpChannelCurrentUncfgGroupNumber  OBJECT-TYPE
--        SYNTAX Counter
--        ACCESS read-only
--        STATUS mandatory
--        DESCRIPTION
--                "This object counts the number of non-configured multicast 
--		 streams that are actually active on this IGMP channel ."
--        DEFVAL { 0 }
--        ::= { igmpChannelEntry 31 }

--igmpChannelBwCacProcessingEnabled  OBJECT-TYPE
--      SYNTAX TruthValue
--      ACCESS read-write
--      STATUS mandatory
--      DESCRIPTION
--       "This object allows to enable or disable Bandwidth CAC for pre-configured 
--        multicast streams on this user interface .When disabled, the IGMP 
--        subsystem will not check whether there is still sufficient bandwidth 
--	left to support another multicast stream on this user interface ." 
--      DEFVAL {true}
--      ::={igmpChannelEntry 32}

--igmpChannelIPAddrAntiSpoofingEnabled  OBJECT-TYPE
--      SYNTAX  TruthValue
--      ACCESS read-write
--      STATUS mandatory
--      DESCRIPTION
--        "This object allows to enable or disable IP@ anti-spoofing on this user-
--         interface .When disabled, the IGMP subsysytem will not check the source
--	 IP@ of the received IGMP packet against the IP@ that was learnt by DHCP
--	 Note :when enabled also teh IP@ 0.0.0.0 is allowed as a valid src IP@ "
--        DEFVAL {true}
--       ::={igmpChannelEntry 33}

--igmpChannelGMQToUserItfVersion OBJECT-TYPE
--      SYNTAX  INTEGER   { system-inherited(1), version-2(2), version-3(3)}
--      ACCESS read-write 
--      STATUS mandatory
--      DESCRIPTION
--        " The GMQToUserItfVersion object allows the operator to configure 
--	whether the iGMP subsystem must initiate IGMPv2 GMQs or IGMPv3 GMQs 
--	on a particular User Interface. When set to IGMPv2 the iSAM IGMP subsystem 
--	initiates GMQs with v2 towards the end-user and forces the end-user on this 
--	User interface to run in IGMPv2 mode; End-user initiated IGMPv3 reports are
--	not accepted.When set to IGMPv3 the iSAM IGMP subsystem initiates GMQs with 
--	v3 towards the end-user. The end-user on this User Interface may run in either
--	IGMPv2 or IGMPv3 mode. Both, end-user initiated IGMPv2 and IGMPv3 reports 
--	are accepted. The object defaults to -inherited- and  inherits the 
--	GMQToUserSideVersion from the System Level object. 
--	If this User Interface (IGMP Channel) requires a different behaviour 
--	than configured in the system level object then the correct value needs 
--	to be configured in this object.
--        This object defaults to inherited "
--         DEFVAL {system-inherited}
--       ::={igmpChannelEntry 34}


-- ===============================================================================
--  IGMP Package Table.
-- ===============================================================================
igmpPackageTable OBJECT-TYPE
    SYNTAX SEQUENCE OF IgmpPackageEntry
    ACCESS not-accessible
    STATUS mandatory
    DESCRIPTION
        "This table provides a name for package bitmaps used in the
        multicastSrcTable.
        ALCATEL NOTE:
            TABLESIZE: 1024
            DESCR: NA"
    ::= {igmpMIB 4}

igmpPackageEntry OBJECT-TYPE
    SYNTAX IgmpPackageEntry
    ACCESS not-accessible
    STATUS mandatory
    DESCRIPTION
        "Each entry contains the information related to the package.
        Row creation : An entry is created by .
        Row deletion :
        Index usage : the index is the .
        Note that entries will be presented to the SNMP manager in full
        lexicographical order."
    INDEX {igmpPackageIndex}
    ::= {igmpPackageTable 1}

IgmpPackageEntry ::=
    SEQUENCE {
        igmpPackageIndex            INTEGER,
        igmpPackageName             OCTET STRING,
        igmpPackageTemplateName     OCTET STRING,
        igmpPackageTemplateVersion  INTEGER
--      igmpPackageNbrUsers         INTEGER
        }

igmpPackageIndex OBJECT-TYPE
    SYNTAX INTEGER
    ACCESS not-accessible
    STATUS mandatory
    DESCRIPTION
        "This object identifies a particular package. Its value is
        associated with the bit positions of objects
        multicastSrcPkgMembBitmap, generalMulticastPkgMembBitmap
        and igmpIntfVcAllowedPackages.
        ALCATEL NOTE:
            ACCESS:      NA            USAGE:       NA
            PERSIST:     YES           INSRVMOD:    NA
            RANGE:       1..1024       DEFVALUE:    NA
            UNITS:       NA            SPARSE:      NA
            DESCR:       NA"
    ::={igmpPackageEntry 1}

igmpPackageName OBJECT-TYPE
    SYNTAX OCTET STRING (SIZE (0..32))
    ACCESS read-write
    STATUS mandatory
    DESCRIPTION
        "This object is the name associated with a particular package.
        ALCATEL NOTE:
            ACCESS:      NA            USAGE:       NA
            PERSIST:     YES           INSRVMOD:    YES
            RANGE:       NA            DEFVALUE:    NA
            UNITS:       NA            SPARSE:      NO
            DESCR:       NA"
    DEFVAL { "" }
    ::={igmpPackageEntry 2}

igmpPackageTemplateName OBJECT-TYPE
    SYNTAX OCTET STRING (SIZE (0..32))
    ACCESS read-write
    STATUS mandatory
    DESCRIPTION
        "This object identifies the service template name on which this
        package is defined.
        ALCATEL NOTE:
            ACCESS:      NA            USAGE:       NA
            PERSIST:     YES           INSRVMOD:    YES
            RANGE:       NA            DEFVALUE:    NA
            UNITS:       NA            SPARSE:      NO
            DESCR:       NA"
    DEFVAL { "" }
    ::={igmpPackageEntry 3}

igmpPackageTemplateVersion OBJECT-TYPE
    SYNTAX INTEGER
    ACCESS read-write
    STATUS mandatory
    DESCRIPTION
        "This object identifies the service template version on which
        this package is defined.
        ALCATEL NOTE:
            ACCESS:      NA            USAGE:       OPT
            PERSIST:     YES           INSRVMOD:    YES
            RANGE:       0..65535      DEFVALUE:    0
            UNITS:       NA            SPARSE:      NO
            DESCR:       NA"
        ::={igmpPackageEntry 4}

-- igmpPackageNbrUsers OBJECT-TYPE
--      ::={igmpPackageEntry 5}

-- ===============================================================================
--  IGMP Module Table.
-- ===============================================================================

igmpModuleTable OBJECT-TYPE
    SYNTAX SEQUENCE OF IgmpModuleEntry
    ACCESS not-accessible
    STATUS mandatory
    DESCRIPTION
        "This table contains aggregated statistics maintained for IGMP proxy
        in system level
        ALCATEL NOTE:
            TABLESIZE: nmbr of slots
            DESCR: NA"
    ::= {igmpMIB 5}

igmpModuleEntry OBJECT-TYPE
    SYNTAX IgmpModuleEntry
    ACCESS not-accessible
    STATUS mandatory
    DESCRIPTION
        "Each entry reflects the aggregrated statistics maintained for
        IGMP proxy.
        Row creation : An entry is created by system.
        Row deletion :  An entry is created by system
        Index usage : the index is the slot index.
        Note that entries will be presented to the SNMP manager in full
        lexicographical order."
    INDEX { igmpModuleSlotIndex }
    ::= {igmpModuleTable 1}

IgmpModuleEntry ::=
        SEQUENCE {
                igmpModuleSlotIndex                   INTEGER,
                igmpModuleTotalMsgsCounter            Counter,
                igmpModuleTotalIGMPMsgsCounter        Counter,
                igmpModuleTotalJoinRequestsCounter    Counter,
                igmpModuleSuccessfulJoinReqCounter    Counter,
                igmpModuleUnsuccessfulJoinReqCounter  Counter,
                igmpModuleTotalLeaveReqCounter        Counter,
                igmpModuleTotalInvalidMsgsCounter     Counter,
                igmpModuleNumConnectsCounter          Counter,
                igmpModuleNumDisconnectsCounter       Counter,
                igmpModulePeakConnectsPerSecond       Counter,
                igmpModulePeakConnectsTime            NetworkTimeInSeconds,
                igmpModulePeakDisconnectsPerSecond    Counter,
                igmpModulePeakDisconnectsTime         NetworkTimeInSeconds,
                igmpModulePeakMsgsPerSecond           Counter,
                igmpModulePeakMsgsTime                NetworkTimeInSeconds,
                igmpModuleCurrentNumRootConnections   Counter,
                igmpModuleNumSecOvrldApp              Counter,
                igmpModuleStatsIntvl                  NetworkTimeInSeconds,
                igmpModuleClearAllStats               TruthValue,
                igmpModuleTotalGMQCounter             Counter,
                igmpModuleTotalGSQCounter             Counter,
                igmpModuleCurrentNumRootConCfgd       Gauge,
                igmpModuleCurrentNumRootConUnCfgd     Gauge,
                igmpModuleCurrentNumRootConNoMemb     Gauge,
		igmpModuleTotalGSSQCounter            Counter

        }

igmpModuleSlotIndex OBJECT-TYPE
    SYNTAX INTEGER
    ACCESS not-accessible
    STATUS mandatory
    DESCRIPTION
        "This index identifies an IGMP module by the logical SlotId.
        ALCATEL NOTE:
            ACCESS:      NA            USAGE:       NA
            PERSIST:     YES           INSRVMOD:    NA
            RANGE:       1..19         DEFVALUE:    NA
            UNITS:       NA            SPARSE:      NO
            DESCR:       NA"
    ::={igmpModuleEntry 1}

igmpModuleTotalMsgsCounter OBJECT-TYPE
    SYNTAX Counter
    ACCESS read-only
    STATUS mandatory
    DESCRIPTION
        "This statistic is the total number of messages received from
        users, including IGMP messages and invalid messages.
        ALCATEL NOTE:
            ACCESS:      NA            USAGE:       NA
            PERSIST:     NO            INSRVMOD:    NA
            RANGE:       NA            DEFVALUE:    0
            UNITS:       msgs          SPARSE:      NO
            DESCR:       NA"
    ::={igmpModuleEntry 2}

igmpModuleTotalIGMPMsgsCounter OBJECT-TYPE
    SYNTAX Counter
    ACCESS read-only
    STATUS mandatory
    DESCRIPTION
        "This statistic is the total number of IGMP messages, which
        includes join and leave requests from users, (both successful
        and unsuccessful).
        ALCATEL NOTE:
            ACCESS:      NA            USAGE:       NA
            PERSIST:     NO            INSRVMOD:    NA
            RANGE:       NA            DEFVALUE:    0
            UNITS:       IGMP msgs     SPARSE:      NO
            DESCR:       NA"
    ::={igmpModuleEntry 3}

igmpModuleTotalJoinRequestsCounter OBJECT-TYPE
    SYNTAX Counter
    ACCESS read-only
    STATUS mandatory
    DESCRIPTION
        "This statistic is the total number of join requests from
        users, which includes successful and unsuccessful attempts.
        ALCATEL NOTE:
            ACCESS:      NA            USAGE:       NA
            PERSIST:     NO            INSRVMOD:    NA
            RANGE:       NA            DEFVALUE:    0
            UNITS:       join request  SPARSE:      NO
            DESCR:       NA"
    ::={igmpModuleEntry 4}

igmpModuleSuccessfulJoinReqCounter OBJECT-TYPE
    SYNTAX Counter
    ACCESS read-only
    STATUS mandatory
    DESCRIPTION
        "This statistic is the total number of successful join requests
        from users which includes new joins (which make a new connection)
        and re-joins (which already have a connection).
        ALCATEL NOTE:
            ACCESS:      NA            USAGE:       NA
            PERSIST:     NO            INSRVMOD:    NA
            RANGE:       NA            DEFVALUE:    0
            UNITS:       join request  SPARSE:      NO
            DESCR:       NA"
    ::={igmpModuleEntry 5}

igmpModuleUnsuccessfulJoinReqCounter OBJECT-TYPE
    SYNTAX Counter
    ACCESS read-only
    STATUS mandatory
    DESCRIPTION
        "This statistic is the total number of unsuccessful new join
        requests from users. The failures could be due to the following
        reasons: permission bitmap failure, bitrate failure, lack of
        resource or invalid group address.
        ALCATEL NOTE:
            ACCESS:      NA            USAGE:       NA
            PERSIST:     NO            INSRVMOD:    NA
            RANGE:       NA            DEFVALUE:    0
            UNITS:       join request  SPARSE:      NO
            DESCR:       NA"
    ::={igmpModuleEntry 6}

igmpModuleTotalLeaveReqCounter OBJECT-TYPE
    SYNTAX Counter
    ACCESS read-only
    STATUS mandatory
    DESCRIPTION
        "This statistic is the total number of leave requests from
        users.
        ALCATEL NOTE:
            ACCESS:      NA            USAGE:       NA
            PERSIST:     NO            INSRVMOD:    NA
            RANGE:       NA            DEFVALUE:    0
            UNITS:       leave request SPARSE:      NO
            DESCR:       NA"
    ::={igmpModuleEntry 7}

igmpModuleTotalInvalidMsgsCounter OBJECT-TYPE
    SYNTAX Counter
    ACCESS read-only
    STATUS mandatory
    DESCRIPTION
        "This statistic is the total number of invalid messages from
        users. These messages could be invalid for the following reasons:
        invalid IGMP message type, invalid IGMP message CRC, invalid IGMP
        message size, non-IGMP frame received, unexpected IGMP Query (GSQ
        or GMQ) received, RFC 1483 errors, MAC layer errors, or IP layer
        errors.
        ALCATEL NOTE:
            ACCESS:      NA            USAGE:       NA
            PERSIST:     NO            INSRVMOD:    NA
            RANGE:       NA            DEFVALUE:    0
            UNITS:       invalid msgs  SPARSE:      NO
            DESCR:       NA"
    ::={igmpModuleEntry 8}

igmpModuleNumConnectsCounter OBJECT-TYPE
    SYNTAX Counter
    ACCESS read-only
    STATUS mandatory
    DESCRIPTION
        "This statistic is the total number of connects due to successful
        new IGMP join requests from users.
        ALCATEL NOTE:
            ACCESS:      NA            USAGE:       NA
            PERSIST:     NO            INSRVMOD:    NA
            RANGE:       NA            DEFVALUE:    0
            UNITS:       connects      SPARSE:      NO
            DESCR:       NA"
    ::={igmpModuleEntry 9}

igmpModuleNumDisconnectsCounter OBJECT-TYPE
    SYNTAX Counter
    ACCESS read-only
    STATUS mandatory
    DESCRIPTION
        "This statistic is the total number of disconnects to users.
        They can be due to GSQ or GMQ timer expiry or the triggering
        of fast channel changes.
        ALCATEL NOTE:
            ACCESS:      NA            USAGE:       NA
            PERSIST:     NO            INSRVMOD:    NA
            RANGE:       NA            DEFVALUE:    0
            UNITS:       disconnects   SPARSE:      NO
            DESCR:       NA"
    ::={igmpModuleEntry 10}

igmpModulePeakConnectsPerSecond OBJECT-TYPE
    SYNTAX Counter
    ACCESS read-only
    STATUS mandatory
    DESCRIPTION
        "This statistic is the peak number of multicast branch
        connections performed per second since the statistics were last
        cleared. This object is defined based on successful JOIN from users.
        ALCATEL NOTE:
            ACCESS:      NA            USAGE:       NA
            PERSIST:     NO            INSRVMOD:    NA
            RANGE:       NA            DEFVALUE:    0
            UNITS:       NA            SPARSE:      NO
            DESCR:       NA"
    ::={igmpModuleEntry 11}

igmpModulePeakConnectsTime OBJECT-TYPE
    SYNTAX NetworkTimeInSeconds
    ACCESS read-only
    STATUS mandatory
    DESCRIPTION
        "This statistic is the network time in seconds indicating when the
        peak number of connects performed per second occurred. This object
        is defined based on successful JOIN from users.
        ALCATEL NOTE:
            ACCESS:      NA            USAGE:       NA
            PERSIST:     NO            INSRVMOD:    NA
            RANGE:       NA            DEFVALUE:    0
            UNITS:       secs          SPARSE:      NO
            DESCR:       NA"
    ::={igmpModuleEntry 12}

igmpModulePeakDisconnectsPerSecond OBJECT-TYPE
    SYNTAX Counter
    ACCESS read-only
    STATUS mandatory
    DESCRIPTION
        "This statistic is the peak number of disconnects to users
        performed per second.
        ALCATEL NOTE:
            ACCESS:      NA            USAGE:       NA
            PERSIST:     NO            INSRVMOD:    NA
            RANGE:       NA            DEFVALUE:    0
            UNITS:       NA            SPARSE:      NO
            DESCR:       NA"
    ::={igmpModuleEntry 13}

igmpModulePeakDisconnectsTime OBJECT-TYPE
    SYNTAX NetworkTimeInSeconds
    ACCESS read-only
    STATUS mandatory
    DESCRIPTION
        "This statistic indicates the network time in seconds of when the
        peak number of disconnects to users performed per second occurred.
        ALCATEL NOTE:
            ACCESS:      NA            USAGE:       NA
            PERSIST:     NO            INSRVMOD:    NA
            RANGE:       NA            DEFVALUE:    0
            UNITS:       secs          SPARSE:      NO
            DESCR:       NA"
    ::={igmpModuleEntry 14}

igmpModulePeakMsgsPerSecond OBJECT-TYPE
    SYNTAX Counter
    ACCESS read-only
    STATUS mandatory
    DESCRIPTION
        "This statistic is the peak number of messages received from
        users per second.
        ALCATEL NOTE:
            ACCESS:      NA            USAGE:       NA
            PERSIST:     NO            INSRVMOD:    NA
            RANGE:       NA            DEFVALUE:    0
            UNITS:       NA            SPARSE:      NO
            DESCR:       NA"
    ::={igmpModuleEntry 15}

igmpModulePeakMsgsTime OBJECT-TYPE
    SYNTAX NetworkTimeInSeconds
    ACCESS read-only
    STATUS mandatory
    DESCRIPTION
        "This statistic indicates the network time in seconds of when the
        peak number of messages received from users per second
        occurred.
        ALCATEL NOTE:
            ACCESS:      NA            USAGE:       NA
            PERSIST:     NO            INSRVMOD:    NA
            RANGE:       NA            DEFVALUE:    0
            UNITS:       secs          SPARSE:      NO
            DESCR:       NA"
    ::={igmpModuleEntry 16}

igmpModuleCurrentNumRootConnections OBJECT-TYPE
    SYNTAX Counter
    ACCESS read-only
    STATUS mandatory
    DESCRIPTION
        "This statistic indicates the number of the connected groups.
        ALCATEL NOTE:
            ACCESS:      NA            USAGE:       NA
            PERSIST:     NO            INSRVMOD:    NA
            RANGE:       NA            DEFVALUE:    0
            UNITS:       groups        SPARSE:      NO
            DESCR:       NA"
    ::={igmpModuleEntry 17}

igmpModuleNumSecOvrldApp OBJECT-TYPE
    SYNTAX Counter
    ACCESS read-only
    STATUS mandatory
    DESCRIPTION
        "This statistic indicates the number of seconds during which
        module overload protection has been applied affecting all IGMP
        channels which are terminated at the IGMP module.
        ALCATEL NOTE:
            ACCESS:      NA            USAGE:       NA
            PERSIST:     NO            INSRVMOD:    NA
            RANGE:       NA            DEFVALUE:    0
            UNITS:       secs          SPARSE:      NO
            DESCR:       NA"
    ::={igmpModuleEntry 18}

igmpModuleStatsIntvl OBJECT-TYPE
    SYNTAX NetworkTimeInSeconds
    ACCESS read-only
    STATUS mandatory
    DESCRIPTION
        "This statistics indicates the network time in seconds
        of when the module-wide statistics were last reset.
        ALCATEL NOTE:
            ACCESS:      NA            USAGE:       NA
            PERSIST:     NO            INSRVMOD:    NA
            RANGE:       NA            DEFVALUE:    0
            UNITS:       secs          SPARSE:      NO
            DESCR:       NA"
    ::={igmpModuleEntry 19}

igmpModuleClearAllStats OBJECT-TYPE
    SYNTAX TruthValue
    ACCESS read-write
    STATUS mandatory
    DESCRIPTION
        "When this object is set to true, all statistics within this MIB
        shall be reset to 0 within the scope of the IGMP module.
        When this object is set to false, the request is ignored.
        ALCATEL NOTE:
            ACCESS:      NA            USAGE:       NA
            PERSIST:     NO            INSRVMOD:    YES
            RANGE:       NA            DEFVALUE:    NA
            UNITS:       NA            SPARSE:      NO
            DESCR:       NA"
    DEFVAL { false }
    ::={igmpModuleEntry 20}

igmpModuleTotalGMQCounter OBJECT-TYPE
    SYNTAX Counter
    ACCESS read-only
    STATUS mandatory
    DESCRIPTION
        "This statistic is the total number of GMQ requests from
        network.
        ALCATEL NOTE:
            ACCESS:      NA            USAGE:       NA
            PERSIST:     NO            INSRVMOD:    NA
            RANGE:       NA            DEFVALUE:    0
            UNITS:       GMQ requests  SPARSE:      NO
            DESCR:       NA"
    ::={igmpModuleEntry 21}

igmpModuleTotalGSQCounter OBJECT-TYPE
    SYNTAX Counter
    ACCESS read-only
    STATUS mandatory
    DESCRIPTION
        "This statistic is the total number of GSQ requests from
        network.
        ALCATEL NOTE:
            ACCESS:      NA            USAGE:       NA
            PERSIST:     NO            INSRVMOD:    NA
            RANGE:       NA            DEFVALUE:    0
            UNITS:       GSQ requests  SPARSE:      NO
            DESCR:       NA"
    ::={igmpModuleEntry 22}

igmpModuleCurrentNumRootConCfgd OBJECT-TYPE
    SYNTAX Gauge
    ACCESS read-only
    STATUS mandatory
    DESCRIPTION
        "This statistic indicates the number of the connected groups who are
        configured in the Multicast Source Table.
        ALCATEL NOTE:
            ACCESS:      NA            USAGE:       NA
            PERSIST:     NO            INSRVMOD:    NA
            RANGE:       NA            DEFVALUE:    0
            UNITS:       groups        SPARSE:      NO
            DESCR:       NA"
    ::={igmpModuleEntry 23}

igmpModuleCurrentNumRootConUnCfgd OBJECT-TYPE
    SYNTAX Gauge
    ACCESS read-only
    STATUS mandatory
    DESCRIPTION
        "This statistic indicates the number of the connected groups who aren't
        configured in the Multicast Source Table.
        ALCATEL NOTE:
            ACCESS:      NA            USAGE:       NA
            PERSIST:     NO            INSRVMOD:    NA
            RANGE:       NA            DEFVALUE:    0
            UNITS:       groups        SPARSE:      NO
            DESCR:       NA"
    ::={igmpModuleEntry 24}

igmpModuleCurrentNumRootConNoMemb OBJECT-TYPE
    SYNTAX Gauge
    ACCESS read-only
    STATUS mandatory
    DESCRIPTION
        "This statistic indicates the number of the connected groups who are
        in reserve state, which means that they have no member, but
        don't leave in order to avoid frequently joining and leaving.
        ALCATEL NOTE:
            ACCESS:      NA            USAGE:       NA
            PERSIST:     NO            INSRVMOD:    NA
            RANGE:       NA            DEFVALUE:    0
            UNITS:       groups        SPARSE:      NO
            DESCR:       NA"
    ::={igmpModuleEntry 25}

igmpModuleTotalGSSQCounter OBJECT-TYPE
    SYNTAX Counter
    ACCESS read-only
    STATUS mandatory
    DESCRIPTION
        "This statistic is the total number of GSSQ requests from
        network.
        ALCATEL NOTE:
            ACCESS:      NA            USAGE:       NA
            PERSIST:     NO            INSRVMOD:    NA
            RANGE:       NA            DEFVALUE:    0
            UNITS:       GSQ requests  SPARSE:      NO
            DESCR:       NA"
    ::={igmpModuleEntry 26}

-- ===============================================================================
--  IGMP Module Multicast Source Expansion Table.
-- ===============================================================================
--
--igmpModuleMcastSrcExpTable OBJECT-TYPE
--    SYNTAX SEQUENCE OF IgmpModuleMcastSrcEntry
--    ACCESS not-accessible
--    STATUS mandatory
--    DESCRIPTION
--        "This table contains multicast source statistics maintained by
--        IGMP proxy, it is only for those groups configured in Multicast
--        Source Table.
--        ALCATEL NOTE:
--            TABLESIZE: 4096 * nmbr of slots
--            DESCR: NA"
--    ::= {igmpMIB 6}
--
--igmpModuleMcastSrcEntry OBJECT-TYPE
--    SYNTAX IgmpModuleMcastSrcEntry
--    ACCESS not-accessible
--    STATUS mandatory
--    DESCRIPTION
--        "Each entry reflects the multicast source statistics collected
--        by the on-board controller on LT, it is only for those groups
--        configured in Multicast Source Table.
--        Row creation : An entry is created by system per slot when
--                 corresponding entry in multicastSourceTable is created.
--        Row deletion :
--        Index usage : the index is the .
--        Note that entries will be presented to the SNMP manager in full
--        lexicographical order."
--    INDEX { igmpModuleSlotIndex, multicastSrcClassDAddr }
--    ::= { igmpModuleMcastSrcExpTable 1}
--
--IgmpModuleMcastSrcEntry ::=
--    SEQUENCE {
--        igmpModuleMcastSrcPeakSubscrIGMPChans     Counter,
--        igmpModuleMcastSrcPeakTime                NetworkTimeInSeconds,
--        igmpModuleMcastSrcCurrentSubscrIGMPChans  Counter,
--        igmpModuleMcastSrcClearStats              TruthValue,
--        igmpModuleMcastSrcConnectFailCounter      Counter,
--        igmpModuleMcastSrcUserSuccJoinReqCounter  Counter
--    }
--
--igmpModuleMcastSrcPeakSubscrIGMPChans OBJECT-TYPE
--    SYNTAX Counter
--    ACCESS read-only
--    STATUS mandatory
--    DESCRIPTION
--        "This is a statistic indicating the peak number of subscribed
--        IGMP channels which have members connected to the source since
--        the last statistics reset. It is only for those groups
--        configured in the Multicast Source Table.
--        ALCATEL NOTE:
--            ACCESS:      NA            USAGE:       NA
--            PERSIST:     NO            INSRVMOD:    NA
--            RANGE:       NA            DEFVALUE:    0
--            UNITS:       IGMP channels SPARSE:      NO
--            DESCR:       NA"
--    ::={ igmpModuleMcastSrcEntry 1}
--
--igmpModuleMcastSrcPeakTime OBJECT-TYPE
--    SYNTAX NetworkTimeInSeconds
--    ACCESS read-only
--    STATUS mandatory
--    DESCRIPTION
--        "This statistic indicates the network time in seconds of when the
--        peak number of subscribed IGMP channels for the source occurred.
--        It is only for those groups configured in Multicast Source Table.
--        ALCATEL NOTE:
--            ACCESS:      NA            USAGE:       NA
--            PERSIST:     NO            INSRVMOD:    NA
--            RANGE:       NA            DEFVALUE:    0
--            UNITS:       secs          SPARSE:      NO
--            DESCR:       NA"
--    ::={ igmpModuleMcastSrcEntry 2}
--
--igmpModuleMcastSrcCurrentSubscrIGMPChans OBJECT-TYPE
--    SYNTAX Counter
--    ACCESS read-only
--    STATUS mandatory
--    DESCRIPTION
--        "This is a statistic indicating the current number of subscribed
--        IGMP channels for the source. It is only for those groups
--        configured in Multicast Source Table.
--        ALCATEL NOTE:
--            ACCESS:      NA            USAGE:       NA
--            PERSIST:     NO            INSRVMOD:    NA
--            RANGE:       NA            DEFVALUE:    0
--            UNITS:       IGMP channels SPARSE:      NO
--            DESCR:       NA"
--    ::={ igmpModuleMcastSrcEntry 3}
--
--igmpModuleMcastSrcClearStats OBJECT-TYPE
--    SYNTAX TruthValue
--    ACCESS read-write
--    STATUS mandatory
--    DESCRIPTION
--        "When set to true, all statistics in this table entry will be
--        cleared. When set to false, the request is ignored.
--        ALCATEL NOTE:
--            ACCESS:      NA            USAGE:       NA
--            PERSIST:     NO            INSRVMOD:    YES
--            RANGE:       NA            DEFVALUE:    NA
--            UNITS:       NA            SPARSE:      NO
--            DESCR:       NA"
--    DEFVAL {false}
--    ::={ igmpModuleMcastSrcEntry 4}
--
--igmpModuleMcastSrcConnectFailCounter OBJECT-TYPE
--    SYNTAX Counter
--    ACCESS read-only
--    STATUS mandatory
--    DESCRIPTION
--        "This object indicates the number of times that an attempt to
--        create a multicast connection fails. It is only for those groups
--        configured in Multicast Source Table.
--        ALCATEL NOTE:
--            ACCESS:      NA            USAGE:       NA
--            PERSIST:     NO            INSRVMOD:    NA
--            RANGE:       NA            DEFVALUE:    0
--            UNITS:       NA            SPARSE:      NO
--            DESCR:       NA"
--    ::={ igmpModuleMcastSrcEntry 5}
--
--igmpModuleMcastSrcUserSuccJoinReqCounter  OBJECT-TYPE
--    SYNTAX Counter
--    ACCESS read-only
--    STATUS mandatory
--    DESCRIPTION
--        "This object indicates the number of succesful joins by a user
--        for this configured group.
--        ALCATEL NOTE:
--            ACCESS:      NA            USAGE:       NA
--            PERSIST:     NO            INSRVMOD:    NA
--            RANGE:       NA            DEFVALUE:    0
--            UNITS:       NA            SPARSE:      NO
--            DESCR:       NA"
--    ::={ igmpModuleMcastSrcEntry 6}
--
--
-- ===============================================================================
--  IGMP System Objects. Note that this is not a table; it's a collection
--  of scalar objects.
-- ===============================================================================

igmpSystemQueryInterval OBJECT-TYPE
    SYNTAX INTEGER (2..3175)
    ACCESS read-write
    STATUS mandatory
    DESCRIPTION
        "The interval at which IGMP general membership queries (GMQs)
        are transmitted (per interface). This value is measured in
        units of seconds. This object is applied to each IGMP
        channel.
        ALCATEL NOTE:
            ACCESS:      NA            USAGE:       NA
            PERSIST:     YES           INSRVMOD:    YES
            RANGE:       NA            DEFVALUE:    125
            UNITS:       secs          SPARSE:      NA
            DESCR:       NA"
    ::={igmpMIB 7}

igmpSystemQueryMaxResponseTime OBJECT-TYPE
    SYNTAX INTEGER (1..31744)
    ACCESS read-write
    STATUS mandatory
    DESCRIPTION
        "The maximum query response time advertised in IGMPv2 queries
      	 and IGMPv3 queries on the interface. This value is measured in
		 units of tenths of seconds. This object is applied to each
		 IGMP channel.
		 The object is shared between IGMPv2 and IGMPv3 but has a
		 different unit.
		 IGMPv2:
             Object value <=255 sec :the time value is equal
             to the object value (units in 100ms)
			 Object value > 255 sec :the time value is 255 sec (units in 100ms)

  		 IGMPv3 :
             Object value <= 128 sec : the timevalue is equal
		     to the object value (units in 100ms)
             Object value > 128 : the timevalue  is equal to the object value
             with a granularity of 8 for the values 128 till 256 increasing
             gradually (2exp) to a object value with a granularity of 1024 for
             the last values (first initially increasing for
             the values 26624 till 31744 .
 	         Default value = 100  or 10sec
        ALCATEL NOTE:
            ACCESS:      NA            USAGE:       NA
            PERSIST:     YES           INSRVMOD:    YES
            RANGE:       NA            DEFVALUE:    100
            UNITS:       100ms         SPARSE:      NA
            DESCR:       NA"
    ::={igmpMIB 8}

igmpSystemRobustness OBJECT-TYPE
    SYNTAX INTEGER (1..10)
    ACCESS read-write
    STATUS mandatory
    DESCRIPTION
        "The Robustness Variable allows tuning for the expected packet
        loss on a subnet. If a subnet is expected to be lossy, the
        Robustness Variable may be increased. IGMP is robust to
        (Robustness Variable-1) packet losses.
        This object is applied to each IGMP channel.
        ALCATEL NOTE:
            ACCESS:      NA            USAGE:       NA
            PERSIST:     YES           INSRVMOD:    YES
            RANGE:       NA            DEFVALUE:    2
            UNITS:       NA            SPARSE:      NA
            DESCR:       NA"
    ::={igmpMIB 9}

igmpSystemLastMembQueryIntvl OBJECT-TYPE
    SYNTAX INTEGER (2..31744)
    ACCESS read-write
    STATUS mandatory
    DESCRIPTION
        "This entry is the spacing between GSQs (group-specific
        queries.) This value is measured in units of tenths of seconds.
        This object is applied to each IGMP channel.
        ALCATEL NOTE:
            ACCESS:      NA            USAGE:       NA
            PERSIST:     YES           INSRVMOD:    YES
            RANGE:       NA            DEFVALUE:    10
            UNITS:       1/10 of secs  SPARSE:      NA
            DESCR:       NA"
    ::={igmpMIB 10}

igmpSystemStartupQueryIntvl OBJECT-TYPE
    SYNTAX INTEGER (1..3175)
    ACCESS read-only
    STATUS mandatory
    DESCRIPTION
        "The interval between general membership queries sent by a querier
        on startup. This value is measured in units of seconds.
        This object is applied to each IGMP channel.
        ALCATEL NOTE:
            ACCESS:      NA            USAGE:       NA
            PERSIST:     NO            INSRVMOD:    NA
            RANGE:       NA            DEFVALUE:    10
            UNITS:       secs          SPARSE:      NA
            DESCR:       NA"
    ::={igmpMIB 11}

igmpSystemStartupQueryCount OBJECT-TYPE
    SYNTAX INTEGER (1..10)
    ACCESS read-only
    STATUS mandatory
    DESCRIPTION
        "The number of queries sent out on startup separated by the
        query interval. This object is applied to each IGMP channel.
        ALCATEL NOTE:
            ACCESS:      NA            USAGE:       NA
            PERSIST:     NO            INSRVMOD:    NA
            RANGE:       NA            DEFVALUE:    2
            UNITS:       NA            SPARSE:      NA
            DESCR:       NA"
    ::={igmpMIB 12}

igmpSystemLastMembQueryCount OBJECT-TYPE
    SYNTAX INTEGER (1..10)
    ACCESS read-write
    STATUS mandatory
    DESCRIPTION
        "The number of unanswered group specific queries sent out
        before it is assumed that there are no local members
        interested in the IP multicast stream. This object is
        applied to each IGMP channel.
        ALCATEL NOTE:
            ACCESS:      NA            USAGE:       NA
            PERSIST:     YES           INSRVMOD:    YES
            RANGE:       NA            DEFVALUE:    2
            UNITS:       queries       SPARSE:      NA
            DESCR:       NA"
    ::={igmpMIB 13}

igmpSystemLastMembMaxResponseTime OBJECT-TYPE
    SYNTAX INTEGER (1..31744)
    ACCESS read-write
    STATUS mandatory
    DESCRIPTION
        "Allows shorter maximum response times. Allows fast channel
        change to occur by configuring the response time inserted into
        a leave. This value is measured in units of tenths of seconds.
        This object is applied to each IGMP channel.
        The object is shared between IGMPv2 and IGMPv3 but has a
        different unit.
        IGMPv2 :
            Object value <=255 sec :the time value is equal to the object value
            (units in 100ms)
		    Object value > 255 :the time value is 255 (units in 100ms)
        IGMPv3 :
            Object value <= 128 sec : the timevalue is equal to the object value
            (units in 100ms)
            Object value > 128 : the timevalue  is equal to the object value
            with a granularity of 8 for the values 128 till 256 increasing
            gradually (2exp) to a object value with a granularity of 1024 for
            the last values (first initially increasing for the values
            26624 till 31744 .
        ALCATEL NOTE:
            ACCESS:      NA            USAGE:       NA
            PERSIST:     YES           INSRVMOD:    YES
            RANGE:       NA            DEFVALUE:    2
            UNITS:       1/10 secs     SPARSE:      NA
            DESCR:       NA"
    ::={igmpMIB 14}

igmpSystemVerifyChecksum OBJECT-TYPE
    SYNTAX TruthValue
    ACCESS read-write
    STATUS mandatory
    DESCRIPTION
        "Indicates whether IGMP checksum verification is performed
        or not on the received IGMP frame. When the value is true,
        packet processing is IGMP v2 or v3 standard compliant.
		When the value is false, the checksum is not done; this may
		result in performance improvements due to the reduced
		processing required.
        This object is applied to each IGMP channel.
        ALCATEL NOTE:
            ACCESS:      NA            USAGE:       NA
            PERSIST:     YES           INSRVMOD:    YES
            RANGE:       NA            DEFVALUE:    false
            UNITS:       NA            SPARSE:      NA
            DESCR:       NA"
    ::={igmpMIB 15}

igmpSystemStatsIntvl OBJECT-TYPE
    SYNTAX NetworkTimeInSeconds
    ACCESS read-only
    STATUS mandatory
    DESCRIPTION
        "This statistics indicates the network time in seconds
        of when the system-wide statistics were last reset.
        ALCATEL NOTE:
            ACCESS:      NA            USAGE:       NA
            PERSIST:     NO            INSRVMOD:    NA
            RANGE:       NA            DEFVALUE:    0
            UNITS:       secs          SPARSE:      NA
            DESCR:       NA"
--  DEFVAL { 0 }
    ::={igmpMIB 16}

igmpSystemClearAllStats OBJECT-TYPE
    SYNTAX TruthValue
    ACCESS read-write
    STATUS mandatory
    DESCRIPTION
        "When this object is set to true, all statistics within this MIB
        shall be reset to 0 for all IGMP modules.
        When set to false, the request is ignored.
        ALCATEL NOTE:
            ACCESS:      NA            USAGE:       NA
            PERSIST:     NO            INSRVMOD:    YES
            RANGE:       NA            DEFVALUE:    false
            UNITS:       NA            SPARSE:      NA
            DESCR:       NA"
    DEFVAL { false }
    ::={igmpMIB 17}

igmpSystemSrcIPAddr OBJECT-TYPE
    SYNTAX IpAddress
    ACCESS read-write
    STATUS mandatory
    DESCRIPTION
        "This object specifies the source IP address which is contained in
        every multicast IP datagrams transmitted on all IGMP
        control channels.
        The IP address is in network-byte order (big-endian).
        Note :Default IP-address 0.0.0.0
        ALCATEL NOTE:
            ACCESS:      NA            USAGE:       NA
            PERSIST:     YES           INSRVMOD:    YES
            RANGE:       NA            DEFVALUE:    0.0.0.0
            UNITS:       NA            SPARSE:      NA
            DESCR:       NA"
	::={ igmpMIB 18}

-- igmpSystemSrcMACAddr OBJECT-TYPE
--      ::={ igmpMIB 19}

igmpSystemUnsolicitedReportIntvl OBJECT-TYPE
    SYNTAX INTEGER (1..255)
    ACCESS read-write
    STATUS mandatory
    DESCRIPTION
        "The interval between repetitions of a host's initial report of
        membership in a group. This value is measured in units of seconds.
        This object is applied to each IGMP channel.
        ALCATEL NOTE:
            ACCESS:      NA            USAGE:       NA
            PERSIST:     YES           INSRVMOD:    YES
            RANGE:       NA            DEFVALUE:    10
            UNITS:       secs          SPARSE:      NA
            DESCR:       NA"
    ::={igmpMIB 21}


igmpSystemChangeOperStatus OBJECT-TYPE
    SYNTAX TruthValue
    ACCESS read-write
    STATUS mandatory
    DESCRIPTION
        "Use this object to start/stop the IGMP&Multicast Application Module
            1) true:  enable  IGMP proxy behaviour
            2) false: disable IGMP proxy behaviour
        Some objects in generalMulticastParameters and
        multicastCapacityParameters can  be modified when
        IgmpSystemChangeOperStatus = false.
        ALCATEL NOTE:
            ACCESS:      NA            USAGE:       NA
            PERSIST:     YES           INSRVMOD:    NO
            RANGE:       NA            DEFVALUE:    false
            UNITS:       secs          SPARSE:      NA
            DESCR:       NA"
    ::={ igmpMIB 22 }

-- ===============================================================================
--  Multicast Static Leaf Table.
--  This table isn't used in ISAM.
-- ===============================================================================


-- ===============================================================================
--  General Group Multicast Parameters
-- ===============================================================================

generalMulticastParamters OBJECT IDENTIFIER ::= { igmpMIB 23 }

-- This objects group contains management information for multicast
-- sources not configured in Multicast Channel Table, such as package
-- Membership Bitmap, estimated traffic parameters, etc. for
-- each multicast source not configured in Multicast Channel Table."


generalMulticastFastChanChange OBJECT-TYPE
    SYNTAX TruthValue
    ACCESS read-write
    STATUS mandatory
    DESCRIPTION
        "This object allows to configure whether fast leave with source
		address tracking or standard leave applies upon the receipt of
		a leave message for configured multicast streams.
		When set to true, the Fast leave with Source Address tracking
		applies.
        ALCATEL NOTE:
            ACCESS:      NA            USAGE:       NA
            PERSIST:     YES           INSRVMOD:    YES
            RANGE:       NA            DEFVALUE:    false
            UNITS:       NA            SPARSE:      NA
            DESCR:       NA"
    ::={ generalMulticastParamters 1 }

generalMulticastPkgMembBitmap OBJECT-TYPE
    SYNTAX OCTET STRING (SIZE(128))
    ACCESS read-write
    STATUS mandatory
    DESCRIPTION
        "This object indicates to which package(s) a class D address
        belongs. A package is a group of sources. Each bit represents
        a package. Thus, bit 1 corresponds to package 1, bit 2 corresponds
        to package 2, and so on in the igmpPackageTable. It is for all
        groups not configured in Multicast Channel Table.

        In accordance with the ASAM MIB convention, the bitmap shall
        function as follows:
        MSB                                     LSB
        byte 0 :  8  7  6  5  4  3  2  1
        byte 1 : 16 15 14 13 12 11 10  9
        byte 2 : 24 23 22 21 20 19 18 17
        byte 3 : 32 31 30 29 28 27 26 25
        byte 4 : 40 39 38 37 36 35 34 33
        byte 5 : 48 47 46 45 44 43 42 41
        byte 6 : 56 55 54 53 52 51 50 49
        byte 7 : 64 63 62 61 60 59 58 57
        ... ... ... ... ... ... ... ...

        byte 127 1024 1023 1022 1021 1020 1019 1018 1017
        Following the convention, byte 0 shall be the first byte (the
        left-most, most significant byte).
        ALCATEL NOTE:
            ACCESS:      NA            USAGE:       NA
            PERSIST:     YES           INSRVMOD:    YES
            RANGE:       NA            DEFVALUE:    NA
            UNITS:       NA            SPARSE:      NA
            DESCR:       NA"
    DEFVAL {'FFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFF'H }
    ::= { generalMulticastParamters 2 }

generalMulticastMaxBitRate OBJECT-TYPE
    SYNTAX INTEGER (0..100000)
    ACCESS read-write
    STATUS deprecated
    DESCRIPTION
        "The Maximum Bit Rate is a reasonable maximum in ATM level
        for the traffic of multicast sources not configured in
        Multicast Channel Table in the transmit(downstream) direction.
        This value is measured in units of 1000 bits per second (kbps).
        ALCATEL NOTE:
            ACCESS:      NA            USAGE:       NA
            PERSIST:     YES           INSRVMOD:    YES
            RANGE:       NA            DEFVALUE:    2500
            UNITS:       kbps          SPARSE:      NA
            DESCR:       Although configurable, this object is not considered
                         by the IGMP subsystem in iSAM"
    ::= { generalMulticastParamters 3 }

generalMulticastMeanBitRate OBJECT-TYPE
    SYNTAX INTEGER (0..100000)
    ACCESS read-write
    STATUS deprecated
    DESCRIPTION
        "The Mean Bit Rate is a reasonable mean value in ATM level
        for the traffic of multicast sources not configured in
        Multicast Channel Table in the transmit(downstream) direction.
        This value is measured in units of 1000 bits per second (kbps).
        The default value is dependent on the generalMulticastMaxBitRate
        object as follows:
        Mean Bitrate = 100% of the Maximum Bitrate
        Note : Although configurable, this object is not considered by
		the IGMP subsystem in iSAM
        ALCATEL NOTE:
            ACCESS:      NA            USAGE:       NA
            PERSIST:     YES           INSRVMOD:    YES
            RANGE:       NA            DEFVALUE:    2500
            UNITS:       kbps          SPARSE:      NA
            DESCR:       Although configurable, this object is not considered
                         by the IGMP subsystem in iSAM"
    ::= { generalMulticastParamters 4 }


-- ===============================================================================
--  Multicast Capacity Parameters
-- ===============================================================================
multicastCapacityParamters OBJECT IDENTIFIER ::= { igmpMIB 24 }

-- This objects group contains management information for multicast
-- capacity, such as Multiplex Efficience of Ethernet,
-- Percent of Bandwidth for multicast, Maximum of groups,
-- Stream Reserve Time etc.

-- multicastCapacityMultEfficiency OBJECT-TYPE
--      ::={ multicastCapacityParamters 1 }

-- multicastCapacityPercentIWFBW OBJECT-TYPE
--      ::={ multicastCapacityParamters 2 }

-- multicastCapacityPercentSingleBW OBJECT-TYPE
--      ::={ multicastCapacityParamters 3 }

-- multicastCapacityPercentSysBW OBJECT-TYPE
--      ::={ multicastCapacityParamters 4 }

multicastCapacityMaxNumGroup OBJECT-TYPE
    SYNTAX INTEGER (0..2048)
    ACCESS read-write
    STATUS mandatory
    DESCRIPTION
        " This object allows to configure the maximum number of multicast
	    streams that can be simultaneously active on the L2/L3  LT board. 
	    For the L2 board there the HW restriction of max 72 simultaneously
	    active multicast streams. 
	    As such, when this object is set to a a value > 72 then for 
        L2 boards, the value 72 is considered.
        It shall be noted that the value of this object includes both,
        pre-configured and non-configured multicast streams.
        ALCATEL NOTE:
            ACCESS:      NA            USAGE:       NA
            PERSIST:     YES           INSRVMOD:    YES
            RANGE:       NA            DEFVALUE:    1024
            UNITS:       stream        SPARSE:      NA
            DESCR:       NA"
    ::={ multicastCapacityParamters 5 }

multicastCapacityMaxNumUnCfg OBJECT-TYPE
    SYNTAX INTEGER (0..1024)
    ACCESS read-write
    STATUS mandatory
    DESCRIPTION
        "This object allows to configure the maximum number of non-configured
        multicast streams that can be simultaneously active on the L2/L3 LT
        board. When igmpSystemUncfgMcastSupport is configured to allow unconfigured SSM,
	then this object refers to the sum of unconfigured ssm and unconfigured asm channels.

        ALCATEL NOTE:
            ACCESS:      NA            USAGE:       NA
            PERSIST:     YES           INSRVMOD:    YES
            RANGE:       NA            DEFVALUE:    64
            UNITS:       stream        SPARSE:      NA
            DESCR:       NA"
    ::={ multicastCapacityParamters 6 }

multicastCapacityCfgSourceReserveTime OBJECT-TYPE
    SYNTAX INTEGER (0..2147483647)
    ACCESS read-write
    STATUS mandatory
    DESCRIPTION
        "This object allows to configure the period (in seconds) that a
	    pre-configured multicast stream must still be kept active on the
	    L2/L3 LT board after the last end-user has disconnected.
        ALCATEL NOTE:
            ACCESS:      NA            USAGE:       NA
            PERSIST:     YES           INSRVMOD:    YES
            RANGE:       NA            DEFVALUE:    125
            UNITS:       secs          SPARSE:      NA
            DESCR:       NA"
    ::={ multicastCapacityParamters 7 }

multicastCapacityUnCfgSourceReserveTime OBJECT-TYPE
    SYNTAX INTEGER (0..2147483647)
    ACCESS read-write
    STATUS mandatory
    DESCRIPTION
        "This object allows to configure the period (in seconds) that a
	    non-configured multicast stream must still be kept active on
	    the L2/L3 LT board after the last end-user has disconnected.
        ALCATEL NOTE:
            ACCESS:      NA            USAGE:       NA
            PERSIST:     YES           INSRVMOD:    YES
            RANGE:       NA            DEFVALUE:    0
            UNITS:       secs          SPARSE:      NA
            DESCR:       NA"
    ::={ multicastCapacityParamters 8 }


-- ===============================================================================
--  Multicast Cascade Port Table
--  This table isn't used in ISAM.
-- ===============================================================================

igmpSystemV1RouterPresentTimeout OBJECT-TYPE
    SYNTAX INTEGER
    ACCESS read-only
    STATUS mandatory
    DESCRIPTION
        "When the system acts as host on the network side of
        the IGMP proxy, this value is the time how long the
        system shall wait after hearing a Version 1 Query
        before it shall send any IGMPv2 messages.  This value
        is measured in units of seconds.
        ALCATEL NOTE:
            ACCESS:      NA            USAGE:       NA
            PERSIST:     NA            INSRVMOD:    NA
            RANGE:       NA            DEFVALUE:    NA
            UNITS:       NA            SPARSE:      NA
            DESCR:       This object is not supported in iSAM"
    ::={igmpMIB 27}

igmpSystemGroupMembershipInterval OBJECT-TYPE
    SYNTAX INTEGER
    ACCESS read-only
    STATUS mandatory
    DESCRIPTION
        "The interval that must pass before the system decides
        there are no more members of a group on a network.
        This value is measured in units of seconds and it is
        equal to ((the Robustness Variable) times (the Query
        Interval)) plus (one Query Response Interval).
        ALCATEL NOTE:
            ACCESS:      NA            USAGE:       NA
            PERSIST:     NA            INSRVMOD:    NA
            RANGE:       DEP           DEFVALUE:    DEP
            UNITS:       secs          SPARSE:      NA
            DESCR:       NA"
    ::={igmpMIB 33}

igmpPreviewRecognitionTime  OBJECT-TYPE
    SYNTAX INTEGER
    ACCESS read-write
    STATUS mandatory
    DESCRIPTION
        "This object allows to configure the time period to validate a
		 preview session for an increment of the current preview
		 counter meaning that when the end-user watches the preview 
		 session of a multicast stream for a time period shorter than
		 the time period configured in this object, that then neither 
		 the igmpChannelCurrentPreviewNumber object nor the 
		 multicastUserItf2MCGroupCurrentPreviewNumber object will be 
		 updated. 
        ALCATEL NOTE:
            ACCESS:      NA            USAGE:       NA
            PERSIST:     YES           INSRVMOD:    NO
            RANGE:       1..120        DEFVALUE:    8
            UNITS:       NA            SPARSE:      NA
            DESCR:       NA"
    ::= { igmpMIB 41}

igmpPreviewCDRGenRecognitionTime  OBJECT-TYPE
    SYNTAX INTEGER
    ACCESS read-write
    STATUS mandatory
    DESCRIPTION
        "This object allows to configure the time period to validate a preview
        session for CDR generation meaning that when the end-user watches the
        preview session of a multicast stream for a time period shorther than
        the time period configured in this object, that then no CDR record
	    shall be generated.
        Range : 0-120 seconds
        ALCATEL NOTE:
            ACCESS:      NA            USAGE:       NA
            PERSIST:     YES           INSRVMOD:    YES
            RANGE:       0..120        DEFVALUE:    2
            UNITS:       secs          SPARSE:      NA
            DESCR:       NA"
    ::= { igmpMIB 42}

igmpPreviewTimeCounterReset  OBJECT-TYPE
    SYNTAX TruthValue
    ACCESS read-write
    STATUS mandatory
    DESCRIPTION
        "Setting this object to 'true' will cause the system to reset the
        multicastUserItf2McGroupCurrentPreviewNumber object for all
        multicast streams and IGMP channels as well as the
        igmpChannelCurrentPreviewNumber object for all IGMP channels in
        the system.
        When set to false, the command is ignored. In case of a Get command,
        the value will be displayed as false.
        ALCATEL NOTE:
            ACCESS:      NA            USAGE:       NA
            PERSIST:     NO            INSRVMOD:    YES
            RANGE:       NA            DEFVALUE:    false
            UNITS:       NA            SPARSE:      NA
            DESCR:       NA"
    ::={igmpMIB 43}

igmpCDRAdminState  OBJECT-TYPE
    SYNTAX TruthValue
    ACCESS read-write
    STATUS mandatory
    DESCRIPTION
        " This object allows the operator to enable / disable CDR record
        generation in the system. When this object is set to 'true',
		the igmp subsystem will generate the start and stop CDR record
		types. In addition it will consider the configured values of
		following objects :
 		    multicastCDRGenTypeInterimCDR,
            multicastCDRGenTypeMaxNbrPreviewsExceeded,
		    multicastCDRGenTypeBlackoutActive,
		    multicastCDRGenTypeNoAccessRights
        When set to false, the IGMP subsystem will stop to generate
		these CDR record types .
        ALCATEL NOTE:
            ACCESS:      NA            USAGE:       NA
            PERSIST:     YES           INSRVMOD:    YES
            RANGE:       NA            DEFVALUE:    false
            UNITS:       NA            SPARSE:      NA
            DESCR:       NA"
    ::={igmpMIB 44}

igmpCDRManualRetrievalFlag  OBJECT-TYPE
    SYNTAX TruthValue
    ACCESS read-write
    STATUS mandatory
    DESCRIPTION
        "This object allows the operator to trigger the immediate
        collection of the CDR records. The CDR records are collected
		from all LT boards, compressed and stored in a file on
        the system disk. When set to 'false', the command is ignored.
		In case of a Get command, the value will be displayed as 'false'.
        ALCATEL NOTE:
            ACCESS:      NA            USAGE:       NA
            PERSIST:     NO            INSRVMOD:    YES
            RANGE:       NA            DEFVALUE:    false
            UNITS:       NA            SPARSE:      NA
            DESCR:       NA"
    ::={igmpMIB 45}

igmpSystemForkingAdminStatus OBJECT-TYPE
    SYNTAX TruthValue
    ACCESS read-write
    STATUS mandatory
    DESCRIPTION
        "This is an indication to enable or disable the IGMP forking on the system level
            1) true:  enable  IGMP forking behaviour
            2) false: disable IGMP forking behaviour
         It does not mean that forking applies always : IGMP forking is anyhow 
         only applicable which IGMP proxy is applicable. Example: there won't be forking
         for business CC vlans and and enabling forking is only applicable when igmp system
         is enabled.         
        ALCATEL NOTE:
            ACCESS:      NA            USAGE:       NA
            PERSIST:     YES           INSRVMOD:    YES
            RANGE:       NA            DEFVALUE:    false
            UNITS:       NA            SPARSE:      NA
            DESCR:       NA"
    ::={ igmpMIB 76 }

igmpSystemVlanSelection OBJECT-TYPE
    SYNTAX TruthValue
    ACCESS read-write
    STATUS mandatory
    DESCRIPTION
        "An indication whether or not user zapping is restricted within a certain multicast vlan.
         o true: multicast channel is selected with vlan matching the igmpChannelProtocolMcastVlan
         o false: multicast channel is selected irrespective of vlan
        ALCATEL NOTE:
            ACCESS:      NA            USAGE:       NA
            PERSIST:     YES           INSRVMOD:    YES
            RANGE:       NA            DEFVALUE:    false
            UNITS:       NA            SPARSE:      NA
            DESCR:       NA"
    ::={ igmpMIB 78 }

igmpSystemDiscardLowerVersions OBJECT-TYPE
    SYNTAX TruthValue
    ACCESS read-write
    STATUS mandatory
    DESCRIPTION
        "Whether or not the system discards IGMP packets with a version lower than what is 
         configured.
        ALCATEL NOTE:
            ACCESS:      NA            USAGE:       NA
            PERSIST:     YES           INSRVMOD:    YES
            RANGE:       NA            DEFVALUE:    false
            UNITS:       NA            SPARSE:      NA
            DESCR:       NA"
    ::={ igmpMIB 88 }

igmpSystemUncfgMcastSupport OBJECT-TYPE
     SYNTAX   INTEGER { legacy(1), asmonly(2), ssmonly(3), asmandssm(4) }
     ACCESS   read-write
     STATUS   mandatory
     DESCRIPTION
         "legacy- This is the default value for this object. Setting the object to
          legacy will enable un-configured SSM and ASM support for  GPON LT cards
          and un-configured ASM support alone for DSL LT cards.
          asmonly - Setting the object to asmonly will enable only unconfigured ASM support for 
                    GPON and DSL LT cards.
          ssmonly - Setting the object to ssmonly will enable only unconfigured SSM support for 
                    GPON and DSL LT cards.
          asmandssm - Setting the object to ssmandasm will enable unconfigured SSM and ASM 
                    support for GPON and DSL LT cards.
          legacy and asmandssm will only be supported in current release. 
          Other objects are added in future when needed.
          Configured SSM and ASM is always supported irrespective of this MIB value.
          ALCATEL NOTE: Currently the support is only for legacy(1) & asmandssm(4).
              ACCESS:     NA       USAGE:      OPT
              PERSIST:    YES      INSRVMOD:   YES
              RANGE:      1,4      DEFVALUE:   legacy(1)
              UNITS:      NA       SPARSE:     NA
              DESCR:      NA"
      ::= {igmpMIB  93 }


-- ==============================================================================
--  IGMP Package to Multicast Channel Table
-- ==============================================================================

igmpPackage2MulticastSrcTable OBJECT-TYPE
    SYNTAX SEQUENCE OF IgmpPkg2McsrcEntry
    ACCESS not-accessible
    STATUS mandatory
    DESCRIPTION
        " This table provides the relationship between a multicast packages
        and the multicast streams associated with this multicast package
        This table applies to pre-configured multicast streams only.
        ALCATEL NOTE:
            TABLESIZE: 4096
            DESCR: NA"
    ::= { igmpMIB 48 }

igmpPkg2McsrcEntry  OBJECT-TYPE
    SYNTAX IgmpPkg2McsrcEntry
    ACCESS not-accessible
    STATUS mandatory
    DESCRIPTION
        "One entry in table igmpPackage2MulticastSrcTable.
        Row creation : An entry is created by system.
        Row deletion : An entry is deleted by system.
        Index usage : the index is the .
        Note that entries will be presented to the SNMP manager in full
        lexicographical order."
    INDEX { igmpPkg2McsrcPackageIndex,
            igmpPkg2McsrcGroupClassDAddr,
            igmpPkg2McsrcGroupSourceIPAddr,
	    igmpPkg2McsrcVlanId } 
    ::= { igmpPackage2MulticastSrcTable 1 }

IgmpPkg2McsrcEntry  ::=
    SEQUENCE {
        igmpPkg2McsrcPackageIndex         INTEGER,
        igmpPkg2McsrcGroupClassDAddr      IpAddress,
        igmpPkg2McsrcGroupSourceIPAddr    IpAddress,
	igmpPkg2McsrcVlanId		  VlanId
    }

igmpPkg2McsrcPackageIndex    OBJECT-TYPE
    SYNTAX INTEGER
    ACCESS read-only
    STATUS mandatory
    DESCRIPTION
        "The Multicast package index as configured in the Multicast Package
        Table. Its index can also be derived from the bit position in the
        multicastSrcPkgMembBitmap object of the Multicast Channel Table, the
        igmpChannelProtocolPermPkgBitmap and the
	    igmpChannelProtocolPreviewPkgBitmap objects of the IGMP Channel
	    Protocol table, the igmpChannelPermPkgBitmap and 
        the igmpChannelPreviewPkgBitmap of the IGMP Channel table.
        ALCATEL NOTE:
            ACCESS:      NA            USAGE:       NA
            PERSIST:     NA            INSRVMOD:    NA
            RANGE:       NA            DEFVALUE:    NA
            UNITS:       NA            SPARSE:      NA
            DESCR:       NA"
    ::={ igmpPkg2McsrcEntry  1}

igmpPkg2McsrcGroupClassDAddr  OBJECT-TYPE
    SYNTAX IpAddress
    ACCESS read-only
    STATUS mandatory
    DESCRIPTION
        "The Multicast group IP Address in network-byte order
	    (big-endian). 
	    The class D address must be in the range of 224.0.0.3 to
	    239.255.255.255 except the reserved values defined in RFC 1700.
        ALCATEL NOTE:
            ACCESS:      NA            USAGE:       NA
            PERSIST:     NA            INSRVMOD:    NA
            RANGE:       NA            DEFVALUE:    NA
            UNITS:       NA            SPARSE:      NA
            DESCR:       NA"
    ::={ igmpPkg2McsrcEntry   2}

igmpPkg2McsrcGroupSourceIPAddr  OBJECT-TYPE
    SYNTAX IpAddress
    ACCESS read-only
    STATUS mandatory
    DESCRIPTION
        "The multicast source IP address in network-byte order (big-endian).
        This is a unicast IP address. For Asm multicast groups,
        the value of this object is set to 0.0.0.0.
        ALCATEL NOTE:
            ACCESS:      NA            USAGE:       NA
            PERSIST:     NA            INSRVMOD:    NA
            RANGE:       NA            DEFVALUE:    NA
            UNITS:       NA            SPARSE:      NA
            DESCR:       NA"
    ::= { igmpPkg2McsrcEntry  3}

igmpPkg2McsrcVlanId  OBJECT-TYPE
    SYNTAX VlanId
    ACCESS read-only
    STATUS mandatory
    DESCRIPTION
        "The multicast vlan Id 
         ALCATEL NOTE:
            ACCESS:      NA            USAGE:       NA
            PERSIST:     NA            INSRVMOD:    NA
            RANGE:       NA            DEFVALUE:    NA
            UNITS:       NA            SPARSE:      NA
            DESCR:       NA"
    ::= { igmpPkg2McsrcEntry  4}



-- ==============================================================================
--  Multicast replication Table User To Source
-- ==============================================================================

multicastUserItf2McGroupAddrTable OBJECT-TYPE
    SYNTAX SEQUENCE OF MulticastUserItf2McGroupAddrEntry
    ACCESS not-accessible
    STATUS mandatory
    DESCRIPTION
        "This table lists the active multicast streams per IGMP channel together with the
        state these multicast streams are currently forced to.
        ALCATEL NOTE:
            TABLESIZE: 5225472 GPON LT:(Max nbr of branches per board (36864) + 
	    max nbr streams in blackout per board(253440))* nbr boards (18)
            DESCR: NA"
    ::= { igmpMIB 49 }

multicastUserItf2McGroupAddrEntry OBJECT-TYPE
    SYNTAX MulticastUserItf2McGroupAddrEntry
    ACCESS not-accessible
    STATUS mandatory
    DESCRIPTION
        "One entry in table multicastUserItf2McGroupAddrTable.
        Row creation : An entry is created by the system.
        Row deletion : An entry is created by the system.
        Index usage : the index is the .
        Note that entries will be presented to the SNMP manager in full
        lexicographical order."
    INDEX { multicastUserItf2McGroupAddrIfIndex,
            multicastUserItf2McGroupAddrVlan,
            multicastUserItf2McGroupAddrClassDAddr,
            multicastUserItf2McGroupAddrSrcIPAddr }
    ::= { multicastUserItf2McGroupAddrTable 1 }

MulticastUserItf2McGroupAddrEntry ::=
    SEQUENCE {
        multicastUserItf2McGroupAddrIfIndex           InterfaceIndex,
        multicastUserItf2McGroupAddrVlan              VlanId,
        multicastUserItf2McGroupAddrClassDAddr        IpAddress,
        multicastUserItf2McGroupAddrSrcIPAddr         IpAddress,
        multicastUserItf2McGroupAddrActualstate       INTEGER,
        multicastUserItf2McGroupCurrentPreviewNumber  INTEGER,
        multicastUserItf2McGroupStatus                INTEGER
    }

multicastUserItf2McGroupAddrIfIndex     OBJECT-TYPE
    SYNTAX InterfaceIndex
    ACCESS not-accessible
    STATUS mandatory
    DESCRIPTION
        "The ifindex of the IGMP channel.
        ALCATEL NOTE:
            ACCESS:      NA            USAGE:       NA
            PERSIST:     NA            INSRVMOD:    NA
            RANGE:       NA            DEFVALUE:    NA
            UNITS:       NA            SPARSE:      NA
            DESCR:       NA"
    ::={ multicastUserItf2McGroupAddrEntry 1 }

multicastUserItf2McGroupAddrVlan        OBJECT-TYPE
    SYNTAX VlanId
    ACCESS not-accessible
    STATUS mandatory
    DESCRIPTION
        "The Vlan in which the multicast stream is provisioned
        by the multicast Service provider.
        ALCATEL NOTE:
            ACCESS:      NA            USAGE:       NA
            PERSIST:     NA            INSRVMOD:    NA
            RANGE:       NA            DEFVALUE:    NA
            UNITS:       NA            SPARSE:      NA
            DESCR:       NA"
    ::={ multicastUserItf2McGroupAddrEntry 2 }

multicastUserItf2McGroupAddrClassDAddr  OBJECT-TYPE
    SYNTAX IpAddress
    ACCESS not-accessible
    STATUS mandatory
    DESCRIPTION
        "The class D address of the multicast stream, in network-byte
        order and in the range 224.0.0.3 up to 239.255.255.255.
	    (big-endian).
        ALCATEL NOTE:
            ACCESS:      NA            USAGE:       NA
            PERSIST:     NA            INSRVMOD:    NA
            RANGE:       NA            DEFVALUE:    NA
            UNITS:       NA            SPARSE:      NA
            DESCR:       NA"
    ::={ multicastUserItf2McGroupAddrEntry 3 }

multicastUserItf2McGroupAddrSrcIPAddr   OBJECT-TYPE
    SYNTAX IpAddress
    ACCESS not-accessible
    STATUS mandatory
    DESCRIPTION
        "The multicast stream unicast source IP address,
	    in network-byte order (big-endian).
        It is set to the value 0.0.0.0 for SM multicast streams.
        ALCATEL NOTE:
            ACCESS:      NA            USAGE:       NA
            PERSIST:     NA            INSRVMOD:    NA
            RANGE:       NA            DEFVALUE:    NA
            UNITS:       NA            SPARSE:      NA
            DESCR:       NA"
    ::={ multicastUserItf2McGroupAddrEntry 4 }

multicastUserItf2McGroupAddrActualstate OBJECT-TYPE
    SYNTAX INTEGER { full-view(1), pre-view(2), black-out(3) }
    ACCESS read-only
    STATUS mandatory
    DESCRIPTION
        "The current state of the multicast stream :
          - full-view : the multicast stream is joined as a full-view session.
          - pre-view : the multicast stream is joined as a pre-view session.
          - black-out : the multicast stream is currently blocked i.e.
	                    the black-out period is running.
        ALCATEL NOTE:
            ACCESS:      NA            USAGE:       NA
            PERSIST:     NA            INSRVMOD:    NA
            RANGE:       NA            DEFVALUE:    NA
            UNITS:       NA            SPARSE:      NA
            DESCR:       NA"
    ::={ multicastUserItf2McGroupAddrEntry 5 }

multicastUserItf2McGroupCurrentPreviewNumber  OBJECT-TYPE
    SYNTAX INTEGER (0..1000)
    ACCESS read-only
    STATUS mandatory
    DESCRIPTION
        " The number of pre-view sessions already been viewed for this
        multicast stream on this IGMP Channel
        ALCATEL NOTE:
            ACCESS:      NA            USAGE:       NA
            PERSIST:     NA            INSRVMOD:    NA
            RANGE:       NA            DEFVALUE:    NA
            UNITS:       NA            SPARSE:      NA
            DESCR:       NA"
    ::={ multicastUserItf2McGroupAddrEntry 6 }
    
multicastUserItf2McGroupStatus OBJECT-TYPE
    SYNTAX INTEGER { static(1), dynamic(2), staticdynamic(3) }
    ACCESS read-only
    STATUS mandatory
    DESCRIPTION
        "The current status of the multicast stream :
          - static : the multicast stream is from a static multicast root
          - staticdynamic : the multicast stream is from a multicast root
                             who has static and dynamic branches.
          - dynamic : the multicast stream is from a dynamic multicast root.
        ALCATEL NOTE:
            ACCESS:      NA            USAGE:       MAND
            PERSIST:     NA            INSRVMOD:    NA
            RANGE:       1|2|3         DEFVALUE:    NA
            UNITS:       NA            SPARSE:      NA
            DESCR:       NA"
    ::={ multicastUserItf2McGroupAddrEntry 7 }


--=============================================================================
--  Multicast system paramaters IGMPv3 
--=============================================================================

igmpSystemGMQToUserSideVersion   OBJECT-TYPE
    SYNTAX  INTEGER   { version2(2), version3(3)}
    ACCESS read-write
    STATUS mandatory
    DESCRIPTION
        "The GMQToUserSideVersion object allows the operator to
        configure whether the iGMP subsystem must initiate IGMPv2 GMQs
        or IGMPv3 GMQs towards the End-user side. When set to IGMPv2 the
        iSAM IGMP subsystem initiates GMQs with v2 towards the end-users
        and expects all end-users to run in IGMPv2 mode;
        End-user initiated IGMPv2 reports are accepted.
        End-user initiated IGMPv1 & IGMPv3 reports are not accepted.
        When set to IGMPv3 the iSAM IGMP subsystem initiates GMQs with
        v3 towards the end-users. End-users may run in either IGMPv2
        or IGMPv3 mode.
        End-user initiated IGMPv2 and IGMPv3 reports are accepted.
        End-user initiated IGMPv1 reports are not accepted.
        This object configures the value on a system wide level.
        The System wide level value is by default inherited by the per
        IGMP Channel defined object.
        The object can only be changed on the condition that the igmp
        protocol is disabled at system level
        ALCATEL NOTE:
            ACCESS:      NA            USAGE:       NA
            PERSIST:     YES           INSRVMOD:    YES
            RANGE:       NA            DEFVALUE:    version3
            UNITS:       NA            SPARSE:      NA
            DESCR:       NA"
    DEFVAL {version3  }
    ::={ igmpMIB 50 }


igmpSystemVlanGenV3ProcessingStatus  OBJECT-TYPE 
    SYNTAX TruthValue
    ACCESS read-write
    STATUS mandatory
    DESCRIPTION
        " The V3ProcessingStatus object allows the operator to
        configure through  which IGMP version, IGMP packets are
        received from and forwarded towards the network side.
        This is a system wide object that in general applies
               to all MSP (pre-configured multicast streams) and ISP
        (non-configured multicast streams) VLANS. Of course, a
        particular MSP or ISP VLAN may cause an exception on the
        generally configured rule; MSP / ISP VLANs that causes
        exeptions must be configured in the IGMP to VLAN Table.
               This object can only be modified on the condition that
        the IGMP protocol is disabled at system level.
                      With the condition that the IGMP Protocol has been enabled
        in the system, the IGMP subsystem will process IGMPv3
        messages in (all) MSP / ISP VLANs if this object is set
                      to 'True'; received IGMP packets with a lower version will
        be dropped. Towards the network side, the IGMP subsystem
        shall generate IGMP packets with the configured version only.
                      With the condition that the IGMP Protocol has been enabled
        in the system, the IGMP subsystem will process IGMPv2
        messages in (all) MSP / ISP VLANs if this object is set
                      to 'False'; received IGMP packets with a higher / lower
        version will be dropped. Towards the network side, the IGMP
        subsystem shall generated IGMP packets with the configured
        version only.
        
              The object defaults to True.
        The object can only be changed when the igmp protocol is
        disabled at ssytem level
        ALCATEL NOTE:
            ACCESS:      NA            USAGE:       NA
            PERSIST:     YES           INSRVMOD:    YES
            RANGE:       NA            DEFVALUE:    true
            UNITS:       NA            SPARSE:      NA
            DESCR:       NA"
    DEFVAL { true }
    ::={ igmpMIB 51}

igmpSystemVlanGenV3MaxNumRecordsReport  OBJECT-TYPE 
    SYNTAX INTEGER (0..10)
    ACCESS read-write
    STATUS mandatory
    DESCRIPTION
        "The VlanGenV3MaxNumRecordsReport object allows the operator to
	    configure the maximum number of records that may be included in
	    an IGMPv3 membership report for all vlan-id's VLANS for which
	    either the V3ProcessingStatus object or the
	    VlanSystemV3ProcessingStatus object is set to 'True' .
	    The maximum number of reports shall be expressed as 2expN value
            (N= 0 to 10). This makes that the number of records include in a
	    membership report shall be one of the following values :
	      1, 2, 4, 8 , 16, 32, 64, 128, 256, 512, 1024.
          The value 1024 means that there is no real limitation regarding
	      the number of records included in the membership report;
        The number of records included in the membership report is
	    limited by the MTU size
	    A modification of the object value will become effective from
	    the next generated V3  membership report onwards.
        ALCATEL NOTE:
            ACCESS:      NA            USAGE:       NA
            PERSIST:     YES           INSRVMOD:    YES
            RANGE:       NA            DEFVALUE:    NA
            UNITS:       NA            SPARSE:      NA
            DESCR:       NA"
    DEFVAL { 3 }
    ::={igmpMIB 52}

igmpSystemOntSignallingEnabled            OBJECT-TYPE
    SYNTAX TruthValue
    ACCESS read-write
    STATUS mandatory
    DESCRIPTION
        "This is the default, system-wide, switch that specifies whether LT
         to ONT signalling should be enabled or disabled. The value of this
         object can be inherited by igmpPonChannelOntSignallingEnabled.

         When LT to ONT signalling is enabled (TRUE), the ONT passes IGMP Join
         requests received from the subscriber to the LT for processing. After
         the LT validates the request, 1) bandwidth not exceeded, 2) stream count
         not exceeded, 3) hosts not exceeded, 4) full-view or preview permission
         granted, 5) message is valid, the LT signals the ONT to start forwarding
         the multicast stream from the PON to the subscriber. The LT signals the
         ONT to stop forwarding after processing a Leave request or preview time
         has expired. This mode of operation will typically be used in a
         deployment where the OLT is not integrated with a third-party IPTV
         middleware application and the access control and viewer statistics
         facilities offered by the OLT are required.

         When LT to ONT signaling is disabled (FALSE), the ONT processes IGMP
         Join requests received from the subscriber. After the ONT validates the
         request, 1) stream count not exceeded, 2) message is valid, it starts
         forwarding the multicast stream from the PON to the subscriber. When a
         Leave request is received from the subscriber, the ONT stops forwarding
         the stream to the subscriber. This mode of operation will typically be
         used in a deployment where the OLT is integrated with a third-party IPTV
         middleware application, like MSTV, and the access control and viewer
         statistics facilities offered by the OLT are not required.

         Applicable only for GPON.

           ALCATEL NOTE:
           ACCESS:    NA
           USAGE:     NA
           PERSIST:   YES
           INSRVMOD:  YES
           RANGE:     true (1), false (2)
           DEFVALUE:  false (2)
           UNITS:     NA
           SPARSE:    NA
           DESCR:     GPON LT Specific"

         ::={ igmpMIB 64}


-- =============================================================================
--  IGMP vlan table .
-- =============================================================================

igmpVlanSystemTable OBJECT-TYPE
    SYNTAX SEQUENCE OF IgmpVlanSystemEntry
    ACCESS not-accessible
    STATUS mandatory
    DESCRIPTION
        "The concept followed by the IGMP to VLAN Table is that only
	    EXCEPTIONAL situations have to be configured in this table. 
	    This means that for all objects defined in this table, a system
	    wide peer object exists which reflects the commonrule for the 
	    MSP / ISP VLANs. Should an MSP / ISP  VLAN form an exception to 
	    one or multiple of these system wide peer objects then an entry 
	    needs to be created in this table for that particular MSP / ISP 
	    VLAN with the exceptional object configured to the required value
        ALCATEL NOTE:
            TABLESIZE: 64
            DESCR: NA"
    ::= { igmpMIB 53 }

igmpVlanSystemEntry OBJECT-TYPE
    SYNTAX IgmpVlanSystemEntry
    ACCESS not-accessible
    STATUS mandatory
    DESCRIPTION
        "Each entry reflects vlan based system parameters.
        Row creation : An entry is created by .
        Row deletion :
        Index usage : the index is the .
        Note that entries will be presented to the SNMP manager in full
        lexicographical order."
    INDEX { igmpVlanSystemVlanId }
    ::= { igmpVlanSystemTable 1}

IgmpVlanSystemEntry ::=
    SEQUENCE {
        igmpVlanSystemVlanId                VlanId,
		igmpVlanSystemVlanRowStatus         RowStatus,
		igmpVlanSystemV3ProcessingStatus  	TruthValue,
		igmpVlanSystemV3MaxNumRecordsReport INTEGER,
		         igmpVlanSystemSendQueries  TruthValue,
         igmpVlanSystemReportSrcIpAddressPresent TruthValue,
         igmpVlanSystemReportSrcIpAddressValue  IpAddress
     }

igmpVlanSystemVlanId      OBJECT-TYPE
    SYNTAX 	VlanId
    ACCESS not-accessible
    STATUS mandatory
    DESCRIPTION
        "This object is used as an index for the igmpVlanSystemTable,
	    Upon the creation of an entry in the IGMP to VLAN Table the 
	    IGMP subsystem shall check the availability of the MSP / ISP
	    VLAN. Upon the receipt of a negative acknowledge 
	    the IGMP subsystem shall reject the configuration request.
        ALCATEL NOTE:
            ACCESS:      NA            USAGE:       MAND
            PERSIST:     YES           INSRVMOD:    YES
            RANGE:       1..4093       DEFVALUE:    NA
            UNITS:       NA            SPARSE:      NA
            DESCR:       NA"
     ::={igmpVlanSystemEntry 1}

igmpVlanSystemVlanRowStatus     OBJECT-TYPE
    SYNTAX 	RowStatus
    ACCESS read-write
    STATUS mandatory
    DESCRIPTION
        "This object is used to create a new row or delete an
        existing row in this table. The possible valid values are:
            (1) active
            (4) createdAndGo
            (6) destroy
        To create an entry in this table, this object should be set to
        CreateAndGo. To delete an entry from this table, RowStatus
        should be set to Destroy value by the SNMP manager.
        This object does not support the dribble-mode.
        ALCATEL NOTE:
            ACCESS:      NA            USAGE:       MAND
            PERSIST:     NO            INSRVMOD:    YES
            RANGE:       1,4,6         DEFVALUE:    NA
            UNITS:       NA            SPARSE:      NA
            DESCR:       NA"
    ::={igmpVlanSystemEntry 2}

    
igmpVlanSystemV3ProcessingStatus  OBJECT-TYPE 
    SYNTAX  TruthValue
    ACCESS read-write
    STATUS mandatory
    DESCRIPTION
        "The VlanSystemV3Processingtatus object allows the
	    operator to configure through which IGMP version, IGMP packets
	    will be received from and forwarded towards the network side in
	    this particular MSP / ISP VLAN .
        With the condition that the IGMP Protocol has been enabled in the
	    system, the IGMP subsystem will process IGMPv3 messages in this
        MSP / ISP VLAN if this object is set version3; received IGMP packets
        with a lower version will be dropped.
	    Towards the network side, the IGMP subsystem shall generated IGMP
	    packets with the configured version only.
        With the condition that the IGMP Protocol has been enabled in the
	    system, the IGMP subsystem will process IGMPv2 messages in (all)
	    MSP / ISP VLANs if this object is set to 'False'; received IGMP packets
        with a higher / lower version will be dropped towards the network side,
        the IGMP subsystem shall generated IGMP packets with the configured
        version only.
        Creating / Removing an entry with the intention to modify the
	    V3ProcessingAdminStatus  of a particular MSP / ISP VLAN shall only be
        accepted on the condition that the IGMP protocol operational state
        has been disabled at system level.
        ALCATEL NOTE:
            ACCESS:      NA            USAGE:       MAND
            PERSIST:     YES           INSRVMOD:    YES
            RANGE:       NA            DEFVALUE:    NA
            UNITS:       NA            SPARSE:      NA
            DESCR:       NA"
    ::={igmpVlanSystemEntry 3}

igmpVlanSystemV3MaxNumRecordsReport  OBJECT-TYPE 
    SYNTAX INTEGER (0..10)
    ACCESS read-write
    STATUS mandatory
    DESCRIPTION
        "The VlanV3MaxNumRecordsReport object allows the operator to
	    configure the maximum number of records that may be included in
	    an IGMPv3 membership report that is sent to the network side.
	    The maximum number of reports shall be expressed as 2expN value
        (N= 0 to 10). This makes that the number of records include in a
	    membership report shall be one of the following values : 1, 2, 4, 8,
        16, 32, 64, 128, 256, 512, 1024.
        The value 1024 means that there is no real limitation regarding
	    the number of records included in the membership report;
	    The number of records included in the membership report is limited
	    by the MTU size.
        ALCATEL NOTE:
            ACCESS:      NA            USAGE:       MAND
            PERSIST:     YES           INSRVMOD:    YES
            RANGE:       NA            DEFVALUE:    3
            UNITS:       NA            SPARSE:      NA
            DESCR:       NA"
    ::={igmpVlanSystemEntry 4}
    
igmpVlanSystemSendQueries  OBJECT-TYPE 
    SYNTAX  TruthValue
    ACCESS read-write
    STATUS mandatory
    DESCRIPTION
        "The VlanSystemSendQueries object allows the
         operator to indicate that for a given VLAN no querier is present.
         When set to true, the centralized NGVR IGMP proxy
         shall sent autonomously GMQ messages.
         When a row is created, and this object is not specified it's value
         will be set to false.
         Object is only applicable for ISAM 7363 MX; for other products the setting of this 
         object to TRUE will be rejected.

        ALCATEL NOTE:
            ACCESS:      NA            USAGE:       MAND
            PERSIST:     YES           INSRVMOD:    YES
            RANGE:       NA            DEFVALUE:    false
            UNITS:       NA            SPARSE:      NA
            DESCR:       NA"
    ::={igmpVlanSystemEntry 5}

igmpVlanSystemReportSrcIpAddressPresent  OBJECT-TYPE 
    SYNTAX  TruthValue
    ACCESS read-write
    STATUS mandatory
    DESCRIPTION
        "When set to true the object igmpVlanSystemReportSrcIpAddressValue
         will be taken into account iso using igmpSystemSrcIPAddr
         When a row is created, and this object is not specified it's value
         will be igmpSystemSrcIPAddr
         Object is only applicable for ISAM 7363 MX; for other products the setting of this 
         object to TRUE will be rejected.

        ALCATEL NOTE:
            ACCESS:      NA            USAGE:       MAND
            PERSIST:     YES           INSRVMOD:    YES
            RANGE:       NA            DEFVALUE:    false
            UNITS:       NA            SPARSE:      NA
            DESCR:       NA"
    ::={igmpVlanSystemEntry 6}

igmpVlanSystemReportSrcIpAddressValue  OBJECT-TYPE 
    SYNTAX IpAddress
    ACCESS read-write
    STATUS mandatory
    DESCRIPTION
        "The VlanSystemReportSrcIpAddressValue object allows the operator to
	 configure per VLAN the source ip to be used in report messages to the network.
         The object is only applicable when VlanSystemReportSrcIpAddressPresent is set to true. 
	 Can only be modified when igmpVlanSystemReportSrcIpAddressPresent is false.
         When a row is created, and this object is not specified it's value
         will be set to 0.0.0.0
         Object is only applicable for ISAM 7363 MX; for other products the setting of this 
         object to  value /= 0.0.0.0 will be rejected.

        ALCATEL NOTE:
            ACCESS:      NA            USAGE:       MAND
            PERSIST:     YES           INSRVMOD:    YES
            RANGE:       NA            DEFVALUE:    NA
            UNITS:       NA            SPARSE:      NA
            DESCR:       NA"
    ::={igmpVlanSystemEntry 7}

-- =============================================================================
--  Multicast replication Table MulticastGroup To user 
--   Show mcast grp-membership 
-- =============================================================================

multicastMcGroupAddr2UserItfTable OBJECT-TYPE
    SYNTAX SEQUENCE OF MulticastMcGroupAddr2UserItfEntry
    ACCESS not-accessible
    STATUS mandatory
    DESCRIPTION
        "This table lists per multicast stream the user interfaces to which
        the system is currently requested to forward this stream.
        ALCATEL NOTE:
            TABLESIZE: 5225472 GPON LT= ((max nbr branches/board(36864)+
	                         (max nbr blackout/board(253440))*18
             DESCR: NA"
    ::= { igmpMIB 54 }

multicastMcGroupAddr2UserItfEntry OBJECT-TYPE
    SYNTAX MulticastMcGroupAddr2UserItfEntry
    ACCESS not-accessible
    STATUS mandatory
    DESCRIPTION
        "One entry in table multicastMcGroupAddr2UserItfTable.
        Row creation : An entry is created by .
        Row deletion :
        Index usage : the index is the .
        Note that entries will be presented to the SNMP manager in full
        lexicographical order."
    INDEX { multicastMcGroupAddr2UserItfClassDAddr,
            multicastMcGroupAddr2UserItfSrcIPAddr,
		    multicastMcGroupAddr2UserItfVlan,
 		    multicastMcGroupAddr2UserItfIfIndex
          }
    ::= { multicastMcGroupAddr2UserItfTable 1 }

MulticastMcGroupAddr2UserItfEntry ::=
    SEQUENCE {
        multicastMcGroupAddr2UserItfClassDAddr	IpAddress,
		multicastMcGroupAddr2UserItfSrcIPAddr	IpAddress,
		multicastMcGroupAddr2UserItfVlan        VlanId,
 		multicastMcGroupAddr2UserItfIfIndex     InterfaceIndex,
 		multicastMcGroupAddr2UserItfActualstate INTEGER,
--		multicastMcGroupAddr2UserItfSrcMode     INTEGER
		multicastMcGroupAddr2UserItfStatus      INTEGER
    }

multicastMcGroupAddr2UserItfClassDAddr  OBJECT-TYPE
    SYNTAX IpAddress
    ACCESS not-accessible
    STATUS mandatory
    DESCRIPTION
        "The multicast group IP @. This is a class D address,
	    in network-byte order (big-endian), in the range of 224.0.0.3
	    upto 239.255.255.255.
        ALCATEL NOTE:
            ACCESS:      NA            USAGE:       MAND
            PERSIST:     NA            INSRVMOD:    NA
            RANGE:       valid multicast calls D address
                                       DEFVALUE:    NA
            UNITS:       NA            SPARSE:      NA
            DESCR:       NA"
    ::={ multicastMcGroupAddr2UserItfEntry 1 }

multicastMcGroupAddr2UserItfSrcIPAddr   OBJECT-TYPE
    SYNTAX IpAddress
    ACCESS not-accessible
    STATUS mandatory
    DESCRIPTION
        "The multicast source IP address. This is a unicast IP address,
        in network-byte order (big-endian).
        The value 0 0 0 0 means the IP address of the source of the
        multicast stream is unknown (ASM multicast groups).
        ALCATEL NOTE:
            ACCESS:      NA            USAGE:       MAND
            PERSIST:     NO            INSRVMOD:    NO
            RANGE:       valid IP address DEFVALUE:    NA
            UNITS:       NA            SPARSE:      NA
            DESCR:       NA"
    ::={ multicastMcGroupAddr2UserItfEntry 2 }

multicastMcGroupAddr2UserItfVlan        OBJECT-TYPE
    SYNTAX VlanId
    ACCESS not-accessible
    STATUS mandatory
    DESCRIPTION
        "This is the Vlan in which the multicast stream is received from the
	    network.
        ALCATEL NOTE:
            ACCESS:      NA            USAGE:       MAND
            PERSIST:     NO            INSRVMOD:    NO
            RANGE:       1..4093       DEFVALUE:    NA
            UNITS:       NA            SPARSE:      NA
            DESCR:       NA"
    ::={ multicastMcGroupAddr2UserItfEntry 3 }


multicastMcGroupAddr2UserItfIfIndex     OBJECT-TYPE
    SYNTAX InterfaceIndex
    ACCESS not-accessible
    STATUS mandatory
    DESCRIPTION
        "This is an IfIndex identifying a user interface receiving
        a multicast stream.
        ALCATEL NOTE:
            ACCESS:      NA            USAGE:       MAND
            PERSIST:     NO            INSRVMOD:    NO
            RANGE:       NA            DEFVALUE:    NA
            UNITS:       NA            SPARSE:      NA
            DESCR:       NA"
    ::={ multicastMcGroupAddr2UserItfEntry 4 }

 

multicastMcGroupAddr2UserItfActualstate OBJECT-TYPE
    SYNTAX INTEGER { full-view(1), pre-view(2), black-out(3)}
    ACCESS read-only
    STATUS mandatory
    DESCRIPTION
        "Gives the actual state of the streaming of the specified
        multicast stream from the specified source to the specified user
        interface.
        ALCATEL NOTE:
            ACCESS:      NA            USAGE:       MAND
            PERSIST:     NO            INSRVMOD:    NO
            RANGE:       NA            DEFVALUE:    full-view(1)
            UNITS:       NA            SPARSE:      NA
            DESCR:       NA"
    ::={ multicastMcGroupAddr2UserItfEntry 5 }
    
multicastMcGroupAddr2UserItfStatus OBJECT-TYPE
    SYNTAX INTEGER { static(1), dynamic(2), staticdynamic(3) }
    ACCESS read-only
    STATUS mandatory
    DESCRIPTION
        "The current status of the multicast stream :
          - static : the multicast stream is from a static multicast root
          - staticdynamic : the multicast stream is from a multicast root
                             who has static and dynamic branches.
          - dynamic : the multicast stream is from a dynamic multicast root.
        ALCATEL NOTE:
            ACCESS:      NA            USAGE:       MAND
            PERSIST:     NA            INSRVMOD:    NA
            RANGE:       1|2|3            DEFVALUE:    NA
            UNITS:       NA            SPARSE:      NA
            DESCR:       NA"
    ::={ multicastMcGroupAddr2UserItfEntry 6 }



-- =============================================================================
--  CDR system Generation method
-- =============================================================================

multicastCDRGenerationMethod  OBJECT-TYPE
    SYNTAX INTEGER { local-file-storage(1),remote-logging(2)}
    ACCESS read-write
    STATUS mandatory
    DESCRIPTION
        "The method the call data record is to be generated and forwarded
        to the operator's management platform either by local file storage
        or immediate logging. If immediate logging is chosen, 
        multicastCDRSystemPollingCycle will be automatically configured to
        60s.
        ALCATEL NOTE:
            ACCESS:      NA            USAGE:       MAND
            PERSIST:     YES           INSRVMOD:    NO
            RANGE:       1|2           DEFVALUE:   local-file-storage(1)
            UNITS:       NA            SPARSE:      NA
            DESCR:       NA"
    DEFVAL { local-file-storage }
    ::={igmpMIB 55}

-- =============================================================================
--  CDR system Generation type  
-- =============================================================================

multicastCDRGenerationParameters OBJECT IDENTIFIER ::= { igmpMIB 56 }

-- This object group contains management information for CDR generation 
-- and collecting such as CDR generation triggers and polling cycle details." 

multicastCDRTypeStartCDR  OBJECT-TYPE
    SYNTAX TruthValue
    ACCESS read-only
    STATUS mandatory
    DESCRIPTION
        "This object provides information whether the start-CDR record type
        generation is switched-on or switched-off.
	    This object shall show the value -true- in case the CDRAdminState
		object has been set to enabled. Otherwise this object shall show
		the value -false-.
        ALCATEL NOTE:
            ACCESS:      NA            USAGE:       NA
            PERSIST:     NA            INSRVMOD:    NA
            RANGE:       NA            DEFVALUE:    NA
            UNITS:       NA            SPARSE:      NA
            DESCR:       NA"
    DEFVAL { true }
    ::={ multicastCDRGenerationParameters 1}

multicastCDRTypeStopCDR  OBJECT-TYPE
    SYNTAX TruthValue
    ACCESS read-only
    STATUS mandatory
    DESCRIPTION
        "This object provides information whether the stop-CDR
	    record type generation is switched-on or switched-off. This
	    object shall show the value -true- in case the CDRAdminState
	    object has been set to enabled. Otherwise this object shall
	    show the value -false-.
        ALCATEL NOTE:
            ACCESS:      NA            USAGE:       NA
            PERSIST:     NA            INSRVMOD:    NA
            RANGE:       NA            DEFVALUE:    NA
            UNITS:       NA            SPARSE:      NA
            DESCR:       NA"
    DEFVAL { true  }
    ::={ multicastCDRGenerationParameters 2}

multicastCDRTypeInterimCDR  OBJECT-TYPE
    SYNTAX TruthValue
    ACCESS read-write
    STATUS mandatory
    DESCRIPTION
        "This object allows to configure whether Interim CDR
        records must be generated or not for the active full-view /
	    pre-view sessions. The periodic time interval by which the interim
	    records are generated is configured in the CDRInterimPeriod object
        ALCATEL NOTE:
            ACCESS:      NA            USAGE:       NA
            PERSIST:     YES           INSRVMOD:    NA
            RANGE:       NA            DEFVALUE:    NA
            UNITS:       NA            SPARSE:      NA
            DESCR:       NA"
    DEFVAL { false }
    ::={ multicastCDRGenerationParameters 3}


multicastCDRTypeMaxNbrPreviewsExceeded OBJECT-TYPE
    SYNTAX TruthValue
    ACCESS read-write
    STATUS mandatory
    DESCRIPTION
        "This object allows to configure whether a CDR record must be generated
        in the situation where an end-user tries to join a pre-view session at
        the moment the Maximum number of preview sessions threshold for
        this multicast stream on this IGMP channel has already reached its
        maximum value.
        This object is only considered when the CDRAdminStatehas been enabled.
        ALCATEL NOTE:
            ACCESS:      NA            USAGE:       MAND
            PERSIST:     YES           INSRVMOD:    NA
            RANGE:       NA            DEFVALUE:    NA
            UNITS:       NA            SPARSE:      NA
            DESCR:       NA"
    DEFVAL { false }
    ::={multicastCDRGenerationParameters 4 }

multicastCDRTypeBlackoutActive OBJECT-TYPE
    SYNTAX TruthValue
    ACCESS read-write
    STATUS mandatory
    DESCRIPTION
        "This object allows to configure whether a CDR record must be generated
        in the situation where an end-user tries to join a pre-view session at
        the moment that the black-out period is active for this particular
        multicast stream on this particular IGMP Channel.
        This object is only considered when the CDRAdminState has been enabled.
        ALCATEL NOTE:
            ACCESS:      NA            USAGE:       MAND
            PERSIST:     YES           INSRVMOD:    NA
            RANGE:       NA            DEFVALUE:    false
            UNITS:       NA            SPARSE:      NA
            DESCR:       NA"
    DEFVAL { false }
    ::={multicastCDRGenerationParameters 5 }
          
multicastCDRTypeNoAccessRights OBJECT-TYPE
    SYNTAX TruthValue
    ACCESS read-write
    STATUS mandatory
    DESCRIPTION
        "This object allows to configure whether a CDR record must be generated
        in the situation where an end-user tries to join a multicast stream
        while no access-rights were assigned to this multicast stream.
        This object is only considered when the CDRAdminState has been enabled.
        ALCATEL NOTE:
            ACCESS:      NA            USAGE:       MAND
            PERSIST:     YES           INSRVMOD:    NA
            RANGE:       NA            DEFVALUE:    false
            UNITS:       NA            SPARSE:      NA
            DESCR:       NA"
    DEFVAL { false }
    ::={multicastCDRGenerationParameters 6 }
 
multicastCDRForSingles OBJECT-TYPE
    SYNTAX INTEGER (1..30)
    ACCESS read-write
    STATUS mandatory
    DESCRIPTION
        "The CDRGenRateForSingles object allows the operator to rate limit
        the generation  of the Max_Nbr_Previews_Exc_CDR, Blackout_Running_CDR,
        and  Acess_Rights_Violated_CDR. The CDRGenForSingles object can be
        configured within the range [1..30] CDR records per minute and defaults
        to 3 per minute.
	    This object becomes only effective in case the cdr-admin-state is
        enabled and either the multicastCDRGenTypeMaxNbrPreviewsExceeded object
        is set to True and/or the multicastCDRGenTypeBlackoutActive object
        is set to True and/or the multicastCDRGenTypeNoAccessRights object
        is set to True.
        A modification of the CDRGenRateForSingles object shall immediately
        This object is only valid when the cdr-admin-state is on.
        ALCATEL NOTE:
            ACCESS:      NA            USAGE:       MAND
            PERSIST:     YES           INSRVMOD:    NA
            RANGE:       NA            DEFVALUE:    NA
            UNITS:       NA            SPARSE:      NA
            DESCR:       NA"
    DEFVAL { 3 }
    ::={multicastCDRGenerationParameters 7}

multicastCDRInterimPeriod OBJECT-TYPE
    SYNTAX INTEGER (0..60)
    ACCESS read-write
    STATUS mandatory
    DESCRIPTION
        "The CDRInterimGenPeriod object allows the operator to configure
        the Interim_CDR generation period. The CDRInterimGenPeriod can be
        configured within the range [0...60] minutes in multiple of 5 minutes
        and defaults to 15 minutes. Only the value '0' and values >= 15
        (in multiples of 5 minutes) shall be considered.
        The value '0' has a special meaning in the sense that configuring
        a value '0' means that the Interim-CDR is generated upon the expiry
        of the quarter of an hour Period (period by which CDR files are
        generated on the system disk). This period is fixed and the generation
        of the Interim-CDRs is independent from the time the full-view or
        pre-view session has started.
        Configuring values from 15 up to 60 minutes means that the Interim_CDR
        period is started at the moment the Start_CDR is generated but
        considering the CDRGenRecognition period meaning that the first
        CDRInterimGenPeriod timer shall be started with a value equal to
        the configured CDRInterimGenPeriod - the CDRGenRecognition period.
        A subsequent CDRInterimGenPeriod is then started with the configured
        value. Consequently the interim-CDR period is started separately for
        each full-view / pre-view session.
        Values in between '0' and '15' minutes are not considered as these
        would cause too many Interim-CDR be genearted. With the current
        dimensioning for memory resources on the LT and NT board and the disk
        space on the system disk, the system is not able to handle such
        a potential huge amount of CDRs with success.
	    This object becomes only effective in case the CDRGenType object has
        been configured to generate Interim-CDRs.
        A modification of the CDRInterimGenPeriod object shall not affect
        the running pre-view / full-view sessions; It becomes only effective
        for new pre-view / full-view sessions.
        ALCATEL NOTE:
            ACCESS:      NA            USAGE:       NA
            PERSIST:     YES           INSRVMOD:    NA
            RANGE:       NA            DEFVALUE:    NA
            UNITS:       NA            SPARSE:      NA
            DESCR:       NA"
    DEFVAL { 15 }
    ::={multicastCDRGenerationParameters 8}

-- =============================================================================
--  CDR system file aging time 
-- =============================================================================

multicastCDRFileAgingTime OBJECT-TYPE
    SYNTAX INTEGER (4..24)
    ACCESS read-write
    STATUS mandatory
    DESCRIPTION
        "The CDRFileAgingTime object allows the operator to configure the CDR
	    file aging time on the system disk. It shall be configurable within
	    the range [4..24] hours in multiple of 1 Hour and defaults to 8
	    hours.
        A modification of the CDRFile AgingTime object becomes effective at
	    the moment a next CDR file is created on the System disk.
        This object is only valid when the cdr-admin-state is on.
        ALCATEL NOTE:
            ACCESS:      NA            USAGE:       NA
            PERSIST:     YES           INSRVMOD:    NA
            RANGE:       NA            DEFVALUE:    NA
            UNITS:       hours         SPARSE:      NA
            DESCR:       NA"
    DEFVAL { 8 }
    ::={igmpMIB 57}

 
-- =============================================================================
--  CDR system polling cycle 
-- ============================================================================

multicastCDRSystemPollingCycle OBJECT-TYPE
    SYNTAX INTEGER (60..900)
    ACCESS read-write
    STATUS mandatory
    DESCRIPTION
        "The CDRPollingCycle object allows the operator to configure the
	    polling period for the CDR records.
	    It shall be configurable in the range [60..900] seconds in multiple of
	    60 seconds and defaults to 180 secs.
        A modification of the CDRPollingCycle object becomes effective at the
	    moment a next periodic polling cycle is started.
	    The current running polling cycle shall not be affected by the changed
        configuration value.
        ALCATEL NOTE:
            ACCESS:      NA            USAGE:       NA
            PERSIST:     YES           INSRVMOD:    NA
            RANGE:       60..900       DEFVALUE:    NA
            UNITS:       seconds       SPARSE:      NA
            DESCR:       NA"
    DEFVAL { 180 }
    ::={igmpMIB 58}
 
-- =============================================================================
--  IGMP CHANNEL PROTOCOL data 
-- =============================================================================

igmpChannelProtocolTable OBJECT-TYPE
    SYNTAX SEQUENCE OF IgmpChannelProtocolEntry
    ACCESS not-accessible
    STATUS mandatory
    DESCRIPTION
        "This table contains igmp channel data for igmpv2 and igmpv3
		data as well as related channel statistics.
        ALCATEL NOTE:
        TABLESIZE: nbr max channels system  
            DESCR: NA"
    ::= { igmpMIB 59}

igmpChannelProtocolEntry OBJECT-TYPE
    SYNTAX IgmpChannelProtocolEntry
    ACCESS not-accessible
    STATUS mandatory
    DESCRIPTION
        "This object contains statistics and counters related to
        multicast of a user multicast capable port.
        Row creation : An entry is created by the system.
        Row deletion : An entry is deleted by the system
        Index usage : the index is the ifIndex of the an access interface.
        Note that entries will be presented to the SNMP manager in full
        lexicographical order."
    INDEX { igmpChannelProtocolIndex  }
    ::= {igmpChannelProtocolTable 1}

IgmpChannelProtocolEntry  ::=
    SEQUENCE {
        igmpChannelProtocolIndex                   		InterfaceIndex,
        igmpChannelProtocolPermPkgBitmap                OCTET STRING,
        igmpChannelProtocolMaxMsgRate                   INTEGER,
        igmpChannelProtocolNoPermJoinCounter            Counter,
        igmpChannelProtocolBitRateFailJoinCounter       Counter,
        igmpChannelProtocolInvalidJoinClassDCounter     Counter,
        igmpChannelProtocolNumSecOvrldProtAppl          Counter,
        igmpChannelProtocolClearStats                   TruthValue,
        igmpChannelProtocolMaxNumGroup                  INTEGER,
        igmpChannelProtocolCurrentNumGroup              Gauge,
        igmpChannelProtocolNumFailJoinCounter           Counter,
        igmpChannelProtocolSysNumFailJoinCounter        Counter,
        igmpChannelProtocolCurrentPreviewNumber         Counter,
        igmpChannelProtocolPreviewPkgBitmap             OCTET STRING,
        igmpChannelProtocolCurrentUncfgGroupNumber      Counter,
        igmpChannelProtocolGMQToUserItfVersion          INTEGER ,
        igmpChannelProtocolTxGeneralQueries             Counter,
        igmpChannelProtocolTxGroupSpecificQueries     	Counter,
        igmpChannelProtocolRxV1Reports		       	Counter,
        igmpChannelProtocolRxV2Reports		       	Counter,
        igmpChannelProtocolRxV3Reports 			    Counter,
        igmpChannelProtocolRxV2Leaves 				Counter,
        igmpChannelProtocolRxValidPackets 			    Counter,
        igmpChannelProtocolRxInvalidPackets      		Counter,
        igmpChannelProtocolRxUnknownTypePackets		    Counter,
        igmpChannelProtocolRxBadLengthDrops 	  	    Counter,
        igmpChannelProtocolRxBadIpChksmDropsCounter     Counter,
        igmpChannelProtocolRxBadIgmpChksmDropsCounter   Counter,
	igmpChannelProtocolRowStatus                    RowStatus,
       	igmpChannelProtocolTxGroupSourceSpecificQueries	Counter,
	igmpChannelProtocolRxReportsWrongMode           Counter,
        igmpChannelProtocolForkingAdminStatus           INTEGER,
        igmpChannelProtocolOntSignallingEnabled         INTEGER,
	igmpChannelProtocolPonBitRateFailJoinCounter    Counter,
	igmpChannelProtocolMcastVlan		        INTEGER,
	igmpChannelProtocolMulticastChannelPriority     INTEGER,
 	igmpChannelProtocolMcastVlanTranslation         TruthValue,
 	igmpChannelProtocolMode                         INTEGER,
        igmpChannelProtocolServiceContextProfile        AsamProfilePointer
    }

igmpChannelProtocolIndex OBJECT-TYPE
    SYNTAX InterfaceIndex
    ACCESS not-accessible
    STATUS mandatory
    DESCRIPTION
        "This is the IfIndex associated with the access interface
		which is carrying the IGMP channel, and the multicast egress 
		traffic.
        ALCATEL NOTE:
            ACCESS:      NA            USAGE:       MAND
            PERSIST:     YES           INSRVMOD:    NO
            RANGE:       NA            DEFVALUE:    NA
            UNITS:       NA            SPARSE:      NO
            DESCR:       NA"
    ::={igmpChannelProtocolEntry 1}


igmpChannelProtocolPermPkgBitmap OBJECT-TYPE
    SYNTAX OCTET STRING (SIZE(128))
    ACCESS read-write
    STATUS mandatory
    DESCRIPTION
        "The purpose of this bitmap is to indicate which packages
        the user is allowed to join. In accordance with the
        ASAM MIB convention, the bitmap shall function as follows:
        MSB                                     LSB
        byte 0 :  8  7  6  5  4  3  2  1
        byte 1 : 16 15 14 13 12 11 10  9
        byte 2 : 24 23 22 21 20 19 18 17
        byte 3 : 32 31 30 29 28 27 26 25
        byte 4 : 40 39 38 37 36 35 34 33
        byte 5 : 48 47 46 45 44 43 42 41
        byte 6 : 56 55 54 53 52 51 50 49
        byte 7 : 64 63 62 61 60 59 58 57
        ... ... ... ... ... ... ... ...

        byte 127 1024 1023 1022 1021 1020 1019 1018 1017
        Following the convention, byte 0 shall be the first byte (the
        left-most, most significant byte).
        ALCATEL NOTE:
            ACCESS:      NA            USAGE:       NA
            PERSIST:     YES           INSRVMOD:    YES
            RANGE:       NA            DEFVALUE:    NA
            UNITS:       NA            SPARSE:      NO
            DESCR:       NA"
    DEFVAL {'0100000000000000000000000000000000000000000000000000000000000000000000000000000000000000000000000000000000000000000000000000000000000000000000000000000000000000000000000000000000000000000000000000000000000000000000000000000000000000000000000000000000000000'H }
    ::= {igmpChannelProtocolEntry 2}

igmpChannelProtocolMaxMsgRate OBJECT-TYPE
    SYNTAX INTEGER (0..256)
    ACCESS read-write
    STATUS mandatory
    DESCRIPTION
        "This object indicates the maximum messages per second that can be
        received by the IGMP protocol stack. When the message rate
        exceeds this value, overload protection will be applied to the
        IGMP channel.By default this Object is in System-Inherited state which 
        will inherit the value from qosDslControlPktRate  object.The configuration of this attribute
        is supported only on GPON LT.for all other LT's this attribute is not supported.
        ALCATEL NOTE:
            ACCESS:      NA            USAGE:       NA
            PERSIST:     YES           INSRVMOD:    NA
            RANGE:       NA            DEFVALUE:    0
            UNITS:       msgs          SPARSE:      NO
            DESCR:       NA"
    ::= {igmpChannelProtocolEntry 3}

igmpChannelProtocolNoPermJoinCounter OBJECT-TYPE
    SYNTAX Counter
    ACCESS read-only
    STATUS mandatory
    DESCRIPTION
        "Indicates the number of times that a permission bitmap failure
        has occurred. (In other words, a request to join a multicast
        channel has been attempted for which the IGMP channel has no
        permission.
        ALCATEL NOTE:
            ACCESS:      NA            USAGE:       NA
            PERSIST:     NO            INSRVMOD:    NA
            RANGE:       0..65535      DEFVALUE:    0
            UNITS:       NA            SPARSE:      NO
            DESCR:       NA"
    ::= {igmpChannelProtocolEntry 4}

igmpChannelProtocolBitRateFailJoinCounter OBJECT-TYPE
    SYNTAX Counter
    ACCESS read-only
    STATUS mandatory
    DESCRIPTION
        "Indicates the number of times that an IGMP join message failed
        to trigger a multicast connection because the resultant
        bandwidth would exceed the maximum total bitrate allowed.
        ALCATEL NOTE:
            ACCESS:      NA            USAGE:       NA
            PERSIST:     NO            INSRVMOD:    NA
            RANGE:       0..65535      DEFVALUE:    0
            UNITS:       NA            SPARSE:      NO
            DESCR:       NA"
    ::= {igmpChannelProtocolEntry 5}

igmpChannelProtocolInvalidJoinClassDCounter OBJECT-TYPE
    SYNTAX Counter
    ACCESS read-only
    STATUS mandatory
    DESCRIPTION
        "Indicates the number of times that the IP address:
            1) isn't multicast address, or
            2) is a reserved multicast address, or
            3) isn't in Multicast Channel Table, but its low-order
               23 bits are the same as those of a group IP address in
               the Multicast Channel Table
        ALCATEL NOTE:
            ACCESS:      NA            USAGE:       NA
            PERSIST:     NO            INSRVMOD:    NA
            RANGE:       0..65535      DEFVALUE:    0
            UNITS:       NA            SPARSE:      NO
            DESCR:       NA"
    ::= {igmpChannelProtocolEntry 6}

igmpChannelProtocolNumSecOvrldProtAppl OBJECT-TYPE
    SYNTAX Counter
    ACCESS read-only
    STATUS mandatory
    DESCRIPTION
        "Indicates the number of one second intervals for which overload
        protection has been applied because the message rate exceeded
        the peak threshold (igmpChannelMaxMsgRate).
        ALCATEL NOTE:
            ACCESS:      NA            USAGE:       NA
            PERSIST:     NO            INSRVMOD:    NA
            RANGE:       0..65535      DEFVALUE:    0
            UNITS:       NA            SPARSE:      NO
            DESCR:       NA"
    ::= {igmpChannelProtocolEntry 7}

igmpChannelProtocolClearStats OBJECT-TYPE
    SYNTAX TruthValue
    ACCESS read-write
    STATUS mandatory
    DESCRIPTION
        "When this object is set to true, the statistics within this
        table are cleared. When this object is set to false, the request is
        ignored.
        ALCATEL NOTE:
            ACCESS:      NA            USAGE:       MAND
            PERSIST:     NO            INSRVMOD:    YES
            RANGE:       NA            DEFVALUE:    NA
            UNITS:       NA            SPARSE:      NO
            DESCR:       NA"
    DEFVAL {false}
    ::={igmpChannelProtocolEntry 8}

 
igmpChannelProtocolMaxNumGroup OBJECT-TYPE
    SYNTAX INTEGER (0..2048)
    ACCESS read-write
    STATUS mandatory
    DESCRIPTION
        "The Maximum Group Number this port(ADSL, PVC) can support.
        When it is 0, this port doesn't support IGMP and
        multicast, and all IGMP messages shouldn't be sent to this
        port and all IGMP messages from this port should be discarded.
        It doesn't include the MAC+VLAN entry for GMQ in ISAM R2.1.
        When modify this object, remove all multicast MAC+VALN entries
        for multicast stream and stop all multicast streams in this port,
        if set it to 0, remove MAC+VLAN entry for GMQ for this port.
        After R2.4, for NP LIM board, this threshold may be increase to 10,
        for BRCM LIM, it still is 4.
        ALCATEL NOTE:
            ACCESS:      NA            USAGE:       MAND
            PERSIST:     YES           INSRVMOD:    YES
            RANGE:       NA            DEFVALUE:    NA
            UNITS:       NA            SPARSE:      NO
            DESCR:       NA"
    DEFVAL { 0 }
    ::= { igmpChannelProtocolEntry 9 }

 
igmpChannelProtocolCurrentNumGroup OBJECT-TYPE
    SYNTAX Gauge
    ACCESS read-only
    STATUS mandatory
    DESCRIPTION
        "Indicates the current group number in this port(ADSL, PVC).
        ALCATEL NOTE:
            ACCESS:      NA            USAGE:       NA
            PERSIST:     NO            INSRVMOD:    NA
            RANGE:       NA            DEFVALUE:    0
            UNITS:       NA            SPARSE:      NO
            DESCR:       NA"
    ::= { igmpChannelProtocolEntry 10 }

igmpChannelProtocolNumFailJoinCounter OBJECT-TYPE
    SYNTAX Counter
    ACCESS read-only
    STATUS mandatory
    DESCRIPTION
        "Indicates the number of times that a join fails
        because the resultant number of simultaneous streams
        was higher than the maximum allowed on the port.
        ALCATEL NOTE:
            ACCESS:      NA            USAGE:       NA
            PERSIST:     NO            INSRVMOD:    NA
            RANGE:       NA            DEFVALUE:    0
            UNITS:       NA            SPARSE:      NO
            DESCR:       NA"
    ::= { igmpChannelProtocolEntry 11}

 
igmpChannelProtocolSysNumFailJoinCounter OBJECT-TYPE
    SYNTAX Counter
    ACCESS read-only
    STATUS mandatory
    DESCRIPTION
        "Indicates the number of times that an IGMP join fails
        because the resultant number of all/unconfigured
        groups was higher than the maximum number of
        all/unconfigured multicast groups allowed.
        ALCATEL NOTE:
            ACCESS:      NA            USAGE:       NA
            PERSIST:     NO            INSRVMOD:    NA
            RANGE:       NA            DEFVALUE:    0
            UNITS:       NA            SPARSE:      NO
            DESCR:       NA"
    ::= { igmpChannelProtocolEntry 12 }

igmpChannelProtocolCurrentPreviewNumber  OBJECT-TYPE
    SYNTAX Counter
    ACCESS read-only
    STATUS mandatory
    DESCRIPTION
        "Indicates the number of preview multicast group
        that igmp channel joins currently.
        ALCATEL NOTE:
            ACCESS:      NA            USAGE:       NA
            PERSIST:     NO            INSRVMOD:    NA
            RANGE:       NA            DEFVALUE:    0
            UNITS:       NA            SPARSE:      NO
            DESCR:       NA"
    ::= { igmpChannelProtocolEntry 13 }

igmpChannelProtocolPreviewPkgBitmap OBJECT-TYPE
    SYNTAX OCTET STRING (SIZE(128))
    ACCESS read-write
    STATUS mandatory
    DESCRIPTION
        "The purpose of this bitmap is to indicate which packages
        the user is allowed to join for preview. In accordance with the
        ASAM MIB convention, the bitmap shall function as follows:
        MSB                                     LSB
        byte 0 :  8  7  6  5  4  3  2  1
        byte 1 : 16 15 14 13 12 11 10  9
        byte 2 : 24 23 22 21 20 19 18 17
        byte 3 : 32 31 30 29 28 27 26 25
        byte 4 : 40 39 38 37 36 35 34 33
        byte 5 : 48 47 46 45 44 43 42 41
        byte 6 : 56 55 54 53 52 51 50 49
        byte 7 : 64 63 62 61 60 59 58 57
        ... ... ... ... ... ... ... ...

        byte 127 1024 1023 1022 1021 1020 1019 1018 1017
        Following the convention, byte 0 shall be the first byte (the
        left-most, most significant byte).
        ALCATEL NOTE:
            ACCESS:      NA            USAGE:       NA
            PERSIST:     YES           INSRVMOD:    YES
            RANGE:       NA            DEFVALUE:    NA
            UNITS:       NA            SPARSE:      NO
            DESCR:       NA"
    DEFVAL {'FFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFFF'H }
    ::= {igmpChannelProtocolEntry 14}



igmpChannelProtocolCurrentUncfgGroupNumber  OBJECT-TYPE
    SYNTAX Counter
    ACCESS read-only
    STATUS mandatory
    DESCRIPTION
        "Indicates the current unconfig group number in this port(ADSL, PVC).
        ALCATEL NOTE:
            ACCESS:      NA            USAGE:       NA
            PERSIST:     NO            INSRVMOD:    NA
            RANGE:       NA            DEFVALUE:    0
            UNITS:       NA            SPARSE:      NO
            DESCR:       NA"
    ::= { igmpChannelProtocolEntry 15 }

 
igmpChannelProtocolGMQToUserItfVersion OBJECT-TYPE
    SYNTAX  INTEGER   { system-inherited(1), version-2(2), version-3(3)}
    ACCESS read-write
    STATUS mandatory
    DESCRIPTION
        "The GMQToUserItfVersion object allows the operator to configure
     	whether the iGMP subsystem must initiate IGMPv2 GMQs or IGMPv3 GMQs
     	on a particular User Interface. When set to IGMPv2 the iSAM IGMP subsystem
     	initiates GMQs with v2 towards the end-user and forces the end-user on this
     	User interface to run in IGMPv2 mode; End-user initiated IGMPv3 reports are
     	not accepted.When set to IGMPv3 the iSAM IGMP subsystem initiates GMQs with 
     	v3 towards the end-user. The end-user on this User Interface may run in either
     	IGMPv2 or IGMPv3 mode. Both, end-user initiated IGMPv2 and IGMPv3 reports
     	are accepted. The object defaults to -inherited- and  inherits the 
     	GMQToUserSideVersion from the System Level object. 
     	If this User Interface (IGMP Channel) requires a different behaviour 
     	than configured in the system level object then the correct value needs 
     	to be configured in this object.
        This object defaults to inherited.
        ALCATEL NOTE:
            ACCESS:      NA            USAGE:       NA
            PERSIST:     YES           INSRVMOD:    YES
            RANGE:       NA            DEFVALUE:    NA
            UNITS:       NA            SPARSE:      NO
            DESCR:       NA"
    DEFVAL { system-inherited }
    ::={igmpChannelProtocolEntry 18}

igmpChannelProtocolTxGeneralQueries  		OBJECT-TYPE
    SYNTAX Counter

    ACCESS read-only
    STATUS mandatory
    DESCRIPTION
        "The TxGeneralQueries object counts the number of General Queries
        that have been transmitted on this user interface.
        ALCATEL NOTE:
            ACCESS:      NA            USAGE:       NA
            PERSIST:     NO            INSRVMOD:    NA
            RANGE:       NA            DEFVALUE:    0
            UNITS:       NA            SPARSE:      NO
            DESCR:       NA"
    ::={igmpChannelProtocolEntry 19}

igmpChannelProtocolTxGroupSpecificQueries 		OBJECT-TYPE
    SYNTAX Counter
    ACCESS read-only
    STATUS mandatory
    DESCRIPTION
        "The TxGroupSpecificQueries object counts the number of Group
        Specific Queries that have been transmitted on this user interface.
        ALCATEL NOTE:
            ACCESS:      NA            USAGE:       NA
            PERSIST:     NO            INSRVMOD:    NA
            RANGE:       NA            DEFVALUE:    0
            UNITS:       NA            SPARSE:      NO
            DESCR:       NA"
    ::={igmpChannelProtocolEntry 20}

igmpChannelProtocolRxV1Reports 			OBJECT-TYPE
    SYNTAX Counter
    ACCESS read-only
    STATUS mandatory
    DESCRIPTION
        "The RxV1Reports object counts the number of V1 Membership
		Reports that were received on this user interface.
        ALCATEL NOTE:
            ACCESS:      NA            USAGE:       NA
            PERSIST:     NO            INSRVMOD:    NA
            RANGE:       NA            DEFVALUE:    0
            UNITS:       NA            SPARSE:      NO
            DESCR:       NA"
    ::={igmpChannelProtocolEntry 21}


igmpChannelProtocolRxV2Reports 			OBJECT-TYPE
    SYNTAX Counter
    ACCESS read-only
    STATUS mandatory
    DESCRIPTION
        "The RxV2Reports object counts the number of V2 Membership
		Reports that were received on this user interface.
        ALCATEL NOTE:
            ACCESS:      NA            USAGE:       NA
            PERSIST:     NO            INSRVMOD:    NA
            RANGE:       NA            DEFVALUE:    0
            UNITS:       NA            SPARSE:      NO
            DESCR:       NA"
    ::={igmpChannelProtocolEntry 22}

igmpChannelProtocolRxV3Reports  			OBJECT-TYPE
    SYNTAX Counter
    ACCESS read-only
    STATUS mandatory
    DESCRIPTION
        "The RxV3Reports object counts the number of V3 Membership
		reports that were received on this user interface.
        ALCATEL NOTE:
            ACCESS:      NA            USAGE:       NA
            PERSIST:     NO            INSRVMOD:    NA
            RANGE:       NA            DEFVALUE:    0
            UNITS:       NA            SPARSE:      NO
            DESCR:       NA"
    ::={igmpChannelProtocolEntry 23}

igmpChannelProtocolRxV2Leaves 			OBJECT-TYPE
    SYNTAX Counter
    ACCESS read-only
    STATUS mandatory
    DESCRIPTION
        "The RxLeaves object counts the number of Leave messages
		that were received on this user interface.
        ALCATEL NOTE:
            ACCESS:      NA            USAGE:       NA
            PERSIST:     NO            INSRVMOD:    NA
            RANGE:       NA            DEFVALUE:    0
            UNITS:       NA            SPARSE:      NO
            DESCR:       NA"
    ::={igmpChannelProtocolEntry 24}

igmpChannelProtocolRxValidPackets 			OBJECT-TYPE
    SYNTAX Counter
    ACCESS read-only
    STATUS mandatory
    DESCRIPTION
        "The RxValidPackets object counts the total number of
		valid IGMP packets that were received on this user interface.
        ALCATEL NOTE:
            ACCESS:      NA            USAGE:       NA
            PERSIST:     NO            INSRVMOD:    NA
            RANGE:       NA            DEFVALUE:    0
            UNITS:       NA            SPARSE:      NO
            DESCR:       NA"
    ::={igmpChannelProtocolEntry 25}

igmpChannelProtocolRxInvalidPackets 			OBJECT-TYPE
    SYNTAX Counter
    ACCESS read-only
    STATUS mandatory
    DESCRIPTION
        "The RxInvalidPackets object counts the total number of
		invalid IGMP packets that were received and dropped on this
		user interface.
        ALCATEL NOTE:
            ACCESS:      NA            USAGE:       NA
            PERSIST:     NO            INSRVMOD:    NA
            RANGE:       NA            DEFVALUE:    0
            UNITS:       NA            SPARSE:      NO
            DESCR:       NA"
    ::={igmpChannelProtocolEntry 26}

igmpChannelProtocolRxUnknownTypePackets  		OBJECT-TYPE
    SYNTAX Counter
    ACCESS read-only
    STATUS mandatory
    DESCRIPTION
        "The RxUnknownTypePackets object counts the total number of
		IGMP packets with an unknown IGMP type were received on this
		user interface.
        ALCATEL NOTE:
            ACCESS:      NA            USAGE:       NA
            PERSIST:     NO            INSRVMOD:    NA
            RANGE:       NA            DEFVALUE:    0
            UNITS:       NA            SPARSE:      NO
            DESCR:       NA"
    ::={igmpChannelProtocolEntry 27}

igmpChannelProtocolRxBadLengthDrops 			OBJECT-TYPE
    SYNTAX Counter
    ACCESS read-only
    STATUS mandatory
    DESCRIPTION
        "The RxBadLengthDrops object counts the total number of
		IGMP packets that were received and dropped on this user
		interface because of a bad packet length.
        ALCATEL NOTE:
            ACCESS:      NA            USAGE:       NA
            PERSIST:     NO            INSRVMOD:    NA
            RANGE:       NA            DEFVALUE:    0
            UNITS:       NA            SPARSE:      NO
            DESCR:       NA"
    ::={igmpChannelProtocolEntry 28}

igmpChannelProtocolRxBadIpChksmDropsCounter     	OBJECT-TYPE
    SYNTAX Counter
    ACCESS read-only
    STATUS mandatory
    DESCRIPTION
        "The RxBadIpChksmDrops object counts the total number of
		IGMP packets that were received and dropped on this user
		interface because of a wrong IP Checksum being set in the
		IP header.
        ALCATEL NOTE:
            ACCESS:      NA            USAGE:       NA
            PERSIST:     NO            INSRVMOD:    NA
            RANGE:       NA            DEFVALUE:    0
            UNITS:       NA            SPARSE:      NO
            DESCR:       NA"
    ::={igmpChannelProtocolEntry 29}

igmpChannelProtocolRxBadIgmpChksmDropsCounter   	OBJECT-TYPE
    SYNTAX Counter
    ACCESS read-only
    STATUS mandatory
    DESCRIPTION
        "The RxBadIgmpChksmDrops object counts the total number of
		IGMP packets that were received and dropped on this user
		interface because of a wrong IGMP Checksum being set in the
		IGMP header.
        ALCATEL NOTE:
            ACCESS:      NA            USAGE:       NA
            PERSIST:     NO            INSRVMOD:    NA
            RANGE:       NA            DEFVALUE:    0
            UNITS:       NA            SPARSE:      NO
            DESCR:       NA"
    ::={igmpChannelProtocolEntry 30}
    
igmpChannelProtocolRowStatus     OBJECT-TYPE
    SYNTAX RowStatus
    ACCESS read-write
    STATUS mandatory
    DESCRIPTION
        "This object is used to create a new row or delete an
        existing row in this table. The possible valid values are:
            (1) active
            (4) createdAndGo
            (6) destroy
        To create an entry in this table, this object should be set to
        CreateAndGo. To delete an entry from this table, RowStatus
        should be set to Destroy value by the SNMP manager.
        ALCATEL NOTE:
            ACCESS:      NA            USAGE:       MAND
            PERSIST:     NO            INSRVMOD:    YES
            RANGE:       1|4|6         DEFVALUE:    NA
            UNITS:       NA            SPARSE:      NA
            DESCR:       NA"
       ::={igmpChannelProtocolEntry 31}

igmpChannelProtocolTxGroupSourceSpecificQueries 		OBJECT-TYPE
    SYNTAX Counter
    ACCESS read-only
    STATUS mandatory
    DESCRIPTION
        "The TxGroupSourceSpecificQueries object counts the number of Group
        Source Specific Queries that have been transmitted on this user interface.
        ALCATEL NOTE:
            ACCESS:      NA            USAGE:       NA
            PERSIST:     NO            INSRVMOD:    NA
            RANGE:       NA            DEFVALUE:    0
            UNITS:       NA            SPARSE:      NO
            DESCR:       NA"
    ::={igmpChannelProtocolEntry 32}
igmpChannelProtocolRxReportsWrongMode 		OBJECT-TYPE
    SYNTAX Counter
    ACCESS read-only
    STATUS mandatory
    DESCRIPTION
        "The RxReportsWrongMode object counts the number of reports 
	 with a wrong mode that have been received on this user interface.
        ALCATEL NOTE:
            ACCESS:      NA            USAGE:       NA
            PERSIST:     NO            INSRVMOD:    NA
            RANGE:       NA            DEFVALUE:    0
            UNITS:       NA            SPARSE:      NO
            DESCR:       NA"
    ::={igmpChannelProtocolEntry 33}

igmpChannelProtocolForkingAdminStatus   OBJECT-TYPE
    SYNTAX  INTEGER   { system-inherited(0), enable(1), disable(2) }
    ACCESS read-write
    STATUS mandatory
    DESCRIPTION
        "This object allows the operator to enable or disable IGMP forking on the IGMP 
         channel. The object defaults to -inherited- and inherits the forkingAdminStatus
         from the system level object. If the user interface (IGMP channel) requires a 
         different behaviour from forking configuration in the system level object, then 
         the correct value needs to be configured in the object.
        ALCATEL NOTE:
            ACCESS:      NA            USAGE:       NA
            PERSIST:     YES           INSRVMOD:    YES
            RANGE:       NA            DEFVALUE:    0
            UNITS:       NA            SPARSE:      NO
            DESCR:       NA"
    DEFVAL { system-inherited }
    ::={igmpChannelProtocolEntry 34}

igmpChannelProtocolOntSignallingEnabled                OBJECT-TYPE
    SYNTAX INTEGER
    ACCESS read-write
    STATUS mandatory
DESCRIPTION
        "When LT to ONT signalling is enabled (TRUE), the ONT passes IGMP Join
         requests received from the subscriber to the LT for processing. After
         the LT validates the request, 1) bandwidth not exceeded, 2) stream count
         not exceeded, 3) hosts not exceeded, 4) full-view or preview permission
         granted, 5) message is valid, the LT signals the ONT to start forwarding
         the multicast stream from the PON to the subscriber. The LT signals the
         ONT to stop forwarding after processing a Leave request or preview time
         has expired. This mode of operation will typically be used in a
         deployment where the OLT is not integrated with a third-party IPTV
         middleware application and the access control and viewer statistics
         facilities offered by the OLT are required.

         When LT to ONT signalling is disabled (FALSE), the ONT processes IGMP
         Join requests received from the subscriber. After the ONT validates the
         request, 1) stream count not exceeded, 2) message is valid, it starts
         forwarding the multicast stream from the PON to the subscriber. When a
         Leave request is received from the subscriber, the ONT stops forwarding
         the stream to the subscriber. This mode of operation will typically be
         used in a deployment where the OLT is integrated with a third-party IPTV
         middleware application, like MSTV, and the access control and viewer
         statistics facilities offered by the OLT are not required.

         When the value is INHERITED, the value is set to the value assigned to
         the igmpSystemOntSignallingEnabled object.

         Applicable only for GPON.

           ALCATEL NOTE:
           ACCESS:    NA
           USAGE:     NA
           PERSIST:   YES
           INSRVMOD:  NO
           RANGE:     true (1), false (2), inherited (3)
           DEFVALUE:  inherited (3)
           UNITS:     NA
           SPARSE:    GPON LT Specific"

       ::={igmpChannelProtocolEntry 35}
              
igmpChannelProtocolPonBitRateFailJoinCounter OBJECT-TYPE
    SYNTAX Counter
    ACCESS read-only
    STATUS mandatory
    DESCRIPTION
        "Indicates the number of times that an IGMP join fails 
         because the resultant bandwidth of all groups was higher than the
         maximum bandwidth allowed for all multicast channels on the PON. 

        ALCATEL NOTE:
            ACCESS:      NA            USAGE:       NA
            PERSIST:     NO            INSRVMOD:    NA
            RANGE:       0..65535      DEFVALUE:    0
            UNITS:       NA            SPARSE:      NO
            DESCR:       NA"

    ::= {igmpChannelProtocolEntry 36}

igmpChannelProtocolMcastVlan  OBJECT-TYPE
    SYNTAX INTEGER
    ACCESS read-write
    STATUS mandatory
    DESCRIPTION
        "If igmpSystemVlanSelection is true, scopes the selection of the 
         multicast channel to a certain vlan.
         o if different from 0, selection is within this vlan
         o if 0, selection is within the port's vlan.
         If igmpSystemVlanSelection is false, then this object is not used.

      ALCATEL NOTE:
            ACCESS:      NA            USAGE:       MAND
            PERSIST:     YES           INSRVMOD:    NO
            RANGE:       0..4093       DEFVALUE:    NA
            UNITS:       NA            SPARSE:      NO
            DESCR:       NA"
     DEFVAL { 0 }
    ::={igmpChannelProtocolEntry 37}


 igmpChannelProtocolMulticastChannelPriority            OBJECT-TYPE
    SYNTAX INTEGER
    ACCESS read-write
    STATUS mandatory
    DESCRIPTION
        "This is the default VLAN tag priority value used by the ONT
         for UNI-side multicast traffic. This value
         overwrites any VLAN priority that is received from
         the PON on GEM port 2047 and before it is
         forwarded to a UNI.

         This is a per IGMP signaling channel setting. 

         Note: The UNI may support multiple IGMP signaling channels
         in the future.

         The ONT writes this priority into Ethernet
         frames carrying multicast traffic.

         Applicable only for GPON.  Object is ignored on DSL LTs.

         A priority of 8 means the ONT will transparently pass-through 
	 the priority received in the multicast stream.

           ALCATEL NOTE:
           ACCESS:    NA
           USAGE:     NA
           PERSIST:   YES
           INSRVMOD:  YES
           RANGE:     0..8
           DEFVALUE:  8
           UNITS:     NA
           SPARSE:    NA"

    ::= {igmpChannelProtocolEntry 38}
   
 igmpChannelProtocolMcastVlanTranslation            OBJECT-TYPE
    SYNTAX TruthValue
    ACCESS read-write
    STATUS mandatory
    DESCRIPTION
        "When this object is set to true, ONT does not do any multicast vlan translation.
        When this object is set to false, ONT will do multicast vlan translation.
        Note: multicast vlan translation will be done at the LT if the 
        multicastTranslationTable is populated.

        ALU impelmentation:
        If this is Enabled, OLT will send 4096 in the multicast VID value 
        field of the uni supplemental 1 V2 message. OLT uses ponVlan from the
        multicastTranslationTable if an entry is populated with corresponding
        networkVlan when sending the control message (join message) towards the ONT.
        
        If it is disbaled, OLT will send multicast VID in the multicast VID value
        field of the uni supplemental 1 V2 message. OLT uses multicast vlan when
        sending the control message (join message) towards the ONT.

        Applicable only for GPON LT's.

        ALCATEL NOTE:
            ACCESS:      NA            USAGE:       NA
            PERSIST:     YES           INSRVMOD:    YES
            RANGE:       NA            DEFVALUE:    false
            UNITS:       NA            SPARSE:      GPON LT Specific
            DESCR:       NA"

    DEFVAL {false}
 
    ::= {igmpChannelProtocolEntry 39}
igmpChannelProtocolMode OBJECT-TYPE
        SYNTAX INTEGER {ipoe(1), pppoe(2)}
        ACCESS read-write
        STATUS mandatory
        DESCRIPTION
           "The value of this setting specifies the mode of operation for
           the IGMP facility that is located on the GLT. The Mode object
	   allows the operator to configure whether the IGMP subsystem must
	   originate GMQs on this particular IGMP channel. When set to pppoe
	   the ISAM IGMP subsystem does not originate GMQs towards the end-user. 
                (1) ipoe (default)
                (2) pppoe
        
	   Applicable only for GPON.
        
	   ALCATEL NOTE:
           ACCESS:    NA
           USAGE:     NA
           PERSIST:   YES
           INSRVMOD:  YES
           RANGE:     ipoe (1) | pppoe (2)
           DEFVALUE:  ipoe (1)
           UNITS:     NA
           SPARSE:    GPON LT Specific"

        ::={igmpChannelProtocolEntry 40}
igmpChannelProtocolServiceContextProfile OBJECT-TYPE
    SYNTAX AsamProfilePointer
    ACCESS read-write
    STATUS mandatory
    DESCRIPTION
         "The value of this object identifies the row in the
          Multicast Service Context Profile Table that applies
          to this particular entry.

           ALCATEL NOTE:
           ACCESS:    NA
           USAGE:     NA
           PERSIST:   YES
           INSRVMOD:  NO
           RANGE:     1..64
           DEFVALUE:  1
           UNITS:     NA
           SPARSE:    NA
           DESCR:     NA"

::= {igmpChannelProtocolEntry 41}

   
--=============================================================================
--  IGMP Multicast Group to Package Table
--=============================================================================

igmpMulticastGroup2PackageTable OBJECT-TYPE
    SYNTAX SEQUENCE OF  IgmpMulticastGroup2PackageEntry
    ACCESS not-accessible
    STATUS mandatory
    DESCRIPTION
        "This table lists the multicast package(s) a multicast stream belongs to.
        This table applies to pre-configured multicast streams only.
        ALCATEL NOTE:
            TABLESIZE: 4096 (max number configured multicast srcs)
            DESCR: NA"
    ::= { igmpMIB 60 }

igmpMulticastGroup2PackageEntry  OBJECT-TYPE
    SYNTAX IgmpMulticastGroup2PackageEntry
    ACCESS not-accessible
    STATUS mandatory
    DESCRIPTION
        "One entry in table igmpPackage2MulticastSrcTable.
        Row creation : An entry is created by the system.
        Row deletion : An entry is created by the system
        Index usage : the index is the multicast and source IP address.
        Note that entries will be presented to the SNMP manager in full
        lexicographical order."
    INDEX { igmpMulticastGroup2PackageClassDAddr,
                igmpMulticastGroup2PackageSourceIPAddr,
		igmpMulticastGroup2PackageVlanId,
		igmpMulticastGroup2PackagePackageIndex  }
    ::= { igmpMulticastGroup2PackageTable 1 }

IgmpMulticastGroup2PackageEntry  ::=
    SEQUENCE {
        igmpMulticastGroup2PackageClassDAddr      IpAddress,
        igmpMulticastGroup2PackageSourceIPAddr    IpAddress,
	igmpMulticastGroup2PackageVlanId          VlanId ,
	igmpMulticastGroup2PackagePackageIndex    INTEGER
    }

igmpMulticastGroup2PackageClassDAddr  OBJECT-TYPE
    SYNTAX IpAddress
    ACCESS read-only
    STATUS mandatory
    DESCRIPTION
        "The multicast group IP@ is network-byte order (big-endian).
        The class D address must be in the range of
        224.0.0.3 to 239.255.255.255 except the reserved valuses defined
        in RFC 1700. In the meantime, those IP addresses in this table
        should be different each other in low-order 23 bits to avoid
        MAC address conflict.
        ALCATEL NOTE:
            ACCESS:      NA            USAGE:       NA
            PERSIST:     NO            INSRVMOD:    NA
            RANGE:       valid multicast calls D address
                                       DEFVALUE:    NA
            UNITS:       NA            SPARSE:      NA
            DESCR:       NA"
    ::={ igmpMulticastGroup2PackageEntry   1}

igmpMulticastGroup2PackageSourceIPAddr  OBJECT-TYPE
    SYNTAX IpAddress
    ACCESS read-only
    STATUS mandatory
    DESCRIPTION
        "The multicast source IP address in network-byte order (big-endian).
        This is a unicast IP Address.
        For ASM multicast groups, the value is set to 0.0.0.0.
        ALCATEL NOTE:
            ACCESS:      NA            USAGE:       NA
            PERSIST:     NO            INSRVMOD:    NA
            RANGE:       valid IPaddress
                                       DEFVALUE:    NA
            UNITS:       NA            SPARSE:      NA
            DESCR:       NA"
    ::= { igmpMulticastGroup2PackageEntry  2}

      
       

igmpMulticastGroup2PackagePackageIndex   OBJECT-TYPE
    SYNTAX INTEGER	(1..1024)
    ACCESS read-only
    STATUS mandatory
    DESCRIPTION
        "This object identifies a particular multicast package.
	    The multicast package index can be associated with the bit position
	    in the multicastSrcPkgMembBitmap object of the Multicast Channel
	    Table, the igmpChannelProtocolPermPkgBitmap and the
	    igmpChannelProtocolPreviewPkgBitmap objects of the IGMP Channel
	    Protocol table, the igmpChannelPermPkgBitmap and
        the igmpChannelPreviewPkgBitmap of the IGMP Channel table.
        ALCATEL NOTE:
            ACCESS:      NA            USAGE:       NA
            PERSIST:     NO            INSRVMOD:    NA
            RANGE:       NA            DEFVALUE:    NA
            UNITS:       NA            SPARSE:      NO
            DESCR:       NA"
    ::={  igmpMulticastGroup2PackageEntry 3}

igmpMulticastGroup2PackageVlanId   OBJECT-TYPE
    SYNTAX  VlanId
    ACCESS read-only
    STATUS mandatory
    DESCRIPTION
        "This object identifies a particular vlanID 
         ALCATEL NOTE:
            ACCESS:      NA            USAGE:       NA
            PERSIST:     NO            INSRVMOD:    NA
            RANGE:       NA            DEFVALUE:    NA
            UNITS:       NA            SPARSE:      NO
            DESCR:       NA"
    ::={  igmpMulticastGroup2PackageEntry 4}

-- ===============================================================================
--  Multicast channel Table  : replaces Multicast source Table 
-- ===============================================================================

multicastChanneltable  OBJECT-TYPE
SYNTAX SEQUENCE OF MulticastChannelEntry
    ACCESS not-accessible
    STATUS mandatory
    DESCRIPTION
        "This table contains management information of pre-configured multicast
        source and group combination for ASM and SSM mode type operations 
	such as source and mcastgroup IP address, VLAN ID, package membership
        bitmap, traffic descriptor, etc. for each multicast source.
	Note :SSM needs IGMPv3 
        ALCATEL NOTE:
            TABLESIZE: 4096
            DESCR: NA"
        ::= { igmpMIB 67 }

multicastChannelEntry OBJECT-TYPE
    SYNTAX MulticastChannelEntry
    ACCESS not-accessible
    STATUS mandatory
    DESCRIPTION
        "This list contains management information for a pre-configured
        multicast source.
        Row creation : An entry is created by operator.
        Row deletion : An entry is deleted by operator.
        Index usage : the indices are the multicast group IP address, Source IP address
        Note that entries will be presented to the SNMP manager in full
        lexicographical order."
        INDEX { multicastChannelGroupAddr,  multicastChannelSourceAddr 
	        }

	    ::= {multicastChanneltable  1}

MulticastChannelEntry ::=
    SEQUENCE {
        multicastChannelGroupAddr               IpAddress,
	multicastChannelSourceAddr	        IpAddress,
        multicastChannelFastChanChange          TruthValue,
        multicastChannelPkgMembBitmap           OCTET STRING,
        multicastChannelName                    OCTET STRING,
        multicastChannelRowStatus               RowStatus,
        multicastChannelGuaranteedBWReserve     TruthValue,
        multicastChannelVLANID                  VlanId,
        multicastChannelServiceName             OCTET STRING,
        multicastChannelMaxPreviewDuration      INTEGER,
        multicastChannelMaxPreviewNumber        INTEGER,
        multicastChannelPreviewBlackoutDuration INTEGER,
        multicastChannelPeakBitRate             INTEGER

     }

multicastChannelGroupAddr OBJECT-TYPE
    SYNTAX IpAddress
    ACCESS not-accessible
    STATUS mandatory
    DESCRIPTION
        "The first index is the multicast group IP address of a multicast stream
        in network-byte order (big-endian). The class D address must be in
        the range of 224.0.0.3 to 239.255.255.255 except the reserved values
        defined in RFC 1700. In the meantime, those IP addresses in this
        table should be different each other in low-order 23 bits to avoid
        MAC address conflict.
        ALCATEL NOTE:
            ACCESS:      NA            USAGE:       NA
            PERSIST:     YES           INSRVMOD:    NA
            RANGE:       224.0.0.3 .. 239.255.255.255
                                       DEFVALUE:    NA
            UNITS:       NA            SPARSE:      NA
            DESCR:       NA"
    ::={multicastChannelEntry 1}

multicastChannelSourceAddr OBJECT-TYPE
    SYNTAX IpAddress
    ACCESS not-accessible
    STATUS mandatory
    DESCRIPTION
        "The second index is the Source Ip address of the SSM (Group,source) combination 
	in network-byte order (big-endian). This address is a Unicast IP address.
 	In case of ASM multicast channel (*,G) :
	   Source IP address is undefined and configured to 0.0.0.0 
	In case of SSM multicast channel (S,G) : 
	   Source IP address is a unicast IP adress.     
	    ALCATEL NOTE:
            ACCESS:      NA            USAGE:       NA
            PERSIST:     YES           INSRVMOD:    NA
            RANGE:       Unicast range 
                                       DEFVALUE:    NA
            UNITS:       NA            SPARSE:      NA
            DESCR:       NA"
    ::={multicastChannelEntry 2}
 
multicastChannelFastChanChange OBJECT-TYPE
    SYNTAX TruthValue
    ACCESS read-write
    STATUS mandatory
    DESCRIPTION
        "This object allows to configure the leave procedure to be applied
		upon the receipt of a leave request from the end-user for this
		particular multicast stream.
		When configured as 'false' then the standard leave procedure
        is initiated, otherwise , if 'true' then the fast leave with
        end-user source IP@ & MAC@ tracking is applied.
        ALCATEL NOTE:
            ACCESS:      NA            USAGE:       NA
            PERSIST:     YES           INSRVMOD:    YES
            RANGE:       NA            DEFVALUE:    NA
            UNITS:       NA            SPARSE:      NO
            DESCR:       NA"
    DEFVAL { true }
    ::={multicastChannelEntry 3}

multicastChannelPkgMembBitmap OBJECT-TYPE
    SYNTAX OCTET STRING (SIZE(128))
    ACCESS read-write
    STATUS mandatory
    DESCRIPTION
        "This object indicates to which package(s) a class D address
        belongs. A package may contain one or a group of multicast streams.
		Each bit represents a package in the igmpPackageTable.
        Thus, bit 1 corresponds to package 1, bit 2 corresponds to package 2,
        and so on.
        In accordance with the ASAM MIB convention, the bitmap shall
        function as follows:
        MSB                            LSB
        byte 0 :  8  7  6  5  4  3  2  1
        byte 1 : 16 15 14 13 12 11 10  9
        byte 2 : 24 23 22 21 20 19 18 17
        byte 3 : 32 31 30 29 28 27 26 25
        byte 4 : 40 39 38 37 36 35 34 33
        byte 5 : 48 47 46 45 44 43 42 41
        byte 6 : 56 55 54 53 52 51 50 49
        byte 7 : 64 63 62 61 60 59 58 57
        ... ... ... ... ... ... ... ...

        byte 127 1024 1023 1022 1021 1020 1019 1018 1017
        Following the convention, byte 0 shall be the first byte (the
        left-most, most significant byte).
        ALCATEL NOTE:
            ACCESS:      NA            USAGE:       NA
            PERSIST:     YES           INSRVMOD:    YES
            RANGE:       NA            DEFVALUE:    NA
            UNITS:       NA            SPARSE:      NO
            DESCR:       NA"
    DEFVAL {'0100000000000000000000000000000000000000000000000000000000000000000000000000000000000000000000000000000000000000000000000000000000000000000000000000000000000000000000000000000000000000000000000000000000000000000000000000000000000000000000000000000000000000'H }
    ::= {multicastChannelEntry 4}

multicastChannelName OBJECT-TYPE
    SYNTAX OCTET STRING (SIZE (0..32))
    ACCESS read-write
    STATUS mandatory
    DESCRIPTION
        "This is a label to make this table more operator friendly.
        Labels can be used to easily identify multicast streams.
        ALCATEL NOTE:
            ACCESS:      NA            USAGE:       NA
            PERSIST:     YES           INSRVMOD:    YES
            RANGE:       NA            DEFVALUE:    NA
            UNITS:       NA            SPARSE:      NO
            DESCR:       NA"
    DEFVAL {""}
    ::= { multicastChannelEntry 5}

 

 
multicastChannelRowStatus OBJECT-TYPE
    SYNTAX RowStatus
    ACCESS read-write
    STATUS mandatory
    DESCRIPTION
        "This object is used to create a new row or delete an
        existing row in this table. The possible valid values are:
            (1) active
            (4) createdAndGo
            (6) destroy
        To create an entry in this table, this object should be set to
        CreateAndGo. To delete an entry from this table, RowStatus
        should be set to Destroy value by the SNMP manager.
        This object does not support the dribble-mode.
        ALCATEL NOTE:
            ACCESS:      NA            USAGE:       MAND
            PERSIST:     NO            INSRVMOD:    YES
            RANGE:       1|4|6         DEFVALUE:    NA
            UNITS:       NA            SPARSE:      NA
            DESCR:       NA"
    ::= {multicastChannelEntry 6}

multicastChannelGuaranteedBWReserve OBJECT-TYPE
    SYNTAX TruthValue
    ACCESS read-write
    STATUS mandatory
    DESCRIPTION
        "This object reserves guaranteed bandwidth for a multicast channel.
        A value of true means bandwidth is reserved.
        A value of false means bandwidth is not reserved so there is a
        probability of blocking. i.e. the multicast  channel may be
        unavailable for connection.
        ALCATEL NOTE:
            ACCESS:      NA            USAGE:       NA
            PERSIST:     YES           INSRVMOD:    YES
            RANGE:       NA            DEFVALUE:    NA
            UNITS:       NA            SPARSE:      NO
            DESCR:       NA"
    DEFVAL { false }
    ::={multicastChannelEntry 7}

 
multicastChannelVLANID OBJECT-TYPE
    SYNTAX VlanId
    ACCESS read-write
    STATUS mandatory
    DESCRIPTION
        "This object specifies the VLAN in which the multicast channel is.
        ALCATEL NOTE:
            ACCESS:      NA            USAGE:       MAND
            PERSIST:     YES           INSRVMOD:    NO
            RANGE:       1..4093       DEFVALUE:    NA
            UNITS:       NA            SPARSE:      NO
            DESCR:       NA"
    ::={multicastChannelEntry 8}

multicastChannelServiceName OBJECT-TYPE
    SYNTAX OCTET STRING (SIZE (0..32))
    ACCESS read-write
    STATUS mandatory
    DESCRIPTION
        "This is a label to identify the service or service provider which
        is the originator of this multicast source.
        ALCATEL NOTE:
            ACCESS:      NA            USAGE:       NA
            PERSIST:     YES           INSRVMOD:    YES
            RANGE:       NA            DEFVALUE:    NA
            UNITS:       NA            SPARSE:      NO
            DESCR:       NA"
    DEFVAL {""}
    ::= { multicastChannelEntry 9}

multicastChannelMaxPreviewDuration  OBJECT-TYPE
    SYNTAX INTEGER (1..6000)
    ACCESS read-write
    STATUS mandatory
    DESCRIPTION
        "This object allows to configure the maximum duration of a
        preview session for this stream.
        Upon the receipt of a join request to preview this stream ,
        the user will be allowed to view this multicast stream for
		a time period equal to the time configured in this object.
		Upon expiry of this time period, the IGMP subsystem will
		autonomously stop this multicast stream and block this stream
		for the concerend IGMP channel for a period equal to the
		time configured in the PreviewBlackoutDuration object.
        ALCATEL NOTE:
            ACCESS:      NA            USAGE:       NA
            PERSIST:     YES           INSRVMOD:    NO
            RANGE:       NA            DEFVALUE:    NA
            UNITS:       secs          SPARSE:      NO
            DESCR:       NA"
    DEFVAL {180}
    ::= {multicastChannelEntry 10}


multicastChannelMaxPreviewNumber  OBJECT-TYPE
    SYNTAX INTEGER (1..100)
    ACCESS read-write
    STATUS mandatory
    DESCRIPTION
        "This object allows to configure the maximum number of previews
		per preview period for this multicast stream at a particular IGMP
		channel . 
        ALCATEL NOTE:
            ACCESS:      NA            USAGE:       NA
            PERSIST:     YES           INSRVMOD:    NO
            RANGE:       NA            DEFVALUE:    NA
            UNITS:       NA            SPARSE:      NO
            DESCR:       NA"
    DEFVAL {3}
    ::= {multicastChannelEntry 11}


multicastChannelPreviewBlackoutDuration  OBJECT-TYPE
    SYNTAX INTEGER (0..7200)
    ACCESS read-write
    STATUS mandatory
    DESCRIPTION
        "This object allows to configure the Preview Blackout Duration
        time for this multicast stream.
        ALCATEL NOTE:
            ACCESS:      NA            USAGE:       NA
            PERSIST:     YES           INSRVMOD:    NO
            RANGE:       NA            DEFVALUE:    NA
            UNITS:       secs          SPARSE:      NO
            DESCR:       NA"
    DEFVAL {0}
    ::= {multicastChannelEntry 12}

multicastChannelPeakBitRate OBJECT-TYPE
    SYNTAX INTEGER (0..100000)
    ACCESS read-write
    STATUS mandatory
    DESCRIPTION
        "The Peak Bit Rate for the traffic of this multicast channel
        in the transmit (downstream) direction.
        This value is measured in units of 1000 bits per second (kbps) based on
        Ethernet packet. 
        ALCATEL NOTE:
            ACCESS:      NA            USAGE:       NA
            PERSIST:     YES           INSRVMOD:    NO
            RANGE:       NA            DEFVALUE:    NA
            UNITS:       kbps          SPARSE:      NO
            DESCR:       NA"
    DEFVAL { 2125 }
    ::= {multicastChannelEntry 15}

-- ===============================================================================
--  Multicast channel Table  : replaces Multicast channel Table due to key extension  
-- ===============================================================================

multicastChnltable  OBJECT-TYPE
SYNTAX SEQUENCE OF MulticastChnlEntry
    ACCESS not-accessible
    STATUS mandatory
    DESCRIPTION
        "This table contains management information of pre-configured multicast
        source and group combination for ASM and SSM mode type operations 
	  such as source and mcastgroup IP address, VLAN ID, package membership
        bitmap, traffic descriptor, etc. for each multicast source.
	  Note :SSM needs IGMPv3 
        ALCATEL NOTE:
            TABLESIZE: 4096
            DESCR: NA"
        ::= { igmpMIB 79 }

multicastChnlEntry OBJECT-TYPE
    SYNTAX MulticastChnlEntry
    ACCESS not-accessible
    STATUS mandatory
    DESCRIPTION
        "This list contains management information for a pre-configured
        multicast source.
        Row creation : An entry is created by operator.
        Row deletion : An entry is deleted by operator.
        Index usage : the indices are the multicast group IP address, Source IP address
        and Vlan id.
        Note that entries will be presented to the SNMP manager in full
        lexicographical order."
        INDEX { multicastChnlGroupAddr,  multicastChnlSourceAddr, 
	        multicastChnlVLANID}

	    ::= {multicastChnltable  1}

MulticastChnlEntry ::=
    SEQUENCE {
        multicastChnlGroupAddr               IpAddress,
        multicastChnlSourceAddr	             IpAddress,
        multicastChnlFastChanChange          TruthValue,
        multicastChnlPkgMembBitmap           OCTET STRING,
        multicastChnlName                    OCTET STRING,
        multicastChnlRowStatus               RowStatus,
        multicastChnlGuaranteedBWReserve     TruthValue,
        multicastChnlVLANID                  VlanId,
        multicastChnlServiceName             OCTET STRING,
        multicastChnlMaxPreviewDuration      INTEGER,
        multicastChnlMaxPreviewNumber        INTEGER,
        multicastChnlPreviewBlackoutDuration INTEGER,
        multicastChnlPeakBitRate             INTEGER,
        multicastChnlGroupAddrEnd            IpAddress,
        multicastChnlServiceContextProfile   AsamProfilePointer
     }

multicastChnlGroupAddr OBJECT-TYPE
    SYNTAX IpAddress
    ACCESS not-accessible
    STATUS mandatory
    DESCRIPTION
        "The first index is the multicast group IP address of a multicast stream
        in network-byte order (big-endian). The class D address must be in
        the range of 224.0.0.3 to 239.255.255.255 except the reserved values
        defined in RFC 1700. In the meantime, those IP addresses in this
        table should be different each other in low-order 23 bits to avoid
        MAC address conflict.
        ALCATEL NOTE:
            ACCESS:      NA            USAGE:       NA
            PERSIST:     YES           INSRVMOD:    NA
            RANGE:       224.0.0.3 .. 239.255.255.255
                                       DEFVALUE:    NA
            UNITS:       NA            SPARSE:      NA
            DESCR:       NA"
    ::={multicastChnlEntry 1}

multicastChnlSourceAddr OBJECT-TYPE
    SYNTAX IpAddress
    ACCESS not-accessible
    STATUS mandatory
    DESCRIPTION
        "The second index is the Source Ip address of the SSM (Group,source) combination 
	in network-byte order (big-endian). This address is a Unicast IP address.
 	In case of ASM multicast channel (*,G) :
	   Source IP address is undefined and configured to 0.0.0.0 
	In case of SSM multicast channel (S,G) : 
	   Source IP address is a unicast IP adress.     
	    ALCATEL NOTE:
            ACCESS:      NA            USAGE:       NA
            PERSIST:     YES           INSRVMOD:    NA
            RANGE:       Unicast range 
                                       DEFVALUE:    NA
            UNITS:       NA            SPARSE:      NA
            DESCR:       NA"
    ::={multicastChnlEntry 2}
 
multicastChnlFastChanChange OBJECT-TYPE
    SYNTAX TruthValue
    ACCESS read-write
    STATUS mandatory
    DESCRIPTION
        "This object allows to configure the leave procedure to be applied
		upon the receipt of a leave request from the end-user for this
		particular multicast stream.
		When configured as 'false' then the standard leave procedure
        is initiated, otherwise , if 'true' then the fast leave with
        end-user source IP@ & MAC@ tracking is applied.
        ALCATEL NOTE:
            ACCESS:      NA            USAGE:       NA
            PERSIST:     YES           INSRVMOD:    YES
            RANGE:       NA            DEFVALUE:    NA
            UNITS:       NA            SPARSE:      NO
            DESCR:       NA"
    DEFVAL { true }
    ::={multicastChnlEntry 3}

multicastChnlPkgMembBitmap OBJECT-TYPE
    SYNTAX OCTET STRING (SIZE(128))
    ACCESS read-write
    STATUS mandatory
    DESCRIPTION
        "This object indicates to which package(s) a class D address
        belongs. A package may contain one or a group of multicast streams.
		Each bit represents a package in the igmpPackageTable.
        Thus, bit 1 corresponds to package 1, bit 2 corresponds to package 2,
        and so on.
        In accordance with the ASAM MIB convention, the bitmap shall
        function as follows:
        MSB                            LSB
        byte 0 :  8  7  6  5  4  3  2  1
        byte 1 : 16 15 14 13 12 11 10  9
        byte 2 : 24 23 22 21 20 19 18 17
        byte 3 : 32 31 30 29 28 27 26 25
        byte 4 : 40 39 38 37 36 35 34 33
        byte 5 : 48 47 46 45 44 43 42 41
        byte 6 : 56 55 54 53 52 51 50 49
        byte 7 : 64 63 62 61 60 59 58 57
        ... ... ... ... ... ... ... ...

        byte 127 1024 1023 1022 1021 1020 1019 1018 1017
        Following the convention, byte 0 shall be the first byte (the
        left-most, most significant byte).
        ALCATEL NOTE:
            ACCESS:      NA            USAGE:       NA
            PERSIST:     YES           INSRVMOD:    YES
            RANGE:       NA            DEFVALUE:    NA
            UNITS:       NA            SPARSE:      NO
            DESCR:       NA"
    DEFVAL {'0100000000000000000000000000000000000000000000000000000000000000000000000000000000000000000000000000000000000000000000000000000000000000000000000000000000000000000000000000000000000000000000000000000000000000000000000000000000000000000000000000000000000000'H }
    ::= {multicastChnlEntry 4}

multicastChnlName OBJECT-TYPE
    SYNTAX OCTET STRING (SIZE (0..32))
    ACCESS read-write
    STATUS mandatory
    DESCRIPTION
        "This is a label to make this table more operator friendly.
        Labels can be used to easily identify multicast streams.
        ALCATEL NOTE:
            ACCESS:      NA            USAGE:       NA
            PERSIST:     YES           INSRVMOD:    YES
            RANGE:       NA            DEFVALUE:    NA
            UNITS:       NA            SPARSE:      NO
            DESCR:       NA"
    DEFVAL {""}
    ::= { multicastChnlEntry 5}
 
multicastChnlRowStatus OBJECT-TYPE
    SYNTAX RowStatus
    ACCESS read-write
    STATUS mandatory
    DESCRIPTION
        "This object is used to create a new row or delete an
        existing row in this table. The possible valid values are:
            (1) active
            (4) createdAndGo
            (6) destroy
        To create an entry in this table, this object should be set to
        CreateAndGo. To delete an entry from this table, RowStatus
        should be set to Destroy value by the SNMP manager.
        This object does not support the dribble-mode.
        ALCATEL NOTE:
            ACCESS:      NA            USAGE:       MAND
            PERSIST:     NO            INSRVMOD:    YES
            RANGE:       1|4|6         DEFVALUE:    NA
            UNITS:       NA            SPARSE:      NA
            DESCR:       NA"
    ::= {multicastChnlEntry 6}

multicastChnlGuaranteedBWReserve OBJECT-TYPE
    SYNTAX TruthValue
    ACCESS read-write
    STATUS mandatory
    DESCRIPTION
        "This object reserves guaranteed bandwidth for a multicast channel.
        A value of true means bandwidth is reserved.
        A value of false means bandwidth is not reserved so there is a
        probability of blocking. i.e. the multicast  channel may be
        unavailable for connection.
        ALCATEL NOTE:
            ACCESS:      NA            USAGE:       NA
            PERSIST:     YES           INSRVMOD:    YES
            RANGE:       NA            DEFVALUE:    NA
            UNITS:       NA            SPARSE:      NO
            DESCR:       NA"
    DEFVAL { false }
    ::={multicastChnlEntry 7}

 
multicastChnlVLANID OBJECT-TYPE
    SYNTAX VlanId
    ACCESS not-accessible
    STATUS mandatory
    DESCRIPTION
        "This object specifies the VLAN in which the multicast channel is.
        ALCATEL NOTE:
            ACCESS:      NA            USAGE:       MAND
            PERSIST:     YES           INSRVMOD:    NO
            RANGE:       1..4093       DEFVALUE:    NA
            UNITS:       NA            SPARSE:      NO
            DESCR:       NA"
    ::={multicastChnlEntry 8}

multicastChnlServiceName OBJECT-TYPE
    SYNTAX OCTET STRING (SIZE (0..32))
    ACCESS read-write
    STATUS mandatory
    DESCRIPTION
        "This is a label to identify the service or service provider which
        is the originator of this multicast source.
        ALCATEL NOTE:
            ACCESS:      NA            USAGE:       NA
            PERSIST:     YES           INSRVMOD:    YES
            RANGE:       NA            DEFVALUE:    NA
            UNITS:       NA            SPARSE:      NO
            DESCR:       NA"
    DEFVAL {""}
    ::= { multicastChnlEntry 9}

multicastChnlMaxPreviewDuration  OBJECT-TYPE
    SYNTAX INTEGER (1..6000)
    ACCESS read-write
    STATUS mandatory
    DESCRIPTION
        "This object allows to configure the maximum duration of a
        preview session for this stream.
        Upon the receipt of a join request to preview this stream ,
        the user will be allowed to view this multicast stream for
		a time period equal to the time configured in this object.
		Upon expiry of this time period, the IGMP subsystem will
		autonomously stop this multicast stream and block this stream
		for the concerend IGMP channel for a period equal to the
		time configured in the PreviewBlackoutDuration object.
        ALCATEL NOTE:
            ACCESS:      NA            USAGE:       NA
            PERSIST:     YES           INSRVMOD:    NO
            RANGE:       NA            DEFVALUE:    NA
            UNITS:       secs          SPARSE:      NO
            DESCR:       NA"
    DEFVAL {180}
    ::= {multicastChnlEntry 10}


multicastChnlMaxPreviewNumber  OBJECT-TYPE
    SYNTAX INTEGER (1..100)
    ACCESS read-write
    STATUS mandatory
    DESCRIPTION
        "This object allows to configure the maximum number of previews
		per preview period for this multicast stream at a particular IGMP
		channel . 
        ALCATEL NOTE:
            ACCESS:      NA            USAGE:       NA
            PERSIST:     YES           INSRVMOD:    NO
            RANGE:       NA            DEFVALUE:    NA
            UNITS:       NA            SPARSE:      NO
            DESCR:       NA"
    DEFVAL {3}
    ::= {multicastChnlEntry 11}


multicastChnlPreviewBlackoutDuration  OBJECT-TYPE
    SYNTAX INTEGER (0..7200)
    ACCESS read-write
    STATUS mandatory
    DESCRIPTION
        "This object allows to configure the Preview Blackout Duration
        time for this multicast stream.
        ALCATEL NOTE:
            ACCESS:      NA            USAGE:       NA
            PERSIST:     YES           INSRVMOD:    NO
            RANGE:       NA            DEFVALUE:    NA
            UNITS:       secs          SPARSE:      NO
            DESCR:       NA"
    DEFVAL {0}
    ::= {multicastChnlEntry 12}

multicastChnlPeakBitRate OBJECT-TYPE
    SYNTAX INTEGER (0..100000)
    ACCESS read-write
    STATUS mandatory
    DESCRIPTION
        "The Peak Bit Rate for the traffic of this multicast channel
        in the transmit (downstream) direction.
        This value is measured in units of 1000 bits per second (kbps) based on
        Ethernet packet. 
        ALCATEL NOTE:
            ACCESS:      NA            USAGE:       NA
            PERSIST:     YES           INSRVMOD:    NO
            RANGE:       NA            DEFVALUE:    NA
            UNITS:       kbps          SPARSE:      NO
            DESCR:       NA"
    DEFVAL { 2125 }
    ::= {multicastChnlEntry 15}

multicastChnlGroupAddrEnd OBJECT-TYPE
        SYNTAX IpAddress
        ACCESS read-write
        STATUS mandatory
        DESCRIPTION
               "This object is the address of a multicast source in network-byte
                order (big-endian). The class D address must be in
                the range of 224.0.0.3 to 239.255.255.255 except the reserved values
                defined in RFC 1700. In the meantime, those IP addresses in this
                table should be different each other in low-order 23 bits to avoid
                MAC address conflict.

                A range of multicast IP addresses (group IP
                addesses) can be defined for the entry.

                The multicastChnlGroupAddr and multicastChnlGroupAddrEnd
                objects respectively define the starting adddress and the ending
                adddress of the range. Both objects can be set to the same value
                to indicate a single multicast IP address for the entry.

           ALCATEL NOTE:
           ACCESS:    NA               USAGE:     NA
           PERSIST:   YES              INSRVMOD:  NO
           RANGE:     224.0.0.3 .. 239.255.255.255
           DEFVALUE:  0.0.0.0          UNITS:     NA 
           SPARSE:    NA               DESCR:     NA"

        ::={ multicastChnlEntry 16}

multicastChnlServiceContextProfile OBJECT-TYPE
    SYNTAX AsamProfilePointer
    ACCESS read-write
    STATUS mandatory
    DESCRIPTION
        " The value of this object identifies the row in the
          Multicast Service Context Profile Table that applies
          to this particular entry.

          Default = 1

           ALCATEL NOTE:
           ACCESS:    NA               USAGE:     NA
           PERSIST:   YES              INSRVMOD:  NO
           RANGE:     1..64            DEFVALUE:  1
           UNITS:     NA               SPARSE:    NA
           DESCR:     NA"

        ::= { multicastChnlEntry 17}


-- ===============================================================================
--  IGMP Module Multicast Channel and Group Expansion Table.
-- ===============================================================================

igmpModuleMcastChannelExpTable OBJECT-TYPE
    SYNTAX SEQUENCE OF IgmpModuleMcastChannelEntry
    ACCESS not-accessible
    STATUS mandatory
    DESCRIPTION
        "This table contains multicast channel statistics maintained by
        IGMP proxy, it is only for those groups configured in Multicast
        Channel Table.
        ALCATEL NOTE:
            TABLESIZE: 4096 * nmbr of slots
            DESCR: NA"
    ::= {igmpMIB 68}

igmpModuleMcastChannelEntry OBJECT-TYPE
    SYNTAX IgmpModuleMcastChannelEntry
    ACCESS not-accessible
    STATUS mandatory
    DESCRIPTION
        "Each entry reflects the multicast source statistics collected
        by the on-board controller on LT, it is only for those source and group
        addresses configured in Multicast Channel  Table.
        Row creation : An entry is created by system per slot when
                 corresponding entry in multicastChannelTable is created.
        Row deletion :
        Index usage : the index is the .
        Note that entries will be presented to the SNMP manager in full
        lexicographical order."
    INDEX { igmpModuleSlotIndex, multicastChannelGroupAddr, multicastChannelSourceAddr
            }

    ::= { igmpModuleMcastChannelExpTable 1}

IgmpModuleMcastChannelEntry ::=
    SEQUENCE {
        igmpModuleMcastChannelPeakSubscrIGMPChans      Counter,
        igmpModuleMcastChannelPeakTime                 NetworkTimeInSeconds,
        igmpModuleMcastChannelCurrentSubscrIGMPChans   Counter,
        igmpModuleMcastChannelClearStats               TruthValue,
        igmpModuleMcastChannelConnectFailCounter       Counter,
        igmpModuleMcastChannelUserSuccJoinReqCounter   Counter
     }

igmpModuleMcastChannelPeakSubscrIGMPChans OBJECT-TYPE
    SYNTAX Counter
    ACCESS read-only
    STATUS mandatory
    DESCRIPTION
        "This is a statistic indicating the peak number of subscribed
        IGMP channels which have members connected to the stream since
        the last statistics reset. It is only for those multicast channels/streams
        configured in the Multicast Channel Table.
        ALCATEL NOTE:
            ACCESS:      NA            USAGE:       NA
            PERSIST:     NO            INSRVMOD:    NA
            RANGE:       NA            DEFVALUE:    0
            UNITS:       IGMP channels SPARSE:      NO
            DESCR:       NA"
    ::={ igmpModuleMcastChannelEntry 1}

igmpModuleMcastChannelPeakTime OBJECT-TYPE
    SYNTAX NetworkTimeInSeconds
    ACCESS read-only
    STATUS mandatory
    DESCRIPTION
        "This statistic indicates the network time in seconds of when the
        peak number of subscribed IGMP channels for the multicast channel/stream occurred.
        It is only for those groups configured in Multicast Channel Table.
        ALCATEL NOTE:
            ACCESS:      NA            USAGE:       NA
            PERSIST:     NO            INSRVMOD:    NA
            RANGE:       NA            DEFVALUE:    0
            UNITS:       secs          SPARSE:      NO
            DESCR:       NA"
    ::={ igmpModuleMcastChannelEntry 2}

igmpModuleMcastChannelCurrentSubscrIGMPChans OBJECT-TYPE
    SYNTAX Counter
    ACCESS read-only
    STATUS mandatory
    DESCRIPTION
        "This is a statistic indicating the current number of subscribed
        IGMP channels for the multicast stream/channele. It is only for those channels
        configured in Multicast Channel Table.
        ALCATEL NOTE:
            ACCESS:      NA            USAGE:       NA
            PERSIST:     NO            INSRVMOD:    NA
            RANGE:       NA            DEFVALUE:    0
            UNITS:       IGMP channels SPARSE:      NO
            DESCR:       NA"
    ::={ igmpModuleMcastChannelEntry 3}

igmpModuleMcastChannelClearStats OBJECT-TYPE
    SYNTAX TruthValue
    ACCESS read-write
    STATUS mandatory
    DESCRIPTION
        "When set to true, all statistics in this table entry will be
        cleared. When set to false, the request is ignored.
        ALCATEL NOTE:
            ACCESS:      NA            USAGE:       NA
            PERSIST:     NO            INSRVMOD:    YES
            RANGE:       NA            DEFVALUE:    NA
            UNITS:       NA            SPARSE:      NO
            DESCR:       NA"
    DEFVAL {false}
    ::={ igmpModuleMcastChannelEntry 4}

igmpModuleMcastChannelConnectFailCounter OBJECT-TYPE
    SYNTAX Counter
    ACCESS read-only
    STATUS mandatory
    DESCRIPTION
        "This object indicates the number of times that an attempt to
        create a multicast connection fails. It is only for those streams/channels
        configured in Multicast Channel Table.
        ALCATEL NOTE:
            ACCESS:      NA            USAGE:       NA
            PERSIST:     NO            INSRVMOD:    NA
            RANGE:       NA            DEFVALUE:    0
            UNITS:       NA            SPARSE:      NO
            DESCR:       NA"
    ::={ igmpModuleMcastChannelEntry 5}

igmpModuleMcastChannelUserSuccJoinReqCounter  OBJECT-TYPE
    SYNTAX Counter
    ACCESS read-only
    STATUS mandatory
    DESCRIPTION
        "This object indicates the number of succesful joins by a user
        for this configured channel.
        ALCATEL NOTE:
            ACCESS:      NA            USAGE:       NA
            PERSIST:     NO            INSRVMOD:    NA
            RANGE:       NA            DEFVALUE:    0
            UNITS:       NA            SPARSE:      NO
            DESCR:       NA"
    ::={ igmpModuleMcastChannelEntry 6}

-- =============================================================================
-- multicastMonitorTable
-- =============================================================================

multicastMonitorTable  OBJECT-TYPE
        SYNTAX SEQUENCE OF MulticastMonitorEntry
        ACCESS not-accessible
        STATUS mandatory
        DESCRIPTION
            "This table supports on-demand monitoring of the loss-of-traffic
             state for a specified multicast stream.

             A loss-of-traffic monitor is supported by counting packets for a
             given multicast stream for a specified time period. After the
             period has expired, the packet count is compared to the packet
             threshold. 

             If the packet count is less than or equal to the threshold, and
             the stream was not previously in the loss-of-traffic state,
             a loss-of-traffic alarm is generated and the stream is marked
             as being in the loss-of-traffic state. 

             If the packet count is greater than the threshold, and the stream
             was previously in the loss-of-traffic state, a clear notification
             is generated and the loss-of-traffic state is removed for the stream.

             This table provides one row for each monitored multicast stream.
             Only configured multicast channels can be monitored.


           ALCATEL NOTE:
           TABLESIZE:  8"

        ::= { igmpMIB 65 }

   multicastMonitorEntry  OBJECT-TYPE
        SYNTAX MulticastMonitorEntry
        ACCESS not-accessible
        STATUS mandatory
        DESCRIPTION 
            "An entry in the Multicast Monitor Table."

        INDEX { multicastMonitorClassDAddr,
                multicastMonitorSrcIpAddr,
		multicastMonitorVLANID }

        ::= { multicastMonitorTable 1 }

   MulticastMonitorEntry ::= SEQUENCE {
       multicastMonitorClassDAddr                        IpAddress,
       multicastMonitorRowStatus                         RowStatus,
       multicastMonitorLossOfTrafficThreshold            Threshold,
       multicastMonitorLossOfTrafficDuration             INTEGER,
       multicastMonitorVLANID                            INTEGER,
       multicastMonitorSrcIpAddr                         IpAddress
        }

multicastMonitorClassDAddr OBJECT-TYPE
        SYNTAX IpAddress
        ACCESS not-accessible
        STATUS mandatory
        DESCRIPTION
            "This index is the address of a multicast source in network-byte
             order (big-endian). The class D address must be in the range of
             224.0.0.0 to 239.255.255.255 except for 224.0.0.1, 224.0.0.2 and
             224.0.0.22. 

             The value is valid if it matches a multicastChannelGroupAddr
             entry provisioned in multicastChannelTable.

           ALCATEL NOTE:
           ACCESS:    NA
           USAGE:     NA
           PERSIST:   YES
           INSRVMOD:  NA
           RANGE:     224.0.0.0 .. 239.255.255.255
                      but not 224.0.0.1, 224.0.0.2, 224.0.0.22
           DEFVALUE:  NA
           UNITS:     NA 
           SPARSE:    NA
           DESCR:     GPON LT Specific"

        ::={ multicastMonitorEntry 1 }

multicastMonitorRowStatus OBJECT-TYPE
        SYNTAX RowStatus
        ACCESS read-write
        STATUS mandatory
        DESCRIPTION
                "This object is used to create a new row or delete an
                existing row in this table. The possible valid values are:
                        (1) active
                        (2) notInService 
                        (4) createdAndGo
                        (6) destroy
                To create an entry in this table, this object should be set to
                CreateAndGo. To delete an entry from this table, RowStatus
                should be set to Destroy value by the SNMP manager.
                This object does not support the dribble-mode.
                
           ALCATEL NOTE:
           ACCESS:    NA
           USAGE:     NA
           PERSIST:   YES
           INSRVMOD:  YES
           RANGE:     active | notInService | createAndGo | destroy
           DEFVALUE:  NA
           UNITS:     NA 
           SPARSE:    NA
           DESCR:     GPON LT Specific"

        ::= {multicastMonitorEntry 2 }


   multicastMonitorLossOfTrafficThreshold  OBJECT-TYPE
        SYNTAX Threshold
        ACCESS read-write
        STATUS mandatory
        DESCRIPTION 
            "This attribute is the loss-of-traffic alarm setting.

             If after multicastMonitorLossOfTrafficDuration,
             the packet count is less than or equal to
             multicastMonitorLossOfTrafficThreshold, then
             the multicast flow state is set to true.

             If after multicastMonitorLossOfTrafficDuration,
             the packet count is greater than
             multicastMonitorLossOfTrafficThreshold, then
             the multicast flow state is set to false.

             If the multicast flow state transitions from false to true,
             an autonomous alarm is generated.

             If the multicast flow state transitions from true to false,
             an clear notification is generated.

           ALCATEL NOTE:
           ACCESS:    NA
           USAGE:     NA
           PERSIST:   YES
           INSRVMOD:  YES
           RANGE:     0..4294967295
           DEFVALUE:  0
           UNITS:     packets
           SPARSE:    NA
           DESCR:     GPON LT Specific"

        ::= { multicastMonitorEntry 3 }

   multicastMonitorLossOfTrafficDuration  OBJECT-TYPE
        SYNTAX INTEGER
        ACCESS read-write
        STATUS mandatory
        DESCRIPTION 
            "This attribute is the amount of time to count packets for the
             monitored multicast stream. At the end of this time period,
             the packet count is compared against
             multicastMonitorLossOfTrafficThreshold to determine if
             the multicast flow state can be set to true or false
             

           ALCATEL NOTE:
           ACCESS:    NA
           USAGE:     NA
           PERSIST:   YES
           INSRVMOD:  YES
           RANGE:     5..2147483647
           DEFVALUE:  15
           UNITS:     seconds
           SPARSE:    NA
           DESCR:     GPON LT Specific"

        ::= { multicastMonitorEntry 4 }

   multicastMonitorVLANID OBJECT-TYPE
           SYNTAX INTEGER
           ACCESS not-accessible
           STATUS mandatory
           DESCRIPTION
                 "This index specifies the VLAN in which the multicast source
                 is delivered.

            ALCATEL NOTE:
            ACCESS:    NA
            USAGE:     NA
            PERSIST:   YES
            INSRVMOD:  NO
            RANGE:     0..4093
            DEFVALUE:  NA
            UNITS:     NA 
            SPARSE:    NA
            DESCR:     GPON LT specific"

         ::={ multicastMonitorEntry 5}

multicastMonitorSrcIpAddr OBJECT-TYPE
    SYNTAX IpAddress
    ACCESS not-accessible
    STATUS mandatory
    DESCRIPTION
        "This index is the Source Ip address of the SSM (Group,source) combination 
    in network-byte order (big-endian). This address is a Unicast IP address.
    In case of ASM multicast channel (*,G) :
       Source IP address is undefined and configured to 0.0.0.0 
    In case of SSM multicast channel (S,G) : 
       Source IP address is a unicast IP adress.

        ALCATEL NOTE:
            ACCESS:      NA
            USAGE:       NA
            PERSIST:     YES
            INSRVMOD:    NA
            RANGE:       Unicast range
            DEFVALUE:    NA
            UNITS:       NA
            SPARSE:      NA
            DESCR:       GPON LT Specific"

    ::={ multicastMonitorEntry 6}
    
    
    
-- ===============================================================================
--  Multicast Static branch Table 
-- ===============================================================================

multicastStaticBranchTable  OBJECT-TYPE
	SYNTAX SEQUENCE OF MulticastStaticBranchEntry
	 ACCESS not-accessible
	STATUS mandatory
    DESCRIPTION
        "This table contains management information of static multicast
        branch.These multicast branches are configured by administrator,
        And can not be deleted dynamically.  This table applies to both
        the NELT-B and GPON-LTs.
        ALCATEL NOTE:
            TABLESIZE: 36864
            DESCR: NA"
        ::= { igmpMIB 77 }

multicastStaticBranchEntry OBJECT-TYPE
    SYNTAX MulticastStaticBranchEntry
    ACCESS not-accessible
    STATUS mandatory
    DESCRIPTION
        "This list contains management information for a static multicast
         branch entry.
        Row creation : An entry is created by operator.
        Row deletion : An entry is deleted by operator.
        Index usage : the indices are the multicast group IP address & Source IP address &
                      interface index
        Note that entries will be presented to the SNMP manager in full
        lexicographical order."
        INDEX { multicastStaticBranchGroupAddr, multicastStaticBranchSourceAddr, multicastStaticBranchPort}

	    ::= {multicastStaticBranchTable  1}

MulticastStaticBranchEntry ::=
    SEQUENCE {
        multicastStaticBranchGroupAddr              IpAddress,
	multicastStaticBranchSourceAddr	            IpAddress,
        multicastStaticBranchPort                   InterfaceIndex, 
        multicastStaticBranchRowStatus              RowStatus
     }

multicastStaticBranchGroupAddr OBJECT-TYPE
    SYNTAX IpAddress
    ACCESS not-accessible
    STATUS mandatory
    DESCRIPTION
        "The first index is the multicast group IP address of a multicast stream
        in network-byte order (big-endian). The class D address must be in
        the range of 224.0.0.3 to 239.255.255.255 except the reserved values
        defined in RFC 1700. In the meantime, those IP addresses in this
        table should be different each other in low-order 23 bits to avoid
        MAC address conflict.
        ALCATEL NOTE:
            ACCESS:      NA            USAGE:       NA
            PERSIST:     YES           INSRVMOD:    NA
            RANGE:       224.0.0.3 .. 239.255.255.255
                                       DEFVALUE:    NA
            UNITS:       NA            SPARSE:      NA
            DESCR:       NA"
::={multicastStaticBranchEntry 1}




multicastStaticBranchSourceAddr OBJECT-TYPE
    SYNTAX IpAddress
    ACCESS not-accessible
    STATUS mandatory
    DESCRIPTION
        "The second index is the Source Ip address of the SSM (Group,source) combination 
	in network-byte order (big-endian). This address is a Unicast IP address.
 	In case of ASM multicast channel (*,G) :
	   Source IP address is undefined and configured to 0.0.0.0 
	In case of SSM multicast channel (S,G) : 
	   Source IP address is a unicast IP adress.     
	    ALCATEL NOTE:
            ACCESS:      NA            USAGE:       NA
            PERSIST:     YES           INSRVMOD:    NA
            RANGE:       Unicast range 
                                       DEFVALUE:    NA
            UNITS:       NA            SPARSE:      NA
            DESCR:       NA"
    ::={multicastStaticBranchEntry 2}
 
multicastStaticBranchPort OBJECT-TYPE
    SYNTAX InterfaceIndex
    ACCESS not-accessible
    STATUS mandatory
    DESCRIPTION
        "This is the IfIndex associated with the access interface
		which is carrying the multicast stream to egress port.
        ALCATEL NOTE:
            ACCESS:      NA            USAGE:       MAND
            PERSIST:     YES           INSRVMOD:    NO
            RANGE:       NA            DEFVALUE:    NA
            UNITS:       NA            SPARSE:      NO
            DESCR:       NA"
::={multicastStaticBranchEntry 3}


multicastStaticBranchRowStatus OBJECT-TYPE
    SYNTAX RowStatus
    ACCESS read-write
    STATUS mandatory
    DESCRIPTION
        "This object is used to create a new row or delete an
        existing row in this table. The possible valid values are:
            (1) active
            (4) createdAndGo
            (6) destroy
        To create an entry in this table, this object should be set to
        CreateAndGo. To delete an entry from this table, RowStatus
        should be set to Destroy value by the SNMP manager.
        This object does not support the dribble-mode.
        ALCATEL NOTE:
            ACCESS:      NA            USAGE:       MAND
            PERSIST:     NO            INSRVMOD:    YES
            RANGE:       1|4|6         DEFVALUE:    NA
            UNITS:       NA            SPARSE:      NA
            DESCR:       NA"
    ::= { multicastStaticBranchEntry 4}


-- ===============================================================================
--  IGMP Module Multicast Channel and Group Expansion Table.
-- ===============================================================================

igmpModuleMcastChnlExpTable OBJECT-TYPE
    SYNTAX SEQUENCE OF IgmpModuleMcastChnlEntry
    ACCESS not-accessible
    STATUS mandatory
    DESCRIPTION
        "This table contains multicast channel statistics maintained by
        IGMP proxy, it is only for those groups configured in Multicast
        Channel Table.
        ALCATEL NOTE:
            TABLESIZE: 4096 * nmbr of slots
            DESCR: NA"
    ::= {igmpMIB 80}

igmpModuleMcastChnlEntry OBJECT-TYPE
    SYNTAX IgmpModuleMcastChnlEntry
    ACCESS not-accessible
    STATUS mandatory
    DESCRIPTION
        "Each entry reflects the multicast source statistics collected
        by the on-board controller on LT, it is only for those source and group
        addresses configured in Multicast Channel  Table.
        Row creation :An entry is created when the first IGMP Join is received for that group in that slot.
        Row deletion :The oldest inactive group entry is deleted when an IGMP Join is received for 4097th group in that slot.
        Index usage : the index is the .
        Note that entries will be presented to the SNMP manager in full
        lexicographical order."
    INDEX { igmpModuleSlotIndex, multicastChnlGroupAddr, multicastChnlSourceAddr,
            multicastChnlVLANID}

    ::= { igmpModuleMcastChnlExpTable 1}

IgmpModuleMcastChnlEntry ::=
    SEQUENCE {
        igmpModuleMcastChnlPeakSubscrIGMPChans      Counter,
        igmpModuleMcastChnlPeakTime                 NetworkTimeInSeconds,
        igmpModuleMcastChnlCurrentSubscrIGMPChans   Counter,
        igmpModuleMcastChnlClearStats               TruthValue,
        igmpModuleMcastChnlConnectFailCounter       Counter,
        igmpModuleMcastChnlUserSuccJoinReqCounter   Counter
     }

igmpModuleMcastChnlPeakSubscrIGMPChans OBJECT-TYPE
    SYNTAX Counter
    ACCESS read-only
    STATUS mandatory
    DESCRIPTION
        "This is a statistic indicating the peak number of subscribed
        IGMP channels which have members connected to the stream since
        the last statistics reset. It is only for those multicast channels/streams
        configured in the Multicast Channel Table.
        ALCATEL NOTE:
            ACCESS:      NA            USAGE:       NA
            PERSIST:     NO            INSRVMOD:    NA
            RANGE:       NA            DEFVALUE:    0
            UNITS:       IGMP channels SPARSE:      NO
            DESCR:       NA"
    ::={ igmpModuleMcastChnlEntry 1}

igmpModuleMcastChnlPeakTime OBJECT-TYPE
    SYNTAX NetworkTimeInSeconds
    ACCESS read-only
    STATUS mandatory
    DESCRIPTION
        "This statistic indicates the network time in seconds of when the
        peak number of subscribed IGMP channels for the multicast channel/stream occurred.
        It is only for those groups configured in Multicast Channel Table.
        ALCATEL NOTE:
            ACCESS:      NA            USAGE:       NA
            PERSIST:     NO            INSRVMOD:    NA
            RANGE:       NA            DEFVALUE:    0
            UNITS:       secs          SPARSE:      NO
            DESCR:       NA"
    ::={ igmpModuleMcastChnlEntry 2}

igmpModuleMcastChnlCurrentSubscrIGMPChans OBJECT-TYPE
    SYNTAX Counter
    ACCESS read-only
    STATUS mandatory
    DESCRIPTION
        "This is a statistic indicating the current number of subscribed
        IGMP channels for the multicast stream/channele. It is only for those channels
        configured in Multicast Channel Table.
        ALCATEL NOTE:
            ACCESS:      NA            USAGE:       NA
            PERSIST:     NO            INSRVMOD:    NA
            RANGE:       NA            DEFVALUE:    0
            UNITS:       IGMP channels SPARSE:      NO
            DESCR:       NA"
    ::={ igmpModuleMcastChnlEntry 3}

igmpModuleMcastChnlClearStats OBJECT-TYPE
    SYNTAX TruthValue
    ACCESS read-write
    STATUS mandatory
    DESCRIPTION
        "When set to true, all statistics in this table entry will be
        cleared. When set to false, the request is ignored.
        ALCATEL NOTE:
            ACCESS:      NA            USAGE:       NA
            PERSIST:     NO            INSRVMOD:    YES
            RANGE:       NA            DEFVALUE:    NA
            UNITS:       NA            SPARSE:      NO
            DESCR:       NA"
    DEFVAL {false}
    ::={ igmpModuleMcastChnlEntry 4}

igmpModuleMcastChnlConnectFailCounter OBJECT-TYPE
    SYNTAX Counter
    ACCESS read-only
    STATUS mandatory
    DESCRIPTION
        "This object indicates the number of times that an attempt to
        create a multicast connection fails. It is only for those streams/channels
        configured in Multicast Channel Table.
        ALCATEL NOTE:
            ACCESS:      NA            USAGE:       NA
            PERSIST:     NO            INSRVMOD:    NA
            RANGE:       NA            DEFVALUE:    0
            UNITS:       NA            SPARSE:      NO
            DESCR:       NA"
    ::={ igmpModuleMcastChnlEntry 5}

igmpModuleMcastChnlUserSuccJoinReqCounter  OBJECT-TYPE
    SYNTAX Counter
    ACCESS read-only
    STATUS mandatory
    DESCRIPTION
        "This object indicates the number of succesful joins by a user
        for this configured channel.
        ALCATEL NOTE:
            ACCESS:      NA            USAGE:       NA
            PERSIST:     NO            INSRVMOD:    NA
            RANGE:       NA            DEFVALUE:    0
            UNITS:       NA            SPARSE:      NO
            DESCR:       NA"
    ::={ igmpModuleMcastChnlEntry 6}

-- =============================================================================
-- multicastServiceContextProfileTable
--
-- This table contains service provider information.
-- 
-- =============================================================================

multicastServiceContextProfileTable OBJECT-TYPE
    SYNTAX SEQUENCE OF MulticastServiceContextProfileEntry
    ACCESS not-accessible
    STATUS mandatory
    DESCRIPTION
        "This object contains a table for creating and storing
         service context profiles. A service context profile is
         used to 1) associate one or more multicast channels
         with a particular service provider, and 2) associate
         one or more IGMP signaling channels (or users) with
         a particular service provider."

::= { igmpMIB 84 }

multicastServiceContextProfileEntry OBJECT-TYPE
    SYNTAX MulticastServiceContextProfileEntry
    ACCESS not-accessible
    STATUS mandatory
    DESCRIPTION
        "Rows of this table contain service context Profiles."

    INDEX {multicastServiceContextProfileIndex}

::= {multicastServiceContextProfileTable 1}

MulticastServiceContextProfileEntry ::=
    SEQUENCE { 
        multicastServiceContextProfileIndex     AsamProfileIndex,
        multicastServiceContextProfileName      AsamProfileName,
        multicastServiceContextProfileRowStatus RowStatus
}

multicastServiceContextProfileIndex OBJECT-TYPE
    SYNTAX AsamProfileIndex
    ACCESS not-accessible
    STATUS mandatory
    DESCRIPTION
        "This object is the index to the multicastServiceContextProfileTable.

         The table always contains profile 1. This is the default profile.

           ALCATEL NOTE:
           ACCESS:    NA
           USAGE:     NA
           PERSIST:   YES
           INSRVMOD:  NO
           RANGE:     1..64
           DEFVALUE:  NA
           UNITS:     NA
           SPARSE:    NA
           DESCR:     NA"

::= {multicastServiceContextProfileEntry 1}

multicastServiceContextProfileName OBJECT-TYPE
    SYNTAX AsamProfileName
    ACCESS read-write
    STATUS mandatory
    DESCRIPTION
        "Octet string storing the operator-given name of the profile

           ALCATEL NOTE:
           ACCESS:    NA
           USAGE:     NA
           PERSIST:   YES
           INSRVMOD:  NO
           RANGE:     1..32 characters
           DEFVALUE:  NA
           UNITS:     NA
           SPARSE:    NA
           DESCR:     NA"

::= {multicastServiceContextProfileEntry 2}

multicastServiceContextProfileRowStatus OBJECT-TYPE
    SYNTAX RowStatus
    ACCESS read-write
    STATUS mandatory
    DESCRIPTION
             "This object is used to create a new row or modify or delete an 
              existing row in this table. The usage is as per standard semantics of 'RowStatus'
              defined in SNMPv2-TC, with following limitations:
              The entry associated with a Profile that is being used may not be deleted.

          ALCATEL NOTE:
          ACCESS: NA
          USAGE: NA
          PERSIST: YES
          INSRVMOD: YES
          RANGE: active | notInService | createAndGo | destroy
          DEFVALUE: NA
          UNITS: NA
          SPARSE: NA
          DESCR: NA"

::= { multicastServiceContextProfileEntry 3 }

multicastServiceContextProfileMappingTable OBJECT-TYPE
     SYNTAX SEQUENCE OF MulticastServiceContextProfileMappingEntry
     ACCESS not-accessible
     STATUS mandatory
     DESCRIPTION
          "This object contains table for service context profile 
name to index mapping"

::= { igmpMIB 85 }

multicastServiceContextProfileMappingEntry OBJECT-TYPE
     SYNTAX MulticastServiceContextProfileMappingEntry
     ACCESS not-accessible
     STATUS mandatory
     DESCRIPTION
          "An entry (conceptual row) representing the service context
Profile name to index mapping. The system automatically creates an entry 
In this table for each corresponding entry created in the service context 
Table. Similarly, when an entry is deleted from service context profile
Table, the corresponding entry in the table is deleted"
     INDEX { multicastServiceContextProfileMappingName }

     ::= { multicastServiceContextProfileMappingTable 1 }

MulticastServiceContextProfileMappingEntry ::=
       SEQUENCE { multicastServiceContextProfileMappingName AsamProfileName,
                  multicastServiceContextProfileMappingIndex AsamProfileIndex
                }

multicastServiceContextProfileMappingName OBJECT-TYPE
     SYNTAX AsamProfileName
     ACCESS not-accessible
     STATUS mandatory
     DESCRIPTION
           "A text string containing the name of
            this profile"

     ::= { multicastServiceContextProfileMappingEntry 1 }

multicastServiceContextProfileMappingIndex OBJECT-TYPE
     SYNTAX AsamProfileIndex
     ACCESS read-only
     STATUS mandatory
     DESCRIPTION 
           "This object is the Profile index."

      ::= { multicastServiceContextProfileMappingEntry 2 }


multicastServiceContextProfileIndexNext OBJECT-TYPE
     SYNTAX AsamNextProfileIndex
     ACCESS read-only
     STATUS mandatory
     DESCRIPTION
           "This object contains an appropriate value to be used for
            multicastServiceContextProfileIndex when creating entries in the
            multicastServiceContextProfileTable.
            The value 0 indicates that no unassigned entries are available. To
            obtain the multicastServiceContextProfileIndex value for a new entry, the
            manager issues a management protocol retrieval operation to obtain the
            current value of this object. After each retrieval, the agent should
            modify the value to the next unassigned index.

           ALCATEL NOTE:
           ACCESS: NA
           USAGE: NA
           PERSIST: YES
           INSRVMOD: NO
           RANGE: 1..64
           DEFVALUE: NA
           UNITS: NA
           SPARSE: NA
           DESCR: NA"

::= { igmpMIB 86 }

        
-- =============================================================================
-- multicastTranslationTable
-- =============================================================================

multicastTranslationTable OBJECT-TYPE
SYNTAX SEQUENCE OF MulticastTranslationEntry
    ACCESS not-accessible
    STATUS mandatory
    DESCRIPTION
        "This table contains multicast vlan translation entries. Each entry in the
        table contains required information to do the multicast vlan translation.
        Entry's can only be added or deleted when igmpSystemChangeOperStatus set to false.
        This is only applicable to GPON LT's and EPON LT's only. 
        DSL LT's will ignore this configuration.
        ALCATEL NOTE:
            TABLESIZE: 64
            DESCR: NA"
        ::= { igmpMIB 83 }

multicastTranslationEntry OBJECT-TYPE
   SYNTAX MulticastTranslationEntry
   ACCESS not-accessible
   STATUS mandatory
   DESCRIPTION
       "Each entry lists the networkVlan and PonVlan used to do the multicast 
       vlan translation when it is enabled.
       Row creation : An entry is created by operator.
       Row deletion : An entry is deleted by operator.
       Index usage : the index is the multicastTranslationNetworkVlan."
       INDEX {multicastTranslationNetworkVlan}
       ::= {multicastTranslationTable 1}

MulticastTranslationEntry ::= SEQUENCE {
            multicastTranslationNetworkVlan   VlanId,
            multicastTranslationPonVlan       VlanId,
            multicastTranslationRowStatus     RowStatus
            }
            
multicastTranslationNetworkVlan  OBJECT-TYPE
    SYNTAX VlanId
    ACCESS read-write
    STATUS mandatory
    DESCRIPTION
       "Network Vlan Id of the multicast vlan translation entry. This vlan will be 
       used to translate the downstream multicast traffic vlan to the PonVlan when
       the multicast translation is enabled.
       NetworkVlan from this entry is translated to PonVlan. 
	   ALCATEL NOTE:
            ACCESS:      NA            USAGE:       NA
            PERSIST:     YES           INSRVMOD:    NA
            RANGE:       2 .. 4093     DEFVALUE:    NA
            UNITS:       NA            SPARSE:      NA
            DESCR:       NA"
    ::={multicastTranslationEntry 1}

multicastTranslationPonVlan  OBJECT-TYPE
    SYNTAX VlanId
    ACCESS read-write
    STATUS mandatory
    DESCRIPTION
       "Pon Vlan Id of the multicast vlan translation entry. This vlan will be 
       used to translate the downstream multicast traffic network vlan to ponVlan
       when the multicast translation is enabled. 
       NetworkVlan from this entry is translated to PonVlan.
	   ALCATEL NOTE:
            ACCESS:      NA            USAGE:       NA
            PERSIST:     YES           INSRVMOD:    NA
            RANGE:       1 .. 4093     DEFVALUE:    NA
            UNITS:       NA            SPARSE:      NA
            DESCR:       NA"
    ::={multicastTranslationEntry 2}
 
multicastTranslationRowStatus OBJECT-TYPE
    SYNTAX RowStatus
    ACCESS read-write
    STATUS mandatory
    DESCRIPTION
        "This object is used to create a new row or delete an
        existing row in this table. The possible valid values are:
            (1) active
            (4) createdAndGo
            (6) destroy
        To create an entry in this table, this object should be set to
        CreateAndGo. To delete an entry from this table, RowStatus
        should be set to Destroy by the SNMP manager.
        This object does not support the dribble-mode.
        Entry's can only be added or deleted when igmpSystemChangeOperStatus set to false.
        ALCATEL NOTE:
            ACCESS:      NA            USAGE:       MAND
            PERSIST:     NO            INSRVMOD:    YES
            RANGE:       1|4|6         DEFVALUE:    NA
            UNITS:       NA            SPARSE:      NA
            DESCR:       NA"
    ::= {multicastTranslationEntry 3}
    

-- =============================================================================
-- multicastPonTranslationTable
-- =============================================================================

multicastPonTranslationTable OBJECT-TYPE
SYNTAX SEQUENCE OF MulticastPonTranslationEntry
    ACCESS not-accessible
    STATUS mandatory
    DESCRIPTION
        "This table contains multicast pon port and network vlan to Ponvlan translation entries. 
        Each entry in the table contains required information to do the multicast vlan translation.
        This is only applicable to EPON LT's only. DSL LT's and GPON LT's will ignore this configuration.
        ALCATEL NOTE:
            TABLESIZE: DEP[(slot number) * (max pon translations per slot)] 
            DESCR: NA"
        ::= { igmpMIB 89 }

multicastPonTranslationEntry OBJECT-TYPE
   SYNTAX MulticastPonTranslationEntry
   ACCESS not-accessible
   STATUS mandatory
   DESCRIPTION
       "Each entry lists the networkVlan and port to Ponvlan translation when it is enabled.
       Row creation : An entry is created by operator.
       Row deletion : An entry is deleted by operator.
       Index usage : the index is the ."
       INDEX {multicastPonTranslationPonIndex,
              multicastPonTranslationNetworkVlan
             }
       ::= {multicastPonTranslationTable 1}

MulticastPonTranslationEntry ::= SEQUENCE {
            multicastPonTranslationPonIndex          InterfaceIndex,
            multicastPonTranslationNetworkVlan       VlanId,
            multicastPonTranslationRowStatus         RowStatus,
            multicastPonTranslationVlanId            VlanId
            }
            
multicastPonTranslationPonIndex  OBJECT-TYPE
    SYNTAX InterfaceIndex
    ACCESS not-accessible
    STATUS mandatory
    DESCRIPTION
       "Pon ifIndex of the multicast vlan translation entry. This index indicate which
        port do the multicast vlan translation.
	   ALCATEL NOTE:
            ACCESS:      NA            USAGE:       NA
            PERSIST:     YES           INSRVMOD:    NA
            RANGE:       NA            DEFVALUE:    NA
            UNITS:       NA            SPARSE:      NA
            DESCR:       NA"
    ::={multicastPonTranslationEntry 1}
            
multicastPonTranslationNetworkVlan  OBJECT-TYPE
    SYNTAX VlanId
    ACCESS not-accessible
    STATUS mandatory
    DESCRIPTION
       "Network Vlan Id of the multicast vlan translation entry. This vlan will be 
       used to translate the downstream multicast traffic vlan to the PonVlan.
	   ALCATEL NOTE:
            ACCESS:      NA            USAGE:       NA
            PERSIST:     YES           INSRVMOD:    NA
            RANGE:       2 .. 4093     DEFVALUE:    NA
            UNITS:       NA            SPARSE:      NA
            DESCR:       NA"
    ::={multicastPonTranslationEntry 2}

multicastPonTranslationRowStatus OBJECT-TYPE
    SYNTAX RowStatus
    ACCESS read-write
    STATUS mandatory
    DESCRIPTION
        "This object is used to create a new row or delete an
        existing row in this table. The possible valid values are:
            (1) active
            (4) createdAndGo
            (6) destroy
        To create an entry in this table, this object should be set to
        CreateAndGo. To delete an entry from this table, RowStatus
        should be set to Destroy by the SNMP manager.
        This object does not support the dribble-mode.
        Entry's can only be added or deleted when no igmp channel enabled on this port.
        ALCATEL NOTE:
            ACCESS:      NA            USAGE:       MAND
            PERSIST:     NO            INSRVMOD:    YES
            RANGE:       1|4|6         DEFVALUE:    NA
            UNITS:       NA            SPARSE:      NA
            DESCR:       NA"
    ::={multicastPonTranslationEntry 3}

multicastPonTranslationVlanId OBJECT-TYPE
    SYNTAX VlanId
    ACCESS read-write
    STATUS mandatory
    DESCRIPTION
       "User Vlan Id of the multicast vlan translation entry. This vlan will be 
       used to translate the downstream multicast traffic network vlan to user Vlan. 
	   ALCATEL NOTE:
            ACCESS:      NA            USAGE:      MAND 
            PERSIST:     YES           INSRVMOD:   YES 
            RANGE:       1 .. 4093     DEFVALUE:    NA
            UNITS:       NA            SPARSE:      NA
            DESCR:       NA"
    ::={multicastPonTranslationEntry 4}

-- =============================================================================
-- igmp stats table for central IGMP snooper
-- =============================================================================



igmpVlanStatsTable OBJECT-TYPE 
          SYNTAX      SEQUENCE OF IgmpVlanStatsEntry 
          MAX-ACCESS  not-accessible 
          STATUS      current 
          DESCRIPTION 
             "This table contains IGMP snooping statistics  
              maintained by the switch. The statistics are
              maintained on a per VLAN basis.

              Table is only applicable for ISAM 7363 MX
	      
	      ALCATEL NOTE:
	      TABLESIZE: 4094 
              DESCR: NA"
          ::= { igmpMIB 90 }
 
      igmpVlanStatsEntry OBJECT-TYPE 
          SYNTAX      IgmpVlanStatsEntry 
          MAX-ACCESS  not-accessible 
          STATUS      current 
          DESCRIPTION 
             "Contains IGMP snooping statistics for a particular VLAN.
	      Row creation : Entry is created when nmhSetDot1qVlanStaticRowStatus is set to active(1).
              Row deletion : Entry is deleted when nmhSetDot1qVlanStaticRowStatus is set to destroy(6).
              Index usage : The index is the vlan id.
              Note that entries will be presented to the SNMP manager in full
              lexicographical order :  sorted on igmpVlanStatsVlanId." 
          INDEX { igmpVlanStatsVlanId } 
          ::= { igmpVlanStatsTable 1 } 
 
      IgmpVlanStatsEntry ::= SEQUENCE { 
          igmpVlanStatsVlanId                	VlanId,
          igmpVlanStatsClearAll                 TruthValue, 
          igmpVlanStatsRxGenQueries          	Counter,
          igmpVlanStatsRxGrpQueries          	Counter,
          igmpVlanStatsRxGrpAndSrcQueries    	Counter,
          igmpVlanStatsRxIgmpReports         	Counter,
          igmpVlanStatsRxIgmpv3Reports       	Counter,
          igmpVlanStatsRxIgmpLeaves          	Counter,
          igmpVlanStatsTxGenQueries          	Counter,
          igmpVlanStatsTxGrpQueries          	Counter,
          igmpVlanStatsTxGrpAndSrcQueries       Counter,
          igmpVlanStatsTxIgmpReports         	Counter,
          igmpVlanStatsTxIgmpv3Reports       	Counter,
          igmpVlanStatsTxIgmpLeaves          	Counter,
          igmpVlanStatsIgmpDroppedPkts       	Counter
        } 

igmpVlanStatsVlanId                OBJECT-TYPE 
           SYNTAX      VlanId 
           MAX-ACCESS  not-accessible 
           STATUS      current 
           DESCRIPTION 
            " VLAN ID for which IGMP snooping statistics are displayed.
	      ALCATEL NOTE:
	      ACCESS:      NA            USAGE:       NA
              PERSIST:     NO            INSRVMOD:    NA
              RANGE:       NA            DEFVALUE:    NA
              UNITS:       NA            SPARSE:      NO
              DESCR:       NA"
           ::= { igmpVlanStatsEntry 1 }

igmpVlanStatsClearAll                 OBJECT-TYPE
          SYNTAX      TruthValue
          MAX-ACCESS  read-write
          STATUS      current
          DESCRIPTION 
 "This object is used to reset all the counters in this table;
When it is set to true(1), all the counters in this row will be
              cleared. 
             Once resetting action is completed, agent sets the value to false(2). 
              If SNMP Manager sets this object to false(2), agent does not take any action. 
              A get operation for this object will always return a value of false(2).
            ALCATEL NOTE:
            	ACCESS:      NA            USAGE:       NA
            	PERSIST:     NO            INSRVMOD:    YES
            	RANGE:       1,2           DEFVALUE:    NA
            	UNITS:       NA            SPARSE:      NO
           	DESCR:       NA"
	    DEFVAL { 2 }
	  ::= { igmpVlanStatsEntry 2}

igmpVlanStatsRxGenQueries OBJECT-TYPE 
           SYNTAX      Counter
           MAX-ACCESS  read-only 
           STATUS      current 
           DESCRIPTION 
               "Provides statistics of General Queries received by the
                snooping switch on the network port. 
                This object will be incremented for every General Query received for the Vlan.
                
	        ALCATEL NOTE:
	        ACCESS:      NA            USAGE:       NA
                PERSIST:     NO            INSRVMOD:    NA
                RANGE:       NA            DEFVALUE:    NA
                UNITS:       NA            SPARSE:      NO
                DESCR:       NA" 
           ::= { igmpVlanStatsEntry 3 } 

      igmpVlanStatsRxGrpQueries OBJECT-TYPE 
           SYNTAX      Counter
           MAX-ACCESS  read-only 
           STATUS      current 
           DESCRIPTION 
               "Provides statistics of Group Specific Queries received
                by the snooping switch on the network port.
                This object will be incremented for every Group Specific Query received for the Vlan.
                
	        ALCATEL NOTE:
	        ACCESS:      NA            USAGE:       NA
                PERSIST:     NO            INSRVMOD:    NA
                RANGE:       NA            DEFVALUE:    NA
                UNITS:       NA            SPARSE:      NO
                DESCR:       NA" 
           ::= { igmpVlanStatsEntry 4} 

      igmpVlanStatsRxGrpAndSrcQueries OBJECT-TYPE 
           SYNTAX      Counter
           MAX-ACCESS  read-only 
           STATUS      current 
           DESCRIPTION 
               "Provides statistics of Group And Source Specific Queries
                received by the snooping switch on the network port.
                This object will be incremented for every Group And Source Specific Query received for the Vlan.
                
	        ALCATEL NOTE:
	        ACCESS:      NA            USAGE:       NA
                PERSIST:     NO            INSRVMOD:    NA
                RANGE:       NA            DEFVALUE:    NA
                UNITS:       NA            SPARSE:      NO
                DESCR:       NA" 
           ::= { igmpVlanStatsEntry 5 } 

      igmpVlanStatsRxIgmpReports OBJECT-TYPE 
           SYNTAX      Counter
           MAX-ACCESS  read-only 
           STATUS      current 
           DESCRIPTION 
               "Provides statistics of IGMPv1/IGMPv2 Membership reports
                received by the snooping switch on the host port.
                
	        ALCATEL NOTE:
	        ACCESS:      NA            USAGE:       NA
                PERSIST:     NO            INSRVMOD:    NA
                RANGE:       NA            DEFVALUE:    NA
                UNITS:       NA            SPARSE:      NO
                DESCR:       NA" 
           ::= { igmpVlanStatsEntry 6 } 

      igmpVlanStatsRxIgmpv3Reports OBJECT-TYPE 
           SYNTAX      Counter
           MAX-ACCESS  read-only 
           STATUS      current 
           DESCRIPTION 
               "Provides statistics of IGMPv3 Membership reports
                received by the snooping switch on the host port.
                
	        ALCATEL NOTE:
	        ACCESS:      NA            USAGE:       NA
                PERSIST:     NO            INSRVMOD:    NA
                RANGE:       NA            DEFVALUE:    NA
                UNITS:       NA            SPARSE:      NO
                DESCR:       NA" 
           ::= { igmpVlanStatsEntry 7 } 

igmpVlanStatsRxIgmpLeaves OBJECT-TYPE 
           SYNTAX      Counter
           MAX-ACCESS  read-only 
           STATUS      current 
           DESCRIPTION 
               "Provides statistics of IGMPv2 Leave messages    
                received by the snooping switch on the host port.
                
	        ALCATEL NOTE:
	        ACCESS:      NA            USAGE:       NA
                PERSIST:     NO            INSRVMOD:    NA
                RANGE:       NA            DEFVALUE:    NA
                UNITS:       NA            SPARSE:      NO
                DESCR:       NA"  
           ::= { igmpVlanStatsEntry 8 } 

  igmpVlanStatsTxGenQueries OBJECT-TYPE 
           SYNTAX      Counter
           MAX-ACCESS  read-only 
           STATUS      current 
           DESCRIPTION 
               "Provides statistics of General Queries transmitted by the
                snooping switch on the network port when it is acts as a querier.
                
	        ALCATEL NOTE:
	        ACCESS:      NA            USAGE:       NA
                PERSIST:     NO            INSRVMOD:    NA
                RANGE:       NA            DEFVALUE:    NA
                UNITS:       NA            SPARSE:      NO
                DESCR:       NA"  
           ::= { igmpVlanStatsEntry 9 } 

      igmpVlanStatsTxGrpQueries OBJECT-TYPE 
           SYNTAX      Counter
           MAX-ACCESS  read-only 
           STATUS      current 
           DESCRIPTION 
               "Provides statistics of Group Specific Queries transmitted
                by the snooping switch on the network port.
                
	        ALCATEL NOTE:
	        ACCESS:      NA            USAGE:       NA
                PERSIST:     NO            INSRVMOD:    NA
                RANGE:       NA            DEFVALUE:    NA
                UNITS:       NA            SPARSE:      NO
                DESCR:       NA" 
           ::= { igmpVlanStatsEntry 10 } 

      igmpVlanStatsTxGrpAndSrcQueries       OBJECT-TYPE 
           SYNTAX      Counter 
           MAX-ACCESS  read-only 
           STATUS      current 
           DESCRIPTION  
             "Provides the number of GSSQ packets trasnsmitted
             by the switch. 
        ALCATEL NOTE:
            ACCESS:      NA           USAGE:       NA
            PERSIST:     NO           INSRVMOD:    NA
            RANGE:       NA           DEFVALUE:    NA
            UNITS:       NA           SPARSE:      NO
            DESCR:       NA"            
           ::= { igmpVlanStatsEntry 11 }

      igmpVlanStatsTxIgmpReports OBJECT-TYPE 
           SYNTAX      Counter
           MAX-ACCESS  read-only 
           STATUS      current 
           DESCRIPTION 
               "Provides statistics of IGMPv1/IGMPv2 Membership reports
                transmitted by the snooping switch on the network port.
                This object will be incremented for every IGMPv1/IGMPv2 Membership report sent by switch for the Vlan for all the ports.
                
	        ALCATEL NOTE:
	        ACCESS:      NA            USAGE:       NA
                PERSIST:     NO            INSRVMOD:    NA
                RANGE:       NA            DEFVALUE:    NA
                UNITS:       NA            SPARSE:      NO
                DESCR:       NA" 
           ::= { igmpVlanStatsEntry 12 } 

      igmpVlanStatsTxIgmpv3Reports OBJECT-TYPE 
           SYNTAX      Counter
           MAX-ACCESS  read-only 
           STATUS      current 
           DESCRIPTION 
               "Provides statistics of IGMPv3 Membership reports
                transmitted by the snooping switch on the network port.
                This object will be incremented for every IGMPv3 Membership report sent 
                by the switch for the Vlan for all the ports.
                
	        ALCATEL NOTE:
	        ACCESS:      NA            USAGE:       NA
                PERSIST:     NO            INSRVMOD:    NA
                RANGE:       NA            DEFVALUE:    NA
                UNITS:       NA            SPARSE:      NO
                DESCR:       NA" 
           ::= { igmpVlanStatsEntry 13 } 

      igmpVlanStatsTxIgmpLeaves OBJECT-TYPE 
           SYNTAX      Counter
           MAX-ACCESS  read-only 
           STATUS      current 
           DESCRIPTION 
               "Provides statistics of IGMPv2 Leave messages    
                transmitted by the snooping switch on the network port.
                This object will be incremented for every IGMPv2 Leave message sent 
                by the switch for the Vlan for all the ports.
                
	        ALCATEL NOTE:
	        ACCESS:      NA            USAGE:       NA
                PERSIST:     NO            INSRVMOD:    NA
                RANGE:       NA            DEFVALUE:    NA
                UNITS:       NA            SPARSE:      NO
                DESCR:       NA" 
           ::= { igmpVlanStatsEntry 14 } 

      igmpVlanStatsIgmpDroppedPkts OBJECT-TYPE 
           SYNTAX      Counter
           MAX-ACCESS  read-only 
           STATUS      current 
           DESCRIPTION 
               "Provides the number of erroneous IGMP packets dropped
                by the snooping switch 
	        ALCATEL NOTE:
	        ACCESS:      NA            USAGE:       NA
                PERSIST:     NO            INSRVMOD:    NA
                RANGE:       NA            DEFVALUE:    NA
                UNITS:       NA            SPARSE:      NO
                DESCR:       NA"
           ::= { igmpVlanStatsEntry 15 } 
           
-- ==============================================================================
--  Multicast replication Table User To Source Per PON
-- ==============================================================================

multicastPonItf2McGroupAddrTable OBJECT-TYPE
    SYNTAX SEQUENCE OF MulticastPonItf2McGroupAddrEntry
    ACCESS not-accessible
    STATUS mandatory
    DESCRIPTION
        "This table lists the active multicast streams per PON together with the
        state these multicast streams are currently forced to.
        ALCATEL NOTE:
            TABLESIZE: 5225472 GPON LT:(Max nbr of branches per board (36864) + 
	    max nbr streams in blackout per board(253440))* nbr boards (18)
            DESCR: NA"
    ::= { igmpMIB 91 }

multicastPonItf2McGroupAddrEntry OBJECT-TYPE
    SYNTAX MulticastPonItf2McGroupAddrEntry
    ACCESS not-accessible
    STATUS mandatory
    DESCRIPTION
        "One entry in table multicastPonItf2McGroupAddrTable.
        Row creation : An entry is created by the system.
        Row deletion : An entry is created by the system.
        Index usage : the index is the .
        Note that entries will be presented to the SNMP manager in full
        lexicographical order."
    INDEX { multicastPonItf2McGroupAddrPonIfIndex,
            multicastPonItf2McGroupAddrIfIndex,
            multicastPonItf2McGroupAddrVlan,
            multicastPonItf2McGroupAddrClassDAddr,
            multicastPonItf2McGroupAddrSrcIPAddr }
    ::= { multicastPonItf2McGroupAddrTable 1 }

MulticastPonItf2McGroupAddrEntry ::=
    SEQUENCE {
        multicastPonItf2McGroupAddrPonIfIndex        InterfaceIndex,
        multicastPonItf2McGroupAddrIfIndex           InterfaceIndex,
        multicastPonItf2McGroupAddrVlan              VlanId,
        multicastPonItf2McGroupAddrClassDAddr        IpAddress,
        multicastPonItf2McGroupAddrSrcIPAddr         IpAddress,
        multicastPonItf2McGroupAddrActualstate       INTEGER,
        multicastPonItf2McGroupCurrentPreviewNumber  INTEGER,
        multicastPonItf2McGroupStatus                INTEGER
    }


multicastPonItf2McGroupAddrPonIfIndex     OBJECT-TYPE
    SYNTAX InterfaceIndex
    ACCESS not-accessible
    STATUS mandatory
    DESCRIPTION
        "The ifindex of the PON.
        ALCATEL NOTE:
            ACCESS:      NA            USAGE:       NA
            PERSIST:     NA            INSRVMOD:    NA
            RANGE:       NA            DEFVALUE:    NA
            UNITS:       NA            SPARSE:      NA
            DESCR:       NA"
    ::={ multicastPonItf2McGroupAddrEntry 1 }

multicastPonItf2McGroupAddrIfIndex     OBJECT-TYPE
    SYNTAX InterfaceIndex
    ACCESS not-accessible
    STATUS mandatory
    DESCRIPTION
        "The ifindex of the IGMP channel.
        ALCATEL NOTE:
            ACCESS:      NA            USAGE:       NA
            PERSIST:     NA            INSRVMOD:    NA
            RANGE:       NA            DEFVALUE:    NA
            UNITS:       NA            SPARSE:      NA
            DESCR:       NA"
    ::={ multicastPonItf2McGroupAddrEntry 2 }

multicastPonItf2McGroupAddrVlan        OBJECT-TYPE
    SYNTAX VlanId
    ACCESS not-accessible
    STATUS mandatory
    DESCRIPTION
        "The Vlan in which the multicast stream is provisioned
        by the multicast Service provider.
        ALCATEL NOTE:
            ACCESS:      NA            USAGE:       NA
            PERSIST:     NA            INSRVMOD:    NA
            RANGE:       NA            DEFVALUE:    NA
            UNITS:       NA            SPARSE:      NA
            DESCR:       NA"
    ::={ multicastPonItf2McGroupAddrEntry 3 }

multicastPonItf2McGroupAddrClassDAddr  OBJECT-TYPE
    SYNTAX IpAddress
    ACCESS not-accessible
    STATUS mandatory
    DESCRIPTION
        "The class D address of the multicast stream, in network-byte
        order and in the range 224.0.0.3 up to 239.255.255.255.
	    (big-endian).
        ALCATEL NOTE:
            ACCESS:      NA            USAGE:       NA
            PERSIST:     NA            INSRVMOD:    NA
            RANGE:       NA            DEFVALUE:    NA
            UNITS:       NA            SPARSE:      NA
            DESCR:       NA"
    ::={ multicastPonItf2McGroupAddrEntry 4 }

multicastPonItf2McGroupAddrSrcIPAddr   OBJECT-TYPE
    SYNTAX IpAddress
    ACCESS not-accessible
    STATUS mandatory
    DESCRIPTION
        "The multicast stream unicast source IP address,
	    in network-byte order (big-endian).
        It is set to the value 0.0.0.0 for SM multicast streams.
        ALCATEL NOTE:
            ACCESS:      NA            USAGE:       NA
            PERSIST:     NA            INSRVMOD:    NA
            RANGE:       NA            DEFVALUE:    NA
            UNITS:       NA            SPARSE:      NA
            DESCR:       NA"
    ::={ multicastPonItf2McGroupAddrEntry 5 }

multicastPonItf2McGroupAddrActualstate OBJECT-TYPE
    SYNTAX INTEGER { full-view(1), pre-view(2), black-out(3) }
    ACCESS read-only
    STATUS mandatory
    DESCRIPTION
        "The current state of the multicast stream :
          - full-view : the multicast stream is joined as a full-view session.
          - pre-view : the multicast stream is joined as a pre-view session.
          - black-out : the multicast stream is currently blocked i.e.
	                    the black-out period is running.
        ALCATEL NOTE:
            ACCESS:      NA            USAGE:       NA
            PERSIST:     NA            INSRVMOD:    NA
            RANGE:       NA            DEFVALUE:    NA
            UNITS:       NA            SPARSE:      NA
            DESCR:       NA"
    ::={ multicastPonItf2McGroupAddrEntry 6 }

multicastPonItf2McGroupCurrentPreviewNumber  OBJECT-TYPE
    SYNTAX INTEGER (0..1000)
    ACCESS read-only
    STATUS mandatory
    DESCRIPTION
        " The number of pre-view sessions already been viewed for this
        multicast stream on this IGMP Channel
        ALCATEL NOTE:
            ACCESS:      NA            USAGE:       NA
            PERSIST:     NA            INSRVMOD:    NA
            RANGE:       NA            DEFVALUE:    NA
            UNITS:       NA            SPARSE:      NA
            DESCR:       NA"
    ::={ multicastPonItf2McGroupAddrEntry 7 }
    
multicastPonItf2McGroupStatus OBJECT-TYPE
    SYNTAX INTEGER { static(1), dynamic(2), staticdynamic(3) }
    ACCESS read-only
    STATUS mandatory
    DESCRIPTION
        "The current status of the multicast stream :
          - static : the multicast stream is from a static multicast root
          - staticdynamic : the multicast stream is from a multicast root
                             who has static and dynamic branches.
          - dynamic : the multicast stream is from a dynamic multicast root.
        ALCATEL NOTE:
            ACCESS:      NA            USAGE:       MAND
            PERSIST:     NA            INSRVMOD:    NA
            RANGE:       1|2|3         DEFVALUE:    NA
            UNITS:       NA            SPARSE:      NA
            DESCR:       NA"
    ::={ multicastPonItf2McGroupAddrEntry 8 }
           

-- ==============================================================================
--  Multicast replication Table User To Source Per ONT
-- ==============================================================================

multicastOntItf2McGroupAddrTable OBJECT-TYPE
    SYNTAX SEQUENCE OF MulticastOntItf2McGroupAddrEntry
    ACCESS not-accessible
    STATUS mandatory
    DESCRIPTION
        "This table lists the active multicast streams per ONT together with the
        state these multicast streams are currently forced to.
        ALCATEL NOTE:
            TABLESIZE: 5225472 GPON LT:(Max nbr of branches per board (36864) + 
	    max nbr streams in blackout per board(253440))* nbr boards (18)
            DESCR: NA"
    ::= { igmpMIB 92 }

multicastOntItf2McGroupAddrEntry OBJECT-TYPE
    SYNTAX MulticastOntItf2McGroupAddrEntry
    ACCESS not-accessible
    STATUS mandatory
    DESCRIPTION
        "One entry in table multicastOntItf2McGroupAddrTable.
        Row creation : An entry is created by the system.
        Row deletion : An entry is created by the system.
        Index usage : the index is the .
        Note that entries will be presented to the SNMP manager in full
        lexicographical order."
    INDEX { multicastOntItf2McGroupAddrOntIfIndex,
            multicastOntItf2McGroupAddrIfIndex,
            multicastOntItf2McGroupAddrVlan,
            multicastOntItf2McGroupAddrClassDAddr,
            multicastOntItf2McGroupAddrSrcIPAddr }
    ::= { multicastOntItf2McGroupAddrTable 1 }

MulticastOntItf2McGroupAddrEntry ::=
    SEQUENCE {
        multicastOntItf2McGroupAddrOntIfIndex        InterfaceIndex,
        multicastOntItf2McGroupAddrIfIndex           InterfaceIndex,
        multicastOntItf2McGroupAddrVlan              VlanId,
        multicastOntItf2McGroupAddrClassDAddr        IpAddress,
        multicastOntItf2McGroupAddrSrcIPAddr         IpAddress,
        multicastOntItf2McGroupAddrActualstate       INTEGER,
        multicastOntItf2McGroupCurrentPreviewNumber  INTEGER,
        multicastOntItf2McGroupStatus                INTEGER
    }


multicastOntItf2McGroupAddrOntIfIndex     OBJECT-TYPE
    SYNTAX InterfaceIndex
    ACCESS not-accessible
    STATUS mandatory
    DESCRIPTION
        "The ifindex of the IGMP channel.
        ALCATEL NOTE:
            ACCESS:      NA            USAGE:       NA
            PERSIST:     NA            INSRVMOD:    NA
            RANGE:       NA            DEFVALUE:    NA
            UNITS:       NA            SPARSE:      NA
            DESCR:       NA"
    ::={ multicastOntItf2McGroupAddrEntry 1 }

multicastOntItf2McGroupAddrIfIndex     OBJECT-TYPE
    SYNTAX InterfaceIndex
    ACCESS not-accessible
    STATUS mandatory
    DESCRIPTION
        "The ifindex of the ONT.
        ALCATEL NOTE:
            ACCESS:      NA            USAGE:       NA
            PERSIST:     NA            INSRVMOD:    NA
            RANGE:       NA            DEFVALUE:    NA
            UNITS:       NA            SPARSE:      NA
            DESCR:       NA"
    ::={ multicastOntItf2McGroupAddrEntry 2 }

multicastOntItf2McGroupAddrVlan        OBJECT-TYPE
    SYNTAX VlanId
    ACCESS not-accessible
    STATUS mandatory
    DESCRIPTION
        "The Vlan in which the multicast stream is provisioned
        by the multicast Service provider.
        ALCATEL NOTE:
            ACCESS:      NA            USAGE:       NA
            PERSIST:     NA            INSRVMOD:    NA
            RANGE:       NA            DEFVALUE:    NA
            UNITS:       NA            SPARSE:      NA
            DESCR:       NA"
    ::={ multicastOntItf2McGroupAddrEntry 3 }

multicastOntItf2McGroupAddrClassDAddr  OBJECT-TYPE
    SYNTAX IpAddress
    ACCESS not-accessible
    STATUS mandatory
    DESCRIPTION
        "The class D address of the multicast stream, in network-byte
        order and in the range 224.0.0.3 up to 239.255.255.255.
	    (big-endian).
        ALCATEL NOTE:
            ACCESS:      NA            USAGE:       NA
            PERSIST:     NA            INSRVMOD:    NA
            RANGE:       NA            DEFVALUE:    NA
            UNITS:       NA            SPARSE:      NA
            DESCR:       NA"
    ::={ multicastOntItf2McGroupAddrEntry 4 }

multicastOntItf2McGroupAddrSrcIPAddr   OBJECT-TYPE
    SYNTAX IpAddress
    ACCESS not-accessible
    STATUS mandatory
    DESCRIPTION
        "The multicast stream unicast source IP address,
	    in network-byte order (big-endian).
        It is set to the value 0.0.0.0 for SM multicast streams.
        ALCATEL NOTE:
            ACCESS:      NA            USAGE:       NA
            PERSIST:     NA            INSRVMOD:    NA
            RANGE:       NA            DEFVALUE:    NA
            UNITS:       NA            SPARSE:      NA
            DESCR:       NA"
    ::={ multicastOntItf2McGroupAddrEntry 5 }

multicastOntItf2McGroupAddrActualstate OBJECT-TYPE
    SYNTAX INTEGER { full-view(1), pre-view(2), black-out(3) }
    ACCESS read-only
    STATUS mandatory
    DESCRIPTION
        "The current state of the multicast stream :
          - full-view : the multicast stream is joined as a full-view session.
          - pre-view : the multicast stream is joined as a pre-view session.
          - black-out : the multicast stream is currently blocked i.e.
	                    the black-out period is running.
        ALCATEL NOTE:
            ACCESS:      NA            USAGE:       NA
            PERSIST:     NA            INSRVMOD:    NA
            RANGE:       NA            DEFVALUE:    NA
            UNITS:       NA            SPARSE:      NA
            DESCR:       NA"
    ::={ multicastOntItf2McGroupAddrEntry 6 }

multicastOntItf2McGroupCurrentPreviewNumber  OBJECT-TYPE
    SYNTAX INTEGER (0..1000)
    ACCESS read-only
    STATUS mandatory
    DESCRIPTION
        " The number of pre-view sessions already been viewed for this
        multicast stream on this IGMP Channel
        ALCATEL NOTE:
            ACCESS:      NA            USAGE:       NA
            PERSIST:     NA            INSRVMOD:    NA
            RANGE:       NA            DEFVALUE:    NA
            UNITS:       NA            SPARSE:      NA
            DESCR:       NA"
    ::={ multicastOntItf2McGroupAddrEntry 7 }
    
multicastOntItf2McGroupStatus OBJECT-TYPE
    SYNTAX INTEGER { static(1), dynamic(2), staticdynamic(3) }
    ACCESS read-only
    STATUS mandatory
    DESCRIPTION
        "The current status of the multicast stream :
          - static : the multicast stream is from a static multicast root
          - staticdynamic : the multicast stream is from a multicast root
                             who has static and dynamic branches.
          - dynamic : the multicast stream is from a dynamic multicast root.
        ALCATEL NOTE:
            ACCESS:      NA            USAGE:       MAND
            PERSIST:     NA            INSRVMOD:    NA
            RANGE:       1|2|3         DEFVALUE:    NA
            UNITS:       NA            SPARSE:      NA
            DESCR:       NA"
    ::={ multicastOntItf2McGroupAddrEntry 8 }

END
