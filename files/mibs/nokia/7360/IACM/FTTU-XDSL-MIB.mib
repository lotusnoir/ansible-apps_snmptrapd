--FTTU XDSL MIB
--XDSL-MIB

-- ============================================================================
--  This specification is published by Alcatel under Non-Disclosure
--  Agreement(s) (NDA) with specific parties and has to be considered as
--  Confidential Information as defined in such NDA.
--  Alcatel reserves the right to revise this document for any reason,
--  including but not limited to conformity with standards promulgated by
--  various agencies, utilisation of advances in the state of the technical
--  areas, or the reflection of changes in the design of any equipment,
--  techniques, or procedures described or referred to herein.
--  The product specifications and other technical or performance information
--  contained herein are subject to change without notice.
--  Updates of this document will be issued under the above NDA's.
--  Alcatel makes no representation or warranty, expressed or implied, with
--  respect to the sufficiency, accuracy, or utility of any information or
--  opinion contained herein. Alcatel expressly advises that any use of for 
--  any purpose or reliance upon this technical reference is at the risk of
--  the user and that Alcatel will not be liable for any damage or injury
--  incurred by any person arising out of the sufficiency, accuracy, or
--  utility of any information or opinion contained herein.
--  This document is not to be construed as a suggestion to any manufacturer
--  to modify or change any of its products, nor does this document represent
--  any commitment by Alcatel to sell or purchase any product.
--  Nothing contained herein will be construed as conferring by implication,
--  estoppel, or otherwise any license or right under any patent, whether or
--  not the use of any information herein necessarily employs an invention of
--  any existing or later issued patent.
--  Alcatel reserves the right not to offer any or all of these products and
--  to withdraw any or all of them at any future time.
--  Copyright (C) 2006, Alcatel. All Rights Reserved.
-- =============================================================================== ==
-- 
--  MODULE-IDENTITY
--  LAST-UPDATED "2016080100000Z"
--  ORGANIZATION "Alcatel"
--  CONTACT-INFO "Email: asam.mibsupport@alcatel.be"
--  DESCRIPTION  "XDSL transport management MIB"

-- REVISION     "2016080100000Z" 
--  DESCRIPTION
--     Version: E1P1 (for ISAM5.5.01))
--     Editor:  Zhang Tinghui
--     Changes:
-- For ISAM5.5.01
-- >> ALU02240881 XDSL ONT-show carrier-data and show operation-data line optimize
--  Per Huang Xurui
--     - add invalid value 0 for carrier-data group MIB and GSubCarrierGroupSizeType.
--         GSubCarrierGroupSizeType
--         gxdslLineCarrierGroupTxPsd
--         gxdslLineCarrierGroupLoad
--         gxdslLineCarrierGroupGain
--         gxdslLineCarrierGroupSnr
--         gxdslLineCarrierGroupQln
--         gxdslLineCarrierGroupHLin
--         gxdslLineCarrierGroupHLog
--         gxdslFarEndLineCarrierGroupTxPsd
--         gxdslFarEndLineCarrierGroupLoad
--         gxdslFarEndLineCarrierGroupGain
--         gxdslFarEndLineCarrierGroupSnr
--         gxdslFarEndLineCarrierGroupQln
--         gxdslFarEndLineCarrierGroupHLin
--         gxdslFarEndLineCarrierGroupHLog
--     - modify the perband MIB default value from 0 to 65535 in 
--     - gxdslLineOperDataEntry and gxdslFarEndLineOperDataEntry.
--         gxdslLinePerBandLoopAttenuationUpstream
--         gxdslLinePerBandSignalAttenuationUpstream
--         gxdslLinePerBandNoiseMarginUpstream
--         gxdslFarEndLinePerBandLoopAttenuationDownstream
--         gxdslFarEndLinePerBandSignalAttenuationDownstream
--         gxdslFarEndLinePerBandNoiseMarginDownstream

-- REVISION     "2016033000000Z" 
--  DESCRIPTION
--     Version: E1P1 (for ISAM5.4.01))
--     Editor:  Zhang Tinghui
--     Changes:

-- For ISAM5.4.01
-- >> ALU02184157 HDR54 - G-010F-A - actual PSD (64635) reported on less data rates

--  Per Huang Xurui
--     - add special value 65535 that means out of range for below attributes
--         gxdslLineLoopAttenuationUpstream
--         gxdslLineSignalAttenuationUpstream
--         gxdslLineNoiseMarginUpstream
--         gxdslLineActualPsdDownstream
--         gxdslLineOutputPowerDownstream
--         gxdslFarEndLineLoopAttenuationDownstream
--         gxdslFarEndLineSignalAttenuationDownstream
--         gxdslFarEndLineNoiseMarginDownstream
--         gxdslFarEndLineActualPsdUpstream
--         gxdslFarEndLineOutputPowerUpstream

-- REVISION     "2016031500000Z" 
--  DESCRIPTION
--     Version: E1P13 (for ISAM5.3.02)
--     Editor:  Huang Xurui
--     Changes:
--     - remove range for below attributes
--         gxdslLineHighestFrequencyUpstream
--         gxdslFarEndLineHighestFrequencyDownstream

-- REVISION     "2015120200000Z" 
--  DESCRIPTION
--     Version: E1P11 (for ISAM5.3.02)
--     Editor:  Li Jianwei
--     Changes:
--     - Update INSRVMOD for below attributes
--         gxdslRtxProfileName
--         gxdslRtxProfileVersionNbr
--         gxdslRtxMode
--         gxdslRtxMinExpThrpt
--         gxdslRtxPlanExpThrpt
--         gxdslRtxMaxExpThrpt
--         gxdslRtxMaxNetDataRate
--         gxdslRtxMinDelay
--         gxdslRtxMaxDelay
--         gxdslRtxMinInpShine
--         gxdslRtxMinInpRein
--         gxdslRtxReinInterArrTime
--         gxdslRtxShineRatio
--         gxdslRtxLeftrThreshold
--         gxdslRtxProfileRowStatus
--     - For GPON - SUPPORTED as of ISAM5.3.02 by RCR ALU02074139
--       For XG-PON1 - NOT SUPPORTED as of ISAM5.3.02
--       For NG-PON2 - NOT SUPPORTED as of ISAM5.3.02

-- REVISION     "2015111000000Z" 
--  DESCRIPTION
--     Version: E1P10 (for ISAM5.3.02))
--     Editor:  Zhang Tinghui
--     Changes:

-- For ISAM5.3.02
-- >> RCR ALU02074139 - VDSL2 parameter configuration and reporting over OMCI (OLT part).

-- Per Huang Xurui
-- - Update description for below attributes
--     gxdslFarEndLineXturOpModeCapabilities   
-- - For GPON - SUPPORTED except otect 9 as of ISAM5.3.02
--   For XG-PON1 - NOT SUPPORTED as of ISAM5.3.02
--   For NG-PON2 - NOT SUPPORTED as of ISAM5.3.02

-- REVISION     "2015110500000Z" 
--  DESCRIPTION
--     Version: E1P9 (for ISAM5.3.02))
--     Editor:  Zhang Tinghui
--     Changes:

-- For ISAM5.3.02
-- >> RCR ALU02074139 - VDSL2 parameter configuration and reporting over OMCI (OLT part).

-- Per Huang Xurui
-- - Update description for below attributes
--     gxdslLineXtucOpModeCapabilities    
--     gxdslFarEndLineXturOpModeCapabilities      
-- - For GPON - SUPPORTED except otect 9 as of ISAM5.3.02
--   For XG-PON1 - NOT SUPPORTED as of ISAM5.3.02
--   For NG-PON2 - NOT SUPPORTED as of ISAM5.3.02

-- REVISION     "2015101000000Z" 
--  DESCRIPTION
--     Version: E1P8 (for ISAM5.3.02)
--     Editor:  Li Chengbing
--     Changes:
--     - Update description for below attributes
--         gxdslLineXtucOpModeCapabilities
--         gxdslLineLastTxStateDownstream
--         gxdslLineHighestFrequencyUpstream
--         gxdslFarEndLineXturOpModeCapabilities
--         gxdslFarEndLineLastTxStateUpstream
--         gxdslFarEndLineHighestFrequencyDownstream
--         gxdslFarEndLineElectricalLengthEstimated
--     - For GPON - SUPPORTED as of ISAM5.3.02 by RCR ALU02074139
--       For XG-PON1 - NOT SUPPORTED as of ISAM5.3.02
--       For NG-PON2 - NOT SUPPORTED as of ISAM5.3.02

-- REVISION     "2015092200000Z" 
--  DESCRIPTION
--     Version: E1P5 (for ISAM5.3.02)
--     Editor:  Li Chengbing
--     Changes:
--     - Add tables: gxdslRtxProfileTable and gxdslRtxProfileMappingTable.
--     - Add attributes gxdslLineRtxUpstreamProfileNbr and gxdslLineRtxDownstreamProfileNbr in table gxdslLineConfTable.
--     - Add SCALARs: gxdslRtxProfileIndexNext and gxdslRtxProfileMaxIndex.
--     - Add mib type GRtxMode.
--     - For GPON - MIB readiness in ISAM5.3.01 by RCR ALU02086399, SUPPORTED as of ISAM5.3.02
--       For XG-PON1 - NOT SUPPORTED as of ISAM5.3.02
--       For NG-PON2 - NOT SUPPORTED as of ISAM5.3.02

-- REVISION     "2015092800000Z" 
--  DESCRIPTION
--     Version: E1P6 (for ISAM5.3.02)
--     Editor:  Li Chengbing
--     Changes:
--     - Update description for attribute gxdslRtxPlanExpThrpt in gxdslRtxProfileTable
--     - Introduced in ISAM5.3.01 MIB for MIB readiness
--        For GPON    - NOT SUPPORTED as of ISAM5.3.02
--        For XG-PON1 - NOT SUPPORTED as of ISAM5.3.02
--        For NG-PON2 - NOT SUPPORTED as of ISAM5.3.02

-- REVISION "201203150000Z"
--  DESCRIPTION
--    "Version: 3FE62312EAAA_V4.3.0.0.0  
--     Editor:  Gerda Mertens
--     Changes:
--        * update description NoDefect vs NoFailure 
--           gxdslLineFailureStatus   
--           gxdslFarEndLineFailureStatus            

-- REVISION      "201101100000Z"
-- DESCRIPTION  ISAM 4.3 MIB UPDATES
--     Version : E1P04
--     Editor  : Pankaj Verma
--     Changes :
--	    -Updated DEFVAL of gxdslLineOpMode
--
-- REVISION      "201101070000Z"
-- DESCRIPTION  ISAM 4.3 MIB UPDATES
-- Version : E1P03
-- Editor  : Pankaj Verma
-- Changes :
-- - Updated description of gxdslLineTpsTcMode
--
-- REVISION     "201101060000Z"
-- DESCRIPTION  ISAM 4.3 MIB UPDATES
-- Version : E1P02
-- Editor  : Pankaj Verma
-- Changes :
-- - Updated description of gxdslLineOpMode & gxdslLineTpsTcMode
--
-- REVISION     "201101030000Z" 
-- DESCRIPTION ISAM 4.3 MIB Updates
-- Version: E1P1 (for ISAM4.3))
-- Editor:  Pankaj Verma, Madhusudanan Subramanian
-- Changes:
-- - For IR ALU00755035 ADSL Support , following table introduced.
--	-gxdslLineSpectrumProfileAdslAdsl2Table 
--       - gadslMaxAggregatePowerLevelDownstream
--	 - gadslMaxAggregatePowerLevelUpstream
--	 - gadslMaxPsdLevelDownstream
--	 - gadslMaxPsdLevelUpstream
--
-- - ADSL2Plus Support , following table introduced.
--	- gxdslLineSpectrumProfileAdsl2PlusTable
--     	 - gadsl2PlusMaxAggregatePowerLevelDownstream
--	 - gadsl2PlusMaxAggregatePowerLevelUpstream
--	 - gadsl2PlusMaxPsdLevelDownstream
--	 - gadsl2PlusMaxPsdLevelUpstream
--
-- - Added mask in following existing table.
--	- gxdslLineConfTable : gxdslLineOpModeMask
--	 -OpMode G.992.1 Annex A non overlapped
--	 -OpMode G.992.5 Annex A non overlapped
--       -OpMode G.992.1/G.992.5 Annex A MultiMode
--	 - Default is 0, which means not configured.
--
-- - Updated description
--     - gxdslLineConfTable
--	 - gxdslLineTpsTcMode: ATM Mode is also supported.
--
--  - Update description
--     - gxdslLineConfTable
--      - gxdslLineActualConfTpsTcMode: This object is supported
--
-- REVISION:    "2010052800000Z" 
-- DESCRIPTION: ISAM R4.2 MIB updates
-- Version:     3HH-08287-DCAA-PBZZA - E1P4 (for ISAM4.2)
-- Editor:      Aravindan Jagannathan
--
-- Updated the following attributes:
--  - Removed defn: gxdslLineConfTable   OBJECT IDENTIFIER ::= { gxdslLine 7 } 
--  - Defined IfIndex and changed ifIndex to IfIndex for gxdslGponOntIndex
--
--
-- REVISION:    "2010052700000Z" 
-- DESCRIPTION: ISAM R4.2 MIB updates
-- Version:     3HH-08287-DCAA-PBZZA - E1P3 (for ISAM4.2)
-- Editor:      Aravindan Jagannathan
--
-- gxdslGponOntDpboProfileNbr       
--   Changed type form AsamProfileIndex to AsamProfilePointer.
--   Changed range to 0..50 and added default value 0.
--
-- gxdslDpboProfileRowStatus       
--   Removed 'Active' option to keep it consistent with Spectrum/Service profiles.
--
--
-- REVISION:    "2010052600000Z" 
-- DESCRIPTION: ISAM R4.2 MIB updates
-- Version:     3HH-08287-DCAA-PBZZA - E1P2 (for ISAM4.2)
-- Editor:      Aravindan Jagannathan
--
-- Updated value range for the attributes:
--  gvdsl2VirtualNoisePsdDownstream
--  gvdsl2VirtualNoisePsdUpstream
--
-- Updated description for the attributes:
--  gvdsl2VirtualNoiseSnrmModeDownstream 
--  gvdsl2VirtualNoiseSnrmModeUpstream
--  gxdslLineActualVirtualNoiseSnrmModeUpstream
--  gxdslFarEndLineActualVirtualNoiseSnrmModeDownstream
--  gxdslDpboProfileRowStatus
--
-- Added a condition to the description:
--  gxdslDpboProfileVersionNbr - only allowed value is 1
--
-- Deleted the attribute:
--  gxdslGponOntRowStatus - not needed as the entries would be auto-created/deleted.
--
-- Updated the attribute:
--  gxdslGponOntIndex - changed type from IfIndex to ifIndex.
--
--
-- REVISION:    "2010052400000Z" 
-- DESCRIPTION: ISAM R4.2 MIB updates
-- Version:     3HH-08287-DCAA-PBZZA - E1P1 (for ISAM4.2)
-- Editor:      Kasi Viswanath, Vidya Kandasamy, Sengottuvelan Srirangan, Aravindan Jagannathan
--
--
-- Changes for IR ALU00312690: 
--
-- Added new table:
--  gxdslDpboProfile
--
-- Added a missing line for the gxdslLineConfTable:
--  gxdslLineConfTable				OBJECT IDENTIFIER ::= { gxdslLine 7 }
--
-- Added a new attribute:
--  gxdslLineDpboProfileNbr in gxdslLineConfTable
--
-- Added a new table:
--  gxdslDpboProfileMappingTable
--
-- Added a new table:
--  gxdslGponOntConfTable
--
-- Added declarations for:
--  ExchangePsdShapeType
--  DpboCustomPsdShapeType
--
-- Changes for IR ALU00312694:
--
-- Changed description for the following attributes:
--  gvdsl2VirtualNoisePsdDownstream
--  gvdsl2VirtualNoisePsdUpstream
--  gvdsl2VirtualNoiseSnrmModeDownstream
--  gvdsl2VirtualNoiseSnrmModeUpstream (snrmode value 3 is now supported)
--
-- Added gxdslFarEndLineActualVirtualNoiseSnrmModeDownstream attribute in gxdslFarEndLineOperDataTable
-- Added gxdslLineActualVirtualNoiseSnrmModeUpstream attribute in gxdslLineOperDataTable
--
--
--
-- REVISION     "2010051300000Z" 
--  DESCRIPTION
--     Version: 3HH-08287-DABA-PBZZA - E1P5 (for ISAM4.0.10)
--     Editor:  John Boyle
--     Changes:
--	- Removed references to specific previous FGUx.x releases.
--     		
--
-- REVISION     "2010042000000Z" 
--  DESCRIPTION
--     Version: 3HH-08287-DABA-PBZZA - E1P4 (for ISAM4.0.10)
--     Editor:  John Boyle
--     Changes:
--	- For FR IR ALU00280408: made following corrections to remove smilint warnings.
--     		- Commented out the following attributes, that were no longer necessary:
--			- gxdslLineConfTableEndMarker
--			- gxdslLineOperDataTableEndMarker
--
--
-- REVISION     "200911100000Z" 
--  DESCRIPTION
--     Version: 3HH-08287-DABA-PBZZA - E1P3 (for ISAM4.0.10)
--     Editor:  John Boyle
--     Changes:
--     In order to avoid object/group name clashes with ISAM XDSL MIB, made following changes:
--	Changed MIB name from XDSL-MIB to FTTU-XDSL-MIB in the MIB DEFINITIONs statement.
--
-- REVISION     "200911050000Z" 
--  DESCRIPTION
--     Version: 3HH-08287-DABA-PBZZA - E1P2 (for ISAM4.0.10)
--     Editor:  John Boyle
--     Changes:
--     In order to avoid object/group name clashes with ISAM XDSL MIB, made following changes:
--	Commented out the following::
-- 		- xdslCoding
-- 		- xdslLineSpectrumProfileAdslAdsl2Table
-- 		- xdslLineSpectrumProfileReAdsl2Table
-- 		- xdslLineSpectrumProfileAdsl2PlusTable
-- 		- xdslLineCurrent1DayTable
-- 		- xdslLinePrevious1DayTable
-- 		- xdslFarEndLineCurrent1DayTable
-- 		- xdslFarEndLinePrevious1DayTable
-- 		- xdslChannelCurrent1DayTable
-- 		- xdslChannelPrevious1DayTable
-- 		- xdslFarEndChannelCurrent1DayTable
-- 		- xdslFarEndChannelPrevious1DayTable
-- 		- All SCALARS in XDSL TEST GROUP
-- 		- xdslLinkUpTable
-- 		- xdslLinkUpTimestamp
-- 		- xdslLinkUpLineBitmapTable
--	Renamed (i.e. FROM xdsl TO gxdsl) all groups and subgroups in the MIB.
--	Renamed (i.e. FROM xdsl TO gxdsl) all objects associated with the following:
--		- xdslPerfInfoTable
--		- xdslLineServiceProfileIndexNext
--		- xdslLineServiceProfileMaxIndex
--		- xdslLineServiceProfileTable
--		- xdslLineServiceProfileChannelTable
--		- xdslLineServiceProfileMappingTable
--		- xdslLineSpectrumProfileIndexNext
--		- xdslLineSpectrumProfileMaxIndex
--		- xdslLineSpectrumProfileTable
--		- xdslLineSpectrumProfileVdslTable
--		- xdslLineSpectrumProfileMappingTable
--		- xdslLineSpectrumProfileVdsl2Table
--		- xdslLineConfTable
--		- xdslLineConfTableEndMarker
--		- xdslLineOperDataTable
--		- xdslLineOperDataTableEndMarker
--		- xdslLineCarrierDataTable
--		- xdslLineFailureStatusTable
--		- xdslLineCurrentIntervalTable
--		- xdslLinePreviousIntervalTable
--		- xdslFarEndLineOperDataTable
--		- xdslFarEndLineCarrierDataTable
--		- xdslFarEndLineFailureStatusTable
--		- xdslFarEndLineCurrentIntervalTable
--		- xdslFarEndLinePreviousIntervalTable
--		- xdslChannelOperDataTable
--		- xdslChannelCurrentIntervalTable
--		- xdslChannelPreviousIntervalTable
--		- xdslFarEndChannelOperDataTable
--		- xdslFarEndChannelCurrentIntervalTable
--		- xdslFarEndChannelPreviousIntervalTable
--		- xdslXturInventoryTable
--		- xdslXtucInventoryTable
--		- xdslLineTcaThresholdTable
--
--
-- REVISION     "200910220000Z" 
--  DESCRIPTION
--     Version: 3HH-08287-DABA-PBZZA - E1P1 (for ISAM4.0.10)
--     Editor:  John Boyle
--     Changes:
--  >> For xdslLineTable, noted following differences for following attributes:
--            - xdslLineServiceProfileNbr - changed lower range and default from 1 to 0.
--            - xdslLineSpectrumProfileNbr - changed lower range and default from 1 to 0.
--	- xdslLineRowStatus - NOT SUPPORTED
--	- xdslLineCustVlan - NOT SUPPORTED
--	- xdslLineQosProfile - NOT SUPPORTED
--	- xdslLineDscpPbitMapProfile - NOT SUPPORTED
--            - xdslLineAdminState - NOT SUPPORTED
--            - xdslLineOpState - NOT SUPPORTED
--	
--
--
-- REVISION     "200806050000Z" 
--  DESCRIPTION
--     Version: E1P2 (for FGU4.6)
--     Editor:  John Boyle
--     Changes:
--      - BDFam37203 - Business Service Requirements
--	- For xdslLineCustVlan attribute in xdslLineConfTable, extended the upper-end VLAN range from 4094 to 4095.
--
-- REVISION     "200806050000Z" 
--  DESCRIPTION
--     Version: E1P1 (for FGU4.6)
--     Editor:  John Boyle
--     Changes:
--      - ANTmt04646 - Support of 8port MDU (FGO4.4)
--	- For  xdslLineOpModeMask attribute in xdslLineConfTable, mentioned that the following values are supported
--	  along with the following compatible bandplans:
--		30a - (with bandplans A998, B998ADE, B998E)
--		17a - (with bandplans A998, B998ADE, B998E) - NOTE: 17a/A998 combo was added in FGU4.6.
--		12b - (with bandplans A998)
--	 	  8c - (with bandplans A998)
--
-- REVISION     "200712110000Z" 
--  DESCRIPTION
--     Version: E1P1 (for FGU4.5.5)
--     Editor:  John Boyle
--     Changes:
--	Mentioned that the following attributes are NOT SUPPORTED for FTTU4.5.5 (never have been for FTTU):
--		- xdslLineIsdnSplitterOptimization attribute in xdslLineConfTable
--		- xdslTestPOTSlineTestDuration attribute in Test Group
--		- xdslCoding attribute
--      - BDFam37366 - VDSL2 Support on M-300 - OLT RCR
--      - BDFam34326 - VDSL MIB Alignment with ISAM - OLT RCR
--	- For xdslLineOpMode attribute in xdslLineSpectrumProfileTable, changed the DEFAULT value note to say
--	  the following:
--	    FTTU FGU4.5.5 ignores the ISAM DEFVAL below, and instead should use following DEFAULT:
--	    '00 00 00 00 00 00 00 00 E4 00 00 00 00 00 00 00'H  (i.e. 30a, 17a, 12b and 8c allowed)
--	- For  xdslLineOpModeMask attribute in xdslLineConfTable, mentioned that the following values are supported
--	  along with the following compatible bandplans:
--		30a - with bandplans A998, B998ADE, B998E)
--		17a - with bandplans B998ADE, B998E)
--		12b - with bandplans A998)
--	 	  8c - with bandplans A998)
--	- For  xdslLineRfiBands attribute in xdslLineSpectrumProfileTable, mentioned that as of FGU4.5.5 the management
--	  interface is permitted to set custom notches.  And added a NOTE regarding OLT performing following VALIDATION:
--	  	- For each notch, StartFreq must be less than EndFreq.
--
--	
--
-- REVISION     "200706010000Z" 
--  DESCRIPTION
--     Version: E1P5
--     Editor:  John Boyle
--     Changes:
--    - For 	xdslLineRfiBands attribute in xdslLineSpectrumProfileTable, corrected a MIB error.
-- 	- Removed the old DEFAULT (that was actually replaced with new default in E1P2 version of this MIB).
--
--
-- REVISION     "200705310000Z" 
--  DESCRIPTION
--     Version: E1P4
--     Editor:  John Boyle
--     Changes:
--    - For 	xdslLineOpMode attribute in XdslLineSpectrumProfileTable, added the following notation:
--     	FTTU FGU4.4 ignores the DEFVAL below, and instead should use following DEFAULT:
--	'00 00 00 00 00 00 00 00 C0 00 00 00 00 00 00 00'H  (i.e. 30a and 17a allowed)
--
-- REVISION     "200705300000Z" 
--  DESCRIPTION
--     Version: E1P3
--     Editor:  John Boyle
--     Changes:
--    - For 	vdsl2PsdPboParamAUpstream and vdsl2PsdPboParamBUpstream attributes in XdslLineSpectrumProfileVdsl2Table, 
--	removed all restrictions regarding values for US0..US4.
--    - For xdslLineTargetNoiseMarginDownstream and xdslLineTargetNoiseMarginUpstream attributes in 
--	xdslLineSpectrumProfileTable, noted following limitation: 
--	Target Noise Margin must be <= Maximum Noise Margin
--
-- REVISION     "200705240000Z" 
--  DESCRIPTION
--     Version: E1P2
--     Editor:  John Boyle
--     Changes:
--    - For 	xdslLineRfiBands attribute in xdslLineSpectrumProfileTable, changed the DEFAULT
--	to accommodate 9 RFI band notches up through 30 MHz -  (per Lane Moss).
--
--      BDFam33200 - Global DSCP to PBit 
--    - For xdslLineDscpPbitMapProfile attribute in xdslLineConfTable, changed comments
--	that referred to QOS MIB (all DSCP-Pbit mapping profiles are in GPON MIB).
--
-- REVISION     "200705090000Z" 
--  DESCRIPTION
--     Version: E1P1 (for FGU4.4.10)
--     Editor:  John Boyle
--     Changes:
--      - ANTms35638 - VDSL Profiles for ETSI in FGU4.4
--	- For vdslBandPlan attribute in xdslLineSpectrumProfileVdslTable, noted that following band plan
--	  must be SUPPORTED for FGU4.4.10:
--		- bandPlanAnnexB998e
--
-- REVISION     "200704170000Z" 
--  DESCRIPTION
--     Version: E1P8
--     Editor:  John Boyle
--     Changes:
--      - For xdslMinImpNoiseProtDownstream and xdslMinImpNoiseProtUpstream attributes
--	 in xdslLineServiceProfileChannel, extended the range from 0..80 to 0..160 in order
--	 to accommodate up to 16 symbols (in 0.1 symbol increments).
--
--
-- REVISION     "200704090000Z" 
--  DESCRIPTION
--     Version: E1P7
--     Editor:  John Boyle
--     Changes:
--      - For xdslLineFailureStatus attribute in xdslLineFailureStatusTable, fixed comment regarding the 
--	newly defined bit position (value 512) that accounts for Line Initialization Failure.
--      - For xdslLinePwrShedOverride attribute in xdslLineConftable, corrected comment to clarify that
--	the line is associated with DSL class, not data class.
--      - Marked following attributes as NOT SUPPORTED for FGU4.4:
--	- xdslLineXtucOpModeCapabilities in xdslLineOperDataTable
--	- xdslFarEndLineXturOpModeCapabilities in xdslFarEndLineOperDataTable
--
-- REVISION     "200704050000Z" 
--  DESCRIPTION
--     Version: E1P6
--     Editor:  John Boyle
--     Changes:
--      - For xdslLine1DayESsTcaThreshold attribute in xdslLineTcaThresholdTable, commented that this
--	attribute is NOT SUPPORTED for FGU4.4.
--      - For xdslLineServiceProfileNbr and xdslLineSpectrumProfileNbr attributes in xdslLineConfTable,
--	made following comments:
--	   	FTTU4.4:  Valid range changed from 0..256 to 1..256. Changed 
--		default to from 0 to NA.  Valid value must be supplied by manager at 
--		row creation.
--                          
--
-- REVISION     "200704030000Z" 
--  DESCRIPTION
--     Version: E1P5
--     Editor:  John Boyle
--     Changes:
--      - For xdslLineFailureStatus attribute in xdslLineFailureStatusTable, defined a bit position (value 512) to 
--	account for Line Initialization Failure.
--
-- REVISION     "200703220000Z" 
--  DESCRIPTION
--     Version: E1P4
--     Editor:  John Boyle
--     Changes:
--      - For xdslXturInvSelfTestResults attribute in xdslXturInventoryTable, removed comment that last 4 bytes
--	would always be zero due to OMCI returning 4 bytes...because this attribute actually contains
--	the ASCII representation of hex value of each nibble of the 4 byte result.
--
-- REVISION     "200703120000Z" 
--  DESCRIPTION
--     Version: E1P3.
--     Editor:  John Boyle
--     Changes:
--     - Added xdslLineRowStatus attribute to xdslLineConfTable - since FTTU requires
--	explicit UNI row creation/deletion via manager action.
--     - Indicated that xdslXtucInventoryTable is SUPPORTED for FGU4.4 (including all
--	attributes defined in table).
--
-- REVISION     "200703050000Z" 
--  DESCRIPTION
--    "Version: E1P2.
--     Editor:  John Boyle
--     Changes:
--     - For xdslLineCarrierGroupLoad & xdslLineCarrierGroupGain attributes (and their
--	farEnd equivalents - made note that MIB will only support a value of 1.
--     - Scoped so the only SUPPORTED values are bandPlanAnnexA998 (default) and
--	 bandPlanAnnexB998ade.
--     - For vdslAdslBandUsage, removed NOT SUPPORTED comment, and added another
--	option 4: don't use 25KHz to 640Khz.  Mentioned that option 3 is NOT SUPPORTED.
--     - For vdsl2MaxAggregatePowerLevelDownstream attribute, changed lower range from -310
--	to 0 (to match OMCI). 
--     - For xdslPerfCurrentIntervalTimeElapsed attribute, changed to NOT SUPPORTED.
--     - For vdsl2PsdShapeDownstream attribute, mentioned that only 2 of the options are SUPPORTED,
--	and changed the default.
--     - For vdsl2RxPsdShapeUpstream attribute, mentioned that ABParam is only SUPPORTED option,
--	and made this the default.
--     - For vdsl2MaxPsdLevelDownstream and vdsl2MaxPsdLevelUpstream, changed range to -600..-300,
--	and changed default to -300.
--     - For vdsl2PsdPboParamAUpstream and vdsl2PsdPboParamBUpstream, made following changes:
--	Noted that US0 and US4 are NOT SUPPORTED (and must be 0).  Noted that values for US1 and US2
--	must be the same.  And changed the defaults to match what Lane Moss specified for Verizon.
--     - Noted that following attributes are NOT SUPPORTED:
--           vdsl2VirtualNoisePsdDownstream 
--           vdsl2VirtualNoisePsdUpstream 
--           vdsl2VirtualNoiseSnrmModeDownstream 
--           vdsl2VirtualNoiseSnrmModeUpstream 
--     - For xdslLineSpectrumProfileVersionNbr and xdslLineServiceProfileVersionNbr, noted that only
--	allowed value is 1 and cannot be incremented.
--     - For xdslLineRAModeDownstream and xdslLineRAModeUpstream, noted that only options
--	SUPPORTED are 1) operator controlled and 2) automatic at startup.
--     - For xdslLineNumberChannels, noted that only SUPPORTED value is 1 (single channel).
--     - For xdslLineConfEntry, noted that row creation and deletion is done explicitly by the manager (i..e. NOT
--	         automatically by the system).
--     - For xdslLineOpModeMask, noted that only 2 values are SUPPORTED (i.e. the bit patterns for
--	30a and 17a.
--     - For xdslLineOpModeBoardCapability, noted that attribute is NOT SUPPORTED.
--     - For xdslLineTpsTcMode, noted that PTM is the only SUPPORTED mode.
--     - For xdslLineOpModeAtmCapability and xdslLineOpModePtmCapability, noted that both attributes
--	are NOT SUPPORTED.
--     - For all PMs associated with LOS counters, noted that MIB contains value of LOS Seconds (i.e. not a count
--	of LOS events).  Applies to current & previous, near-end and far-end.
--     - For xdslLinePowerMgtMode, noted that ony SUPPORTED value is 0.
--     - For xdslXturInvSelfTestResults, noted the 4 least significant octets are always 0, since OMCI only reports 4 bytes.
--
--
-- REVISION     "200702080000Z" 
--  DESCRIPTION
--    "Version: Used For IP1 version of the FTTU XDSL PB spec.
--     Editor:  Atahan Tuzel
--     Changes:
--     FE and Previous Interval PMs amd Opstat are aligned with their NE equivalent for support notes
--     New Not Supported: CECs PM for Channel
--     New Not Supported: Electrical Length Estimate for FE Line
-- REVISION     "200702060000Z" 
--  DESCRIPTION
--    "Version: xxxx
--     Editor:  Atahan Tuzel
--     Changes:
--     New Index for xdslPerfInfoTable
--     New object in xdslPerfInfoTable for L2UNI Valid Intervals
--     New objects in xdslLineConfTable for:
--                  Administartive State
--                  Operational State
--                  Power Shedding
--                  DSCP Mapping
--     Newly supported: xdslLineCarrierDataMode
--     New Value for xdslLineCarrierDataMode to indicate failure
--     Newly supported: xdslLineLoopDiagnosticsMode
--     Newly supported: xdslLineRelCapacityOccupationUpstream
--     Newly supported: xdslFarEndLineRelCapacityOccupationUpstream
--     Newly supported: All objects except for TSS & Tx-PSD related ones in
--                      xdslLineCarrierDataTable
--                      xdslFarEndLineCarrierDataTable
--     New Value for xdslLineFailureStatus: 32 (LOL)
--     Newly supported: xdslChannelAttaibableBitrateUpstream
--     Newly supported: xdslFarEndChannelAttainableBitrateDownstream
--     Newly supported: xdslLineTcaThresholdTable for 
--                          15-min ES/SES/UAS Near End and Far END
--
--     See FGU4.4 pre-fixed notes
-- REVISION     "200612070000Z" 
--  DESCRIPTION
--    "Version: xxxx
--     Editor:  Atahan Tuzel
--     Changes: See FGU4.4 pre-fixed notes

-- REVISION     "200610160000Z"
--  DESCRIPTION
--    "Version: 3FE21279EAAA_V3.3.0.0.1
--     Editor:  Laurent Deru
--     Changes:
--     * BDFhw78319 : Artificial Noise
--       - addition of following object to xdslLineSpectrumProfileTable 
--           - xdslLineArtificialNoisePsdDownstream
--       - description of vdsl2VirtualNoisePsdDownstream and
--         vdsl2VirtualNoisePsdUpstream corrected : if virtual noise is defined
--         there must be at least two psd points. 
--    "
--  REVISION     "200608300000Z"
--  DESCRIPTION
--    "Version: 3FE21279EAAA_V3.3.0.0.0
--     Editor:  Karel Meijfroidt/Pierre Ceurvelts
--     Changes:
--     * Alcatel notes related to the number of supported xdslLineServiceProfiles
--       and xdslLineSpectrumProfiles updated from 100 to 256 where applicable
--     * ITU-T G993.2 bandPlans added
--    "
--
--  REVISION     "200606260000Z"
--  DESCRIPTION
--    "Version: 3FE21279EAAA_V3.2.0.0.0
--     Editor:  Agnes Lauryssens
--     Changes:
--     * Alcatel notes added
--       Not supported MIB objects commented out
--           xdslActDfltSpectrumProfileNbr
--           xdslActDfltServiceProfileNbr          
--           xdslNewDfltSpectrumProfileNbr         
--           xdslNewDfltServiceProfileNbr          
--           xdslDfltProfileModifyStatus
--       Frequency change 1100 -> 1104, 2000 -> 2008
--    "
--
--  REVISION     "200604260000Z"
--  DESCRIPTION
--    "Version: 3FE21279EAAA_V3.1.0.0.1
--     Editor : Agnes Lauryssens
--     Changes:
--     * description corrected of vdslMaxPsdLevelDownstream/Upstream and 
--       vdsl2MaxPsdLevelDownstream : integer range corrected (-995 corrected 
--       to - 955)
--     * description corrected of vdsl2VirtualNoisePsdUpstream (downstream
--       corrected to upstream)
--     * description corrected of vdsl2VirtualNoiseSnrmmodeDownstream/Upstream
--       and 
--       vdsl2VirtualNoisePsdDownstream/Upstream (snrmmode3 is for future use, 
--       VirtualNoisePsd only applicable for snrmmode2) 
--     * description corrected of xdslLineLoopDiagnosticMode (also applicable
--       for VDSL2) 
--    "
--
--  REVISION     "200602280000Z"
--  DESCRIPTION
--    "Version: 3FE21279EAAA_V3.1.0.0.0
--     Editor : Agnes Lauryssens
--     Changes:
-- * BDFhw50950: support of SRA on (Re)ADSL2/2+
--   - addition of following objects to xdslLineSpectrumProfileTable 
--       - xdslLineRAUNoiseMarginDownstream
--       - xdslLineRAUNoiseMarginUpstream
--       - xdslLineRAUTimeDownstream
--       - xdslLineRAUTimeUpstream
--       - xdslLineRADNoiseMarginDownstream
--       - xdslLineRADNoiseMarginUpstream
--       - xdslLineRADTimeDownstream
--       - xdslLineRADTimeUpstream
--    - addition of following objects to xdslLineCurrentIntervalTable
--       - xdslLineCurrentIntervalRAUCounter     
--       - xdslLineCurrentIntervalRADCounter
--    - addition of following objects to xdslLineCurrent1DayTable
--       - xdslLineCurrent1DayRAUCounter     
--       - xdslLineCurrent1DayRADCounter
--    - addition of following objects to xdslLinePreviousIntervalTable
--       - xdslLinePreviousIntervalRAUCounter     
--       - xdslLinePreviousIntervalRADCounter
--    - addition of following objects to xdslLinePrevious1DayTable
--       - xdslLinePrevious1DayRAUCounter     
--       - xdslLinePrevious1DayRADCounter
--    - addition of following objects to xdslFarEndLineCurrentIntervalTable
--       - xdslFarEndLineCurrentIntervalRAUCounter     
--       - xdslFarEndLineCurrentIntervalRADCounter
--    - addition of following objects to xdslFarEndLineCurrent1DayTable
--       - xdslFarEndLineCurrent1DayRAUCounter     
--       - xdslFarEndLineCurrent1DayRADCounter
--    - addition of following objects to xdslFarEndLinePreviousIntervalTable
--       - xdslFarEndLinePreviousIntervalRAUCounter     
--       - xdslFarEndLinePreviousIntervalRADCounter
--    - addition of following objects to xdslFarEndLinePrevious1DayTable
--       - xdslFarEndLinePrevious1DayRAUCounter     
--       - xdslFarEndLinePrevious1DayRADCounter
-- * BDFhw50951: support of Low Power (L2/L3) on (Re)ADSL2/2+
--   - addition of following object to xdslLineSpectrumProfileTable
--       - xdslLineL2AtprT
--   - addition of following object to xdslFarEndChannelOperDataTable
--       - xdslFarEndChannelActualL2LowPowerBitrateDownstream
-- *  others:
--   - description changed of objects 
--     adsl2PlusCustomPsdShapeDownstream/Upstream
--      OCTET 0 (frequency scale) put to reserved as this parameter is ignored
--      by the modem
--   - description changed of objects
--      adsl2PlusCustomPsdShapeDownstream/Upstream 
--      OCTET 3 (PSD level) range extended to 0 dBm/Hz (as defined in 
--      standards)
--      the same update done for :
--        - adslCustomPsdShapeDownstream/Upstream
--        - reAdsl2CustomPsdShapeDownstream/Upstream
--        - vdslCustomPsdShapeDownstream/Upstream
--        - vdslCustomRxPsdShapeUpstream
--        - vdsl2CustomPsdShapeDownstream/Upstream
--        - vdsl2CustomRxPsdShapeUpstream
--   - description changed of objects
--     adsl2PlusCustomPsdShapeDownstream/Upstream 
--      typo correction : adsl2PlusCustomPsdShapeDownstream ->
--      ...PsdDownstream
--      the same update done for :
--        - adslCustomPsdShapeDownstream/Upstream
--        - reAdsl2CustomPsdShapeDownstream/Upstream
--        - vdslCustomPsdShapeDownstream/Upstream
--   - description changed of xdsllineActualPsdDownstream and 
--     xdslFarEndLineActualPsdUpstream
--      restriction on applicability removed  
--   - description changed of objects xdslLineBondingModeChannel1/2/3/4 
--      set requests are ignored on these objects. 
--    "
--
--  REVISION     "200601130000Z"
--  DESCRIPTION
--    "Version: 3FE21279EAAA_V2.4.0.1.1
--     Editors: Etienne Henriet, D. Pholien
--     Changes:
-- * BDFhw65138: update description of xdslLineSpectrumProfileIndex to clarify
--   getnext behaviour. 
-- * BDFhw74515: mib corrections for VDSL2 and ADSL ATM mode support on VDSL
--   boards.
--   - update defval values of following parameters:
--     vdslOptBandUsage, vdslAdslBandUsage, vdslPboModeUpstream,
--     vdslRxPsdShapeUpstream, vdsl2PsdShapeDown/Upstream,
--     vdsl2RxPsdShapeUpstream, xdslLineTpsTcMode.
--   - TpsTcMode related changes:
--     Add new value (default) to TpsTcModeType.
--     Update description of xdslLineTpsTcMode, xdslLineOpModeMask,
--     xdslLineOpModeBoardCapability, xdslLineOpModeAtmCapability and
--     xdslLineOpModePtmCapability.
--     Add new parameter: xdslLineActualConfTpsTcMode.
--   - Update description of following parameters:
--      - xdslLineSpectrumProfileVdslTable and xdslLineSpectrumProfileVdslEntry
--      - all parameters in xdslLineSpectrumProfileVdslTable: indicate whether
--        VDSL1 specific or common to VDSL1/VDSL2
--      - xdslLineSpectrumProfileVdsl2Table
--      - vdsl2MaxAggregatePowerLevelDownstream/Upstream
--      - vdsl2RxPsdShapeUpstream
--      - vdsl2CustomRxPsdShapeUpstream
--      - vdsl2PsdPboElectrLengthUpstream
--      - vdsl2MaxPsdLevelDownstream/Upstream
--      - xdslLineHighestFrequencyUpstream and
--        xdslFarEndLineHighestFrequencyDownstream
--      - update parameters in xdslLineCarrierDataTable and
--        xdslFarEndLineCarrierDataTable: include up to 5 bands, use carrier
--        group indexing and make other editorial changes
--      - xdslLineCarrierTssDownstream/xdslFarEndLineCarrierTssUpstream: remove
--        definition (for further study)
--      - xdslLineCarrierTxPsdDownstream/xdslFarEndLineCarrierTxPsdUpstream:
--        update definition
--      - vdsl2VirtualNoisePsdDownstream/Upstream
--      - xdslLineServiceProfileScope and xdslLineSpectrumProfileScope
-- * BDFhw52676: Alm for low DSL ports rate and statistic
--   - add xdslLinkUpTable, xdslLinkUpTimestamp and xdslLinkUpLineBitmapTable.
--    "
--
--  REVISION     "200510140000Z"
--  DESCRIPTION
--    "Version: 3FE21279EAAA_E2.4.0.1 
--     Editor : Etienne Henriet
--     Changes:
-- * Review comments
-- * Status clarification of the network scope for the profiles
-- * Updates for ISAM R2.4 (VDSL2 and ADSL-1 mode support on VDSL boards)
-- *  RCR BDFhw41436
-- - OpModeBoardCapability has to be kept for backward compatibility reasons.
--   Behaviour changes.
-- - Replace FramingMode by standard terminology TpsTcMode.
-- - OpModeType extended to 16 bytes instead of 32.
-- *  RCR BDFhw39398
-- - Restructure VDSL tables to avoid unuseful duplication of information.
-- - Frequency ranges extended from 12000 to 30000 to account for VDSL2 range.
-- - Clarification of the Carrier Group role in the Carrier Data 
--   representation.
-- - Addition of the XTU-R/C Electrical Length and Timing Advance oper data.
-- - Addition of the actual TpcTcMode in the oper data.
-- - Update of VDSL-x default values
--    "
--
--  REVISION     "200509260000Z"
--  DESCRIPTION
--    "Version: 3FE21279EAAA_E2.4.0.0 
--     Editor : Etienne Henriet, Benoit Seutin
--     Changes
-- * Updates for ISAM R2.4 (VDSL2 and ADSL-1 mode support on VDSL boards)
-- *  RCR BDFhw41436
-- - Introduce FramingMode in xdslLineConfTable. Consequence:
--   OpModeBoardCapability becomes obsolete.
-- - Update line configuration/reconfiguration scenario
-- *  RCR BDFhw39398
-- - Add new bandPlan bandPlanAU2ext
-- - Add vdsl2PsdDownstream and vdsl2PsdDownstream types
-- - Add xdslErasureDetection to XdslLineServiceProfileChannelEntry
-- - Increase max bitrate range from 65535 to 262143 kbit/s
-- - Increase max number of RfiBands from 8 to 16
-- - Add new parameters to XdslLineSpectrumProfileVdslEntry. 
--   Consequence: a new value per tone set has to be added for 
--   vdslGhsTonesTxPowerControl.
-- - Increase max number of bands of vdslCustomBandPlan from 5 to 8
-- - Increase max number of Psd points of vdslCustomPsdShapeDown from 20 to 32
-- - Add xdslLineSpectrumProfileVdsl2Table new table
-- - Add new parameters to xdslLineOperDataEntry
-- - Add new Carrier Data type: CarrierTxPsd
-- - Add new CECs PM counter in xdslChannel
-- - Add support of Sub-Carrier Group
--    "

--
--  REVISION     "200509160000Z"
--  DESCRIPTION
--    "Version: 3FE21279EAAA_E2.3.0.2 / 3FE21279AAAA_E2.3.1.0
--     Editors: Diane Pholien, Zhang Gang
--     Changes:
--  * BDFhw49413: Add xdslLineSpectrumProfileIndexOffset and update the
--    description of xdslLineSpectrumProfileIndex to support the retrieval of
--    the updated parameter values during a spectrum profile modification.
--  * update description of xdslLineServiceProfileScope and
--    xdslLineSpectrumProfileScope
--  * BDFhw54799: Support of SRA & L0-L3 power mgt
--    update description of xdslLineRAModeDownstream/Upstream: RA Mode 3
--    supported
--    update description of xdslLineL0Time (line-up with standard)
--    update description of xdslLinePowerMgtMode
--    add object xdslLinePowerMgtState to xdslLineOperDataTable
--    "
--
--  REVISION     "200507050000Z"
--  DESCRIPTION
--    "Version: 3FE21279EAAA_E2.3.0.0
--     Editor : Diane Pholien
--     Changes:
--  * extend the vdslAdslBandUsage definition and add vdslAdslBandEndFreq
--    to configure the ADSL band (1.1 MHz, 2.2 MHz or configurable).
--  * add vdslGhsTonesTxPowerControl.
--  * add xdslLineServiceProfileMappingTable.
--  * add xdslLineSpectrumProfileMappingTable.
--    "
--
--  REVISION     "200506230000Z"
--  DESCRIPTION
--    "Version: 3FE21279EAAA_E2.2.1.0
--     Editor : Yoeri Apts
--     Changes:
--     * Addition of new vdslPsdShapeDownstream values.
--    "
--
--  REVISION     "200502210000Z"
--  DESCRIPTION
--    "Version: 3FE21279EAAA_E2.2.0.1
--     Editor : Diane Pholien
--     Changes:
--     * Description of xdslChannelActualImpNoiseProtDownstream and
--       xdslFarEndChannelActualImpNoiseProtUpstream: extend range to 16
--       symbols instead of 8.
--    "
--
--  REVISION     "200411100000Z"
--  DESCRIPTION
--    "Version: 3FE21279EAAA_E2.2.0.0
--     Editor : Frank Devolder
--     Changes:
--     * Configuration of VDSL Optional Band End Frequency
--    "
--
--  REVISION     "200410150000Z"
--  DESCRIPTION
--    "Version: 3FE21279AAAA_ E5.1.3.0
--     Editor : Frank Devolder
--     Changes:
--  * replace "ATM bitrate" by "net data rate", in order to cover ATM
--    as well as PTM mode (editorial change).
--  * extend OpMode bitmap with new VDSL mode IEEE 802.3ah
--  * vdslModemFeatures: update description
--  * define additional VDSL PSD shapes
--  * add xdslLineCarrierSpacingDownstream and 
--    xdslFarEndLineCarrierSpacingUpstream
--    "
--
--  REVISION     "200405190000Z"
--  DESCRIPTION
--    "Version: 3FE21279AAAA_E4.7.0.0
--     Editor : Frank Devolder
--     Changes:
--  * BDFhw11651: Support of ADSL2/ADSL2+ Annex M (extended upstream mode)
--    extend OpMode bitmap definition
--  * BDFhw08585: Multi-ADSL Bonding
--    define BondingModeType
--    add configurable object xdslLineBondingModeChannel1
--  * Redefine xdslLineCarrierTssDownstream and 
--    xdslFarEndLineCarrierTssUpstream
--  * xdslLineL0Time and xdslLineL2Time: extend range from 255s to 1800s
--    "
--
--  REVISION     "200403010000Z"
--  DESCRIPTION
--    "Version: 3FE21279AAAA_E4.5.1.3
--     Editor : Diane Pholien
--     Changes:
--  * CR BDFhw12585: The number of symbols needs 2 octets instead of 1,
--    update description of the following parameters:
--      xdslLineCarrierSnrUpstream
--      xdslLineCarrierQlnUpstream
--      xdslLineCarrierHlinUpstream
--      xdslLineCarrierHlogUpstream
--      xdslFarEndLineCarrierSnrDownstream
--      xdslFarEndLineCarrierQlnDownstream
--      xdslFarEndLineCarrierHlinDownstream
--      xdslFarEndLineCarrierHlogDownstream
--    "
--
--  REVISION     "200402060000Z"
--  DESCRIPTION
--    "Version: 3FE21279AAAA_E4.5.1.2
--     Editor : Diane Pholien
--     Changes:
--  * CR CR BDFhw07094: set DEFVAL value = 1 of following attributes:
--  adslModemFeatures, reAdsl2ModemFeatures, adsl2PlusModemFeatures,
--  vdslModemFeatures.
--  * CR BDFhw09154: update description of xdslLineXtucOpModeCapabilities
--  * CR BDFhw07219: change range of xdslMaxInterleavingDelayDownstream
--  and -Upstream to (1-63 ms), remove special value '0'.
--  * CR BDFhw11052: add new OID to xdslLineSpectrumProfileTable,
--  xdslLineSpectrumProfileModifyStatus.
--  * CR BDFhw12034: HLOG mi needs 2 bytes, update syntax description of
--  xdslLineCarrierHlogUpstream and -Downstream.
--  * line up customPsdShape range for all flavours and directions (US, DS,
--  RX US).
--  Correct VDSL US max aggregate range: [-310 to 255]
--    "
--
--  REVISION     "200310200000Z"
--  DESCRIPTION
--    "Version: 3FE21279AAAA_E4.5.1.1 (ED1 released version)
--     Editor : Diane Pholien
--    " 
--  
--  REVISION     "200310060000Z"
--  DESCRIPTION
--    "Version: 3FE21279AAAA_E4.5.1.0 (Ed1 proposal 3 version)
--     Editor : Diane Pholien
--    " 
-- ===============================================================================

FTTU-XDSL-MIB DEFINITIONS ::= BEGIN


IMPORTS
        
        Counter, 
        TimeTicks, 
        Gauge
                FROM RFC1155-SMI

        OBJECT-TYPE
                FROM RFC-1212
                
        ifIndex
                FROM ITF-MIB

        RowStatus
                FROM SNMPv2-TC

        asam
                FROM SYSTEM-MIB

        AsamNextProfileIndex, 
        AsamMaxProfileIndex, 
        AsamProfileIndex,
        AsamProfilePointer, 
        AsamProfileName, 
        AsamProfileScope,
        AsamProfileRefCount
                FROM ASAM-TC-MIB

        eqptSlotId
                FROM ASAM-EQUIP-MIB;

--FGU4.4: REPOSITIONING OF THE XDSL MIB UNDER AN APON BRANCH
apon                             OBJECT IDENTIFIER ::= { asam 35 }
fttuXdslMIB                      OBJECT IDENTIFIER ::= { apon 25 }
-- xdslMIB                          OBJECT IDENTIFIER ::= { asam 39 }
gxdslMIB                          OBJECT IDENTIFIER ::= { fttuXdslMIB 1}

-- groups in XDSL-MIB

gxdslLine                         OBJECT IDENTIFIER ::= { gxdslMIB 3 }

gxdslFarEndLine                   OBJECT IDENTIFIER ::= { gxdslMIB 4 }

gxdslChannel                      OBJECT IDENTIFIER ::= { gxdslMIB 5 }

gxdslFarEndChannel                OBJECT IDENTIFIER ::= { gxdslMIB 6 }

gxdslTest                         OBJECT IDENTIFIER ::= { gxdslMIB 7 }

gxdslXturInventory                OBJECT IDENTIFIER ::= { gxdslMIB 8 }

gxdslXtucInventory                OBJECT IDENTIFIER ::= { gxdslMIB 9 }

gxdslLineTcaThreshold             OBJECT IDENTIFIER ::= { gxdslMIB 10 }

gxdslChannelTcaThreshold          OBJECT IDENTIFIER ::= { gxdslMIB 11 }

gxdslLinkUp                       OBJECT IDENTIFIER ::= { gxdslMIB 12 }

gxdslDpboProfile					OBJECT IDENTIFIER ::= { gxdslMIB 13 }
gxdslGponOnt					    OBJECT IDENTIFIER ::= { gxdslMIB 14 }



-- further subgroups

gxdslLineServiceProfile           OBJECT IDENTIFIER ::= { gxdslLine 3 }

gxdslLineSpectrumProfile          OBJECT IDENTIFIER ::= { gxdslLine 6 }

gxdslLineCurrent                  OBJECT IDENTIFIER ::= { gxdslLine 8 }

gxdslLinePrevious                 OBJECT IDENTIFIER ::= { gxdslLine 9 }

gxdslLineDfltProfiles             OBJECT IDENTIFIER ::= { gxdslLine 11 }

gxdslRtxProfile                   OBJECT IDENTIFIER ::= { gxdslLine 14 }

gxdslFarEndLineCurrent            OBJECT IDENTIFIER ::= { gxdslFarEndLine 1 }

gxdslFarEndLinePrevious           OBJECT IDENTIFIER ::= { gxdslFarEndLine 2 }

gxdslChannelCurrent               OBJECT IDENTIFIER ::= { gxdslChannel 1 }

gxdslChannelPrevious              OBJECT IDENTIFIER ::= { gxdslChannel 2 }

gxdslFarEndChannelCurrent         OBJECT IDENTIFIER ::= { gxdslFarEndChannel 1 }

gxdslFarEndChannelPrevious        OBJECT IDENTIFIER ::= { gxdslFarEndChannel 2 }

gxdslTestTypes                    OBJECT IDENTIFIER ::= { gxdslTest 1 }

gxdslTestCodes                    OBJECT IDENTIFIER ::= { gxdslTest 2 }


GXdslRAModeType ::=           INTEGER {
                                 operatorControlledRateAdaptive(1),
                                 automaticRateAdaptiveAtStartup(2),
                                 dynamicRateAdaptive(3)
                                        }

GSplitterOptimizationType ::= INTEGER {
                                 pots      (1),
                                 isdn      (2)
                                 } 

GOpModeType ::=               OCTET STRING (SIZE (16))
-- Increased from 8 to 16 to support VDSL-2 and future flavours 

GTpsTcModeType ::=            INTEGER {
                                 atm        (1),
                                 ptm        (2),
                                 default    (3)
                                 }

GCarrierSpacingType ::=       INTEGER {
                                 singleCarrierSpacing(1),
                                 doubleCarrierSpacing(2),
                                 halfCarrierSpacing(3),
                                 quarterCarrierSpacing(4)
                                 }

GSubCarrierGroupSizeType ::= INTEGER (0..8) 
-- allowed invalid value 0 and valid values 1,2,4 and 8


GFrequencyType ::=            INTEGER(0..30000)
-- Expressed in kHz 

GVdslBandPlanType ::=         INTEGER {
                                 bandPlanCustom   (1),
                                 bandPlanA4       (2),
                                 bandPlanA3       (3),
                                 bandPlanA2       (4),
                                 bandPlanB4       (5),
                                 bandPlanB3       (6),
                                 bandPlanB2       (7),
                                 bandPlanC4       (8),
                                 bandPlanC3       (9),
                                 bandPlanC2      (10),
                                 bandPlanChinaA3 (11), 
                                 bandPlanChinaA2 (12),
                                 bandPlanChinaB3 (13),
                                 bandPlanChinaB2 (14),
                                 bandPlanAU2ext  (15),
                                 bandPlanAnnexA998 (16),
                                 bandPlanAnnexB997e (17),
                                 bandPlanAnnexB998e (18),      
                                 bandPlanAnnexB998ade (19), 
                                 bandPlanAnnexBhpe (20),    
                                 bandPlanAnnexC (21),
                                 bandPlanAnnexB998ade17ds30us35 (22),
                                 bandPlanAnnexB998e17ds30us35 (23),
                                 bandPlanAnnexB998ade17ds35 (24),
                                 bandPlanAnnexB998e17ds35 (25)              
                                 }

GOptBandUsageType ::=         INTEGER {
                                 optBandOff(1),
                                 optBandUpstream(2),
                                 optBandDownstream(3)
                                 }

GAdslPsdDownstreamType ::=    INTEGER {
                                 adslCustomPsdDownstream(1),
                                 adslStdPsdDownstream (2)
                                 }

GAdslPsdUpstreamType ::=      INTEGER {
                                 adslCustomPsdUpstream(1),
                                 adslStdPsdUpstream (2)
                                 }
GReAdsl2PsdDownstreamType ::= INTEGER {
                                 reAdsl2CustomPsdDownstream(1),
                                 reAdsl2StdPsdDownstream (2)
                                 }

GReAdsl2PsdUpstreamType ::=   INTEGER {
                                 reAdsl2CustomPsdUpstream(1),
                                 reAdsl2StdPsdUpstream (2)
                                 }


GAdsl2PlusPsdDownstreamType ::= INTEGER {
                                 adsl2PlusCustomPsdDownstream(1),
                                 adsl2PlusStdPsdDownstream (2),
                                 adsl2PlusCa100PsdDownstream (3),
                                 adsl2PlusCa110PsdDownstream (4),
                                 adsl2PlusCa120PsdDownstream (5),
                                 adsl2PlusCa130PsdDownstream (6),
                                 adsl2PlusCa140PsdDownstream (7),
                                 adsl2PlusCa150PsdDownstream (8),
                                 adsl2PlusCa160PsdDownstream (9),
                                 adsl2PlusCa170PsdDownstream (10),
                                 adsl2PlusCa180PsdDownstream (11),
                                 adsl2PlusCa190PsdDownstream (12),
                                 adsl2PlusCa200PsdDownstream (13),
                                 adsl2PlusCa210PsdDownstream (14),
                                 adsl2PlusCa220PsdDownstream (15),
                                 adsl2PlusCa230PsdDownstream (16),
                                 adsl2PlusCa240PsdDownstream (17),
                                 adsl2PlusCa250PsdDownstream (18),
                                 adsl2PlusCa260PsdDownstream (19),
                                 adsl2PlusCa270PsdDownstream (20),
                                 adsl2PlusCa280PsdDownstream (21)
                                 }

GAdsl2PlusPsdUpstreamType ::= INTEGER {
                                 adsl2PlusCustomPsdUpstream(1),
                                 adsl2PlusStdPsdUpstream (2)
                                 }

GVdslPsdDownstreamType ::=    INTEGER {
                                 vdslCustomPsdDownstream(1),
                                 vdslAnsiFttexM1PsdDownstream(2),
                                 vdslAnsiFttexM2PsdDownstream(3),
                                 vdslAnsiFttcabM1PsdDownstream(4),
                                 vdslAnsiFttcabM2PsdDownstream(5),
                                 vdslEtsiPexP1M1PsdDownstream(6),
                                 vdslEtsiPexP1M2PsdDownstream(7),
                                 vdslEtsiPexP2M1PsdDownstream(8),
                                 vdslEtsiPexP2M2PsdDownstream(9),
                                 vdslEtsiPcabM1PsdDownstream(10),
                                 vdslEtsiPcabM2PsdDownstream(11),
                                 vdslAnsiFttCabM1AdslPsdDownstream(12),
                                 vdslAnsiFttCabM2AdslPsdDownstream(13),
                                 vdslAnsiFttCabM1Adsl2PlusPsdDownstream(14),
                                 vdslAnsiFttCabM2Adsl2PlusPsdDownstream(15),
                                 vdslEtsiPcabXM1AdslPsdDownstream(16),
                                 vdslEtsiPcabXM2AdslPsdDownstream(17),
                                 vdslEtsiPcabM1Adsl2PlusPsdDownstream(18),
                                 vdslEtsiPcabM2Adsl2PlusPsdDownstream(19),
                                 vdslEtsiPexM2AdslSample1PsdDownstream(20),
                                 vdslEtsiPexM2AdslSample2PsdDownstream(21),
                                 vdslEtsiPexM2AdslSample3PsdDownstream(22),
                                 vdslEtsiPexM2AdslSample4PsdDownstream(23)
                                }

GVdslPsdUpstreamType ::=      INTEGER {
                                 vdslCustomPsdUpstream(1),
                                 vdslAnsiFttexM1PsdUpstream(2),
                                 vdslAnsiFttexM2PsdUpstream(3),
                                 vdslAnsiFttcabM1PsdUpstream(4),
                                 vdslAnsiFttcabM2PsdUpstream(5),
                                 vdslEtsiPM1PsdUpstream(6),
                                 vdslEtsiPM2PsdUpstream(7)
                                 }

GVdslRxPsdUpstreamType ::=    INTEGER {
                                 vdslCustomRxPsdUpstream(1),
                                 vdslAnsiARxPsdUpstream(2),
                                 vdslAnsiFRxPsdUpstream(3),
                                 vdslAnsiCustomExRxPsdUpstream(4),
                                 vdslAnsiCustomCabRxPsdUpstream(5),
                                 vdslEtsiARxPsdUpstream(6),
                                 vdslEtsiBRxPsdUpstream(7),
                                 vdslEtsiCRxPsdUpstream(8),
                                 vdslEtsiDRxPsdUpstream(9),
                                 vdslEtsiERxPsdUpstream(10),
                                 vdslEtsiFRxPsdUpstream(11),
                                 vdslEtsiCustomExRxPsdUpstream(12),
                                 vdslEtsiCustomCabRxPsdUpstream(13),
                                 vdslABParamRxPsdUpstream(14)
                                 }

GVdsl2PsdUpstreamType ::=     INTEGER {
                                 vdsl2CustomPsdUpstream(1),
                                 vdsl2RegionAPsdUpstream(2),
                                 vdsl2RegionBM1PsdUpstream(3),
                                 vdsl2RegionBM2PsdUpstream(4),
                                 vdsl2RegionCPsdUpstream(5)
                                 }

GVdsl2PsdDownstreamType ::=   INTEGER {
                                 vdsl2CustomPsdDownstream(1),
                                 vdsl2RegionAPsdDownstream(2),
                                 vdsl2RegionBM1PsdDownstream(3),
                                 vdsl2RegionBM2PsdDownstream(4),
                                 vdsl2RegionCPsdDownstream(5)
                                 }

GSnrmMode ::=                 INTEGER {
                                 snrmMode1(1),
                                 snrmMode2(2),
                                 snrmMode3(3)
                                 }

GCustomPsdShapeType ::=       OCTET STRING (SIZE (0..97))

GVirtualNoisePsdDownType ::=  OCTET STRING (SIZE (0..97))

GVirtualNoisePsdUpType ::=    OCTET STRING (SIZE (0..49))

GExchangePsdShapeType ::=     OCTET STRING (SIZE (0..65))

GDpboCustomPsdShapeType ::=   OCTET STRING (SIZE (0..129))

GPerBandABParamType  ::=      OCTET STRING (SIZE (10))

GPerBandOperDataType ::=      OCTET STRING (SIZE (10))

GPboModeType ::=              INTEGER {
                                 pboModeOff(1),
                                 pboModeOn(2)
                                 }

GBondingModeType ::=          INTEGER {
                                 native(1),
                                 atmBonding(2)
                                 }

GArtificialNoisePsdDownType ::=  OCTET STRING (SIZE (0..97))

Boolean ::= INTEGER (0..1)

IfIndex ::= INTEGER (1..2147483647)

GRtxMode ::=  INTEGER {
                       rtxForbidden  (1),
                       rtxPreferred  (2),
                       rtxForced     (3),
                       rtxTestmode   (4),
                       rtxNoOverrule (255)
                     }

-- FGU4.4: Double Indexing of the MIB
-- SpIndex is a FTTU definition that allows
-- indexing deeper into the ONT. The
-- coding semantics of this 32 bit index is defined
-- in the management interface (PB) document containing
-- this MIB (search for SpIndex for affected tables).
--
-- Due to the double indexing scheme introduced this way, the standard IF-tables 
-- can not be used. Therefore references to those tables and related behaviour
-- inherited from the base iSAM xDSL MIB is modified.

   SpIndex ::= INTEGER (1..2147483647)

-- XDSL MIB 

-- xdslCoding              OBJECT-TYPE
--         SYNTAX          INTEGER {
--                                  xdslCodingOther(1),
--                                  adslCodingDMT(2),
--                                  xdslCodingCAP(3)
--                                 }
--         ACCESS          read-only
--         STATUS          mandatory
--         DESCRIPTION 
--         "This object describes the type of modulation technique in use for the 
--          system.
-- 
--          ALCATEL NOTE:
--              ACCESS:   NA                  USAGE:    NA
--              PERSIST:  NO                  INSRVMOD: NA
--              RANGE:    adslCodingDMT       DEFVALUE: adslCodingDMT
--              UNITS:    NA                  SPARSE:   NA
--              DESCR:    NA
-- 
--   FTTU4.5.5 - attribute is NOT SUPPORTED (never has been for FTTU).
--      "
-- ::= {xdslMIB 1}
        
gxdslPerfInfoTable       OBJECT-TYPE 
        SYNTAX          SEQUENCE OF GxdslPerfInfoEntry
        ACCESS          not-accessible
        STATUS          mandatory
        DESCRIPTION     
        "The performance information table.

         ALCATEL NOTE:
             TABLESIZE: DEP [number of XDSL lines and number of XDSL channels]                    
             DESCR:     NA                  
        "
::= {gxdslMIB 2}

gxdslPerfInfoEntry       OBJECT-TYPE
        SYNTAX          GxdslPerfInfoEntry
        ACCESS          not-accessible
        STATUS          mandatory
        DESCRIPTION     
        "An entry in the XDSL PerfInfo table.

         Row creation : Entries for all XDSL lines and all XDSL channels belonging
                        to a board are created when the board becomes operational.
         Row deletion : Entries for all XDSL lines and all XDSL channels belonging
                        to a board are deleted when the board becomes unavailable.
        " 
        INDEX          {ifIndex, gxdslPerfSpIndex}
::= {gxdslPerfInfoTable 1}

GxdslPerfInfoEntry ::=
        SEQUENCE {
            gxdslPerfCurrentIntervalTimeElapsed        INTEGER,
            gxdslPerfCurrent1DayTimeElapsed            INTEGER,
            gxdslPerfValidIntervals                    INTEGER,
            gxdslPerfValid1Days                        INTEGER,
            gxdslPerfL2UNIValidIntervals               INTEGER,
            gxdslPerfSpIndex                           SpIndex
        }

gxdslPerfCurrentIntervalTimeElapsed     OBJECT-TYPE
        SYNTAX          INTEGER (1..900)
        ACCESS          read-only
        STATUS          mandatory
        DESCRIPTION     
        "The number of seconds, including partial seconds, that have elapsed 
         since the beginning of the current interval error-measurement period.

         ALCATEL NOTE:
             ACCESS:   NA                  USAGE:    NA
             PERSIST:  NO                  INSRVMOD: NA
             RANGE:    NA                  DEFVALUE: 0
             UNITS:    seconds             SPARSE:   NA
             DESCR:    NA

        FGU4.4: THIS OBJECT IS NOT SUPPORTED  "
::= {gxdslPerfInfoEntry 1}

gxdslPerfCurrent1DayTimeElapsed         OBJECT-TYPE
        SYNTAX          INTEGER (1..86400)
        ACCESS          read-only
        STATUS          mandatory
        DESCRIPTION     
        "The number of seconds, including partial seconds,bthat have elapsed 
         since the beginning of the current 1 day error-measurement period.

         ALCATEL NOTE:
             ACCESS:   NA                  USAGE:    NA
             PERSIST:  NO                  INSRVMOD: NA
             RANGE:    NA                  DEFVALUE: 0
             UNITS:    seconds             SPARSE:   NA
             DESCR:    NA

        FGU4.4: THIS OBJECT IS NOT SUPPORTED "
::= {gxdslPerfInfoEntry 2}

gxdslPerfValidIntervals                 OBJECT-TYPE  
        SYNTAX          INTEGER (0..192)
        ACCESS          read-only
        STATUS          mandatory
        DESCRIPTION 
        "The number of previous intervals for which valid data has been stored.
         An XDSL device must support at least n intervals. 
         The minimum value of n is 4, the default value of n is 32 and the 
         maximum value of n is 192. 
         The value of this object will be n unless the device was brought 
         online within the last nx15  minutes, in which case the value will be 
         the number of complete 15 minute intervals the device has been online.

         ALCATEL NOTE:
             ACCESS:   NA                  USAGE:    NA
             PERSIST:  NO                  INSRVMOD: NA
             RANGE:    NA                  DEFVALUE: 0
             UNITS:    NA                  SPARSE:   NA
             DESCR:    NA
        "
::= {gxdslPerfInfoEntry 3}

gxdslPerfValid1Days      OBJECT-TYPE
        SYNTAX          INTEGER (0..7)
        ACCESS          read-only
        STATUS          mandatory
        DESCRIPTION 
        "The number of previous 1Days for which valid data has been stored. 
         An XDSL device must support at least n days. The minimum value of n is
         1, the default value of n is 1 and the maximum value of n is 7. 
         The value of this object will be n unless the device was brought 
         online within the last nx24  hours, in which case the value will be 
         the number of complete days the device has been online.

         ALCATEL NOTE:
             ACCESS:   NA                  USAGE:    NA
             PERSIST:  NO                  INSRVMOD: NA
             RANGE:    0..1                DEFVALUE: 0
             UNITS:    NA                  SPARSE:   NA
             DESCR:    NA
        
        FGU4.4: THIS OBJECT IS NOT SUPPORTED "
::= {gxdslPerfInfoEntry 4}

gxdslPerfL2UNIValidIntervals                 OBJECT-TYPE  
        SYNTAX          INTEGER (0..192)
        ACCESS          read-only
        STATUS          mandatory
        DESCRIPTION 
        "The number of previous intervals for which valid data has been stored.
         An XDSL device must support at least n intervals. 
         The minimum value of n is 4, the default value of n is 32 and the 
         maximum value of n is 192. 
         The value of this object will be n unless the device was brought 
         online within the last nx15  minutes, in which case the value will be 
         the number of complete 15 minute intervals the device has been online.

         ALCATEL NOTE:
             ACCESS:   NA                  USAGE:    NA
             PERSIST:  NO                  INSRVMOD: NA
             RANGE:    NA                  DEFVALUE: 0
             UNITS:    NA                  SPARSE:   NA
             DESCR:    NA
        
FGU4.4: THIS OBJECT IS ADDED IN ORDER TO ACCOUNT FOR L2-UNI PM THAT  CAN BE TURNED ON/OFF separately from XDSL LINE AND CHANNEL PM"
::= {gxdslPerfInfoEntry 5}

gxdslPerfSpIndex  OBJECT-TYPE
	SYNTAX 	SpIndex
	ACCESS	not-accessible
	STATUS	mandatory
	DESCRIPTION 
		"Each row is also indexed by a number that
		 contains the slot number and port number
		 within the ONT. 
           
             ALCATEL NOTE: THIS OBJECT IS ADDED TO THE xDSL MIB DUE TO THE 
                           DOUBLE INDEXING SCHEME THAT DOES NOT ALLOW THE USE        
                           OF STANDARD IF-TABLES TO FULL EXTENT "
	::= { gxdslPerfInfoEntry 6 }


-- The XDSL Line Group

gxdslLineServiceProfileIndexNext        OBJECT-TYPE
        SYNTAX          AsamNextProfileIndex
        ACCESS          read-only
        STATUS          mandatory
        DESCRIPTION     
        "This object contains an appropriate value to be used for 
         xdslLineServiceProfileIndex when creating entries in the
         xdslLineServiceProfileTable. 
         The value 0 indicates that no unassigned entries are available. To 
         obtain the xdslLineNextServiceProfileIndex value for a new entry, the
         manager issues a management protocol retrieval operation to obtain the
         current value of this object.  After each retrieval, the agent should
         modify the value to the next unassigned index.

         ALCATEL NOTE:
             ACCESS:   NA                  USAGE:    NA
             PERSIST:  NO                  INSRVMOD: NA
             RANGE:    0..256              DEFVALUE: 1
             UNITS:    NA                  SPARSE:   NA
             DESCR:    NA
        "
::= {gxdslLine 1}

gxdslLineServiceProfileMaxIndex         OBJECT-TYPE
        SYNTAX          AsamMaxProfileIndex
        ACCESS          read-only
        STATUS          mandatory
        DESCRIPTION
        "This object represents the maximum number of xdslLineServiceProfiles
         that can be created. The object xdslLineServiceProfileIndexNext will 
         have values ranging from 1 to the value represented by this object.

         ALCATEL NOTE:
             ACCESS:   NA                  USAGE:    NA
             PERSIST:  NO                  INSRVMOD: NA
             RANGE:    256..256            DEFVALUE: 256
             UNITS:    NA                  SPARSE:   NA
             DESCR:    NA
        "
::= {gxdslLine 2}

gxdslLineServiceProfileTable            OBJECT-TYPE
        SYNTAX          SEQUENCE OF GxdslLineServiceProfileEntry
        ACCESS          not-accessible
        STATUS          mandatory
        DESCRIPTION     
        "This table contains the service related parameters of the modem
         configuration. One entry in this table reflects a profile which can
         be used to configure the modem for a physical line.

         ALCATEL NOTE:
             TABLESIZE: 256                    
             DESCR:     NA                  
         "
::= {gxdslLineServiceProfile 1}

gxdslLineServiceProfileEntry            OBJECT-TYPE
        SYNTAX          GxdslLineServiceProfileEntry
        ACCESS          not-accessible
        STATUS          mandatory
        DESCRIPTION     
        "Each entry consists of a list of service related parameters that serve 
         to configure an XDSL modem. A profile can be created in one step with
         all necessary parameter values and xdslLineServiceProfileRowStatus set
         to createAndGo.
         It can also be created in several steps by specifying values of a few
         objects in each step. The xdslLineServiceProfileRowStatus is set to
         createAndWait in the first step and to Active in the last step.

         Row creation : An entry is created when the manager requests to create
                        a service profile.
         Row deletion : An entry is deleted when the manager requests to delete
                        a service profile.
        "
        INDEX          {gxdslLineServiceProfileIndex}
::= {gxdslLineServiceProfileTable 1}

GxdslLineServiceProfileEntry ::=
        SEQUENCE {
            gxdslLineServiceProfileIndex               AsamProfileIndex,
            gxdslLineServiceProfileName                AsamProfileName,
            gxdslLineServiceProfileScope               AsamProfileScope,
            gxdslLineServiceProfileVersionNbr          INTEGER,
            gxdslLineServiceProfileUsedStatus          AsamProfileRefCount,
            gxdslLineRAModeDownstream                  GXdslRAModeType,
            gxdslLineRAModeUpstream                    GXdslRAModeType,
            gxdslLineNumberChannels                    INTEGER,
            gxdslLineServiceProfileRowStatus           RowStatus
        }

gxdslLineServiceProfileIndex            OBJECT-TYPE
        SYNTAX          AsamProfileIndex
        ACCESS          not-accessible
        STATUS          mandatory
        DESCRIPTION     
        "This object is used to uniquely identify an entry in this table.
         It is used by the line configuration table to identify a row of this
         table. The max value of this object is limited to
         xdslLineServiceProfileMaxIndex value.

         ALCATEL NOTE:
             ACCESS:   NA                  USAGE:    NA
             PERSIST:  YES                 INSRVMOD: NA
             RANGE:    1..256              DEFVALUE: NA
             UNITS:    NA                  SPARSE:   NA
             DESCR:    NA
        "
::= {gxdslLineServiceProfileEntry 1}

gxdslLineServiceProfileName             OBJECT-TYPE
        SYNTAX          AsamProfileName
        ACCESS          read-write
        STATUS          mandatory
        DESCRIPTION     
        "A textual name identifying this profile. This name has to be unique
         within the assigned scope.

         ALCATEL NOTE:
             ACCESS:   NA                  USAGE:    MAND 
             PERSIST:  YES                 INSRVMOD: YES
             RANGE:    NA                  DEFVALUE: NA
             UNITS:    characters          SPARSE:   NA
             DESCR:    NA
        "
::= {gxdslLineServiceProfileEntry 2}

gxdslLineServiceProfileScope            OBJECT-TYPE
        SYNTAX          AsamProfileScope
        ACCESS          read-write
        STATUS          mandatory
        DESCRIPTION     
        "A profile can be qualified as having a local scope or a network wide 
         scope. As some managers may not support the network profile scope,
         the use of local scope is strongly recommended.

         ALCATEL NOTE:
             ACCESS:   NA                  USAGE:    OPT 
             PERSIST:  YES                 INSRVMOD: YES
             RANGE:    NA                  DEFVALUE: NA
             UNITS:    NA                  SPARSE:   NA
             DESCR:    NA
        "
        DEFVAL          {localScope}
::= {gxdslLineServiceProfileEntry 3}

gxdslLineServiceProfileVersionNbr       OBJECT-TYPE
        SYNTAX          INTEGER
        ACCESS          read-write
        STATUS          mandatory
        DESCRIPTION     
        "The manager can associate a version number to the profile. It is set 
         to 1 when the profile is first created and will be incremented by the
         manager when the profile is modified.

         ALCATEL NOTE:
             ACCESS:   NA                  USAGE:    OPT 
             PERSIST:  YES                 INSRVMOD: NO
             RANGE:    NA                  DEFVALUE: NA
             UNITS:    NA                  SPARSE:   NA
             DESCR:    NA

     For FGU4.4, only allowed value is 1 and cannot be incremented. "
        DEFVAL          {1}
::= {gxdslLineServiceProfileEntry 4}

gxdslLineServiceProfileUsedStatus       OBJECT-TYPE
        SYNTAX          AsamProfileRefCount
        ACCESS          read-only
        STATUS          mandatory
        DESCRIPTION
        "Indicates the number of entities using this profile. If the reference
         count is greater than 0, then this profile is 'in use', and may NOT be
         deleted. If the value is 0, then this profile is 'not in use', and can
         be deleted.  
       
         ALCATEL NOTE:
             ACCESS:   NA                  USAGE:    NA
             PERSIST:  NO                  INSRVMOD: NA
             RANGE:    NA                  DEFVALUE: 0
             UNITS:    NA                  SPARSE:   NA
             DESCR:    NA
        "
::= {gxdslLineServiceProfileEntry 5}

gxdslLineRAModeDownstream               OBJECT-TYPE
        SYNTAX          GXdslRAModeType
        ACCESS          read-write
        STATUS          mandatory
        DESCRIPTION     
        "This object specifies the mode for rate adaptation for the downstream 
         direction: 

         operatorControlledRateAdaptive(1): 
         The object xdslPlannedBitrateDownstream specifies the bitrate the 
         modem must operate at for the corresponding bearer channel in the
         downstream direction, with a noise margin which is larger or equal to
         the specified Target Noise Margin. If the modem fails to achieve 
         this bitrate, it will reinitialize. Although the modem and the line
         might be able to support a higher bitrate, the modem will not transmit
         at a higher rate  than what is requested.
         The modem will maintain the specified planned bitrate during showtime.
         
         automaticRateAdaptiveAtStartup(2) :     
         The object xdslMinBitrateDownstream specifies the minimum data rate 
         the modem must operate at in the downstream direction, with a noise
         margin which is larger or equal to the specified Target Noise Margin.
         If it fails to achieve this bitrate the modem will reinitialize.
         As long as the data rate is below the maximum bitrate, bitrate
         increase has priority over transmit power reduction. The modem is not
         allowed to set up a data rate that is higher than the specified
         maximum data rate. The xdslLineRARatioDownstream object specifies how
         bitrate in excess of the minimum bitrate must be allocated among
         multiple channels. 
         During showtime no rate adaptation is allowed. 

         dynamicRateAdaptive(3):  
         In this mode, the data rate is automatically selected at startup (as
         in mode 2), but during showtime, rate adaptation is allowed. The
         downstream data rate can vary between the downstream minimum data rate
         and the downstream maximum data rate. Downstream Rate Adaptation is
         performed when the conditions specified for Downstream Upshift Noise
         Margin and Downstream Upshift Interval - or for Downstream Downshift
         Noise Margin and Downstream Downshift Interval - are satisfied.

         ALCATEL NOTE:
             ACCESS:   NA                  USAGE:    OPT
             PERSIST:  YES                 INSRVMOD: NO
             RANGE:    NA                  DEFVALUE: NA
             UNITS:    NA                  SPARSE:   NA
             DESCR:    NA

      For FGU4.4, only options SUPPORTED are:
	operatorControlledRateAdaptive(1)
	automaticRateAdaptiveAtStartup(2)
        "
        DEFVAL          {automaticRateAdaptiveAtStartup}           
    ::= {gxdslLineServiceProfileEntry 6}

gxdslLineRAModeUpstream  OBJECT-TYPE
        SYNTAX          GXdslRAModeType
        ACCESS          read-write
        STATUS          mandatory
        DESCRIPTION     
        "This object specifies the mode for rate adaptation for the upstream 
         directions:

         operatorControlledRateAdaptive(1): 
         The object xdslPlannedBitrateUpstream specifies the bitrate the 
         modem must operate at for the corresponding bearer channel in the
         upstream direction, with a noise margin which is larger or equal to
         the specified Target Noise Margin. If the modem fails to achieve 
         this bitrate, it will reinitialize. Although the modem and the line
         might be able to support a higher bitrate, the modem will not transmit
         at a higher rate  than what is requested.
         The modem will maintain the specified planned bitrate during showtime.

         automaticRateAdaptiveAtStartup(2) :     
         The object xdslMinBitrateUpstream specifies the minimum data rate 
         the modem must operate at in the upstream direction, with a noise
         margin which is larger or equal to the specified Target Noise Margin.
         If it fails to achieve this bitrate the modem will reinitialize.
         As long as the data rate is below the maximum bitrate, bitrate
         increase has priority over transmit power reduction. The modem is not
         allowed to set up a data rate that is higher than the specified
         maximum data rate. The xdslLineRARatioUpstream object specifies how
         bitrate in excess of the minimum bitrate must be allocated among
         multiple channels. 
         During showtime no rate adaptation is allowed. 

         dynamicRateAdaptive(3):
         In this mode, the data rate is automatically selected at startup (as
         in mode 2), but during showtime, rate adaptation is allowed. The
         upstream data rate can vary between the upstream minimum data rate and
         the upstream maximum data rate. Upstream Rate Adaptation is performed
         when the conditions specified for Upstream Upshift Noise Margin and
         Upstream Upshift Interval - or for Upstream Downshift Noise Margin and
         Upstream Downshift Interval - are satisfied.

         ALCATEL NOTE:
             ACCESS:   NA                  USAGE:    OPT
             PERSIST:  YES                 INSRVMOD: NO
             RANGE:    NA                  DEFVALUE: NA
             UNITS:    NA                  SPARSE:   NA
             DESCR:    NA

      For FGU4.4, only options SUPPORTED are:
	operatorControlledRateAdaptive(1)
	automaticRateAdaptiveAtStartup(2)
        "
        DEFVAL          {automaticRateAdaptiveAtStartup}           
::= {gxdslLineServiceProfileEntry 7}

gxdslLineNumberChannels  OBJECT-TYPE
        SYNTAX          INTEGER
        ACCESS          read-write
        STATUS          mandatory
        DESCRIPTION     
        "This object defines the number of channels on the xdsl line.
         Range: 1 to 4 channels. 

         ALCATEL NOTE:
             ACCESS:   NA                  USAGE:    OPT
             PERSIST:  YES                 INSRVMOD: NO
             RANGE:    1                   DEFVALUE: NA
             UNITS:    channels            SPARSE:   NA
             DESCR:    The object is supported to avoid future database 
                       migration but should not be set.
                       Set requests will be rejected (badvalue) if the value
                       differs from the default value.

     FGU4.4:  The only value SUPPORTED is 1 (single channel)  "
        DEFVAL          {1}           
::= {gxdslLineServiceProfileEntry 8}

gxdslLineServiceProfileRowStatus        OBJECT-TYPE
        SYNTAX          RowStatus
        ACCESS          read-write
        STATUS          mandatory
        DESCRIPTION 
        "This object is used to create a new row or delete an existing row in
         this table. The usage is as per standard semantics of 'RowStatus'
         defined in SNMPv2-TC.
            o Both 'createAndGo' and 'createAndWait' options of row creation
              are supported.
            o The entry associated with a Profile that is being used may
              not be deleted.

         ALCATEL NOTE:
             ACCESS:   NA                  USAGE:    MAND
             PERSIST:  YES                 INSRVMOD: YES
             RANGE:    NA                  DEFVALUE: NA
             UNITS:    NA                  SPARSE:   NA
             DESCR:    NA
        "
::= {gxdslLineServiceProfileEntry 9}

gxdsllLineServiceProfileChannelTable     OBJECT-TYPE
        SYNTAX          SEQUENCE OF GxdsllLineServiceProfileChannelEntry
        ACCESS          not-accessible
        STATUS          mandatory
        DESCRIPTION     
        "This table contains the service related parameters that characterize
         the bearer channels within an xdslLineServiceProfile. The creation of
         an xdslLineServiceProfileEntry includes the creation of an
         xdslLineServiceProfileChannelEntry for each channel of the service
         profile(i.e.  xdslLineNumberChannels entries in total).

         ALCATEL NOTE:
             TABLESIZE: DEP [256 * number of channels (1)]                    
             DESCR:     NA                  
        "
::= {gxdslLineServiceProfile 2}

gxdsllLineServiceProfileChannelEntry     OBJECT-TYPE
        SYNTAX          GxdsllLineServiceProfileChannelEntry
        ACCESS          not-accessible
        STATUS          mandatory
        DESCRIPTION     
        "Each entry consists of a list of service related parameters that serve 
         to configure one bearer channel of an xdsl modem configuration
         profile.

         Row creation : When an entry is created in the 
                        xdslLineServiceProfileTable, entries (for each channel)
                        with the same xdslLineServiceProfileIndex are created in
                        this table.
         Row deletion : When an entry is deleted from the
                        xdslLineServiceProfileTable, the entries (for each 
                        channel) with the same xdslLineServiceProfileIndex are
                        deleted from this table. 
        "
        INDEX          {gxdslLineServiceProfileIndex,
                        gxdsllLineServiceProfileChannelNumber}
::= {gxdsllLineServiceProfileChannelTable 1}

GxdsllLineServiceProfileChannelEntry ::=
        SEQUENCE {
            gxdsllLineServiceProfileChannelNumber       INTEGER,
            gxdsllRARatioDownstream                     INTEGER,
            gxdsllRARatioUpstream                       INTEGER,
            gxdsllMinBitrateDownstream                  INTEGER,
            gxdsllMinBitrateUpstream                    INTEGER,
            gxdsllPlannedBitrateDownstream              INTEGER,
            gxdsllPlannedBitrateUpstream                INTEGER,
            gxdsllMaxBitrateDownstream                  INTEGER,
            gxdsllMaxBitrateUpstream                    INTEGER,
            gxdsllL2LowPowerBitrateDownstream           INTEGER,
            gxdsllMaxInterleavingDelayDownstream        INTEGER,
            gxdsllMaxInterleavingDelayUpstream          INTEGER,
            gxdsllMinImpNoiseProtDownstream             INTEGER,
            gxdsllMinImpNoiseProtUpstream               INTEGER,
            gxdsllErasureDetectionDownstream            INTEGER,
            gxdsllErasureDetectionUpstream              INTEGER
        }

gxdsllLineServiceProfileChannelNumber    OBJECT-TYPE
        SYNTAX          INTEGER
        ACCESS          not-accessible
        STATUS          mandatory
        DESCRIPTION     
        "This object is used by the xdslLineServiceProfileChannelTable
         together with the xdslLineServiceProfileIndex to identify a row of
         this table. Range: 1 to 4.

         ALCATEL NOTE:
             ACCESS:   NA                  USAGE:    NA
             PERSIST:  YES                 INSRVMOD: NA
             RANGE:    NA                  DEFVALUE: NA
             UNITS:    NA                  SPARSE:   NA
             DESCR:    NA
        "
::= {gxdsllLineServiceProfileChannelEntry 1}

gxdsllRARatioDownstream   OBJECT-TYPE
        SYNTAX          INTEGER
        ACCESS          read-write
        STATUS          mandatory
        DESCRIPTION     
        "This object specifies the ratio that should be taken into account for
         allocating available data rate (in excess of the minimum data rate
         summed over all bearer channels) among the different bearer channels
         in the downstream direction.
         The ratio is defined as a percentage from 0 to 100.
         This parameter is only meaningfull in case multiple channels are used
         (e.g. 2 for dual latency, possibly up to 4 in the future for ADSL2)
         and must be fixed to 100 in case of single latency.
         The sum of the raRatios for all channels should be 100.
         The excessive bitrate (i.e. the available bitrate - the sum of the
         minimum bitrates) must be distributed among the different channels
         according to their respective raRatio.
         When the max bitrate is achieved for one of the channels, the raRatio
         of that channel must be distributed to the other channels according to
         their respective raRatio share.
         E.g. in case of 3 channels/raRatios: ch1/50%, ch2/20%, ch3/30%
         When ch1 max bit rate is achieved, its 50% raRatio is distributed 
         among ch2 (+20%) and ch3 (+30%) -> ch2/40%, ch3/60%.

         ALCATEL NOTE:
             ACCESS:   NA                  USAGE:    OPT
             PERSIST:  YES                 INSRVMOD: NO
             RANGE:    100                 DEFVALUE: 100
             UNITS:    percent             SPARSE:   NA
             DESCR:    The object is supported to avoid future database 
                       migration but should not be set.
                       Set requests will be rejected (badvalue) if the value
                       differs from the default value.
        "
::= {gxdsllLineServiceProfileChannelEntry 2}

gxdsllRARatioUpstream     OBJECT-TYPE
        SYNTAX          INTEGER
        ACCESS          read-write
        STATUS          mandatory
        DESCRIPTION     
        "This object specifies the ratio that should be taken into account for
         allocating available data rate (in excess of the minimum data rate
         summed over all bearer channels) among the different bearer channels
         in the upstream direction.
         The ratio is defined as a percentage from 0 to 100.
         This parameter is only meaningfull in case multiple channels are used
         (e.g. 2 for dual latency, possibly up to 4 in the future for ADSL2)
         and must be fixed to 100 in case of single latency.
         The sum of the raRatios for all channels should be 100.
         The excessive bitrate (i.e. the available bitrate - the sum of the
         minimum bitrates) must be distributed among the different channels
         according to their respective raRatio.
         When the max bitrate is achieved for one of the channels, the raRatio
         of that channel must be distributed to the other channels according to
         their respective raRatio share.
         E.g. in case of 3 channels/raRatios: ch1/50%, ch2/20%, ch3/30%
         When ch1 max bit rate is achieved, its 50% raRatio is distributed
         among ch2 (+20%) and ch3 (+30%) -> ch2/40%, ch3/60%.

         ALCATEL NOTE:
             ACCESS:   NA                  USAGE:    OPT
             PERSIST:  YES                 INSRVMOD: NO
             RANGE:    100                 DEFVALUE: 100
             UNITS:    percent             SPARSE:   NA
             DESCR:    The object is supported to avoid future database 
                       migration but should not be set.
                       Set requests will be rejected (badvalue) if the value
                       differs from the default value.
        "
::= {gxdsllLineServiceProfileChannelEntry 3}

gxdsllMinBitrateDownstream               OBJECT-TYPE
        SYNTAX          INTEGER
        ACCESS          read-write
        STATUS          mandatory
        DESCRIPTION     
        "This object contains the minimum bitrate that must be set up and
         maintained downstream in case of automaticRateAdaptiveAtStartup RA
         mode. This parameter has no meaning in operatorControlledRateAdaptive
         RA mode. 
         
         ALCATEL NOTE:
             ACCESS:   NA                  USAGE:    OPT
             PERSIST:  YES                 INSRVMOD: NO
             RANGE:    0..262143           DEFVALUE: 1024
             UNITS:    kbits/sec           SPARSE:   NA
             DESCR:    NA
        "
::= {gxdsllLineServiceProfileChannelEntry 4}   
        
        
gxdsllMinBitrateUpstream  OBJECT-TYPE
        SYNTAX          INTEGER
        ACCESS          read-write
        STATUS          mandatory
        DESCRIPTION     
        "This object contains the minimum bitrate that must be set up and
         maintained upstream in case of automaticRateAdaptiveAtStartup RA
         mode. This parameter has no meaning in operatorControlledRateAdaptive
         RA mode. 

         ALCATEL NOTE:
             ACCESS:   NA                  USAGE:    OPT
             PERSIST:  YES                 INSRVMOD: NO
             RANGE:    0..262143           DEFVALUE: 64
             UNITS:    kbits/sec           SPARSE:   NA
             DESCR:    NA
       "
::= {gxdsllLineServiceProfileChannelEntry 5}

gxdsllPlannedBitrateDownstream           OBJECT-TYPE
        SYNTAX          INTEGER
        ACCESS          read-write
        STATUS          mandatory
        DESCRIPTION     
        "This object contains the planned bitrate for the downstream data flow.
         It specifies the bit rate that must be set up and maintained in case
         of operatorControlledRateAdaptive RA mode. 

         ALCATEL NOTE:
             ACCESS:   NA                  USAGE:    OPT
             PERSIST:  YES                 INSRVMOD: NO
             RANGE:    0..262143           DEFVALUE: 1536
             UNITS:    kbits/sec           SPARSE:   NA
             DESCR:    NA
        
         FGU4.4:  THIS OBJECT IS NOT SUPPORTED "
::= {gxdsllLineServiceProfileChannelEntry 6}

gxdsllPlannedBitrateUpstream             OBJECT-TYPE
        SYNTAX          INTEGER
        ACCESS          read-write
        STATUS          mandatory
        DESCRIPTION     
        "This object contains the planned bitrate for the upstream data flow.
         It specifies the bit rate that must be set up and maintained in case
         of operatorControlledRateAdaptive RA mode.
 
         ALCATEL NOTE:
             ACCESS:   NA                  USAGE:    OPT
             PERSIST:  YES                 INSRVMOD: NO
             RANGE:    0..262143           DEFVALUE: 128
             UNITS:    kbits/sec           SPARSE:   NA
             DESCR:    NA
        
         FGU4.4:  THIS OBJECT IS NOT SUPPORTED "
::= {gxdsllLineServiceProfileChannelEntry 7}
                        
gxdsllMaxBitrateDownstream               OBJECT-TYPE
        SYNTAX          INTEGER
        ACCESS          read-write
        STATUS          mandatory
        DESCRIPTION     
        "This object contains the maximum allowed bit rate which can be set up
         and maintained downstream in case of automaticRateAdaptiveAtStartup RA
         mode. This parameter has no meaning in operatorControlledRateAdaptive
         RA mode. 

         ALCATEL NOTE:
             ACCESS:   NA                  USAGE:    OPT
             PERSIST:  YES                 INSRVMOD: NO
             RANGE:    0..262143           DEFVALUE: 6144
             UNITS:    kbits/sec           SPARSE:   NA
             DESCR:    NA
        "
::= {gxdsllLineServiceProfileChannelEntry 8}

gxdsllMaxBitrateUpstream                 OBJECT-TYPE
        SYNTAX          INTEGER
        ACCESS          read-write
        STATUS          mandatory
        DESCRIPTION     
        "This object contains the maximum allowed bit rate which can be set up
         and maintained upstream in case of automaticRateAdaptiveAtStartup RA
         mode. This parameter has no meaning in operatorControlledRateAdaptive
         RA mode. 

         ALCATEL NOTE:
             ACCESS:   NA                  USAGE:    OPT
             PERSIST:  YES                 INSRVMOD: NO
             RANGE:    0..262143           DEFVALUE: 640
             UNITS:    kbits/sec           SPARSE:   NA
             DESCR:    NA
        "
::= {gxdsllLineServiceProfileChannelEntry 9}

gxdsllL2LowPowerBitrateDownstream        OBJECT-TYPE
        SYNTAX          INTEGER
        ACCESS          read-write
        STATUS          mandatory
        DESCRIPTION     
        "This parameter specifies the minimum downstream net data rate that has
         to be supported for the bearer channel during the low power state L2.
         
         ALCATEL NOTE:
             ACCESS:   NA                  USAGE:    OPT
             PERSIST:  YES                 INSRVMOD: NO
             RANGE:    0..262143           DEFVALUE: 128
             UNITS:    kbits/sec           SPARSE:   NA
             DESCR:    NA
        
         FGU4.4:  THIS OBJECT IS NOT SUPPORTED "
::= {gxdsllLineServiceProfileChannelEntry 10}

gxdsllMaxInterleavingDelayDownstream     OBJECT-TYPE
        SYNTAX          INTEGER
        ACCESS          read-write
        STATUS          mandatory
        DESCRIPTION     
        "This object defines a maximum for the delay introduced by the
         interleaving and deinterleaving function in the given direction.
         The XTU-C and XTU-R must choose their interleaving and coding
         parameters within the max interleaved delay and min impulse noise
         protection constraints. 
         The value 1 is used to specify that fast or pseudo fast latency
         (i.e. no interleaving) must be used.

         ALCATEL NOTE:
             ACCESS:   NA                  USAGE:    OPT
             PERSIST:  YES                 INSRVMOD: NO
             RANGE:    1..63               DEFVALUE: 16
             UNITS:    milliseconds        SPARSE:   NA
             DESCR:    NA
        "       
::= {gxdsllLineServiceProfileChannelEntry 11}

gxdsllMaxInterleavingDelayUpstream       OBJECT-TYPE
        SYNTAX          INTEGER
        ACCESS          read-write
        STATUS          mandatory
        DESCRIPTION     
        "This object defines a maximum for the delay introduced by the
         interleaving and deinterleaving function in the given direction.
         The XTU-C and XTU-R must choose their interleaving and coding
         parameters within the max interleaved delay and min impulse noise
         protection constraints. 
         The value 1 is used to specify that fast or pseudo fast latency
         (i.e. no interleaving) must be used.

         ALCATEL NOTE:
             ACCESS:   NA                  USAGE:    OPT
             PERSIST:  YES                 INSRVMOD: NO
             RANGE:    1..63               DEFVALUE: 16
             UNITS:    milliseconds        SPARSE:   NA
             DESCR:    NA
        "               
::= {gxdsllLineServiceProfileChannelEntry 12}

gxdsllMinImpNoiseProtDownstream          OBJECT-TYPE
        SYNTAX          INTEGER
        ACCESS          read-write
        STATUS          mandatory
        DESCRIPTION     
        "This object defines the minimum impulse noise protection for the
         given direction. It is expressed in symbols.
         Range: 0 to 16 symbols in steps of 0.1 symbol.
         The minimum impulse noise protection is represented as
         1/10 * xdslMinImpNoiseProtDownstream.

         ALCATEL NOTE:
             ACCESS:   NA                  USAGE:    OPT
             PERSIST:  YES                 INSRVMOD: NA
             RANGE:    0..160               DEFVALUE: 0
             UNITS:    0.1 symbols         SPARSE:   NA
             DESCR:    NA
        "
::= {gxdsllLineServiceProfileChannelEntry 13}

gxdsllMinImpNoiseProtUpstream            OBJECT-TYPE
        SYNTAX          INTEGER
        ACCESS          read-write
        STATUS          mandatory
        DESCRIPTION     
        "This object defines the minimum impulse noise protection for the
         given direction. It is expressed in symbols.
         Range: 0 to 16 symbols in steps of 0.1 symbol.
         The minimum impulse noise protection is represented as
         1/10 * xdslMinImpNoiseProtUpstream.

         ALCATEL NOTE:
             ACCESS:   NA                  USAGE:    OPT
             PERSIST:  YES                 INSRVMOD: NO
             RANGE:    0..160               DEFVALUE: 0
             UNITS:    0.1 symbols         SPARSE:   NA
             DESCR:    NA
        "
::= {gxdsllLineServiceProfileChannelEntry 14}

gxdsllErasureDetectionDownstream         OBJECT-TYPE
        SYNTAX          INTEGER
        ACCESS          read-write
        STATUS          mandatory
        DESCRIPTION
        "Indicates whether the erasure detection mechanism is allowed to be
         taken into account in order to reach the MinInp.
         Value 1 = MinInp must be reached even without erasure
         detection
         Value 0 = MinInp must be reached with or without
         erasure detection

         ALCATEL NOTE:
             ACCESS:   NA                  USAGE:    OPT
             PERSIST:  YES                 INSRVMOD: NO
             RANGE:    0..1                DEFVALUE: 0
             UNITS:    NA                  SPARSE:   NA
             DESCR:    NA
        
         FGU4.4:  THIS OBJECT IS NOT SUPPORTED "
::= {gxdsllLineServiceProfileChannelEntry 15}

gxdsllErasureDetectionUpstream           OBJECT-TYPE
        SYNTAX          INTEGER
        ACCESS          read-write
        STATUS          mandatory
        DESCRIPTION
        "Indicates whether the erasure detection mechanism is allowed to be
         taken into account in order to reach the MinInp.
         Value 1 = MinInp must be reached even without erasure
         detection
         Value 0 = MinInp must be reached with or without
         erasure detection

         ALCATEL NOTE:
             ACCESS:   NA                  USAGE:    OPT
             PERSIST:  YES                 INSRVMOD: NO
             RANGE:    0..1                DEFVALUE: 0
             UNITS:    NA                  SPARSE:   NA
             DESCR:    NA
        
         FGU4.4:  THIS OBJECT IS NOT SUPPORTED "
::= {gxdsllLineServiceProfileChannelEntry 16}

gxdslLineServiceProfileMappingTable     OBJECT-TYPE
        SYNTAX          SEQUENCE OF GxdslLineServiceProfileMappingEntry
        ACCESS          not-accessible
        STATUS          mandatory
        DESCRIPTION
        "The (conceptual) table listing the profile name to profile Index
         Mapping.

         ALCATEL NOTE:
             TABLESIZE: 256                    
             DESCR:     NA                  
        " 
::= {gxdslLineServiceProfile 3}

gxdslLineServiceProfileMappingEntry     OBJECT-TYPE
        SYNTAX          GxdslLineServiceProfileMappingEntry
        ACCESS          not-accessible
        STATUS          mandatory
        DESCRIPTION
        "An entry (conceptual row) representing the profile Name to Index
         Mapping.

         Row creation : When an entry is created in the 
                        xdslLineServiceProfileTable, an entry is created in
                        this table.
         Row deletion : When an entry is deleted from the
                        xdslLineServiceProfileTable, the entry is deleted from
                        this table. 
        "
        INDEX          {gxdslLineServiceProfileMappingName,
                        gxdslLineServiceProfileMappingScope}
::= { gxdslLineServiceProfileMappingTable 1 }

GxdslLineServiceProfileMappingEntry ::=
        SEQUENCE {
            gxdslLineServiceProfileMappingName         AsamProfileName,
            gxdslLineServiceProfileMappingScope        AsamProfileScope,
            gxdslLineServiceProfileMappingIndex        AsamProfileIndex
        }

gxdslLineServiceProfileMappingName      OBJECT-TYPE
        SYNTAX          AsamProfileName
        ACCESS          not-accessible
        STATUS          mandatory
        DESCRIPTION
        "The Service profile name.

         ALCATEL NOTE:
             ACCESS:   NA                  USAGE:    NA
             PERSIST:  NO                  INSRVMOD: NA
             RANGE:    NA                  DEFVALUE: NA
             UNITS:    NA                  SPARSE:   NA
             DESCR:    NA
        "
::= { gxdslLineServiceProfileMappingEntry 1 }

gxdslLineServiceProfileMappingScope     OBJECT-TYPE
        SYNTAX          AsamProfileScope
        ACCESS          not-accessible
        STATUS          mandatory
        DESCRIPTION
        "The Service profile scope.

         ALCATEL NOTE:
             ACCESS:   NA                  USAGE:    NA
             PERSIST:  NO                  INSRVMOD: NA
             RANGE:    NA                  DEFVALUE: NA
             UNITS:    NA                  SPARSE:   NA
             DESCR:    NA
        "
::= { gxdslLineServiceProfileMappingEntry 2 }

gxdslLineServiceProfileMappingIndex     OBJECT-TYPE
        SYNTAX          AsamProfileIndex
        ACCESS          read-only
        STATUS          mandatory
        DESCRIPTION
        "The Index of the corresponding service profile.

         ALCATEL NOTE:
             ACCESS:   NA                  USAGE:    NA
             PERSIST:  NO                  INSRVMOD: NA
             RANGE:    1..256              DEFVALUE: NA
             UNITS:    NA                  SPARSE:   NA
             DESCR:    NA
        "
::= { gxdslLineServiceProfileMappingEntry 3 }

gxdslLineSpectrumProfileIndexNext       OBJECT-TYPE
        SYNTAX          AsamNextProfileIndex
        ACCESS          read-only
        STATUS          mandatory
        DESCRIPTION     
        "This object contains an appropriate value to be used for 
         xdslLineSpectrumProfileIndex when creating entries in the
         xdslLineSpectrumProfileTable. 
         The value 0 indicates that no unassigned entries are available. To 
         obtain the xdslLineNextSpectrumProfileIndex value for a new entry, the
         manager issues a management protocol retrieval operation to obtain the
         current value of this object.  After each retrieval, the agent should
         modify the value to the next unassigned index.

         ALCATEL NOTE:
             ACCESS:   NA                  USAGE:    NA
             PERSIST:  NO                  INSRVMOD: NA
             RANGE:    0..256              DEFVALUE: 1
             UNITS:    NA                  SPARSE:   NA
             DESCR:    NA
        "
::= {gxdslLine 4}

gxdslLineSpectrumProfileMaxIndex        OBJECT-TYPE
        SYNTAX          AsamMaxProfileIndex
        ACCESS          read-only
        STATUS          mandatory
        DESCRIPTION
        "This object represents the maximum number of xdslLineSpectrumProfiles
         that can be created. The object xdslLineSpectrumProfileIndexNext will 
         have values ranging from 1 to the value represented by this object.

         ALCATEL NOTE:
             ACCESS:   NA                  USAGE:    NA
             PERSIST:  NO                  INSRVMOD: NA
             RANGE:    256..256            DEFVALUE: 256
             UNITS:    NA                  SPARSE:   NA
             DESCR:    NA
        "
::= {gxdslLine 5}

gxdslLineSpectrumProfileTable           OBJECT-TYPE
        SYNTAX          SEQUENCE OF GxdslLineSpectrumProfileEntry
        ACCESS          not-accessible
        STATUS          mandatory
        DESCRIPTION     
        "This table contains the spectrum related parameters of the modem
         configuration. One entry in this table reflects a profile which
         can be used to configure the modem for a physical line.

         ALCATEL NOTE:
             TABLESIZE: 256                    
             DESCR:     NA                  
        "
::= {gxdslLineSpectrumProfile 1}

gxdslLineSpectrumProfileEntry           OBJECT-TYPE
        SYNTAX          GxdslLineSpectrumProfileEntry
        ACCESS          not-accessible
        STATUS          mandatory
        DESCRIPTION     
        "Each entry consists of a list of line related parameters that serve 
         to configure an XDSL modem. A profile can be created in one step with
         all necessary parameter values and xdslLineSpectrumProfileRowStatus
         set to createAndGo.
         It can also be created in several steps by specifying values of a few
         objects in each step. The xdslLineSpectrumProfileRowStatus is set to
         createAndWait in the first step and to Active in the last step.

         Row creation : An entry is created when the manager requests to create
                        a spectrum profile.
         Row deletion : An entry is deleted when the manager requests to delete
                        a spectrum profile.
        "
        INDEX          {gxdslLineSpectrumProfileIndex}
::= {gxdslLineSpectrumProfileTable 1}

GxdslLineSpectrumProfileEntry ::=
        SEQUENCE {
            gxdslLineSpectrumProfileIndex              AsamProfileIndex,
            gxdslLineSpectrumProfileName               AsamProfileName,
            gxdslLineSpectrumProfileScope              AsamProfileScope,
            gxdslLineSpectrumProfileVersionNbr         INTEGER,
            gxdslLineSpectrumProfileUsedStatus         AsamProfileRefCount, 
            gxdslLineOpMode                            GOpModeType,
            gxdslLineMinNoiseMarginDownstream          INTEGER,
            gxdslLineMinNoiseMarginUpstream            INTEGER,
            gxdslLineTargetNoiseMarginDownstream       INTEGER,
            gxdslLineTargetNoiseMarginUpstream         INTEGER,
            gxdslLineMaxNoiseMarginDownstream          INTEGER,
            gxdslLineMaxNoiseMarginUpstream            INTEGER,
            gxdslLineCarrierMaskDownstream             OCTET STRING,
            gxdslLineCarrierMaskUpstream               OCTET STRING,
            gxdslLineRfiBands                          OCTET STRING,
            gxdslLinePowerMgtMode                      INTEGER,
            gxdslLineL0Time                            INTEGER,   
            gxdslLineL2Time                            INTEGER,
            gxdslLineL2Atpr                            INTEGER,        
            gxdslLineSpectrumProfileRowStatus          RowStatus,
            gxdslLineSpectrumProfileModifyStatus       INTEGER,
            gxdslLineL2AtprT                           INTEGER,
            gxdslLineRAUNoiseMarginDownstream          INTEGER,
            gxdslLineRAUNoiseMarginUpstream            INTEGER,
            gxdslLineRAUTimeDownstream                 INTEGER,
            gxdslLineRAUTimeUpstream                   INTEGER,
            gxdslLineRADNoiseMarginDownstream          INTEGER,
            gxdslLineRADNoiseMarginUpstream            INTEGER,
            gxdslLineRADTimeDownstream                 INTEGER,
            gxdslLineRADTimeUpstream                   INTEGER,
            gxdslLineArtificialNoisePsdDownstream      GArtificialNoisePsdDownType
        }

gxdslLineSpectrumProfileIndex           OBJECT-TYPE
        SYNTAX          AsamProfileIndex
        ACCESS          not-accessible
        STATUS          mandatory
        DESCRIPTION     
        "This object is used to uniquely identify an entry in this table.
         It is used by the line configuration table to identify a row of this
         table. The max value of this object is limited to
         xdslLineSpectrumProfileMaxIndex value.
         In addition, special index values are defined to identify temporary
         entries in this table used to contain the modifications performed on
         an existing profile. The index value of such an entry is obtained by
         adding a fixed offset to the corresponding index. The value of this
         offset is contained in xdslLineSpectrumProfileIndexOffset. A temporary
         entry exists only during the profile modification, it is created at
         xdslLineSpectrumProfileModifyStatus = modifyStart and is deleted at
         modifyCancel or modifyComplete. It can only be accessed during the
         modification to retrieve the updated parameters values of a profile.
         The nominal entry contains the original profile settings and is not
         updated until the profile modification is completed and validated.
         The offset entries are read only, all write operations must be
         performed using the nominal index.
         The getnext can be used to retrieve the nominal spectrum profile
         entries and does not return the temporary profiles entries at the
         special offset index values.

         ALCATEL NOTE:
             ACCESS:   NA                  USAGE:    NA
             PERSIST:  YES                 INSRVMOD: NA
             RANGE:    1..256              DEFVALUE: NA
             UNITS:    NA                  SPARSE:   NA
             DESCR:    NA
        "
::= {gxdslLineSpectrumProfileEntry 1}

gxdslLineSpectrumProfileName            OBJECT-TYPE
        SYNTAX          AsamProfileName
        ACCESS          read-write
        STATUS          mandatory
        DESCRIPTION     
        "A textual name identifying this profile. This name has to be unique
         within the assigned scope.

         ALCATEL NOTE:
             ACCESS:   NA                  USAGE:    MAND
             PERSIST:  YES                 INSRVMOD: YES
             RANGE:    NA                  DEFVALUE: NA
             UNITS:    NA                  SPARSE:   NA
             DESCR:    NA
        "
::= {gxdslLineSpectrumProfileEntry 2}

gxdslLineSpectrumProfileScope           OBJECT-TYPE
        SYNTAX          AsamProfileScope
        ACCESS          read-write
        STATUS          mandatory
        DESCRIPTION     
        "A  profile can be qualified as having a local scope or a network wide 
         scope. As some managers may not support the network profile scope,
         the use of local scope is strongly recommended.

         ALCATEL NOTE:
             ACCESS:   NA                  USAGE:    OPT 
             PERSIST:  YES                 INSRVMOD: YES
             RANGE:    NA                  DEFVALUE: NA
             UNITS:    NA                  SPARSE:   NA
             DESCR:    NA
        "
        DEFVAL          {localScope}
::= {gxdslLineSpectrumProfileEntry 3}

gxdslLineSpectrumProfileVersionNbr      OBJECT-TYPE
        SYNTAX          INTEGER
        ACCESS          read-write
        STATUS          mandatory
        DESCRIPTION     
        "The manager can associate a version number to the profile. It is set
         to 1 when the profile is first created and will be incremented by the
         manager when the profile is modified.

         ALCATEL NOTE:
             ACCESS:   NA                  USAGE:    OPT
             PERSIST:  YES                 INSRVMOD: YES
             RANGE:    NA                  DEFVALUE: NA
             UNITS:    NA                  SPARSE:   NA
             DESCR:    NA

     For FGU4.4, only allowed value is 1 and cannot be incremented.  "
        DEFVAL          {1}
::= {gxdslLineSpectrumProfileEntry 4}

gxdslLineSpectrumProfileUsedStatus      OBJECT-TYPE
        SYNTAX          AsamProfileRefCount
        ACCESS          read-only
        STATUS          mandatory
        DESCRIPTION
        "Indicates the number of entities using this profile. If the reference
         count is greater than 0, then this profile is 'in use', and may NOT be
         deleted. If the value is 0, then this profile is 'not in use', and can
         be deleted.

         ALCATEL NOTE:
             ACCESS:   NA                  USAGE:    NA
             PERSIST:  NO                  INSRVMOD: NA
             RANGE:    NA                  DEFVALUE: 0
             UNITS:    NA                  SPARSE:   NA
             DESCR:    NA
        "
::= {gxdslLineSpectrumProfileEntry 5}

gxdslLineOpMode          OBJECT-TYPE
        SYNTAX          GOpModeType
        ACCESS          read-write
        STATUS          mandatory 
        DESCRIPTION 
        "This object defines the operational modes allowed by the corresponding
         configuration profile. 
         It is coded in a bitmap defined as follows (based on G.997.1,
         transmission system enabling). More than one mode can be set
         simultaneously.
         The respective operational modes correspond to the following integer
         values in the bitmap, other bit positions are reserved for future use.
       
         Octet 1 (ADSL):
         1:  ANSI T1.413-1998
         2:  ETSI DTS/TM06006
         4:  G.992.1 operation over POTS non-overlapped spectrum (Annex A of
             G.992.1)
         8:  G.992.1 operation over POTS overlapped spectrum (Annex A of
             G.992.1)
         16: G.992.1 operation over ISDN non-overlapped spectrum (Annex B
             of G.992.1)
         32: G.992.1 operation over ISDN overlapped spectrum (Annex B of
             G.992.1)
         64: G.992.1 operation in conjunction with TCM-ISDN non-overlapped
             spectrum (Annex C of G.992.1)
         128:G.992.1 operation in conjunction with TCM-ISDN overlapped
             spectrum (Annex C of G.992.1)

         Octet 2 (ADSL):
         1:  G.992.2 operation over POTS non-overlapped spectrum (Annex A of
             G.992.2)
         2:  G.992.2 operation over POTS overlapped spectrum (Annex B of
             G.992.2).
         4:  G.992.2 operation in conjunction with TCM-ISDN non-overlapped
             spectrum (Annex C of G.992.2)
         8:  G.992.2 operation in conjunction with TCM-ISDN overlapped
             spectrum(Annex C of G.992.2)

         Octet 3 (ADSL2):
         4:  G.992.3 operation over POTS non-overlapped spectrum (Annex A of
             G.992.3)
         8:  G.992.3 operation over POTS overlapped spectrum (Annex A of
             G.992.3)
         16: G.992.3 operation over ISDN non-overlapped spectrum (Annex B of
             G.992.3)
         32: G.992.3 operation over ISDN overlapped spectrum (Annex B of
             G.992.3)

         Octet 4 (ADSL2):
         1:  G.992.4 operation over POTS non-overlapped spectrum (Annex A of
             G.992.4)
         2:  G.992.4 operation over POTS overlapped spectrum (Annex A of
             G.992.4)
         16: G.992.3 All Digital Mode operation with non-overlapped spectrum
             (Annex I of G.992.3)
         32: G.992.3 All Digital Mode operation with overlapped spectrum (Annex
             I of G.992.3)
         64: G.992.3 All Digital Mode operation with non-overlapped spectrum
             (Annex J of G.992.3)
         128:G.992.3 All Digital Mode operation with overlapped spectrum
             (Annex J of G.992.3)

         Octet 5 (ADSL2):
         1:  G.992.4 All Digital Mode operation with non-overlapped spectrum
             (Annex I of G.992.4)
         2:  G.992.4 All Digital Mode operation with overlapped spectrum
             (Annex I of G.992.4).
         4:  G.992.3 operation over POTS non-overlapped spectrum US mask 1
             (Annex L mode 1 of G.992.3)
         8:  G.992.3 operation over POTS non-overlapped spectrum US mask 2
             (Annex L mode 2 of G.992.3)
         16: G.992.3 operation over POTS overlapped spectrum US mask 1
             (Annex L mode 3 of G.992.3).
         32: G.992.3 operation over POTS overlapped spectrum US mask 2
             (Annex L mode 4 of G.992.3).
         64: G.992.3 Extended Upstream operation over POTS with non-overlapped
             spectrum (Annex M of G.992.3)
         128:G.992.3 Extended Upstream operation over POTS with overlapped
             spectrum (Annex M of G.992.3)

         Octet 6 (ADSL2):
         1:  G.992.5 operation over POTS non-overlapped spectrum (Annex A of
             G.992.5)
         2:  G.992.5 operation over POTS overlapped spectrum (Annex A of
             G.992.5)
         4:  G.992.5 operation over ISDN non-overlapped spectrum (Annex B of
             G.992.5)
         8:  G.992.5 operation over ISDN overlapped spectrum (Annex B of
             G.992.5)
         64: G.992.5 All Digital Mode operation with non-overlapped spectrum
             (Annex I of G.992.5)
         128:G.992.5 All Digital Mode operation with overlapped spectrum
             (Annex I of G.992.5)

         Octet 7 (VDSL):
         1:  ANSI T1.424
         2:  ETSI TS 101 270
         4:  ITU G.993.1
         8:  IEEE 802.3ah

         Octet 8 (ADSL2):
         1:  G.992.5 All Digital Mode operation with non-overlapped spectrum
             (Annex J of G.992.5)
         2:  G.992.5 All Digital Mode operation with overlapped spectrum
             (Annex J of G.992.5)
         4:  G.992.5 Extended Upstream operation over POTS non-overlapped 
             spectrum
             (Annex M of G.992.5)
         8:  G.992.5 Extended Upstream operation over POTS overlapped spectrum
             (Annex M of G.992.5)       

         Octet 9 (VDSL2):
         1:  G.993.2_ 8A VDSL-2 with profile 8A
         2:  G.993.2_ 8B VDSL-2 with profile 8B
         4:  G.993.2_ 8C VDSL-2 with profile 8C 
         8:  G.993.2_ 8D VDSL-2 with profile 8D
         16: G.993.2_12A VDSL-2 with profile 12A
         32: G.993.2_12B VDSL-2 with profile 12B 
         64: G.993.2_17A VDSL-2 with profile 17A 
         128:G.993.2_30A VDSL-2 with profile 30A 

         Octet 10-16:  Reserved for further use

         The actual operational mode is reflected by the
         xdslLineActualOperationalMode object.

         ALCATEL NOTE:
             ACCESS:   NA                  USAGE:    OPT
             PERSIST:  YES                 INSRVMOD: YES
             RANGE:    NA                  DEFVALUE: NA
             UNITS:    NA                  SPARSE:   NA
             DESCR:    
		All the above operational modes can be enabled in the Spectrum profile. 
             But only the following modes are actually supported by the gxdslLine:
             Octet 1 (ADSL):
             4: G.992.1 operation over POTS non-overlapped spectrum (Annex A of G.992.1)
             Octet 6 (ADSL2):
             1: G.992.5 operation over POTS non-overlapped spectrum (Annex A of G.992.5)
             Octet 9 (VDSL2):
             4:  G.993.2_ 8C VDSL-2 with profile 8C 
             32: G.993.2_12B VDSL-2 with profile 12B 
             64: G.993.2_17A VDSL-2 with profile 17A 
             128:G.993.2_30A VDSL-2 with profile 30A 
		"
        DEFVAL          {'0000000000000000E400000000000000'H}
::= {gxdslLineSpectrumProfileEntry 6}

gxdslLineMinNoiseMarginDownstream       OBJECT-TYPE
        SYNTAX          INTEGER
        ACCESS          read-write   
        STATUS          mandatory
        DESCRIPTION
        "Used during showtime and independant of rate adaptation mode. When
         current noise margin falls below the Minimum Noise Margin and no
         bitswap action can help this anymore, the modem will reinitialize.
         Limitation: Minimum Noise Margin <= Target Noise Margin
         Expressed in dB.
         Range: 0 to 31 dB with 0,1 dB steps.
         The minimum noise margin is represented as
         1/10 * xdslLineMinNoiseMarginDownstream.

         ALCATEL NOTE:
             ACCESS:   NA                  USAGE:    OPT
             PERSIST:  YES                 INSRVMOD: YES
             RANGE:    0..310              DEFVALUE: NA
             UNITS:    dB / 10             SPARSE:   NA
             DESCR:    NA
        "
        DEFVAL          {0}           
::= {gxdslLineSpectrumProfileEntry 7}

gxdslLineMinNoiseMarginUpstream         OBJECT-TYPE
        SYNTAX          INTEGER
        ACCESS          read-write
        STATUS          mandatory 
        DESCRIPTION 
        "Used during showtime and independant of rate adaptation mode. When
         current noise margin falls below the Minimum Noise Margin and no 
         bitswap action can help this anymore, the modem will reinitialize.
         Limitation: Minimum Noise Margin <= Target Noise Margin
         Expressed in dB.
         Range: 0 to 31 dB with 0,1 dB steps.
         The minimum noise margin is represented as
         1/10 * xdslLineMinNoiseMarginUpstream.
    
         ALCATEL NOTE:
             ACCESS:   NA                  USAGE:    OPT
             PERSIST:  YES                 INSRVMOD: YES
             RANGE:    0..310              DEFVALUE: NA
             UNITS:    dB / 10             SPARSE:   NA
             DESCR:    NA
        "
        DEFVAL          {0}           
::= {gxdslLineSpectrumProfileEntry 8}

gxdslLineTargetNoiseMarginDownstream    OBJECT-TYPE
        SYNTAX          INTEGER
        ACCESS          read-write
        STATUS          mandatory
        DESCRIPTION     
        "Used at startup for all rate adaptation modes. This is the Noise
         Margin the ATU-R receiver shall achieve, relative to a BER of 1E-7 or 
         better for each of the downstream bearer channels, to successfully
         complete initialization. It is expressed in dB.
         Limitation: Target Noise Margin <= Maximum Noise Margin
         Expressed in dB.
         Range: 0 to 31 dB with 0,1 dB steps.
         The target noise margin is represented as
         1/10 * xdslLineTargetNoiseMarginDownstream.

         ALCATEL NOTE:
             ACCESS:   NA                  USAGE:    OPT
             PERSIST:  YES                 INSRVMOD: NA
             RANGE:    0..310              DEFVALUE: NA
             UNITS:    dB / 10             SPARSE:   NA
             DESCR:    NA
        "
        DEFVAL          {60}           
::= {gxdslLineSpectrumProfileEntry 9}

gxdslLineTargetNoiseMarginUpstream      OBJECT-TYPE
        SYNTAX          INTEGER
        ACCESS          read-write
        STATUS          mandatory    
        DESCRIPTION     
        "Used at startup for all rate adaptation modes. This is the Noise 
         Margin the ATU-C receiver shall achieve, relative to a BER of 1E-7 or 
         better for each of the upstream bearer channels, to successfully
         complete initialization. It is expressed in dB.
         Limitation: Target Noise Margin <= Maximum Noise Margin
         Expressed in dB.
         Range: 0 to 31 dB with 0,1 dB steps.
         The target noise margin is represented as
         1/10 * xdslLineTargetNoiseMarginUpstream.

         ALCATEL NOTE:
             ACCESS:   NA                  USAGE:    OPT
             PERSIST:  YES                 INSRVMOD: YES
             RANGE:    0..310              DEFVALUE: NA
             UNITS:    dB / 10             SPARSE:   NA
             DESCR:    NA
        "
        DEFVAL          {60}           
::= {gxdslLineSpectrumProfileEntry 10}

gxdslLineMaxNoiseMarginDownstream       OBJECT-TYPE
        SYNTAX          INTEGER
        ACCESS          read-write
        STATUS          mandatory 
        DESCRIPTION 
        "Used at startup and showtime, independently of RA mode.
         When the noise margin is higher than the Maximum Noise Margin, then
         the modem will take action to reduce the peer modem power to get the
         noise margin below this value.
         When the noise margin is lower than the Maximum Noise Margin, then the
         modem will take action to increase the peer modem power to get the
         noise margin as close as possible to this value.
         Expressed in dB.
         Range: 0 to 31 dB with 0,1 dB steps, plus value 51,1 dB used as 
         special value.
         Special value 51,1 dB is used to indicate that no max noise margin 
         limit must be applied.
         The maximum noise margin is represented as
         1/10 * xdslLineMaxNoiseMarginDownstream.

         ALCATEL NOTE:
             ACCESS:   NA                  USAGE:    OPT
             PERSIST:  YES                 INSRVMOD: YES
             RANGE:    0..310, 511         DEFVALUE: NA
             UNITS:    dB / 10             SPARSE:   NA
             DESCR:    NA
        "
        DEFVAL          {511}           
::= {gxdslLineSpectrumProfileEntry 11}
    
gxdslLineMaxNoiseMarginUpstream         OBJECT-TYPE
        SYNTAX          INTEGER
        ACCESS          read-write
        STATUS          mandatory 
        DESCRIPTION 
        "Used at startup and showtime, independently of RA mode.
         When the noise margin is higher than the Maximum Noise Margin, then 
         the modem will take action to reduce the peer modem power to get the 
         noise margin below this value.
         When the noise margin is lower than the Maximum Noise Margin, then the
         modem will take action to increase the peer modem power to get the
         noise margin as close as possible to this value.
         Expressed in dB.
         Range: 0 to 31 dB with 0,1 dB steps, plus value 51,1 dB used as
         special value.
         Special value 51,1 dB is used to indicate that no max noise margin 
         limit must be applied.
         The maximum noise margin is represented as
         1/10 * xdslLineMaxNoiseMarginUpstream.    

         ALCATEL NOTE:
             ACCESS:   NA                  USAGE:    OPT
             PERSIST:  YES                 INSRVMOD: YES
             RANGE:    0..310, 511         DEFVALUE: NA
             UNITS:    dB / 10             SPARSE:   NA
             DESCR:    NA
        "
        DEFVAL          {511}           
::= {gxdslLineSpectrumProfileEntry 12}

gxdslLineCarrierMaskDownstream          OBJECT-TYPE
        SYNTAX          OCTET STRING (SIZE (64))
        ACCESS          read-write
        STATUS          mandatory
        DESCRIPTION     
        "The downstream carrier mask pattern is a bitlist of 512 bits, each bit
         corresponding to one frequency carrier of the DMT modem system. 
         Carrier 0 is represented by the most significant bit of the map, 
         carrier 511 is represented by the least significant bit of the map.
         A downstream carrier is suppressed by setting its corresponding bit to
         1.
         Pilot tones may not be suppressed. If one of the masked carrier is
         defined as a pilot tone in the applicable DSL standard, the modem will 
         not initialize.
         The masking of carriers that are not used in the downstream direction
         or that are not used by the XDSL operational mode will be ignored.
         Carriers 0 to 255 are used for all ADSL/ADSL2 operational modes except 
         for ADSL2 Plus which uses carriers 0 to 511.
         The carrier mask is not used in VDSL mode and will be ignored.

         ALCATEL NOTE:
             ACCESS:   NA                  USAGE:    OPT
             PERSIST:  YES                 INSRVMOD: YES
             RANGE:    NA                  DEFVALUE: NA
             UNITS:    NA                  SPARSE:   NA
             DESCR:    NA
        
         FGU4.4:  THIS OBJECT IS NOT SUPPORTED "
        DEFVAL      {'00000000000000000000000000000000000000000000000000000000000000000000000000000000000000000000000000000000000000000000000000000000'H}
::= {gxdslLineSpectrumProfileEntry 13}

gxdslLineCarrierMaskUpstream            OBJECT-TYPE
        SYNTAX          OCTET STRING (SIZE (8))
        ACCESS          read-write
        STATUS          mandatory
        DESCRIPTION     
        "The upstream carrier mask pattern is a bitlist of 64 bits, each bit
         corresponding to one frequency carrier of the DMT modem system. 
         Carrier 0 is represented by the most significant bit of the map, 
         carrier 63 is represented by the least significant bit of the map.
         An upstream carrier is suppressed by setting its corresponding bit to
         1.
         Pilot tones may not be suppressed. If one of the masked carrier is 
         defined as a pilot tone in the applicable DSL standard, the modem will
         not initialize.
         The masking of carriers that are not used in the upstream direction
         or that are not used by the XDSL operational mode will be ignored.
         Carriers 0 to 63 are used for all ADSL/ADSL2 operational modes.
         The carrier mask is not used in VDSL mode and will be ignored.

         ALCATEL NOTE:
             ACCESS:   NA                  USAGE:    OPT
             PERSIST:  YES                 INSRVMOD: YES
             RANGE:    NA                  DEFVALUE: NA
             UNITS:    NA                  SPARSE:   NA
             DESCR:    NA
        
         FGU4.4:  THIS OBJECT IS NOT SUPPORTED "
        DEFVAL          {'0000000000000000'H }
::= {gxdslLineSpectrumProfileEntry 14}

gxdslLineRfiBands        OBJECT-TYPE
        SYNTAX          OCTET STRING (SIZE (0..80))
        ACCESS          read-write
        STATUS          mandatory
        DESCRIPTION     
        "This object specifies a list of RF bands (HAM or AM) for
         egress control and ingress cancelling. Up to 16 RF signals can be
         specified.
         The RF band list is coded as a variable length octet string defined
         as follows.
         OCTET 0..4 define the characteristics of RF BAND #1:
         OCTET 0..1: INTEGER (0..30000), start frequency (in kHz) of the
         first RF signal. In case of a single carrier RF signal, it is equal
         to the carrier frequency of the signal. 
         The value is defined as MSB-LSB (big-endian).
         OCTETS 2..3: INTEGER (0..30000), stop frequency (in kHz)of the first
         RF signal. In case of a single carrier RF signal, it is equal
         to the carrier frequency of the signal.
         The value is defined as MSB-LSB (big-endian).
         OCTET 4 - bits 0..1: INTEGER (0..3), indicates the type of RF signal:
         Hamband (1), AM signal (2).
         OCTETS 4 - bits 2..3: INTEGER (0..3), egress control, defines whether
         and how egress control must be applied in the corresponding RF band:
         egressNoControl(1), egressNotched(2).
         OCTETS 4 - bits 4..5: INTEGER (0..3), ingress level, defines the
         level of ingress to be expected from the corresponding RF signal:
         ingressLow(1), ingressWeak(2), ingressStrong (3).     
         And so on  up to
         OCTETS (N-1)*5..(N*5)-1: define the characteristics of the last
         RF BAND #N with N<=16.

         ALCATEL NOTE:
             ACCESS:   NA                  USAGE:    OPT
             PERSIST:  YES                 INSRVMOD: YES
             RANGE:    NA                  DEFVALUE: NA
             UNITS:    NA                  SPARSE:   NA
             DESCR:    NA

	FTTU NOTE: The following default value decodes to the following RFI Band information:
	StartFreq  EndFreq  RFItype  EgressCtl  IngressLvl
  	1800        2000            1              2          1
  	3500        4000            1              2          1
  	7000        7300            1              2          1
 	10100      10150           1              2          1
	14000      14350           1              2          1
	18068      18168           1              2          1
	21000      21450            1             2          1
	24890      24990           1              2          1
	28000      29700           1              2          1

	FTTU NOTE: As of FGU4.5.5, the mangement interface will be permitted to SET custom notches.  Whether an MDU
	can handle the custom notch - that remains to be seen.
	OLT should perform following VALIDATIONS:
	- For each notch - StartFreq must be less than EndFreq

        "
        DEFVAL          {'070807D0190DAC0FA0191B581C8419277427A61936B0380E19469446F819520853CA19613A619E196D60740419'H }
::= {gxdslLineSpectrumProfileEntry 15}

gxdslLinePowerMgtMode    OBJECT-TYPE
        SYNTAX          INTEGER
        ACCESS          read-write
        STATUS          mandatory
        DESCRIPTION     
        "This object specifies the permission of power management states.
         It is coded in a bitmap. The respective power states correspond to
         the following integer values in the bitmap, other bit positions are
         reserved for future use.
         1:  L2 allowed
         2:  L3 allowed
         Because autonomous transitions to L3 are not supported, only the 
         L3 triggered from CPE shall be supported. 
         The integer values 0 (no L2, no L3), 
                            1 (L2, no L3), 
                            2 (no L2, L3) and
                            3 (L2, L3) can be set.

         ALCATEL NOTE:
             ACCESS:   NA                  USAGE:    OPT
             PERSIST:  YES                 INSRVMOD: YES
             RANGE:    0..3                DEFVALUE: NA
             UNITS:    NA                  SPARSE:   NA
             DESCR:    NA

     FGU4.4:  The only SUPPORTED value is 0.
        "
        DEFVAL          {0}
::= {gxdslLineSpectrumProfileEntry 16}

gxdslLineL0Time          OBJECT-TYPE
        SYNTAX          INTEGER
        ACCESS          read-write
        STATUS          mandatory
        DESCRIPTION     
        "This object specifies the minimum time between an exit from the L2
         state and the next entry into the L2 state. 

         ALCATEL NOTE:
             ACCESS:   NA                  USAGE:    OPT
             PERSIST:  YES                 INSRVMOD: YES
             RANGE:    0..1800             DEFVALUE: NA
             UNITS:    seconds             SPARSE:   NA
             DESCR:    NA
        
         FGU4.4:  THIS OBJECT IS NOT SUPPORTED "
        DEFVAL          {255}
::= {gxdslLineSpectrumProfileEntry 17}

gxdslLineL2Time          OBJECT-TYPE
        SYNTAX          INTEGER
        ACCESS          read-write
        STATUS          mandatory
        DESCRIPTION     
        "This object specifies the time between L2 entry and first power trim
         or between two consecutive power trims. 

         ALCATEL NOTE:
             ACCESS:   NA                  USAGE:    OPT
             PERSIST:  YES                 INSRVMOD: YES
             RANGE:    0..1800             DEFVALUE: NA
             UNITS:    seconds             SPARSE:   NA
             DESCR:    NA
        
         FGU4.4:  THIS OBJECT IS NOT SUPPORTED "
        DEFVAL          {60}
::= {gxdslLineSpectrumProfileEntry 18}

gxdslLineL2Atpr          OBJECT-TYPE
        SYNTAX          INTEGER
        ACCESS          read-write
        STATUS          mandatory
        DESCRIPTION     
        "This object specifies the maximum aggregate transmit power reduction
         that can be performed in the L2 Request or through a single power trim 
         in the L2 state. It is expressed in dB.

         ALCATEL NOTE:
             ACCESS:   NA                  USAGE:    OPT
             PERSIST:  YES                 INSRVMOD: YES
             RANGE:    0..31               DEFVALUE: NA
             UNITS:    dB                  SPARSE:   NA
             DESCR:    NA
        
         FGU4.4:  THIS OBJECT IS NOT SUPPORTED "
        DEFVAL          {3}
::= {gxdslLineSpectrumProfileEntry 19}

gxdslLineSpectrumProfileRowStatus       OBJECT-TYPE
        SYNTAX          RowStatus
        ACCESS          read-write
        STATUS          mandatory
        DESCRIPTION 
        "This object is used to create a new row or delete an existing row in
         this table. The usage is as per standard semantics of 'RowStatus'
         defined in SNMPv2-TC.
            o Both 'createAndGo' and 'createAndWait' options of row creation
              are supported.
            o The entry associated with a Profile that is being used may
              not be deleted.

         ALCATEL NOTE:
             ACCESS:   NA                  USAGE:    MAND
             PERSIST:  YES                 INSRVMOD: YES
             RANGE:    NA                  DEFVALUE: NA
             UNITS:    NA                  SPARSE:   NA
             DESCR:    NA
        "
::= {gxdslLineSpectrumProfileEntry 20}

gxdslLineSpectrumProfileModifyStatus OBJECT-TYPE
        SYNTAX          INTEGER {
                            modifyStart (1),
                            modifyCancel (2),
                            modifyComplete (3)
                        }
        ACCESS          read-write
        STATUS          mandatory 
        DESCRIPTION 
        "This variable is used to modify a line spectrum profile after
         it has been created.
         The following values are defined:
          - modifyStart (1): set by the manager to enable the
            modification of the parameters of the spectrum profile.
          - modifyCancel (2): set by the manager to stop the profile
            modification and cancel all changes. The original profile
            settings are maintained.
          - modifyComplete (3): used by the manager to activate the
            changes and replace the old profile. The modification of the
            spectrum profile parameters (other than name, scope, version) 
            is disabled.
            The system will also set the 
            xdslLineSpectrumProfileModifyStatus value to 'modifyComplete'
            after a modifyCancel request from the manager.
           See xdslLineSpectrumProfileIndex about the retrieval of the
           original or the updated profile setting values during the profile
           modification.

         ALCATEL NOTE:
             ACCESS:   NA                  USAGE:    OPT
             PERSIST:  YES                 INSRVMOD: YES
             RANGE:    NA                  DEFVALUE: NA
             UNITS:    NA                  SPARSE:   NA
             DESCR:    NA
        
         FGU4.4:  THIS OBJECT IS NOT SUPPORTED "
        DEFVAL          {modifyComplete}
 ::= {gxdslLineSpectrumProfileEntry 21}

gxdslLineL2AtprT         OBJECT-TYPE
        SYNTAX          INTEGER
        ACCESS          read-write
        STATUS          mandatory
        DESCRIPTION     
        "This object specifies the total maximum aggregate transmit power
         reduction that can be performed in the L2 state. This is the sum of 
         all reductions of L2 Request and power trims in the L2 state. It is
         expressed in dB.

         ALCATEL NOTE:
             ACCESS:   NA                  USAGE:    OPT
             PERSIST:  YES                 INSRVMOD: YES
             RANGE:    0..31               DEFVALUE: NA
             UNITS:    dB                  SPARSE:   NA
             DESCR:    NA
        
         FGU4.4:  THIS OBJECT IS NOT SUPPORTED "
        DEFVAL          {31}
::= {gxdslLineSpectrumProfileEntry 22}

gxdslLineRAUNoiseMarginDownstream       OBJECT-TYPE
        SYNTAX          INTEGER
        ACCESS          read-write
        STATUS          mandatory
        DESCRIPTION      
        "This object specifies the Downstream Upshift Noise Margin for Rate
         Adaptation. If the downstream noise margin is above the Downstream
         Upshift Noise Margin and stays above that for more than the time
         specified by the Downstream Minimum Upshift Rate Adaptation Interval, 
         the XTU R shall attempt to increase the downstream net data rate. It 
         is expressed in dB.
         Range: 0 to 31 dB in steps of 0.1 dB. The Downstream Upshift Noise 
         Margin is represented as 1/10 * xdslLineRAUNoiseMarginDownstream.

         ALCATEL NOTE:
             ACCESS:   NA                  USAGE:    OPT
             PERSIST:  YES                 INSRVMOD: YES
             RANGE:    0..310              DEFVALUE: NA
             UNITS:    dB / 10             SPARSE:   NA
             DESCR:    NA
        
         FGU4.4:  THIS OBJECT IS NOT SUPPORTED "
        DEFVAL          {70}           
::= {gxdslLineSpectrumProfileEntry 23}

gxdslLineRAUNoiseMarginUpstream         OBJECT-TYPE
        SYNTAX          INTEGER
        ACCESS          read-write
        STATUS          mandatory
        DESCRIPTION      
        "This object specifies the Upstream Upshift Noise Margin for Rate
         Adaptation. If the upstream noise margin is above the Upstream Upshift
         Noise Margin and stays above that for more than the time specified by
         the Upstream Minimum Upshift Rate Adaptation Interval, the XTU C shall
         attempt to increase the upstream net data rate. It is expressed in dB.
         Range: 0 to 31 dB in steps of 0.1 dB. The Upstream Upshift Noise 
         Margin is represented as 1/10 * xdslLineRAUNoiseMarginUpstream.

         ALCATEL NOTE:
             ACCESS:   NA                  USAGE:    OPT
             PERSIST:  YES                 INSRVMOD: YES
             RANGE:    0..310              DEFVALUE: NA
             UNITS:    dB / 10             SPARSE:   NA
             DESCR:    NA
        
         FGU4.4:  THIS OBJECT IS NOT SUPPORTED "
        DEFVAL          {70}           
::= {gxdslLineSpectrumProfileEntry 24}

gxdslLineRAUTimeDownstream              OBJECT-TYPE
        SYNTAX          INTEGER
        ACCESS          read-write
        STATUS          mandatory
        DESCRIPTION      
        "This object specifies the Downstream Minimum Upshift Rate Adaptation
         Interval. This is the interval of time the downstream noise margin 
         should stay above the Downstream Upshift Noise Margin before the XTU R 
         shall attempt to increase the downstream net data rate.

         ALCATEL NOTE:
             ACCESS:   NA                  USAGE:    OPT
             PERSIST:  YES                 INSRVMOD: YES
             RANGE:    0..16383            DEFVALUE: NA
             UNITS:    seconds             SPARSE:   NA
             DESCR:    NA
        
         FGU4.4:  THIS OBJECT IS NOT SUPPORTED "
        DEFVAL          {300}           
::= {gxdslLineSpectrumProfileEntry 25}

gxdslLineRAUTimeUpstream OBJECT-TYPE
        SYNTAX          INTEGER
        ACCESS          read-write
        STATUS          mandatory
        DESCRIPTION      
        "This object specifies the Upstream Minimum Upshift Rate Adaptation
         Interval. This is the interval of time the upstream noise margin 
         should stay above the Upstream Upshift Noise Margin before the XTU C 
         shall attempt to increase the upstream net data rate.

         ALCATEL NOTE:
             ACCESS:   NA                  USAGE:    OPT
             PERSIST:  YES                 INSRVMOD: YES
             RANGE:    0..16383            DEFVALUE: NA
             UNITS:    seconds             SPARSE:   NA
             DESCR:    NA
        
         FGU4.4:  THIS OBJECT IS NOT SUPPORTED "
        DEFVAL          {300}           
::= {gxdslLineSpectrumProfileEntry 26}

gxdslLineRADNoiseMarginDownstream       OBJECT-TYPE
        SYNTAX          INTEGER
        ACCESS          read-write
        STATUS          mandatory
        DESCRIPTION      
        "This object specifies the Downstream Downshift Noise Margin for Rate
         Adaptation. If the downstream noise margin is below the Downstream
         Downshift Noise Margin and stays below that for more than the time
         specified by the Downstream Minimum Downshift Rate Adaptation 
         Interval, the XTU R shall attempt to decrease the downstream net data 
         rate. It is expressed in dB.
         Range: 0 to 31 dB in steps of 0.1 dB. The Downstream Downshift Noise
         Margin is represented as 1/10 * xdslLineRADNoiseMarginDownstream.

         ALCATEL NOTE:
             ACCESS:   NA                  USAGE:    OPT
             PERSIST:  YES                 INSRVMOD: YES
             RANGE:    0..310              DEFVALUE: NA
             UNITS:    dB / 10             SPARSE:   NA
             DESCR:    NA
        
         FGU4.4:  THIS OBJECT IS NOT SUPPORTED "
        DEFVAL          {20} 
::= {gxdslLineSpectrumProfileEntry 27}

gxdslLineRADNoiseMarginUpstream         OBJECT-TYPE
        SYNTAX          INTEGER
        ACCESS          read-write
        STATUS          mandatory
        DESCRIPTION      
        "This object specifies the Upstream Downshift Noise Margin for Rate
         Adaptation. If the upstream noise margin is below the Upstream
         Downshift Noise Margin and stays below that for more than the time
         specified by the Upstream Minimum Downshift Rate Adaptation Interval,
         the XTU C shall attempt to decrease the upstream net data rate. It is 
         expressed in dB.
         Range: 0 to 31 dB in steps of 0.1 dB. The Upstream Downshift Noise
         Margin is represented as 1/10 * xdslLineRADNoiseMarginUpstream.

         ALCATEL NOTE:
             ACCESS:   NA                  USAGE:    OPT
             PERSIST:  YES                 INSRVMOD: YES
             RANGE:    0..310              DEFVALUE: NA
             UNITS:    dB / 10             SPARSE:   NA
             DESCR:    NA
        
         FGU4.4:  THIS OBJECT IS NOT SUPPORTED "
        DEFVAL          {20}           
::= {gxdslLineSpectrumProfileEntry 28}

gxdslLineRADTimeDownstream              OBJECT-TYPE
        SYNTAX          INTEGER
        ACCESS          read-write
        STATUS          mandatory
        DESCRIPTION      
        "This object specifies the Downstream Minimum Downshift Rate Adaptation
         Interval. This is the interval of time the downstream noise margin 
         should stay below the Downstream Downshift Noise Margin before the XTU
         R shall attempt to decrease the downstream net data rate.

         ALCATEL NOTE:
             ACCESS:   NA                  USAGE:    OPT
             PERSIST:  YES                 INSRVMOD: YES
             RANGE:    0..16383            DEFVALUE: NA
             UNITS:    seconds             SPARSE:   NA
             DESCR:    NA
        
         FGU4.4:  THIS OBJECT IS NOT SUPPORTED "
        DEFVAL          {30}           
::= {gxdslLineSpectrumProfileEntry 29}

gxdslLineRADTimeUpstream OBJECT-TYPE
        SYNTAX          INTEGER
        ACCESS          read-write
        STATUS          mandatory
        DESCRIPTION      
        "This object specifies the Upstream Minimum Downshift Rate Adaptation
         Interval. This is the interval of time the upstream noise margin 
         should stay below the Upstream Downshift Noise Margin before the XTU C 
         shall attempt to decrease the upstream net data rate.

         ALCATEL NOTE:
             ACCESS:   NA                  USAGE:    OPT
             PERSIST:  YES                 INSRVMOD: YES
             RANGE:    0..16383            DEFVALUE: NA
             UNITS:    seconds             SPARSE:   NA
             DESCR:    NA
        
         FGU4.4:  THIS OBJECT IS NOT SUPPORTED "
        DEFVAL          {30}           
::= {gxdslLineSpectrumProfileEntry 30}

gxdslLineArtificialNoisePsdDownstream         OBJECT-TYPE
        SYNTAX          GArtificialNoisePsdDownType
        ACCESS          read-write
        STATUS          mandatory
        DESCRIPTION     
        "This object specifies the transmitter-referred artificial noise level
         to be used as additional noise source at the downstream transmitter.
         A number of 2 to 32 Artificial Noise PSD points can be specified
         downstream.
         An empty sequence means that no artificial noise shall be used.
         The successive PSD points must have increasing (>/=) frequencies.
         It is allowed that for two successive PSD points, different PSD
         levels are defined at a same frequency (brickwall).
         Artificial Noise PSD points are defined in the range -140dBm/Hz..-40 
         dBm/Hz.
         A special value (-167,5 dBm/Hz) states no artificial noise has to be
         applied.
         The Artificial Noise PSD Shape is coded as a variable length octet string
         defined as follows:
         Octet 0: reserved 
         Octet 1..3: defines PSD point #1
         OCTETS 1..2: INTEGER (0..30000), frequency of PSD point #1,
         expressed in kHz. The value is defined as MSB-LSB (big-endian).
         OCTET 3: INTEGER (0..200), -2*(40 + PSD level) (in dBm/Hz) of
         PSD point#1.
         OCTETS 4..6: define the frequency and PSD level of PSD point #2.
         ...        up to
         OCTETS 3*N-2..3*N: define the frequency and PSD level of the last PSD
         point #N with N<=32.

         ALCATEL NOTE:
             ACCESS:   NA                  USAGE:    OPT
             PERSIST:  YES                 INSRVMOD: YES
             RANGE:    0..97               DEFVALUE: ''H
             UNITS:    NA                  SPARSE:   NA
             DESCR:    NA
        
         FGU4.4:  THIS OBJECT IS NOT SUPPORTED "
::= {gxdslLineSpectrumProfileEntry 31}

   gxdslLineSpectrumProfileAdslAdsl2Table  OBJECT-TYPE
           SYNTAX          SEQUENCE OF GxdslLineSpectrumProfileAdslAdsl2Entry
           ACCESS          not-accessible
           STATUS          mandatory
          DESCRIPTION     
          "This table is part of the line profile. It contains the line
            related parameters of the ONT XDSL Line configuration that apply to the ADSL
            and/or ADSL2 operational modes and use specific values for these modes
            of operation. These parameters are ignored in case another operational
            mode is used.
   
            ALCATEL NOTE:
                TABLESIZE: 256                    
                DESCR:     NA                  
         
           ISR4.3:  THIS TABLE IS NOW SUPPORTED "
   ::= {gxdslLineSpectrumProfile 2}
 
   gxdslLineSpectrumProfileAdslAdsl2Entry  OBJECT-TYPE
           SYNTAX          GxdslLineSpectrumProfileAdslAdsl2Entry
           ACCESS          not-accessible
           STATUS          mandatory
           DESCRIPTION     
           "Each entry consists of a list of line related parameters that serve 
            to configure an ONT XDSL Line  in case the ADSL or ADSL2 modes of
            operation are used.
   
            Row creation : When an entry is created in the 
                           gxdslLineSpectrumProfileTable, an entry with the same 
                           gxdslLineSpectrumIndex is created in this table.
            Row deletion : When an entry is deleted from the
                           gxdslLineSpectrumProfileTable, the entry with the same
                           gxdslLineSpectrumIndex is deleted from this table. 
           "
           INDEX          {gxdslLineSpectrumProfileIndex}
   ::= {gxdslLineSpectrumProfileAdslAdsl2Table 1}
 
   GxdslLineSpectrumProfileAdslAdsl2Entry ::=
           SEQUENCE {
--             adslModemFeatures                         INTEGER,
               gadslMaxAggregatePowerLevelDownstream      INTEGER,
               gadslMaxAggregatePowerLevelUpstream        INTEGER,
               gadslMaxPsdLevelDownstream                 INTEGER,
               gadslMaxPsdLevelUpstream                   INTEGER
--             adslPsdShapeDownstream                    GAdslPsdDownstreamType,
--             adslCustomPsdShapeDownstream              GCustomPsdShapeType, 
--             adslPsdShapeUpstream                      GAdslPsdUpstreamType,
--             adslCustomPsdShapeUpstream                GCustomPsdShapeType,
--             adslPboModeUpstream                       GPboModeType,
--             adslMaxRxAggregatePowerLevelUpstream      INTEGER
       	}
        
-- adslModemFeatures       OBJECT-TYPE
--         SYNTAX          INTEGER
--         ACCESS          read-write
--         STATUS          mandatory 
--         DESCRIPTION 
--         "This object allows to enable/disable specific features of the modem.
--          It is a bitmap represented as a sum and allows multiple features to be
--          configured simultaneously. Currently only bit 0 is used, the other
--          bits are reserved for future use.
--          Bitmap values:
--          1   Strict compliancy, the modem should turn off all
--              features not strictly compliant with the standards.
--              The modem is allowed to use proprietary features when
--              bit 0 is set to 0.
-- 
--          ALCATEL NOTE:
--              ACCESS:   NA                  USAGE:    OPT
--              PERSIST:  YES                 INSRVMOD: YES
--              RANGE:    0..1                DEFVALUE: 1
--              UNITS:    NA                  SPARSE:   NA
--              DESCR:    NA
--         "
-- ::= {xdslLineSpectrumProfileAdslAdsl2Entry 1}
-- 
   gadslMaxAggregatePowerLevelDownstream   OBJECT-TYPE
           SYNTAX          INTEGER
           ACCESS          read-write
           STATUS          mandatory
           DESCRIPTION     
           "This parameter indicates the maximum power allowed on 
            the line for the downstream direction. If the necessary power level 
            exceeds the level given by this parameter the ONT XDSL Line will reinitialize.  
            The aggregate power has a range of 0 dBm to +25.5 dBm in steps of 0.1
            dB. It is represented as 1/10 * gadslMaxAggregatePowerLevelDownstream.
            In case the corresponding DSL standard imposes a more stringent value
            for this parameter, the configured value will be ignored and the
            standard value will apply.
   
            ALCATEL NOTE:
                ACCESS:   NA                  USAGE:    OPT
                PERSIST:  YES                 INSRVMOD: NA
                RANGE:    0..255              DEFVALUE: 255
                UNITS:    dBm / 10            SPARSE:   NA
                DESCR:    NA
           "
   ::=  {gxdslLineSpectrumProfileAdslAdsl2Entry 2}
          
   gadslMaxAggregatePowerLevelUpstream     OBJECT-TYPE
           SYNTAX          INTEGER
           ACCESS          read-write
           STATUS          mandatory
           DESCRIPTION     
           "This parameter indicates the maximum power allowed on the line for the 
            upstream direction. If the necessary power level exceeds the level 
            given by this parameter the ONT XDSL Line will re-initialize. 
            The aggregate power has a range of 0 dBm to +25.5 dBm in steps of 0.1
            dB. It is represented as 1/10 * gadslMaxAggregatePowerLevelUpstream.
            In case the corresponding DSL standard imposes a more stringent value
            for this parameter, the configured value will be ignored and the
            standard value will be used.
   
            ALCATEL NOTE:
                ACCESS:   NA                  USAGE:    OPT
                PERSIST:  YES                 INSRVMOD: YES
                RANGE:    0..255              DEFVALUE: 255
                UNITS:    dBm / 10            SPARSE:   NA
                DESCR:    NA
           "
   ::=  {gxdslLineSpectrumProfileAdslAdsl2Entry 3}
   
   gadslMaxPsdLevelDownstream              OBJECT-TYPE
           SYNTAX          INTEGER
           ACCESS          read-write
           STATUS          mandatory
           DESCRIPTION     
           "This object gives the power spectral density allowed on the line
            for the downstream band. A lower value results in reduction of 
            power consumption, by paying the price of having a lower capacity. 
            It is expressed in dBm/Hz.
            When a PSD shape is configured, this parameter can be used to specify
            an additional constraint on the max PSD level.
            The PSD has a range of -60 dBm/Hz to -40 dBm/Hz in steps of 0.1 dB.
            It is represented as 1/10* gxdslLineMaxPsdLevelDownstream.
            In case the corresponding DSL standard imposes a more stringent value
            for this parameter, the configured value will be ignored and the
            standard value will apply.
   
            ALCATEL NOTE:
                ACCESS:   NA                  USAGE:    OPT
                PERSIST:  YES                 INSRVMOD: YES
                RANGE:    -600..-400          DEFVALUE: -400
                UNITS:    dBm/Hz * 1/10       SPARSE:   NA
                DESCR:    NA
           "
   ::= {gxdslLineSpectrumProfileAdslAdsl2Entry 4}
   
   gadslMaxPsdLevelUpstream                OBJECT-TYPE
           SYNTAX          INTEGER
           ACCESS          read-write
           STATUS          mandatory
           DESCRIPTION     
           "This object gives the power spectral density (in dBm/Hz) allowed on 
            the line for the upstream band. A lower value results in reduction of 
            power consumption, by paying the price of having a lower capacity. 
            It is expressed in dBm/Hz.
            When a PSD shape is configured, this parameter can be used to specify
            an additional constraint on the max PSD level.
            The PSD has a range of -60 dBm/Hz to -38 dBm/Hz in steps of 0.1 dB.
            It is represented as 1/10* gxdslLineMaxPsdLevelUpstream.
            In case the corresponding DSL standard imposes a more stringent value
            for this parameter, the configured value will be ignored and the
            standard value will apply.
   
            ALCATEL NOTE:
                ACCESS:   NA                  USAGE:    OPT
                PERSIST:  YES                 INSRVMOD: YES
                RANGE:    -600..-380          DEFVALUE: -380
                UNITS:    dBm/Hz * 1/10       SPARSE:   NA
                DESCR:    NA
           "
   ::= {gxdslLineSpectrumProfileAdslAdsl2Entry 5}
-- 
-- adslPsdShapeDownstream                 OBJECT-TYPE
--         SYNTAX          GAdslPsdDownstreamType
--         ACCESS          read-write
--         STATUS          mandatory
--         DESCRIPTION     
--         "This parameter defines the PSD shape that must be applied for ADSL
--          in the downstream direction.
--          adslCustomPsdDownstream: a custom PSD Shape is defined in
--          adslCustomPsdShapeDownstream.
--          adslStdPsdDownstream: the standard PSD shape is applied.
-- 
--          ALCATEL NOTE:
--              ACCESS:   NA                  USAGE:    OPT
--              PERSIST:  YES                 INSRVMOD: YES
--              RANGE:    adslStdPsdDownstream 
--              DEFVALUE: adslStdPsdDownstream
--              UNITS:    NA                  SPARSE:   NA
--              DESCR:    The object is supported to avoid future database 
--                        migration but should not be set.
--                        Set requests will be rejected (badvalue) if the value
--                        differs from the default value.
--         "
-- ::= {xdslLineSpectrumProfileAdslAdsl2Entry 6}
-- 
-- adslCustomPsdShapeDownstream           OBJECT-TYPE
--         SYNTAX          GCustomPsdShapeType 
--         ACCESS          read-write
--         STATUS          mandatory
--         DESCRIPTION     
--         "This object specifies PSD points of a custom ADSL PSD Shape for
--          the downstream direction in case adslPsdShapeDownstream =
--          adslCustomPsdDownstream and it will be ignored otherwise.
--          A number of 2 to 20 PSD points can be specified.
--          The successive PSD points must have increasing (>/=) frequencies.
--          It is allowed that for two successive PSD points, different PSD
--          levels are defined at a same frequency (brickwall).
--          The custom PSD Shape is coded as a variable length octet string
--          defined as follows:
--          OCTET 0: defines the frequency scale to be used for the interpolation
--          of the PSD Shape data (0x00= linear frequency scale,
--          0x01 = logarithmic frequency scale).
--          OCTETS 1..2: INTEGER (0..1104), frequency of the first PSD point
--          expressed in kHz. The value is defined as MSB-LSB (big-endian).
--          OCTET 3: INTEGER (0..255), -2*PSD level (in dBm/Hz) of the first
--          PSD point.
--          OCTETS 4..6: define the frequency and PSD level of PSD point 2.
--          ...        up to
--          OCTETS 3*N-2..3*N: define the frequency and PSD level of the last PSD
--          point N with N<=20.
-- 
--          ALCATEL NOTE:
--              ACCESS:   NA                  USAGE:    OPT
--              PERSIST:  YES                 INSRVMOD: YES
--              RANGE:    0                   DEFVALUE: ''H
--              UNITS:    OCTETS              SPARSE:   NA
--              DESCR:    The object is supported to avoid future database 
--                        migration but should not be set.
--                        Set requests will be rejected (badvalue) if the value
--                        differs from the default value.
--         "
-- ::= {xdslLineSpectrumProfileAdslAdsl2Entry 7}
-- 
-- adslPsdShapeUpstream    OBJECT-TYPE
--         SYNTAX          GAdslPsdUpstreamType
--         ACCESS          read-write
--         STATUS          mandatory
--         DESCRIPTION     
--         "This parameter defines the PSD Shape that must be applied for ADSL
--          in the upstream direction.
--          adslCustomPsdUpstream: a custom PSD Shape is defined in
--          adslCustomPsdShapeUpstream.
--          adslStdPsdUpstream: the standard PSD shape is applied.
-- 
--          ALCATEL NOTE:
--              ACCESS:   NA                  USAGE:    OPT
--              PERSIST:  YES                 INSRVMOD: YES
--              RANGE:    adslStdPsdUpstream  DEFVALUE: adslStdPsdUpstream
--              UNITS:    NA                  SPARSE:   NA
--              DESCR:    The object is supported to avoid future database 
--                        migration but should not be set.
--                        Set requests will be rejected (badvalue) if the value
--                        differs from the default value.
--         "
-- ::= {xdslLineSpectrumProfileAdslAdsl2Entry 8}
-- 
-- adslCustomPsdShapeUpstream             OBJECT-TYPE
--         SYNTAX          GCustomPsdShapeType 
--         ACCESS          read-write
--         STATUS          mandatory
--         DESCRIPTION     
--         "This object specifies PSD points of a custom ADSL PSD Shape for
--          the upstream direction in case adslPsdShapeUpstream =
--          adslCustomPsdUpstream and it will be ignored otherwise.
--          A number of 2 to 20 points can be specified.
--          The successive PSD points must have increasing (>/=) frequencies.
--          It is allowed that for two successive PSD points, different PSD
--          levels are defined at a same frequency (brickwall).
--          The custom PSD Shape is coded as a variable length octet string
--          defined as follows:
--          OCTET 0: defines the frequency scale to be used for the interpolation
--          of the PSD Shape data (0x00= linear frequency scale,
--          0x01 = logarithmic frequency scale).
--          OCTETS 1..2: INTEGER (0..1104), frequency of the first PSD point
--          expressed in kHz. The value is defined as MSB-LSB (big-endian).
--          OCTET 3: INTEGER (0..255), represents -2*PSD level (in dBm/Hz)
--          of the first PSD point.
--          OCTETS 4..6:  define the frequency and PSD level of PSD point 2.
--          ...        up to
--          OCTETS 3*N-2..3*N: define the frequency and PSD level of the last PSD
--          point N with N<=20.
-- 
--          ALCATEL NOTE:
--              ACCESS:   NA                  USAGE:    OPT
--              PERSIST:  YES                 INSRVMOD: YES
--              RANGE:    0                   DEFVALUE: ''H
--              UNITS:    OCTETS              SPARSE:   NA
--              DESCR:    The object is supported to avoid future database 
--                        migration but should not be set.
--                        Set requests will be rejected (badvalue) if the value
--                        differs from the default value.
--         "
-- ::= {xdslLineSpectrumProfileAdslAdsl2Entry 9}
-- 
-- adslPboModeUpstream     OBJECT-TYPE
--         SYNTAX          GPboModeType
--         ACCESS          read-write
--         STATUS          mandatory
--         DESCRIPTION     
--         "Identifies the upstream power backoff mode.
--          pboModeOff: upstream power backoff is OFF, no power cutback is applied
--             by the receiver.
--          pboModeOn: upstream power backoff is ON, upstream power cutback is
--             requested if the RX aggregate power exceeds the max RX aggregate
--             power (adslMaxRxAggregatePowerUpstream).
-- 
--          ALCATEL NOTE:
--              ACCESS:   NA                  USAGE:    OPT
--              PERSIST:  YES                 INSRVMOD: YES
--              RANGE:    NA                  DEFVALUE: pboModeOff
--              UNITS:    NA                  SPARSE:   NA
--              DESCR:    NA
--         "
-- ::= {xdslLineSpectrumProfileAdslAdsl2Entry 10}
-- 
-- adslMaxRxAggregatePowerLevelUpstream   OBJECT-TYPE
--         SYNTAX          INTEGER
--         ACCESS          read-write
--         STATUS          mandatory
--         DESCRIPTION     
--         "This parameter indicates the maximum receive power allowed on the line
--          for the upstream direction.
--          The aggregate power has a range of -25.5 dBm to +25.5 dBm in steps of
--          0.1 dB. It is represented as 1/10 * adslMaxRxAggregatePowerUpstream.
-- 
--          ALCATEL NOTE:
--              ACCESS:   NA                  USAGE:    OPT
--              PERSIST:  YES                 INSRVMOD: YES
--              RANGE:    -255..255           DEFVALUE: 255
--              UNITS:    dBm / 10            SPARSE:   NA
--              DESCR:    NA
--         "
-- ::= {xdslLineSpectrumProfileAdslAdsl2Entry 11}
-- 
-- xdslLineSpectrumProfileReAdsl2Table    OBJECT-TYPE
--         SYNTAX          SEQUENCE OF XdslLineSpectrumProfileReAdsl2Entry
--         ACCESS          not-accessible
--         STATUS          mandatory
--         DESCRIPTION     
--         "This table is part of the line profile. It contains the line
--          related parameters of the modem configuration that apply to the
--          READSL2 operational mode and use specific values for this mode of
--          operation. These parameters are ignored in case another operational
--          mode is used.
--
--          ALCATEL NOTE:
--              TABLESIZE: 256                   
--              DESCR:     NA                  
--         
--          FGU4.4:  THIS TABLE IS NOT SUPPORTED "
-- ::= {gxdslLineSpectrumProfile 3}
-- 
-- xdslLineSpectrumProfileReAdsl2Entry    OBJECT-TYPE
--         SYNTAX          XdslLineSpectrumProfileReAdsl2Entry
--         ACCESS          not-accessible
--         STATUS          mandatory
--         DESCRIPTION     
--         "Each entry consists of a list of line related parameters that serve 
--          to configure an XDSL modem in case the READSL2 mode of operation is
--          used.
-- 
--          Row creation : When an entry is created in the 
--                         xdslLineSpectrumProfileTable, an entry with the same 
--                         xdslLineSpectrumIndex is created in this table.
--          Row deletion : When an entry is deleted from the
--                         xdslLineSpectrumProfileTable, the entry with the same
--                         xdslLineSpectrumIndex is deleted from this table. 
--         "
--         INDEX          {xdslLineSpectrumProfileIndex}
-- ::= {xdslLineSpectrumProfileReAdsl2Table 1}
-- 
-- XdslLineSpectrumProfileReAdsl2Entry ::=
--         SEQUENCE {
--             reAdsl2ModemFeatures                      INTEGER,
--             reAdsl2MaxAggregatePowerLevelDownstream   INTEGER,
--             reAdsl2MaxAggregatePowerLevelUpstream     INTEGER,
--             reAdsl2MaxPsdLevelDownstream              INTEGER,
--             reAdsl2MaxPsdLevelUpstream                INTEGER,
--             reAdsl2PsdShapeDownstream                 GReAdsl2PsdDownstreamType,
--             reAdsl2CustomPsdShapeDownstream           GCustomPsdShapeType,
--             reAdsl2PsdShapeUpstream                   GReAdsl2PsdUpstreamType,
--             reAdsl2CustomPsdShapeUpstream             GCustomPsdShapeType,
--             reAdsl2PboModeUpstream                    GPboModeType,
--             reAdsl2MaxRxAggregatePowerLevelUpstream   INTEGER
--         }
-- 
-- reAdsl2ModemFeatures    OBJECT-TYPE
--         SYNTAX          INTEGER
--         ACCESS          read-write
--         STATUS          mandatory 
--         DESCRIPTION 
--         "This object allows to enable/disable specific features of the modem.
--          It is a bitmap represented as a sum and allows multiple features to be
--          configured simultaneously. Currently only bit 0 is used, the other
--          bits are reserved for future use.
--          Bitmap values:
--           1   Strict compliancy, the modem should turn off all features not
--               strictly compliant with the standards.
--               The modem is allowed to use proprietary features when
--               bit 0 is set to 0.
-- 
--          ALCATEL NOTE:
--              ACCESS:   NA                  USAGE:    OPT
--              PERSIST:  YES                 INSRVMOD: YES
--              RANGE:    0..1                DEFVALUE: 1
--              UNITS:    NA                  SPARSE:   NA
--              DESCR:    NA
--         "
-- ::= {xdslLineSpectrumProfileReAdsl2Entry 1}
-- 
-- reAdsl2MaxAggregatePowerLevelDownstream          OBJECT-TYPE
--         SYNTAX          INTEGER
--         ACCESS          read-write
--         STATUS          mandatory
--         DESCRIPTION     
--         "This parameter indicates the maximum power allowed on 
--          the line for the downstream direction. If the necessary power level 
--          exceeds the level given by this parameter the modem will re-
--          initialize.  
--          The aggregate power has a range of 0 dBm to +25.5 dBm in steps of 0.1
--          dB.
--          It is represented as 1/10 * reAdsl2MaxAggregatePowerLevelDownstream.
--          In case the corresponding DSL standard imposes a more stringent value
--          for this parameter, the configured value will be ignored and the
--          standard value will apply.
-- 
--          ALCATEL NOTE:
--              ACCESS:   NA                  USAGE:    OPT
--              PERSIST:  YES                 INSRVMOD: YES
--              RANGE:    0..255              DEFVALUE: 255
--              UNITS:    dBm / 10            SPARSE:   NA
--              DESCR:    NA
--         "
-- ::= {xdslLineSpectrumProfileReAdsl2Entry 2}
-- 
-- reAdsl2MaxAggregatePowerLevelUpstream  OBJECT-TYPE
--         SYNTAX          INTEGER
--         ACCESS          read-write
--         STATUS          mandatory
--         DESCRIPTION     
--         "This parameter indicates the maximum power allowed on the line for the 
--          upstream direction. If the necessary power level exceeds the level 
--          given by this parameter the modem will re-initialize. 
--          The aggregate power has a range of 0 dBm to 25.5 dBm in steps of 0.1
--          dB.
--          It is represented as 1/10 * reAdsl2MaxAggregatePowerLevelUpstream.
--          In case the corresponding DSL standard imposes a more stringent value
--          for this parameter, the configured value will be ignored and the
--          standard value will apply.
-- 
--         ALCATEL NOTE:
--              ACCESS:   NA                  USAGE:    OPT
--              PERSIST:  YES                 INSRVMOD: YES
--              RANGE:    0..255              DEFVALUE: 255
--              UNITS:    dBm / 10            SPARSE:   NA
--              DESCR:    NA
--         "
-- ::= {xdslLineSpectrumProfileReAdsl2Entry 3}
-- 
-- reAdsl2MaxPsdLevelDownstream           OBJECT-TYPE
--         SYNTAX          INTEGER
--         ACCESS          read-write
--         STATUS          mandatory
--         DESCRIPTION     
--         "This object gives the power spectral density allowed on the line
--          for the downstream band. A lower value results in reduction of 
--          power consumption, by paying the price of having a lower capacity. 
--          It is expressed in dBm/Hz.
--          When a PSD shape is configured, this parameter can be used to specify
--          an additional constraint on the max PSD level.
--          The PSD has a range of -60 dBm/Hz to -37 dBm/Hz in steps of 0.1 dB.
--          It is represented as 1/10* reAdsl2MaxPsdLevelDownstream.
--          In case the corresponding DSL standard imposes a more stringent value
--          for this parameter, the configured value will be ignored and the
--          standard value will apply.
-- 
--          ALCATEL NOTE:
--              ACCESS:   NA                  USAGE:    OPT
--              PERSIST:  YES                 INSRVMOD: YES
--              RANGE:    -600..-370          DEFVALUE: -370
--              UNITS:    dBm/Hz * 1/10       SPARSE:   NA
--              DESCR:    NA
--         "
-- ::= {xdslLineSpectrumProfileReAdsl2Entry 4}
-- 
-- reAdsl2MaxPsdLevelUpstream             OBJECT-TYPE
--         SYNTAX          INTEGER
--         ACCESS          read-write
--         STATUS          mandatory
--         DESCRIPTION     
--         "This object gives the power spectral density allowed on the line
--          for the upstream band. A lower value results in reduction of 
--          power consumption, by paying the price of having a lower capacity. 
--          It is expressed in dBm/Hz.
--          When a PSD shape is configured, this parameter can be used to specify
--          an additional constraint on the max PSD level.
--          The PSD has a range of -60 dBm/Hz to -32.9 dBm/Hz in steps of 0.1 dB.
--          It is represented as 1/10* reAdsl2MaxPsdLevelUpstream.
--          In case the corresponding DSL standard imposes a more stringent value
--          for this parameter, the configured value will be ignored and the
--          standard value will apply.
-- 
--          ALCATEL NOTE:
--              ACCESS:   NA                  USAGE:    OPT
--              PERSIST:  YES                 INSRVMOD: YES
--              RANGE:    -600..-329          DEFVALUE: -329
--              UNITS:    dBm/Hz * 1/10       SPARSE:   NA
--              DESCR:    NA
--         "
-- ::= {xdslLineSpectrumProfileReAdsl2Entry 5}
-- 
-- reAdsl2PsdShapeDownstream              OBJECT-TYPE
--         SYNTAX          GReAdsl2PsdDownstreamType
--         ACCESS          read-write
--         STATUS          mandatory
--         DESCRIPTION     
--         "This parameter defines the PSD Shape that must be applied for READSL2
--          in the downstream direction.
--          reAdsl2CustomPsdDownstream: a custom PSD Shape is defined in
--          reAdsl2CustomPsdShapeDownstream.
--          reAdsl2StdPsdDownstream: the standard PSD shape is applied.
-- 
--          ALCATEL NOTE:
--              ACCESS:   NA                  USAGE:    OPT
--              PERSIST:  YES                 INSRVMOD: YES
--              RANGE:    reAdsl2StdPsdDownstream 
--              DEFVALUE: reAdsl2StdPsdDownstream
--              UNITS:    NA                  SPARSE:   NA
--              DESCR:    The object is supported to avoid future database 
--                        migration but should not be set.
--                        Set requests will be rejected (badvalue) if the value
--                        differs from the default value.
--         "
-- ::= {xdslLineSpectrumProfileReAdsl2Entry 6}
-- 
-- reAdsl2CustomPsdShapeDownstream        OBJECT-TYPE
--         SYNTAX          GCustomPsdShapeType 
--         ACCESS          read-write
--         STATUS          mandatory
--         DESCRIPTION     
--         "This object specifies PSD points of a custom READSL2 PSD Shape for
--          the downstream direction in case reAdsl2PsdShapeDownstream =
--          reAdsl2CustomPsdDownstream and it will be ignored otherwise.
--          A number of 2 to 20 PSD points can be specified.
--          The successive PSD points must have increasing (>/=) frequencies.
--          It is allowed that for two successive PSD points, different PSD
--          levels are defined at a same frequency (brickwall).
--          The custom PSD Shape is coded as a variable length octet string
--          defined as follows:
--          OCTET 0: defines the frequency scale to be used for the interpolation
--          of the PSD Shape data (0x00= linear frequency scale,
--          0x01 = logarithmic frequency scale).
--          OCTETS 1..2: INTEGER (0..2208), frequency of the first PSD point
--          expressed in kHz. The value is defined as MSB-LSB (big-endian).
--          OCTET 3: INTEGER (0..255), -2*PSD level (in dBm/Hz) of the first
--          PSD point.
--          OCTETS 4..6: define the frequency and PSD level of PSD point 2.
--          ...        up to
--          OCTETS 3*N-2..3*N: define the frequency and PSD level of the last PSD
--          point N with N<=20.
-- 
--          ALCATEL NOTE:
--              ACCESS:   NA                  USAGE:    OPT
--              PERSIST:  YES                 INSRVMOD: YES
--              RANGE:    0                   DEFVALUE: ''H
--              UNITS:    OCTETS              SPARSE:   NA
--              DESCR:    The object is supported to avoid future database 
--                        migration but should not be set.
--                        Set requests will be rejected (badvalue) if the value
--                        differs from the default value.
--         "
-- ::= {xdslLineSpectrumProfileReAdsl2Entry 7}
-- 
-- reAdsl2PsdShapeUpstream                OBJECT-TYPE
--         SYNTAX          GReAdsl2PsdUpstreamType
--         ACCESS          read-write
--         STATUS          mandatory
--         DESCRIPTION     
--         "This parameter defines the PSD Shape that must be applied for READSL2
--          in the upstream direction.
--          reAdsl2CustomPsdUpstream: a custom PSD Shape is defined in
--          reAdsl2CustomPsdShapeUpstream.
--          reAdsl2StdPsdUpstream: the standard PSD shape is applied.
-- 
--          ALCATEL NOTE:
--              ACCESS:   NA                  USAGE:    OPT
--              PERSIST:  YES                 INSRVMOD: YES
--              RANGE:    reAdsl2StdPsdUpstream
--              DEFVALUE: reAdsl2StdPsdUpstream
--              UNITS:    NA                  SPARSE:   NA
--              DESCR:    The object is supported to avoid future database 
--                        migration but should not be set.
--                        Set requests will be rejected (badvalue) if the value
--                        differs from the default value.
--         "
-- ::= {xdslLineSpectrumProfileReAdsl2Entry 8}
-- 
-- reAdsl2CustomPsdShapeUpstream          OBJECT-TYPE
--         SYNTAX          GCustomPsdShapeType 
--         ACCESS          read-write
--         STATUS          mandatory
--         DESCRIPTION     
--         "This object specifies PSD points of a custom READSL2 PSD Shape for
--          the upstream direction in case reAdsl2PsdShapeUpstream =
--          reAdsl2CustomPsdUpstream and it will be ignored otherwise.
--          A number of 2 to 20 points can be specified.
--          The successive PSD points must have increasing (>/=) frequencies.
--          It is allowed that for two successive PSD points, different PSD
--          levels are defined at a same frequency (brickwall).
--          The custom PSD Shape is coded as a variable length octet string
--          defined as follows:
--          OCTET 0: defines the frequency scale to be used for the interpolation
--          of the PSD Shape data (0x00= linear frequency scale,
--          0x01 = logarithmic frequency scale).
--          OCTETS 1..2: INTEGER (0..2208), frequency of the first PSD point
--          expressed in kHz. The value is defined as MSB-LSB (big-endian).
--          OCTET 3: INTEGER (0..255), represents -2*PSD level (in dBm/Hz)
--          of the first PSD point.
--          OCTETS 4..6:  define the frequency and PSD level of PSD point 2.
--          ...        up to
--          OCTETS 3*N-2..3*N: define the frequency and PSD level of the last PSD
--          point N with N<=20.
-- 
--          ALCATEL NOTE:
--              ACCESS:   NA                  USAGE:    OPT
--              PERSIST:  YES                 INSRVMOD: YES
--              RANGE:    0                   DEFVALUE: ''H
--              UNITS:    OCTETS              SPARSE:   NA
--              DESCR:    The object is supported to avoid future database 
--                        migration but should not be set.
--                        Set requests will be rejected (badvalue) if the value
--                        differs from the default value.
--         "
-- ::= {xdslLineSpectrumProfileReAdsl2Entry 9}
-- 
-- reAdsl2PboModeUpstream  OBJECT-TYPE
--         SYNTAX          GPboModeType
--         ACCESS          read-write
--         STATUS          mandatory
--         DESCRIPTION     
--         "Identifies the upstream PSD power backoff mode.
--          pboModeOff: upstream power backoff is OFF, no power cutback is applied
--          by the receiver.
--          pboModeOn: upstream power backoff is ON, upstream power cutback is
--          requested if the RX aggregate power exceeds the max RX aggregate power
--          (reAdsl2MaxRxAggregatePowerUpstream).
-- 
--          ALCATEL NOTE:
--              ACCESS:   NA                  USAGE:    OPT
--              PERSIST:  YES                 INSRVMOD: YES
--              RANGE:    NA                  DEFVALUE: pboModeOff
--              UNITS:    NA                  SPARSE:   NA
--              DESCR:    NA
--         "
-- ::= {xdslLineSpectrumProfileReAdsl2Entry 10}
-- 
-- reAdsl2MaxRxAggregatePowerLevelUpstream     OBJECT-TYPE
--         SYNTAX          INTEGER
--         ACCESS          read-write
--         STATUS          mandatory
--         DESCRIPTION     
--         "This parameter indicates the maximum receive power allowed on the line
--          for the upstream direction.
--          The aggregate power has a range of -25.5 dBm to +25.5 dBm in steps of
--          0.1 dB. 
--          It is represented as 1/10 * reAdsl2MaxRxAggregatePowerUpstream.
-- 
--          ALCATEL NOTE:
--              ACCESS:   NA                  USAGE:    OPT
--              PERSIST:  YES                 INSRVMOD: YES
--              RANGE:    -255..255           DEFVALUE: 255
--              UNITS:    dBm / 10            SPARSE:   NA
--              DESCR:    NA
--         "
-- ::= {xdslLineSpectrumProfileReAdsl2Entry 11}
-- 
   gxdslLineSpectrumProfileAdsl2PlusTable  OBJECT-TYPE
           SYNTAX          SEQUENCE OF GxdslLineSpectrumProfileAdsl2PlusEntry
           ACCESS          not-accessible
           STATUS          mandatory
           DESCRIPTION     
           "This table is part of the line profile. It contains the line
            related parameters of the modem configuration that apply to the ADSL2
            Plus operational mode and use specific values for this mode of
            operation. These parameters are ignored in case another operational
            mode is used.
   
            ALCATEL NOTE:
                TABLESIZE: 256                    
                DESCR:     NA                  
           
            ISR4.3:  THIS TABLE IS NOW SUPPORTED "
   ::= {gxdslLineSpectrumProfile 4}
  
   gxdslLineSpectrumProfileAdsl2PlusEntry  OBJECT-TYPE
           SYNTAX          GxdslLineSpectrumProfileAdsl2PlusEntry
           ACCESS          not-accessible
           STATUS          mandatory
           DESCRIPTION     
           "Each entry consists of a list of line related parameters that serve 
            to configure an ONT XDSL Line in case the ADSL2 Plus mode of operation is
            used.
   
            Row creation : When an entry is created in the 
                           gxdslLineSpectrumProfileTable, an entry with the same 
                           gxdslLineSpectrumIndex is created in this table.
            Row deletion : When an entry is deleted from the
                           gxdslLineSpectrumProfileTable, the entry with the same
                           gxdslLineSpectrumIndex is deleted from this table. 
           "
           INDEX          {gxdslLineSpectrumProfileIndex}
   ::= {gxdslLineSpectrumProfileAdsl2PlusTable 1}
   
   GxdslLineSpectrumProfileAdsl2PlusEntry ::=
           SEQUENCE {
--             adsl2PlusModemFeatures                    INTEGER,
               gadsl2PlusMaxAggregatePowerLevelDownstream INTEGER,
               gadsl2PlusMaxAggregatePowerLevelUpstream   INTEGER,
               gadsl2PlusMaxPsdLevelDownstream            INTEGER,
               gadsl2PlusMaxPsdLevelUpstream              INTEGER
--             adsl2PlusPsdShapeDownstream             GAdsl2PlusPsdDownstreamType,
--             adsl2PlusCustomPsdShapeDownstream         GCustomPsdShapeType,
--             adsl2PlusPsdShapeUpstream                 GAdsl2PlusPsdUpstreamType,
--             adsl2PlusCustomPsdShapeUpstream           GCustomPsdShapeType,
--             adsl2PlusPboModeUpstream                  GPboModeType,
--             adsl2PlusMaxRxAggregatePowerLevelUpstream INTEGER
           }
-- 
-- adsl2PlusModemFeatures                 OBJECT-TYPE
--         SYNTAX      INTEGER
--         ACCESS      read-write
--         STATUS      mandatory 
--         DESCRIPTION 
--         "This object allows to enable/disable specific features of the modem.
--          It is a bitmap represented as a sum and allows multiple features to be
--          configured simultaneously. Currently only bit 0 is used, the other
--          bits are reserved for future use.
--          Bitmap values:
--           1   Strict compliancy, the modem should turn off all features not
--               strictly compliant with the standards.
--               The modem is allowed to use proprietary features when
--               bit 0 is set to 0.
-- 
--          ALCATEL NOTE:
--              ACCESS:   NA                  USAGE:    OPT
--              PERSIST:  YES                 INSRVMOD: YES
--              RANGE:    0..1                DEFVALUE: 1
--              UNITS:    NA                  SPARSE:   NA
--              DESCR:    NA
--         "
-- ::= {xdslLineSpectrumProfileAdsl2PlusEntry 1}
-- 
   gadsl2PlusMaxAggregatePowerLevelDownstream        OBJECT-TYPE
           SYNTAX          INTEGER
           ACCESS          read-write
           STATUS          mandatory
           DESCRIPTION     
           "This parameter indicates the maximum power allowed on 
            the line for the downstream direction. If the necessary power level 
            exceeds the level given by this parameter the ONT XDSL Line will re-
            initialize.  
            The aggregate power has a range of 0 dBm to 25.5 dBm in steps of 0.1
            dB.
            It is represented as 1/10 * gadsl2PlusMaxAggregatePowerLevelDownstream.
            In case the corresponding DSL standard imposes a more stringent value
            for this parameter, the configured value will be ignored and the
            standard value will apply.
   
            ALCATEL NOTE:
                ACCESS:   NA                  USAGE:    OPT
                PERSIST:  YES                 INSRVMOD: YES
                RANGE:    0..255              DEFVALUE: 255
                UNITS:    dBm / 10            SPARSE:   NA
                DESCR:    NA
           "
   ::= {gxdslLineSpectrumProfileAdsl2PlusEntry 2}
   
   gadsl2PlusMaxAggregatePowerLevelUpstream          OBJECT-TYPE
           SYNTAX          INTEGER
           ACCESS          read-write
           STATUS          mandatory
           DESCRIPTION     
           "This parameter indicates the maximum power allowed on the line for the 
            upstream direction. If the necessary power level exceeds the level 
            given by this parameter the ONT XDSL Line will re-initialize. 
            The aggregate power has a range of 0 dBm to +25.5 dBm in steps of 0.1
            dB.
            It is represented as 1/10 * gadsl2PlusMaxAggregatePowerLevelUpstream.
            In case the corresponding DSL standard imposes a more stringent value
            for this parameter, the configured value will be ignored and the
            standard value will apply.
   
            ALCATEL NOTE:
                ACCESS:   NA                  USAGE:    OPT
                PERSIST:  YES                 INSRVMOD: YES
                RANGE:    0..255              DEFVALUE: 255
                UNITS:    dBm / 10            SPARSE:   NA
                DESCR:    NA
           "
   ::= {gxdslLineSpectrumProfileAdsl2PlusEntry 3}
   
   gadsl2PlusMaxPsdLevelDownstream         OBJECT-TYPE
           SYNTAX          INTEGER
           ACCESS          read-write
           STATUS          mandatory
           DESCRIPTION     
           "This object gives the power spectral density allowed on the line
            for the downstream band. A lower value results in reduction of 
            power consumption, by paying the price of having a lower capacity. 
            It is expressed in dBm/Hz.
            When a PSD shape is configured, this parameter can be used to specify
            an additional constraint on the max PSD level.
            The PSD has a range of -60 dBm/Hz to -40 dBm/Hz in steps of 0.1 dB.
            It is represented as 1/10* gadsl2PlusMaxPsdLevelDownstream.
            In case the corresponding DSL standard imposes a more stringent value
            for this parameter, the configured value will be ignored and the
            standard value will apply.
   
            ALCATEL NOTE:
                ACCESS:   NA                  USAGE:    OPT
                PERSIST:  YES                 INSRVMOD: YES
                RANGE:    -600..-400          DEFVALUE: -400
                UNITS:    dBm/Hz * 1/10       SPARSE:   NA
                DESCR:    NA
           "
   ::= {gxdslLineSpectrumProfileAdsl2PlusEntry 4}
   
   gadsl2PlusMaxPsdLevelUpstream           OBJECT-TYPE
           SYNTAX          INTEGER
           ACCESS          read-write
           STATUS          mandatory
           DESCRIPTION     
           "This object gives the power spectral density allowed on the line
            for the upstream band. A lower value results in reduction of 
            power consumption, by paying the price of having a lower capacity. 
            It is expressed in dBm/Hz.
            When a PSD shape is configured, this parameter can be used to specify
            an additional constraint on the max PSD level.
            The PSD has a range of -60 dBm/Hz to -38 dBm/Hz in steps of 0.1 dB.
            It is represented as 1/10* gadsl2PlusMaxPsdLevelUpstream.
            In case the corresponding DSL standard imposes a more stringent value
            for this parameter, the configured value will be ignored and the
            standard value will apply.
   
            ALCATEL NOTE:
                ACCESS:   NA                  USAGE:    OPT
                PERSIST:  YES                 INSRVMOD: YES
                RANGE:    -600..-380          DEFVALUE: -380
                UNITS:    dBm/Hz * 1/10       SPARSE:   NA
                DESCR:    NA
           "
   ::= {gxdslLineSpectrumProfileAdsl2PlusEntry 5}
   
-- adsl2PlusPsdShapeDownstream            OBJECT-TYPE
--         SYNTAX          GAdsl2PlusPsdDownstreamType
--         ACCESS          read-write
--         STATUS          mandatory
--         DESCRIPTION     
--         "This parameter defines the PSD Shape that must be applied for ADSL2+
--          in the downstream direction.
--          adsl2PlusCustomPsdDownstream: a custom PSD Shape is defined in
--          adsl2PlusCustomPsdShapeDownstream.
--          adsl2PlusStdPsdDownstream: the standard PSD mask for central office
--          deployment is applied.
--          adsl2PlusCa100PsdDownstream, adsl2PlusCa110PsdDownstream,... 
--          adsl2PlusCa280PsdDownstream: selection of PSD masks for cabinet
--          deployment whith cut-off frequencies at carrier 100, 110, ... 280
--          respectively.
-- 
--          ALCATEL NOTE:
--              ACCESS:   NA                  USAGE:    OPT
--              PERSIST:  YES                 INSRVMOD: YES
--              RANGE:    NA                  DEFVALUE: adsl2PlusStdPsdDownstream
--              UNITS:    NA                  SPARSE:   NA
--              DESCR:    NA
--         "
-- ::= {xdslLineSpectrumProfileAdsl2PlusEntry 6}
-- 
-- adsl2PlusCustomPsdShapeDownstream      OBJECT-TYPE
--         SYNTAX          GCustomPsdShapeType 
--         ACCESS          read-write
--         STATUS          mandatory
--         DESCRIPTION     
--         "This object specifies PSD points of a custom ADSL+ PSD Shape for
--          the downstream direction in case adsl2PlusPsdShapeDownstream =
--          adsl2PlusCustomPsdDownstream and it will be ignored otherwise.
--          A number of 2 to 20 PSD points can be specified.
--          The successive PSD points must have increasing (>/=) frequencies.
--          It is allowed that for two successive PSD points, different PSD
--          levels are defined at a same frequency (brickwall).
--          The custom PSD Shape is coded as a variable length octet string
--          defined as follows:
--          OCTET 0: reserved, fixed value 0x00 when PSD points specified
--          OCTETS 1..2: INTEGER (0..2208), frequency of the first PSD point
--          expressed in kHz. The value is defined as MSB-LSB (big-endian).
--          OCTET 3: INTEGER (0..255), -2*PSD level (in dBm/Hz) of the first
--          PSD point.
--          OCTETS 4..6: define the frequency and PSD level of PSD point 2.
--          ...        up to
--          OCTETS 3*N-2..3*N: define the frequency and PSD level of the last PSD
--          point N with N<=20.
-- 
--          ALCATEL NOTE:
--              ACCESS:   NA                  USAGE:    OPT
--              PERSIST:  YES                 INSRVMOD: YES
--              RANGE:    0..60               DEFVALUE: ''H
--              UNITS:    OCTETS              SPARSE:   NA
--              DESCR:    NA
--         "
-- ::= {xdslLineSpectrumProfileAdsl2PlusEntry 7}
-- 
-- adsl2PlusPsdShapeUpstream              OBJECT-TYPE
--         SYNTAX          GAdsl2PlusPsdUpstreamType
--         ACCESS          read-write
--         STATUS          mandatory
--         DESCRIPTION     
--         "This parameter defines the PSD Shape that must be applied for ADSL+
--          in the upstream direction.
--          adsl2PlusCustomPsdUpstream: a custom PSD Shape is defined in
--          adsl2PlusCustomPsdShapeUpstream.
--          adsl2PlusStdPsdUpstream: the standard PSD shape is applied.
-- 
--          ALCATEL NOTE:
--              ACCESS:   NA                  USAGE:    OPT
--              PERSIST:  YES                 INSRVMOD: YES
--              RANGE:    adsl2PlusStdPsdUpstream
--              DEFVALUE: adsl2PlusStdPsdUpstream
--              UNITS:    NA                  SPARSE:   NA
--              DESCR:    The object is supported to avoid future database 
--                        migration but should not be set.
--                        Set requests will be rejected (badvalue) if the value
--                        differs from the default value.
--         "
-- ::= {xdslLineSpectrumProfileAdsl2PlusEntry 8}
-- 
-- adsl2PlusCustomPsdShapeUpstream        OBJECT-TYPE
--         SYNTAX          GCustomPsdShapeType 
--         ACCESS          read-write
--         STATUS          mandatory
--         DESCRIPTION     
--         "This object specifies PSD points of a custom ADSL+ PSD Shape for
--          the upstream direction in case adsl2PlusPsdShapeUpstream =
--          adsl2PlusCustomPsdUpstream and it will be ignored otherwise.
--          A number of 2 to 20 points can be specified.
--          The successive PSD points must have increasing (>/=) frequencies.
--          It is allowed that for two successive PSD points, different PSD
--          levels are defined at a same frequency (brickwall).
--          The custom PSD Shape is coded as a variable length octet string
--          defined as follows:
--          OCTET 0: reserved, fixed value 0x00 when PSD points specified 
--          OCTETS 1..2: INTEGER (0..2208), frequency of the first PSD point
--          expressed in kHz. The value is defined as MSB-LSB (big-endian).
--          OCTET 3: INTEGER (0..255), represents -2*PSD level (in dBm/Hz)
--          of the first PSD point.
--          OCTETS 4..6:  define the frequency and PSD level of PSD point 2.
--          ...        up to
--          OCTETS 3*N-2..3*N: define the frequency and PSD level of the last PSD
--          point N with N<=20.
-- 
--          ALCATEL NOTE:
--              ACCESS:   NA                  USAGE:    OPT
--              PERSIST:  YES                 INSRVMOD: YES
--              RANGE:    0                   DEFVALUE: ''H
--              UNITS:    OCTETS              SPARSE:   NA
--              DESCR:    The object is supported to avoid future database 
--                        migration but should not be set.
--                        Set requests will be rejected (badvalue) if the value
--                        differs from the default value.
--         "
-- ::= {xdslLineSpectrumProfileAdsl2PlusEntry 9}
-- 
-- adsl2PlusPboModeUpstream               OBJECT-TYPE
--         SYNTAX          GPboModeType
--         ACCESS          read-write
--         STATUS          mandatory
--         DESCRIPTION     
--         "Identifies the upstream PSD power backoff mode.
--          pboModeOff: upstream power backoff is OFF, no power cutback is applied
--          by the receiver.
--          pboModeOn: upstream power backoff is ON, upstream power cutback is
--          requested if the RX aggregate power exceeds the max RX aggregate power
--          (adsl2PlusMaxRxAggregatePowerUpstream).
-- 
--          ALCATEL NOTE:
--              ACCESS:   NA                  USAGE:    OPT
--              PERSIST:  YES                 INSRVMOD: YES
--              RANGE:    NA                  DEFVALUE: pboModeOff
--              UNITS:    NA                  SPARSE:   NA
--              DESCR:    NA
--         "
-- ::= {xdslLineSpectrumProfileAdsl2PlusEntry 10}
-- 
-- adsl2PlusMaxRxAggregatePowerLevelUpstream       OBJECT-TYPE
--         SYNTAX          INTEGER
--         ACCESS          read-write
--         STATUS          mandatory
--         DESCRIPTION     
--         "This parameter indicates the maximum receive power allowed on the line
--          for the upstream direction.
--          The aggregate power has a range of -25.5 dBm to +25.5 dBm in steps of
--          0.1 dB.
--          It is represented as 1/10 * adsl2PlusMaxRxAggregatePowerUpstream.
-- 
--          ALCATEL NOTE:
--              ACCESS:   NA                  USAGE:    OPT
--              PERSIST:  YES                 INSRVMOD: YES
--              RANGE:    -255..255           DEFVALUE: 255
--              UNITS:    dBm / 10            SPARSE:   NA
--              DESCR:    NA
--         "
-- ::= {xdslLineSpectrumProfileAdsl2PlusEntry 11}
-- 
 
gxdslLineSpectrumProfileVdslTable       OBJECT-TYPE
        SYNTAX          SEQUENCE OF GxdslLineSpectrumProfileVdslEntry
        ACCESS          not-accessible
        STATUS          mandatory
        DESCRIPTION     
        "This table is part of the line profile. It contains the line
         related parameters of the modem configuration that apply to the VDSL
         operational modes (VDSL1 and VDSL2). 
         It contains two types of parameters:
         - The common VDSL parameters that apply to VDSL1 and VDSL2 operational
           modes and have the same value. These parameters are ignored in case
           an ADSL operational mode is used.
         - The VDSL1 specific parameters that contain values only applicable to
           VDSL1 operational modes. These parameters are ignored in case
           another operational mode is used.
         The VDSL2 operational modes also use specific parameters, these are
         included in the xdslLineSpectrumProfileVdsl2Table.

         ALCATEL NOTE:
             TABLESIZE: 256                    
             DESCR:     NA                  
        "
::= {gxdslLineSpectrumProfile 5}

gxdslLineSpectrumProfileVdslEntry       OBJECT-TYPE
        SYNTAX          GxdslLineSpectrumProfileVdslEntry
        ACCESS          not-accessible
        STATUS          mandatory
        DESCRIPTION     
        "Each entry consists of a list of line related parameters that serve 
         to configure an XDSL modem in case the VDSL mode of operation is
         used (VDSL1 or VDSL2).

         Row creation : When an entry is created in the 
                        xdslLineSpectrumProfileTable, an entry with the same 
                        xdslLineSpectrumIndex is created in this table.
         Row deletion : When an entry is deleted from the
                        xdslLineSpectrumProfileTable, the entry with the same
                        xdslLineSpectrumIndex is deleted from this table. 
        "
        INDEX          {gxdslLineSpectrumProfileIndex}
::= {gxdslLineSpectrumProfileVdslTable 1}

GxdslLineSpectrumProfileVdslEntry ::=
        SEQUENCE {
            gvdslModemFeatures                         INTEGER,
            gvdslBandPlan                              GVdslBandPlanType,
            gvdslBandPlanCFx                           GFrequencyType,
            gvdslCustomBandPlan                        OCTET STRING,
            gvdslOptBandUsage                          GOptBandUsageType,
            gvdslAdslBandUsage                         INTEGER,
            gvdslMaxAggregatePowerLevelDownstream      INTEGER,
            gvdslMaxAggregatePowerLevelUpstream        INTEGER,
            gvdslPsdShapeDownstream                    GVdslPsdDownstreamType,
            gvdslCustomPsdShapeDownstream              GCustomPsdShapeType,
            gvdslPsdShapeUpstream                      GVdslPsdUpstreamType,
            gvdslCustomPsdShapeUpstream                GCustomPsdShapeType,
            gvdslPboModeUpstream                       GPboModeType,
            gvdslRxPsdShapeUpstream                    GVdslRxPsdUpstreamType,
            gvdslCustomRxPsdShapeUpstream              GCustomPsdShapeType,
            gvdslOptBandEndFreq                        INTEGER,
            gvdslAdslBandEndFreq                       INTEGER,
            gvdslGhsTonesTxPowerControl                INTEGER,
            gvdslGhsTonesTxPowerControlA43             INTEGER,
            gvdslGhsTonesTxPowerControlB43             INTEGER,
            gvdslGhsTonesTxPowerControlA43c            INTEGER,
            gvdslGhsTonesTxPowerControlV43             INTEGER,
            gvdslGhsTonesTxPowerLevelA43               INTEGER,
            gvdslGhsTonesTxPowerLevelB43               INTEGER,
            gvdslGhsTonesTxPowerLevelA43c              INTEGER,
            gvdslGhsTonesTxPowerLevelV43               INTEGER,
            gvdslMaxBandNumber                         INTEGER,
            gvdslMaxFrequency                          GFrequencyType,
            gvdslMaxPsdLevelDownstream                 INTEGER,
            gvdslMaxPsdLevelUpstream                   INTEGER,
            gvdslPsdPboParamAUpstream                  GPerBandABParamType,
            gvdslPsdPboParamBUpstream                  GPerBandABParamType
        }

gvdslModemFeatures       OBJECT-TYPE
        SYNTAX          INTEGER
        ACCESS          read-write
        STATUS          mandatory 
        DESCRIPTION 
        "VDSL1 specific, this object allows to enable/disable specific features
         of the modem.
         It is a bitmap represented as a sum and allows multiple features to be
         configured simultaneously. Currently only bit 0 is used, the other
         bits are reserved for future use.
         Bitmap values:
          1   Strict compliancy, the modem should turn off all features not
              strictly compliant with the standards.
              The modem is allowed to use proprietary features when
              bit 0 is set to 0.

         ALCATEL NOTE:
             ACCESS:   NA                  USAGE:    OPT
             PERSIST:  YES                 INSRVMOD: YES
             RANGE:    0..1                DEFVALUE: 1
             UNITS:    NA                  SPARSE:   NA
             DESCR:    NA
        
         FGU4.4:  THIS OBJECT IS NOT SUPPORTED "
::= {gxdslLineSpectrumProfileVdslEntry 1}
       
gvdslBandPlan            OBJECT-TYPE
        SYNTAX          GVdslBandPlanType
        ACCESS          read-write
        STATUS          mandatory
        DESCRIPTION     
        "Common to VDSL1/VDSL2, this object specifies the VDSL band plan:
         bandPlanCustom: a custom bandplan is defined in vdslCustomBandPlan.
         bandPlanA4:      4 bands 998 band plan (Bandplan-A in ITU-T G.993.1)
         bandPlanA3:      3 bands 998 band plan
         bandPlanA2:      2 bands 998 band plan
         bandPlanB4:      4 bands 997 band plan (Bandplan-B in ITU-T G.993.1)
         bandPlanB3:      3 bands 997 band plan
         bandPlanB2:      2 bands 997 band plan
         bandPlanC4:      4 bands Fx band plan (Bandplan-C in ITU-T G.993.1)
                           This plan uses a variable frequency Fx specified
                           in vdslBandPlanCFx.
         bandPlanC3:      3 bands Fx band plan
         bandPlanC2:      2 bands Fx band plan
         bandPlanChinaA3:  3 bands China band plan 1. 
         bandPlanChinaA2:  2 bands China band plan 1. 
         bandPlanChinaB3:  3 bands China band plan 2. 
         bandPlanChinaB2:  2 bands China band plan 2.
bandPlanAU2ext:    
         band plan 998 with US2 band extended to 30 MHz.         
bandPlanAnnexA998:    ITU-T G993.2 VDSL2 Annex A (998 extended) band plan 
         bandPlanAnnexB997e:   ITU-T G993.2 VDSL2 Annex B band plan type 997E
         bandPlanAnnexB998e:   ITU-T G993.2 VDSL2 Annex B band plan type 998E 
         bandPlanAnnexB998ade: ITU-T G993.2 VDSL2 Annex B band plan type 998ADE 
         bandPlanAnnexBhpe:    ITU-T G993.2 VDSL2 Annex B band plan type HPE 
         bandPlanAnnexC:       ITU-T G993.2 VDSL2 Annex C band plan 
	 bandPlanAnnexB998ade17ds30us35:  G993.2 VDSL2 Annex B band plan type 998ADE17	
         extended with DS band to 30 MHz and US band to 35 MHz. 
         bandPlanAnnexB998e17ds30us35:    G993.2 VDSL2 Annex B band plan type 998E17	
         extended with DS band to 30 MHz and US band to 35 MHz. 
         bandPlanAnnexB998ade17ds35:  G993.2 VDSL2 Annex B band plan type 998ADE17	
         extended with DS band to 35 MHz. 
         bandPlanAnnexB998e17ds35:    G993.2 VDSL2 Annex B band plan type 998E17	
         extended with DS band to 35 MHz.

         ALCATEL NOTE:
             ACCESS:   NA                  USAGE:    OPT
             PERSIST:  YES                 INSRVMOD: YES
             RANGE:    bandplanA4, bandplanA3, bandplanA2, 
                       bandplanB4, bandplanB3, bandplanB2,
                       bandPlanAnnexA998, bandPlanAnnexB997e,
                       bandPlanAnnexB998e, bandPlanAnnexB998ade,
                       bandPlanAnnexBhpe, bandPlanAnnexC,
                       bandPlanAnnexB998ade17ds30us35,
                       bandPlanAnnexB998e17ds30us35,
                       bandPlanAnnexB998ade17ds35, bandPlanAnnexB998e17ds35
             DEFVALUE: bandPlanAnnexA998
             UNITS:    NA                  SPARSE:   NA
             DESCR:    NA 

	FGU4.4 - the only SUPPORTED values are bandPlanAnnexA998 and bandPlanAnnexB998ade
	FGU4.4.10 - must also SUPPORT bandPlanAnnexB998e
        "
::= {gxdslLineSpectrumProfileVdslEntry 2}

gvdslBandPlanCFx         OBJECT-TYPE
        SYNTAX          GFrequencyType
        ACCESS          read-write
        STATUS          mandatory
        DESCRIPTION     
        "Common to VDSL1/VDSL2, this object specifies Fx in case of band
         plan C, ignored otherwise.

         ALCATEL NOTE:
             ACCESS:   NA                  USAGE:    OPT
             PERSIST:  YES                 INSRVMOD: YES
             RANGE:    0                   DEFVALUE: 0
             UNITS:    kHz                 SPARSE:   NA
             DESCR:    The object is supported to avoid future database 
                       migration but should not be set.
                       Set requests will be rejected (badvalue) if the value
                       differs from the default value.
        
         FGU4.4:  THIS OBJECT IS NOT SUPPORTED "
::= {gxdslLineSpectrumProfileVdslEntry 3}

gvdslCustomBandPlan      OBJECT-TYPE
        SYNTAX          OCTET STRING (SIZE (0..40))
        ACCESS          read-write
        STATUS          mandatory
        DESCRIPTION     
        "Common to VDSL1/VDSL2, this object defines a custom band plan when
         vdslBandPlan = bandPlanCustom, ignored otherwise.
         Up to 8 bands (upstream + downstream) are configurable.
         The custom band plan is coded as a variable length octet string
         defined as follows:
         OCTET 0..4 define the characteristics of BAND #1:
         OCTET 0-1: INTEGER (0..30000), start frequency of band 1 expressed
                    in kHz. The value is defined as MSB-LSB (big-endian).
         OCTET 2-3: INTEGER (0..30000), stop frequency of band 1 expressed
                    in kHz. The value is defined as MSB-LSB (big-endian).
         OCTET 4:    indicates the direction of the band (0x00= downstream,
                    0x01 = upstream).
         OCTET 5-9: Idem, define the characteristics of band #2.
         ...        up to
         OCTETS (N-1)*5..(N*5)-1: define the characteristics of the last
                    BAND #N with N<=8.

         ALCATEL NOTE:
             ACCESS:   NA                  USAGE:    OPT
             PERSIST:  YES                 INSRVMOD: YES
             RANGE:    0                   DEFVALUE: ''H
             UNITS:    octets              SPARSE:   NA
             DESCR:    The object is supported to avoid future database 
                       migration but should not be set.
                       Set requests will be rejected (badvalue) if the value
                       differs from the default value.
        
         FGU4.4:  THIS OBJECT IS NOT SUPPORTED "         
::= {gxdslLineSpectrumProfileVdslEntry 4}

gvdslOptBandUsage        OBJECT-TYPE
        SYNTAX          GOptBandUsageType
        ACCESS          read-write
        STATUS          mandatory
        DESCRIPTION     
        "Common to VDSL1/VDSL2, this object indicates if the XDSL is allowed
         to use the optional band (25 kHz..x kHz) or not and defines its
         direction in case allowed. The end frequency x is fixed to 138 kHz by
         default, or separately configurable by setting vdslOptBandEndFreq.
         The optional band usage is independent from the ADSL Band usage
         parameter.
         In case the ADSL band usage is not allowed and the optional band usage 
         is allowed, the modem is allowed to use the optional band.
         optBandOff:        usage of optional band is not allowed.
         optBandUpstream:   optional band can be used for upstream.
         optBandDownstream: optional band can be used for downstream.

         ALCATEL NOTE:
             ACCESS:   NA                  USAGE:    OPT
             PERSIST:  YES                 INSRVMOD: YES
             RANGE:    NA                  DEFVALUE: optBandOff
             UNITS:    NA                  SPARSE:   NA
             DESCR:    NA
        
         FGU4.4:  THIS OBJECT IS NOT SUPPORTED "
::= {gxdslLineSpectrumProfileVdslEntry 5}

gvdslAdslBandUsage       OBJECT-TYPE
        SYNTAX          INTEGER
        ACCESS          read-write
        STATUS          mandatory
        DESCRIPTION     
        "Common to VDSL1/VDSL2, this object Specifies whether the XDSL is
         allowed or not to use the given ADSL spectrum.
         0: usage of ADSL spectrum is allowed.
         1: usage of the ADSL (25kHz - 1.1Mhz) spectrum is not allowed.
         2: usage of the ADSL2+ (25kHz - 2.2Mhz)spectrum is not allowed.
         3: usage of the ADSL spectrum is not allowed until the ADSL
         frequency specfied in vdslAdslBandEndFreq. ((option NOT SUPPORTED for FGU4.4).
         4: usage of ADSL (25kHz - 640kHz) spectrum is not allowed
         For VDSL, this controls the use of the ADSL spectrum portion within 
         the VDSL frequency plan defined in vdslBandPlan and vdslOptBandUsage.

         ALCATEL NOTE:
             ACCESS:   NA                  USAGE:    OPT
             PERSIST:  YES                 INSRVMOD: YES
             RANGE:    0..4                DEFVALUE: 1
             UNITS:    NA                  SPARSE:   NA
             DESCR:    NA
         "
::= {gxdslLineSpectrumProfileVdslEntry 6}

gvdslMaxAggregatePowerLevelDownstream   OBJECT-TYPE
        SYNTAX          INTEGER
        ACCESS          read-write
        STATUS          mandatory
        DESCRIPTION     
        "VDSL1 specific, this object indicates the maximum power allowed on 
         the line for the downstream direction. If the necessary power level 
         exceeds the level given by this parameter the modem will re-
         initialize.  
         The aggregate power has a range of -31 dBm to +25.5 dBm in steps of
         0.1 dB.
         It is represented as 1/10 * vdslMaxAggregatePowerLevelDownstream.

         ALCATEL NOTE:
             ACCESS:   NA                  USAGE:    OPT
             PERSIST:  YES                 INSRVMOD: YES
             RANGE:    -310..255           DEFVALUE: 255
             UNITS:    dBm / 10            SPARSE:   NA
             DESCR:    NA
        
         FGU4.4:  THIS OBJECT IS NOT SUPPORTED "
::= {gxdslLineSpectrumProfileVdslEntry 7}

gvdslMaxAggregatePowerLevelUpstream     OBJECT-TYPE
        SYNTAX          INTEGER
        ACCESS          read-write
        STATUS          mandatory
        DESCRIPTION     
        "VDSL1 specific, this object indicates the maximum power allowed on
         the line for the upstream direction. If the necessary power level
         exceeds the level given by this parameter the modem will re-
         initialize. 
         The aggregate power has a range of -31 dBm to +25.5 dBm in steps of 
         0.1 dB. 
         It is represented as 1/10 * vdslMaxAggregatePowerLevelUpstream .

         ALCATEL NOTE:
             ACCESS:   NA                  USAGE:    OPT
             PERSIST:  YES                 INSRVMOD: YES
             RANGE:    -310..255           DEFVALUE: 255
             UNITS:    dBm / 10            SPARSE:   NA
             DESCR:    NA
        
         FGU4.4:  THIS OBJECT IS NOT SUPPORTED "
::= {gxdslLineSpectrumProfileVdslEntry 8}

gvdslPsdShapeDownstream  OBJECT-TYPE
        SYNTAX          GVdslPsdDownstreamType
        ACCESS          read-write
        STATUS          mandatory
        DESCRIPTION     
        "VDSL1 specific, this object defines the PSD Shape that must be applied
         for VDSL in the downstream direction.
         vdslCustomPsdDownstream: a custom PSD Shape is defined in
         vdslCustomPsdShapeDownstream.
         A predefined PSD (ANSI or ETSI)can be selected from the following
         list:
           vdslAnsiFttexM1PsdDownstream
           vdslAnsiFttexM2PsdDownstream
           vdslAnsiFttcabM1PsdDownstream
           vdslAnsiFttcabM2PsdDownstream
           vdslEtsiPexP1M1PsdDownstream
           vdslEtsiPexP1M2PsdDownstream
           vdslEtsiPexP2M1PsdDownstream
           vdslEtsiPexP2M2PsdDownstream
           vdslEtsiPcabM1PsdDownstream
           vdslEtsiPcabM2PsdDownstream
           vdslAnsiFttCabM1AdslPsdDownstream
           vdslAnsiFttCabM2AdslPsdDownstream
           vdslAnsiFttCabM1Adsl2PlusPsdDownstream
           vdslAnsiFttCabM2Adsl2PlusPsdDownstream
           vdslEtsiPcabXM1AdslPsdDownstream
           vdslEtsiPcabXM2AdslPsdDownstream
           vdslEtsiPcabM1Adsl2PlusPsdDownstream
           vdslEtsiPcabM2Adsl2PlusPsdDownstream
           vdslEtsiPexM2AdslSample1PsdDownstream
           vdslEtsiPexM2AdslSample2PsdDownstream
           vdslEtsiPexM2AdslSample3PsdDownstream
           vdslEtsiPexM2AdslSample4PsdDownstream

         ALCATEL NOTE:
             ACCESS:   NA                  USAGE:    OPT
             PERSIST:  YES                 INSRVMOD: YES
             RANGE:    NA           
             DEFVALUE: vdslEtsiPcabM1PsdDownstream
             UNITS:    NA                  SPARSE:   NA
             DESCR:    NA 
        
         FGU4.4:  THIS OBJECT IS NOT SUPPORTED "
::= {gxdslLineSpectrumProfileVdslEntry 9}

gvdslCustomPsdShapeDownstream           OBJECT-TYPE
        SYNTAX          GCustomPsdShapeType 
        ACCESS          read-write
        STATUS          mandatory
        DESCRIPTION     
        "VDSL1 specific, this object specifies PSD points of a custom VDSL PSD
         Shape for the downstream direction in case vdslPsdShapeDownstream =
         vdslCustomPsdDownstream and it will be ignored otherwise.
         A number of 2 to 32 PSD points can be specified.
         The successive PSD points must have increasing (>/=) frequencies.
         It is allowed that for two successive PSD points, different PSD
         levels are defined at a same frequency (brickwall).
         The custom PSD Shape is coded as a variable length octet string
         defined as follows:
         OCTET 0: defines the characteristics (type and scale) of the PSD
         shape.
         OCTET 0- bit 0..1: defines the frequency scale to be used for the
         interpolation of the PSD Shape data (00= linear frequency scale,
         01 = logarithmic frequency scale).
         OCTET 0- bit 2..3: defines the type of the PSD shape (00= PSD mask,
         01= PSD template).
         Octet 1..3: defines PSD point #1
         OCTETS 1..2: INTEGER (0..30000), frequency of PSD point #1,
         expressed in kHz. The value is defined as MSB-LSB (big-endian).
         OCTET 3: INTEGER (0..255), -2*PSD level (in dBm/Hz) of
         PSD point#1.
         OCTETS 4..6: define the frequency and PSD level of PSD point #2.
         ...        up to
         OCTETS 3*N-2..3*N: define the frequency and PSD level of the last PSD
         point #N with N<=32.

         ALCATEL NOTE:
             ACCESS:   NA                  USAGE:    OPT
             PERSIST:  YES                 INSRVMOD: YES
             RANGE:    0..97               DEFVALUE: ''H
             UNITS:    NA                  SPARSE:   NA
             DESCR:    NA
        
         FGU4.4:  THIS OBJECT IS NOT SUPPORTED "
::= {gxdslLineSpectrumProfileVdslEntry 10}

gvdslPsdShapeUpstream    OBJECT-TYPE
        SYNTAX          GVdslPsdUpstreamType
        ACCESS          read-write
        STATUS          mandatory
        DESCRIPTION     
        "VDSL1 specific, this object defines the PSD Shape that must be applied
         for VDSL in the upstream direction.
         vdslCustomPsdUpstream: a custom PSD Shape is defined in
         vdslCustomPsdShapeUpstream.
         A predefined PSD (ANSI or ETSI)can be selected from the following 
         list:
           vdslAnsiFttexM1PsdUpstream
           vdslAnsiFttexM2PsdUpstream
           vdslAnsiFttcabM1PsdUpstream
           vdslAnsiFttcabM2PsdUpstream
           vdslEtsiPM1PsdUpstream
           vdslEtsiPM2PsdUpstream

         ALCATEL NOTE:
             ACCESS:   NA                  USAGE:    OPT
             PERSIST:  YES                 INSRVMOD: YES
             RANGE:    all, except vdslCustomPsdUpstream                  
             DEFVALUE: vdslEtsiPM1PsdUpstream
             UNITS:    NA                  SPARSE:   NA
             DESCR:    NA 
        
         FGU4.4:  THIS OBJECT IS NOT SUPPORTED "
::= {gxdslLineSpectrumProfileVdslEntry 11}

gvdslCustomPsdShapeUpstream             OBJECT-TYPE
        SYNTAX         GCustomPsdShapeType 
        ACCESS          read-write
        STATUS          mandatory
        DESCRIPTION     
        "VDSL1 specific, this object specifies PSD points of a custom VDSL PSD
         Shape for the upstream direction in case vdslPsdShapeUpstream =
         vdslCustomPsdUpstream and it will be ignored otherwise.
         A number of 2 to 20 points can be specified.
         The successive PSD points must have increasing (>/=) frequencies.
         It is allowed that for two successive PSD points, different PSD
         levels are defined at a same frequency (brickwall).
         The custom PSD Shape is coded as a variable length octet string
         defined as follows:
         OCTET 0: defines the characteristics (type and scale) of the PSD 
         shape.
         OCTET 0- bit 0..1: defines the frequency scale to be used for the
         interpolation of the PSD Shape data (00= linear frequency scale,
         01 = logarithmic frequency scale).
         OCTET 0- bit 2..3: defines the type of the PSD shape (00= PSD mask,
         01= PSD template).
         Octet 1..3: defines PSD point #1
         OCTETS 1..2: INTEGER (0..30000), frequency of PSD point #1,
         expressed in kHz. The value is defined as MSB-LSB (big-endian).
         OCTET 3: INTEGER (0..255), -2*PSD level (in dBm/Hz) of
         PSD point#1.
         OCTETS 4..6: define the frequency and PSD level of PSD point #2.
         ...        up to
         OCTETS 3*N-2..3*N: define the frequency and PSD level of the last PSD
         point #N with N<=20.

         ALCATEL NOTE:
             ACCESS:   NA                  USAGE:    OPT
             PERSIST:  YES                 INSRVMOD: YES
             RANGE:    0                   DEFVALUE: ''H
             UNITS:    NA                  SPARSE:   NA
             DESCR:    The object is supported to avoid future database 
                       migration but should not be set.
                       Set requests will be rejected (badvalue) if the value
                       differs from the default value.
        
         FGU4.4:  THIS OBJECT IS NOT SUPPORTED "
::= {gxdslLineSpectrumProfileVdslEntry 12}

gvdslPboModeUpstream     OBJECT-TYPE
        SYNTAX          GPboModeType
        ACCESS          read-write
        STATUS          mandatory
        DESCRIPTION     
        "Common to VDSL1/VDSL2, this object identifies the upstream PSD power
         backoff mode.
         pboModeOff: upstream PSD power backoff is OFF i.e. the TX PSD is used.
         pboModeOn: upstream PSD power backoff is ON i.e. the PBO RX PSD
         Shape defined in vdslRxPsdShapeUpstream is used.

         ALCATEL NOTE:
             ACCESS:   NA                  USAGE:    OPT
             PERSIST:  YES                 INSRVMOD: YES
             RANGE:    NA                  DEFVALUE: pboModeOn
             UNITS:    NA                  SPARSE:   NA
             DESCR:    NA
        "
::= {gxdslLineSpectrumProfileVdslEntry 13}

gvdslRxPsdShapeUpstream  OBJECT-TYPE
        SYNTAX          GVdslRxPsdUpstreamType
        ACCESS          read-write
        STATUS          mandatory
        DESCRIPTION     
        "VDSL1 specific, this object defines the reference Rx PSD Shape to be
        used for upstream power backoff.
        vdslCustomRxPsdUpstream: a custom reference Rx PSD Shape is defined
        in vdslCustomRxPsdShapeUpstream.
        A predefined standard or custom PSD can be selected from the following
        list:
          vdslAnsiARxPsdUpstream
          vdslAnsiFRxPsdUpstream
          vdslAnsiCustomExRxPsdUpstream
          vdslAnsiCustomCabRxPsdUpstream
          vdslEtsiARxPsdUpstream
          vdslEtsiBRxPsdUpstream
          vdslEtsiCRxPsdUpstream
          vdslEtsiDRxPsdUpstream
          vdslEtsiERxPsdUpstream
          vdslEtsiFRxPsdUpstream
          vdslEtsiCustomExRxPsdUpstream
          vdslEtsiCustomCabRxPsdUpstream
          vdslABParamRxPsdUpstream

         ALCATEL NOTE:
             ACCESS:   NA                  USAGE:    OPT
             PERSIST:  YES                 INSRVMOD: YES
             RANGE:    NA                  DEFVALUE: vdslEtsiARxPsdUpstream
             UNITS:    NA                  SPARSE:   NA
             DESCR:    NA 
        
         FGU4.4:  THIS OBJECT IS NOT SUPPORTED "
::= {gxdslLineSpectrumProfileVdslEntry 14}

gvdslCustomRxPsdShapeUpstream           OBJECT-TYPE
        SYNTAX          GCustomPsdShapeType 
        ACCESS          read-write
        STATUS          mandatory
        DESCRIPTION     
        "VDSL1 specific, this object specifies PSD points of a custom reference
         receive VDSL PSD Shape for upstream power backoff in case
         vdslRxPsdShapeUpstream = vdslCustomRxPsdUpstream  and it will be 
         ignored otherwise. A number of 2 to 20 PSD points can be specified.
         The successive PSD points must have increasing (>/=) frequencies.
         It is allowed that for two successive PSD points, different PSD
         levels are defined at a same frequency (brickwall).
         The custom PSD Shape is coded as a variable length octet string
         defined as follows:
         OCTET 0: defines the characteristics (type and scale) of the PSD 
         shape.
         OCTET 0- bit 0..1: defines the frequency scale to be used for the
         interpolation of the PSD Shape data (00= linear frequency scale,
         01 = logarithmic frequency scale).
         OCTET 0- bit 2..3: defines the type of the PSD shape (00= PSD mask,
         01= PSD template).
         Octet 1..3: defines PSD point #1
         OCTETS 1..2: INTEGER (0..30000), frequency of PSD point #1,
         expressed in kHz. The value is defined as MSB-LSB (big-endian).
         OCTET 3: INTEGER (255..0), -2*PSD level (in dBm/Hz) of
         PSD point#1.
         OCTETS 4..6: define the frequency and PSD level of PSD point #2.
         ...        up to
         OCTETS 3*N-2..3*N: define the frequency and PSD level of the last PSD
         point #N with N<=20.

         ALCATEL NOTE:
             ACCESS:   NA                  USAGE:    OPT
             PERSIST:  YES                 INSRVMOD: YES
             RANGE:    0..61               DEFVALUE: ''H
             UNITS:    NA                  SPARSE:   NA
             DESCR:    NA
        
         FGU4.4:  THIS OBJECT IS NOT SUPPORTED "
::= {gxdslLineSpectrumProfileVdslEntry 15}

gvdslOptBandEndFreq      OBJECT-TYPE
        SYNTAX          INTEGER 
        ACCESS          read-write
        STATUS          mandatory
        DESCRIPTION     
        "Common to VDSL1/VDSL2, this object specifies the end frequency of the
         VDSL optional band in case the use of the optional band is allowed
         (vdslOptBandUsage <> optBandOff).
         The end frequency is configurable from 138 kHz to 276 kHz in steps of
         1 kHz.

         ALCATEL NOTE:
             ACCESS:   NA                  USAGE:    OPT
             PERSIST:  YES                 INSRVMOD: YES
             RANGE:    138..276            DEFVALUE: 138
             UNITS:    kHz                 SPARSE:   NA
             DESCR:    NA
        
         FGU4.4:  THIS OBJECT IS NOT SUPPORTED "
::= {gxdslLineSpectrumProfileVdslEntry 16}

gvdslAdslBandEndFreq     OBJECT-TYPE
        SYNTAX          INTEGER 
        ACCESS          read-write
        STATUS          mandatory
        DESCRIPTION 
        "Common to VDSL1/VDSL2, this object specifies the end frequency of the
         ADSL band in case the use of the ADSL band by VDSL is not allowed with
         (vdslAdslBandUsage = 3).
         The end frequency is configurable from 276 kHz to 2208 kHz in steps of
         1 kHz.

         ALCATEL NOTE:
             ACCESS:   NA                  USAGE:    OPT
             PERSIST:  YES                 INSRVMOD: YES
             RANGE:    276..2208           DEFVALUE: 1104
             UNITS:    kHz                 SPARSE:   NA
             DESCR:    NA
        
         FGU4.4:  THIS OBJECT IS NOT SUPPORTED "
::= {gxdslLineSpectrumProfileVdslEntry 17}

gvdslGhsTonesTxPowerControl             OBJECT-TYPE
        SYNTAX          INTEGER 
        ACCESS          read-write
        STATUS          mandatory
        DESCRIPTION     
        "Common to VDSL1/VDSL2, this object specifies how to control the Tx 
         power of the G.hs tones.
         0: default, the max power as per G994.1 standard definition applies.
         1: auto, the max Tx power level is derived from the
         vdslPsdShapeDownstream.
     2: per tone set. Instead of vdslGhsTonesTxPowerControl,
     use parameters vdslGhsTonesTxPowerControlA43,
     vdslGhsTonesTxPowerControlB43, vdslGhsTonesTxPowerControlA43c, 
     vdslGhsTonesTxPowerControlB43, vdslGhsTonesTxPowerControlA43c, 
     vdslGhsTonesTxPowerControlV43, vdslGhsTonesTxPowerLevelA43,
     vdslGhsTonesTxPowerLevelB43, vdslGhsTonesTxPowerLevelA43c,
     vdslGhsTonesTxPowerLevelV43

         ALCATEL NOTE:
             ACCESS:   NA                  USAGE:    OPT
             PERSIST:  YES                 INSRVMOD: YES
             RANGE:    0..2                DEFVALUE: 0
             UNITS:    NA                  SPARSE:   NA
             DESCR:    NA
    
         FGU4.4:  THIS OBJECT IS NOT SUPPORTED "
::= {gxdslLineSpectrumProfileVdslEntry 18}

gvdslGhsTonesTxPowerControlA43          OBJECT-TYPE
        SYNTAX          INTEGER 
        ACCESS          read-write
        STATUS          mandatory
        DESCRIPTION     
        "Common to VDSL1/VDSL2, this object specifies how to control the Tx 
         power of the G.hs tones for DS tones set A43.
         0: default, the max power as per G994.1 standard definition applies.
         1: auto, the max Tx power level is derived from the
           vdslPsdShapeDownstream.
         2: manual, the value set in vdslGhsTonesTxPowerLevelA43 applies.

         ALCATEL NOTE:
             ACCESS:   NA                  USAGE:    OPT
             PERSIST:  YES                 INSRVMOD: YES
             RANGE:    0..2                DEFVALUE: 0
             UNITS:    NA                  SPARSE:   NA
             DESCR:    NA
        
         FGU4.4:  THIS OBJECT IS NOT SUPPORTED "
::= {gxdslLineSpectrumProfileVdslEntry 19}

gvdslGhsTonesTxPowerControlB43          OBJECT-TYPE
        SYNTAX          INTEGER 
        ACCESS          read-write
        STATUS          mandatory
        DESCRIPTION     
        "Common to VDSL1/VDSL2, this object specifies how to control the Tx
         power of the G.hs tones for DS tones set B43.
         0: default, the max power as per G994.1 standard definition applies.
         1: auto, the max Tx power level is derived from the
            vdslPsdShapeDownstream.
         2: manual, the value set in vdslGhsTonesTxPowerLevelB43 applies.

         ALCATEL NOTE:
             ACCESS:   NA                  USAGE:    OPT
             PERSIST:  YES                 INSRVMOD: YES
             RANGE:    0..2                DEFVALUE: 0
             UNITS:    NA                  SPARSE:   NA
             DESCR:    NA
        
         FGU4.4:  THIS OBJECT IS NOT SUPPORTED "
::= {gxdslLineSpectrumProfileVdslEntry 20}

gvdslGhsTonesTxPowerControlA43c         OBJECT-TYPE
        SYNTAX          INTEGER 
        ACCESS          read-write
        STATUS          mandatory
        DESCRIPTION     
        "Common to VDSL1/VDSL2, this object specifies how to control the Tx
         power of the G.hs tones for DS tones set A43c.
         0: default, the max power as per G994.1 standard definition applies.
         1: auto, the max Tx power level is derived from the
          vdslPsdShapeDownstream.
         2: manual, the value set in vdslGhsTonesTxPowerLevelA43c applies.

         ALCATEL NOTE:
             ACCESS:   NA                  USAGE:    OPT
             PERSIST:  YES                 INSRVMOD: YES
             RANGE:    0..2                DEFVALUE: 0
             UNITS:    NA                  SPARSE:   NA
             DESCR:    NA
        
         FGU4.4:  THIS OBJECT IS NOT SUPPORTED "
::= {gxdslLineSpectrumProfileVdslEntry 21}

gvdslGhsTonesTxPowerControlV43          OBJECT-TYPE
        SYNTAX          INTEGER 
        ACCESS          read-write
        STATUS          mandatory
        DESCRIPTION     
        "Common to VDSL1/VDSL2, this object specifies how to control the Tx 
         power of the G.hs tones for DS tones set V43.
         0: default, the max power as per G994.1 standard definition applies.
         1: auto, the max Tx power level is derived from the
           vdslPsdShapeDownstream.
         2: manual, the value set in vdslGhsTonesTxPowerLevelV43 applies.

         ALCATEL NOTE:
             ACCESS:   NA                  USAGE:    OPT
             PERSIST:  YES                 INSRVMOD: YES
             RANGE:    0..2                DEFVALUE: 0
             UNITS:    NA                  SPARSE:   NA
             DESCR:    NA
        
         FGU4.4:  THIS OBJECT IS NOT SUPPORTED "
::= {gxdslLineSpectrumProfileVdslEntry 22}

gvdslGhsTonesTxPowerLevelA43            OBJECT-TYPE
        SYNTAX          INTEGER 
        ACCESS          read-write
        STATUS          mandatory
        DESCRIPTION     
        "Common to VDSL1/VDSL2, this object defines the maximum power of DS 
         tones used during G.hs(handshake) sequence when DS tone set A43 is
         used and entry vdslGhsTonesTxPowerControlA43 is set to 2 (manual 
         mode). It is ignored otherwise.
         Value is given in dBm/Hz.  The power of each tone of the set shall
         be equivalent to the given PSD value integrated in a total bandwidth
         of 4.3125 kHz.  Admissible range is between -99 dBm/Hz and
         -40 dBm/Hz with a step of 0.5 dBm/Hz.
         Special value -99 dBm/Hz indicates that the full set
         shall not be used (i.e. no power allowed).

         ALCATEL NOTE:
             ACCESS:   NA                  USAGE:    OPT
             PERSIST:  YES                 INSRVMOD: YES
             RANGE:    -198..-80           DEFVALUE: -80
             UNITS:    dBm/Hz * 1/2        SPARSE:   NA
             DESCR:    NA
        
         FGU4.4:  THIS OBJECT IS NOT SUPPORTED "
::= {gxdslLineSpectrumProfileVdslEntry 23}

gvdslGhsTonesTxPowerLevelB43            OBJECT-TYPE
        SYNTAX          INTEGER 
        ACCESS          read-write
        STATUS          mandatory
        DESCRIPTION     
        "Common to VDSL1/VDSL2, this object defines the maximum power of DS
         tones used during G.hs(handshake) sequence when DS tone set B43 is 
         used and entry vdslGhsTonesTxPowerControlB43 is set to 2 (manual
         mode).  It is ignored otherwise. 
         Value is given in dBm/Hz.  The power of each tone of the set shall
         be equivalent to the given PSD value integrated in a total bandwidth
         of 4.3125 kHz.  Admissible range is between -99 dBm/Hz and
         -40 dBm/Hz with a step of 0.5 dBm/Hz.
         Special value -99 dBm/Hz indicates that the full set
         shall not be used (i.e. no power allowed).

         ALCATEL NOTE:
             ACCESS:   NA                  USAGE:    OPT
             PERSIST:  yes                 INSRVMOD: YES
             RANGE:    -198..-80           DEFVALUE: -80
             UNITS:    dBm/Hz * 1/2        SPARSE:   NA
             DESCR:    NA
        
         FGU4.4:  THIS OBJECT IS NOT SUPPORTED "
::= {gxdslLineSpectrumProfileVdslEntry 24}

gvdslGhsTonesTxPowerLevelA43c           OBJECT-TYPE
        SYNTAX          INTEGER 
        ACCESS          read-write
        STATUS          mandatory
        DESCRIPTION     
        "Common to VDSL1/VDSL2, this object defines the maximum power of DS
         tones used during G.hs(handshake) sequence when DS tone set A43c is 
         used and entry vdslGhsTonesTxPowerControlA43c is set to 2 (manual
         mode).  It is ignored otherwise.
         Value is given in dBm/Hz.  The power of each tone of the set shall
         be equivalent to the given PSD value integrated in a total bandwidth
         of 4.3125 kHz.  Admissible range is between -99 dBm/Hz and
         -40 dBm/Hz with a step of 0.5 dBm/Hz.
         Special value -99 dBm/Hz indicates that the full set
         shall not be used (i.e. no power allowed).

         ALCATEL NOTE:
             ACCESS:   NA                  USAGE:    OPT
             PERSIST:  YES                 INSRVMOD: YES
             RANGE:    -198..-80           DEFVALUE: -80
             UNITS:    dBm/Hz * 1/2        SPARSE:   NA
             DESCR:    NA
        
         FGU4.4:  THIS OBJECT IS NOT SUPPORTED "
::= {gxdslLineSpectrumProfileVdslEntry 25}

gvdslGhsTonesTxPowerLevelV43            OBJECT-TYPE
        SYNTAX          INTEGER 
        ACCESS          read-write
        STATUS          mandatory
        DESCRIPTION     
        "Common to VDSL1/VDSL2, this object defines the maximum power of DS 
         tones used during G.hs(handshake) sequence when DS tone set V43 is
         used and entry vdslGhsTonesTxPowerControlV43 is set to 2 (manual
         mode).  It is ignored otherwise.
         Value is given in dBm/Hz.  The power of each tone of the set shall
         be equivalent to the given PSD value integrated in a total bandwidth
         of 4.3125 kHz.  Admissible range is between -99 dBm/Hz and
         -40 dBm/Hz with a step of 0.5 dBm/Hz.
         Special value -99 dBm/Hz indicates that the full set
         shall not be used (i.e. no power allowed).

         ALCATEL NOTE:
             ACCESS:   NA                  USAGE:    OPT
             PERSIST:  YES                 INSRVMOD: YES
             RANGE:    -198..-80           DEFVALUE: -80
             UNITS:    dBm/Hz * 1/2        SPARSE:   NA
             DESCR:    NA
        
         FGU4.4:  THIS OBJECT IS NOT SUPPORTED "
::= {gxdslLineSpectrumProfileVdslEntry 26}

gvdslMaxBandNumber       OBJECT-TYPE
        SYNTAX          INTEGER 
        ACCESS          read-write
        STATUS          mandatory
        DESCRIPTION     
        "Common to VDSL1/VDSL2, this object specifies the maximum number of
         bands to be used from the specified band plan. This number aggregates
         upstream and downstream bands and does not include the optional band,
         which needs to be configured separately.
         Range is 2 to 8, with special value 0 meaning 'unrestricted'

         ALCATEL NOTE:
             ACCESS:   NA                  USAGE:    OPT
             PERSIST:  YES                 INSRVMOD: YES
             RANGE:    0, 2..8             DEFVALUE: 0
             UNITS:    NA                  SPARSE:   NA
             DESCR:    NA
        
         FGU4.4:  THIS OBJECT IS NOT SUPPORTED "
::= {gxdslLineSpectrumProfileVdslEntry 27}

gvdslMaxFrequency        OBJECT-TYPE
        SYNTAX          GFrequencyType 
        ACCESS          read-write
        STATUS          mandatory
        DESCRIPTION     
        "Common to VDSL1/VDSL2, this object specifies the maximum frequency
         that can be used during showtime in the range 1104...30000 kHz.
         Value 0 means 'unlimited'.

         ALCATEL NOTE:
             ACCESS:   NA                  USAGE:    OPT
             PERSIST:  YES                 INSRVMOD: YES
             RANGE:    0, 1104..30000      DEFVALUE: 0
             UNITS:    kHz                 SPARSE:   NA
             DESCR:    NA
        
         FGU4.4:  THIS OBJECT IS NOT SUPPORTED "
::= {gxdslLineSpectrumProfileVdslEntry 28}

gvdslMaxPsdLevelDownstream              OBJECT-TYPE
        SYNTAX          INTEGER
        ACCESS          read-write
        STATUS          mandatory
        DESCRIPTION     
        "VDSL1 specific, this object specifies a maximum PSD level for
         downstream, flat over the passband as an additional restriction to
         the PSD shape.
         Range is -95.5 to 0 dBm/Hz, in steps of 0.1 dB, the maximum 
         value '0' meaning 'no constraint'.
         It is represented as 1/10* vdslMaxPsdLevelDownstream.
         In case the corresponding DSL standard imposes a more stringent value
         for this parameter, the configured value will be ignored and the
         standard value will apply.

         ALCATEL NOTE:
             ACCESS:   NA                  USAGE:    OPT
             PERSIST:  YES                 INSRVMOD: YES
             RANGE:    -955..0             DEFVALUE: 0
             UNITS:    dBm/Hz * 1/10       SPARSE:   NA
             DESCR:    NA
        
         FGU4.4:  THIS OBJECT IS NOT SUPPORTED "
::= {gxdslLineSpectrumProfileVdslEntry 29}

gvdslMaxPsdLevelUpstream OBJECT-TYPE
        SYNTAX          INTEGER
        ACCESS          read-write
        STATUS          mandatory
        DESCRIPTION     
        "VDSL1 specific, this object specifies a maximum PSD level for
         upstream, flat over the passband as an additional restriction to the
         PSD shape.
         Range is -95.5 to 0 dBm/Hz, , in steps of 0.1 dB, the maximum 
         value '0' meaning 'no constraint'.
         It is represented as 1/10* vdslMaxPsdLevelUpstream.
         In case the corresponding DSL standard imposes a more stringent value
         for this parameter, the configured value will be ignored and the
         standard value will apply.

         ALCATEL NOTE:
             ACCESS:   NA                  USAGE:    OPT
             PERSIST:  YES                 INSRVMOD: YES
             RANGE:    -955..0             DEFVALUE: 0
             UNITS:    dBm/Hz * 1/10       SPARSE:   NA
             DESCR:    NA
        
         FGU4.4:  THIS OBJECT IS NOT SUPPORTED "
::= {gxdslLineSpectrumProfileVdslEntry 30}

gvdslPsdPboParamAUpstream               OBJECT-TYPE
        SYNTAX          GPerBandABParamType
        ACCESS          read-write
        STATUS          mandatory
        DESCRIPTION     
        "VDSL1 specific, this object specifies the parameter A value for each
         band (including optional band) for computing the PSD reference for US
         PBO.
         Range of this parameter for each band is 40..80.95 dBm/Hz in steps of
         0.01 dBm/Hz.
         OCTETS (0,1) represent parameter A of band 0, coded as an integer in
         the range 4000..8095 (actual value * 100).
         The value is defined as MSB-LSB (big-endian).
         OCTETS (2*N,2*N+1) represent parameter A of band N, coded as an 
         integer in the range 4000..8095 (actual value * 100)
         Maximum value for N is 4.
         Default values are defined as follows:
            * US0: a = 40 ; b = 0 
            * US1: a = 47.3 ; b = 19.77 
            * US2: a = 54 ; b = 15.77 
            * US3: a = 54 ; b = 10.77 
            * US4: a = 54 ; b = 9.43 
          Source:
            * US0: No USPBO 
            * US1 & US2: VDSL1 ETSI F 
            * US3 & US4: Copy of US2, considering constant turnover atenuation:
              US1_b assumed at 5 MHz extrapolated at 17 (US3) and 22 (US4) MHz,
              using a k*sqrt(f) = CST rule.
         This parameter is used when vdslRxPsdShapeUp is set to
         vdslABParamRxPsdUp and ignored otherwise.

         ALCATEL NOTE:
             ACCESS:   NA                  USAGE:    OPT
             PERSIST:  YES                 INSRVMOD: YES
             RANGE:    NA                  
             DEFVALUE: '0F A0 12 7A 15 18 15 18 15 18'H
             UNITS:    NA                  SPARSE:   NA
             DESCR:    NA
        
         FGU4.4:  THIS OBJECT IS NOT SUPPORTED "
::= {gxdslLineSpectrumProfileVdslEntry 31}

gvdslPsdPboParamBUpstream               OBJECT-TYPE
        SYNTAX          GPerBandABParamType
        ACCESS          read-write
        STATUS          mandatory
        DESCRIPTION
        "VDSL1 specific, this object specifies the parameter B value for each
         band (including optional band) for computing the PSD reference for US
         PBO.
         Range of this parameter for each band is 0..40.95 dBm/Hz in steps of
         0.01 dBm/Hz.
         OCTETS (0,1) represent parameter B of band 0, coded as an integer in 
         the range 0..4095. The value is defined as MSB-LSB (big-endian).
         OCTETS (2*N,2*N+1) represent parameter B of band N, coded as an 
         integer in the range 0..4095
         Maximum value for N is 4.
         Default values are defined as follows:
            * US0: a = 40 ; b = 0 
            * US1: a = 47.3 ; b = 19.77 
            * US2: a = 54 ; b = 15.77 
            * US3: a = 54 ; b = 10.77 
            * US4: a = 54 ; b = 9.43 
          Source:
            * US0: No USPBO 
            * US1 & US2: VDSL1 ETSI F 
            * US3 & US4: Copy of US2, considering constant turnover atenuation:
              US1_b assumed at 5 MHz extrapolated at 17 (US3) and 22 (US4) MHz,
              using a k*sqrt(f) = CST rule.
         This parameter is used when vdslRxPsdShapeUp is set to 
         vdslABParamRxPsdUp and ignored otherwise.

         ALCATEL NOTE:
             ACCESS:   NA                  USAGE:    OPT
             PERSIST:  YES                 INSRVMOD: YES
             RANGE:    NA
             DEFVALUE: '00 00 07 B9 06 29 04 35 03 AF'H
             UNITS:    NA                  SPARSE:   NA
             DESCR:    NA
        
         FGU4.4:  THIS OBJECT IS NOT SUPPORTED "
::= {gxdslLineSpectrumProfileVdslEntry 32}

gxdslLineSpectrumProfileMappingTable    OBJECT-TYPE
        SYNTAX          SEQUENCE OF GxdslLineSpectrumProfileMappingEntry
        ACCESS          not-accessible
        STATUS          mandatory
        DESCRIPTION
        "The (conceptual) listing the profile name to profile Index
         Mapping.

         ALCATEL NOTE:
             TABLESIZE: 256                    
             DESCR:     NA                          
        " 
::= {gxdslLineSpectrumProfile 6}

gxdslLineSpectrumProfileMappingEntry    OBJECT-TYPE
      SYNTAX            GxdslLineSpectrumProfileMappingEntry
      ACCESS            not-accessible
      STATUS            mandatory
      DESCRIPTION
        "An entry (conceptual row) representing the profile Name to Index
         Mapping.

         Row creation : When an entry is created in the 
                        xdslLineSpectrumProfileTable, an entry is created in
                        this table.
         Row deletion : When an entry is deleted from the
                        xdslLineSpectrumProfileTable, the entry is deleted from
                        this table.
        "
      INDEX            {gxdslLineSpectrumProfileMappingName, 
                        gxdslLineSpectrumProfileMappingScope}
::= { gxdslLineSpectrumProfileMappingTable 1 }

GxdslLineSpectrumProfileMappingEntry ::=
        SEQUENCE {
            gxdslLineSpectrumProfileMappingName        AsamProfileName,
            gxdslLineSpectrumProfileMappingScope       AsamProfileScope,
            gxdslLineSpectrumProfileMappingIndex       AsamProfileIndex
        }

gxdslLineSpectrumProfileMappingName     OBJECT-TYPE
        SYNTAX          AsamProfileName
        ACCESS          not-accessible
        STATUS          mandatory
        DESCRIPTION
        "The Spectrum profile name.

         ALCATEL NOTE:
             ACCESS:   NA                  USAGE:    NA
             PERSIST:  NO                  INSRVMOD: NA
             RANGE:    NA                  DEFVALUE: NA
             UNITS:    NA                  SPARSE:   NA
             DESCR:    NA
        "
::= { gxdslLineSpectrumProfileMappingEntry 1 }

gxdslLineSpectrumProfileMappingScope    OBJECT-TYPE
        SYNTAX          AsamProfileScope
        ACCESS          not-accessible
        STATUS          mandatory
        DESCRIPTION
        "The Spectrum profile scope.

         ALCATEL NOTE:
             ACCESS:   NA                  USAGE:    NA
             PERSIST:  NO                  INSRVMOD: NA
             RANGE:    NA                  DEFVALUE: NA
             UNITS:    NA                  SPARSE:   NA
             DESCR:    NA
        "

::= { gxdslLineSpectrumProfileMappingEntry 2 }

gxdslLineSpectrumProfileMappingIndex    OBJECT-TYPE
        SYNTAX          AsamProfileIndex
        ACCESS          read-only
        STATUS          mandatory
        DESCRIPTION
        "The Index of the corresponding spectrum profile.

         ALCATEL NOTE:
             ACCESS:   NA                  USAGE:    NA
             PERSIST:  NO                  INSRVMOD: NA
             RANGE:    1..256              DEFVALUE: NA
             UNITS:    NA                  SPARSE:   NA
             DESCR:    NA
        "
::= { gxdslLineSpectrumProfileMappingEntry 3 }

gxdslLineSpectrumProfileVdsl2Table      OBJECT-TYPE
        SYNTAX          SEQUENCE OF GxdslLineSpectrumProfileVdsl2Entry
        ACCESS          not-accessible
        STATUS          mandatory
        DESCRIPTION     
        "This table is part of the line profile. It contains the line
         related parameters of the modem configuration that apply to the VDSL2
         operational mode and use specific values for this mode of operation.
         These parameters are ignored in case another operational mode is used.
         All the common VDSL parameters (i.e. the parameters using the same
         value for VDSL1 and VDSL2) are provided in the
         xdslLineSpectrumProfileVdslTable.  
         The VDSL2 table contains the VDSL2 specific parameters (i.e. not
         common).

         ALCATEL NOTE:
             TABLESIZE: 256                   
             DESCR:     NA                  
         "
::= {gxdslLineSpectrumProfile 7}

gxdslLineSpectrumProfileVdsl2Entry      OBJECT-TYPE
        SYNTAX          GxdslLineSpectrumProfileVdsl2Entry
        ACCESS          not-accessible
        STATUS          mandatory
        DESCRIPTION     
        "Each entry consists of a list of line related parameters that serve 
         to configure an XDSL modem in case the VDSL2 mode of operation is
         used.

         Row creation : When an entry is created in the 
                        xdslLineSpectrumProfileTable, an entry with the same 
                        xdslLineSpectrumIndex is created in this table.
         Row deletion : When an entry is deleted from the
                        xdslLineSpectrumProfileTable, the entry with the same
                        xdslLineSpectrumIndex is deleted from this table. 
        "
        INDEX          {gxdslLineSpectrumProfileIndex}
::= {gxdslLineSpectrumProfileVdsl2Table 1}

GxdslLineSpectrumProfileVdsl2Entry ::=
        SEQUENCE {
            gvdsl2ModemFeatures                        INTEGER,
            gvdsl2MaxAggregatePowerLevelDownstream     INTEGER,
            gvdsl2MaxAggregatePowerLevelUpstream       INTEGER,
            gvdsl2PsdShapeDownstream                   GVdsl2PsdDownstreamType,
            gvdsl2CustomPsdShapeDownstream             GCustomPsdShapeType,
            gvdsl2PsdShapeUpstream                     GVdsl2PsdUpstreamType,
            gvdsl2CustomPsdShapeUpstream              GCustomPsdShapeType,
            gvdsl2RxPsdShapeUpstream                   GVdslRxPsdUpstreamType,
            gvdsl2CustomRxPsdShapeUpstream             GCustomPsdShapeType,
            gvdsl2PsdPboElectrLengthUpstream           INTEGER,
            gvdsl2MaxPsdLevelDownstream                INTEGER,
            gvdsl2MaxPsdLevelUpstream                  INTEGER,
            gvdsl2PsdPboParamAUpstream                 GPerBandABParamType,
            gvdsl2PsdPboParamBUpstream                 GPerBandABParamType,
            gvdsl2VirtualNoisePsdDownstream            GVirtualNoisePsdDownType,
            gvdsl2VirtualNoisePsdUpstream              GVirtualNoisePsdUpType,
            gvdsl2VirtualNoiseSnrmModeDownstream       GSnrmMode,
            gvdsl2VirtualNoiseSnrmModeUpstream         GSnrmMode
        }

gvdsl2ModemFeatures      OBJECT-TYPE
        SYNTAX          INTEGER
        ACCESS          read-write
        STATUS          mandatory 
        DESCRIPTION 
        "This object allows to enable/disable specific features of the modem.
         It is a bitmap represented as a sum and allows multiple features to be
         configured simultaneously. Currently only bit 0 is used, the other
         bits are reserved for future use.
         Bitmap values:
          1   Strict compliancy, the modem should turn off all features not
              strictly compliant with the standards.
              The modem is allowed to use proprietary features when
              bit 0 is set to 0.

         ALCATEL NOTE:
             ACCESS:   NA                  USAGE:    OPT
             PERSIST:  YES                 INSRVMOD: YES
             RANGE:    0..1                DEFVALUE: 1
             UNITS:    NA                  SPARSE:   NA
             DESCR:    NA
        
         FGU4.4:  THIS OBJECT IS NOT SUPPORTED "
::= {gxdslLineSpectrumProfileVdsl2Entry 1}
       
gvdsl2MaxAggregatePowerLevelDownstream  OBJECT-TYPE
        SYNTAX          INTEGER
        ACCESS          read-write
        STATUS          mandatory
        DESCRIPTION     
        "This parameter indicates the maximum power allowed on 
         the line for the downstream direction. If the necessary power level 
         exceeds the level given by this parameter the modem will re-
         initialize.  
         The aggregate power has a range of 0 dBm to +25.5 dBm in steps of 
         0.1 dB. 
         It is represented as 1/10 * vdsl2MaxAggregatePowerLevelDownstream.

         ALCATEL NOTE:
             ACCESS:   NA                  USAGE:    OPT
             PERSIST:  YES                 INSRVMOD: YES
             RANGE:    0..255           DEFVALUE: 255
             UNITS:    dBm / 10            SPARSE:   NA
             DESCR:    NA
        "
::= {gxdslLineSpectrumProfileVdsl2Entry 2}

gvdsl2MaxAggregatePowerLevelUpstream    OBJECT-TYPE
        SYNTAX          INTEGER
        ACCESS          read-write
        STATUS          mandatory
        DESCRIPTION     
        "This parameter indicates the maximum power allowed on the line for the 
         upstream direction. If the necessary power level exceeds the level 
         given by this parameter the modem will re-initialize. 
         The aggregate power has a range of -31 dBm to +25.5 dBm in steps of 
         0.1 dB. 
         It is represented as 1/10 * vdsl2MaxAggregatePowerLevelUpstream .

         ALCATEL NOTE:
             ACCESS:   NA                  USAGE:    OPT
             PERSIST:  YES                 INSRVMOD: YES
             RANGE:    -310..255           DEFVALUE: 255
             UNITS:    dBm / 10            SPARSE:   NA
             DESCR:    NA
        
         FGU4.4:  THIS OBJECT IS NOT SUPPORTED "
::= {gxdslLineSpectrumProfileVdsl2Entry 3}

gvdsl2PsdShapeDownstream                OBJECT-TYPE
        SYNTAX          GVdsl2PsdDownstreamType
        ACCESS          read-write
        STATUS          mandatory
        DESCRIPTION     
        "This parameter defines the PSD Shape that must be applied for VDSL
         in the downstream direction.
         In case a vdsl2PsdShapeDownstream other than vdsl2CustomPsdDownstream
         is defined, vdsl2CustomPsdShapeDownstream may be empty.
         If vdsl2PsdShapeDownstream equals vdsl2CustomPsdDownstream and no
         vdsl2CustomPsdShapeDownstream is defined, the configuration shall be
         rejected.
         If vdsl2PsdShapeDownstream differs from vdsl2CustomPsdDownstream and 
         vdsl2CustomPsdShapeDownstream is defined, the minimum of the two masks
         shall be taken, tone per tone.
         A predefined PSD (ANSI or ETSI)can be selected from the following 
         list:
           vdsl2CustomPsdDownstream (meaning no pre-defined PSD shape is used) (NOT SUPPORTED for FGU4.4)
           vdsl2RegionAPsdDownstream
           vdsl2RegionBM1PsdDownstream (NOT SUPPORTED for FGU4.4)
           vdsl2RegionBM2PsdDownstream
           vdsl2RegionCPsdDownstream (NOT SUPPORTED for FGU4.4)

         ALCATEL NOTE:
             ACCESS:   NA                  USAGE:    OPT
             PERSIST:  YES                 INSRVMOD: YES
             RANGE:    NA                  
             DEFVALUE: vdsl2RegionAPsdDownstream
             UNITS:    NA                  SPARSE:   NA
             DESCR:    NA
        " 
::= {gxdslLineSpectrumProfileVdsl2Entry 4}

gvdsl2CustomPsdShapeDownstream          OBJECT-TYPE
        SYNTAX          GCustomPsdShapeType 
        ACCESS          read-write
        STATUS          mandatory
        DESCRIPTION     
        "This object specifies PSD points of a custom VDSL PSD Shape for
         the downstream direction.  It will always be taken into account, 
         whatever the value of vdsl2PsdShapeDownstream.
         In case a vdsl2PsdShapeDownstream other than vdsl2CustomPsdDownstream
         is defined, this object can be empty.
         A number of 2 to 32 PSD points can be specified.
         The successive PSD points must have increasing (>/=) frequencies.
         It is allowed that for two successive PSD points, different PSD
         levels are defined at a same frequency (brickwall).
         The custom PSD Shape is coded as a variable length octet string
         defined as follows:
         OCTET 0: defines the characteristics (type and scale) of the PSD
         shape.
         OCTET 0- bit 0..1: defines the frequency scale to be used for the
         interpolation of the PSD Shape data (00= linear frequency scale,
         01 = logarithmic frequency scale).
         OCTET 0- bit 2..3: defines the type of the PSD shape (00= PSD mask,
         01= PSD template).
         Octet 1..3: defines PSD point #1
         OCTETS 1..2: INTEGER (0..30000), frequency of PSD point #1,
         expressed in kHz. The value is defined as MSB-LSB (big-endian).
         OCTET 3: INTEGER (0..255), -2*PSD level (in dBm/Hz) of
         PSD point#1.
         OCTETS 4..6: define the frequency and PSD level of PSD point #2.
         ...        up to
         OCTETS 3*N-2..3*N: define the frequency and PSD level of the last PSD
         point #N with N<=32.

         ALCATEL NOTE:
             ACCESS:   NA                  USAGE:    OPT
             PERSIST:  YES                 INSRVMOD: YES
             RANGE:    0..97               DEFVALUE: ''H
             UNITS:    NA                  SPARSE:   NA
             DESCR:    NA
        
         For GPON    - SUPPORTED as of ISAM5.3.01	
         For XG-PON1 - NOT SUPPORTED as of ISAM5.3.01	
         For NG-PON2 - NOT SUPPORTED as of ISAM5.3.01 "
::= {gxdslLineSpectrumProfileVdsl2Entry 5}

gvdsl2PsdShapeUpstream   OBJECT-TYPE
        SYNTAX          GVdsl2PsdUpstreamType
        ACCESS          read-write
        STATUS          mandatory
        DESCRIPTION     
        "This parameter defines the PSD Shape that must be applied for VDSL
         in the upstream direction.
         In case a vdsl2PsdShapeUpstream other than vdsl2CustomPsdUpstream is
         defined, vdsl2CustomPsdShapeUpstream may be empty.
         If vdsl2PsdShapeUpstream equals vdsl2CustomPsdUpstream and no
         vdsl2CustomPsdShapeUpstream is defined, the configuration shall be
         rejected.
         If vdsl2PsdShapeUpstream differs from vdsl2CustomPsdUpstream and 
         vdsl2CustomPsdShapeUpstream is defined, the minimum of the two masks
         shall be taken, tone per tone.
         A predefined PSD (ANSI or ETSI) can be selected from the following 
         list:
           vdsl2CustomPsdUpstream (meaning no pre-defined PSD shape is used)
           vdsl2RegionAPsdUpstream
           vdsl2RegionBM1PsdUpstream
           vdsl2RegionBM2PsdUpstream
           vdsl2RegionCPsdUpstream

         ALCATEL NOTE:
             ACCESS:   NA                  USAGE:    OPT
             PERSIST:  YES                 INSRVMOD: YES
             RANGE:    NA                  DEFVALUE: vdsl2RegionBM1PsdUpstream
             UNITS:    NA                  SPARSE:   NA
             DESCR:    NA
        
         FGU4.4:  THIS OBJECT IS NOT SUPPORTED "
::= {gxdslLineSpectrumProfileVdsl2Entry 6}

gvdsl2CustomPsdShapeUpstream            OBJECT-TYPE
        SYNTAX          GCustomPsdShapeType 
        ACCESS          read-write
        STATUS          mandatory
        DESCRIPTION     
        "This object specifies PSD points of a custom VDSL PSD Shape for
         the upstream direction.  It will always be taken into account, 
         whatever the value of vdsl2PsdShapeUpstream.
         A number of 2 to 20 points can be specified.
         The successive PSD points must have increasing (>/=) frequencies.
         It is allowed that for two successive PSD points, different PSD
         levels are defined at a same frequency (brickwall).
         The custom PSD Shape is coded as a variable length octet string
         defined as follows:
         OCTET 0: defines the characteristics (type and scale) of the PSD
         shape.
         OCTET 0- bit 0..1: defines the frequency scale to be used for the
         interpolation of the PSD Shape data (00= linear frequency scale,
         01 = logarithmic frequency scale).
         OCTET 0- bit 2..3: defines the type of the PSD shape (00= PSD mask,
         01= PSD template).
         Octet 1..3: defines PSD point #1
         OCTETS 1..2: INTEGER (0..30000), frequency of PSD point #1,
         expressed in kHz. The value is defined as MSB-LSB (big-endian).
         OCTET 3: INTEGER (0..255), -2*PSD level (in dBm/Hz) of
         PSD point#1.
         OCTETS 4..6: define the frequency and PSD level of PSD point #2.
         ...        up to
         OCTETS 3*N-2..3*N: define the frequency and PSD level of the last PSD
         point #N with N<=20.

         ALCATEL NOTE:
             ACCESS:   NA                  USAGE:    OPT
             PERSIST:  YES                 INSRVMOD: YES
             RANGE:    0..61               DEFVALUE: ''H
             UNITS:    NA                  SPARSE:   NA
             DESCR:    NA
        
         For GPON    - SUPPORTED as of ISAM5.3.01	
         For XG-PON1 - NOT SUPPORTED as of ISAM5.3.01	
         For NG-PON2 - NOT SUPPORTED as of ISAM5.3.01 "
 
::= {gxdslLineSpectrumProfileVdsl2Entry 7}

gvdsl2RxPsdShapeUpstream                OBJECT-TYPE
        SYNTAX          GVdslRxPsdUpstreamType
        ACCESS          read-write
        STATUS          mandatory
        DESCRIPTION     
        "This parameter defines the reference Rx PSD Shape to be used
         for upstream power backoff.
         vdslCustomRxPsdUpstream: a custom reference Rx PSD Shape is defined
         in vdsl2CustomRxPsdShapeUpstream.
         A predefined standard or custom PSD can selected from the following
         list:
          vdslAnsiARxPsdUpstream
          vdslAnsiFRxPsdUpstream
          vdslAnsiCustomExRxPsdUpstream
          vdslAnsiCustomCabRxPsdUpstream
          vdslEtsiARxPsdUpstream
          vdslEtsiBRxPsdUpstream
          vdslEtsiCRxPsdUpstream
          vdslEtsiDRxPsdUpstream
          vdslEtsiERxPsdUpstream
          vdslEtsiFRxPsdUpstream
          vdslEtsiCustomExRxPsdUpstream
          vdslEtsiCustomCabRxPsdUpstream
          vdslABParamRxPsdUpstream  (For FGU4.4, this is the only SUPPORTED option)

         ALCATEL NOTE:
             ACCESS:   NA                  USAGE:    OPT
             PERSIST:  YES                 INSRVMOD: YES
             RANGE:    NA                  DEFVALUE: vdslABParamRxPsdUpstream
             UNITS:    NA                  SPARSE:   NA
             DESCR:    NA
        "
::= {gxdslLineSpectrumProfileVdsl2Entry 8}

gvdsl2CustomRxPsdShapeUpstream          OBJECT-TYPE
        SYNTAX          GCustomPsdShapeType 
        ACCESS          read-write
        STATUS          mandatory
        DESCRIPTION     
        "This object specifies PSD points of a custom reference receive VDSL
         PSD Shape for upstream power backoff in case
         vdsl2RxPsdShapeUpstream = vdslCustomRxPsdUpstream  and it will be
         ignored otherwise. A number of 2 to 20 PSD points can be specified.
         The successive PSD points must have increasing (>/=) frequencies.
         It is allowed that for two successive PSD points, different PSD
         levels are defined at a same frequency (brickwall).
         The custom PSD Shape is coded as a variable length octet string
         defined as follows:
         OCTET 0: defines the characteristics (type and scale) of the PSD 
         shape.
         OCTET 0- bit 0..1: defines the frequency scale to be used for the
         interpolation of the PSD Shape data (00= linear frequency scale,
         01 = logarithmic frequency scale).
         OCTET 0- bit 2..3: defines the type of the PSD shape (00= PSD mask,
         01= PSD template).
         Octet 1..3: defines PSD point #1
         OCTETS 1..2: INTEGER (0..30000), frequency of PSD point #1,
         expressed in kHz. The value is defined as MSB-LSB (big-endian).
         OCTET 3: INTEGER (0..255), -2*PSD level (in dBm/Hz) of
         PSD point#1.
         OCTETS 4..6: define the frequency and PSD level of PSD point #2.
         ...        up to
         OCTETS 3*N-2..3*N: define the frequency and PSD level of the last PSD
         point #N with N<=20.

         ALCATEL NOTE:
             ACCESS:   NA                  USAGE:    OPT
             PERSIST:  YES                 INSRVMOD: YES
             RANGE:    0..61               DEFVALUE: ''H
             UNITS:    NA                  SPARSE:   NA
             DESCR:    NA
        
         For GPON    - SUPPORTED as of ISAM5.3.01	
         For XG-PON1 - NOT SUPPORTED as of ISAM5.3.01	
         For NG-PON2 - NOT SUPPORTED as of ISAM5.3.01 "
::= {gxdslLineSpectrumProfileVdsl2Entry 9}

gvdsl2PsdPboElectrLengthUpstream        OBJECT-TYPE
        SYNTAX          INTEGER 
        ACCESS          read-write
        STATUS          mandatory
        DESCRIPTION     
        "This object specifies the electrical length to be used with the AB
         parameters.  It has to be set to the maximal value when the electrical
         length XTU-R estimate should be used.  Range is 0 to 127.5 dB (at 1
         MHz) with a granularity of 0.5 dB.
         Special value 256 means 'electricalLengthEstimated', indicating that
         the US Power Back-off electrical length estimated by the VTU-R is not
         overwritten by any fixed configuration value given either by an 
         operator or by a manager(N.A...).  However, in this case, the VTU-O 
         transceiver is still allowed to automatically overwrite the VTU-R 
         estimated value (which is the normal behaviour).  In other words, this 
         concerns operator overwrite, not VTU-O overwrite.
         Note: the electrical length is positive when the loop gain is negative
         in dB.
         integer range: 0..255 (= actual value * 2) + special value 256

         ALCATEL NOTE:
             ACCESS:   NA                  USAGE:    OPT
             PERSIST:  YES                 INSRVMOD: YES
             RANGE:    0..256              DEFVALUE: 256
             UNITS:    dB / 2              SPARSE:   NA
             DESCR:    NA
        "
::= {gxdslLineSpectrumProfileVdsl2Entry 10}

gvdsl2MaxPsdLevelDownstream             OBJECT-TYPE
        SYNTAX          INTEGER
        ACCESS          read-write
        STATUS          mandatory
        DESCRIPTION     
        "This object specifies a maximum PSD level for downstream, flat over
         the passband as an additional restriction to the PSD shape.
         Range is -60.0 to -30.0 dBm/Hz, in steps of 0.1 dB, the maximum 
         value '0' meaning 'no constraint'.
         It is represented as 1/10* vdsl2MaxPsdLevelDownstream.
         In case the corresponding DSL standard imposes a more stringent value
         for this parameter, the configured value will be ignored and the
         standard value will apply.

         ALCATEL NOTE:
             ACCESS:   NA                  USAGE:    OPT
             PERSIST:  YES                 INSRVMOD: YES
             RANGE:    -600..-300             DEFVALUE: -300
             UNITS:    dBm/Hz * 1/10       SPARSE:   NA
             DESCR:    NA
        "
::= {gxdslLineSpectrumProfileVdsl2Entry 11}

gvdsl2MaxPsdLevelUpstream               OBJECT-TYPE
        SYNTAX          INTEGER
        ACCESS          read-write
        STATUS          mandatory
        DESCRIPTION     
        "This object specifies a maximum PSD level for upstream, flat over
         the passband as an additional restriction to the PSD shape.
         Range is -60.0 to -30.0 dBm/Hz, , in steps of 0.1 dB, the maximum 
         value '0'  meaning 'no constraint'.
         It is represented as 1/10* vdsl2MaxPsdLevelUpstream.
         In case the corresponding DSL standard imposes a more stringent value
         for this parameter, the configured value will be ignored and the
         standard value will apply.
         integer range: -600..-300

         ALCATEL NOTE:
             ACCESS:   NA                  USAGE:    OPT
             PERSIST:  YES                 INSRVMOD: YES
             RANGE:    -600..-300             DEFVALUE: -300
             UNITS:    dBm/Hz * 1/10       SPARSE:   NA
             DESCR:    NA
        "
::= {gxdslLineSpectrumProfileVdsl2Entry 12}

gvdsl2PsdPboParamAUpstream              OBJECT-TYPE
        SYNTAX          GPerBandABParamType
        ACCESS          read-write
        STATUS          mandatory
        DESCRIPTION     
        "This object specifies the parameter A value for each band (including
         optional band) for computing the PSD reference for US PBO.
         Range of this parameter for each band is 40..80.95 dBm/Hz in steps of
         0.01 dBm/Hz.
         OCTETS (0,1) represent parameter A of band 0, coded as an integer in
         the range 4000..8095. The value is defined as MSB-LSB (big-endian).
         OCTETS (2*N,2*N+1) represent parameter A of band N, coded as an 
         integer in the range 4000..8095
         Maximum value for N is 4.
         Default values are defined as follows:
            * US0: a = 0 ; b = 0 
            * US1: a = 60.0 ; b = 8.28 
            * US2: a = 60.0 ; b = 8.28 
            * US3: a = 60.0 ; b = 8.28 
            * US4: a = 0 ; b = 0 
          Source:
            * US0: No USPBO 
            * US1 & US2: VDSL1 ETSI F 
            * US3 & US4: Copy of US2, considering constant turnover atenuation:
              US1_b assumed at 5 MHz extrapolated at 17 (US3) and 22 (US4) MHz,
              using a k*sqrt(f) = CST rule.
         This parameter is used when vdslRxPsdShapeUp is set to
         vdslABParamRxPsdUp and ignored otherwise.

         ALCATEL NOTE:
             ACCESS:   NA                  USAGE:    OPT
             PERSIST:  YES                 INSRVMOD: YES
             RANGE:    NA 
             DEFVALUE: '00 00 17 70 17 70 17 70 00 00'H
             UNITS:    NA                  SPARSE:   NA
             DESCR:    NA

    NOTE:  For FGU4.4.10, removed restrictions regarding values for US0..US4  "
::= {gxdslLineSpectrumProfileVdsl2Entry 13}

gvdsl2PsdPboParamBUpstream              OBJECT-TYPE
        SYNTAX          GPerBandABParamType
        ACCESS          read-write
        STATUS          mandatory
        DESCRIPTION     
        "This object specifies the parameter B value for each band (including
         optional band) for computing the PSD reference for US PBO.
         Range of this parameter for each band is 0..40.95 dBm/Hz in steps of 
         0.01 dBm/Hz.
         OCTETS (0,1) represent parameter B of band 0, coded as an integer in 
         the range 0..4095. The value is defined as MSB-LSB (big-endian).
         OCTETS (2*N,2*N+1) represent parameter B of band N, coded as an 
         integer in the range 0..4095
         Maximum value for N is 4.
         Default values are defined as follows:
            * US0: a = 0 ; b = 0 
            * US1: a = 60.0 ; b = 8.28 
            * US2: a = 60.0 ; b = 8.28 
            * US3: a = 60.0 ; b = 8.28 
            * US4: a = 0 ; b = 0 
          Source:
            * US0: No USPBO 
            * US1 & US2: VDSL1 ETSI F 
            * US3 & US4: Copy of US2, considering constant turnover atenuation:
              US1_b assumed at 5 MHz extrapolated at 17 (US3) and 22 (US4) MHz,
              using a k*sqrt(f) = CST rule.
         This parameter is used when vdslRxPsdShapeUp is set to
         vdslABParamRxPsdUp and ignored otherwise.

         ALCATEL NOTE:
             ACCESS:   NA                  USAGE:    OPT
             PERSIST:  YES                 INSRVMOD: YES
             RANGE:    NA 
             DEFVALUE: '00 00 03 3C 03 3C 03 3C 00 00'H
             UNITS:    NA                  SPARSE:   NA
             DESCR:    NA

   NOTE:  For FGU4.4.10, removed restrictions regarding values for US0..US4  "
::= {gxdslLineSpectrumProfileVdsl2Entry 14}

gvdsl2VirtualNoisePsdDownstream         OBJECT-TYPE
        SYNTAX          GVirtualNoisePsdDownType
        ACCESS          read-write
        STATUS          mandatory
        DESCRIPTION     
        "This object specifies the transmitter-referred virtual noise level for
         determining the SNR margin in the corresponding downstream bands.
         A number of 2 to 32 Virtual Noise PSD points can be specified downstream.
         An empty sequence means that no virtual noise shall be used.
         The successive PSD points must have increasing (>/=) frequencies.
         It is allowed that for two successive PSD points, different PSD
         levels are defined at a same frequency (brickwall).
         Virtual Noise PSD points are defined in the range -140dBm/Hz..-40 
         dBm/Hz.
         A special value (-167,5 dBm/Hz) states no virtual noise has to be
         applied.
         The custom Virtual Noise PSD Shape is coded as a variable length
         octet string defined as follows:
         Octet 0: reserved 
         Octet 1..3: defines PSD point #1
         OCTETS 1..2: INTEGER (0..30000), frequency of PSD point #1,
         expressed in kHz. The value is defined as MSB-LSB (big-endian).
         OCTET 3: INTEGER (0..200), -2*(40 + PSD level) (in dBm/Hz) of
         PSD point#1.
         OCTETS 4..6: define the frequency and PSD level of PSD point #2.
         ...        up to
         OCTETS 3*N-2..3*N: define the frequency and PSD level of the last PSD
         point #N with N<=32.
         This parameter is used when vdsl2virtualNoiseSnrmModeDownstream is set
         to snrmMode2 and ignored otherwise.

         ALCATEL NOTE:
             ACCESS:   NA                  USAGE:    OPT
             PERSIST:  YES                 INSRVMOD: YES
             RANGE:    0..97               DEFVALUE: ''H
             UNITS:    NA                  SPARSE:   NA
             DESCR:    NA

         FGU4.4:  THIS OBJECT IS NOT SUPPORTED  "
::= {gxdslLineSpectrumProfileVdsl2Entry 15}

gvdsl2VirtualNoisePsdUpstream           OBJECT-TYPE
        SYNTAX          GVirtualNoisePsdUpType
        ACCESS          read-write
        STATUS          mandatory
        DESCRIPTION     
        "This object specifies the transmitter-referred virtual noise level for
         determining the SNR margin in the corresponding upstream bands.
         A number of 2 to 16 Virtual Noise PSD points can be specified upstream.
         An empty sequence means that no virtual noise shall be used.
         The successive PSD points must have increasing (>/=) frequencies.
         It is allowed that for two successive PSD points, different PSD
         levels are defined at a same frequency (brickwall).
         Virtual Noise PSD points are defined in the range -140dBm/Hz..-40
         dBm/Hz.
         A special value (-167,5 dBm/Hz) states no virtual noise has to be
         applied.
         The custom Virtual Noise PSD Shape is coded as a variable length
         octet string defined as follows:
         Octet 0: reserved 
         Octet 1..3: defines PSD point #1
         OCTETS 1..2: INTEGER (0..30000), frequency of PSD point #1,
         expressed in kHz. The value is defined as MSB-LSB (big-endian).
         OCTET 3: INTEGER (0..200), -2*(40 + PSD level) (in dBm/Hz) of
         PSD point#1.
         OCTETS 4..6: define the frequency and PSD level of PSD point #2.
         ...        up to
         OCTETS 3*N-2..3*N: define the frequency and PSD level of the last PSD
         point #N with N<=16.
         This parameter is used when vdsl2virtualNoiseSnrmModeUpstream is set
         to snrmMode2 and ignored otherwise.

         ALCATEL NOTE:
             ACCESS:   NA                  USAGE:    OPT
             PERSIST:  YES                 INSRVMOD: YES
             RANGE:    0..49               DEFVALUE: ''H
             UNITS:    NA                  SPARSE:   NA
             DESCR:    NA

         FGU4.4:  THIS OBJECT IS NOT SUPPORTED  "
::= {gxdslLineSpectrumProfileVdsl2Entry 16}

gvdsl2VirtualNoiseSnrmModeDownstream    OBJECT-TYPE
        SYNTAX          GSnrmMode
        ACCESS          read-write
        STATUS          mandatory
        DESCRIPTION     
        "This object specifies the downstream mode of the  Virtual Noise Signal
         to Noise Ratio Margin, which is the maximum increase of the reference
         noise level, such that the VTU can still meet all the target BERs.
          snrmmode1: the reference noise PSD is the external noise PSD present 
                     at U interface.
          snrmmode2: the reference noise PSD is the maximum (tone per tone) 
                     between the external noise PSD present at U interface and 
                     the received virtual noise as specified in 
                     vdsl2VirtualNoisePsdDownstream
          snrmmode3: not supported, for future use

         ALCATEL NOTE:
             ACCESS:   NA                  USAGE:    OPT
             PERSIST:  YES                 INSRVMOD: YES
             RANGE:    snrmMode1, snrmMode2                                    
             DEFVALUE: snrmMode1
             UNITS:    NA                  SPARSE:   NA
             DESCR:    NA

           FGU4.4:  THIS OBJECT IS NOT SUPPORTED  "
::= {gxdslLineSpectrumProfileVdsl2Entry 17}

gvdsl2VirtualNoiseSnrmModeUpstream      OBJECT-TYPE
        SYNTAX          GSnrmMode
        ACCESS          read-write
        STATUS          mandatory
        DESCRIPTION     
        "This object specifies the upstream mode of the  Virtual Noise Signal
         to Noise Ratio Margin, which is the maximum increase of the reference
         noise level, such that the VTU can still meet all the target BERs.
          snrmmode1: the reference noise PSD is the external noise PSD present 
                     at U interface.
          snrmmode2: the reference noise PSD is the maximum (tone per tone) 
                     between the external noise PSD present at U interface and 
                     the received virtual noise as specified in 
                     vdsl2VirtualNoisePsdUpstream
          snrmmode3: not supported, for future use

         ALCATEL NOTE:
             ACCESS:   NA                  USAGE:    OPT
             PERSIST:  YES                 INSRVMOD: YES
             RANGE:    snrmMode1, snrmMode2                  
             DEFVALUE: snrmMode1
             UNITS:    NA                  SPARSE:   NA
             DESCR:    NA

          FGU4.4:  THIS OBJECT IS NOT SUPPORTED   "
::= {gxdslLineSpectrumProfileVdsl2Entry 18}

gxdslLineConfTable       OBJECT-TYPE
        SYNTAX          SEQUENCE OF GxdslLineConfEntry
        ACCESS          not-accessible
        STATUS          mandatory
        DESCRIPTION     
        "This table contains per line configuration information about the
         modem.

         ALCATEL NOTE:
             TABLESIZE: DEP [number of XDSL lines]                    
             DESCR:     NA                  
        "
::= {gxdslLine 7}

gxdslLineConfEntry       OBJECT-TYPE
        SYNTAX          GxdslLineConfEntry
        ACCESS          not-accessible
        STATUS          mandatory
        DESCRIPTION     
        "An entry in the xdslLineConfTable contains configuration
         information about the modem related with one physical entry.

         Row creation : For ISAM, Entries for all XDSL lines belonging to a board are 
                        created by the system when the board is planned.
         Row deletion : For ISAM, Entries for all XDSL lines belonging to a board are 
                        deleted by the system when the board is unplanned.

        FGU4.4:  Row creation and deletion is done explicitly by the manager (i..e. NOT
	         automatically by the system). 
        "
        INDEX          {ifIndex, gxdslLineSpIndex}
::= {gxdslLineConfTable 1}

GxdslLineConfEntry ::=
        SEQUENCE {
            gxdslLineServiceProfileNbr                 AsamProfilePointer,
            gxdslLineSpectrumProfileNbr                AsamProfilePointer,
            gxdslLineIsdnSplitterOptimization          GSplitterOptimizationType,
            gxdslLineOpModeMask                        GOpModeType,
            gxdslLineOpModeBoardCapability             GOpModeType,
            gxdslLineCarrierDataMode                   INTEGER,
            gxdslLineLoopDiagnosticsMode               INTEGER,
            gxdslLineTestModes                         INTEGER,
            gxdslLineBondingModeChannel1               GBondingModeType,
            gxdslLineBondingModeChannel2               GBondingModeType,
            gxdslLineBondingModeChannel3               GBondingModeType,
            gxdslLineBondingModeChannel4               GBondingModeType,
            gxdslLineTpsTcMode                         GTpsTcModeType,
            gxdslLineOpModeAtmCapability               GOpModeType,
            gxdslLineOpModePtmCapability               GOpModeType,
            gxdslLineActualConfTpsTcMode               GTpsTcModeType,
            gxdslLinePMEnable                          INTEGER,
            gxdslLineCustVlan                          INTEGER,
            gxdslLineQosProfile                        AsamProfilePointer,
            gxdslLineEtherTrafficPMCollectEnable       INTEGER,
            gxdslLineSpIndex                           SpIndex,
            gxdslLineAdminState                        INTEGER,
            gxdslLineOpState                           INTEGER,
            gxdslLinePwrShedOverride                   Boolean,
            gxdslLineDscpPbitMapProfile                AsamProfilePointer,
            gxdslLineRowStatus                         RowStatus,
            gxdslLineDpboProfileNbr                    AsamProfilePointer,
            gxdslLineRtxUpstreamProfileNbr             AsamProfilePointer,
            gxdslLineRtxDownstreamProfileNbr           AsamProfilePointer
        }
        
gxdslLineServiceProfileNbr              OBJECT-TYPE
        SYNTAX          AsamProfilePointer
        ACCESS          read-write
        STATUS          mandatory
        DESCRIPTION     
        "This object identifies the row of the xdslLineServiceProfileTable
         which defines the valid profile for the interface.

         ALCATEL NOTE:
             ACCESS:   NA                  USAGE:    OPT
             PERSIST:  YES                 INSRVMOD: YES
             RANGE:    0..256              DEFVALUE: 0
             UNITS:    NA                  SPARSE:   NA
             DESCR:    NA

   FTTU4.4:  Valid range changed from 0..256 to 1..256. Changed 
   default to from 0 to NA.  Valid value must be supplied by manager at 
   row creation.

  For ISAM4.0.10, changed range back to 0..256 and DEFAULT to 0 - stems from
  lines being auto-created as opposed to being manually created.  "
::= {gxdslLineConfEntry 1}

gxdslLineSpectrumProfileNbr             OBJECT-TYPE
        SYNTAX          AsamProfilePointer
        ACCESS          read-write
        STATUS          mandatory
        DESCRIPTION     
        "This object identifies the row of the xdslLineSpectrumProfileTable
         which defines the valid profile for the interface.
         ALCATEL NOTE:

             ACCESS:   NA                  USAGE:    OPT
             PERSIST:  YES                 INSRVMOD: YES
             RANGE:    0..256              DEFVALUE: 0
             UNITS:    NA                  SPARSE:   NA
             DESCR:    NA
   FTTU4.4:  Valid range changed from 0..256 to 1..256. Changed 
   default to from 0 to NA.  Valid value must be supplied by manager at 
   row creation.

  For ISAM4.0.10, changed range back to 0..256 and DEFAULT to 0 - stems from
  lines being auto-created as opposed to being manually created.  "
::= {gxdslLineConfEntry 2}

gxdslLineIsdnSplitterOptimization       OBJECT-TYPE  
        SYNTAX          GSplitterOptimizationType
        ACCESS          read-write
        STATUS          mandatory
        DESCRIPTION     
        "The  ISDN splitter can be optimized for POTS or for ISDN.

         ALCATEL NOTE:
             ACCESS:   NA                  USAGE:    OPT
             PERSIST:  YES                 INSRVMOD: YES
             RANGE:    isdn                DEFVALUE: isdn
             UNITS:    NA                  SPARSE:   NA
             DESCR:    The object is supported to avoid future database 
                       migration but should not be set.
                       Set requests will be rejected (badvalue) if the value
                       differs from the default value.

  FTTU4.5.5:  This attribute is NOT SUPPORTED (never has been for FTTU).
        "
::= {gxdslLineConfEntry 3}

gxdslLineOpModeMask      OBJECT-TYPE
        SYNTAX          GOpModeType
        ACCESS          read-write
        STATUS          mandatory 
        DESCRIPTION 
        "This variable controls the operational modes allowed on the line.
         It can be used to disable an operational mode that is enabled in the
         line spectrum configuration profile (xdslLineOpMode) but is not 
         allowed on the line. 
         The modes which are not supported by the line (i.e. not set in the
         corresponding xdslLineOpModeBoardCapability) must be disabled.
         An operational mode is allowed on the line when it is enabled in
         xdslLineOpMode and in xdslLineOpModeMask.
         It uses the same bitmap coding as defined in gxdslLineOpMode.
         '0' is used as default value to indicate that no operatoinal modes are 
	 configured on the line.
         The actual operational mode is reflected by the 
         'xdslLineActualOperationalMode' object.

         ALCATEL NOTE:
             ACCESS:   NA                  USAGE:    OPT 
             PERSIST:  YES                 INSRVMOD: YES
             RANGE:    NA                  
             DEFVALUE: '00 00 00 00 00 00 00 00 
                        00 00 00 00 00 00 00 00'H
             UNITS:    NA                  SPARSE:   NA
             DESCR:    NA

      As of FGU4.6, only SUPPORTED values are the following:
	'00 00 00 00 00 00 00 00 00 01 00 00 00 00 00 00'H  (i.e. 35b)
	'00 00 00 00 00 00 00 00 80 00 00 00 00 00 00 00'H  (i.e. 30a - with bandplans A998, B998ADE, and B998E)
	'00 00 00 00 00 00 00 00 40 00 00 00 00 00 00 00'H  (i.e. 17a - with bandplans A998, B998ADE, and B998E)
	'00 00 00 00 00 00 00 00 20 00 00 00 00 00 00 00'H  (i.e. 12b - with bandplans A998)
	'00 00 00 00 00 00 00 00 04 00 00 00 00 00 00 00'H  (i.e.   8c - with bandplans A998)
        '04 00 00 00 00 00 00 00 00 00 00 00 00 00 00 00'H  (Annex A of G.992.1)
	'00 00 00 00 00 01 00 00 00 00 00 00 00 00 00 00'H  (Annex A of G.992.5)
	'04 00 00 00 00 01 00 00 00 00 00 00 00 00 00 00'H  (Annex A of G.992.1&Annex A of G.992.5 multimode)
        "
::= {gxdslLineConfEntry 4}

gxdslLineOpModeBoardCapability          OBJECT-TYPE
        SYNTAX          GOpModeType
        ACCESS          read-only
        STATUS          mandatory 
        DESCRIPTION 
        "This variable used to indicate which operational modes are supported 
         by the board for the corresponding line and can therefore be enabled
         in the xdslLineOpModeMask.  Due to the introduction of TpsTcMode, the
         board capability has been further refined to differentiate OpModes 
         supported in Atm and/or Ptm modes, see xdslLineOpModeAtmCapability and
         xdslLineOpModePtmCapability. The object xdslLineOpModeBoardCapability
         has been maintained for backward compatibility reasons and can be used
         to obtain the overall opmode board capabilities independantly of the
         selected TpsTcMode.

         ALCATEL NOTE:
             ACCESS:   NA                  USAGE:    NA
             PERSIST:  NO                  INSRVMOD: NA
             RANGE:    NA                  DEFVALUE: NA
             UNITS:    NA                  SPARSE:   NA
             DESCR:    NA

           FGU4.4:  THIS OBJECT IS NOT SUPPORTED
        "
::= {gxdslLineConfEntry 5}

gxdslLineCarrierDataMode OBJECT-TYPE
        SYNTAX          INTEGER {
                            carrierDataModeOff (1),
                            carrierDatamodeOn (2),
                            carrierDatamodeOnInit (3),
                            carrierDataModeFailed (4)
                        }
        ACCESS          read-write
        STATUS          mandatory 
        DESCRIPTION 
        "This variable is used to enable or disable the collection during
         normal operation of detailed carrier data measurements for the
         corresponding XDSL line:
         - carrierDataModeOff disables the collection of carrier data
           measurements.
         - carrierDataModeOn enables the collection of carrier data
           measurewments.
           Carrier data measurements which are performed at initialization may
           not be available since the line will not be reinitialized.
         - carrierDataModeOnInit enables the collection of carrier data
           measurements and forces a reinitialization of the line so that the
           carrier data measured during initialization will also be collected

--FGU4.4: New Value added due to OMCI component in the FTTU architecture:
         - carrierDataModeFailed: Indicates that remote ONU equipment failed
           to enable the carrier data mode on this line
         ALCATEL NOTE:
             ACCESS:   NA                  USAGE:    OPT 
             PERSIST:  YES                 INSRVMOD: YES
             RANGE:    NA                  DEFVALUE: carrierDataModeOff
             UNITS:    NA                  SPARSE:   NA
             DESCR:    NA
        
         FGU4.4: THIS OBJECT IS EXPANDED "
::= {gxdslLineConfEntry 6}

gxdslLineLoopDiagnosticsMode            OBJECT-TYPE
        SYNTAX          INTEGER {
                            loopDiagnosticsOff (1),
                            loopDiagnosticsInit (2),
                            loopDiagnosticsCompleted (3),
                            loopDiagnosticsFailed (4)
                        }
        ACCESS          read-write
        STATUS          mandatory 
        DESCRIPTION 
        "This variable is effective for modems with ADSL2 or VDSL2 operational
         modes capabilities only.
         The manager can request the modem to perform a loop diagnostics
         initialisation for this XDSL line where detailed line measurements
         are performed. 
         The system will autonomously overwrite this variable when the loop
         diagnostics initialisation is completed or failed.
         The possible values are:
         - loopDiagnosticsInit (2): set by the manager to put the line in loop
           diagnostics mode and to start a loop diagnostics test.
           Only allowed for modems with ADSL2 or VDSL2 modes capabilities.
         - loopDiagnosticsCompleted (3): set by the system to indicate that
           diagnostics data can be retrieved.
         - loopDiagnosticsFailed (4): set by the system to indicate that the
           loop diagnostics initialization has failed and no diagnostics data
           can be retrieved.
         - loopDiagnosticsOff (1): allows the manager to leave the loop
           diagnostics mode. Loop diagnostics data is not available anymore.

         ALCATEL NOTE:
             ACCESS:   NA                  USAGE:    OPT 
             PERSIST:  NO                  INSRVMOD: YES
             RANGE:    NA                  DEFVALUE: loopDiagnosticsOff
             UNITS:    NA                  SPARSE:   NA
             DESCR:    NA    "
::= {gxdslLineConfEntry 7}

gxdslLineTestModes OBJECT-TYPE
        SYNTAX      INTEGER
        ACCESS      read-write
        STATUS      mandatory 
        DESCRIPTION 
        "This variable allows to enable/disable particular XDSL modem test
         modes.
         It is coded as a bitmap defined as follows:
         - For future use -.
         ALCATEL NOTE:
             ACCESS:   NA                  USAGE:    NA
             PERSIST:  NA                  INSRVMOD: NA
             RANGE:    NA                  DEFVALUE: NA
             UNITS:    NA                  SPARSE:   NA
             DESCR:    This object is not supported.
         
         FGU4.4:  THIS OBJECT IS NOT SUPPORTED "
::= {gxdslLineConfEntry 8}

gxdslLineBondingModeChannel1            OBJECT-TYPE   
        SYNTAX          GBondingModeType
        ACCESS          read-write
        STATUS          mandatory 
        DESCRIPTION 
        "This variable allows to configure XDSL Channel 1 either in native mode
         or in bonding mode.

         ALCATEL NOTE:
             ACCESS:   NA                  USAGE:    OPT
             PERSIST:  YES                 INSRVMOD: YES
             RANGE:    NA                  DEFVALUE: native
             UNITS:    NA                  SPARSE:   NA
             DESCR:    Set requests on this object are ignored. Updates are done
                       automatically by the system.
        
         FGU4.4:  THIS OBJECT IS NOT SUPPORTED "
::= {gxdslLineConfEntry 9}

gxdslLineBondingModeChannel2 OBJECT-TYPE
        SYNTAX      GBondingModeType
        ACCESS      read-write
        STATUS      mandatory 
        DESCRIPTION 
        "This variable allows to configure XDSL Channel 2 either in native mode or
         in ATM bonding mode.
         Set requests on this object are ignored. Updates are done automatically by 
         the system.
         ALCATEL NOTE:
             ACCESS:   NA                  USAGE:    NA
             PERSIST:  NA                  INSRVMOD: NA
             RANGE:    NA                  DEFVALUE: NA
             UNITS:    NA                  SPARSE:   NA
             DESCR:    This object is not supported.
         
         FGU4.4:  THIS OBJECT IS NOT SUPPORTED "
        DEFVAL { native }
::= {gxdslLineConfEntry 10}

gxdslLineBondingModeChannel3 OBJECT-TYPE
        SYNTAX      GBondingModeType
        ACCESS      read-write
        STATUS      mandatory 
        DESCRIPTION 
        "This variable allows to configure XDSL Channel 3 either in native mode or
         in ATM bonding mode.
         Set requests on this object are ignored. Updates are done automatically by 
         the system.
        DEFVAL { native }
         ALCATEL NOTE:
             ACCESS:   NA                  USAGE:    NA
             PERSIST:  NA                  INSRVMOD: NA
             RANGE:    NA                  DEFVALUE: NA
             UNITS:    NA                  SPARSE:   NA
             DESCR:    This object is not supported.
         
         FGU4.4:  THIS OBJECT IS NOT SUPPORTED "
::= {gxdslLineConfEntry 11}

gxdslLineBondingModeChannel4 OBJECT-TYPE
        SYNTAX      GBondingModeType
        ACCESS      read-write
        STATUS      mandatory 
        DESCRIPTION 
        "This variable allows to configure XDSL Channel 4 either in native mode or
         in ATM bonding mode.
         Set requests on this object are ignored. Updates are done automatically by 
         the system.
         ALCATEL NOTE:
             ACCESS:   NA                  USAGE:    NA
             PERSIST:  NA                  INSRVMOD: NA
             RANGE:    NA                  DEFVALUE: NA
             UNITS:    NA                  SPARSE:   NA
             DESCR:    This object is not supported.
         
         FGU4.4:  THIS OBJECT IS NOT SUPPORTED "
        DEFVAL { native }
::= {gxdslLineConfEntry 12}

gxdslLineTpsTcMode       OBJECT-TYPE
        SYNTAX          GTpsTcModeType
        ACCESS          read-write
        STATUS          mandatory
        DESCRIPTION
        "This variable allows to configure the TpsTc Mode of the line.
         atm: the atm transfer mode is selected
         ptm: the ptm transfer mode is selected
         The actual configured value is given by xdslLineActualConfTpsTcMode.

         ALCATEL NOTE:
             ACCESS:   NA                  USAGE:    OPT 
             PERSIST:  YES                 INSRVMOD: YES
             RANGE:    NA                  DEFVALUE: PTM 
             UNITS:    NA                  SPARSE:   NA
             DESCR:    NA
        "
::= {gxdslLineConfEntry 15}

gxdslLineOpModeAtmCapability            OBJECT-TYPE
        SYNTAX          GOpModeType
        ACCESS          read-only
        STATUS          mandatory
        DESCRIPTION
        "This variable indicates which operational modes are supported by
         the board for the corresponding line in ATM TpsTc mode.

         ALCATEL NOTE:
             ACCESS:   NA                  USAGE:    NA
             PERSIST:  NO                  INSRVMOD: NA
             RANGE:    NA                  DEFVALUE: NA 
             UNITS:    NA                  SPARSE:   NA
             DESCR:    NA

           FGU4.4:  THIS OBJECT IS NOT SUPPORTED
        "  
::= {gxdslLineConfEntry 16}

gxdslLineOpModePtmCapability            OBJECT-TYPE
        SYNTAX          GOpModeType
        ACCESS          read-only
        STATUS          mandatory
        DESCRIPTION
        "This variable indicates which operational modes are supported by
         the board for the corresponding line in PTM TpsTc mode.

         ALCATEL NOTE:
             ACCESS:   NA                  USAGE:    NA
             PERSIST:  NO                  INSRVMOD: NA
             RANGE:    NA                  DEFVALUE: NA 
             UNITS:    NA                  SPARSE:   NA
             DESCR:    NA

           FGU4.4:  THIS OBJECT IS NOT SUPPORTED
         "
::= {gxdslLineConfEntry 17}

gxdslLineActualConfTpsTcMode OBJECT-TYPE
        SYNTAX      GTpsTcModeType
        ACCESS      read-only
        STATUS      mandatory
        DESCRIPTION
        "This variable indicates which TpsTc Mode is configured on the line:
         atm: the atm transfer mode is configured
         ptm: the ptm transfer mode is configured.
         ALCATEL NOTE:
             ACCESS:   NA                  USAGE:    NA
             PERSIST:  NA                  INSRVMOD: NA
             RANGE:    NA                  DEFVALUE: NA
             UNITS:    NA                  SPARSE:   NA
             DESCR:    NA
         "
::= {gxdslLineConfEntry 18}

--FGU4.4: THE FOLLOWING OBJECTS ARE ADDED TO THE XDSL MIB DUE TO GPON ARCHITECTURE

gxdslLinePMEnable OBJECT-TYPE
       SYNTAX       INTEGER
                      {
                      enabled(1),         
                      disabled(2)        
                      }
       ACCESS       read-write
       STATUS       mandatory
       DESCRIPTION
           "Defines whether performance monitoring and collection is enabled for this
            VDSL line and associated channels (i.e both line and channel PM are
            enabled/disabled in tandem).
           
             ALCATEL NOTE: THIS OBJECT IS ADDED TO THE xDSL MIB FOR OMCI COMPLIANCE & 
             IN ORDER TO ALLOW FLEXIBLE LIMITATIONS ON PM COLLECTION TASK"

       DEFVAL  {2}

       ::= { gxdslLineConfEntry 19 }


gxdslLineCustVlan  OBJECT-TYPE
	SYNTAX 	INTEGER  (0..4095)
	ACCESS	read-write
	STATUS	mandatory
	DESCRIPTION 
		" This is the default Customer VLAN ID
		  used by the ONU for this VDSL UNI.

		  Default = 0 . 

              ALCATEL NOTE: This object is Alcatel Proprietary.

	For ISAM4.0.10, this attribute is NOT SUPPORTED. "
	::= { gxdslLineConfEntry 20 }

gxdslLineQosProfile OBJECT-TYPE
	    SYNTAX	AsamProfilePointer
	    ACCESS read-write
	    STATUS	mandatory
	    DESCRIPTION
		    " This object is used to reference the appropriate
		     QOS Profile (in the QOS MIB) --> for tag marking.

  		     The ONT LAN UNI is associated with one OLT bridge port
		     which is associated with one QOS Profile. 

              ALCATEL NOTE: This object is Alcatel Proprietary.

	For ISAM4.0.10, this attribute is NOT SUPPORTED. "
     	::= { gxdslLineConfEntry 21 }

gxdslLineEtherTrafficPMCollectEnable OBJECT-TYPE
       SYNTAX       INTEGER
                      {
                      enabled(1),         
                      disabled(2)        
                      }
       ACCESS       read-write
       STATUS       mandatory
       DESCRIPTION
           "Defines whether performance monitoring and collection is enabled for the
            Ethernet Layer 2 related to this VDSL line.
           
             ALCATEL NOTE: THIS OBJECT IS ADDED TO THE IETF MIB FOR OMCI COMPLIANCE & 
             IN ORDER TO ALLOW FLEXIBLE LIMITATIONS ON PM COLLECTION TASK"

       DEFVAL  {2}

       ::= { gxdslLineConfEntry 22 }


gxdslLineSpIndex  OBJECT-TYPE
	SYNTAX 	SpIndex
	ACCESS	not-accessible
	STATUS	mandatory
	DESCRIPTION 
		"Each row is also indexed by a number that
		 contains the slot number and port number
		 within the ONT. 
           
             ALCATEL NOTE: THIS OBJECT IS ADDED TO THE xDSL MIB DUE TO THE 
DOUBLE INDEXING SCHEME THAT DOES NOT ALLOW THE USE 	                          OF STANDARD IF-TABLES TO FULL EXTENT "
	::= { gxdslLineConfEntry 23 }

gxdslLineAdminState OBJECT-TYPE
       SYNTAX       INTEGER
                      {
                      unLocked(1),         
                      locked(2)
                      }
       ACCESS       read-write
       STATUS       mandatory
       DESCRIPTION
           "Defines administrative state for the VDSL physical line.
           
             ALCATEL NOTE: THIS OBJECT IS ADDED TO THE XDSL MIB FOR OMCI COMPLIANCE & DUE TO THE
	 DOUBLE INDEXING SCHEME THAT DOES NOT ALLOW THE USE OF STANDARD IF-TABLES TO FULL EXTENT

	For ISAM4.0.10, this attribute is NOT SUPPORTED.  "

       DEFVAL  {1}

       ::= { gxdslLineConfEntry 24 }

 gxdslLineOpState OBJECT-TYPE
       SYNTAX       INTEGER
                      {
                      enabled(1),         
                      disabled(2)     
                      }
       ACCESS       read-only
       STATUS       mandatory
       DESCRIPTION
           "Reflects the operational state for the VDSL physical line.
           
             ALCATEL NOTE: THIS OBJECT IS ADDED TO THE XDSL MIB FOR OMCI COMPLIANCE & DUE TO THE
	DOUBLE INDEXING SCHEME THAT DOES NOT ALLOW THE USE OF STANDARD IF-TABLES TO FULL EXTENT

	For ISAM4.0.10, this attribute is NOT SUPPORTED. "

       ::= { gxdslLineConfEntry 25 }

gxdslLinePwrShedOverride  OBJECT-TYPE
 	SYNTAX  Boolean
 	ACCESS read-write
 	STATUS mandatory
 	DESCRIPTION 
  		"Allows setting as follows:
 
   	TRUE = 1 = port excluded from DSL class power shedding
   		FALSE = 0 = port included in DSL class power shedding
 
   		Default = 0 = FALSE

FGU4.4: THIS OBJECT IS ADDED TO THE XDSL MIB PER FTTU UNI MANAGEMENT REQUIREMENTS"
 

 ::= { gxdslLineConfEntry 26 } 
 
gxdslLineDscpPbitMapProfile OBJECT-TYPE
 	SYNTAX AsamProfilePointer
 	ACCESS read-write
 	STATUS mandatory
 	DESCRIPTION
  		" This object is used to reference the appropriate
    		DSCP-to-Pbit mapping profile (in the GPON MIB).
 
   		The value 0 means that the system wide defaults are used (See GPON MIB).
 
    		Modification is permitted (without having to ADMIN DOWN the UNI).
    		Default = 0 = meaning use system wide defaults. 

FGU4.4: THIS OBJECT IS ADDED TO THE XDSL MIB PER FTTU UNI MANAGEMENT REQUIREMENTS

For ISAM4.0.10, this attribute is NOT SUPPORTED. "

 ::= { gxdslLineConfEntry 27 }


gxdslLineRowStatus OBJECT-TYPE
       SYNTAX       RowStatus
       ACCESS       read-write
       STATUS       mandatory
       DESCRIPTION
           "This object is used to create a new row or modify or
           delete an existing row in this table.

FGU4.4: THIS OBJECT IS ADDED TO THE XDSL MIB PER FTTU UNI MANAGEMENT REQUIREMENTS.


For ISAM4.0.10, this attribute is NOT SUPPORTED.  "

::= { gxdslLineConfEntry 28 }

gxdslLineDpboProfileNbr OBJECT-TYPE
        SYNTAX          AsamProfilePointer
        ACCESS          read-write
        STATUS          mandatory
        DESCRIPTION     
        "This object identifies the row of the gxdslDpboProfileTable
         which defines the valid profile for the interface.

         ALCATEL NOTE:
             ACCESS:   NA                  USAGE:    OPT
             PERSIST:  YES                 INSRVMOD: YES
             RANGE:    0..50               DEFVALUE: NA
             UNITS:    NA                  SPARSE:   NA
             DESCR:    NA
        "
::= {gxdslLineConfEntry 29}

gxdslLineRtxUpstreamProfileNbr OBJECT-TYPE
        SYNTAX          AsamProfilePointer
        ACCESS          read-write
        STATUS          mandatory
        DESCRIPTION     
        "This object identifies the row of the gxdslRtxProfileTable in upstream direction which defines the valid profile for the interface.

        ALCATEL NOTE:
             ACCESS:   NA                  USAGE:    OPT
             PERSIST:  YES                 INSRVMOD: YES
             RANGE:    0..128              DEFVALUE: NA
             UNITS:    NA                  SPARSE:   NA
             DESCR:    NA

        Introduced in ISAM5.3.01 MIB for MIB readiness
        For GPON - SUPPORTED as of ISAM5.3.02
        For XG-PON1 - NOT SUPPORTED as of ISAM5.3.02
        For NG-PON2 - NOT SUPPORTED as of ISAM5.3.02
        "
::= {gxdslLineConfEntry 30}

gxdslLineRtxDownstreamProfileNbr OBJECT-TYPE
        SYNTAX          AsamProfilePointer
        ACCESS          read-write
        STATUS          mandatory
        DESCRIPTION     
        "This object identifies the row of the gxdslRtxProfileTable in downstream direction which defines the valid profile for the interface.

        ALCATEL NOTE:
             ACCESS:   NA                  USAGE:    OPT
             PERSIST:  YES                 INSRVMOD: YES
             RANGE:    0..128              DEFVALUE: NA
             UNITS:    NA                  SPARSE:   NA
             DESCR:    NA

        Introduced in ISAM5.3.01 MIB for MIB readiness
        For GPON - SUPPORTED as of ISAM5.3.02
        For XG-PON1 - NOT SUPPORTED as of ISAM5.3.02
        For NG-PON2 - NOT SUPPORTED as of ISAM5.3.02
        "
::= {gxdslLineConfEntry 31}

-- gxdslLineConfTableEndMarker       OBJECT-TYPE
--         SYNTAX          INTEGER
--        ACCESS          read-only
--        STATUS          mandatory
--        DESCRIPTION     
--        " This object is a dummy OID used to mark the end of xdslLineConfTable,
--           so that GET-NEXT  has a clean break before wandering off into xdslLineOperDataTable.
--
--	Attribute is commented out as of ISAM4.0.10 "
-- ::= {gxdslLineConfTable 2}


gxdslLineOperDataTable   OBJECT-TYPE
        SYNTAX          SEQUENCE OF GxdslLineOperDataEntry
        ACCESS          not-accessible
        STATUS          mandatory
        DESCRIPTION     
        "The xdsl line operational data table.

         ALCATEL NOTE:
             TABLESIZE: DEP [number of XDSL lines]                   
             DESCR:     NA                  
        "
::= {gxdslLineCurrent 1}

gxdslLineOperDataEntry   OBJECT-TYPE
        SYNTAX          GxdslLineOperDataEntry                   
        ACCESS          not-accessible
        STATUS          mandatory
        DESCRIPTION     
        "An entry in the xdsl line operational data table.

         Row creation : Entries for all XDSL lines belonging to a board are 
                        created when the board becomes operational.
         Row deletion : Entries for all XDSL lines belonging to a board are 
                        deleted when the board becomes unavailable.
        "
        INDEX          {ifIndex, gxdslLineOperSpIndex}
::= {gxdslLineOperDataTable 1}

GxdslLineOperDataEntry ::=
        SEQUENCE {
            gxdslLineRelCapacityOccupationUpstream     INTEGER,
            gxdslLineNoiseMarginUpstream               INTEGER,
            gxdslLineOutputPowerDownstream             INTEGER,
            gxdslLineSignalAttenuationUpstream         INTEGER,
            gxdslLineLoopAttenuationUpstream           INTEGER,
            gxdslLineActualOpMode                      GOpModeType, 
            gxdslLineXtucOpModeCapabilities            GOpModeType,
            gxdslLineLastTxStateDownstream             INTEGER,
            gxdslLineActualPsdDownstream               INTEGER,
            gxdslLinePowerMgtState                     INTEGER,
            gxdslLinePerBandLoopAttenuationUpstream    GPerBandOperDataType,
            gxdslLinePerBandSignalAttenuationUpstream  GPerBandOperDataType,
            gxdslLinePerBandNoiseMarginUpstream        GPerBandOperDataType,
            gxdslLineHighestFrequencyUpstream          INTEGER,
            gxdslLineElectricalLengthUsed              INTEGER,
            gxdslLineTimingAdvanceCorrected            INTEGER,
            gxdslLineActualTpsTcMode                   GTpsTcModeType,
            gxdslLineOperSpIndex                       SpIndex,
	    gxdslLineActualVirtualNoiseSnrmModeUpstream  GSnrmMode
        }

gxdslLineRelCapacityOccupationUpstream  OBJECT-TYPE
        SYNTAX          INTEGER
        ACCESS          read-only
        STATUS          mandatory
        DESCRIPTION     
        "This parameter represents the ratio of the actual line bitrate over
         the maximum attainable line bitrate in the upstream direction. The
         line rate is equal to the net data rate rate plus all overhead
         information (framing overhead, Reed Solomon overhead, Trellis 
         overhead).
         When the modem is not in showtime, then the value measured in
         preceeding showtime session is returned. The value is fixed to 100%
         in case of activation failure when for that particular direction a
         bitrate higher than the attainable bitrate has been requested.
         When no data is available (e.g. before first showtime) value 0
         is used.
         Range is 0 to 100% with a granularity of 1 %.

         ALCATEL NOTE:
             ACCESS:   NA                  USAGE:    NA
             PERSIST:  NO                  INSRVMOD: NA
             RANGE:    0..100              DEFVALUE: 0
             UNITS:    percent             SPARSE:   NA
             DESCR:    NA"
::= {gxdslLineOperDataEntry 1}

gxdslLineNoiseMarginUpstream            OBJECT-TYPE
        SYNTAX          INTEGER
        ACCESS          read-only
        STATUS          mandatory
        DESCRIPTION     
        "This parameter indicates the current noise margin for the upstream
         direction. When the modem is not in showtime this 
         object will have the previously measured value. 
         When no data is available (e.g. before first showtime) value 0
         is used.
         Range is -64 to 63 dB with a granularity of 0,1 dB.
         It is represented as 1/10 * xdslLineNoiseMarginUpstream.
         The special value 65535 indicates that the noise margin is out of
         range.

         ALCATEL NOTE:
             ACCESS:   NA                  USAGE:    NA
             PERSIST:  NO                  INSRVMOD: NA
             RANGE:    -640..630, 65535    DEFVALUE: 0
             UNITS:    dB / 10             SPARSE:   NA
             DESCR:    NA
        "
::= {gxdslLineOperDataEntry 2}

gxdslLineOutputPowerDownstream          OBJECT-TYPE
        SYNTAX          INTEGER
        ACCESS          read-only
        STATUS          mandatory
        DESCRIPTION     
        "This object gives the actual aggregate output power for the downstream 
         carriers. When the modem is not in showtime this object will have the
         previously measured value.
         When no data is available (e.g. before first showtime) value 0
         is used.
         Range is -31 to 31 dBm with a granularity of 0,1 dB.
         It is expressed as 1/10 * xdslLineOutputPowerDownstream .The special
         value 65535 indicates that the actual aggregate output power is out of
         range.

         ALCATEL NOTE:
             ACCESS:   NA                  USAGE:    NA
             PERSIST:  NO                  INSRVMOD: NA
             RANGE:    -310..310, 65535    DEFVALUE: 0
             UNITS:    dBm / 10            SPARSE:   NA
             DESCR:    NA
        "
::= {gxdslLineOperDataEntry 3}

gxdslLineSignalAttenuationUpstream      OBJECT-TYPE
        SYNTAX          INTEGER
        ACCESS          read-only
        STATUS          mandatory
        DESCRIPTION     
        "This object gives the difference in dB between the power measured at
         the near-end receiver and that transmitted from the far-end. The
         signal attenuation is measured over all data carriers and is updated
         during showtime.
         When the modem is not in showtime this object will have the value
         measured during the previous showtime session.
         When no data is available (e.g. before first showtime) value 0
         is used.
         It is represented as 1/10 * xdslLineSignalAttenuationUpstream, with
         a range of (0..127dB) and a granularity of 0.1 dB.The special 
         value 65535 indicates that the signal attenuation is out of range.

         ALCATEL NOTE:
             ACCESS:   NA                  USAGE:    NA
             PERSIST:  NO                  INSRVMOD: NA
             RANGE:    0..1270, 65535      DEFVALUE: 0
             UNITS:    dB / 10             SPARSE:   NA
             DESCR:    NA
        "
::= {gxdslLineOperDataEntry 4}

gxdslLineLoopAttenuationUpstream        OBJECT-TYPE
        SYNTAX          INTEGER
        ACCESS          read-only
        STATUS          mandatory
        DESCRIPTION     
        "This object gives the difference in dB between the power 
         measured at the near-end receiver and that transmitted from the
         far-end over all sub-carriers. The loop attenuation is measured at
         initialization and is not updated during showtime.
         When the modem is not in showtime this object will have the value
         measured during the previous showtime session.
         When no data is available (e.g. before first showtime) value 0
         is used.
         It is represented as 1/10 * xdslLineLoopAttenuationUpstream, with
         a range of (0..127dB) and a granularity of 0.1 dB.The special
         value 65535 indicates that the loop attenuation is out of range.

         ALCATEL NOTE:
             ACCESS:   NA                  USAGE:    NA
             PERSIST:  NO                  INSRVMOD: NA
             RANGE:    0..1270, 65535      DEFVALUE: 0
             UNITS:    dB / 10             SPARSE:   NA
             DESCR:    NA
        "
::= {gxdslLineOperDataEntry 5}

gxdslLineActualOpMode    OBJECT-TYPE
        SYNTAX          GOpModeType
        ACCESS          read-only
        STATUS          mandatory
        DESCRIPTION 
        "This variable consists of a bitmap which represents the operational 
         mode of the ATU-C. In case the modem is not operational this object 
         represents the operational mode of the most recent initialization 
         procedure.
         If the modem has not been initialized yet, this object will have the
         value 0. It uses the same coding as defined in xdslLineOpMode.

         ALCATEL NOTE:
             ACCESS:   NA                  USAGE:    NA
             PERSIST:  NO                  INSRVMOD: NA
             RANGE:    NA
             DEFVALUE: '00 00 00 00 00 00 00 00 
                        00 00 00 00 00 00 00 00'H
             UNITS:    NA                  SPARSE:   NA
             DESCR:    NA
        "
::= {gxdslLineOperDataEntry 6}

gxdslLineXtucOpModeCapabilities         OBJECT-TYPE
        SYNTAX          GOpModeType
        ACCESS          read-only
        STATUS          mandatory
        DESCRIPTION 
        "This variable consists of a bitmap which represents the operational
         modes enabled at the XTU-C. It uses the same coding as defined in
         gxdslLineOpMode.The octet 9 is not supported and it's value will
         always be 0.

         ALCATEL NOTE:
             ACCESS:   NA                  USAGE:    NA
             PERSIST:  NO                  INSRVMOD: NA
             RANGE:    NA 
             DEFVALUE: '00 00 00 00 00 00 00 00 
                        00 00 00 00 00 00 00 00'H
             UNITS:    NA                  SPARSE:   NA
             DESCR:    NA

         FGU4.4:  THIS OBJECT IS NOT SUPPORTED
         For GPON - SUPPORTED except otect 9 as of ISAM5.3.02
         For XG-PON1 - NOT SUPPORTED as of ISAM5.3.02
         For NG-PON2 - NOT SUPPORTED as of ISAM5.3.02
        "
::= {gxdslLineOperDataEntry 7}

gxdslLineLastTxStateDownstream     OBJECT-TYPE
        SYNTAX          INTEGER
        ACCESS          read-only
        STATUS          mandatory
        DESCRIPTION     
        "This object gives the last successful transmitted initialisation state
         as defined in G.997.1. It is reported for ADSL2 modes in Loop
         Diagnostics State only.
         ALCATEL NOTE:
             ACCESS:   NA                  USAGE:    NA
             PERSIST:  NA                  INSRVMOD: NA
             RANGE:    NA                  DEFVALUE: NA
             UNITS:    NA                  SPARSE:   NA
             DESCR:    NA
         
         FGU4.4 This object is not supported.
         For GPON - SUPPORTED as of ISAM5.3.02
         For XG-PON1 - NOT SUPPORTED as of ISAM5.3.02
         For NG-PON2 - NOT SUPPORTED as of ISAM5.3.02
        "
::= {gxdslLineOperDataEntry 8}

gxdslLineActualPsdDownstream            OBJECT-TYPE
        SYNTAX          INTEGER
        ACCESS          read-only
        STATUS          mandatory
        DESCRIPTION     
        "This object gives the average transmit power spectrum density over the
         used carriers in the downstream direction as measured at the U-C
         reference point.
         When the modem is not in showtime this object will have the value
         measured during the previous showtime session.
         When no data is available (e.g. before first showtime) value 0
         is used.
         Range is -95.5 dBm/Hz to 0 dBm/Hz with 0,1 dB steps. The actual PSD is
         represented as 1/10 * xdslLineActualPsdDownstream.The special value
         65535 indicates that the actual PSD is out of range.

         ALCATEL NOTE:
             ACCESS:   NA                  USAGE:    NA
             PERSIST:  NO                  INSRVMOD: NA
             RANGE:    -955..0, 65535      DEFVALUE: 0
             UNITS:    dBm/Hz * 1/10       SPARSE:   NA
             DESCR:    NA
        "
::= {gxdslLineOperDataEntry 9}

gxdslLinePowerMgtState   OBJECT-TYPE
        SYNTAX          INTEGER {
                            l0 (1),
                            l1 (2),
                            l2 (3),
                            l3 (4)
                        }
        ACCESS          read-only
        STATUS          mandatory
        DESCRIPTION     
        "This object indicates the actual power management state of the line:
         - l0 (Synchronized): full transmission (i.e. showtime)
         - l1 (Low power): there is transmission on the line but the downstream
           net data rate is reduced. This state is NOT supported (replaced by
           L2 in standards).
         - l2 (Low power): there is transmission on the line but the downstream
           net data rate is reduced
         - l3 (No power): there is no transmission on the line

         ALCATEL NOTE:
             ACCESS:   NA                  USAGE:    NA
             PERSIST:  NO                  INSRVMOD: NA
             RANGE:    NA                  DEFVALUE: l3
             UNITS:    NA                  SPARSE:   NA
             DESCR:    NA
        "
::= {gxdslLineOperDataEntry 10}

gxdslLinePerBandLoopAttenuationUpstream           OBJECT-TYPE
        SYNTAX          GPerBandOperDataType
        ACCESS          read-only
        STATUS          mandatory
        DESCRIPTION
        "This object indicates loop attenuation for each upstream band 
         (including optional band) in case of VDSL2.
         It is represented as 1/10 * xdslLinePerBandLoopAttenuationUpstream,
         for each band with a range of (0..127dB) and a granularity of 0.1 dB.
         Max value is used to indicate that no Opdata is available for the
         corresponding band.
         OCTETS (0,1) represent value for band 0, coded as an integer in the
         range 0.. 1270. The special value 65535 indicates the attenuation
         per band is out of range to be represented.The value is defined as
         MSB-LSB (big-endian).
         OCTETS (2*N,2*N+1) represent value for band N, coded as an integer in
         the range 0.. 1270. The special value 65535 indicates the attenuation
         per band is out of range to be represented.The value is defined as
         MSB-LSB (big-endian).
         Maximum value for N is 4.

         ALCATEL NOTE:
             ACCESS:   NA                  USAGE:    NA
             PERSIST:  NO                  INSRVMOD: NA
             RANGE:    NA
             DEFVALUE: 'FF FF FF FF FF FF FF FF FF FF'H
             UNITS:    NA                  SPARSE:   NA
             DESCR:    NA
        "
::= {gxdslLineOperDataEntry 11}

gxdslLinePerBandSignalAttenuationUpstream         OBJECT-TYPE
        SYNTAX          GPerBandOperDataType
        ACCESS          read-only
        STATUS          mandatory
        DESCRIPTION
        "This object indicates signal attenuation for each upstream band 
         (including optional band) in case of VDSL2.
         It is represented as 1/10 * xdslLinePerBandSignalAttenuationUpstream,
         for each band with a range of (0..127dB) and a granularity of 0.1 dB.
         Max value is used to indicate that no Opdata is available for the
         corresponding band.
         OCTETS (0,1) represent value for band 0, coded as an integer in the
         range 0.. 1270. The special value 65535 indicates the attenuation
         per band is out of range to be represented.The value is defined as
         MSB-LSB (big-endian).
         OCTETS (2*N,2*N+1) represent value for band N, coded as an integer in
         the range 0.. 1270. The special value 65535 indicates the attenuation
         per band is out of range to be represented.The value is defined as 
         MSB-LSB (big-endian).
         Maximum value for N is 4.

         ALCATEL NOTE:
             ACCESS:   NA                  USAGE:    NA
             PERSIST:  NO                  INSRVMOD: NA
             RANGE:    NA
             DEFVALUE: 'FF FF FF FF FF FF FF FF FF FF'H
             UNITS:    NA                  SPARSE:   NA
             DESCR:    NA
        "
::= {gxdslLineOperDataEntry 12}

gxdslLinePerBandNoiseMarginUpstream     OBJECT-TYPE
        SYNTAX          GPerBandOperDataType
        ACCESS          read-only
        STATUS          mandatory
        DESCRIPTION
        "This object indicates noise margin for each upstream band (including 
         optional band in case of VDSL2.
         It is represented as 1/10 * xdslLinePerBandNoiseMarginUpstream,
         for each band with a range of (-64..63dB) and a granularity of 0.1 dB.
         Max value is used to indicate that no Opdata is available for the
         corresponding band.
         OCTETS (0,1) represent value for band 0, coded as an integer in the
         range 0.. 1270(0 means -64dB and 1270 means 63dB).The special 
         value 65535 indicates the noise margin per band is out of range 
         to be represented.The value is defined as MSB-LSB (big-endian).
         OCTETS (2*N,2*N+1) represent value for band N, coded as an integer in 
         the range 0.. 1270(0 means -64dB and 1270 means 63dB).The special 
         value 65535 indicates the noise margin per band is out of range 
         to be represented.The value is defined as MSB-LSB (big-endian).
         Maximum value for N is 4.

         ALCATEL NOTE:
             ACCESS:   NA                  USAGE:    NA
             PERSIST:  NO                  INSRVMOD: NA
             RANGE:    NA
             DEFVALUE: 'FF FF FF FF FF FF FF FF FF FF'H
             UNITS:    NA                  SPARSE:   NA
             DESCR:    NA
        "
::= {gxdslLineOperDataEntry 13}

gxdslLineHighestFrequencyUpstream       OBJECT-TYPE
        SYNTAX          INTEGER
        ACCESS          read-only
        STATUS          mandatory
        DESCRIPTION
        "This object indicates the highest carrier frequency used
         in the upstream direction in case of VDSL2 and G.Fast.

         ALCATEL NOTE:
             ACCESS:   NA                  USAGE:    NA
             PERSIST:  NO                  INSRVMOD: NA
             RANGE:    NA                  DEFVALUE: 0
             UNITS:    kHz                 SPARSE:   NA
             DESCR:    NA
        
         FGU4.4:  THIS OBJECT IS NOT SUPPORTED
         For GPON - SUPPORTED as of ISAM5.3.02
         For XG-PON1 - NOT SUPPORTED as of ISAM5.3.02
         For NG-PON2 - NOT SUPPORTED as of ISAM5.3.02
        "
::= {gxdslLineOperDataEntry 14}

gxdslLineElectricalLengthUsed           OBJECT-TYPE
        SYNTAX          INTEGER
        ACCESS          read-only
        STATUS          mandatory
        DESCRIPTION
        "This object indicates the Line Electrical Length actually used
         by XTU-C when mode is VDSL2.
         Range: 0 to 127.5 dB @ 1MHz , with 0.5 dB steps.
         Integer range: 0..255, actual value * 2.

         ALCATEL NOTE:
             ACCESS:   NA                  USAGE:    NA
             PERSIST:  NO                  INSRVMOD: NA
             RANGE:    0..255              DEFVALUE: 0
             UNITS:    dB/2 @ 1Mhz         SPARSE:   NA
             DESCR:    NA
        "
::= {gxdslLineOperDataEntry 15}

gxdslLineTimingAdvanceCorrected         OBJECT-TYPE
        SYNTAX          INTEGER
        ACCESS          read-only
        STATUS          mandatory
        DESCRIPTION
        "This object defines the timing advance of transmitted symbol with 
         respect to the received symbol when mode is VDSL-2.  Near end value
         corresponds to the value corrected by XTU-C.
         Range: -250000..250000 ns in steps of 10 ns.
         Integer range: -25000..25000 (actual value / 10)

         ALCATEL NOTE:
             ACCESS:   NA                  USAGE:    NA
             PERSIST:  NO                  INSRVMOD: NA
             RANGE:    -25000..25000       DEFVALUE: 0
             UNITS:    ns * 10             SPARSE:   NA
             DESCR:    NA
        
         FGU4.4:  THIS OBJECT IS NOT SUPPORTED "
::= {gxdslLineOperDataEntry 16}

gxdslLineActualTpsTcMode                OBJECT-TYPE
        SYNTAX          GTpsTcModeType
        ACCESS          read-only
        STATUS          mandatory
        DESCRIPTION
        "This object indicates the TpsTcMode that is actually used.

         ALCATEL NOTE:
             ACCESS:   NA                  USAGE:    NA
             PERSIST:  NO                  INSRVMOD: NA
             RANGE:    atm,ptm             DEFVALUE: ptm
             UNITS:    NA                  SPARSE:   NA
             DESCR:    NA
        "
::= {gxdslLineOperDataEntry 17}

gxdslLineOperSpIndex  OBJECT-TYPE
	SYNTAX 	SpIndex
	ACCESS	not-accessible
	STATUS	mandatory
	DESCRIPTION 
		"Each row is also indexed by a number that
		 contains the slot number and port number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslLineOperDataEntry 18 }

gxdslLineActualVirtualNoiseSnrmModeUpstream    OBJECT-TYPE
        SYNTAX          GSnrmMode
        ACCESS          read-only
        STATUS          mandatory
        DESCRIPTION     
        "This object specifies the upstream mode of the  Virtual Noise Signal
         to Noise Ratio Margin, that is actually being used.
          snrmmode1: virtual noise is disabled.
          snrmmode2: virtual noise is enabled, using gvdsl2VirtualNoisePsdUpstream
                     as the transmitter referred noise.
          snrmmode3: virtual noise is enabled, using gvdsl2VirtualNoisePsdUpstream
                     as the receiver referred noise.

         ALCATEL NOTE:
             ACCESS:   NA                  USAGE:    NA
             PERSIST:  NA                  INSRVMOD: NA
             RANGE:    NA                  DEFVALUE: snrmMode1
             UNITS:    NA                  SPARSE:   NA
             DESCR:    NA
        "   
    ::= { gxdslLineOperDataEntry 19 }

-- gxdslLineOperDataTableEndMarker       OBJECT-TYPE
--        SYNTAX          INTEGER
--        ACCESS          read-only
--        STATUS          mandatory
--        DESCRIPTION     
--        " This object is a dummy OID used to mark the end of xdslLineOperDataTable,
--           so that GET-NEXT  has a clean break before wandering off into xdslLineCarrierDataTable.
--
-- 	 Attribute is commented out as of ISAM4.0.10 "
-- ::= {gxdslLineOperDataTable 2}

gxdslLineCarrierDataTable               OBJECT-TYPE
        SYNTAX          SEQUENCE OF GxdslLineCarrierDataEntry
        ACCESS          not-accessible
        STATUS          mandatory
        DESCRIPTION     
        "The xdsl line carrier data table.

         ALCATEL NOTE:
             TABLESIZE: DEP [number of XDSL lines]                    
             DESCR:     NA                  
        "
::= {gxdslLineCurrent 2}

gxdslLineCarrierDataEntry               OBJECT-TYPE
        SYNTAX          GxdslLineCarrierDataEntry                   
        ACCESS          not-accessible
        STATUS          mandatory
        DESCRIPTION     
        "An entry in the xdsl line carrier data table.

         Row creation : Entries for all XDSL lines belonging to a board are 
                        created when the board becomes operational.
         Row deletion : Entries for all XDSL lines belonging to a board are 
                        deleted when the board becomes unavailable.
        "
        INDEX          {ifIndex, gxdslLineCarrierSpIndex}
::= {gxdslLineCarrierDataTable 1}

GxdslLineCarrierDataEntry ::=
        SEQUENCE {
            gxdslLineCarrierLoadDownstream             OCTET STRING,
            gxdslLineCarrierGainDownstream             OCTET STRING,
            gxdslLineCarrierTssDownstream              OCTET STRING,
            gxdslLineCarrierSnrUpstream                OCTET STRING,
            gxdslLineCarrierQlnUpstream                OCTET STRING,
            gxdslLineCarrierHlinUpstream               OCTET STRING,
            gxdslLineCarrierHlogUpstream               OCTET STRING,
            gxdslLineCarrierSpacingDownstream          GCarrierSpacingType,
            gxdslLineCarrierTxPsdDownstream            OCTET STRING,
            gxdslLineCarrierGroupTxPsd                 GSubCarrierGroupSizeType,
            gxdslLineCarrierGroupLoad                  GSubCarrierGroupSizeType,
            gxdslLineCarrierGroupGain                  GSubCarrierGroupSizeType,
            gxdslLineCarrierGroupTss                  GSubCarrierGroupSizeType,
            gxdslLineCarrierGroupSnr                   GSubCarrierGroupSizeType,
            gxdslLineCarrierGroupQln                   GSubCarrierGroupSizeType,
            gxdslLineCarrierGroupHLin                  GSubCarrierGroupSizeType,
            gxdslLineCarrierGroupHLog                  GSubCarrierGroupSizeType,
            gxdslLineCarrierSpIndex                    SpIndex
         }

gxdslLineCarrierLoadDownstream          OBJECT-TYPE
        SYNTAX          OCTET STRING
        ACCESS          read-only
        STATUS          mandatory
        DESCRIPTION     
        "This object represents the bit load distribution i.e. the number of
         bits per carrier group over the downstream passband.
         When the modem is not in showtime this object will have the previously
         measured value.
         When the data are not available because the measurement is not
         completed, not enabled or not supported, an empty string will be
         returned.
         The XDSL downstream passband is composed of one or more bands (maximum
         5,including VDSL optional band). Each carrier can carry up to 15 bits.
         The carrier load is coded as a bitmap defined as follows:
         OCTETS 0,1: INTEGER (0..4096), index of the start carrier group of the
         first downstream band. The value is defined as MSB-LSB (big-endian).
         OCTETS 2,3: INTEGER (0..4096), index of the stop carrier group of the
         first downstream band. The value is defined as MSB-LSB (big-endian).
         OCTET 4: contains the bit load of the first two carrier groups of the
         band.
         The load of the first carrier group uses the most significant 4 bits
         nibble.
         Range is 0-15 bits per carrier group, with a granularity of 1
         bit/carrier group.
         OCTETS 5..L: and so on, up to the last carrier group of the first
         downstream band. The last nibble of OCTET L is set to 0x0 if not used.
         OCTETS L+1..M: contain the start/stop carrier groups and the carrier
         load of the second downstream band when available.
         OCTETS M+1..N: contain the start/stop carrier groups and the carrier
         load of the third downstream band when available.
         OCTETS N+1..P: contain the start/stop carrier groups and the carrier
         load of the fourth downstream band when available.
         OCTETS P+1..Q: contain the start/stop carrier groups and the carrier
         load of the fifth downstream band when available.

         ALCATEL NOTE:
             ACCESS:   NA                  USAGE:    NA
             PERSIST:  NO                  INSRVMOD: NA
             RANGE:    0..4117             DEFVALUE: ''H
             UNITS:    octets              SPARSE:   NA
             DESCR:    NA
        "
::= {gxdslLineCarrierDataEntry 1}

gxdslLineCarrierGainDownstream          OBJECT-TYPE
        SYNTAX          OCTET STRING
        ACCESS          read-only
        STATUS          mandatory
        DESCRIPTION     
        "This object provides the gain allocation (i.e. gi) per carrier group 
         over the downstream passband.
         When the modem is not in showtime this object will have the previously
         measured value.
         When the data are not available because the measurement is not
         completed, not enabled or not supported, an empty string will be
         returned.
         The XDSL downstream passband is composed of one or more bands (maximum
         5, including VDSL optional band). The gain has a range of 
         approximately 0 - 8, in steps of 1/512.
         The gain value is represented as gi/512 on a linear scale with gi
         a 12 bits unsigned integer in the 0 to 4095 range given by the 12 LSB
         bits of a 2 bytes integer.
         The carrier gain allocation is coded as a bitmap defined as
         follows:
         OCTETS 0,1: INTEGER (0..4096), index of the start carrier group of the
         first downstream band. The value is defined as MSB-LSB (big-endian).
         OCTETS 2,3: INTEGER (0..4096), index of the stop carrier group of the
         first downstream band. The value is defined as MSB-LSB (big-endian).
         OCTETS 4,5: INTEGER, contains the gain of the first carrier group of
         the band (start carrier group).
         OCTETS 6..L: and so on until the last carrier group of the first
         downstream band (stop carrier group).
         OCTETS L+1..M: contain the start/stop carrier groups and the carrier
         gain of the second downstream band when available.
         OCTETS M+1..N: contain the start/stop carrier groups and the carrier
         gain of the third downstream band when available.
         OCTETS N+1..P: contain the start/stop carrier groups and the carrier
         gain of the fourth downstream band when available.
         OCTETS P+1..Q: contain the start/stop carrier groups and the carrier
         gain of the fifth downstream band when available.

         ALCATEL NOTE:
             ACCESS:   NA                  USAGE:    NA
             PERSIST:  NO                  INSRVMOD: NA
             RANGE:    0..8214             DEFVALUE: ''H
             UNITS:    octets              SPARSE:   NA
             DESCR:    NA
         "
::= {gxdslLineCarrierDataEntry 2}

gxdslLineCarrierTssDownstream     OBJECT-TYPE
        SYNTAX                    OCTET STRING
        ACCESS                    read-only
        STATUS                    mandatory
        DESCRIPTION     
         "This object provides the Transmit Spectrum Shaping parameters
         (i.e. tssi) for the downstream direction.
         Its definition is for further study.
         ALCATEL NOTE:
             ACCESS:   NA                  USAGE:    NA
             PERSIST:  NA                  INSRVMOD: NA
             RANGE:    NA                  DEFVALUE: NA
             UNITS:    NA                  SPARSE:   NA
             DESCR:    This object is not supported.
         
         FGU4.4:  THIS OBJECT IS NOT SUPPORTED "
::= {gxdslLineCarrierDataEntry 3}

gxdslLineCarrierSnrUpstream             OBJECT-TYPE
        SYNTAX          OCTET STRING
        ACCESS          read-only
        STATUS          mandatory
        DESCRIPTION     
        "This object provides the Signal to Noise Ratio per carrier group over
         the upstream passband.
         When the modem is not in showtime this object will have the previously
         measured value.
         When the data are not available because the measurement is not
         completed, not enabled or not supported, an empty string will be
         returned.
         The XDSL upstream passband is composed of one or more bands (maximum
         5, including VDSL optional band). The SNR has a range from -32 to 95
         dB in steps of 0.5 dB.
         It is represented as SNRi = -32 + snri/2, with snri an 8 bit
         unsigned integer in the range 0 to 254.
         The special value 255 indicates that no measurement is available for
         the carrier or that the measurement is out of range.
         The carrier snrs are coded as a bitmap defined as follows:
         OCTETS 0,1: INTEGER, contains the number of symbols used to
         measure the data. The value is defined as MSB-LSB (big-endian).
         OCTETS 2,3: INTEGER (0..4096), index of the start carrier group of the
         first upstream band. The value is defined as MSB-LSB (big-endian).
         OCTETS 4,5: INTEGER (0..4096), index of the stop carrier group of the
         first upstream band. The value is defined as MSB-LSB (big-endian).
         OCTETS 6: INTEGER, contains the snr of the first carrier group of the
         band (start carrier group).
         OCTETS 7..L: and so on until the last carrier group of the first
         upstream band (stop carrier group).
         OCTETS L+1..M: contain the start/stop carrier groups and the carrier
         snr of the second upstream band when available.
         OCTETS M+1..N: contain the start/stop carrier groups and the carrier
         snr of the third upstream band when available.
         OCTETS N+1..P: contain the start/stop carrier groups and the carrier
         snr of the fourth upstream band when available.
         OCTETS P+1..Q: contain the start/stop carrier groups and the carrier
         snr of the fifth upstream band when available.

         ALCATEL NOTE:
             ACCESS:   NA                  USAGE:    NA
             PERSIST:  NO                  INSRVMOD: NA
             RANGE:    0..4119             DEFVALUE: ''H
             UNITS:    octets              SPARSE:   NA
             DESCR:    NA "
::= {gxdslLineCarrierDataEntry 4}

gxdslLineCarrierQlnUpstream             OBJECT-TYPE
        SYNTAX          OCTET STRING
        ACCESS          read-only
        STATUS          mandatory
        DESCRIPTION     
        "This object provides the Quiet Line Noise measurement (QLN) per
         carrier group over the upstream passband.
         When the data are not available because the measurement is not
         completed, not enabled or not supported, an empty string will be
         returned.
         The XDSL upstream passband is composed of one or more bands (maximum
         5, including VDSL optional band). The QLN has a range from -150 dBm/Hz
         to -23 dBm/Hz in steps
         of 0.5 dB. It is represented as QLNi = -23 - qlni/2, with qlni an
         8 bit unsigned integer in the range 0 to 254.
         The special value 255 indicates that no measurement is available for
         the carrier or that the measurement is out of range.
         The carrier qlns are coded as a bitmap defined as follows:
         OCTETS 0,1: INTEGER, contains the number of symbols used to
         measure the data. The value is defined as MSB-LSB (big-endian).
         OCTETS 2,3: INTEGER (0..4096), index of the start carrier group of the
         first upstream band. The value is defined as MSB-LSB (big-endian).
         OCTETS 4,5: INTEGER (0..4096), index of the stop carrier group of the
         first upstream band. The value is defined as MSB-LSB (big-endian).
         OCTETS 6: INTEGER, contains the qln of the first carrier group of the
         band (start carrier group).
         OCTETS 7..L: and so on until the last carrier group of the first
         upstream band (stop carrier group).
         OCTETS L+1..M: contain the start/stop carrier groups and the carrier
         qln of the second downstream band when available.
         OCTETS M+1..N: contain the start/stop carrier groups and the carrier
         qln of the third upstream band when available.
         OCTETS N+1..P: contain the start/stop carrier groups and the carrier
         qln of the fourth upstream band when available.
         OCTETS P+1..Q: contain the start/stop carrier groups and the carrier
         qln of the fifth upstream band when available.

         ALCATEL NOTE:
             ACCESS:   NA                  USAGE:    NA
             PERSIST:  NO                  INSRVMOD: NA
             RANGE:    0..4119             DEFVALUE: ''H
             UNITS:    octets              SPARSE:   NA
             DESCR:    NA "
::= {gxdslLineCarrierDataEntry 5}

gxdslLineCarrierHlinUpstream            OBJECT-TYPE
        SYNTAX          OCTET STRING
        ACCESS          read-only
        STATUS          mandatory
        DESCRIPTION      
        "This object provides the channel characteristics function complex
         values in linear scale for each carrier group over the upstream
         passband.
         When the data are not available because the measurement is not
         completed, not enabled or not supported, an empty string will be
         returned.
         The XDSL upstream passband is composed of one or more bands (maximum
         5, including VDSL optional band ).
         HLIN has a range of approximately +6 dB to -90 dB, with a granularity
         of 2^-15. The Hlin is represented as
         HLINi = (scale/2^15)*((ai+j*bi)/2^15),
         with ai and bi 2 bytes signed integers in the range -32767 to 32767.
         The special value -32768 indicates that no measurement is available
         for the carrier or that the measurement is out of range.
         The scale factor is a 2 bytes unsigned integer. The scale factor
         must be chosen such that:
         max(|Ai|,|Bi|) over all i is equal to 2^15-1, i.e. over all carriers
         of the XDSL band(s) of the corresponding direction.

         The carrier HLINs are coded as a bitmap defined as follows:
         OCTETS 0,1: INTEGER, contains the number of symbols used to
         measure the data. The value is defined as MSB-LSB (big-endian).
         OCTETS 2,3: INTEGER(0..65535), contains the scale factor to apply to
         the hlin values, over the upstream band(s).
         The value is defined as MSB-LSB (big-endian).
         OCTETS 4,5: INTEGER (0..4096), index of the start carrier group of the
         first upstream band. The value is defined as MSB-LSB (big-endian).
         OCTETS 6,7: INTEGER (0..4096), index of the stop carrier group of the
         first upstream band. The value is defined as MSB-LSB (big-endian).
         OCTETS 8,9: SIGNED INTEGER , contains the ai for the first carrier
         group of the band (start carrier group).
         The value is defined as MSB-LSB (big-endian).
         OCTETS 10,11: SIGNED INTEGER , contains the bi for the first carrier
         group of the band (start carrier group). 
         The value is defined as MSB-LSB (big-endian).
         OCTETS 12..L: ai and bi for the next carrier group and so on until the 
         last carrier group of the first upstream band (stop carrier group).
         OCTETS L+1..M: contain the start/stop carrier groups and the HLIN ai
         and bi of the second upstream band when available.
         OCTETS M+1..N: contain the start/stop carrier groups and the HLIN ai
         and bi of the third upstream band when available.
         OCTETS N+1..P: contain the start/stop carrier groups and the HLIN ai
         and bi of the fourth upstream band when available.
         OCTETS P+1..Q: contain the start/stop carrier groups and the HLIN ai
         and bi of the fifth upstream band when available.

         ALCATEL NOTE:
             ACCESS:   NA                  USAGE:    NA
             PERSIST:  NO                  INSRVMOD: NA
             RANGE:    0..8218             DEFVALUE: ''H
             UNITS:    octets              SPARSE:   NA
             DESCR:    NA "
::= {gxdslLineCarrierDataEntry 6}

gxdslLineCarrierHlogUpstream            OBJECT-TYPE
        SYNTAX          OCTET STRING
        ACCESS          read-only
        STATUS          mandatory
        DESCRIPTION     
        "This object provides the channel characteristics function real values
         in dB for each carrier group over the upstream passband.
         When the data are not available because the measurement is not
         completed, not enabled or not supported, an empty string will be
         returned.
         The XDSL upstream passband is composed of one or more bands (maximum
         5, including VDSL optional band).
         Hlog has a range of approximately +6 dB to -96 dB in steps of
         0.1 dB. The Hlog is represented as HLOGi = 6 - mi/10,
         with mi a 10 bits unsigned integer in the range 0 to 1022.
         The special value 1023 indicates that no measurement is available for
         the carrier or that the measurement is out of range.

         The carrier HLOGs are coded as a bitmap defined as follows:
         OCTETS 0,1: INTEGER, contains the number of symbols used to
         measure the data. The value is defined as MSB-LSB (big-endian).
         OCTETS 2,3: INTEGER (0..4096), index of the start carrier group of the
         first upstream band. The value is defined as MSB-LSB (big-endian).
         OCTETS 4,5: INTEGER (0..4096), index of the stop carrier group of the
         first upstream band. The value is defined as MSB-LSB (big-endian).
         OCTETS 6,7: INTEGER (0..1023), contains the HLOG mi of the first
         carrier group of the band (start carrier group).
         The value is defined as MSB-LSB (big-endian).
         OCTETS 8..L: mi for the next carrier group and so on until the last
         carrier group of the first upstream band (stop carrier group).
         OCTETS L+1..M: contain the start/stop carrier groups and the HLOG mi
         of the second upstream band when available.
         OCTETS M+1..N: contain the start/stop carrier groups and the HLOG mi
         of the third upstream band when available.
         OCTETS N+1..P: contain the start/stop carrier groups and the HLOG mi
         of the fourth upstream band when available.
         OCTETS P+1..Q: contain the start/stop carrier groups and the HLOG mi
         of the fifth upstream band when available.

         ALCATEL NOTE:
             ACCESS:   NA                  USAGE:    NA
             PERSIST:  NO                  INSRVMOD: NA
             RANGE:    0..8216             DEFVALUE: ''H
             UNITS:    octets              SPARSE:   NA
             DESCR:    NA "
::= {gxdslLineCarrierDataEntry 7}

gxdslLineCarrierSpacingDownstream       OBJECT-TYPE
        SYNTAX          GCarrierSpacingType
        ACCESS          read-only
        STATUS          mandatory
        DESCRIPTION     
        "This object provides the actual carrier spacing used on the XDSL line 
         in the downstream direction:
          singleCarrierSpacing:  4.3125 kHz 
          doubleCarrierSpacing:  8.6250 kHz 
          halfCarrierSpacing:    2.15625 kHz 
          quarterCarrierSpacing: 1.078125 kHz

         ALCATEL NOTE:
             ACCESS:   NA                  USAGE:    NA
             PERSIST:  NO                  INSRVMOD: NA
             RANGE:    NA                  DEFVALUE: NA
             UNITS:    NA                  SPARSE:   NA
             DESCR:    NA
        "
::= {gxdslLineCarrierDataEntry 8}

gxdslLineCarrierTxPsdDownstream         OBJECT-TYPE
        SYNTAX          OCTET STRING
        ACCESS          read-only
        STATUS          mandatory
        DESCRIPTION
        "Provides the actual transmit PSD per carrier group over the
         downstream passband.
         When the modem is not in showtime this object will have the previously
         measured value.
         When the data are not available because the measurement is not
         completed, not enabled or not supported, an empty string will be
         returned.
         The XDSL downstream passband is composed of one or more bands (maximum
         5, including VDSL optional band). 
         The PSD has a range from -127 dBm/Hz to 0 dBm/Hz in steps of 0.5 dB.
         It is represented as PSDi = - psdi/2, with psdi an 8 bit
         unsigned integer in the range 0 to 254.
         The special value 255 indicates that no measurement is available for
         the carrier, the carrier is not loaded, or that the measurement is out
         of range.
         The carrier Tx PSD is coded as a bitmap defined as follows:
         OCTETS 0,1: INTEGER (0..4096), index of the start carrier group of the
         downstream band. The value is defined as MSB-LSB (big-endian).
         OCTETS 2,3: INTEGER (0..4096), index of the stop carrier group of the
         downstream band. The value is defined as MSB-LSB (big-endian).
         OCTET 4: INTEGER(0..255), PSD of the first carrier group of the band
         (start carrier group).
         OCTETS 5..L: and so on until the last carrier group of the first
         downstream band (stop carrier group).
         OCTETS L+1..M: contain the start/stop carrier groups and the carrier
         PSD of the second downstream band when available.
         OCTETS M+1..N: contain the start/stop carrier groups and the carrier
         PSD of the third downstream band when available.
         OCTETS N+1..P: contain the start/stop carrier groups and the carrier
         PSD of the fourth downstream band when available.
         OCTETS P+1..Q: contain the start/stop carrier groups and the carrier
         PSD of the fifth downstream band when available.

         ALCATEL NOTE:
             ACCESS:   NA                  USAGE:    NA
             PERSIST:  NO                  INSRVMOD: NA
             RANGE:    0..4117             DEFVALUE: ''H
             UNITS:    octets              SPARSE:   NA
             DESCR:    NA 
        
         FGU4.4: THIS OBJECT IS NOT SUPPORTED "
::= {gxdslLineCarrierDataEntry 9}

gxdslLineCarrierGroupTxPsd              OBJECT-TYPE
        SYNTAX          GSubCarrierGroupSizeType
        ACCESS          read-only
        STATUS          mandatory
        DESCRIPTION
        "Provides the grouping factor for Actual Tx Power Spectrum Density
         carrier data octet-string.  The grouping factor represents the number
         of carriers that have been grouped together in view to reduce data 
         size.The valid value is 1/2/4/8 and the invalid value is 0.

         ALCATEL NOTE:
             ACCESS:   NA                  USAGE:    NA
             PERSIST:  NO                  INSRVMOD: NA
             RANGE:    0, 1, 2, 4, 8       DEFVALUE: 1
             UNITS:    NA                  SPARSE:   NA
             DESCR:    NA 
        
         FGU4.4: THIS OBJECT IS NOT SUPPORTED "
::= {gxdslLineCarrierDataEntry 10}

gxdslLineCarrierGroupLoad               OBJECT-TYPE
        SYNTAX          GSubCarrierGroupSizeType
        ACCESS          read-only
        STATUS          mandatory
        DESCRIPTION
        "Provides the grouping factor for carrier load data octet-
         string.  The grouping factor represents the number of carriers that
         have been grouped together in view to reduce data size.
         The valid value is 1/2/4/8 and the invalid value is 0.

         ALCATEL NOTE:
             ACCESS:   NA                  USAGE:    NA
             PERSIST:  NO                  INSRVMOD: NA
             RANGE:    0, 1, 2, 4, 8       DEFVALUE: 1
             UNITS:    NA                  SPARSE:   NA
             DESCR:    NA

	For FGU4.4, the only supported value is 1.   "
::= {gxdslLineCarrierDataEntry 11}

gxdslLineCarrierGroupGain               OBJECT-TYPE
        SYNTAX          GSubCarrierGroupSizeType
        ACCESS          read-only
        STATUS          mandatory
        DESCRIPTION
        "Provides the grouping factor for carrier gain allocation data octet-
         string.  The grouping factor represents the number of carriers that
         have been grouped together in view to reduce data size.
         The valid value is 1/2/4/8 and the invalid value is 0.

         ALCATEL NOTE:
             ACCESS:   NA                  USAGE:    NA
             PERSIST:  NO                  INSRVMOD: NA
             RANGE:    0, 1, 2, 4, 8       DEFVALUE: 1
             UNITS:    NA                  SPARSE:   NA
             DESCR:    NA

	For FGU4.4, the only supported value is 1. "
::= {gxdslLineCarrierDataEntry 12}

gxdslLineCarrierGroupTss				OBJECT-TYPE
		SYNTAX					GSubCarrierGroupSizeType
		ACCESS					read-only
		STATUS					mandatory
		DESCRIPTION
		"Provides the grouping factor for Transmit Spectrum Shaping carrier data
		 octet-string.  The grouping factor represents the number of carriers that
		 have been grouped together in view to reduce data size.
         ALCATEL NOTE:
             ACCESS:   NA                  USAGE:    NA
             PERSIST:  NA                  INSRVMOD: NA
             RANGE:    NA                  DEFVALUE: NA
             UNITS:    NA                  SPARSE:   NA
             DESCR:    This object is not supported.
         
         FGU4.4:  THIS OBJECT IS NOT SUPPORTED "
::= {gxdslLineCarrierDataEntry 13}

gxdslLineCarrierGroupSnr OBJECT-TYPE
        SYNTAX          GSubCarrierGroupSizeType
        ACCESS          read-only
        STATUS          mandatory
        DESCRIPTION
        "Provides the grouping factor for Signal to Noise Ratio per carrier 
         data octet-string.  The grouping factor represents the number of 
         carriers that have been grouped together in view to reduce data size.
         The valid value is 1/2/4/8 and the invalid value is 0.

         ALCATEL NOTE:
             ACCESS:   NA                  USAGE:    NA
             PERSIST:  NO                  INSRVMOD: NA
             RANGE:    0, 1, 2, 4, 8       DEFVALUE: 1
             UNITS:    NA                  SPARSE:   NA
             DESCR:    NA "
::= {gxdslLineCarrierDataEntry 14}

gxdslLineCarrierGroupQln OBJECT-TYPE
        SYNTAX          GSubCarrierGroupSizeType
        ACCESS          read-only
        STATUS          mandatory
        DESCRIPTION
        "Provides the grouping factor for Quiet Line Noise data octet-
         string.  The grouping factor represents the number of carriers that
         have been grouped together in view to reduce data size.
         The valid value is 1/2/4/8 and the invalid value is 0.

         ALCATEL NOTE:
             ACCESS:   NA                  USAGE:    NA
             PERSIST:  NO                  INSRVMOD: NA
             RANGE:    0, 1, 2, 4, 8       DEFVALUE: 1
             UNITS:    NA                  SPARSE:   NA
             DESCR:    NA "
::= {gxdslLineCarrierDataEntry 15}

gxdslLineCarrierGroupHLin               OBJECT-TYPE
        SYNTAX          GSubCarrierGroupSizeType
        ACCESS          read-only
        STATUS          mandatory
        DESCRIPTION
        "Provides the grouping factor for Complex Channel Characteristics data
         in linear scale.  The grouping factor represents the number of 
         carriers that have been grouped together in view to reduce data size.
         The valid value is 1/2/4/8 and the invalid value is 0.

         ALCATEL NOTE:
             ACCESS:   NA                  USAGE:    NA
             PERSIST:  NO                  INSRVMOD: NA
             RANGE:    0, 1, 2, 4, 8       DEFVALUE: 1
             UNITS:    NA                  SPARSE:   NA
             DESCR:    NA "
::= {gxdslLineCarrierDataEntry 16}

gxdslLineCarrierGroupHLog               OBJECT-TYPE
        SYNTAX          GSubCarrierGroupSizeType
        ACCESS          read-only
        STATUS          mandatory
        DESCRIPTION
        "Provides the grouping factor for Channel Characteristics data in dB.
         The grouping factor represents the number of carriers that
         have been grouped together in view to reduce data size.
         The valid value is 1/2/4/8 and the invalid value is 0.

         ALCATEL NOTE:
             ACCESS:   NA                  USAGE:    NA
             PERSIST:  NO                  INSRVMOD: NA
             RANGE:    0, 1, 2, 4, 8       DEFVALUE: 1
             UNITS:    NA                  SPARSE:   NA
             DESCR:    NA "
::= {gxdslLineCarrierDataEntry 17}

gxdslLineCarrierSpIndex  OBJECT-TYPE
	SYNTAX 	SpIndex
	ACCESS	not-accessible
	STATUS	mandatory
	DESCRIPTION 
		"Each row is also indexed by a number that
		 contains the slot number and port number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslLineCarrierDataEntry 18 }


gxdslLineFailureStatusTable             OBJECT-TYPE
        SYNTAX          SEQUENCE OF GxdslLineFailureStatusEntry
        ACCESS          not-accessible
        STATUS          mandatory
        DESCRIPTION     
        "The xdsl line near end failure status table.

         ALCATEL NOTE:
             TABLESIZE: DEP [number of XDSL lines]                    
             DESCR:     NA                  
        "
::= {gxdslLineCurrent 3}
        
gxdslLineFailureStatusEntry             OBJECT-TYPE
        SYNTAX          GxdslLineFailureStatusEntry                      
        ACCESS          not-accessible
        STATUS          mandatory
        DESCRIPTION     
        "An entry in the xdsl line near end failure status table.

         Row creation : Entries for all XDSL lines belonging to a board are 
                        created when the board becomes operational.
         Row deletion : Entries for all XDSL lines belonging to a board are 
                        deleted when the board becomes unavailable.
        "
        INDEX          {ifIndex, gxdslLineFailureSpIndex}
::= {gxdslLineFailureStatusTable 1}
        
GxdslLineFailureStatusEntry ::=
        SEQUENCE {
                gxdslLineFailureStatus           INTEGER,
                gxdslLineFailureSpIndex          SpIndex
        }

gxdslLineFailureStatus   OBJECT-TYPE
        SYNTAX          INTEGER (1..65535)  
        ACCESS          read-only
        STATUS          mandatory
        DESCRIPTION 
        "This variable indicates the status of the near end interface. It is a 
         bitmap represented as a sum, therefore, it can represent multiple 
         failure simultaneuosly. The xdslLineNoFailure should be set if and only 
         if no other  flag is set. The various bit positions are:
           1     xdslLineNoFailure
           2     xdslLineLOS (loss of signal) in the upstream direction
           4     xdslLineLOF (loss of frame) in the upstream direction 
           8     xdslLineLOM (loss of margin) in the upstream direction
          16     xdslLineLPR (loss of power) of the ATU-C

--FGU4.4: LOL condition added (value 32):           
          32      xdslLineLOL (loss of link)

          64     xdslLineESE (Excessive Severe Errors) in the upstream
       direction
         128     xdslLineActivationFailure due to configuration error
         256     xdslLineActivationFailure due to configuration not feasible
--FGU4.4: Line Initialization Failure condition added (value 512):           
         512      xdslLineInitFailure (line initialization failure)
         1024..2048 reserved
         4096    xdslLineBitrateThreshold for the upstream direction.

         ALCATEL NOTE:
             ACCESS:   NA                  USAGE:    NA
             PERSIST:  NO                  INSRVMOD: NA
             RANGE:    NA                  DEFVALUE: 1
             UNITS:    NA                  SPARSE:   NA
             DESCR:    NA
        "
::= {gxdslLineFailureStatusEntry 1}

gxdslLineFailureSpIndex  OBJECT-TYPE
	SYNTAX 	SpIndex
	ACCESS	not-accessible
	STATUS	mandatory
	DESCRIPTION 
		"Each row is also indexed by a number that
		 contains the slot number and port number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslLineFailureStatusEntry 2 }


gxdslLineCurrentIntervalTable           OBJECT-TYPE
        SYNTAX          SEQUENCE OF GxdslLineCurrentIntervalEntry
        ACCESS          not-accessible
        STATUS          mandatory
        DESCRIPTION     
        "The xdsl line near end current interval table.

         ALCATEL NOTE:
             TABLESIZE: DEP [number of XDSL lines]                    
             DESCR:     NA                  
        "
::= {gxdslLineCurrent 4}
        
gxdslLineCurrentIntervalEntry           OBJECT-TYPE
        SYNTAX          GxdslLineCurrentIntervalEntry                    
        ACCESS          not-accessible
        STATUS          mandatory
        DESCRIPTION     
        "An entry in the xdsl line near end current interval table.

         Row creation : Entries for all XDSL lines belonging to a board are 
                        created when the board becomes operational.
         Row deletion : Entries for all XDSL lines belonging to a board are 
                        deleted when the board becomes unavailable.
        "
        INDEX          {ifIndex, gxdslLineCurrentSpIndex}
::= {gxdslLineCurrentIntervalTable 1}

GxdslLineCurrentIntervalEntry ::=
        SEQUENCE {
            gxdslLineCurrentIntervalLOSCounter         Counter,
            gxdslLineCurrentIntervalLOFCounter         Counter,
            gxdslLineCurrentIntervalLOMCounter         Counter,
            gxdslLineCurrentIntervalLPRCounter         Counter,
            gxdslLineCurrentIntervalESECounter         Counter,
            gxdslLineCurrentIntervalESCounter          Counter,
            gxdslLineCurrentIntervalSESCounter         Counter,
            gxdslLineCurrentIntervalUASCounter         Counter,
            gxdslLineCurrentIntervalReInitCounter      Counter,
            gxdslLineCurrentIntervalFailedInitCounter  Counter,
            gxdslLineCurrentIntervalMeasuredTime       INTEGER,
            gxdslLineCurrentIntervalInvalidDataFlag    INTEGER,
            gxdslLineCurrentIntervalRAUCounter         Counter,
            gxdslLineCurrentIntervalRADCounter         Counter,
            gxdslLineCurrentIntervalInitErr            Counter,
            gxdslLineCurrentIntervalInitTimeout        Counter,
            gxdslLineCurrentSpIndex                    SpIndex
        }

gxdslLineCurrentIntervalLOSCounter      OBJECT-TYPE
        SYNTAX          Counter
        ACCESS          read-only
        STATUS          mandatory
        DESCRIPTION     
        "This object represents for the current 15 minute interval the LOS 
         failure count, which is the number of occurences of an LOS failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA

     FGU4.4:  The counter associated with the number of LOS Seconds encountered 
         by the line in the current 15 minute interval (i.e. count of LOS seconds, not LOS events).
        "
::= {gxdslLineCurrentIntervalEntry 1}

gxdslLineCurrentIntervalLOFCounter      OBJECT-TYPE
        SYNTAX          Counter
        ACCESS          read-only
        STATUS          mandatory
        DESCRIPTION     
        "This object represents for the current 15 minute interval the LOF 
         failure count, which is the number of occurences of an LOF failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA
        "
::= {gxdslLineCurrentIntervalEntry 2}

gxdslLineCurrentIntervalLOMCounter      OBJECT-TYPE
        SYNTAX          Counter
        ACCESS          read-only
        STATUS          mandatory
        DESCRIPTION     
        "This object represents for the current 15 minute interval the LOM
         failure count, which is the number of occurences of a LOM failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA
        
         FGU4.4:  THIS OBJECT IS NOT SUPPORTED "
::= {gxdslLineCurrentIntervalEntry 3}

gxdslLineCurrentIntervalLPRCounter       OBJECT-TYPE
        SYNTAX          Counter
        ACCESS          read-only
        STATUS          mandatory
        DESCRIPTION     
        "This object represents for the current 15 minute interval the LPR 
         failure count, which is the number of occurences of an LPR failure 
         event, where a failure event occurs when the failure is declared and 
         ends when the failure clears.
         ALCATEL NOTE:
             ACCESS:   NA                  USAGE:    NA
             PERSIST:  NA                  INSRVMOD: NA
             RANGE:    NA                  DEFVALUE: NA
             UNITS:    NA                  SPARSE:   NA
             DESCR:    This object is not supported.
         "
::= {gxdslLineCurrentIntervalEntry 4}

gxdslLineCurrentIntervalESECounter      OBJECT-TYPE
        SYNTAX          Counter
        ACCESS          read-only
        STATUS          mandatory
        DESCRIPTION     
        "This object represents for the current 15 minute interval the ESE 
         failure count, which is the number of occurences of an ESE failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA
        
         FGU4.4:  THIS OBJECT IS NOT SUPPORTED "
::= {gxdslLineCurrentIntervalEntry 5}

gxdslLineCurrentIntervalESCounter       OBJECT-TYPE
        SYNTAX          Counter
        ACCESS          read-only
        STATUS          mandatory
        DESCRIPTION     
        "The counter associated with the number of Errored Seconds encountered 
         by the line in the current 15 minute interval.

         ALCATEL NOTE:
             ACCESS:   NA                  USAGE:    NA
             PERSIST:  NO                  INSRVMOD: NA
             RANGE:    NA                  DEFVALUE: 0
             UNITS:    NA                  SPARSE:   NA
             DESCR:    NA
        "
::= {gxdslLineCurrentIntervalEntry 6}

gxdslLineCurrentIntervalSESCounter      OBJECT-TYPE
        SYNTAX          Counter
        ACCESS          read-only
        STATUS          mandatory
        DESCRIPTION     
        "The counter associated with the number of Severely Errored Seconds
         encountered by the line in the current 15 minute interval.

         ALCATEL NOTE:
             ACCESS:   NA                  USAGE:    NA
             PERSIST:  NO                  INSRVMOD: NA
             RANGE:    NA                  DEFVALUE: 0
             UNITS:    NA                  SPARSE:   NA
             DESCR:    NA
        "
::= {gxdslLineCurrentIntervalEntry 7}

gxdslLineCurrentIntervalUASCounter      OBJECT-TYPE
        SYNTAX          Counter
        ACCESS          read-only
        STATUS          mandatory
        DESCRIPTION     
        "The counter associated with the number of Unavailable Seconds
         encountered by the line in the current 15 minute interval.

         ALCATEL NOTE:
             ACCESS:   NA                  USAGE:    NA
             PERSIST:  NO                  INSRVMOD: NA
             RANGE:    NA                  DEFVALUE: 0
             UNITS:    NA                  SPARSE:   NA
             DESCR:    NA
        "
::= {gxdslLineCurrentIntervalEntry 8}

gxdslLineCurrentIntervalReInitCounter   OBJECT-TYPE
        SYNTAX          Counter
        ACCESS          read-only
        STATUS          mandatory
        DESCRIPTION     
        "This object represents for the current 15 minute interval the number
         of times the modem left showtime and tried to re-initialize the line
         because of detection of a persistent defect.

         ALCATEL NOTE:
             ACCESS:   NA                  USAGE:    NA
             PERSIST:  NO                  INSRVMOD: NA
             RANGE:    NA                  DEFVALUE: 0
             UNITS:    NA                  SPARSE:   NA
             DESCR:    NA
        "
::= {gxdslLineCurrentIntervalEntry 9}

gxdslLineCurrentIntervalFailedInitCounter         OBJECT-TYPE
        SYNTAX          Counter
        ACCESS          read-only
        STATUS          mandatory
        DESCRIPTION     
        "This object represents for the current 15 minute interval the number
         of times the modem tries to initialize the line but fails.

         ALCATEL NOTE:
             ACCESS:   NA                  USAGE:    NA
             PERSIST:  NO                  INSRVMOD: NA
             RANGE:    NA                  DEFVALUE: 0
             UNITS:    NA                  SPARSE:   NA
             DESCR:    NA
        "
::= {gxdslLineCurrentIntervalEntry 10}

gxdslLineCurrentIntervalMeasuredTime    OBJECT-TYPE
        SYNTAX          INTEGER(0..900)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA
        
         FGU4.4:  THIS OBJECT IS NOT SUPPORTED "
::= {gxdslLineCurrentIntervalEntry 11}

gxdslLineCurrentIntervalInvalidDataFlag OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA
        
         FGU4.4:  THIS OBJECT IS NOT SUPPORTED "
::= {gxdslLineCurrentIntervalEntry 12}

gxdslLineCurrentIntervalRAUCounter      OBJECT-TYPE
        SYNTAX          Counter
        ACCESS          read-only
        STATUS          mandatory
        DESCRIPTION     
        "This object represents for the current 15 minute interval the RAU 
         anomaly count, which is the number of occurences of an Upshift Rate
         Adaptation.

         ALCATEL NOTE:
             ACCESS:   NA                  USAGE:    NA
             PERSIST:  NO                  INSRVMOD: NA
             RANGE:    NA                  DEFVALUE: 0
             UNITS:    NA                  SPARSE:   NA
             DESCR:    NA
        
         FGU4.4:  THIS OBJECT IS NOT SUPPORTED "
::= {gxdslLineCurrentIntervalEntry 13}

gxdslLineCurrentIntervalRADCounter      OBJECT-TYPE
        SYNTAX          Counter
        ACCESS          read-only
        STATUS          mandatory
        DESCRIPTION     
        "This object represents for the current 15 minute interval the RAD 
         anomaly count, which is the number of occurences of a Downshift Rate
         Adaptation.

         ALCATEL NOTE:
             ACCESS:   NA                  USAGE:    NA
             PERSIST:  NO                  INSRVMOD: NA
             RANGE:    NA                  DEFVALUE: 0
             UNITS:    NA                  SPARSE:   NA
             DESCR:    NA
        
         FGU4.4:  THIS OBJECT IS NOT SUPPORTED "
::= {gxdslLineCurrentIntervalEntry 14}


--FGU4.4: THE FOLLOWING TWO COUNTERS ARE ADDED TO THE XDSL MIB PER CUSTOMER REQUIEMENTS


gxdslLineCurrentIntervalInitErr OBJECT-TYPE
       SYNTAX       Counter
       ACCESS       read-only
       STATUS       mandatory
       DESCRIPTION
           "Count of Initialization Errors.

         FGU4.4:  THIS OBJECT IS NOT SUPPORTED "

       ::= { gxdslLineCurrentIntervalEntry 15 }


gxdslLineCurrentIntervalInitTimeout OBJECT-TYPE
       SYNTAX       Counter
       ACCESS       read-only
       STATUS       mandatory
       DESCRIPTION
           "Count of Initialization Timeouts. "

       ::= { gxdslLineCurrentIntervalEntry 16 }




gxdslLineCurrentSpIndex  OBJECT-TYPE
	SYNTAX 	SpIndex
	ACCESS	not-accessible
	STATUS	mandatory
	DESCRIPTION 
		"Each row is also indexed by a number that
		 contains the slot number and port number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslLineCurrentIntervalEntry 17 }


-- xdslLineCurrent1DayTablxdsl           OBJECT-TYPE
--         SYNTAX          SEQUENCE OF XdslLineCurrent1DayEntry
--         ACCESS          not-accessible
--         STATUS          mandatory
--         DESCRIPTION     
--         "The xdsl line near end current 1 day table.
-- 
--          ALCATEL NOTE:
--              TABLESIZE: DEP [number of XDSL lines]                    
--              DESCR:     NA                  
--         
--          FGU4.4:  THIS TABLE IS NOT SUPPORTED "
-- ::= {gxdslLineCurrent 5}
--         
-- xdslLineCurrent1DayEntry               OBJECT-TYPE
--         SYNTAX          XdslLineCurrent1DayEntry                        
--         ACCESS          not-accessible
--         STATUS          mandatory
--         DESCRIPTION     
--         "An entry in the xdsl line near end current 1 day table.
-- 
--          Row creation : Entries for all XDSL lines belonging to a board are 
--                         created when the board becomes operational.
--          Row deletion : Entries for all XDSL lines belonging to a board are 
--                         deleted when the board becomes unavailable.
--         "
--         INDEX          {ifIndex}
-- ::= {xdslLineCurrent1DayTable 1}
-- 
-- XdslLineCurrent1DayEntry ::=
--         SEQUENCE {
--             xdslLineCurrent1DayLOSCounter             Counter,
--             xdslLineCurrent1DayLOFCounter             Counter,
--             xdslLineCurrent1DayLOMCounter             Counter,
--             xdslLineCurrent1DayLPRCounter             Counter,
--             xdslLineCurrent1DayESECounter             Counter,
--             xdslLineCurrent1DayESCounter              Counter,
--             xdslLineCurrent1DaySESCounter             Counter,
--             xdslLineCurrent1DayUASCounter             Counter,
--             xdslLineCurrent1DayReInitCounter          Counter,
--             xdslLineCurrent1DayFailedInitCounter      Counter,
--             xdslLineCurrent1DayMeasuredTime           INTEGER,
--             xdslLineCurrent1DayInvalidDataFlag        INTEGER,
--             xdslLineCurrent1DayRAUCounter             Counter,
--             xdslLineCurrent1DayRADCounter             Counter
--         }
-- 
-- xdslLineCurrent1DayLOSCounter          OBJECT-TYPE
--         SYNTAX          Counter
--         ACCESS          read-only
--         STATUS          mandatory
--         DESCRIPTION     
--         "This object represents for the current 1 day interval the LOS failure 
--          count, which is the number of occurences of an LOS failure event,
--          where a failure event occurs when the failure is declared and ends
--          when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLineCurrent1DayEntry 1}
-- 
-- xdslLineCurrent1DayLOFCounter          OBJECT-TYPE
--         SYNTAX          Counter
--         ACCESS          read-only
--         STATUS          mandatory
--         DESCRIPTION     
--         "This object represents for the current 1 day interval 
--          the LOF failure count, which is the number of occurences of an LOF 
--          failure event, where a failure event occurs when the failure is 
--          declared and ends when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLineCurrent1DayEntry 2}
-- 
-- xdslLineCurrent1DayLOMCounter          OBJECT-TYPE
--         SYNTAX          Counter
--         ACCESS          read-only
--         STATUS          mandatory
--         DESCRIPTION     
--         "This object represents for the current 1 day interval 
--          the LOM failure count, which is the number of occurences of a LOM
--          failure event, where a failure event occurs when the failure is 
--          declared and ends when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLineCurrent1DayEntry 3}
-- 
-- xdslLineCurrent1DayLPRCounter   OBJECT-TYPE
--         SYNTAX          Counter
--         ACCESS          read-only
--         STATUS          mandatory
--         DESCRIPTION     
--         "This object represents for the current 1 day interval the LPR failure
--          count, which is the number of occurences of an LPR failure event,
--          where a failure event occurs when the failure is declared and ends
--          when the failure clears.
--          ALCATEL NOTE:
--              ACCESS:   NA                  USAGE:    NA
--              PERSIST:  NA                  INSRVMOD: NA
--              RANGE:    NA                  DEFVALUE: NA
--              UNITS:    NA                  SPARSE:   NA
--              DESCR:    This object is not supported.
--          "
-- ::= {xdslLineCurrent1DayEntry 4}
-- 
-- xdslLineCurrent1DayESECounter          OBJECT-TYPE
--         SYNTAX          Counter
--         ACCESS          read-only
--         STATUS          mandatory
--         DESCRIPTION     
--         "This object represents for the current 1 day interval the ESE 
--          failure count, which is the number of occurences of an ESE failure 
--          event, where a failure event occurs when the failure is declared and 
--          ends when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLineCurrent1DayEntry 5}
-- 
-- xdslLineCurrent1DayESCounter           OBJECT-TYPE
--         SYNTAX          Counter
--         ACCESS          read-only
--         STATUS          mandatory
--         DESCRIPTION     
--         "The counter associated with the number of Errored Seconds encountered 
--          by the line in the current 1 day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLineCurrent1DayEntry 6}
-- 
-- xdslLineCurrent1DaySESCounter          OBJECT-TYPE
--         SYNTAX          Counter
--         ACCESS          read-only
--         STATUS          mandatory
--         DESCRIPTION     
--         "The counter associated with the number of Severely Errored Seconds
--          encountered by the line in the current 1 day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLineCurrent1DayEntry 7}
-- 
-- xdslLineCurrent1DayUASCounter          OBJECT-TYPE
--         SYNTAX          Counter
--         ACCESS          read-only
--         STATUS          mandatory
--         DESCRIPTION     
--         "The counter associated with the number of Unavailable Seconds
--          encountered by the line in the current 1 Day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLineCurrent1DayEntry 8}
-- 
-- xdslLineCurrent1DayReInitCounter       OBJECT-TYPE
--         SYNTAX          Counter
--         ACCESS          read-only
--         STATUS          mandatory
--         DESCRIPTION     
--         "This object represents for the current 1 day interval the number of
--          times the modem left showtime and tried to re-initialize the line
--          because of detection of a persistent defect.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLineCurrent1DayEntry 9}
-- 
-- xdslLineCurrent1DayFailedInitCounter   OBJECT-TYPE
--         SYNTAX          Counter
--         ACCESS          read-only
--         STATUS          mandatory
--         DESCRIPTION     
--         "This object represents for the current 1 day interval the number of
--          times the modem tries to initialize the line but fails.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLineCurrent1DayEntry 10}
-- 
-- xdslLineCurrent1DayMeasuredTime        OBJECT-TYPE
--         SYNTAX          INTEGER(0..86400)
--         ACCESS          read-only
--         STATUS          mandatory
--         DESCRIPTION     
--         "The amount of time, measured in seconds, that statistics for this 
--          entry have been counted.
-- 
--          ALCATEL NOTE:
--              ACCESS:   NA                  USAGE:    NA
--              PERSIST:  NO                  INSRVMOD: NA
--              RANGE:    NA                  DEFVALUE: 0
--              UNITS:    seconds             SPARSE:   NA
--              DESCR:    NA
--         "
-- ::= {xdslLineCurrent1DayEntry 11}
-- 
-- xdslLineCurrent1DayInvalidDataFlag     OBJECT-TYPE
--         SYNTAX          INTEGER
--         ACCESS          read-only
--         STATUS          mandatory
--         DESCRIPTION     
--         "This object indicates the validity of the corresponding PM data.
--          It is set to 1 when the PM data is incomplete or invalid and set to 0
--          when the PM data is complete and valid.
-- 
--          ALCATEL NOTE:
--              ACCESS:   NA                  USAGE:    NA
--              PERSIST:  NO                  INSRVMOD: NA
--              RANGE:    0..1                DEFVALUE: 1
--              UNITS:    NA                  SPARSE:   NA
--              DESCR:    NA
--         "
-- ::= {xdslLineCurrent1DayEntry 12}
-- 
-- xdslLineCurrent1DayRAUCounter          OBJECT-TYPE
--         SYNTAX          Counter
--         ACCESS          read-only
--         STATUS          mandatory
--         DESCRIPTION     
--         "This object represents for the current 1 day interval the RAU anomaly 
--          count, which is the number of occurences of an Upshift Rate 
--          Adaptation.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLineCurrent1DayEntry 13}
-- 
-- xdslLineCurrent1DayRADCounter          OBJECT-TYPE
--         SYNTAX          Counter
--         ACCESS          read-only
--         STATUS          mandatory
--         DESCRIPTION     
--         "This object represents for the current 1 day interval the RAD anomaly 
--          count, which is the number of occurences of a Downshift Rate 
--          Adaptation.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLineCurrent1DayEntry 14}

gxdslLinePreviousIntervalTable          OBJECT-TYPE
        SYNTAX          SEQUENCE OF GxdslLinePreviousIntervalEntry
        ACCESS          not-accessible
        STATUS          mandatory
        DESCRIPTION     
        "The xdsl line near end previous interval table.

         ALCATEL NOTE:
             TABLESIZE: DEP [number of XDSL lines * 192]                    
             DESCR:     NA                  
        "
::= {gxdslLinePrevious 1}
        
gxdslLinePreviousIntervalEntry          OBJECT-TYPE
        SYNTAX          GxdslLinePreviousIntervalEntry                   
        ACCESS          not-accessible
        STATUS          mandatory
        DESCRIPTION     
        "An entry in the xdsl line near end previous interval table.

         Row creation : Entries for all XDSL lines belonging to a board are 
                        created when the board becomes operational.
         Row deletion : Entries for all XDSL lines belonging to a board are 
                        deleted when the board becomes unavailable.
        "
        INDEX          {ifIndex, gxdslLinePreviousSpIndex,
                        gxdslLinePreviousIntervalNumber}
::= {gxdslLinePreviousIntervalTable 1}

GxdslLinePreviousIntervalEntry ::=
        SEQUENCE {
            gxdslLinePreviousIntervalNumber            INTEGER,
            gxdslLinePreviousIntervalLOSCounter        Counter,
            gxdslLinePreviousIntervalLOFCounter        Counter,
            gxdslLinePreviousIntervalLOMCounter        Counter,
            gxdslLinePreviousIntervalLPRCounter        Counter,
            gxdslLinePreviousIntervalESECounter        Counter,
            gxdslLinePreviousIntervalESCounter         Counter,
            gxdslLinePreviousIntervalSESCounter        Counter,
            gxdslLinePreviousIntervalUASCounter        Counter,
            gxdslLinePreviousIntervalReInitCounter     Counter,
            gxdslLinePreviousIntervalFailedInitCounter Counter,
            gxdslLinePreviousIntervalMeasuredTime      INTEGER,
            gxdslLinePreviousIntervalInvalidDataFlag   INTEGER,
            gxdslLinePreviousIntervalRAUCounter        Counter,
            gxdslLinePreviousIntervalRADCounter        Counter,
            gxdslLinePreviousIntervalInitErr           Counter,
            gxdslLinePreviousIntervalInitTimeout       Counter,
            gxdslLinePreviousSpIndex                   SpIndex
        }
        
gxdslLinePreviousIntervalNumber         OBJECT-TYPE
        SYNTAX          INTEGER(1..192)
        ACCESS          read-only
        STATUS          mandatory
        DESCRIPTION     
        "A number between 1 and 192, which identifies the interval for which 
         the set of statistics is available. The interval identified by 1 is 
         the most recently completed 15 minute interval, and the interval
         identified by N is the interval immediately preceding the one
         identified by N-1.

         ALCATEL NOTE:
             ACCESS:   NA                  USAGE:    NA
             PERSIST:  NO                  INSRVMOD: NA
             RANGE:    NA                  DEFVALUE: NA
             UNITS:    NA                  SPARSE:   NA
             DESCR:    NA
        "
::= {gxdslLinePreviousIntervalEntry 1}

gxdslLinePreviousIntervalLOSCounter     OBJECT-TYPE
        SYNTAX          Counter
        ACCESS          read-only
        STATUS          mandatory
        DESCRIPTION     
        "This object represents for a particular 15 minute interval the LOS 
         failure count, which is the number of occurences of an LOS failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA

     FGU4.4:  The counter associated with the number of LOS Seconds encountered 
         by the line in the current 15 minute interval (i.e. count of LOS seconds, not LOS events).
        "
::= {gxdslLinePreviousIntervalEntry 2}

gxdslLinePreviousIntervalLOFCounter     OBJECT-TYPE
        SYNTAX          Counter
        ACCESS          read-only
        STATUS          mandatory
        DESCRIPTION     
        "This object represents for a particular 15 minute interval the LOF 
         failure count, which is the number of occurences of an LOF failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA
        "
::= {gxdslLinePreviousIntervalEntry 3}

gxdslLinePreviousIntervalLOMCounter     OBJECT-TYPE
        SYNTAX          Counter
        ACCESS          read-only
        STATUS          mandatory
        DESCRIPTION     
        "This object represents for a particular 15 minute interval the LOM 
         failure count, which is the number of occurences of a LOM failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA
        
         FGU4.4:  THIS OBJECT IS NOT SUPPORTED "
::= {gxdslLinePreviousIntervalEntry 4}

gxdslLinePreviousIntervalLPRCounter      OBJECT-TYPE
        SYNTAX          Counter
        ACCESS          read-only
        STATUS          mandatory
        DESCRIPTION
        "This object represents for a particular 15 minute interval the LPR 
         failure count, which is the number of occurences of an LPR failure 
         event, where a failure event occurs when the failure is declared and 
         ends when the failure clears.
         ALCATEL NOTE:
             ACCESS:   NA                  USAGE:    NA
             PERSIST:  NA                  INSRVMOD: NA
             RANGE:    NA                  DEFVALUE: NA
             UNITS:    NA                  SPARSE:   NA
             DESCR:    This object is not supported.
         
        
         FGU4.4:  THIS OBJECT IS NOT SUPPORTED "
::= {gxdslLinePreviousIntervalEntry 5}

gxdslLinePreviousIntervalESECounter     OBJECT-TYPE
        SYNTAX          Counter
        ACCESS          read-only
        STATUS          mandatory
        DESCRIPTION     
        "This object represents for a particular 15 minute interval the ESE 
         failure count, which is the number of occurences of an ESE failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED"
   ::= {gxdslLinePreviousIntervalEntry 6}

gxdslLinePreviousIntervalESCounter      OBJECT-TYPE
        SYNTAX          Counter
        ACCESS          read-only
        STATUS          mandatory
        DESCRIPTION  
        "The counter associated with the number of Errored Seconds encountered 
         by the line in a particular 15 minute interval.

         ALCATEL NOTE:
             ACCESS:   NA                  USAGE:    NA
             PERSIST:  NO                  INSRVMOD: NA
             RANGE:    NA                  DEFVALUE: 0
             UNITS:    NA                  SPARSE:   NA
             DESCR:    NA
        "
   ::= {gxdslLinePreviousIntervalEntry 7}

gxdslLinePreviousIntervalSESCounter     OBJECT-TYPE
        SYNTAX          Counter
        ACCESS          read-only
        STATUS          mandatory
        DESCRIPTION  
        "The counter associated with the number of Severely Errored Seconds
         encountered by the line in a particular 15 minute interval.

         ALCATEL NOTE:
             ACCESS:   NA                  USAGE:    NA
             PERSIST:  NO                  INSRVMOD: NA
             RANGE:    NA                  DEFVALUE: 0
             UNITS:    NA                  SPARSE:   NA
             DESCR:    NA
        "
   ::= {gxdslLinePreviousIntervalEntry 8}

gxdslLinePreviousIntervalUASCounter     OBJECT-TYPE
        SYNTAX          Counter
        ACCESS          read-only
        STATUS          mandatory
        DESCRIPTION  
        "The counter associated with the number of Unavailable Seconds
         encountered by the line in a particular 15 minute interval.

         ALCATEL NOTE:
             ACCESS:   NA                  USAGE:    NA
             PERSIST:  NO                  INSRVMOD: NA
             RANGE:    NA                  DEFVALUE: 0
             UNITS:    NA                  SPARSE:   NA
             DESCR:    NA
        "
   ::= {gxdslLinePreviousIntervalEntry 9}

gxdslLinePreviousIntervalReInitCounter  OBJECT-TYPE
        SYNTAX          Counter
        ACCESS          read-only
        STATUS          mandatory
        DESCRIPTION     
        "This object represents for a particular 15 minute interval the number
         of times the modem left showtime and tried to re-initialize the line
         because of detection of a persistent defect.

         ALCATEL NOTE:
             ACCESS:   NA                  USAGE:    NA
             PERSIST:  NO                  INSRVMOD: NA
             RANGE:    NA                  DEFVALUE: 0
             UNITS:    NA                  SPARSE:   NA
             DESCR:    NA
        "
::= {gxdslLinePreviousIntervalEntry 10}

gxdslLinePreviousIntervalFailedInitCounter        OBJECT-TYPE
        SYNTAX          Counter
        ACCESS          read-only
        STATUS          mandatory
        DESCRIPTION     
        "This object represents for a particular 15 minute interval the number
         of times the modem tries to initialize the line but fails.

         ALCATEL NOTE:
             ACCESS:   NA                  USAGE:    NA
             PERSIST:  NO                  INSRVMOD: NA
             RANGE:    NA                  DEFVALUE: 0
             UNITS:    NA                  SPARSE:   NA
             DESCR:    NA
        "
::= {gxdslLinePreviousIntervalEntry 11}

gxdslLinePreviousIntervalMeasuredTime   OBJECT-TYPE
        SYNTAX          INTEGER(0..900)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA
        
        
         FGU4.4:  THIS OBJECT IS NOT SUPPORTED"
::= {gxdslLinePreviousIntervalEntry 12}

gxdslLinePreviousIntervalInvalidDataFlag          OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA
        
        
         FGU4.4:  THIS OBJECT IS NOT SUPPORTED"
::= {gxdslLinePreviousIntervalEntry 13}

gxdslLinePreviousIntervalRAUCounter     OBJECT-TYPE
        SYNTAX          Counter
        ACCESS          read-only
        STATUS          mandatory
        DESCRIPTION     
        "This object represents for a particular 15 minute interval the RAU 
         anomaly count, which is the number of occurences of an Upshift Rate
         Adaptation.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED"
::= {gxdslLinePreviousIntervalEntry 14}

gxdslLinePreviousIntervalRADCounter     OBJECT-TYPE
        SYNTAX          Counter
        ACCESS          read-only
        STATUS          mandatory
        DESCRIPTION     
        "This object represents for a particular 15 minute interval the RAD 
         anomaly count, which is the number of occurences of a Downshift Rate 
         Adaptation.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED  "
::= {gxdslLinePreviousIntervalEntry 15}

--FGU4.4: THE FOLLOWING TWO COUNTERS ARE ADDED TO THE XDSL MIB PER CUSTOMER REQUIEMENTS


gxdslLinePreviousIntervalInitErr OBJECT-TYPE
       SYNTAX       Counter
       ACCESS       read-only
       STATUS       mandatory
       DESCRIPTION
           "Count of Initialization Errors.

         FGU4.4:  THIS OBJECT IS NOT SUPPORTED  "

       ::= { gxdslLinePreviousIntervalEntry 16 }


gxdslLinePreviousIntervalInitTimeout OBJECT-TYPE
       SYNTAX       Counter
       ACCESS       read-only
       STATUS       mandatory
       DESCRIPTION
           "Count of Initialization Timeouts. "

       ::= { gxdslLinePreviousIntervalEntry 17 }


gxdslLinePreviousSpIndex  OBJECT-TYPE
	SYNTAX 	SpIndex
	ACCESS	not-accessible
	STATUS	mandatory
	DESCRIPTION 
		"Each row is also indexed by a number that
		 contains the slot number and port number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslLinePreviousIntervalEntry 18 }

-- xdslLinePrevious1DayTable              OBJECT-TYPE
--         SYNTAX          SEQUENCE OF XdslLinePrevious1DayEntry
--         ACCESS          not-accessible
--         STATUS          mandatory
--         DESCRIPTION     
--         "The xdsl line near end previous 1 day table.
-- 
--          ALCATEL NOTE:
--              TABLESIZE: DEP [number of XDSL lines * number of days (1)]                  
--              DESCR:     NA                  
--         
--          FGU4.4:  THIS TABLE IS NOT SUPPORTED "
-- ::= {gxdslLinePrevious 2}
--         
-- xdslLinePrevious1DayEntry              OBJECT-TYPE
--         SYNTAX          XdslLinePrevious1DayEntry                       
--         ACCESS          not-accessible
--         STATUS          mandatory
--         DESCRIPTION     
--         "An entry in the xdsl line near end previous 1 day table.
-- 
--          Row creation : Entries for all XDSL lines belonging to a board are 
--                         created when the board becomes operational.
--          Row deletion : Entries for all XDSL lines belonging to a board are 
--                         deleted when the board becomes unavailable.
--         "
--         INDEX          {ifIndex, 
--                         xdslLinePrevious1DayNumber}
-- ::= {xdslLinePrevious1DayTable 1}
-- 
-- XdslLinePrevious1DayEntry ::=
--         SEQUENCE {
--             xdslLinePrevious1DayNumber                INTEGER,
--             xdslLinePrevious1DayLOSCounter            Counter,
--             xdslLinePrevious1DayLOFCounter            Counter,
--             xdslLinePrevious1DayLOMCounter            Counter,
--             xdslLinePrevious1DayLPRCounter            Counter,
--             xdslLinePrevious1DayESECounter            Counter,
--             xdslLinePrevious1DayESCounter             Counter,
--             xdslLinePrevious1DaySESCounter            Counter,
--             xdslLinePrevious1DayUASCounter            Counter,
--             xdslLinePrevious1DayReInitCounter         Counter,
--             xdslLinePrevious1DayFailedInitCounter     Counter,
--             xdslLinePrevious1DayMeasuredTime          INTEGER,
--             xdslLinePrevious1DayInvalidDataFlag       INTEGER,
--             xdslLinePrevious1DayRAUCounter            Counter,
--             xdslLinePrevious1DayRADCounter            Counter
--         }
-- 
-- xdslLinePrevious1DayNumber             OBJECT-TYPE
--         SYNTAX          INTEGER(1..7)
--         ACCESS          read-only
--         STATUS          mandatory
--         DESCRIPTION     
--         "A number between 1 and 7, which identifies the day for which the 
--          set of statistics is available. The day identified by 1 is the 
--          most recently completed 1Day, and the day identified 
--          by N is the day immediately preceding the one identified by N-1.
-- 
--          ALCATEL NOTE:
--              ACCESS:   NA                  USAGE:    NA
--              PERSIST:  NO                  INSRVMOD: NA
--              RANGE:    1                   DEFVALUE: NA
--              UNITS:    NA                  SPARSE:   NA
--              DESCR:    Only statistics for one previous day is kept.
--         "
-- ::= {xdslLinePrevious1DayEntry 1}
-- 
-- xdslLinePrevious1DayLOSCounter         OBJECT-TYPE
--         SYNTAX          Counter
--         ACCESS          read-only
--         STATUS          mandatory
--         DESCRIPTION     
--         "This object represents for the previous 1 day interval the LOS failure 
--          count, which is the number of occurences of an LOS failure event,
--          where a failure event occurs when the failure is declared and ends
--          when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLinePrevious1DayEntry 2}
-- 
-- xdslLinePrevious1DayLOFCounter         OBJECT-TYPE
--         SYNTAX          Counter
--         ACCESS          read-only
--         STATUS          mandatory
--         DESCRIPTION     
--         "This object represents for the previous 1 day interval the LOF failure 
--          count, which is the number of occurences of an LOF failure event, 
--          where a failure event occurs when the failure is declared and ends
--          when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLinePrevious1DayEntry 3}
-- 
-- xdslLinePrevious1DayLOMCounter         OBJECT-TYPE
--         SYNTAX          Counter
--         ACCESS          read-only
--         STATUS          mandatory
--         DESCRIPTION     
--         "This object represents for the previous 1 day interval the LOM failure 
--          count, which is the number of occurences of a LOM failure event, where 
--          a failure event occurs when the failure is declared and ends when the 
--          failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLinePrevious1DayEntry 4}
-- 
-- xdslLinePrevious1DayLPRCounter  OBJECT-TYPE
--         SYNTAX  Counter
--         ACCESS  read-only
--         STATUS  mandatory
--         DESCRIPTION     
--         "This object represents for the previous 1 day interval the LPR failure 
--          count, which is the number of occurences of an LPR failure event,
--          where a failure event occurs when the failure is declared and ends
--          when the failure clears.
--          ALCATEL NOTE:
--              ACCESS:   NA                  USAGE:    NA
--              PERSIST:  NA                  INSRVMOD: NA
--              RANGE:    NA                  DEFVALUE: NA
--              UNITS:    NA                  SPARSE:   NA
--              DESCR:    This object is not supported.
--          "
-- ::= {xdslLinePrevious1DayEntry 5}
-- 
-- xdslLinePrevious1DayESECounter         OBJECT-TYPE
--         SYNTAX          Counter
--         ACCESS          read-only
--         STATUS          mandatory
--         DESCRIPTION     
--         "This object represents for the previous 1 day interval the ESE 
--          failure count, which is the number of occurences of an ESE failure 
--          event, where a failure event occurs when the failure is declared and 
--          ends when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLinePrevious1DayEntry 6}
-- 
-- xdslLinePrevious1DayESCounter          OBJECT-TYPE
--         SYNTAX          Counter
--         ACCESS          read-only
--         STATUS          mandatory
--         DESCRIPTION     
--         "The counter associated with the number of Errored Seconds encountered 
--          by the line in the previous 1 day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLinePrevious1DayEntry 7}
-- 
-- xdslLinePrevious1DaySESCounter         OBJECT-TYPE
--         SYNTAX          Counter
--         ACCESS          read-only
--         STATUS          mandatory
--         DESCRIPTION     
--         "The counter associated with the number of Severely Errored Seconds
--          encountered by the line in the previous 1 day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLinePrevious1DayEntry 8}
-- 
-- xdslLinePrevious1DayUASCounter         OBJECT-TYPE
--         SYNTAX          Counter
--         ACCESS          read-only
--         STATUS          mandatory
--         DESCRIPTION     
--         "The counter associated with the number of Unavailable Seconds
--          encountered by the line in the previous 1 day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLinePrevious1DayEntry 9}
-- 
-- xdslLinePrevious1DayReInitCounter      OBJECT-TYPE
--         SYNTAX          Counter
--         ACCESS          read-only
--         STATUS          mandatory
--         DESCRIPTION     
--         "This object represents for the previous 1 day interval the number of
--          times the modem left showtime and tried to re-initialize the line
--          because of detection of a persistent defect.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLinePrevious1DayEntry 10}
-- 
-- xdslLinePrevious1DayFailedInitCounter  OBJECT-TYPE
--         SYNTAX          Counter
--         ACCESS          read-only
--         STATUS          mandatory
--         DESCRIPTION     
--         "This object represents for the previous 1 day interval the number of
--          times the modem tries to initialize the line but fails.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLinePrevious1DayEntry 11}
-- 
-- xdslLinePrevious1DayMeasuredTime       OBJECT-TYPE
--         SYNTAX          INTEGER(0..86400)
--         ACCESS          read-only
--         STATUS          mandatory
--         DESCRIPTION     
--         "The amount of time, measured in seconds, that statistics for this
--          entry have been counted.
-- 
--          ALCATEL NOTE:
--              ACCESS:   NA                  USAGE:    NA
--              PERSIST:  NO                  INSRVMOD: NA
--              RANGE:    NA                  DEFVALUE: 0
--              UNITS:    seconds             SPARSE:   NA
--              DESCR:    NA
--         "
-- ::= {xdslLinePrevious1DayEntry 12}
-- 
-- xdslLinePrevious1DayInvalidDataFlag    OBJECT-TYPE
--         SYNTAX          INTEGER
--         ACCESS          read-only
--         STATUS          mandatory
--         DESCRIPTION     
--         "This object indicates the validity of the corresponding PM data.
--          It is set to 1 when the PM data is incomplete or invalid and set to 0
--          when the PM data is complete and valid.
-- 
--          ALCATEL NOTE:
--              ACCESS:   NA                  USAGE:    NA
--              PERSIST:  NO                  INSRVMOD: NA
--              RANGE:    0..1                DEFVALUE: 1
--              UNITS:    NA                  SPARSE:   NA
--              DESCR:    NA
--         "
-- ::= {xdslLinePrevious1DayEntry 13}
-- 
-- xdslLinePrevious1DayRAUCounter         OBJECT-TYPE
--         SYNTAX          Counter
--         ACCESS          read-only
--         STATUS          mandatory
--         DESCRIPTION     
--         "This object represents for the previous 1 day interval the RAU anomaly 
--          count, which is the number of occurences of an Upshift Rate 
--          Adaptation.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLinePrevious1DayEntry 14}
-- 
-- xdslLinePrevious1DayRADCounter         OBJECT-TYPE
--         SYNTAX          Counter
--         ACCESS          read-only
--         STATUS          mandatory
--         DESCRIPTION     
--         "This object represents for the previous 1 day interval the RAD anomaly 
--          count, which is the number of occurences of a Downshift Rate 
--          Adaptation.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslLinePrevious1DayEntry 15}

gxdslLineSpectrumProfileIndexOffset     OBJECT-TYPE
        SYNTAX          AsamMaxProfileIndex
        ACCESS          read-only
        STATUS          mandatory
        DESCRIPTION
        "This object represents the offset to be added to an existing spectrum
         profile index during a modification in order to access the temporary
         profile entry that contains the updates being done on that profile, 
         see xdslLineSpectrumProfileIndex.

         ALCATEL NOTE:
             ACCESS:   NA                  USAGE:    NA
             PERSIST:  NO                  INSRVMOD: NA
             RANGE:    1000                DEFVALUE: 1000
             UNITS:    NA                  SPARSE:   NA
             DESCR:    NA
        "
::= {gxdslLine 10}

-- xdslActDfltSpectrumProfileNbr         OBJECT-TYPE
-- ::= {gxdslLineDfltProfiles 1}

-- xdslActDfltServiceProfileNbr          OBJECT-TYPE
-- ::= { gxdslLineDfltProfiles 2}

-- xdslNewDfltSpectrumProfileNbr         OBJECT-TYPE
-- ::= { gxdslLineDfltProfiles 3}

-- xdslNewDfltServiceProfileNbr          OBJECT-TYPE
-- ::= { gxdslLineDfltProfiles 4}

-- xdslDfltProfileModifyStatus           OBJECT-TYPE
-- ::= { gxdslLineDfltProfiles 5}

--      The XDSL Far End Line Group

gxdslFarEndLineOperDataTable            OBJECT-TYPE
        SYNTAX          SEQUENCE OF GxdslFarEndLineOperDataEntry
        ACCESS          not-accessible
        STATUS          mandatory
        DESCRIPTION     
        "The xdsl far end line operational data table.

         ALCATEL NOTE:
             TABLESIZE: DEP [number of XDSL lines]                    
             DESCR:     NA                  
        "
::= {gxdslFarEndLineCurrent 1}

gxdslFarEndLineOperDataEntry            OBJECT-TYPE
        SYNTAX          GxdslFarEndLineOperDataEntry                     
        ACCESS          not-accessible
        STATUS          mandatory
        DESCRIPTION     
        "An entry in the xdsl far end line operational data table.

         Row creation : Entries for all XDSL lines belonging to a board are 
                        created when the board becomes operational.
         Row deletion : Entries for all XDSL lines belonging to a board are 
                        deleted when the board becomes unavailable.
        "
        INDEX          {ifIndex, gxdslFarEndLineOperSpIndex}
::= {gxdslFarEndLineOperDataTable 1}

GxdslFarEndLineOperDataEntry ::=
        SEQUENCE {
          gxdslFarEndLineRelCapacityOccupationDownstream    INTEGER,
          gxdslFarEndLineNoiseMarginDownstream              INTEGER,
          gxdslFarEndLineOutputPowerUpstream                INTEGER,
          gxdslFarEndLineSignalAttenuationDownstream        INTEGER,
          gxdslFarEndLineLoopAttenuationDownstream          INTEGER,
          gxdslFarEndLineXturOpModeCapabilities             GOpModeType,
          gxdslFarEndLineLastTxStateUpstream                INTEGER,
          gxdslFarEndLineActualPsdUpstream                  INTEGER,
          gxdslFarEndLinePerBandLoopAttenuationDownstream   GPerBandOperDataType,
          gxdslFarEndLinePerBandSignalAttenuationDownstream GPerBandOperDataType,
          gxdslFarEndLinePerBandNoiseMarginDownstream       GPerBandOperDataType,
          gxdslFarEndLineHighestFrequencyDownstream         INTEGER,
          gxdslFarEndLineElectricalLengthEstimated          INTEGER,
          gxdslFarEndLineTimingAdvanceProposed              INTEGER,
          gxdslFarEndLineOperSpIndex                        SpIndex,
	  gxdslFarEndLineActualVirtualNoiseSnrmModeDownstream  GSnrmMode
        }

gxdslFarEndLineRelCapacityOccupationDownstream    OBJECT-TYPE
        SYNTAX          INTEGER
        ACCESS          read-only
        STATUS          mandatory
        DESCRIPTION     
        "This parameter represents the ratio of the actual line bitrate over
         the maximum attainable line bitrate in the downstream direction,
         calculated in the latency path in use and represented in percentages.
         The line rate is equal to the net data rate plus all overhead 
         information (framing overhead, Reed Solomon overhead, Trellis 
         overhead). 
         When the modem is not in showtime, then the value measured in 
         preceeding showtime session is returned. The value is fixed to 100% in 
         case of activation failure when for that particular downstream 
         direction a bitrate higher than the attainable bitrate has been
         requested.
         When no data is available (e.g. before first showtime) value 0
         is used.
         Range is 0 to 100% with a granularity of 1 %.

         ALCATEL NOTE:
             ACCESS:   NA                  USAGE:    NA
             PERSIST:  NO                  INSRVMOD: NA
             RANGE:    0..100              DEFVALUE: 0
             UNITS:    percent             SPARSE:   NA
             DESCR:    NA
        "
::= {gxdslFarEndLineOperDataEntry 1}

gxdslFarEndLineNoiseMarginDownstream    OBJECT-TYPE
        SYNTAX          INTEGER
        ACCESS          read-only
        STATUS          mandatory
        DESCRIPTION     
        "This parameter indicates the current noise margin 
         for the downstream direction. When the modem is not in showtime this
         object will have the previously measured value.
         When no data is available (e.g. before first showtime) value 0
         is used.
         Range is -64 to 63 dB with a granularity of 0,1 dB.
         It is representyes as 1/10 * xdslFarEndLineNoiseMarginDownstream.
         The special value 65535 indicates that the noise margin is out of
         range.

         ALCATEL NOTE:
             ACCESS:   NA                  USAGE:    NA
             PERSIST:  NO                  INSRVMOD: NA
             RANGE:    -640..630, 65535    DEFVALUE: 0
             UNITS:    dB / 10             SPARSE:   NA
             DESCR:    NA
        "
::= {gxdslFarEndLineOperDataEntry 2}

gxdslFarEndLineOutputPowerUpstream      OBJECT-TYPE
        SYNTAX          INTEGER
        ACCESS          read-only
        STATUS          mandatory
        DESCRIPTION     
        "This object gives the actual aggregate output power for the upstream 
         carriers. When the modem is not in showtime this object will have the
         previously measured value. 
         When no data is available (e.g. before first showtime) value 0
         is used.
         Range is -31 to 31 dBm with a granularity of 0,1 dB.
         It is representyes as 1/10 * xdslFarEndLineOutputPowerUpstream.
         The special value 65535 indicates that the actual aggregate output
         power is out of range.

         ALCATEL NOTE:
             ACCESS:   NA                  USAGE:    NA
             PERSIST:  NO                  INSRVMOD: NA
             RANGE:    -310..310, 65535    DEFVALUE: 0
             UNITS:    dBm / 10            SPARSE:   NA
             DESCR:    NA
        "
::= {gxdslFarEndLineOperDataEntry 3}

gxdslFarEndLineSignalAttenuationDownstream        OBJECT-TYPE
        SYNTAX          INTEGER
        ACCESS          read-only
        STATUS          mandatory
        DESCRIPTION     
        "This object gives the difference in dB between the power measured at
         the far-end receiver and that transmitted from the near-end. The
         signal attenuation is measured over all data carriers and is updated
         during showtime.
         When the modem is not in showtime this object will have the value
         measured during the previous showtime session.
         When no data is available (e.g. before first showtime) value 0
         is used.
         It is represented as 1/10 * xdslFarEndLineSignalAttenuationDownstream, 
         with a range of (0..127dB) and a granularity of 0.1 dB.The special
         value 65535 indicates that the signal attenuation is out of range.

         ALCATEL NOTE:
             ACCESS:   NA                  USAGE:    NA
             PERSIST:  NO                  INSRVMOD: NA
             RANGE:    0..1270, 65535      DEFVALUE: 0
             UNITS:    dB / 10             SPARSE:   NA
             DESCR:    NA
        "
::= {gxdslFarEndLineOperDataEntry 4}

gxdslFarEndLineLoopAttenuationDownstream          OBJECT-TYPE
        SYNTAX          INTEGER
        ACCESS          read-only
        STATUS          mandatory
        DESCRIPTION     
        "This object gives the difference in dB between the power 
         measured at the far-end receiver and that transmitted from the
         near-end over all sub-carriers. The loop attenuation is measured at
         initialization and is not updated during showtime.
         When the modem is not in showtime this object will have the value
         measured during the previous showtime session.
         When no data is available (e.g. before first showtime) value 0
         is used.
         It is represented as 1/10 * xdslFarEndLineLoopAttenuationDownstream,
         with a range of (0..127dB) and a granularity of 0.1 dB.The special
         value 65535 indicates that the loop attenuation is out of range.

         ALCATEL NOTE:
             ACCESS:   NA                  USAGE:    NA
             PERSIST:  NO                  INSRVMOD: NA
             RANGE:    0..1270, 65535      DEFVALUE: 0
             UNITS:    dB / 10             SPARSE:   NA
             DESCR:    NA
        "
::= {gxdslFarEndLineOperDataEntry 5}

gxdslFarEndLineXturOpModeCapabilities   OBJECT-TYPE
        SYNTAX          GOpModeType
        ACCESS          read-only
        STATUS          mandatory
        DESCRIPTION 
        "This variable consists of a bitmap which represents the operational
         modes supported at the XTU-R. It uses the same coding as defined in
         gxdslLineOpMode.The octet 9 is not supported and it's value will
         always be 0.
         When the modem is not in showtime this object will have the value
         measured during the previous showtime session.
         When no data is available (e.g. before first showtime) value 0
         is used.

         ALCATEL NOTE:
             ACCESS:   NA                  USAGE:    NA
             PERSIST:  NO                  INSRVMOD: NA
             RANGE:    NA
             DEFVALUE: '00 00 00 00 00 00 00 00 
                        00 00 00 00 00 00 00 00'H
             UNITS:    NA                  SPARSE:   NA
             DESCR:    NA
 
         FGU4.4 - THIS OBJECT IS NOT SUPPORTED
         For GPON - SUPPORTED except octet 9 as of ISAM5.3.02
         For XG-PON1 - NOT SUPPORTED as of ISAM5.3.02
         For NG-PON2 - NOT SUPPORTED as of ISAM5.3.02
        "
::= {gxdslFarEndLineOperDataEntry 6}

gxdslFarEndLineLastTxStateUpstream     OBJECT-TYPE
        SYNTAX          INTEGER
        ACCESS          read-only
        STATUS          mandatory
        DESCRIPTION     
        "This object gives the last successful transmitted initialisation state
         as defined in G.999.1. It is reported for ADSL2 modes in Loop
         Diagnostics State only.
         ALCATEL NOTE:
             ACCESS:   NA                  USAGE:    NA
             PERSIST:  NA                  INSRVMOD: NA
             RANGE:    NA                  DEFVALUE: NA
             UNITS:    NA                  SPARSE:   NA
             DESCR:    NA
         
         FGU4.4  This object is not supported.
         For GPON - SUPPORTED as of ISAM5.3.02
         For XG-PON1 - NOT SUPPORTED as of ISAM5.3.02
         For NG-PON2 - NOT SUPPORTED as of ISAM5.3.02
        "
::= {gxdslFarEndLineOperDataEntry 7}

gxdslFarEndLineActualPsdUpstream        OBJECT-TYPE
        SYNTAX          INTEGER
        ACCESS          read-only
        STATUS          mandatory
        DESCRIPTION     
        "This object gives the average transmit power spectrum density over the
         used carriers in the upstream direction as measured at the U-C
         reference point.
         When the modem is not in showtime this object will have the value
         measured during the previous showtime session.
         When no data is available (e.g. before first showtime) value 0
         is used.
         Range is -95.5 dBm/Hz to 0 dBm/Hz with 0,1 dB steps. The actual PSD is
         represented as 1/10 * xdslFarEndLineActualPsdUpstream.The special
         value 65535 indicates that the actual PSD is out of range.

         ALCATEL NOTE:
             ACCESS:   NA                  USAGE:    NA
             PERSIST:  NO                  INSRVMOD: NA
             RANGE:    -955..0, 65535      DEFVALUE: 0
             UNITS:    dBm/Hz * 1/10       SPARSE:   NA
             DESCR:    NA
        "
::= {gxdslFarEndLineOperDataEntry 8}

gxdslFarEndLinePerBandLoopAttenuationDownstream   OBJECT-TYPE
        SYNTAX          GPerBandOperDataType
        ACCESS          read-only
        STATUS          mandatory
        DESCRIPTION
        "This object indicates loop attenuation for each downstream
         band (including optional band) in case of VDSL2.
         It is represented for each band as 
         1/10 * xdslFarEndLinePerBandLoopAttenuationDownstream,
         with a range of (0..127dB) and a granularity of 0.1 dB.
         Max value is used to indicate that no Opdata is available for the
         corresponding band.
         OCTETS (0,1) represent value for band 0, coded as an integer in the
         range 0.. 1270. The special value 65535 indicates the attenuation
         per band is out of range to be represented.The value is defined as
         MSB-LSB (big-endian).
         OCTETS (2*N,2*N+1) represent value for band N, coded as an integer in
         the range 0.. 1270. The special value 65535 indicates the attenuation
         per band is out of range to be represented.The value is defined as
         MSB-LSB (big-endian).
         Maximum value for N is 4.

         ALCATEL NOTE:
             ACCESS:   NA                  USAGE:    NA
             PERSIST:  NO                  INSRVMOD: NA
             RANGE:    NA 
             DEFVALUE: 'FF FF FF FF FF FF FF FF FF FF'H
             UNITS:    NA                  SPARSE:   NA
             DESCR:    NA
        "
::= {gxdslFarEndLineOperDataEntry 9}

gxdslFarEndLinePerBandSignalAttenuationDownstream OBJECT-TYPE
        SYNTAX          GPerBandOperDataType
        ACCESS          read-only
        STATUS          mandatory
        DESCRIPTION
        "This object indicates signal attenuation for each downstream
         band (including optional band) in case of VDSL2.
         It is represented for each band
         as 1/10 * xdslFarEndLinePerBandSignalAttenuationDownstream,
         with a range of (0..127dB) and a granularity of 0.1 dB.
         Max value is used to indicate that no Opdata is available for the
         corresponding band.
         OCTETS (0,1) represent value for band 0, coded as an integer in the
         range 0.. 1270. The special value 65535 indicates the attenuation
         per band is out of range to be represented.The value is defined as
         MSB-LSB (big-endian).
         OCTETS (2*N,2*N+1) represent value for band N, coded as an integer in 
         the range 0.. 1270. The special value 65535 indicates the attenuation
         per band is out of range to be represented.The value is defined as
         MSB-LSB (big-endian).
         Maximum value for N is 4.

         ALCATEL NOTE:
             ACCESS:   NA                  USAGE:    NA
             PERSIST:  NO                  INSRVMOD: NA
             RANGE:    NA
             DEFVALUE: 'FF FF FF FF FF FF FF FF FF FF'H
             UNITS:    NA                  SPARSE:   NA
             DESCR:    NA
        "
::= {gxdslFarEndLineOperDataEntry 10}

gxdslFarEndLinePerBandNoiseMarginDownstream       OBJECT-TYPE
        SYNTAX          GPerBandOperDataType
        ACCESS          read-only
        STATUS          mandatory
        DESCRIPTION
        "This object indicates noise margin for each upstream band (including
         optional band) in case of VDSL2. It is represented as 1/10 * 
         xdslFarEndLinePerBandNoiseMarginDownstream, with a range of 
         (-64..63dB) and a granularity of 0.1 dB for each band.
         Max value is used to indicate that no Opdata is available for the
         corresponding band.
         OCTETS (0,1) represent value for band 0, coded as an integer in the
         range 0..1270(0 means -64dB and 1270 means 63dB).The special 
         value 65535 indicates the noise margin per band is out of range 
         to be represented.The value is defined as MSB-LSB (big-endian).
         OCTETS (2*N,2*N+1) represent value for band N, coded as an integer in 
         the range 0..1270(0 means -64dB and 1270 means 63dB).The special 
         value 65535 indicates the noise margin per band is out of range 
         to be represented.The value is defined as MSB-LSB (big-endian).
         Maximum value for N is 4.

         ALCATEL NOTE:
             ACCESS:   NA                  USAGE:    NA
             PERSIST:  NO                  INSRVMOD: NA
             RANGE:    NA
             DEFVALUE: 'FF FF FF FF FF FF FF FF FF FF'H
             UNITS:    NA                  SPARSE:   NA
             DESCR:    NA
        "
::= {gxdslFarEndLineOperDataEntry 11}

gxdslFarEndLineHighestFrequencyDownstream         OBJECT-TYPE
        SYNTAX          INTEGER
        ACCESS          read-only
        STATUS          mandatory
        DESCRIPTION
        "This object indicates the highest carrier frequency used
         in the downstream direction in case of VDSL2 and G.Fast.

         ALCATEL NOTE:
             ACCESS:   NA                  USAGE:    NA
             PERSIST:  NO                  INSRVMOD: NA
             RANGE:    NA                  DEFVALUE: 0
             UNITS:    kHz                 SPARSE:   NA
             DESCR:    NA
        
        
         FGU4.4:  THIS OBJECT IS NOT SUPPORTED
         For GPON - SUPPORTED as of ISAM5.3.02
         For XG-PON1 - NOT SUPPORTED as of ISAM5.3.02
         For NG-PON2 - NOT SUPPORTED as of ISAM5.3.02
        "
::= {gxdslFarEndLineOperDataEntry 12}

gxdslFarEndLineElectricalLengthEstimated          OBJECT-TYPE
        SYNTAX          INTEGER
        ACCESS          read-only
        STATUS          mandatory
        DESCRIPTION
        "This object indicates the Line Electrical Length actually estimated
         by XTU-R when mode is VDSL2.
         Range: 0 to 127.5 dB @ 1MHz , with 0.5 dB steps.
         Integer range: 0..255, actual value * 2.

         ALCATEL NOTE:
             ACCESS:   NA                  USAGE:    NA
             PERSIST:  NO                  INSRVMOD: NA
             RANGE:    0..255              DEFVALUE: 0
             UNITS:    dB/2 @ 1MHz         SPARSE:   NA
             DESCR:    NA
        
         FGU4.4:  THIS OBJECT IS NOT SUPPORTED
         For GPON - SUPPORTED as of ISAM5.3.02
         For XG-PON1 - NOT SUPPORTED as of ISAM5.3.02
         For NG-PON2 - NOT SUPPORTED as of ISAM5.3.02
        "
::= {gxdslFarEndLineOperDataEntry 13}

gxdslFarEndLineTimingAdvanceProposed    OBJECT-TYPE
        SYNTAX          INTEGER
        ACCESS          read-only
        STATUS          mandatory
        DESCRIPTION
        "This object defines the timing advance of transmitted symbol with 
         respect to the received symbol when mode is VDSL-2.  Near end value
         corresponds to the value proposed by XTU-R.
         Range: -250000..250000 ns in steps of 10 ns.
         Integer range: -25000..25000 (actual value / 10)

         ALCATEL NOTE:
             ACCESS:   NA                  USAGE:    NA
             PERSIST:  NO                  INSRVMOD: NA
             RANGE:    -25000..25000       DEFVALUE: 0
             UNITS:    ns * 10             SPARSE:   NA
             DESCR:    NA
        
        
         FGU4.4:  THIS OBJECT IS NOT SUPPORTED "
::= {gxdslFarEndLineOperDataEntry 14}

gxdslFarEndLineOperSpIndex  OBJECT-TYPE
	SYNTAX 	SpIndex
	ACCESS	not-accessible
	STATUS	mandatory
	DESCRIPTION 
		"Each row is also indexed by a number that
		 contains the slot number and port number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslFarEndLineOperDataEntry 15 }

gxdslFarEndLineActualVirtualNoiseSnrmModeDownstream OBJECT-TYPE
        SYNTAX          GSnrmMode	
        ACCESS          read-only
        STATUS          mandatory
        DESCRIPTION     
        "This object specifies the downstream mode of the  Virtual Noise Signal
         to Noise Ratio Margin, that is actually being used.
          snrmmode1: virtual noise is disabled.
          snrmmode2: virtual noise is enabled, using gvdsl2VirtualNoisePsdDownstream
                     as the transmitter referred noise
          snrmmode3: not supported, for future use

         ALCATEL NOTE:
             ACCESS:   NA                  USAGE:    NA
             PERSIST:  NA                  INSRVMOD: NA
             RANGE:    snrmMode1, snrmMode2
             DEFVALUE: snrmMode1
             UNITS:    NA                  SPARSE:   NA
             DESCR:    NA
        "
    ::= { gxdslFarEndLineOperDataEntry 16}


gxdslFarEndLineCarrierDataTable         OBJECT-TYPE
        SYNTAX          SEQUENCE OF GxdslFarEndLineCarrierDataEntry
        ACCESS          not-accessible
        STATUS          mandatory
        DESCRIPTION     
        "The xdsl far end line carrier data table.

         ALCATEL NOTE:
             TABLESIZE: DEP [number of XDSL lines]                   
             DESCR:     NA                  
        "
::= {gxdslFarEndLineCurrent 2}

gxdslFarEndLineCarrierDataEntry         OBJECT-TYPE
        SYNTAX          GxdslFarEndLineCarrierDataEntry                   
        ACCESS          not-accessible
        STATUS          mandatory
        DESCRIPTION     
        "An entry in the xdsl far end line carrier data table.

         Row creation : Entries for all XDSL lines belonging to a board are 
                        created when the board becomes operational.
         Row deletion : Entries for all XDSL lines belonging to a board are 
                        deleted when the board becomes unavailable.
        "
        INDEX          {ifIndex, gxdslFarEndLineCarrierSpIndex}
::= {gxdslFarEndLineCarrierDataTable 1}

GxdslFarEndLineCarrierDataEntry ::=
        SEQUENCE {
            gxdslFarEndLineCarrierLoadUpstream         OCTET STRING,
            gxdslFarEndLineCarrierGainUpstream         OCTET STRING,
            gxdslFarEndLineCarrierTssUpstream          OCTET STRING,
            gxdslFarEndLineCarrierSnrDownstream        OCTET STRING,
            gxdslFarEndLineCarrierQlnDownstream        OCTET STRING,
            gxdslFarEndLineCarrierHlinDownstream       OCTET STRING,
            gxdslFarEndLineCarrierHlogDownstream       OCTET STRING,
            gxdslFarEndLineCarrierSpacingUpstream      GCarrierSpacingType,
            gxdslFarEndLineCarrierTxPsdUpstream        OCTET STRING,
            gxdslFarEndLineCarrierGroupTxPsd           GSubCarrierGroupSizeType,
            gxdslFarEndLineCarrierGroupLoad            GSubCarrierGroupSizeType,
            gxdslFarEndLineCarrierGroupGain            GSubCarrierGroupSizeType,
            gxdslFarEndLineCarrierGroupTss            GSubCarrierGroupSizeType,
            gxdslFarEndLineCarrierGroupSnr             GSubCarrierGroupSizeType,
            gxdslFarEndLineCarrierGroupQln             GSubCarrierGroupSizeType,
            gxdslFarEndLineCarrierGroupHLin            GSubCarrierGroupSizeType,
            gxdslFarEndLineCarrierGroupHLog            GSubCarrierGroupSizeType,
            gxdslFarEndLineCarrierSpIndex              SpIndex
        }

gxdslFarEndLineCarrierLoadUpstream      OBJECT-TYPE
        SYNTAX          OCTET STRING
        ACCESS          read-only
        STATUS          mandatory
        DESCRIPTION     
        "This object represents the bit load distribution i.e. the number of
         bits per carrier group over the upstream passband.
         When the modem is not in showtime this object will have the previously
         measured value.
         When the data are not available because the measurement is not
         completed, not enabled or not supported, an empty string will be
         returned.
         The XDSL upstream passband is composed of one or more bands (maximum
         5,including VDSL optional band). Each carrier can carry up to 15 bits.
         The carrier load is coded as a bitmap defined as follows:
         OCTETS 0,1: INTEGER (0..4096), index of the start carrier group of the
         first upstream band. The value is defined as MSB-LSB (big-endian).
         OCTETS 2,3: INTEGER (0..4096), index of the stop carrier group of the
         first upstream band. The value is defined as MSB-LSB (big-endian).
         OCTET 4: contains the bit load of the first two carrier groups of the
         band. The load of the first carrier group uses the most significant 4
         bits nibble.
         Range is 0-15 bits per carrier group, with a granularity of 1 bit/
         carrier group.
         OCTETS 5..L: and so on, up to the last carrier group of the first
         upstream band. The last nibble of OCTET L is set to 0x0 if not used.
         OCTETS L+1..M: contain the start/stop carrier groups and the carrier
         load of the second upstream band when available.
         OCTETS M+1..N: contain the start/stop carrier groups and the carrier
         load of the third upstream band when available.
         OCTETS N+1..P: contain the start/stop carrier groups and the carrier
         load of the fourth upstream band when available.
         OCTETS P+1..Q: contain the start/stop carrier groups and the carrier
         load of the fifth upstream band when available.

         ALCATEL NOTE:
             ACCESS:   NA                  USAGE:    NA
             PERSIST:  NO                  INSRVMOD: NA
             RANGE:    0..4117             DEFVALUE: ''H
             UNITS:    octets              SPARSE:   NA
             DESCR:    NA
        "
::= {gxdslFarEndLineCarrierDataEntry 1}

gxdslFarEndLineCarrierGainUpstream      OBJECT-TYPE
        SYNTAX          OCTET STRING
        ACCESS          read-only
        STATUS          mandatory
        DESCRIPTION     
        "This object provides the gain allocation (i.e. gi) per carrier group
         over the upstream passband.
         When the modem is not in showtime this object will have the previously
         measured value.
         When the data are not available because the measurement is not
         completed, not enabled or not supported, an empty string will be
         returned.
         The XDSL upstream passband is composed of one or more bands (maximum
         5, including VDSL optional band ).
         The gain has a range of approximately 0 - 8, in steps of 1/512. 
         The gain value is represented as gi/512 on a linear scale with gi a
         12 bits unsigned integer in the 0 to 4095 range given by the 12 LSB
         bits of a 2 bytes integer. 
         The carrier gain allocation is coded as a bitmap defined as follows:
         OCTETS 0,1: INTEGER (0..4096), index of the start carrier group of the
         first upstream band. The value is defined as MSB-LSB (big-endian).
         OCTETS 2,3: INTEGER (0..4096), index of the stop carrier group of the
         first upstream band. The value is defined as MSB-LSB (big-endian).
         OCTETS 4,5: INTEGER, contains the gain of the first carrier group of
         the band (start carrier group). 
         The value is defined as MSB-LSB (big-endian).
         OCTETS 6..L: and so on until the last carrier group of the first
         upstream band (stop carrier group).
         OCTETS L+1..M: contain the start/stop carrier groups and the carrier
         gain of the second upstream band when available.
         OCTETS M+1..N: contain the start/stop carrier groups and the carrier
         gain of the third upstream band when available.
         OCTETS N+1..P: contain the start/stop carrier groups and the carrier
         gain of the fourth upstream band when available.
         OCTETS P+1..Q: contain the start/stop carrier groups and the carrier
         gain of the fifth upstream band when available.

         ALCATEL NOTE:
             ACCESS:   NA                  USAGE:    NA
             PERSIST:  NO                  INSRVMOD: NA
             RANGE:    0..8214             DEFVALUE: ''H
             UNITS:    octets              SPARSE:   NA
             DESCR:    NA "
::= {gxdslFarEndLineCarrierDataEntry 2}

gxdslFarEndLineCarrierTssUpstream     OBJECT-TYPE
        SYNTAX                    OCTET STRING
        ACCESS                    read-only
        STATUS                    mandatory
        DESCRIPTION     
         "This object provides the Transmit Spectrum Shaping parameters
         (i.e. tssi) for the upstream direction.
         Its definition is for further study.
         ALCATEL NOTE:
             ACCESS:   NA                  USAGE:    NA
             PERSIST:  NA                  INSRVMOD: NA
             RANGE:    NA                  DEFVALUE: NA
             UNITS:    NA                  SPARSE:   NA
             DESCR:    This object is not supported.
         
         FGU4.4:  THIS OBJECT IS NOT SUPPORTED "
::= {gxdslFarEndLineCarrierDataEntry 3}

gxdslFarEndLineCarrierSnrDownstream     OBJECT-TYPE
        SYNTAX          OCTET STRING
        ACCESS          read-only
        STATUS          mandatory
        DESCRIPTION     
        "This object provides the Signal to Noise Ratio per carrier group over
         the downstream passband.
         When the modem is not in showtime this object will have the previously
         measured value.
         When the data are not available because the measurement is not
         completed, not enabled or not supported, an empty string will be
         returned.
         The XDSL downstream passband is composed of one or more bands (maximum
         5, including VDSL optional band).
         The SNR has a range from -32 to 95 dB in steps of 0.5 dB.
         It is represented as SNRi = -32 + snri/2, with snri an 8 bit
         unsigned integer in the range 0 to 254.
         The special value 255 indicates that no measurement is available for
         the carrier or that the measurement is out of range.
         The carrier snrs are coded as a bitmap defined as follows:
         OCTETS 0,1: INTEGER, contains the number of symbols used to
         measure the data. The value is defined as MSB-LSB (big-endian).
         OCTETS 2,3: INTEGER (0..4096), index of the start carrier group of the
         first downstream band. The value is defined as MSB-LSB (big-endian).
         OCTETS 4,5: INTEGER (0..4096), index of the stop carrier group of the
         first downstream band. The value is defined as MSB-LSB (big-endian).
         OCTETS 6: INTEGER, contains the snr of the first carrier group of the
         band (start carrier group).
         OCTETS 7..L: and so on until the last carrier group of the first
         downstream band (stop carrier group).
         OCTETS L+1..M: contain the start/stop carrier groups and the carrier
         snr of the second downstream band when available.
         OCTETS M+1..N: contain the start/stop carrier groups and the carrier
         snr of the third downstream band when available.
         OCTETS N+1..P: contain the start/stop carrier groups and the carrier
         snr of the fourth downstream band when available.
         OCTETS P+1..Q: contain the start/stop carrier groups and the carrier
         snr of the fifth downstream band when available.

         ALCATEL NOTE:
             ACCESS:   NA                  USAGE:    NA
             PERSIST:  NO                  INSRVMOD: NA
             RANGE:    0..4119             DEFVALUE: ''H
             UNITS:    octets              SPARSE:   NA
             DESCR:    NA "
::= {gxdslFarEndLineCarrierDataEntry 4}

gxdslFarEndLineCarrierQlnDownstream     OBJECT-TYPE
        SYNTAX          OCTET STRING
        ACCESS          read-only
        STATUS          mandatory
        DESCRIPTION     
        "This object provides the Quiet Line Noise measurement (QLN) per
         carrier group over the downstream passband.
         When the data are not available because the measurement is not
         completed, not enabled or not supported, an empty string will be
         returned.
         The XDSL downstream passband is composed of one or more bands (maximum
         5, including VDSL optional band).
         The QLN has a range from -150 dBm/Hz to -23 dBm/Hz in steps of
         0.5 dB. It is represented as QLNi = -23 - qlni/2, with qlni an 8 bit
         unsigned integer in the range 0 to 254.
         The special value 255 indicates that no measurement is available for
         the carrier or that the measurement is out of range.
         The carrier qlns are coded as a bitmap defined as follows:
         OCTETS 0,1: INTEGER, contains the number of symbols used to
         measure the data. The value is defined as MSB-LSB (big-endian).
         OCTETS 2,3: INTEGER (0..4096), index of the start carrier group of the
         first downstream band. The value is defined as MSB-LSB (big-endian).
         OCTETS 4,5: INTEGER (0..4096), index of the stop carrier group of the
         first downstream band. The value is defined as MSB-LSB (big-endian).
         OCTETS 6: INTEGER, contains the qln of the first carrier group of the
         band (start carrier group).
         OCTETS 7..L: and so on until the last carrier group of the first
         downstream band (stop carrier group).
         OCTETS L+1..M: contain the start/stop carrier groups and the carrier
         qln of the second downstream band when available.
         OCTETS M+1..N: contain the start/stop carrier groups and the carrier
         qln of the third downstream band when available.
         OCTETS N+1..P: contain the start/stop carrier groups and the carrier
         qln of the fourth downstream band when available.
         OCTETS P+1..Q: contain the start/stop carrier groups and the carrier
         qln of the fifth downstream band when available.

         ALCATEL NOTE:
             ACCESS:   NA                  USAGE:    NA
             PERSIST:  NO                  INSRVMOD: NA
             RANGE:    0..4119             DEFVALUE: ''H
             UNITS:    octets              SPARSE:   NA
             DESCR:    NA "
::= {gxdslFarEndLineCarrierDataEntry 5}

gxdslFarEndLineCarrierHlinDownstream    OBJECT-TYPE
        SYNTAX          OCTET STRING
        ACCESS          read-only
        STATUS          mandatory
        DESCRIPTION      
        "This object provides the channel characteristics function complex
         values in linear scale for each carrier group over the downstream
         passband.
         When the data are not available because the measurement is not
         completed, not enabled or not supported, an empty string will be
         returned.
         The XDSL downstream passband is composed of one or more bands (maximum
         5, including VDSL optional band).
         HLIN has a range of approximately +6 dB to -90 dB, with a granularity
         of 2^-15. The Hlin is represented as
         HLINi = (scale/2^15)*((ai+j*bi)/2^15),
         with ai and bi 2 bytes signed integers in the range -32767 to 32767.
         The special value -32768 indicates that no measurement is available
         for the carrier or that the measurement is out of range.
         The scale factor is a 2 bytes unsigned integer. The scale factor
         must be chosen such that:
         max(|Ai|,|Bi|) over all i is equal to 2^15-1, i.e. over all carriers
         of the XDSL band(s) of the corresponding direction.

         The carrier HLINs are coded as a bitmap defined as follows:
         OCTETS 0,1: INTEGER, contains the number of symbols used to
         measure the data. The value is defined as MSB-LSB (big-endian).
         OCTETS 2,3: INTEGER(0..65535), contains the scale factor to apply to
         the hlin values over the downstream band(s).
         The value is defined as MSB-LSB (big-endian).
         OCTETS 4,5: INTEGER (0..4096), index of the start carrier group of the
         first downstream band. The value is defined as MSB-LSB (big-endian).
         OCTETS 6,7: INTEGER (0..4096), index of the stop carrier group of the
         first downstream band. The value is defined as MSB-LSB (big-endian).
         OCTETS 8,9: SIGNED INTEGER , contains the ai for the first carrier
         group of the band (start carrier group).
         The value is defined as MSB-LSB (big-endian).
         OCTETS 10,11: SIGNED INTEGER , contains the bi for the first carrier
         group of the band (start carrier group).
         The value is defined as MSB-LSB (big-endian).
         OCTETS 12..L: ai and bi for the next carrier group and so on until the
         last carrier group of the first downstream band (stop carrier group).
         OCTETS L+1..M: contain the start/stop carrier groups and the HLIN ai
         and bi of the second downstream band when available.
         OCTETS M+1..N: contain the start/stop carrier groups and the HLIN ai
         and bi of the third downstream band when available.
         OCTETS N+1..P: contain the start/stop carrier groups and the HLIN ai
         and bi of the fourth downstream band when available.
         OCTETS P+1..Q: contain the start/stop carrier groups and the HLIN ai
         and bi of the fifth downstream band when available.

         ALCATEL NOTE:
             ACCESS:   NA                  USAGE:    NA
             PERSIST:  NO                  INSRVMOD: NA
             RANGE:    0..8218             DEFVALUE: ''H
             UNITS:    octets              SPARSE:   NA
             DESCR:    NA "
::= {gxdslFarEndLineCarrierDataEntry 6}

gxdslFarEndLineCarrierHlogDownstream    OBJECT-TYPE
        SYNTAX          OCTET STRING
        ACCESS          read-only
        STATUS          mandatory
        DESCRIPTION     
        "This object provides the channel characteristics function real values
         in dB for each carrier group over the downstream passband.
         When the data are not available because the measurement is not
         completed, not enabled or not supported, an empty string will be
         returned.
         The XDSL downstream passband is composed of one or more bands (maximum
         5, including VDSL optional band).
         Hlog has a range of approximately +6 dB to - 96 dB in steps of
         0.1 dB. The Hlog is represented as HLOGi = 6 - mi/10,
         with mi a 10 bits unsigned integer in the range 0 to 1022.
         The special value 1023 indicates that no measurement is available for
         the carrier or that the measurement is out of range.

         The carrier HLOGs are coded as a bitmap defined as follows:
         OCTETS 0,1: INTEGER, contains the number of symbols used to
         measure the data. The value is defined as MSB-LSB (big-endian).
         OCTETS 2,3: INTEGER (0..4096), index of the start carrier group of the
         first downstream band. The value is defined as MSB-LSB (big-endian).
         OCTETS 4,5: INTEGER (0..4096), index of the stop carrier group of the
         first downstream band. The value is defined as MSB-LSB (big-endian).
         OCTETS 6,7: INTEGER (0..1023), contains the HLOG mi of the first
         carrier group of the band (start carrier group).
         The value is defined as MSB-LSB (big-endian).
         OCTETS 8..L: mi for the next carrier group and so on until the last
         carrier group of the first downstream band (stop carrier group).
         OCTETS L+1..M: contain the start/stop carrier groups and the HLOG mi
         of the second downstream band when available.
         OCTETS M+1..N: contain the start/stop carrier groups and the HLOG mi
         of the third downstream band when available.
         OCTETS N+1..P: contain the start/stop carrier groups and the HLOG mi
         of the fourth downstream band when available.
         OCTETS P+1..Q: contain the start/stop carrier groups and the HLOG mi
         of the fifth downstream band when available.

         ALCATEL NOTE:
             ACCESS:   NA                  USAGE:    NA
             PERSIST:  NO                  INSRVMOD: NA
             RANGE:    0..8216             DEFVALUE: ''H
             UNITS:    octets              SPARSE:   NA
             DESCR:    NA "
::= {gxdslFarEndLineCarrierDataEntry 7}

gxdslFarEndLineCarrierSpacingUpstream   OBJECT-TYPE
        SYNTAX          GCarrierSpacingType
        ACCESS          read-only
        STATUS          mandatory
        DESCRIPTION     
        "This object provides the actual carrier spacing used on the XDSL line
         in the upstream direction:
          singleCarrierSpacing:  4.3125 kHz 
          doubleCarrierSpacing:  8.6250 kHz 
          halfCarrierSpacing:    2.15625 kHz 
          quarterCarrierSpacing: 1.078125 kHz

         ALCATEL NOTE:
             ACCESS:   NA                  USAGE:    NA
             PERSIST:  NO                  INSRVMOD: NA
             RANGE:    NA                  DEFVALUE: NA
             UNITS:    NA                  SPARSE:   NA
             DESCR:    NA
        "
::= {gxdslFarEndLineCarrierDataEntry 8}

gxdslFarEndLineCarrierTxPsdUpstream     OBJECT-TYPE
        SYNTAX          OCTET STRING
        ACCESS          read-only
        STATUS          mandatory
        DESCRIPTION
        "Provides the actual transmit PSD per carrier group over the
         upstream passband.
         When the modem is not in showtime this object will have the previously
         measured value.
         When the data are not available because the measurement is not
         completed, not enabled or not supported, an empty string will be
         returned.
         The XDSL upstream passband is composed of one or more bands (maximum
         5, including VDSL optional band). 
         The PSD has a range from -127 dBm/Hz to 0 dBm/Hz in steps of 0.5 dB.
         It is represented as PSDi = - psdi/2, with psdi an 8 bit
         unsigned integer in the range 0 to 254.
         The special value 255 indicates that no measurement is available for
         the carrier, the carrier is not loaded, or that the measurement is out
         of range.
         The carrier Tx PSD is coded as a bitmap defined as follows:
         OCTETS 0,1: INTEGER (0..4096), index of the start carrier group of the
         upstream band. The value is defined as MSB-LSB (big-endian).
         OCTETS 2,3: INTEGER (0..4096), index of the stop carrier group of the
         upstream band. The value is defined as MSB-LSB (big-endian).
         OCTET 4: INTEGER(0..255), PSD of the first carrier group of the band
         (start carrier group).
         OCTETS 5..L: and so on until the last carrier group of the first
         downstream band (stop carrier group).
         OCTETS L+1..M: contain the start/stop carrier groups and the carrier
         PSD of the second upstream band when available.
         OCTETS M+1..N: contain the start/stop carrier groups and the carrier
         PSD of the third upstream band when available.
         OCTETS N+1..P: contain the start/stop carrier groups and the carrier
         PSD of the fourth upstream band when available.
         OCTETS P+1..Q: contain the start/stop carrier groups and the carrier
         PSD of the fifth upstream band when available.

         ALCATEL NOTE:
             ACCESS:   NA                  USAGE:    NA
             PERSIST:  NO                  INSRVMOD: NA
             RANGE:    0..4117             DEFVALUE: ''H
             UNITS:    octets              SPARSE:   NA
             DESCR:    NA
        
         FGU4.4: THIS OBJECT IS NOT SUPPORTED "
::= {gxdslFarEndLineCarrierDataEntry 9}

gxdslFarEndLineCarrierGroupTxPsd        OBJECT-TYPE
        SYNTAX          GSubCarrierGroupSizeType
        ACCESS          read-only
        STATUS          mandatory
        DESCRIPTION
        "Provides the grouping factor for Actual Tx Power Spectrum Density
         carrier data octet-string.  The grouping factor represents the number
         of carriers that have been grouped together in view to reduce data 
         size.The valid value is 1/2/4/8 and the invalid value is 0.

         ALCATEL NOTE:
             ACCESS:   NA                  USAGE:    NA
             PERSIST:  NO                  INSRVMOD: NA
             RANGE:    0, 1, 2, 4, 8       DEFVALUE: 1
             UNITS:    NA                  SPARSE:   NA
             DESCR:    NA
        
         FGU4.4: THIS OBJECT IS NOT SUPPORTED "
::= {gxdslFarEndLineCarrierDataEntry 10}

gxdslFarEndLineCarrierGroupLoad         OBJECT-TYPE
        SYNTAX          GSubCarrierGroupSizeType
        ACCESS          read-only
        STATUS          mandatory
        DESCRIPTION
        "Provides the grouping factor for carrier load data octet-
         string.  The grouping factor represents the number of carriers that
         have been grouped together in view to reduce data size.
         The valid value is 1/2/4/8 and the invalid value is 0.

         ALCATEL NOTE:
             ACCESS:   NA                  USAGE:    NA
             PERSIST:  NO                  INSRVMOD: NA
             RANGE:    0, 1, 2, 4, 8       DEFVALUE: 1
             UNITS:    NA                  SPARSE:   NA
             DESCR:    NA

	For FGU4.4, the only supported value is 1.  "
::= {gxdslFarEndLineCarrierDataEntry 11}

gxdslFarEndLineCarrierGroupGain         OBJECT-TYPE
        SYNTAX          GSubCarrierGroupSizeType
        ACCESS          read-only
        STATUS          mandatory
        DESCRIPTION
        "Provides the grouping factor for carrier gain allocation data octet-
         string.  The grouping factor represents the number of carriers that
         have been grouped together in view to reduce data size.
         The valid value is 1/2/4/8 and the invalid value is 0.

         ALCATEL NOTE:
             ACCESS:   NA                  USAGE:    NA
             PERSIST:  NO                  INSRVMOD: NA
             RANGE:    0, 1, 2, 4, 8          DEFVALUE: 1
             UNITS:    NA                  SPARSE:   NA
             DESCR:    NA

	For FGU4.4, the only supported value is 1.  "
::= {gxdslFarEndLineCarrierDataEntry 12}

gxdslFarEndLineCarrierGroupTss				OBJECT-TYPE
		SYNTAX					GSubCarrierGroupSizeType
		ACCESS					read-only
		STATUS					mandatory
		DESCRIPTION
		"Provides the grouping factor for Transmit Spectrum Shaping carrier data
		 octet-string.  The grouping factor represents the number of carriers that
		 have been grouped together in view to reduce data size.
         ALCATEL NOTE:
             ACCESS:   NA                  USAGE:    NA
             PERSIST:  NA                  INSRVMOD: NA
             RANGE:    NA                  DEFVALUE: NA
             UNITS:    NA                  SPARSE:   NA
             DESCR:    This object is not supported.
         
         FGU4.4:  THIS OBJECT IS NOT SUPPORTED "
::= {gxdslFarEndLineCarrierDataEntry 13}

gxdslFarEndLineCarrierGroupSnr          OBJECT-TYPE
        SYNTAX          GSubCarrierGroupSizeType
        ACCESS          read-only
        STATUS          mandatory
        DESCRIPTION
        "Provides the grouping factor for Signal to Noise Ratio per carrier
         data octet-string.  The grouping factor represents the number of 
         carriers that have been grouped together in view to reduce data size.
         The valid value is 1/2/4/8 and the invalid value is 0.

         ALCATEL NOTE:
             ACCESS:   NA                  USAGE:    NA
             PERSIST:  NO                  INSRVMOD: NA
             RANGE:    0, 1, 2, 4, 8       DEFVALUE: 1
             UNITS:    NA                  SPARSE:   NA
             DESCR:    NA "
::= {gxdslFarEndLineCarrierDataEntry 14}

gxdslFarEndLineCarrierGroupQln          OBJECT-TYPE
        SYNTAX          GSubCarrierGroupSizeType
        ACCESS          read-only
        STATUS          mandatory
        DESCRIPTION
        "Provides the grouping factor for Quiet Line Noise data octet-
         string.  The grouping factor represents the number of carriers that
         have been grouped together in view to reduce data size.
         The valid value is 1/2/4/8 and the invalid value is 0.

         ALCATEL NOTE:
             ACCESS:   NA                  USAGE:    NA
             PERSIST:  NO                  INSRVMOD: NA
             RANGE:    0, 1, 2, 4, 8          DEFVALUE: 1
             UNITS:    NA                  SPARSE:   NA
             DESCR:    NA "
::= {gxdslFarEndLineCarrierDataEntry 15}

gxdslFarEndLineCarrierGroupHLin         OBJECT-TYPE
        SYNTAX          GSubCarrierGroupSizeType
        ACCESS          read-only
        STATUS          mandatory
        DESCRIPTION
        "Provides the grouping factor for Complex Channel Characteristics data
         in linear scale.  The grouping factor represents the number of 
         carriers that have been grouped together in view to reduce data size.
         The valid value is 1/2/4/8 and the invalid value is 0.

         ALCATEL NOTE:
             ACCESS:   NA                  USAGE:    NA
             PERSIST:  NO                  INSRVMOD: NA
             RANGE:    0, 1, 2, 4, 8          DEFVALUE: 1
             UNITS:    NA                  SPARSE:   NA
             DESCR:    NA "
::= {gxdslFarEndLineCarrierDataEntry 16}

gxdslFarEndLineCarrierGroupHLog         OBJECT-TYPE
        SYNTAX          GSubCarrierGroupSizeType
        ACCESS          read-only
        STATUS          mandatory
        DESCRIPTION
        "Provides the grouping factor for Channel Characteristics data in dB.
         The grouping factor represents the number of carriers that
         have been grouped together in view to reduce data size.
         The valid value is 1/2/4/8 and the invalid value is 0.

         ALCATEL NOTE:
             ACCESS:   NA                  USAGE:    NA
             PERSIST:  NO                  INSRVMOD: NA
             RANGE:    0, 1, 2, 4, 8          DEFVALUE: 1
             UNITS:    NA                  SPARSE:   NA
             DESCR:    NA  "
::= {gxdslFarEndLineCarrierDataEntry 17}

gxdslFarEndLineCarrierSpIndex  OBJECT-TYPE
	SYNTAX 	SpIndex
	ACCESS	not-accessible
	STATUS	mandatory
	DESCRIPTION 
		"Each row is also indexed by a number that
		 contains the slot number and port number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslFarEndLineCarrierDataEntry 18 }


gxdslFarEndLineFailureStatusTable       OBJECT-TYPE
        SYNTAX          SEQUENCE OF GxdslFarEndLineFailureStatusEntry
        ACCESS          not-accessible
        STATUS          mandatory
        DESCRIPTION     
        "The xdsl far end line failure status table.

         ALCATEL NOTE:
             TABLESIZE: DEP [number of XDSL lines]                   
             DESCR:     NA                  
        "
::= {gxdslFarEndLineCurrent 3}
        
gxdslFarEndLineFailureStatusEntry       OBJECT-TYPE
        SYNTAX          GxdslFarEndLineFailureStatusEntry                        
        ACCESS          not-accessible
        STATUS          mandatory
        DESCRIPTION     
        "An entry in the xdsl line far end failure status table.

         Row creation : Entries for all XDSL lines belonging to a board are 
                        created when the board becomes operational.
         Row deletion : Entries for all XDSL lines belonging to a board are 
                        deleted when the board becomes unavailable.
        "
        INDEX          {ifIndex, gxdslFarEndLineFailureSpIndex}
::= {gxdslFarEndLineFailureStatusTable 1}
        
GxdslFarEndLineFailureStatusEntry ::=
        SEQUENCE {
                gxdslFarEndLineFailureStatus             INTEGER,
                gxdslFarEndLineFailureSpIndex            SpIndex
        }

gxdslFarEndLineFailureStatus            OBJECT-TYPE
        SYNTAX          INTEGER (1..65535)
        ACCESS          read-only
        STATUS          mandatory
        DESCRIPTION 
        "This variable indicates the status of the far end interface. It is
         a bitmap represented as a sum, therefore, it can represent multiple
         failure simultaneuosly. The xdslFarEndLineNoFailure should be set if
         and only if no other flag is set. The various bit positions are:
             1      xdslFarEndLineNoFailure
2      xdslFarEndLineLOS (loss of signal) in the downstream 
                    direction
             4      xdslFarEndLineLOF (loss of frame) in the downstream
                    direction 
             8      xdslFarEndLineLOM (loss of margin) in the downstream
                    direction 
            16      xdslFarEndLineLPR (loss of power) of the XTU-R
            32      xdslFarEndLineLOL (loss of link)
            64      xdslFarEndLineESE (Excessive severe errors)
           128      xdslFarEndLineActivationFailure due to communication
                    problems  
           256      xdslFarEndLineActivationFailure due to no XTU-R detected
    512 ..2048      reserved
          4096      xdslFarEndLineBitrateThreshold for the downstream
                    direction.

         ALCATEL NOTE:
             ACCESS:   NA                  USAGE:    NA
             PERSIST:  NO                  INSRVMOD: NA
             RANGE:    NA                  DEFVALUE: 1
             UNITS:    NA                  SPARSE:   NA
             DESCR:    NA
        "
::= {gxdslFarEndLineFailureStatusEntry 1}


gxdslFarEndLineFailureSpIndex  OBJECT-TYPE
	SYNTAX 	SpIndex
	ACCESS	not-accessible
	STATUS	mandatory
	DESCRIPTION 
		"Each row is also indexed by a number that
		 contains the slot number and port number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslFarEndLineFailureStatusEntry 2 }

gxdslFarEndLineCurrentIntervalTable     OBJECT-TYPE
        SYNTAX          SEQUENCE OF GxdslFarEndLineCurrentIntervalEntry
        ACCESS          not-accessible
        STATUS          mandatory
        DESCRIPTION 
        "The xdsl far end line current interval table.

         ALCATEL NOTE:
             TABLESIZE: DEP [number of XDSL lines]                    
             DESCR:     NA                  
        "
::= {gxdslFarEndLineCurrent 4}
        
gxdslFarEndLineCurrentIntervalEntry     OBJECT-TYPE
        SYNTAX          GxdslFarEndLineCurrentIntervalEntry                      
        ACCESS          not-accessible
        STATUS          mandatory
        DESCRIPTION     
        "An entry in the xdsl far end line current interval table.

         Row creation : Entries for all XDSL lines belonging to a board are 
                        created when the board becomes operational.
         Row deletion : Entries for all XDSL lines belonging to a board are 
                        deleted when the board becomes unavailable.
        "
        INDEX          {ifIndex, gxdslFarEndLineCurrentSpIndex}
::= {gxdslFarEndLineCurrentIntervalTable 1}

GxdslFarEndLineCurrentIntervalEntry ::=
        SEQUENCE {
            gxdslFarEndLineCurrentIntervalLOSCounter      Counter,
            gxdslFarEndLineCurrentIntervalLOFCounter      Counter,
            gxdslFarEndLineCurrentIntervalLOMCounter      Counter,
            gxdslFarEndLineCurrentIntervalLPRCounter      Counter,
            gxdslFarEndLineCurrentIntervalLOLCounter      Counter,
            gxdslFarEndLineCurrentIntervalESECounter      Counter,
            gxdslFarEndLineCurrentIntervalESCounter       Counter,
            gxdslFarEndLineCurrentIntervalSESCounter      Counter,
            gxdslFarEndLineCurrentIntervalUASCounter      Counter,
            gxdslFarEndLineCurrentIntervalMeasuredTime    INTEGER,        
            gxdslFarEndLineCurrentIntervalInvalidDataFlag INTEGER,
            gxdslFarEndLineCurrentIntervalRAUCounter      Counter,
            gxdslFarEndLineCurrentIntervalRADCounter      Counter,
            gxdslFarEndLineCurrentSpIndex                 SpIndex
        }        

gxdslFarEndLineCurrentIntervalLOSCounter          OBJECT-TYPE
        SYNTAX          Counter
        ACCESS          read-only
        STATUS          mandatory
        DESCRIPTION     
        "This object represents for the current 15 minute interval the LOS 
         failure count, which is the number of occurences of an LOS failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA
        
         FGU4.4: THIS OBJECT IS IMPLEMENTED AS LOS SECONDS PER CUSTOMER REQUIREMENT"
::= {gxdslFarEndLineCurrentIntervalEntry 1}

gxdslFarEndLineCurrentIntervalLOFCounter          OBJECT-TYPE
        SYNTAX          Counter
        ACCESS          read-only
        STATUS          mandatory
        DESCRIPTION     
        "This object represents for the current 15 minute interval the LOF 
         failure count, which is the number of occurences of an LOF failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA
        "
::= {gxdslFarEndLineCurrentIntervalEntry 2}

gxdslFarEndLineCurrentIntervalLOMCounter          OBJECT-TYPE
        SYNTAX          Counter
        ACCESS          read-only
        STATUS          mandatory
        DESCRIPTION     
        "This object represents for the current 15 minute interval the LOM 
         failure count, which is the number of occurences of an LOM failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED"
::= {gxdslFarEndLineCurrentIntervalEntry 3}

gxdslFarEndLineCurrentIntervalLPRCounter          OBJECT-TYPE
        SYNTAX          Counter
        ACCESS          read-only
        STATUS          mandatory
        DESCRIPTION     
        "This object represents for the current 15 minute interval the LPR 
         failure count, which is the number of occurences of an LPR failure 
         event, where a failure event occurs when the failure is declared and 
         ends when the failure  clears.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED"
::= {gxdslFarEndLineCurrentIntervalEntry 4}

gxdslFarEndLineCurrentIntervalLOLCounter          OBJECT-TYPE
        SYNTAX          Counter
        ACCESS          read-only
        STATUS          mandatory
        DESCRIPTION     
        "This object represents for the current 15 minute interval the LOL 
         failure count, which is the number of occurences of an LOL failure 
         event, where a failure event occurs when the failure is declared and 
         ends when the failure clears.

         ALCATEL NOTE:
             ACCESS:   NA                  USAGE:    NA
             PERSIST:  NO                  INSRVMOD: NA
             RANGE:    0                   DEFVALUE: 0
             UNITS:    NA                  SPARSE:   NA
             DESCR:    Because an LOL failure event never occurs, the value of
                       the counter is always 0.
        
        
         FGU4.4:  THIS OBJECT IS NOT SUPPORTED"
::= {gxdslFarEndLineCurrentIntervalEntry 5}

gxdslFarEndLineCurrentIntervalESECounter          OBJECT-TYPE
        SYNTAX          Counter
        ACCESS          read-only
        STATUS          mandatory
        DESCRIPTION     
        "This object represents for the current 15 minute interval the ESE 
         failure count, which is the number of occurences of an ESE failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED"
::= {gxdslFarEndLineCurrentIntervalEntry 6}

gxdslFarEndLineCurrentIntervalESCounter OBJECT-TYPE
        SYNTAX          Counter
        ACCESS          read-only
        STATUS          mandatory
        DESCRIPTION     
        "The counter associated with the number of Errored Seconds encountered 
         by the line in the current 15 min interval.

         ALCATEL NOTE:
             ACCESS:   NA                  USAGE:    NA
             PERSIST:  NO                  INSRVMOD: NA
             RANGE:    NA                  DEFVALUE: 0
             UNITS:    NA                  SPARSE:   NA
             DESCR:    NA
        "
::= {gxdslFarEndLineCurrentIntervalEntry 7}

gxdslFarEndLineCurrentIntervalSESCounter          OBJECT-TYPE
        SYNTAX          Counter
        ACCESS          read-only
        STATUS          mandatory
        DESCRIPTION     
        "The counter associated with the number of Severely Errored Seconds
         encountered by the line in the current 15 min interval.

         ALCATEL NOTE:
             ACCESS:   NA                  USAGE:    NA
             PERSIST:  NO                  INSRVMOD: NA
             RANGE:    NA                  DEFVALUE: 0
             UNITS:    NA                  SPARSE:   NA
             DESCR:    NA
        "
::= {gxdslFarEndLineCurrentIntervalEntry 8}

gxdslFarEndLineCurrentIntervalUASCounter          OBJECT-TYPE
        SYNTAX          Counter
        ACCESS          read-only
        STATUS          mandatory
        DESCRIPTION     
        "The counter associated with the number of Unavailable Seconds
         encountered by the line in the current 15 min interval.

         ALCATEL NOTE:
             ACCESS:   NA                  USAGE:    NA
             PERSIST:  NO                  INSRVMOD: NA
             RANGE:    NA                  DEFVALUE: 0
             UNITS:    NA                  SPARSE:   NA
             DESCR:    NA
        "
::= {gxdslFarEndLineCurrentIntervalEntry 9}

gxdslFarEndLineCurrentIntervalMeasuredTime        OBJECT-TYPE
        SYNTAX          INTEGER(0..900)
        ACCESS          read-only
        STATUS          mandatory
        DESCRIPTION     
        "The amount of time, measured in seconds, that statistics for this 
         entry have been counted.

         ALCATEL NOTE:
             ACCESS:   NA                  USAGE:    NA
             PERSIST:  NO                  INSRVMOD: NA
             RANGE:    NA                  DEFVALUE: 0
             UNITS:    seconds             SPARSE:   NA
             DESCR:    NA
        
        
         FGU4.4:  THIS OBJECT IS NOT SUPPORTED"
::= {gxdslFarEndLineCurrentIntervalEntry 10}

gxdslFarEndLineCurrentIntervalInvalidDataFlag     OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA
        
        
         FGU4.4:  THIS OBJECT IS NOT SUPPORTED"
::= {gxdslFarEndLineCurrentIntervalEntry 11}

gxdslFarEndLineCurrentIntervalRAUCounter          OBJECT-TYPE
        SYNTAX          Counter
        ACCESS          read-only
        STATUS          mandatory
        DESCRIPTION     
        "This object represents for the current 15 minute interval the RAU 
         anomaly count, which is the number of occurences of an Upshift Rate
         Adaptation.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED"
::= {gxdslFarEndLineCurrentIntervalEntry 12}

gxdslFarEndLineCurrentIntervalRADCounter          OBJECT-TYPE
        SYNTAX          Counter
        ACCESS          read-only
        STATUS          mandatory
        DESCRIPTION     
        "This object represents for the current 15 minute interval the RAD 
         anomaly count, which is the number of occurences of a Downshift Rate
         Adaptation.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED"
::= {gxdslFarEndLineCurrentIntervalEntry 13}


gxdslFarEndLineCurrentSpIndex  OBJECT-TYPE
	SYNTAX 	SpIndex
	ACCESS	not-accessible
	STATUS	mandatory
	DESCRIPTION 
		"Each row is also indexed by a number that
		 contains the slot number and port number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslFarEndLineCurrentIntervalEntry 14 }

-- xdslFarEndLineCurrent1DayTable         OBJECT-TYPE
--         SYNTAX          SEQUENCE OF XdslFarEndLineCurrent1DayEntry
--         ACCESS          not-accessible
--         STATUS          mandatory
--         DESCRIPTION     
--         "The xdsl line far end current 1 day table.
-- 
--          ALCATEL NOTE:
--              TABLESIZE: DEP [number of XDSL lines]                    
--              DESCR:     NA                  
--         
--          FGU4.4:  THIS TABLE IS NOT SUPPORTED "
-- ::= {gxdslFarEndLineCurrent 5}
--         
-- xdslFarEndLineCurrent1DayEntry         OBJECT-TYPE
--         SYNTAX          XdslFarEndLineCurrent1DayEntry                  
--         ACCESS          not-accessible
--         STATUS          mandatory
--         DESCRIPTION     
--         "An entry in the xdsl line far end current 1 day table.
-- 
--          Row creation : Entries for all XDSL lines belonging to a board are 
--                         created when the board becomes operational.
--          Row deletion : Entries for all XDSL lines belonging to a board are 
--                         deleted when the board becomes unavailable.
--         "
--         INDEX          {ifIndex}
-- ::= {xdslFarEndLineCurrent1DayTable 1}
-- 
-- XdslFarEndLineCurrent1DayEntry ::=
--         SEQUENCE {
--             xdslFarEndLineCurrent1DayLOSCounter       Counter,
--             xdslFarEndLineCurrent1DayLOFCounter       Counter,
--             xdslFarEndLineCurrent1DayLOMCounter       Counter,
--             xdslFarEndLineCurrent1DayLPRCounter       Counter,
--             xdslFarEndLineCurrent1DayLOLCounter       Counter,
--             xdslFarEndLineCurrent1DayESECounter       Counter,
--             xdslFarEndLineCurrent1DayESCounter        Counter,
--             xdslFarEndLineCurrent1DaySESCounter       Counter,
--             xdslFarEndLineCurrent1DayUASCounter       Counter,
--             xdslFarEndLineCurrent1DayMeasuredTime     INTEGER,
--             xdslFarEndLineCurrent1DayInvalidDataFlag  INTEGER,
--             xdslFarEndLineCurrent1DayRAUCounter       Counter,
--             xdslFarEndLineCurrent1DayRADCounter       Counter
--         }
-- xdslFarEndLineCurrent1DayLOSCounter    OBJECT-TYPE
--         SYNTAX          Counter
--         ACCESS          read-only
--         STATUS          mandatory
--         DESCRIPTION     
--         "This object represents for the current 1 day interval the LOS failure 
--          count, which is the number of occurences of an LOS failure event,
--          where a failure event occurs when the failure is declared and ends
--          when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLineCurrent1DayEntry 1}
-- 
-- xdslFarEndLineCurrent1DayLOFCounter    OBJECT-TYPE
--         SYNTAX          Counter
--         ACCESS          read-only
--         STATUS          mandatory
--         DESCRIPTION     
--         "This object represents for the current 1 day interval the LOF failure 
--          count, which is the number of occurences of an LOF failure event, 
--          where a failure event occurs when the failure is declared and ends
--          when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLineCurrent1DayEntry 2}
-- 
-- xdslFarEndLineCurrent1DayLOMCounter    OBJECT-TYPE
--         SYNTAX          Counter
--         ACCESS          read-only
--         STATUS          mandatory
--         DESCRIPTION     
--         "This object represents for the current 1 day interval the LOM failure 
--          count, which is the number of occurences of an LOM failure event, 
--          where a failure event occurs when the failure is declared and ends
--          when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLineCurrent1DayEntry 3}
-- 
-- xdslFarEndLineCurrent1DayLPRCounter    OBJECT-TYPE
--         SYNTAX          Counter
--         ACCESS          read-only
--         STATUS          mandatory
--         DESCRIPTION     
--         "This object represents for the current 1 day interval the LPR failure 
--          count, which is the number of occurences of an LPR failure event,
--          where a failure event occurs when the failure is declared and ends
--          when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLineCurrent1DayEntry 4}
-- 
-- xdslFarEndLineCurrent1DayLOLCounter    OBJECT-TYPE
--         SYNTAX          Counter
--         ACCESS          read-only
--         STATUS          mandatory
--         DESCRIPTION     
--         "This object represents for the current 1 day interval the LOL failure 
--          count, which is the number of occurences of an LOL failure event, 
--          where a failure event occurs when the failure is declared and ends 
--          when the failure clears.
-- 
--          ALCATEL NOTE:
--              ACCESS:   NA                  USAGE:    NA
--              PERSIST:  NO                  INSRVMOD: NA
--              RANGE:    0                   DEFVALUE: 0
--              UNITS:    NA                  SPARSE:   NA
--              DESCR:    Because an LOL failure event never occurs, the value of
--                        the counter is always 0.
--         "
-- ::= {xdslFarEndLineCurrent1DayEntry 5}
-- 
-- xdslFarEndLineCurrent1DayESECounter    OBJECT-TYPE
--         SYNTAX          Counter
--         ACCESS          read-only
--         STATUS          mandatory
--         DESCRIPTION     
--         "This object represents for the current 1 day interval the ESE failure 
--          count, which is the number of occurences of an ESE failure event, 
--          where a failure event occurs when the failure is declared and ends 
--          when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLineCurrent1DayEntry 6}
-- 
-- 
-- xdslFarEndLineCurrent1DayESCounter    OBJECT-TYPE
--         SYNTAX          Counter
--         ACCESS          read-only
--         STATUS          mandatory
--         DESCRIPTION     
--         "The counter associated with the number of Errored Seconds encountered 
--          by the line in the current 1 Day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLineCurrent1DayEntry 7}
-- 
-- xdslFarEndLineCurrent1DaySESCounter    OBJECT-TYPE
--         SYNTAX          Counter
--         ACCESS          read-only
--         STATUS          mandatory
--         DESCRIPTION     
--         "The counter associated with the number of Severely Errored Seconds
--          encountered by the line in the current 1 Day interval.
-- 
--          ALCATEL NOTE:
--           ACCESS:   NA                  USAGE:    NA
--            PERSIST:  NO                  INSRVMOD: NA
--              RANGE:    NA                  DEFVALUE: 0
--              UNITS:    NA                  SPARSE:   NA
--              DESCR:    NA
--         "
-- ::= {xdslFarEndLineCurrent1DayEntry 8}
-- 
-- xdslFarEndLineCurrent1DayUASCounter    OBJECT-TYPE
--         SYNTAX          Counter
--         ACCESS          read-only
--         STATUS          mandatory
--         DESCRIPTION     
--         "The counter associated with the number of Unavailable Seconds
--          encountered by the line in the current 1 Day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLineCurrent1DayEntry 9}
-- 
-- xdslFarEndLineCurrent1DayMeasuredTime  OBJECT-TYPE
--         SYNTAX          INTEGER(0..86400)
--         ACCESS          read-only
--         STATUS          mandatory
--         DESCRIPTION     
--         "The amount of time, measured in seconds, that statistics for this
--          entry have been counted.
-- 
--          ALCATEL NOTE:
--              ACCESS:   NA                  USAGE:    NA
--              PERSIST:  NO                  INSRVMOD: NA
--              RANGE:    NA                  DEFVALUE: 0
--              UNITS:    seconds             SPARSE:   NA
--              DESCR:    NA
--          "
-- ::= {xdslFarEndLineCurrent1DayEntry 10}
-- 
-- xdslFarEndLineCurrent1DayInvalidDataFlag         OBJECT-TYPE
--         SYNTAX          INTEGER
--         ACCESS          read-only
--         STATUS          mandatory
--         DESCRIPTION     
--         "This object indicates the validity of the corresponding PM data.
--          It is set to 1 when the PM data is incomplete or invalid and set to 0
--          when the PM data is complete and valid.
-- 
--          ALCATEL NOTE:
--              ACCESS:   NA                  USAGE:    NA
--              PERSIST:  NO                  INSRVMOD: NA
--              RANGE:    0..1                DEFVALUE: 0
--              UNITS:    NA                  SPARSE:   NA
--              DESCR:    NA
--         "
-- ::= {xdslFarEndLineCurrent1DayEntry 11}
-- 
-- xdslFarEndLineCurrent1DayRAUCounter    OBJECT-TYPE
--         SYNTAX          Counter
--         ACCESS          read-only
--         STATUS          mandatory
--         DESCRIPTION     
--         "This object represents for the current 1 day interval the RAU anomaly 
--          count, which is the number of occurences of an Upshift Rate 
--          Adaptation.
-- 
--          ALCATEL NOTE:
--              ACCESS:   NA                  USAGE:    NA
--              PERSIST:  NO                  INSRVMOD: NA
--              RANGE:    NA                  DEFVALUE: 1
--              UNITS:    NA                  SPARSE:   NA
--              DESCR:    NA
--         "
-- ::= {xdslFarEndLineCurrent1DayEntry 12}
-- 
-- xdslFarEndLineCurrent1DayRADCounter    OBJECT-TYPE
--         SYNTAX          Counter
--         ACCESS          read-only
--         STATUS          mandatory
--         DESCRIPTION     
--         "This object represents for the current 1 day interval the RAD anomaly 
--          count, which is the number of occurences of a Downshift Rate 
--          Adaptation.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLineCurrent1DayEntry 13}

gxdslFarEndLinePreviousIntervalTable    OBJECT-TYPE
        SYNTAX          SEQUENCE OF GxdslFarEndLinePreviousIntervalEntry
        ACCESS          not-accessible
        STATUS          mandatory
        DESCRIPTION     
        "The xdsl line far end previous interval table.
         ALCATEL NOTE:
             TABLESIZE: DEP [number of XDSL lines * 192]                    
             DESCR:     NA                  
        "
::= {gxdslFarEndLinePrevious 1}
        
gxdslFarEndLinePreviousIntervalEntry    OBJECT-TYPE
        SYNTAX          GxdslFarEndLinePreviousIntervalEntry                     
        ACCESS          not-accessible
        STATUS          mandatory
        DESCRIPTION     
        "An entry in the xdsl line far end previous interval table.

         Row creation : Entries for all XDSL lines belonging to a board are 
                        created when the board becomes operational.
         Row deletion : Entries for all XDSL lines belonging to a board are 
                        deleted when the board becomes unavailable.
        "
        INDEX          {ifIndex, gxdslFarEndLinePreviousSpIndex,
                        gxdslFarEndLinePreviousIntervalNumber}
::= {gxdslFarEndLinePreviousIntervalTable 1}

GxdslFarEndLinePreviousIntervalEntry ::=
        SEQUENCE {
            gxdslFarEndLinePreviousIntervalNumber          INTEGER,
            gxdslFarEndLinePreviousIntervalLOSCounter      Counter,
            gxdslFarEndLinePreviousIntervalLOFCounter      Counter,
            gxdslFarEndLinePreviousIntervalLOMCounter      Counter,
            gxdslFarEndLinePreviousIntervalLPRCounter      Counter,
            gxdslFarEndLinePreviousIntervalLOLCounter      Counter,
            gxdslFarEndLinePreviousIntervalESECounter      Counter,
            gxdslFarEndLinePreviousIntervalESCounter       Counter,
            gxdslFarEndLinePreviousIntervalSESCounter      Counter,
            gxdslFarEndLinePreviousIntervalUASCounter      Counter,
            gxdslFarEndLinePreviousIntervalMeasuredTime    INTEGER,
            gxdslFarEndLinePreviousIntervalInvalidDataFlag INTEGER,
            gxdslFarEndLinePreviousIntervalRAUCounter      Counter,
            gxdslFarEndLinePreviousIntervalRADCounter      Counter,
            gxdslFarEndLinePreviousSpIndex                 SpIndex
        }
        
gxdslFarEndLinePreviousIntervalNumber   OBJECT-TYPE
        SYNTAX          INTEGER(1..192)
        ACCESS          read-only
        STATUS          mandatory
        DESCRIPTION     
        "A number between 1 and 192, which identifies the interval for which
         the set of statistics is available. The interval identified by 1 is 
         the most recently completed 15 minute interval, and the interval
         identified by N is the interval immediately preceding the one
         identified by N-1.

         ALCATEL NOTE:
             ACCESS:   NA                  USAGE:    NA
             PERSIST:  NO                  INSRVMOD: NA
             RANGE:    NA                  DEFVALUE: NA
             UNITS:    NA                  SPARSE:   NA
             DESCR:    NA
        "
::= {gxdslFarEndLinePreviousIntervalEntry 1}

gxdslFarEndLinePreviousIntervalLOSCounter         OBJECT-TYPE
        SYNTAX          Counter
        ACCESS          read-only
        STATUS          mandatory
        DESCRIPTION     
        "This object represents for a particular 15 minute interval the LOS 
         failure count, which is the number of occurences of an LOS failure 
         event, where a failure event occurs when the failure is declared and 
         ends when the failure clears.

         ALCATEL NOTE:
             ACCESS:   NA                  USAGE:    NA
             PERSIST:  NO                  INSRVMOD: NA
             RANGE:    NA                  DEFVALUE: NA
             UNITS:    NA                  SPARSE:   NA
             DESCR:    NA

     FGU4.4:  The counter associated with the number of LOS Seconds encountered 
         by the line in the current 15 minute interval (i.e. count of LOS seconds, not LOS events).
        "
::= {gxdslFarEndLinePreviousIntervalEntry 2}

gxdslFarEndLinePreviousIntervalLOFCounter         OBJECT-TYPE
        SYNTAX          Counter
        ACCESS          read-only
        STATUS          mandatory
        DESCRIPTION     
        "This object represents for a particular 15 minute interval the LOF 
         failure count, which is the number of occurences of an LOF failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA
        "
::= {gxdslFarEndLinePreviousIntervalEntry 3}

gxdslFarEndLinePreviousIntervalLOMCounter         OBJECT-TYPE
        SYNTAX          Counter
        ACCESS          read-only
        STATUS          mandatory
        DESCRIPTION     
        "This object represents for a particular 15 minute interval the LOM 
         failure count, which is the number of occurences of an LOM failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED"
::= {gxdslFarEndLinePreviousIntervalEntry 4}

gxdslFarEndLinePreviousIntervalLPRCounter         OBJECT-TYPE
        SYNTAX          Counter
        ACCESS          read-only
        STATUS          mandatory
        DESCRIPTION     
        "This object represents for a particular 15 minute interval the LPR 
         failure count, which is the number of occurences of an LPR failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED"
::= {gxdslFarEndLinePreviousIntervalEntry 5}

gxdslFarEndLinePreviousIntervalLOLCounter         OBJECT-TYPE
        SYNTAX          Counter
        ACCESS          read-only
        STATUS          mandatory
        DESCRIPTION     
        "This object represents for a particular 15 minute interval the LOL 
         failure count, which is the number of occurences of an LOL failure 
         event, where a failure event occurs when the failure is declared and 
         ends when the failure clears.

         ALCATEL NOTE:
             ACCESS:   NA                  USAGE:    NA
             PERSIST:  NO                  INSRVMOD: NA
             RANGE:    0                   DEFVALUE: 0
             UNITS:    NA                  SPARSE:   NA
             DESCR:    Because an LOL failure event never occurs, the value of
                       the counter is always 0.
        
        
         FGU4.4:  THIS OBJECT IS NOT SUPPORTED"
::= {gxdslFarEndLinePreviousIntervalEntry 6}

gxdslFarEndLinePreviousIntervalESECounter         OBJECT-TYPE
        SYNTAX          Counter
        ACCESS          read-only
        STATUS          mandatory
        DESCRIPTION     
        "This object represents for a particular 15 minute interval the ESE 
         failure count, which is the number of occurences of an ESE failure 
         event, where a failure event occurs when the failure is declared and 
         ends when the failure clears.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED"
::= {gxdslFarEndLinePreviousIntervalEntry 7}

gxdslFarEndLinePreviousIntervalESCounter          OBJECT-TYPE
        SYNTAX          Counter
        ACCESS          read-only
        STATUS          mandatory
        DESCRIPTION     
        "The counter associated with the number of Errored Seconds encountered 
         by the line in a particular 15 minute interval.

         ALCATEL NOTE:
             ACCESS:   NA                  USAGE:    NA
             PERSIST:  NO                  INSRVMOD: NA
             RANGE:    NA                  DEFVALUE: 0
             UNITS:    NA                  SPARSE:   NA
             DESCR:    NA
        "
::= {gxdslFarEndLinePreviousIntervalEntry 8}

gxdslFarEndLinePreviousIntervalSESCounter         OBJECT-TYPE
        SYNTAX          Counter
        ACCESS          read-only
        STATUS          mandatory
        DESCRIPTION     
        "The counter associated with the number of  Severely Errored Seconds
         encountered by the line in a particular 15 minute interval.

         ALCATEL NOTE:
             ACCESS:   NA                  USAGE:    NA
             PERSIST:  NO                  INSRVMOD: NA
             RANGE:    NA                  DEFVALUE: 0
             UNITS:    NA                  SPARSE:   NA
             DESCR:    NA
        "
::= {gxdslFarEndLinePreviousIntervalEntry 9}

gxdslFarEndLinePreviousIntervalUASCounter         OBJECT-TYPE
        SYNTAX          Counter
        ACCESS          read-only
        STATUS          mandatory
        DESCRIPTION     
        "The counter associated with the number of  Unavailable Seconds
         encountered by the line in a particular 15 minute interval.

         ALCATEL NOTE:
             ACCESS:   NA                  USAGE:    NA
             PERSIST:  NO                  INSRVMOD: NA
             RANGE:    NA                  DEFVALUE: 0
             UNITS:    NA                  SPARSE:   NA
             DESCR:    NA
        "
::= {gxdslFarEndLinePreviousIntervalEntry 10}

gxdslFarEndLinePreviousIntervalMeasuredTime       OBJECT-TYPE
        SYNTAX          INTEGER(0..900)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA
        
        
         FGU4.4:  THIS OBJECT IS NOT SUPPORTED"
::= {gxdslFarEndLinePreviousIntervalEntry 11}

gxdslFarEndLinePreviousIntervalInvalidDataFlag    OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA
        
        
         FGU4.4:  THIS OBJECT IS NOT SUPPORTED"
::= {gxdslFarEndLinePreviousIntervalEntry 12}

gxdslFarEndLinePreviousIntervalRAUCounter         OBJECT-TYPE
        SYNTAX          Counter
        ACCESS          read-only
        STATUS          mandatory
        DESCRIPTION     
        "This object represents for a particular 15 minute interval the RAU 
         anomaly count, which is the number of occurences of an Upshift Rate 
         Adaptation.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED"
::= {gxdslFarEndLinePreviousIntervalEntry 13}

gxdslFarEndLinePreviousIntervalRADCounter         OBJECT-TYPE
        SYNTAX          Counter
        ACCESS          read-only
        STATUS          mandatory
        DESCRIPTION     
        "This object represents for a particular 15 minute interval the RAD 
         anomaly count, which is the number of occurences of a Downshift Rate
         Adaptation.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED"
::= {gxdslFarEndLinePreviousIntervalEntry 14}

gxdslFarEndLinePreviousSpIndex  OBJECT-TYPE
	SYNTAX 	SpIndex
	ACCESS	not-accessible
	STATUS	mandatory
	DESCRIPTION 
		"Each row is also indexed by a number that
		 contains the slot number and port number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslFarEndLinePreviousIntervalEntry 15 }


-- xdslFarEndLinePrevious1DayTable        OBJECT-TYPE
--         SYNTAX          SEQUENCE OF XdslFarEndLinePrevious1DayEntry
--         ACCESS          not-accessible
--         STATUS          mandatory
--         DESCRIPTION     
--         "The xdsl line far end previous 1 day table.
--          ALCATEL NOTE:
--              TABLESIZE: DEP [number of XDSL lines * number of days (1)]                     
--              DESCR:     NA                  
--         
--          FGU4.4:  THIS TABLE IS NOT SUPPORTED "
-- ::= {gxdslFarEndLinePrevious 2}
--      
-- xdslFarEndLinePrevious1DayEntry        OBJECT-TYPE
--         SYNTAX          XdslFarEndLinePrevious1DayEntry                 
--         ACCESS          not-accessible
--         STATUS          mandatory
--         DESCRIPTION     
--         "An entry in the xdsl line far end previous 1 day table.
-- 
--          Row creation : Entries for all XDSL lines belonging to a board are 
--                         created when the board becomes operational.
--          Row deletion : Entries for all XDSL lines belonging to a board are 
--                         deleted when the board becomes unavailable.
--         "
--         INDEX          {ifIndex, 
--                         xdslFarEndLinePrevious1DayNumber}
-- 
-- ::= {xdslFarEndLinePrevious1DayTable 1}
-- 
-- XdslFarEndLinePrevious1DayEntry ::=
--         SEQUENCE {
--             xdslFarEndLinePrevious1DayNumber          INTEGER,
--             xdslFarEndLinePrevious1DayLOSCounter      Counter,
--             xdslFarEndLinePrevious1DayLOFCounter      Counter,
--             xdslFarEndLinePrevious1DayLOMCounter      Counter,
--             xdslFarEndLinePrevious1DayLPRCounter      Counter,
--             xdslFarEndLinePrevious1DayLOLCounter      Counter,
--             xdslFarEndLinePrevious1DayESECounter      Counter,
--             xdslFarEndLinePrevious1DayESCounter       Counter,
--             xdslFarEndLinePrevious1DaySESCounter      Counter,
--             xdslFarEndLinePrevious1DayUASCounter      Counter,
--             xdslFarEndLinePrevious1DayMeasuredTime    INTEGER,
--             xdslFarEndLinePrevious1DayInvalidDataFlag INTEGER,
--             xdslFarEndLinePrevious1DayRAUCounter      Counter,
--             xdslFarEndLinePrevious1DayRADCounter      Counter
--         }
-- 
-- xdslFarEndLinePrevious1DayNumber       OBJECT-TYPE
--         SYNTAX          INTEGER(1..7)
--         ACCESS          read-only
--         STATUS          mandatory
--         DESCRIPTION     
--         "A number between 1 and 7, which identifies the day for which the 
--          set of statistics is available. The day identified by 1 is the 
--          most recently completed 1Day, and the day identified 
--          by N is the day immediately preceding the one identified by N-1.
-- 
--          ALCATEL NOTE:
--              ACCESS:   NA                  USAGE:    NA
--              PERSIST:  NO                  INSRVMOD: NA
--              RANGE:    1                   DEFVALUE: NA
--              UNITS:    NA                  SPARSE:   NA
--              DESCR:    Only statistics for one previous day is kept.
--         "
-- ::= {xdslFarEndLinePrevious1DayEntry 1}
-- 
-- xdslFarEndLinePrevious1DayLOSCounter   OBJECT-TYPE
--         SYNTAX          Counter
--         ACCESS          read-only
--         STATUS          mandatory
--         DESCRIPTION     
--         "This object represents for the previous 1 day interval the LOS failure
--          count, which is the number of occurences of an LOS failure event, 
--          where a failure event occurs when the failure is declared and ends
--          when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLinePrevious1DayEntry 2}
-- 
-- xdslFarEndLinePrevious1DayLOFCounter   OBJECT-TYPE
--         SYNTAX          Counter
--         ACCESS          read-only
--         STATUS          mandatory
--         DESCRIPTION     
--         "This object represents for the previous 1 day interval the LOF failure
--          count, which is the number of occurences of an LOF failure event,
--          where a failure event occurs when the failure is declared and ends 
--          when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLinePrevious1DayEntry 3}
-- 
-- xdslFarEndLinePrevious1DayLOMCounter   OBJECT-TYPE
--         SYNTAX          Counter
--         ACCESS          read-only
--         STATUS          mandatory
--         DESCRIPTION     
--         "This object represents for the previous 1 day interval the LOM failure
--          count, which is the number of occurences of an LOM failure event, 
--          where a failure event occurs when the failure is declared and ends 
--          when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLinePrevious1DayEntry 4}
-- 
-- xdslFarEndLinePrevious1DayLPRCounter   OBJECT-TYPE
--         SYNTAX          Counter
--         ACCESS          read-only
--         STATUS          mandatory
--         DESCRIPTION     
--         "This object represents for the previous 1 day interval the LPR failure
--          count, which is the number of occurences of an LPR failure event, 
--          where a failure event occurs when the failure is declared and ends
--          when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLinePrevious1DayEntry 5}
-- 
-- xdslFarEndLinePrevious1DayLOLCounter   OBJECT-TYPE
--         SYNTAX          Counter
--         ACCESS          read-only
--         STATUS          mandatory
--         DESCRIPTION     
--         "This object represents for the previous 1 day interval the LOL failure
--          count, which is the number of occurences of an LOL failure event, 
--          where a failure event occurs when the failure is declared and ends 
--          when the failure clears.
-- 
--          ALCATEL NOTE:
--              ACCESS:   NA                  USAGE:    NA
--              PERSIST:  NO                  INSRVMOD: NA
--              RANGE:    0                   DEFVALUE: 0
--              UNITS:    NA                  SPARSE:   NA
--              DESCR:    Because an LOL failure event never occurs, the value of
--                        the counter is always 0.
--         "
-- ::= {xdslFarEndLinePrevious1DayEntry 6}
-- 
-- xdslFarEndLinePrevious1DayESECounter   OBJECT-TYPE
--         SYNTAX          Counter
--         ACCESS          read-only
--         STATUS          mandatory
--         DESCRIPTION     
--         "This object represents for the previous 1 day interval the ESE failure
--          count, which is the number of occurences of an ESE failure event, 
--          where a failure event occurs when the failure is declared and ends 
--          when the failure clears.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLinePrevious1DayEntry 7}
-- 
-- xdslFarEndLinePrevious1DayESCounter    OBJECT-TYPE
--         SYNTAX          Counter
--         ACCESS          read-only
--         STATUS          mandatory
--         DESCRIPTION     
--         "The counter associated with the number of Errored Seconds encountered 
--          by the line in the previous 1 day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLinePrevious1DayEntry 8}
-- 
-- xdslFarEndLinePrevious1DaySESCounter   OBJECT-TYPE
--         SYNTAX          Counter
--         ACCESS          read-only
--         STATUS          mandatory
--         DESCRIPTION     
--         "The counter associated with the number of  Severely Errored Seconds
--          encountered by the line in the previous 1 day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLinePrevious1DayEntry 9}
-- 
-- xdslFarEndLinePrevious1DayUASCounter   OBJECT-TYPE
--         SYNTAX          Counter
--         ACCESS          read-only
--         STATUS          mandatory
--         DESCRIPTION     
--         "The counter associated with the number of Unavailable Seconds
--          encountered by the line in the previous 1 day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLinePrevious1DayEntry 10}
-- 
-- xdslFarEndLinePrevious1DayMeasuredTime OBJECT-TYPE
--         SYNTAX          INTEGER(0..86400)
--         ACCESS          read-only
--         STATUS          mandatory
--         DESCRIPTION      
--         "The amount of time, measured in seconds, that statistics for this
--          entry have been counted.
-- 
--          ALCATEL NOTE:
--              ACCESS:   NA                  USAGE:    NA
--              PERSIST:  NO                  INSRVMOD: NA
--              RANGE:    NA                  DEFVALUE: 0
--              UNITS:    seconds             SPARSE:   NA
--              DESCR:    NA
--         "
-- ::= {xdslFarEndLinePrevious1DayEntry 11}
-- 
-- xdslFarEndLinePrevious1DayInvalidDataFlag        OBJECT-TYPE
--         SYNTAX          INTEGER
--         ACCESS          read-only
--         STATUS          mandatory
--         DESCRIPTION      
--         "This object indicates the validity of the corresponding PM data.
--          It is set to 1 when the PM data is incomplete or invalid and set to 0
--          when the PM data is complete and valid.
-- 
--          ALCATEL NOTE:
--              ACCESS:   NA                  USAGE:    NA
--              PERSIST:  NO                  INSRVMOD: NA
--              RANGE:    0..1                DEFVALUE: 1
--              UNITS:    NA                  SPARSE:   NA
--              DESCR:    NA
--         "
-- ::= {xdslFarEndLinePrevious1DayEntry 12}
-- 
-- xdslFarEndLinePrevious1DayRAUCounter   OBJECT-TYPE
--         SYNTAX          Counter
--         ACCESS          read-only
--         STATUS          mandatory
--         DESCRIPTION     
--         "This object represents for the previous 1 day interval the RAU anomaly 
--          count, which is the number of occurences of an Upshift Rate 
--          Adaptation.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLinePrevious1DayEntry 13}
-- 
-- xdslFarEndLinePrevious1DayRADCounter   OBJECT-TYPE
--         SYNTAX          Counter
--         ACCESS          read-only
--         STATUS          mandatory
--         DESCRIPTION     
--         "This object represents for the previous 1 day interval the RAD anomaly 
--          count, which is the number of occurences of a Downshift Rate 
--          Adaptation.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndLinePrevious1DayEntry 14}

--      The XDSL Channel Group

gxdslChannelOperDataTable               OBJECT-TYPE
        SYNTAX          SEQUENCE OF GxdslChannelOperDataEntry
        ACCESS          not-accessible
        STATUS          mandatory
        DESCRIPTION     
        "The xdsl channel operational data table.

         ALCATEL NOTE:
             TABLESIZE: DEP [number of XDSL lines * maximum number of channels
                             per XDSL line (1)]                    
             DESCR:     NA                  
        "
::= {gxdslChannelCurrent 1}

gxdslChannelOperDataEntry               OBJECT-TYPE
        SYNTAX          GxdslChannelOperDataEntry
        ACCESS          not-accessible
        STATUS          mandatory
        DESCRIPTION     
        "An entry in the xdsl channel operational data table.

         Row creation : Entries for all XDSL channels belonging to a board are 
                        created when the board becomes operational.
         Row deletion : Entries for all XDSL channels belonging to a board are 
                        deleted when the board becomes unavailable.
        "
        INDEX          {ifIndex, gxdslChannelOperSpIndex}
::= {gxdslChannelOperDataTable 1}

GxdslChannelOperDataEntry ::=
        SEQUENCE {
            gxdslChannelActualBitrateUpstream              INTEGER,
            gxdslChannelAttainableBitrateUpstream          INTEGER,
            gxdslChannelActualInterleavingDelayDownstream  INTEGER,
            gxdslChannelActualImpNoiseProtDownstream       INTEGER,
            gxdslChannelOperSpIndex                        SpIndex
        }

gxdslChannelActualBitrateUpstream       OBJECT-TYPE
        SYNTAX          INTEGER
        ACCESS          read-only
        STATUS          mandatory
        DESCRIPTION     
        "When the modem is in showtime, then this object gives the actual net
         data rate for the upstream fast or interleaved channel data flow. When
         not in showtime, then this object has the value measured in preceeding
         showtime session. After an activation failure, this object represents
         the value as available till activation failure. A value 0 means that
         no data is available.

         ALCATEL NOTE:
             ACCESS:   NA                  USAGE:    NA
             PERSIST:  NO                  INSRVMOD: NA
             RANGE:    0..262143           DEFVALUE: 0
             UNITS:    kbits/sec           SPARSE:   NA
             DESCR:    NA
        "
::= {gxdslChannelOperDataEntry 1}

gxdslChannelAttainableBitrateUpstream   OBJECT-TYPE
        SYNTAX         INTEGER
        ACCESS         read-only
        STATUS         mandatory
        DESCRIPTION 
        "This object contains the maximum attainable net data rate the modem 
         can support on the corresponding channel. 
         When the modem is not in showtime this object will have the value
         measured during the previous showtime session.
         When no data is available (e.g. before first showtime) value 0
         is used.

         ALCATEL NOTE:
             ACCESS:   NA                  USAGE:    NA
             PERSIST:  NO                  INSRVMOD: NA
             RANGE:    0..262143           DEFVALUE: 0
             UNITS:    kbits/sec           SPARSE:   NA
             DESCR:    NA "
::= {gxdslChannelOperDataEntry 2}

gxdslChannelActualInterleavingDelayDownstream     OBJECT-TYPE
        SYNTAX          INTEGER
        ACCESS          read-only
        STATUS          mandatory
        DESCRIPTION     
        "This object gives the actual delay caused by the interleaving and
         deinterleaving functionality.
         When the modem is not in showtime this object will have the value
         measured during the previous showtime session.
         When no data is available (e.g. before first showtime) value 0
         is used.
         Delay range is 0 to 255 ms in steps of 1 ms.

         ALCATEL NOTE:
             ACCESS:   NA                  USAGE:    NA
             PERSIST:  NO                  INSRVMOD: NA
             RANGE:    0..255              DEFVALUE: 0
             UNITS:    milliseconds        SPARSE:   NA
             DESCR:    NA
        "
::= {gxdslChannelOperDataEntry 3}

gxdslChannelActualImpNoiseProtDownstream          OBJECT-TYPE
        SYNTAX          INTEGER
        ACCESS          read-only
        STATUS          mandatory
        DESCRIPTION     
        "This object gives the actual impulse noise protection.
         When the modem is not in showtime this object will have the value
         measured during the previous showtime session.
         When no data is available (e.g. before first showtime) value 0
         is used.
         Rate is 0 to 25.5 symbols in steps of 0.1 symbol.
         It is represented as 1/10 * xdslChannelActualImpNoiseProtDownstream.

         ALCATEL NOTE:
             ACCESS:   NA                  USAGE:    NA
             PERSIST:  NO                  INSRVMOD: NA
             RANGE:    0..255              DEFVALUE: 0
             UNITS:    symbols / 10        SPARSE:   NA
             DESCR:    NA
        "
::= {gxdslChannelOperDataEntry 4}

gxdslChannelOperSpIndex  OBJECT-TYPE
	SYNTAX 	SpIndex
	ACCESS	not-accessible
	STATUS	mandatory
	DESCRIPTION 
		"Each row is also indexed by a number that
		 contains the slot number, port number and channel number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslChannelOperDataEntry 5 }


gxdslChannelCurrentIntervalTable        OBJECT-TYPE
        SYNTAX          SEQUENCE OF GxdslChannelCurrentIntervalEntry
        ACCESS          not-accessible
        STATUS          mandatory
        DESCRIPTION     
        "The xdsl channel current interval table.

         ALCATEL NOTE:
             TABLESIZE: DEP [number of XDSL lines * maximum number of channels
                             per XDSL line (1)]                    
             DESCR:     NA                  
        "
::= {gxdslChannelCurrent 2}

gxdslChannelCurrentIntervalEntry        OBJECT-TYPE
        SYNTAX          GxdslChannelCurrentIntervalEntry
        ACCESS          not-accessible
        STATUS          mandatory
        DESCRIPTION     
        "An entry in the xdsl channel current interval table.

         Row creation : Entries for all XDSL channels belonging to a board are 
                        created when the board becomes operational.
         Row deletion : Entries for all XDSL channels belonging to a board are 
                        deleted when the board becomes unavailable.
        "
        INDEX          {ifIndex, gxdslChannelCurrentSpIndex}
::= {gxdslChannelCurrentIntervalTable 1}

GxdslChannelCurrentIntervalEntry ::=
        SEQUENCE {
            gxdslChannelCurrentIntervalCVs             Counter,
            gxdslChannelCurrentIntervalFECCs           Counter,
            gxdslChannelCurrentIntervalMeasuredTime    INTEGER,
            gxdslChannelCurrentIntervalInvalidDataFlag INTEGER,
            gxdslChannelCurrentIntervalCECs            Counter,
            gxdslChannelCurrentSpIndex                 SpIndex
        }

gxdslChannelCurrentIntervalCVs          OBJECT-TYPE
        SYNTAX          Counter
        ACCESS          read-only
        STATUS          mandatory
        DESCRIPTION     
        "The counter associated with the number of Coding Violations
         encountered by the channel in the current 15 minute interval.

         ALCATEL NOTE:
             ACCESS:   NA                  USAGE:    NA
             PERSIST:  NO                  INSRVMOD: NA
             RANGE:    NA                  DEFVALUE: 0
             UNITS:    NA                  SPARSE:   NA
             DESCR:    NA
        "
::= {gxdslChannelCurrentIntervalEntry 1}

gxdslChannelCurrentIntervalFECCs        OBJECT-TYPE
        SYNTAX          Counter
        ACCESS          read-only
        STATUS          mandatory
        DESCRIPTION     
        "The counter associated with the number of corrected codewords 
         encountered by the channel, respectively corrected octets in case of
         VDSL G.993.1, in the current 15 minute interval. If more 
         than one error occurs per superframe then only 1 is reported.

         ALCATEL NOTE:
             ACCESS:   NA                  USAGE:    NA
             PERSIST:  NO                  INSRVMOD: NA
             RANGE:    NA                  DEFVALUE: 0
             UNITS:    NA                  SPARSE:   NA
             DESCR:    NA
        "
::= {gxdslChannelCurrentIntervalEntry 2}

gxdslChannelCurrentIntervalMeasuredTime OBJECT-TYPE
        SYNTAX          INTEGER(0..900)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA
        
         FGU4.4:  THIS OBJECT IS NOT SUPPORTED "
::= {gxdslChannelCurrentIntervalEntry 3}

gxdslChannelCurrentIntervalInvalidDataFlag        OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA
        
         FGU4.4:  THIS OBJECT IS NOT SUPPORTED "
::= {gxdslChannelCurrentIntervalEntry 4}

gxdslChannelCurrentIntervalCECs         OBJECT-TYPE
        SYNTAX          Counter
        ACCESS          read-only
        STATUS          mandatory
        DESCRIPTION
        "The counter associated with the number of codewords errors
         encountered by the far end channel in the current 15 minute interval.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED "
::= {gxdslChannelCurrentIntervalEntry 5}

gxdslChannelCurrentSpIndex  OBJECT-TYPE
	SYNTAX 	SpIndex
	ACCESS	not-accessible
	STATUS	mandatory
	DESCRIPTION 
		"Each row is also indexed by a number that
		 contains the slot number, port number and channel number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslChannelCurrentIntervalEntry 6 }



-- xdslChannelCurrent1DayTable            OBJECT-TYPE
--         SYNTAX          SEQUENCE OF XdslChannelCurrent1DayEntry
--         ACCESS          not-accessible
--         STATUS          mandatory
--         DESCRIPTION     
--         "The xdsl channel near end current 1 day table.
-- 
--          ALCATEL NOTE:
--              TABLESIZE: DEP [number of XDSL lines * maximum number of channels
--                              per XDSL line (1)]                    
--              DESCR:     NA                  
--         
--          FGU4.4:  THIS TABLE IS NOT SUPPORTED "
-- ::= {gxdslChannelCurrent 3}
--      
-- xdslChannelCurrent1DayEntry            OBJECT-TYPE
--         SYNTAX          XdslChannelCurrent1DayEntry                     
--         ACCESS          not-accessible
--         STATUS          mandatory
--         DESCRIPTION     
--          "An entry in the xdsl channel near end current 1 day table.
-- 
--          Row creation : Entries for all XDSL channels belonging to a board are 
--                         created when the board becomes operational.
--          Row deletion : Entries for all XDSL channels belonging to a board are 
--                         deleted when the board becomes unavailable.
--          "
--         INDEX          {ifIndex}
-- ::= {xdslChannelCurrent1DayTable 1}
-- 
-- XdslChannelCurrent1DayEntry ::=
--         SEQUENCE {
--             xdslChannelCurrent1DayCVs                 Counter,
--             xdslChannelCurrent1DayFECCs               Counter,
--             xdslChannelCurrent1DayMeasuredTime        INTEGER,
--             xdslChannelCurrent1DayInvalidDataFlag     INTEGER,
--             xdslChannelCurrent1DayCECs                Counter
--         }
-- 
-- xdslChannelCurrent1DayCVs              OBJECT-TYPE
--         SYNTAX          Counter
--         ACCESS          read-only
--         STATUS          mandatory
--         DESCRIPTION     
--         "The counter associated with the number of Coding Violations 
--          encountered by the channel in the current 1 day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslChannelCurrent1DayEntry 1}
-- 
-- xdslChannelCurrent1DayFECCs            OBJECT-TYPE
--         SYNTAX          Counter
--         ACCESS          read-only
--         STATUS          mandatory
--         DESCRIPTION     
--         "The counter associated with the number of corrected codewords 
--          encountered by the channel, respectively corrected octets in case of
--          VDSL G.993.1, in the current 1 day interval. If more than
--          one error occurs per superframe then only 1 is reported.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslChannelCurrent1DayEntry 2}
-- 
-- xdslChannelCurrent1DayMeasuredTime     OBJECT-TYPE
--         SYNTAX          INTEGER(0..86400)
--         ACCESS          read-only
--         STATUS          mandatory
--         DESCRIPTION     
--         "The amount of time, measured in seconds, that statistics for this
--          entry have been counted.
-- 
--          ALCATEL NOTE:
--              ACCESS:   NA                  USAGE:    NA
--              PERSIST:  NO                  INSRVMOD: NA
--              RANGE:    NA                  DEFVALUE: 0
--              UNITS:    seconds             SPARSE:   NA
--              DESCR:    NA
--         "
-- ::= {xdslChannelCurrent1DayEntry 3}
-- 
-- xdslChannelCurrent1DayInvalidDataFlag  OBJECT-TYPE
--         SYNTAX          INTEGER
--         ACCESS          read-only
--         STATUS          mandatory
--         DESCRIPTION     
--         "This object indicates the validity of the corresponding PM data.
--          It is set to 1 when the PM data is incomplete or invalid and set to 0
--          when the PM data is complete and valid.
-- 
--          ALCATEL NOTE:
--              ACCESS:   NA                  USAGE:    NA
--              PERSIST:  NO                  INSRVMOD: NA
--              RANGE:    0..1                DEFVALUE: 1
--              UNITS:    NA                  SPARSE:   NA
--              DESCR:    NA
--         "
-- ::= {xdslChannelCurrent1DayEntry 4}
-- 
-- xdslChannelCurrent1DayCECs             OBJECT-TYPE
--         SYNTAX          Counter
--         ACCESS          read-only
--         STATUS          mandatory
--         DESCRIPTION
--         "The counter associated with the number of codewords errors
--          encountered by the far end channel in the current 15 minute interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslChannelCurrent1DayEntry 5}

gxdslChannelPreviousIntervalTable       OBJECT-TYPE
        SYNTAX          SEQUENCE OF GxdslChannelPreviousIntervalEntry
        ACCESS          not-accessible
        STATUS          mandatory
        DESCRIPTION     
        "The xdsl channel previous interval table.

         ALCATEL NOTE:
             TABLESIZE: DEP [number of XDSL lines * maximum number of channels
                             per XDSL line (1) * 192]                    
             DESCR:     NA                  
        "
::= {gxdslChannelPrevious 1}

gxdslChannelPreviousIntervalEntry       OBJECT-TYPE
        SYNTAX          GxdslChannelPreviousIntervalEntry
        ACCESS          not-accessible
        STATUS          mandatory
        DESCRIPTION     
        "An entry in the xdsl channel previous interval table.

         Row creation : Entries for all XDSL channels belonging to a board are 
                        created when the board becomes operational.
         Row deletion : Entries for all XDSL channels belonging to a board are 
                        deleted when the board becomes unavailable.
        "
        INDEX          {ifIndex, gxdslChannelPreviousSpIndex,
                        gxdslChannelPreviousIntervalNumber}
::= {gxdslChannelPreviousIntervalTable 1}

GxdslChannelPreviousIntervalEntry ::=
        SEQUENCE {
            gxdslChannelPreviousIntervalNumber           INTEGER,
            gxdslChannelPreviousIntervalCVs              Counter,
            gxdslChannelPreviousIntervalFECCs            Counter,
            gxdslChannelPreviousIntervalMeasuredTime     INTEGER,
            gxdslChannelPreviousIntervalInvalidDataFlag  INTEGER,
            gxdslChannelPreviousIntervalCECs             Counter,
            gxdslChannelPreviousSpIndex                  SpIndex
        }
        
gxdslChannelPreviousIntervalNumber      OBJECT-TYPE
        SYNTAX          INTEGER(1..192)
        ACCESS          read-only
        STATUS          mandatory
        DESCRIPTION     
        "A number between 1 and 192, which identifies the interval for which
         the set of statistics is available. The interval identified by 1 is
         the most recently completed 15 minute interval, and the interval
         identified by N is the interval immediately preceding the one 
         identified by N-1.

         ALCATEL NOTE:
             ACCESS:   NA                  USAGE:    NA
             PERSIST:  NO                  INSRVMOD: NA
             RANGE:    NA                  DEFVALUE: NA
             UNITS:    NA                  SPARSE:   NA
             DESCR:    NA
        "
::= {gxdslChannelPreviousIntervalEntry 1}

gxdslChannelPreviousIntervalCVs         OBJECT-TYPE
        SYNTAX          Counter
        ACCESS          read-only
        STATUS          mandatory
        DESCRIPTION     
        "The counter associated with the number of Coding Violations
         encountered by the channel in a particular 15 minute interval.

         ALCATEL NOTE:
             ACCESS:   NA                  USAGE:    NA
             PERSIST:  NO                  INSRVMOD: NA
             RANGE:    NA                  DEFVALUE: 0
             UNITS:    NA                  SPARSE:   NA
             DESCR:    NA
        "
::= {gxdslChannelPreviousIntervalEntry 2}

gxdslChannelPreviousIntervalFECCs       OBJECT-TYPE
        SYNTAX          Counter
        ACCESS          read-only
        STATUS          mandatory
        DESCRIPTION     
        "The counter associated with the number of corrected codewords 
         encountered by the channel, respectively corrected octets in case of
         VDSL G.993.1, in a particular 15 minute interval. 
         If more than one error occurs per superframe then only
         1 is reported.

         ALCATEL NOTE:
             ACCESS:   NA                  USAGE:    NA
             PERSIST:  NO                  INSRVMOD: NA
             RANGE:    NA                  DEFVALUE: 0
             UNITS:    NA                  SPARSE:   NA
             DESCR:    NA
        "
::= {gxdslChannelPreviousIntervalEntry 3}

gxdslChannelPreviousIntervalMeasuredTime          OBJECT-TYPE
        SYNTAX          INTEGER(0..900)
        ACCESS          read-only
        STATUS          mandatory
        DESCRIPTION     
        "The amount of time, measured in seconds, that statistics for this 
         entry have been counted.

         ALCATEL NOTE:
             ACCESS:   NA                  USAGE:    NA
             PERSIST:  NO                  INSRVMOD: NA
             RANGE:    NA                  DEFVALUE: 0
             UNITS:    seconds             SPARSE:   NA
             DESCR:    NA
        
        
         FGU4.4:  THIS OBJECT IS NOT SUPPORTED"
::= {gxdslChannelPreviousIntervalEntry 4}

gxdslChannelPreviousIntervalInvalidDataFlag       OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA
        
        
         FGU4.4:  THIS OBJECT IS NOT SUPPORTED"
::= {gxdslChannelPreviousIntervalEntry 5}

gxdslChannelPreviousIntervalCECs        OBJECT-TYPE
        SYNTAX          Counter
        ACCESS          read-only
        STATUS          mandatory
        DESCRIPTION
        "The counter associated with the number of codewords errors
         encountered by the far end channel in a particular 15 minute interval.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED"
::= {gxdslChannelPreviousIntervalEntry 6}

gxdslChannelPreviousSpIndex  OBJECT-TYPE
	SYNTAX 	SpIndex
	ACCESS	not-accessible
	STATUS	mandatory
	DESCRIPTION 
		"Each row is also indexed by a number that
		 contains the slot number, port number and channel number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslChannelPreviousIntervalEntry 7 }



-- xdslChannelPrevious1DayTable           OBJECT-TYPE
--         SYNTAX          SEQUENCE OF XdslChannelPrevious1DayEntry
--         ACCESS          not-accessible
--         STATUS          mandatory
--         DESCRIPTION     
--         "The xdsl channel near end previous 1 day table.
-- 
--          ALCATEL NOTE:
--              TABLESIZE: DEP [number of XDSL lines * maximum number of channels
--                              per XDSL line (1) * number of days (1)]                   
--              DESCR:     NA                  
--         
--          FGU4.4:  THIS TABLE IS NOT SUPPORTED "
-- ::= {gxdslChannelPrevious 2}
--         
-- xdslChannelPrevious1DayEntry           OBJECT-TYPE
--         SYNTAX  XdslChannelPrevious1DayEntry                    
--         ACCESS  not-accessible
--         STATUS  mandatory
--         DESCRIPTION     
--         "An entry in the xdsl channel near end previous 1 day table.
-- 
--          Row creation : Entries for all XDSL channels belonging to a board are 
--                         created when the board becomes operational.
--          Row deletion : Entries for all XDSL channels belonging to a board are 
--                         deleted when the board becomes unavailable.
--         "
--         INDEX          {ifIndex, 
--                         xdslChannelPrevious1DayNumber}
-- ::= {xdslChannelPrevious1DayTable 1}
-- 
-- XdslChannelPrevious1DayEntry ::=
--         SEQUENCE {
--             xdslChannelPrevious1DayNumber             INTEGER,
--             xdslChannelPrevious1DayCVs                Counter,
--             xdslChannelPrevious1DayFECCs              Counter,
--             xdslChannelPrevious1DayMeasuredTime       INTEGER,
--             xdslChannelPrevious1DayInvalidDataFlag    INTEGER,
--             xdslChannelPrevious1DayCECs               Counter
--         }
-- 
-- xdslChannelPrevious1DayNumber          OBJECT-TYPE
--         SYNTAX          INTEGER(1..7)
--         ACCESS          read-only
--         STATUS          mandatory
--         DESCRIPTION     
--         "A number between 1 and 7, which identifies the day for which the 
--          set of statistics is available. The day identified by 1 is the 
--          most recently completed 1Day, and the day identified 
--          by N is the day immediately preceding the one identified by N-1.
-- 
--          ALCATEL NOTE:
--              ACCESS:   NA                  USAGE:    NA
--              PERSIST:  NO                  INSRVMOD: NA
--              RANGE:    1                   DEFVALUE: NA
--              UNITS:    NA                  SPARSE:   NA
--              DESCR:    Only statistics for one previous day is kept.
--         "
-- ::= {xdslChannelPrevious1DayEntry 1}
-- 
-- xdslChannelPrevious1DayCVs             OBJECT-TYPE
--         SYNTAX          Counter
--         ACCESS          read-only
--         STATUS          mandatory
--         DESCRIPTION     
--         "The counter associated with the number of Coding Violations
--          encountered by the channel in the previous 1 day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslChannelPrevious1DayEntry 2}
-- 
-- xdslChannelPrevious1DayFECCs           OBJECT-TYPE
--         SYNTAX          Counter
--         ACCESS          read-only
--         STATUS          mandatory
--         DESCRIPTION     
--         "The counter associated with the number of corrected codewords
--          encountered by the channel, respectively corrected octets in case of
--          VDSL G.993.1, in the previous 1 day interval.
--          If more than one error occurs per superframe then only 1 is reported.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslChannelPrevious1DayEntry 3}
-- 
-- xdslChannelPrevious1DayMeasuredTime    OBJECT-TYPE
--         SYNTAX          INTEGER(0..86400)
--         ACCESS          read-only
--         STATUS          mandatory
--         DESCRIPTION     
--         "The amount of time, measured in seconds, that statistics for this
--          entry have been counted.
-- 
--          ALCATEL NOTE:
--              ACCESS:   NA                  USAGE:    NA
--              PERSIST:  NO                  INSRVMOD: NA
--              RANGE:    NA                  DEFVALUE: 0
--              UNITS:    seconds             SPARSE:   NA
--              DESCR:    NA
--         "
-- ::= {xdslChannelPrevious1DayEntry 4}
-- 
-- xdslChannelPrevious1DayInvalidDataFlag OBJECT-TYPE
--         SYNTAX          INTEGER
--         ACCESS          read-only
--         STATUS          mandatory
--         DESCRIPTION     
--         "This object indicates the validity of the corresponding PM data.
--          It is set to 1 when the PM data is incomplete or invalid and set to 0
--          when the PM data is complete and valid.
-- 
--          ALCATEL NOTE:
--              ACCESS:   NA                  USAGE:    NA
--              PERSIST:  NO                  INSRVMOD: NA
--              RANGE:    0..1                DEFVALUE: 1
--              UNITS:    NA                  SPARSE:   NA
--              DESCR:    NA
--         "
-- ::= {xdslChannelPrevious1DayEntry 5}
-- 
-- xdslChannelPrevious1DayCECs            OBJECT-TYPE
--         SYNTAX  Counter
--         ACCESS  read-only
--         STATUS  mandatory
--         DESCRIPTION
--         "The counter associated with the number of codewords errors
--          encountered by the far end channel in the previous 1 day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslChannelPrevious1DayEntry 6}

--      The XDSL Far End Channel Group

gxdslFarEndChannelOperDataTable         OBJECT-TYPE
        SYNTAX          SEQUENCE OF GxdslFarEndChannelOperDataEntry
        ACCESS          not-accessible
        STATUS          mandatory
        DESCRIPTION     
        "The xdsl far end channel operational data table.

         ALCATEL NOTE:
             TABLESIZE: DEP [number of XDSL lines * maximum number of channels
                             per XDSL line (1)]                    
             DESCR:     NA                  
        "
::= {gxdslFarEndChannelCurrent 1}

gxdslFarEndChannelOperDataEntry         OBJECT-TYPE
        SYNTAX          GxdslFarEndChannelOperDataEntry
        ACCESS          not-accessible
        STATUS          mandatory
        DESCRIPTION     
        "An entry in the xdsl far end channel operational data table.

         Row creation : Entries for all XDSL channels belonging to a board are 
                        created when the board becomes operational.
         Row deletion : Entries for all XDSL channels belonging to a board are 
                        deleted when the board becomes unavailable.
        "
        INDEX          {ifIndex, gxdslFarEndChannelOperSpIndex}
::= {gxdslFarEndChannelOperDataTable 1}

GxdslFarEndChannelOperDataEntry ::=
        SEQUENCE {
            gxdslFarEndChannelActualBitrateDownstream           INTEGER,
            gxdslFarEndChannelAttainableBitrateDownstream       INTEGER,
            gxdslFarEndChannelActualInterleavingDelayUpstream   INTEGER,
            gxdslFarEndChannelActualImpNoiseProtUpstream        INTEGER,
            gxdslFarEndChannelActualL2LowPowerBitrateDownstream INTEGER,
            gxdslFarEndChannelOperSpIndex                       SpIndex
        }

gxdslFarEndChannelActualBitrateDownstream         OBJECT-TYPE
        SYNTAX          INTEGER
        ACCESS          read-only
        STATUS          mandatory
        DESCRIPTION     
        "When the modem is in showtime, then this object gives the actual net
         data rate for the downstream fast or interleaved data flow. When not
         in showtime, then this object has the value measured in preceeding
         showtime session. After an activation failure, this object represents
         the value as available till activation failure. A value 0 means that
         no data is available.

         ALCATEL NOTE:
             ACCESS:   NA                  USAGE:    NA
             PERSIST:  NO                  INSRVMOD: NA
             RANGE:    0..262143           DEFVALUE: 0
             UNITS:    kbits/sec           SPARSE:   NA
             DESCR:    NA
        "
::= {gxdslFarEndChannelOperDataEntry 1}

gxdslFarEndChannelAttainableBitrateDownstream     OBJECT-TYPE
        SYNTAX          INTEGER
        ACCESS          read-only
        STATUS          mandatory
        DESCRIPTION 
        "This object contains the maximum attainable net data rate the modem
         can support on corresponding channel.
         When the modem is not in showtime this object will have the value
         measured during the previous showtime session.
         When no data is available (e.g. before first showtime) value 0
         is used. 

         ALCATEL NOTE:
             ACCESS:   NA                  USAGE:    NA
             PERSIST:  NO                  INSRVMOD: NA
             RANGE:    0..262143           DEFVALUE: 0
             UNITS:    kbit/sec            SPARSE:   NA
             DESCR:    NA "
::= {gxdslFarEndChannelOperDataEntry 2}

gxdslFarEndChannelActualInterleavingDelayUpstream OBJECT-TYPE
        SYNTAX          INTEGER
        ACCESS          read-only
        STATUS          mandatory
        DESCRIPTION     
        "This object gives the actual delay caused by the interleaving and
         deinterleaving functionality.
         When the modem is not in showtime this object will have the value
         measured during the previous showtime session.
         When no data is available (e.g. before first showtime) value 0
         is used.
         Delay range is 0 to 255 ms in steps of 1 ms.

         ALCATEL NOTE:
             ACCESS:   NA                  USAGE:    NA
             PERSIST:  NO                  INSRVMOD: NA
             RANGE:    0..255              DEFVALUE: 0
             UNITS:    milliseconds        SPARSE:   NA
             DESCR:    NA
        "
::= {gxdslFarEndChannelOperDataEntry 3}

gxdslFarEndChannelActualImpNoiseProtUpstream      OBJECT-TYPE
        SYNTAX          INTEGER
        ACCESS          read-only
        STATUS          mandatory
        DESCRIPTION     
        "This object gives the actual impulse noise protection.
         When the modem is not in showtime this object will have the value
         measured during the previous showtime session.
         When no data is available (e.g. before first showtime) value 0
         is used.
         Rate is 0 to 16 symbols in steps of 0.1 symbol.
         It is represented as 1/10 * 
         xdslFarEndChannelActualImpNoiseProtDownstream 

         ALCATEL NOTE:
             ACCESS:   NA                  USAGE:    NA
             PERSIST:  NO                  INSRVMOD: NA
             RANGE:    0..160              DEFVALUE: 0
             UNITS:    symbols / 10        SPARSE:   NA
             DESCR:    NA
        "
::= {gxdslFarEndChannelOperDataEntry 4}

gxdslFarEndChannelActualL2LowPowerBitrateDownstream         OBJECT-TYPE
        SYNTAX          INTEGER
        ACCESS          read-only
        STATUS          mandatory
        DESCRIPTION     
        "When the modem is in the L2 Low Power state, then this object gives
         the actual L2 net data rate for the downstream channel data flow. When 
         not in L2, then this object has the value measured in preceeding L2 
         state. A value 0 means that no data is available.

         ALCATEL NOTE:
             ACCESS:   NA                  USAGE:    NA
             PERSIST:  NO                  INSRVMOD: NA
             RANGE:    0..262143           DEFVALUE: 0
             UNITS:    kbits/sec           SPARSE:   NA
             DESCR:    NA
        
         FGU4.4:  THIS OBJECT IS NOT SUPPORTED "
::= {gxdslFarEndChannelOperDataEntry 5}

gxdslFarEndChannelOperSpIndex  OBJECT-TYPE
	SYNTAX 	SpIndex
	ACCESS	not-accessible
	STATUS	mandatory
	DESCRIPTION 
		"Each row is also indexed by a number that
		 contains the slot number, port number and channel number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslFarEndChannelOperDataEntry 6 }



gxdslFarEndChannelCurrentIntervalTable  OBJECT-TYPE
        SYNTAX          SEQUENCE OF GxdslFarEndChannelCurrentIntervalEntry
        ACCESS          not-accessible
        STATUS          mandatory
        DESCRIPTION     
        "The xdsl far end channel current interval table.

         ALCATEL NOTE:
             TABLESIZE: DEP [number of XDSL lines * maximum number of channels
                             per XDSL line (1)]                    
             DESCR:     NA                  
        "
::= {gxdslFarEndChannelCurrent 2}

gxdslFarEndChannelCurrentIntervalEntry  OBJECT-TYPE
        SYNTAX          GxdslFarEndChannelCurrentIntervalEntry
        ACCESS          not-accessible
        STATUS          mandatory
        DESCRIPTION     
        "An entry in the xdsl far end channel current interval table.

         Row creation : Entries for all XDSL channels belonging to a board are 
                        created when the board becomes operational.
         Row deletion : Entries for all XDSL channels belonging to a board are 
                        deleted when the board becomes unavailable.
        "
        INDEX          {ifIndex, gxdslFarEndChannelCurrentSpIndex}
::= {gxdslFarEndChannelCurrentIntervalTable 1}

GxdslFarEndChannelCurrentIntervalEntry ::=
        SEQUENCE {
            gxdslFarEndChannelCurrentIntervalCVs             Counter,
            gxdslFarEndChannelCurrentIntervalFECCs           Counter,
            gxdslFarEndChannelCurrentIntervalMeasuredTime    INTEGER,
            gxdslFarEndChannelCurrentIntervalInvalidDataFlag INTEGER,
            gxdslFarEndChannelCurrentIntervalCECs            Counter,
            gxdslFarEndChannelCurrentSpIndex                 SpIndex
        }

gxdslFarEndChannelCurrentIntervalCVs    OBJECT-TYPE
        SYNTAX          Counter
        ACCESS          read-only
        STATUS          mandatory
        DESCRIPTION     
        "The counter associated with the number of Coding Violations
         encountered by the far end channel in the current 15 minute interval.

         ALCATEL NOTE:
             ACCESS:   NA                  USAGE:    NA
             PERSIST:  NO                  INSRVMOD: NA
             RANGE:    NA                  DEFVALUE: 0
             UNITS:    NA                  SPARSE:   NA
             DESCR:    NA
        "
::= {gxdslFarEndChannelCurrentIntervalEntry 1}

gxdslFarEndChannelCurrentIntervalFECCs  OBJECT-TYPE
        SYNTAX          Counter
        ACCESS          read-only
        STATUS          mandatory
        DESCRIPTION     
        "The counter associated with the number of corrected codewords
         encountered by the far end channel, respectively corrected octets in case of
         VDSL G.993.1, in the current 15 minute interval.
         If more than one error occurs per superframe then only 1 is reported.

         ALCATEL NOTE:
             ACCESS:   NA                  USAGE:    NA
             PERSIST:  NO                  INSRVMOD: NA
             RANGE:    NA                  DEFVALUE: 0
             UNITS:    NA                  SPARSE:   NA
             DESCR:    NA
        "
::= {gxdslFarEndChannelCurrentIntervalEntry 2}

gxdslFarEndChannelCurrentIntervalMeasuredTime     OBJECT-TYPE
        SYNTAX          INTEGER(0..900)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA
        
        
         FGU4.4:  THIS OBJECT IS NOT SUPPORTED "
::= {gxdslFarEndChannelCurrentIntervalEntry 3}

gxdslFarEndChannelCurrentIntervalInvalidDataFlag  OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA
        
        
         FGU4.4:  THIS OBJECT IS NOT SUPPORTED"
::= {gxdslFarEndChannelCurrentIntervalEntry 4}

gxdslFarEndChannelCurrentIntervalCECs   OBJECT-TYPE
        SYNTAX          Counter
        ACCESS          read-only
        STATUS          mandatory
        DESCRIPTION
        "The counter associated with the number of codewords errors
         encountered by the far end channel in the current 15 minute interval.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED "
::= {gxdslFarEndChannelCurrentIntervalEntry 5}

gxdslFarEndChannelCurrentSpIndex  OBJECT-TYPE
	SYNTAX 	SpIndex
	ACCESS	not-accessible
	STATUS	mandatory
	DESCRIPTION 
		"Each row is also indexed by a number that
		 contains the slot number, port number and channel number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslFarEndChannelCurrentIntervalEntry 6 }



-- xdslFarEndChannelCurrent1DayTable      OBJECT-TYPE
--         SYNTAX          SEQUENCE OF XdslFarEndChannelCurrent1DayEntry
--         ACCESS          not-accessible
--         STATUS          mandatory
--         DESCRIPTION     
--         "The xdsl channel far end current 1 day table.
-- 
--          ALCATEL NOTE:
--              TABLESIZE: DEP [number of XDSL lines * maximum number of channels
--                              per XDSL line (1)]                    
--              DESCR:     NA                  
--         
--          FGU4.4:  THIS TABLE IS NOT SUPPORTED "
-- ::= {gxdslFarEndChannelCurrent 3}
--      
-- xdslFarEndChannelCurrent1DayEntry      OBJECT-TYPE
--         SYNTAX  XdslFarEndChannelCurrent1DayEntry                       
--         ACCESS  not-accessible
--         STATUS  mandatory
--         DESCRIPTION     
--         "An entry in the xdsl channel far end current 1 day table.
-- 
--          Row creation : Entries for all XDSL channels belonging to a board are 
--                         created when the board becomes operational.
--          Row deletion : Entries for all XDSL channels belonging to a board are 
--                         deleted when the board becomes unavailable.
--         "
--         INDEX          {ifIndex}
-- ::= {xdslFarEndChannelCurrent1DayTable 1}
-- 
-- XdslFarEndChannelCurrent1DayEntry ::=
--         SEQUENCE {
--             xdslFarEndChannelCurrent1DayCVs             Counter,
--             xdslFarEndChannelCurrent1DayFECCs           Counter,
--             xdslFarEndChannelCurrent1DayMeasuredTime    INTEGER,
--             xdslFarEndChannelCurrent1DayInvalidDataFlag INTEGER,
--             xdslFarEndChannelCurrent1DayCECs            Counter
--         }
-- 
-- xdslFarEndChannelCurrent1DayCVs        OBJECT-TYPE
--         SYNTAX          Counter
--         ACCESS          read-only
--         STATUS          mandatory
--         DESCRIPTION     
--         "The counter associated with the number of Coding Violations 
--          encountered by the far end channel in the current 1 day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndChannelCurrent1DayEntry 1}
-- 
-- xdslFarEndChannelCurrent1DayFECCs      OBJECT-TYPE
--         SYNTAX          Counter
--         ACCESS          read-only
--         STATUS          mandatory
--         DESCRIPTION     
--         "The counter associated with the number of corrected codewords
--          encountered by the far end channel, respectively corrected octets in case of
--          VDSL G.993.1, in the current 1 day interval.
--          If more than one error occurs per superframe then only 1 is reported.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndChannelCurrent1DayEntry 2}
-- 
-- xdslFarEndChannelCurrent1DayMeasuredTime         OBJECT-TYPE
--         SYNTAX          INTEGER(0..86400)
--         ACCESS          read-only
--         STATUS          mandatory
--         DESCRIPTION     
--         "The amount of time, measured in seconds, that statistics for this
--          entry have been counted.
-- 
--          ALCATEL NOTE:
--              ACCESS:   NA                  USAGE:    NA
--              PERSIST:  NO                  INSRVMOD: NA
--              RANGE:    NA                  DEFVALUE: 0
--              UNITS:    seconds             SPARSE:   NA
--              DESCR:    NA
--         "
-- ::= {xdslFarEndChannelCurrent1DayEntry 3}
-- 
-- xdslFarEndChannelCurrent1DayInvalidDataFlag      OBJECT-TYPE
--         SYNTAX          INTEGER
--         ACCESS          read-only
--         STATUS          mandatory
--         DESCRIPTION     
--         "This object indicates the validity of the corresponding PM data.
--          It is set to 1 when the PM data is incomplete or invalid and set to 0
--          when the PM data is complete and valid.
-- 
--          ALCATEL NOTE:
--              ACCESS:   NA                  USAGE:    NA
--              PERSIST:  NO                  INSRVMOD: NA
--              RANGE:    0..1                DEFVALUE: 1
--              UNITS:    NA                  SPARSE:   NA
--              DESCR:    NA
--         "
-- ::= {xdslFarEndChannelCurrent1DayEntry 4}
-- 
-- xdslFarEndChannelCurrent1DayCECs       OBJECT-TYPE
--         SYNTAX          Counter
--         ACCESS          read-only
--         STATUS          mandatory
--         DESCRIPTION
--         "The counter associated with the number of codewords errors
--          encountered by the far end channel in the current 1 day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndChannelCurrent1DayEntry 5}

gxdslFarEndChannelPreviousIntervalTable OBJECT-TYPE
        SYNTAX          SEQUENCE OF GxdslFarEndChannelPreviousIntervalEntry
        ACCESS          not-accessible
        STATUS          mandatory
        DESCRIPTION     
        "The xdsl far end channel previous interval table.
         ALCATEL NOTE:
             TABLESIZE: DEP [number of XDSL lines * maximum number of channels
                             per XDSL line (1) * 192]                    
             DESCR:     NA                  
        "
::= {gxdslFarEndChannelPrevious 1}

gxdslFarEndChannelPreviousIntervalEntry OBJECT-TYPE
        SYNTAX          GxdslFarEndChannelPreviousIntervalEntry
        ACCESS          not-accessible
        STATUS          mandatory
        DESCRIPTION     
        "An entry in the xdsl far end channel previous interval table.

         Row creation : Entries for all XDSL channels belonging to a board are 
                        created when the board becomes operational.
         Row deletion : Entries for all XDSL channels belonging to a board are 
                        deleted when the board becomes unavailable.
        "
        INDEX          {ifIndex, gxdslFarEndChannelPreviousSpIndex, 
                        gxdslFarEndChannelPreviousIntervalNumber}
::= {gxdslFarEndChannelPreviousIntervalTable 1}

GxdslFarEndChannelPreviousIntervalEntry ::=
        SEQUENCE {
            gxdslFarEndChannelPreviousIntervalNumber           INTEGER,
            gxdslFarEndChannelPreviousIntervalCVs              Counter,
            gxdslFarEndChannelPreviousIntervalFECCs            Counter,
            gxdslFarEndChannelPreviousIntervalMeasuredTime     INTEGER,
            gxdslFarEndChannelPreviousIntervalInvalidDataFlag  INTEGER,
            gxdslFarEndChannelPreviousIntervalCECs             Counter,
            gxdslFarEndChannelPreviousSpIndex                  SpIndex
        }
        
gxdslFarEndChannelPreviousIntervalNumber          OBJECT-TYPE
       SYNTAX           INTEGER(1..192)
       ACCESS           read-only
       STATUS           mandatory
       DESCRIPTION     
       "A number between 1 and 192, which identifies the interval for which the
        set of statistics is available. The interval identified by 1 is the
        most recently completed 15 minute interval, and the interval
        identified by N is the interval immediately preceding the one
        identified by N-1.

         ALCATEL NOTE:
             ACCESS:   NA                  USAGE:    NA
             PERSIST:  NO                  INSRVMOD: NA
             RANGE:    NA                  DEFVALUE: NA
             UNITS:    NA                  SPARSE:   NA
             DESCR:    NA
        "
::= {gxdslFarEndChannelPreviousIntervalEntry 1}

gxdslFarEndChannelPreviousIntervalCVs   OBJECT-TYPE
        SYNTAX          Counter
        ACCESS          read-only
        STATUS          mandatory
        DESCRIPTION     
        "The counter associated with the number of Coding Violations 
         encountered by the far end channel in a particular 15 minute interval.

         ALCATEL NOTE:
             ACCESS:   NA                  USAGE:    NA
             PERSIST:  NO                  INSRVMOD: NA
             RANGE:    NA                  DEFVALUE: 0
             UNITS:    NA                  SPARSE:   NA
             DESCR:    NA
        "
::= {gxdslFarEndChannelPreviousIntervalEntry 2}

gxdslFarEndChannelPreviousIntervalFECCs OBJECT-TYPE
        SYNTAX          Counter
        ACCESS          read-only
        STATUS          mandatory
        DESCRIPTION     
        "The counter associated with the number of corrected codewords 
         encountered by the far end channel, respectively corrected octets in case of
         VDSL G.993.1, in a particular 15 minute interval.
         If more than one error occurs per superframe then only 1 is reported.

         ALCATEL NOTE:
             ACCESS:   NA                  USAGE:    NA
             PERSIST:  NO                  INSRVMOD: NA
             RANGE:    NA                  DEFVALUE: 0
             UNITS:    NA                  SPARSE:   NA
             DESCR:    NA
        "
::= {gxdslFarEndChannelPreviousIntervalEntry 3}

gxdslFarEndChannelPreviousIntervalMeasuredTime    OBJECT-TYPE
        SYNTAX          INTEGER(0..900)
        ACCESS          read-only
        STATUS          mandatory
        DESCRIPTION     
        "The amount of time, measured in seconds, that statistics for this
         entry have been counted.

         ALCATEL NOTE:
             ACCESS:   NA                  USAGE:    NA
             PERSIST:  NO                  INSRVMOD: NA
             RANGE:    NA                  DEFVALUE: 0
             UNITS:    seconds             SPARSE:   NA
             DESCR:    NA
        
        
         FGU4.4:  THIS OBJECT IS NOT SUPPORTED"
::= {gxdslFarEndChannelPreviousIntervalEntry 4}

gxdslFarEndChannelPreviousIntervalInvalidDataFlag OBJECT-TYPE
        SYNTAX          INTEGER
        ACCESS          read-only
        STATUS          mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    0..1                DEFVALUE: 1
             UNITS:    NA                  SPARSE:   NA
             DESCR:    NA
        
        
         FGU4.4:  THIS OBJECT IS NOT SUPPORTED"
::= {gxdslFarEndChannelPreviousIntervalEntry 5}


gxdslFarEndChannelPreviousIntervalCECs  OBJECT-TYPE
        SYNTAX          Counter
        ACCESS          read-only
        STATUS          mandatory
        DESCRIPTION
        "The counter associated with the number of codewords errors
         encountered by the far end channel in a particular 15 minute interval.

         ALCATEL NOTE:
             ACCESS:   NA                  USAGE:    NA
             PERSIST:  NO                  INSRVMOD: NA
             RANGE:    NA                  DEFVALUE: 0
             UNITS:    NA                  SPARSE:   NA
             DESCR:    NA
        
        
         FGU4.4:  THIS OBJECT IS NOT SUPPORTED"
::= {gxdslFarEndChannelPreviousIntervalEntry 6}

gxdslFarEndChannelPreviousSpIndex  OBJECT-TYPE
	SYNTAX 	SpIndex
	ACCESS	not-accessible
	STATUS	mandatory
	DESCRIPTION 
		"Each row is also indexed by a number that
		 contains the slot number, port number and channel number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslFarEndChannelPreviousIntervalEntry 7 }



-- xdslFarEndChannelPrevious1DayTable     OBJECT-TYPE
--         SYNTAX          SEQUENCE OF XdslFarEndChannelPrevious1DayEntry
--         ACCESS          not-accessible
--         STATUS          mandatory
--         DESCRIPTION     
--         "The xdsl channel far end previous 1 day table.
-- 
--          ALCATEL NOTE:
--              TABLESIZE: DEP [number of XDSL lines * maximum number of channels
--                              per XDSL line (1) * number of days (1)]                    
--              DESCR:     NA                  
--         
--          FGU4.4:  THIS TABLE IS NOT SUPPORTED "
-- ::= {gxdslFarEndChannelPrevious 2}
--      
-- xdslFarEndChannelPrevious1DayEntry     OBJECT-TYPE
--         SYNTAX          XdslFarEndChannelPrevious1DayEntry                      
--         ACCESS          not-accessible
--         STATUS          mandatory
--         DESCRIPTION     
--         "An entry in the xdsl channel far end previous 1 day table.
-- 
--          Row creation : Entries for all XDSL channels belonging to a board are 
--                         created when the board becomes operational.
--          Row deletion : Entries for all XDSL channels belonging to a board are 
--                         deleted when the board becomes unavailable.
--         "
--         INDEX          {ifIndex, 
--                         xdslFarEndChannelPrevious1DayNumber}
-- ::= {xdslFarEndChannelPrevious1DayTable 1}
-- 
-- XdslFarEndChannelPrevious1DayEntry ::=
--         SEQUENCE {
--             xdslFarEndChannelPrevious1DayNumber             INTEGER,
--             xdslFarEndChannelPrevious1DayCVs                Counter,
--             xdslFarEndChannelPrevious1DayFECCs              Counter,
--             xdslFarEndChannelPrevious1DayMeasuredTime       INTEGER,
--             xdslFarEndChannelPrevious1DayInvalidDataFlag    INTEGER,
--             xdslFarEndChannelPrevious1DayCECs               Counter
--         }
-- 
-- xdslFarEndChannelPrevious1DayNumber    OBJECT-TYPE
--        SYNTAX  INTEGER(1..7)
--        ACCESS  read-only
--        STATUS  mandatory
--        DESCRIPTION     
--         "A number between 1 and 7, which identifies the day for which the
--          set of statistics is available. The day identified by 1 is the most
--          recently completed 1Day, and the day identified by
--          N is the day immediately preceding the one identified by N-1.
-- 
--          ALCATEL NOTE:
--              ACCESS:   NA                  USAGE:    NA
--              PERSIST:  NO                  INSRVMOD: NA
--              RANGE:    1                   DEFVALUE: NA
--              UNITS:    NA                  SPARSE:   NA
--              DESCR:    Only statistics for one previous day is kept.
--         "
-- ::= {xdslFarEndChannelPrevious1DayEntry 1}
-- 
-- xdslFarEndChannelPrevious1DayCVs       OBJECT-TYPE
--         SYNTAX          Counter
--         ACCESS          read-only
--         STATUS          mandatory
--         DESCRIPTION     
--         "The counter associated with the number of Coding Violations
--          encountered by the far end channel in the previous 1 day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndChannelPrevious1DayEntry 2}
-- 
-- xdslFarEndChannelPrevious1DayFECCs     OBJECT-TYPE
--         SYNTAX          Counter
--         ACCESS          read-only
--         STATUS          mandatory
--         DESCRIPTION     
--         "The counter associated with the number of corrected codewords 
--          encountered by the far end channel, respectively corrected octets in case of
--          VDSL G.993.1, in the previous 1 day interval. If 
--          more than one error occurs per superframe then only 1 is reported.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndChannelPrevious1DayEntry 3}
-- 
-- xdslFarEndChannelPrevious1DayMeasuredTime        OBJECT-TYPE
--         SYNTAX          INTEGER(0..86400)
--         ACCESS          read-only
--         STATUS          mandatory
--         DESCRIPTION     
--         "The amount of time, measured in seconds, that statistics for this
--          entry have been counted.
-- 
--          ALCATEL NOTE:
--              ACCESS:   NA                  USAGE:    NA
--              PERSIST:  NO                  INSRVMOD: NA
--              RANGE:    NA                  DEFVALUE: 0
--              UNITS:    seconds             SPARSE:   NA
--              DESCR:    NA
--         "
-- ::= {xdslFarEndChannelPrevious1DayEntry 4}
-- 
-- xdslFarEndChannelPrevious1DayInvalidDataFlag     OBJECT-TYPE
--         SYNTAX          INTEGER
--         ACCESS          read-only
--         STATUS          mandatory
--         DESCRIPTION     
--         "This object indicates the validity of the corresponding PM data.
--          It is set to 1 when the PM data is incomplete or invalid and set to 0
--          when the PM data is complete and valid.
-- 
--          ALCATEL NOTE:
--              ACCESS:   NA                  USAGE:    NA
--              PERSIST:  NO                  INSRVMOD: NA
--              RANGE:    0..1                DEFVALUE: 1
--              UNITS:    NA                  SPARSE:   NA
--              DESCR:    NA
--         "
-- ::= {xdslFarEndChannelPrevious1DayEntry 5}
-- 
-- xdslFarEndChannelPrevious1DayCECs      OBJECT-TYPE
--         SYNTAX          Counter
--         ACCESS          read-only
--         STATUS          mandatory
--         DESCRIPTION
--         "The counter associated with the number of codewords errors
--          encountered by the far end channel in a particular 1 Day interval.
-- 
--          ALCATEL NOTE:
--              ACCESS:   NA                  USAGE:    NA
--              PERSIST:  NO                  INSRVMOD: NA
--              RANGE:    NA                  DEFVALUE: 0
--              UNITS:    NA                  SPARSE:   NA
--              DESCR:    NA
--         "
-- ::= {xdslFarEndChannelPrevious1DayEntry 6}

-- 
-- XDSL TEST GROUP
--

-- xdslPOTSlineTest             OBJECT IDENTIFIER ::= {gxdslTestTypes 1}

-- xdslXtucNotReachable         OBJECT IDENTIFIER ::= {gxdslTestCodes 1}

-- xdslXturNotReachable        OBJECT IDENTIFIER ::= {gxdslTestCodes 2}

-- xdslNonAlcatelXtur          OBJECT IDENTIFIER ::= {gxdslTestCodes 3}

-- xdslNoHardwareSupport        OBJECT IDENTIFIER ::= {gxdslTestCodes 4}

-- xdslAnotherTestInProgress    OBJECT IDENTIFIER ::= {gxdslTestCodes 5}

-- xdslPreparingPOTSTest       OBJECT IDENTIFIER ::= {gxdslTestCodes 6}

-- xdslLineModeIsdn            OBJECT IDENTIFIER ::= {gxdslTestCodes 7}

-- xdslTestPOTSlineTestDuration           OBJECT-TYPE
--         SYNTAX          TimeTicks 
--         ACCESS          read-write
--         STATUS          mandatory
--         DESCRIPTION 
--         "Configurable test duration time, the same for all lines.
-- 
--          ALCATEL NOTE:
--              ACCESS:   NA                  USAGE:    NA
--              PERSIST:  NO                  INSRVMOD: YES
--              RANGE:    1..300              DEFVALUE: 300
--              UNITS:    seconds             SPARSE:   NA
--              DESCR:    NA
-- 
--   FTTU4.5.5 - attribute is NOT SUPPORTED (Never has been for FTTU)
--         "
-- ::= {gxdslTest 3}
-- 
 
gxdslXturInventoryTable  OBJECT-TYPE
         SYNTAX          SEQUENCE OF GxdslXturInventoryEntry
         ACCESS          not-accessible
         STATUS          mandatory
         DESCRIPTION
         "This table provides one row for each XTU-R, containing the
          inventory data of that XTU-R. When not in showtime, the previous 
          inventory data values will be returned. If no value is available,
          an empty string will be returned.
 
          ALCATEL NOTE:
              TABLESIZE: DEP [number of XDSL lines]                    
              DESCR:     NA                  
        "
::= {gxdslXturInventory 1}

gxdslXturInventoryEntry  OBJECT-TYPE
        SYNTAX          GxdslXturInventoryEntry
        ACCESS          not-accessible
        STATUS          mandatory
        DESCRIPTION
        "An entry in the xdslXturInventoryTable.

         Row creation : Entries for all XDSL channels belonging to a board are 
                        created when the board becomes operational.
         Row deletion : Entries for all XDSL channels belonging to a board are 
                        deleted when the board becomes unavailable.
        "
        INDEX          {ifIndex, gxdslXturSpIndex}
::= {gxdslXturInventoryTable 1}
  
GxdslXturInventoryEntry ::=
        SEQUENCE {
            gxdslXturInvModemVendorID                  OCTET STRING,
            gxdslXturInvSystemSerialNumber             OCTET STRING,
            gxdslXturInvSystemVendorID                 OCTET STRING,
            gxdslXturInvSystemVersionNumber            OCTET STRING,
            gxdslXturInvSelfTestResults                OCTET STRING,
            gxdslXturSpIndex                           SpIndex
        }
    
gxdslXturInvModemVendorID               OBJECT-TYPE
        SYNTAX     OCTET STRING (SIZE (0..16))
        ACCESS     read-only
        STATUS     mandatory
        DESCRIPTION
        "The vendor ID retrieved during handshaking is considered as the
         vendor ID of the XTU-R modem. The binary vendor identification field
         is a binary string of N bytes. This string is converted, nibble by
         nibble, in a hexadecimal format resulting in an ASCII text string of
         2*N characters, i.e. each byte of the vendor ID code is represented by
         2 hexadecimal characters.
         The vendor ID is composed as follows:
            - for ANSI & ETSI: 2 bytes vendor specific code
            - for ITU-T: 8 bytes code, composed of
                * T.35 country code (2 bytes)
                * provider code (4 bytes)
                * vendor-specific information (2 bytes)

         ALCATEL NOTE:
             ACCESS:   NA                  USAGE:    NA
             PERSIST:  NO                  INSRVMOD: NA
             RANGE:    NA                  DEFVALUE: ''H
             UNITS:    ASCII characters    SPARSE:   NA
             DESCR:    NA
        "
::= { gxdslXturInventoryEntry 1 }

gxdslXturInvSystemSerialNumber          OBJECT-TYPE
        SYNTAX          OCTET STRING (SIZE (0..32))
        ACCESS          read-only
        STATUS          mandatory
        DESCRIPTION
        "The unique vendor specific string that identifies the vendor
         equipment, and which is retrieved via the XDSL EOC. The value of the
         serial number is vendor discretionary.
         The serial number stored in the XTU-R consists of 32 bytes (see
         G.992.1/2) and is mapped straightforward onto this MIB object (see 
         also RFC2662).
         As the XTU-R serial number already consists of alphanumerical
         characters, no conversion is needed to make the value humanly 
         readable.

         ALCATEL NOTE:
             ACCESS:   NA                  USAGE:    NA
             PERSIST:  NO                  INSRVMOD: NA
             RANGE:    NA                  DEFVALUE: ''H
             UNITS:    ASCII characters    SPARSE:   NA
             DESCR:    NA
        "
::= { gxdslXturInventoryEntry 2 }

gxdslXturInvSystemVendorID              OBJECT-TYPE
        SYNTAX          OCTET STRING (SIZE (0..16))
        ACCESS          read-only
        STATUS          mandatory
        DESCRIPTION
        "The vendor ID retrieved via the XDSL EOC is considered as the vendor
         ID of the XTU-R assembly (CPE). The binary vendor identification field
         is a binary string of N bytes. This string is converted, nibble by
         nibble, in a hexadecimal format resulting in an ASCII text string of
         2*N characters, i.e. each byte of the vendor ID code is represented by
         2 hexadecimal characters.
         The vendor ID is composed as follows:
           - for ANSI & ETSI: 2 bytes vendor specific code
           - for ITU-T: 8 bytes code, composed of
               * T.35 country code (2 bytes)
               * provider code (4 bytes)
               * vendor-specific information (2 bytes)

         ALCATEL NOTE:
             ACCESS:   NA                  USAGE:    NA
             PERSIST:  NO                  INSRVMOD: NA
             RANGE:    NA                  DEFVALUE: ''H
             UNITS:    ASCII characters    SPARSE:   NA
             DESCR:    NA
        "
 ::= { gxdslXturInventoryEntry 3 }

 gxdslXturInvSystemVersionNumber        OBJECT-TYPE
        SYNTAX          OCTET STRING (SIZE (0..34))
        ACCESS          read-only
        STATUS          mandatory
        DESCRIPTION
        "The vendor specific version number retrieved via the XDSL EOC.
         The binary version number field is a binary string of N bytes. This
         string is converted, nibble by nibble, in a hexadecimal format
         resulting in an ASCII text string of 2*N characters, i.e. each byte of
         the version number code is represented by 2 hexadecimal characters.
         The format and length of the XTU-R version number is vendor
         discretionary.
         This number will be truncated in case its length exceeds 17 bytes.
         Alcatel note: The maximum size of 34 allows to store the complete
         contents of the version number returned by the Alcatel XTU-R.

         ALCATEL NOTE:
             ACCESS:   NA                  USAGE:    NA
             PERSIST:  NO                  INSRVMOD: NA
             RANGE:    NA                  DEFVALUE: ''H
             UNITS:    ASCII characters    SPARSE:   NA
             DESCR:    NA
        "
::= { gxdslXturInventoryEntry 4 }

gxdslXturInvSelfTestResults             OBJECT-TYPE
        SYNTAX          OCTET STRING (SIZE (0..8))
        ACCESS          read-only
        STATUS          mandatory
        DESCRIPTION
        "Self test results value retrieved via the the XDSL EOC. This
         parameter is a N-bytes binary code. This string is converted, nibble
         by nibble, in a hexadecimal format resulting in an ASCII text string
         of 2*N characters, i.e. each byte of the self test results code is
         represented by 2 hexadecimal characters.
         The most significant octet (= first octet) is 00hex if the self test
         passed and 01hex if the self test failed. The interpretation of the 
         other octets is vendor discretionary.

         ALCATEL NOTE:
             ACCESS:   NA                  USAGE:    NA
             PERSIST:  NO                  INSRVMOD: NA
             RANGE:    NA                  DEFVALUE: ''H
             UNITS:    ASCII characters    SPARSE:   NA
             DESCR:    NA
        "
::= { gxdslXturInventoryEntry 5 }


gxdslXturSpIndex  OBJECT-TYPE
	SYNTAX 	SpIndex
	ACCESS	not-accessible
	STATUS	mandatory
	DESCRIPTION 
		"Each row is also indexed by a number that
		 contains the slot number and port number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslXturInventoryEntry 6 }


gxdslXtucInventoryTable OBJECT-TYPE
        SYNTAX     SEQUENCE OF GxdslXtucInventoryEntry
        ACCESS     not-accessible
        STATUS     mandatory
        DESCRIPTION
        "This table provides one row for each XTU-C, containing the
         inventory data of that XTU-C.
         ALCATEL NOTE:
             DESCR:    This table is SUPPORTED for FGU4.4.
         "
::= {gxdslXtucInventory 1}

gxdslXtucInventoryEntry OBJECT-TYPE
        SYNTAX     GxdslXtucInventoryEntry
        ACCESS     not-accessible
        STATUS     mandatory
        DESCRIPTION
        "An entry in the xdslXtucInventoryTable.
         ALCATEL NOTE:
             DESCR:    This object is SUPPORTED for FGU4.4.
         "
        INDEX      {ifIndex, gxdslXtucSpIndex}
::= {gxdslXtucInventoryTable 1}

GxdslXtucInventoryEntry ::=
        SEQUENCE {
        gxdslXtucInvSystemSerialNumber    OCTET STRING,
        gxdslXtucInvSystemVendorID        OCTET STRING,
        gxdslXtucInvSystemVersionNumber   OCTET STRING,
        gxdslXtucInvModemVendorID         OCTET STRING,
        gxdslXtucSpIndex                  SpIndex
        }
 
gxdslXtucInvSystemSerialNumber OBJECT-TYPE
        SYNTAX     OCTET STRING (SIZE (0..32))
        ACCESS     read-only
        STATUS     mandatory
        DESCRIPTION
        "The unique vendor specific string that identifies the vendor equipment.
         The value of the serial number is vendor discretionary.
         The serial number stored in the XTU-C consists of 32 bytes (see
         G.992.1/2) and is mapped straightforward onto this MIB object (see
         also RFC2662).
         As the XTU-C serial number already consists of alphanumerical 
         characters, no conversion is needed to make the value humanly
         readable.
         ALCATEL NOTE:
             ACCESS:   NA                  USAGE:    NA
             PERSIST:  NA                  INSRVMOD: NA
             RANGE:    NA                  DEFVALUE: NA
             UNITS:    NA                  SPARSE:   NA
             DESCR:    This object is SUPPORTED for FGU4.4.
         "
::= { gxdslXtucInventoryEntry 1 }

gxdslXtucInvSystemVendorID OBJECT-TYPE
        SYNTAX     OCTET STRING (SIZE (0..16))
        ACCESS     read-only
        STATUS     mandatory
        DESCRIPTION
        "The vendor ID of the XTU-C assembly. The binary vendor identification
         field is a binary string of N bytes. This string is converted, nibble
         by nibble, in a hexadecimal format resulting in an ASCII text string
         of 2*N characters, i.e. each byte of the vendor ID code is
         represented by 2 hexadecimal characters.
         The vendor ID is composed as follows:
           - for ANSI & ETSI: 2 bytes vendor specific code
           - for ITU-T: 8 bytes code, composed of
               * T.35 country code (2 bytes)
               * provider code (4 bytes)
               * vendor-specific information (2 bytes)
         ALCATEL NOTE:
             ACCESS:   NA                  USAGE:    NA
             PERSIST:  NA                  INSRVMOD: NA
             RANGE:    NA                  DEFVALUE: NA
             UNITS:    NA                  SPARSE:   NA
             DESCR:    This object is SUPPORTED for FGU4.4.
         "
::= { gxdslXtucInventoryEntry 2 }

gxdslXtucInvSystemVersionNumber OBJECT-TYPE
        SYNTAX     OCTET STRING (SIZE (0..34))
        ACCESS     read-only
        STATUS     mandatory
        DESCRIPTION
        "The vendor specific version number. The binary version number field
         is a binary string of N bytes. This string is converted, nibble by
         nibble, in a hexadecimal format resulting in an ASCII text string of
         2*N characters, i.e. each byte of the version number code
         is represented by 2 hexadecimal characters.
         The format and length of the XTU-C version number is vendor
         discretionary.
         This number will be truncated in case its length exceeds 17 bytes.
         Alcatel note: The maximum size of 34 allows to store the complete
         content of the version number returned by the Alcatel XTU-C.
         ALCATEL NOTE:
             ACCESS:   NA                  USAGE:    NA
             PERSIST:  NA                  INSRVMOD: NA
             RANGE:    NA                  DEFVALUE: NA
             UNITS:    NA                  SPARSE:   NA
             DESCR:    This object is SUPPORTED for FGU4.4.
         "
::= { gxdslXtucInventoryEntry 3 }

gxdslXtucInvModemVendorID OBJECT-TYPE
        SYNTAX     OCTET STRING (SIZE (0..16))
        ACCESS     read-only
        STATUS     mandatory
        DESCRIPTION
        "The vendor ID of the XTU-C modem. The binary vendor identification
         field is a binary string of N bytes. This string is converted, nibble
         by nibble, in a  hexadecimal format resulting in an ASCII text string
         of 2*N characters, i.e. each byte of the vendor ID code is represented
         by 2 hexadecimal characters.
         The vendor ID is composed as follows:
           - for ANSI & ETSI: 2 bytes vendor specific code
           - for ITU-T: 8 bytes code, composed of
               * T.35 country code (2 bytes)
               * provider code (4 bytes)
               * vendor-specific information (2 bytes)
         ALCATEL NOTE:
             ACCESS:   NA                  USAGE:    NA
             PERSIST:  NA                  INSRVMOD: NA
             RANGE:    NA                  DEFVALUE: NA
             UNITS:    NA                  SPARSE:   NA
             DESCR:    This object is SUPPORTED for FGU4.4.
         "
::= { gxdslXtucInventoryEntry 4 }

gxdslXtucSpIndex  OBJECT-TYPE
	SYNTAX 	SpIndex
	ACCESS	not-accessible
	STATUS	mandatory
	DESCRIPTION 
		"Each row is also indexed by a number that
		 contains the slot number and port number
		 within the ONT. 
           
             ALCATEL NOTE: THIS OBJECT IS ADDED TO THE xDSL MIB DUE TO THE 
                           DOUBLE INDEXING SCHEME THAT DOES NOT ALLOW THE USE OF 
                           STANDARD IF-TABLES TO FULL EXTENT "
	::= { gxdslXtucInventoryEntry 5 }



gxdslLineTcaThresholdTable              OBJECT-TYPE
        SYNTAX          SEQUENCE OF GxdslLineTcaThresholdEntry
        ACCESS          not-accessible
        STATUS          mandatory
        DESCRIPTION
        "The XDSL line TCA threshold table, containing the thresholds for
         the TCA's for the XDSL line (both near-end and far-end.

         ALCATEL NOTE:
             TABLESIZE: DEP [number of XDSL lines]                    
             DESCR:     NA"
::= { gxdslLineTcaThreshold  1 }

gxdslLineTcaThresholdEntry              OBJECT-TYPE
        SYNTAX          GxdslLineTcaThresholdEntry
        ACCESS          not-accessible
        STATUS          mandatory
        DESCRIPTION
        "An entry in the XDSL line TCA threshold table.

         Row creation : Entries for all XDSL lines belonging to a board are 
                        created by the system when the board is planned.
         Row deletion : Entries for all XDSL lines belonging to a board are 
                        deleted by the system when the board is unplanned.

       FGU4.4:  Table rows are created/deleted when the corresponding line
	        is created/deleted.
        "
        INDEX          {ifIndex, tcaThresholdSpIndex }
::= { gxdslLineTcaThresholdTable  1 }

GxdslLineTcaThresholdEntry ::=
        SEQUENCE {
            gxdslLineTcaEnable                         INTEGER,
            gxdslLineIntervalESsTcaThreshold           INTEGER,
            gxdslLineIntervalSESsTcaThreshold          INTEGER,
            gxdslLineIntervalUASsTcaThreshold          INTEGER,
            gxdslLine1DayESsTcaThreshold               INTEGER,
            gxdslLine1DaySESsTcaThreshold              INTEGER,
            gxdslLine1DayUASsTcaThreshold              INTEGER,
            gxdslFarEndLineIntervalESsTcaThreshold     INTEGER,
            gxdslFarEndLineIntervalSESsTcaThreshold    INTEGER,
            gxdslFarEndLineIntervalUASsTcaThreshold    INTEGER,
            gxdslFarEndLine1DayESsTcaThreshold         INTEGER,
            gxdslFarEndLine1DaySESsTcaThreshold        INTEGER,
            gxdslFarEndLine1DayUASsTcaThreshold        INTEGER,
            tcaThresholdSpIndex                       SpIndex
        }

gxdslLineTcaEnable       OBJECT-TYPE
        SYNTAX          INTEGER {
                            enabled(1),
                            disabled(2) 
                        }
        ACCESS          read-write
        STATUS          mandatory
        DESCRIPTION
        "This variable allows the manager to enable/disable the reporting of
         TCA's for this XDSL line.

         ALCATEL NOTE:
             ACCESS:   NA                  USAGE:    OPT
             PERSIST:  YES                 INSRVMOD: YES
             RANGE:    NA                  DEFVALUE: disabled
             UNITS:    NA                  SPARSE:   NA
             DESCR:    NA
        "
::= { gxdslLineTcaThresholdEntry 1 }

gxdslLineIntervalESsTcaThreshold        OBJECT-TYPE
        SYNTAX          INTEGER(0..900)
        ACCESS          read-write
        STATUS          mandatory
        DESCRIPTION
        "XDSL TCA threshold for Errored Seconds at the near end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA
        "
::= { gxdslLineTcaThresholdEntry  2 }

gxdslLineIntervalSESsTcaThreshold       OBJECT-TYPE
        SYNTAX          INTEGER(0..900)
        ACCESS          read-write
        STATUS          mandatory
        DESCRIPTION
        "XDSL TCA threshold for Severely Errored Seconds at the near end.
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA
        "
::= { gxdslLineTcaThresholdEntry  3 }

gxdslLineIntervalUASsTcaThreshold       OBJECT-TYPE
        SYNTAX          INTEGER(0..900)
        ACCESS          read-write
        STATUS          mandatory
        DESCRIPTION
        "XDSL TCA threshold for Unavailable Seconds at the near end.
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA
        "
::= { gxdslLineTcaThresholdEntry  4 }

gxdslLine1DayESsTcaThreshold            OBJECT-TYPE
        SYNTAX          INTEGER(0..86400)
        ACCESS          read-write
        STATUS          mandatory
        DESCRIPTION
        "XDSL TCA threshold for Errored Seconds at the near end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA

         FGU4.4: THIS OBJECT IS NOT SUPPORTED        "
::= { gxdslLineTcaThresholdEntry  5 }

gxdslLine1DaySESsTcaThreshold           OBJECT-TYPE
        SYNTAX          INTEGER(0..86400)
        ACCESS          read-write
        STATUS          mandatory
        DESCRIPTION
        "XDSL TCA threshold for Severely Errored Seconds at the near end.
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA
        
         FGU4.4: THIS OBJECT IS NOT SUPPORTED "
::= { gxdslLineTcaThresholdEntry  6 }

gxdslLine1DayUASsTcaThreshold           OBJECT-TYPE
        SYNTAX          INTEGER(0..86400)
        ACCESS          read-write
        STATUS          mandatory
        DESCRIPTION
        "XDSL TCA threshold for Unavailable Seconds at the near end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA
        
        
         FGU4.4: THIS OBJECT IS NOT SUPPORTED "
::= { gxdslLineTcaThresholdEntry  7 }

gxdslFarEndLineIntervalESsTcaThreshold  OBJECT-TYPE
        SYNTAX          INTEGER(0..900)
        ACCESS          read-write
        STATUS          mandatory
        DESCRIPTION
        "XDSL TCA threshold for Errored Seconds at the far end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA
        "
::= { gxdslLineTcaThresholdEntry  8 }

gxdslFarEndLineIntervalSESsTcaThreshold OBJECT-TYPE
        SYNTAX          INTEGER(0..900)
        ACCESS          read-write
        STATUS          mandatory
        DESCRIPTION
        "XDSL TCA threshold for Severely Errored Seconds at the far end.
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA
        "
::= { gxdslLineTcaThresholdEntry  9 }

gxdslFarEndLineIntervalUASsTcaThreshold OBJECT-TYPE
        SYNTAX          INTEGER(0..900)
        ACCESS          read-write
        STATUS          mandatory
        DESCRIPTION
        "XDSL TCA threshold for Unavailable Seconds at the far end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA
        "
::= { gxdslLineTcaThresholdEntry  10 }

gxdslFarEndLine1DayESsTcaThreshold      OBJECT-TYPE
        SYNTAX          INTEGER(0..86400)
        ACCESS          read-write
        STATUS          mandatory
        DESCRIPTION
        "XDSL TCA threshold for Errored Seconds at the far end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA
        
        
         FGU4.4: THIS OBJECT IS NOT SUPPORTED "
::= { gxdslLineTcaThresholdEntry  11 }

gxdslFarEndLine1DaySESsTcaThreshold     OBJECT-TYPE
        SYNTAX          INTEGER(0..86400)
        ACCESS          read-write
        STATUS          mandatory
        DESCRIPTION
        "XDSL TCA threshold for Severely Errored Seconds at the far end.
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA
        
        
         FGU4.4: THIS OBJECT IS NOT SUPPORTED "
::= { gxdslLineTcaThresholdEntry  12 }

gxdslFarEndLine1DayUASsTcaThreshold OBJECT-TYPE
        SYNTAX          INTEGER(0..86400)
        ACCESS          read-write
        STATUS          mandatory
        DESCRIPTION
        "XDSL TCA threshold for Unavailable Seconds at the far end. 
         A value of zero means that the threshold is disabled.

         ALCATEL NOTE:
             ACCESS:   NA                  USAGE:    OPT
             PERSIST:  YES                 INSRVMOD: YES
             RANGE:    NA                  DEFVALUE: 0
             UNITS:    NA                  SPARSE:   NA
             DESCR:    NA
        
        
         FGU4.4: THIS OBJECT IS NOT SUPPORTED "
::= { gxdslLineTcaThresholdEntry  13 }


tcaThresholdSpIndex  OBJECT-TYPE
	SYNTAX 	SpIndex
	ACCESS	not-accessible
	STATUS	mandatory
	DESCRIPTION 
		"Each row is also indexed by a number that
		 contains the slot number and port number
		 within the ONT. 
           
             ALCATEL NOTE: THIS OBJECT IS ADDED TO THE xDSL MIB DUE TO THE 
                           DOUBLE INDEXING SCHEME THAT DOES NOT ALLOW THE USE 
                           OF STANDARD IF-TABLES TO FULL EXTENT "
	::= { gxdslLineTcaThresholdEntry  14 }


--
-- xdslLinkUpTable         OBJECT-TYPE
--         SYNTAX          SEQUENCE OF XdslLinkUpEntry
--         ACCESS          not-accessible
--         STATUS          mandatory
--         DESCRIPTION
--         "The xDSL Link Up record table contains for each line the latest
--          link-up timestamp and the latest link-down timestamp along with other
--          operational and configuration parameters.
-- 
--          ALCATEL NOTE:
--              TABLESIZE: DEP [number of XDSL lines]                    
--              DESCR:     NA                  
--          
--         
--          FGU4.4:  THIS TABLE IS NOT SUPPORTED "
-- ::= { gxdslLinkUp  1 }
-- 
-- xdslLinkUpEntry         OBJECT-TYPE
--         SYNTAX          XdslLinkUpEntry
--         ACCESS          not-accessible
--         STATUS          mandatory
--         DESCRIPTION
--         "An entry in the xDSL Link Up table.
-- 
--          Row creation : Entries for all XDSL kines belonging to a board are 
--                         created when the board becomes operational.
--          Row deletion : Entries for all XDSL lines belonging to a board are 
--                         deleted when the board becomes unavailable.
--         "
--         INDEX          {ifIndex }
-- ::= { xdslLinkUpTable  1 }
-- 
-- XdslLinkUpEntry ::=
--         SEQUENCE {
--             xdslLinkUpTimestampDown                   Gauge,
--             xdslLinkUpTimestampUp                     Gauge,
--             xdslLinkUpActualBitrateUpstream           INTEGER,
--             xdslLinkUpActualBitrateDownstream         INTEGER,
--             xdslLinkUpActualNoiseMarginUpstream       INTEGER,
--             xdslLinkUpActualNoiseMarginDownstream     INTEGER,
--             xdslLinkUpAttenuationUpstream             INTEGER,
--             xdslLinkUpAttenuationDownstream           INTEGER,
--             xdslLinkUpAttainableBitrateUpstream       INTEGER,
--             xdslLinkUpAttainableBitrateDownstream     INTEGER,
--             xdslLinkUpMaxBitrateUpstream              INTEGER,
--             xdslLinkUpMaxBitrateDownstream            INTEGER,
--             xdslLinkUpThresholdBitrateUpstream        INTEGER,
--             xdslLinkUpThresholdBitrateDownstream      INTEGER,
--             xdslLinkUpMaxDelayUpstream                INTEGER,
--             xdslLinkUpMaxDelayDownstream              INTEGER,
--             xdslLinkUpTargetNoiseMarginUpstream       INTEGER,
--             xdslLinkUpTargetNoiseMarginDownstream     INTEGER
--         }
-- 
-- xdslLinkUpTimestampDown OBJECT-TYPE
--         SYNTAX          Gauge 
--         ACCESS          read-only
--         STATUS          mandatory
--         DESCRIPTION
--         "This object contains the latest link down timestamp. It gives the
--          network time in seconds (start counting since January 1, 1900) when
--          the line went latest out of service.
-- 
--          ALCATEL NOTE:
--              ACCESS:   NA                  USAGE:    NA
--              PERSIST:  NO                  INSRVMOD: NA
--              RANGE:    NA                  DEFVALUE: 0
--              UNITS:    seconds             SPARSE:   NA
--              DESCR:    NA
--         "
-- ::= { xdslLinkUpEntry 1 }
-- 
-- xdslLinkUpTimestampUp   OBJECT-TYPE
--         SYNTAX          Gauge 
--         ACCESS          read-only
--         STATUS          mandatory
--         DESCRIPTION
--         "This object contains the latest link up timestamp. It gives the 
--          network time in seconds (start counting since January 1, 1900) when 
--          the line came latest in showtime and remained in showtime for at least
--          10 seconds (recorded time is time of entering showtime + 10 seconds).
--         
--          ALCATEL NOTE:
--              ACCESS:   NA                  USAGE:    NA
--              PERSIST:  NO                  INSRVMOD: NA
--              RANGE:    NA                  DEFVALUE: 0
--              UNITS:    seconds             SPARSE:   NA
--              DESCR:    NA
--         "
-- ::= { xdslLinkUpEntry 2 }
-- 
-- xdslLinkUpActualBitrateUpstream        OBJECT-TYPE
--         SYNTAX          INTEGER 
--         ACCESS          read-only
--         STATUS          mandatory
--         DESCRIPTION
--         "This object gives the actual net data rate for the upstream channel
--          data flow. 
--          The data is retrieved when the lines come in showtime and remains in 
--          showtime for at least 10 seconds. 
--          A value 0 means that no data is available.
-- 
 --         ALCATEL NOTE:
--             ACCESS:   NA                  USAGE:    NA
--             PERSIST:  NO                  INSRVMOD: NA
--             RANGE:    0..262143           DEFVALUE: 0
--             UNITS:    kbits/sec           SPARSE:   NA
--             DESCR:    NA
--        "
-- ::= { xdslLinkUpEntry 3 }
-- 
-- xdslLinkUpActualBitrateDownstream      OBJECT-TYPE
--         SYNTAX          INTEGER 
--         ACCESS          read-only
--         STATUS          mandatory
--         DESCRIPTION
--         "This object gives the actual net data for the downstream channel data
--          flow. 
--          The data is retrieved when the line comes in showtime and remains in 
--          showtime for at least 10 seconds. 
--          A value 0 means that no data is available.
-- 
--          ALCATEL NOTE:
--              ACCESS:   NA                  USAGE:    NA
--              PERSIST:  NO                  INSRVMOD: NA
--              RANGE:    0..262143           DEFVALUE: 0
--              UNITS:    kbits/sec           SPARSE:   NA
--              DESCR:    NA
--         "
-- ::= { xdslLinkUpEntry 4 }
-- 
-- xdslLinkUpActualNoiseMarginUpstream    OBJECT-TYPE
--        SYNTAX          INTEGER 
--         ACCESS          read-only
--         STATUS          mandatory
--         DESCRIPTION
--         "This object gives the realised noise margin for the upstream 
--          direction.
--          The data is retrieved when the line comes in showtime and remains in 
--          showtime for at least 10 seconds. 
--          It is represented as 1/10 * xdslLinkUpActualNoiseMarginUpstream, with
--          a range of (-64 .. 63 dB).
--          A value 0 means that no data is available.
-- 
--          ALCATEL NOTE:
--              ACCESS:   NA                  USAGE:    NA
--              PERSIST:  NO                  INSRVMOD: NA
--              RANGE:    -640..630           DEFVALUE: 0
--              UNITS:    dB / 10             SPARSE:   NA
--              DESCR:    NA
--         "
-- ::= { xdslLinkUpEntry 5 }
-- 
-- xdslLinkUpActualNoiseMarginDownstream  OBJECT-TYPE
--         SYNTAX          INTEGER 
--         ACCESS          read-only
--         STATUS          mandatory
--         DESCRIPTION
--         "This object gives the realised noise margin for the downstream 
--          direction.
--          The data is retrieved when the line comes in showtime and remains in 
--          showtime for at least 10 seconds. 
--          It is represented as 1/10 * xdslLinkUpActualNoiseMarginDownstream, 
--          with a range of (-64 .. 63 dB).
--          A value 0 means that no data is available.
-- 
--          ALCATEL NOTE:
--              ACCESS:   NA                  USAGE:    NA
--              PERSIST:  NO                  INSRVMOD: NA
--              RANGE:    -640..630           DEFVALUE: 0
--              UNITS:    dB / 10             SPARSE:   NA
--              DESCR:    NA
--         "
-- ::= { xdslLinkUpEntry 6 }
-- 
-- xdslLinkUpAttenuationUpstream          OBJECT-TYPE
--         SYNTAX          INTEGER 
--         ACCESS          read-only
--         STATUS          mandatory
--         DESCRIPTION
--         "This object gives the measured difference in dB between the power
--          received by the near-end receiver and the signal power transmitted by  
--          the far-end transmitter. Only power over those tones carrying data is 
--          taken into account.
--          It corresponds with xdslLineSignalAttenuationUpstream in the 
--          xdslLineOperDataTable.
--          It is represented as 1/10 * xdslLinkUpAttenuationUpstream, with a 
--          range of (0 .. 127 dB).
--          The data is retrieved when the line comes in showtime and remains in 
--          showtime for at least 10 seconds. 
--          A value 0 means that no data is available.
-- 
--          ALCATEL NOTE:
--              ACCESS:   NA                  USAGE:    NA
--              PERSIST:  NO                  INSRVMOD: NA
--              RANGE:    0..1270             DEFVALUE: 0
--              UNITS:    dB / 10             SPARSE:   NA
--              DESCR:    NA
--         "
-- ::= { xdslLinkUpEntry 7 }
-- 
-- xdslLinkUpAttenuationDownstream        OBJECT-TYPE
--         SYNTAX          INTEGER 
--         ACCESS          read-only
--         STATUS          mandatory
--         DESCRIPTION
--         "This object gives the measured difference in dB between the power
--          received by the far-end receiver and the signal power transmitted by  
--          the near-end transmitter. Only power over those tones carrying data is 
--          taken into account.
--          It corresponds with xdslFarEndLineSignalAttenuationDownstream in the 
--          xdslFarEndLineOperDataTable.
--          It is represented as 1/10 * xdslLinkUpAttenuationDownstream, with a 
--          range of (0 .. 127 dB).
--          The data is retrieved when the line comes in showtime and remains in 
--          showtime for at least 10 seconds. 
--          A value 0 means that no data is available.
-- 
--          ALCATEL NOTE:
--              ACCESS:   NA                  USAGE:    NA
--              PERSIST:  NO                  INSRVMOD: NA
--              RANGE:    0..1270             DEFVALUE: 0
--              UNITS:    dB / 10             SPARSE:   NA
--              DESCR:    NA
--         "
-- ::= { xdslLinkUpEntry 8 }
-- 
-- xdslLinkUpAttainableBitrateUpstream    OBJECT-TYPE
--         SYNTAX          INTEGER 
--         ACCESS          read-only
--         STATUS          mandatory
--         DESCRIPTION
--         "This object contains the maximum attainable net data rate the modem 
--          can support on the corresponding channel in the upstream direction.
--          The data is retrieved when the line comes in showtime and remains in 
--          showtime for at least 10 seconds. 
--          A value 0 means that no data is available.
-- 
--          ALCATEL NOTE:
--              ACCESS:   NA                  USAGE:    NA
--              PERSIST:  NO                  INSRVMOD: NA
--              RANGE:    0..262143           DEFVALUE: 0
--              UNITS:    kbits/sec           SPARSE:   NA
--              DESCR:    NA
--         "
-- ::= { xdslLinkUpEntry 9 }
-- 
-- xdslLinkUpAttainableBitrateDownstream  OBJECT-TYPE
--         SYNTAX          INTEGER 
--         ACCESS          read-only
--         STATUS          mandatory
--         DESCRIPTION
--         "This object contains the maximum attainable net data rate the modem 
--          can support on the corresponding channel in the downstream direction. 
--          The data is retrieved when the line comes in showtime and remains in 
--          showtime for at least 10 seconds. 
--          A value 0 means that no data is available.
-- 
--          ALCATEL NOTE:
--              ACCESS:   NA                  USAGE:    NA
--              PERSIST:  NO                  INSRVMOD: NA
--              RANGE:    0..262143           DEFVALUE: 0
--              UNITS:    kbits/sec           SPARSE:   NA
--              DESCR:    NA
--         "
-- ::= { xdslLinkUpEntry 10 }
-- 
-- xdslLinkUpMaxBitrateUpstream           OBJECT-TYPE
--         SYNTAX          INTEGER 
--         ACCESS          read-only
--         STATUS          mandatory
--         DESCRIPTION
--         "This object contains the configured maximum bitrate for the upstream 
--          data flow. 
--          It corresponds with the data configured in xdslMaxBitrateUpstream of 
--          the xdslLineServiceProfileTable in the XDSL-MIB.
--          A value 0 means that no data is available. 
-- 
--          ALCATEL NOTE:
--              ACCESS:   NA                  USAGE:    NA
--              PERSIST:  NO                  INSRVMOD: NA
--              RANGE:    0..262143           DEFVALUE: 0
--              UNITS:    kbits/sec           SPARSE:   NA
--              DESCR:    NA
--         "
-- ::= { xdslLinkUpEntry 11 }
-- 
-- xdslLinkUpMaxBitrateDownstream         OBJECT-TYPE
--         SYNTAX          INTEGER 
--         ACCESS          read-only
--         STATUS          mandatory
--         DESCRIPTION
--         "This object contains the configured maximum bitrate for the downstream
--          data flow. 
--          It corresponds with the data configured in xdslMaxBitrateDownstream of
--          the xdslLineServiceProfileTable in the XDSL-MIB.
--          A value 0 means that no data is available.
 -- 
 --         ALCATEL NOTE:
 --             ACCESS:   NA                  USAGE:    NA
 --             PERSIST:  NO                  INSRVMOD: NA
 --             RANGE:    0..262143           DEFVALUE: 0
 --             UNITS:    kbits/sec           SPARSE:   NA
 --             DESCR:    NA
 --        "
-- ::= { xdslLinkUpEntry 12 }
-- 
-- xdslLinkUpThresholdBitrateUpstream     OBJECT-TYPE
--         SYNTAX          INTEGER 
--         ACCESS          read-only
--         STATUS          mandatory
--         DESCRIPTION
--         "This object contains the configured threshold bitrate for the upstream 
--          data flow. 
--          When the actual bitrate as recorded in xdslLinkUpActualBitrateUpstream 
--          is lower than this threshold value, a near-end - Bitrate Threshold 
--          Alarm is raised.  
--          It corresponds with the data configured in xdslPlannedBitrateUpstream
--          of the xdslLineServiceProfileTable in the XDSL-MIB.
--          A value 0 means that no data is available.
-- 
--          ALCATEL NOTE:
--              ACCESS:   NA                  USAGE:    NA
--              PERSIST:  NO                  INSRVMOD: NA
--              RANGE:    0..262143           DEFVALUE: 0
--              UNITS:    kbits/sec           SPARSE:   NA
--              DESCR:    NA
--         "
-- ::= { xdslLinkUpEntry 13 }
-- 
-- xdslLinkUpThresholdBitrateDownstream   OBJECT-TYPE
--         SYNTAX          INTEGER 
--         ACCESS          read-only
--         STATUS          mandatory
--         DESCRIPTION
--         "This object contains the configured threshold bitrate for the 
--          downstream data flow. 
--          When the actual bitrate as recorded in 
--          xdslLinkUpActualBitrateDownstream is lower than this threshold value,
--          a far-end - Bitrate Threshold Alarm is raised.  
--          It corresponds with the data configured in 
--          xdslPlannedBitrateDownUpstream of the xdslLineServiceProfileTable in
--          the XDSL_MIB
--          A value 0 means that no data is available.
-- 
--          ALCATEL NOTE:
--              ACCESS:   NA                  USAGE:    NA
--              PERSIST:  NO                  INSRVMOD: NA
--              RANGE:    0..262143           DEFVALUE: 0
--              UNITS:    kbits/sec           SPARSE:   NA
--              DESCR:    NA
--         "
-- ::= { xdslLinkUpEntry 14 }
-- 
-- xdslLinkUpMaxDelayUpstream             OBJECT-TYPE
--         SYNTAX          INTEGER 
--         ACCESS          read-only
--         STATUS          mandatory
--         DESCRIPTION
--         "This object contains the configured maximum interleaving delay for the 
--          upstream data flow. 
--          It corresponds with the data configured in 
--          xdslMaxInterleavingDelayUpstream of the 
--          adslLineServiceProfileChannelTable in the XDSL-MIB.
--          A value 0 means that no data is available.
-- 
--          ALCATEL NOTE:
--              ACCESS:   NA                  USAGE:    NA
--              PERSIST:  NO                  INSRVMOD: NA
--              RANGE:    0..63               DEFVALUE: 0
--              UNITS:    milliseconds        SPARSE:   NA
--              DESCR:    NA
--         "
-- ::= { xdslLinkUpEntry 15 }
-- 
-- xdslLinkUpMaxDelayDownstream           OBJECT-TYPE
--         SYNTAX          INTEGER 
--         ACCESS          read-only
--         STATUS          mandatory
--         DESCRIPTION
--         "This object contains the configured maximum interleaving delay for the 
--          downstream data flow. 
--          It corresponds with the data configured in 
--          xdslMaxInterleavingDelayDownstream of the 
--          xdslLineServiceProfileChannelTable in the XDSL-MIB.
--          A value 0 means that no data is available.
-- 
--          ALCATEL NOTE:
--              ACCESS:   NA                  USAGE:    NA
--              PERSIST:  NO                  INSRVMOD: NA
--              RANGE:    0..63               DEFVALUE: 0
--              UNITS:    milliseconds        SPARSE:   NA
--              DESCR:    NA
--         "
-- ::= { xdslLinkUpEntry 16 }
-- 
-- xdslLinkUpTargetNoiseMarginUpstream    OBJECT-TYPE
--         SYNTAX          INTEGER 
--         ACCESS          read-only
--         STATUS          mandatory
--         DESCRIPTION
--         "This object contains the configured target noise margin for the 
--          upstream data flow. 
--          It corresponds with the data configured in 
--          xdslLineTargetNoiseMarginUpstream of the xdslLineSpectrumProfileTable
--          in the XDSL-MIB.
--          It is represented as 1/10 * xdslLinkUpTargetNoiseMarginUpstream, with
--          a range of (0..31 dB).
--          A value 0 means that no data is available.
-- 
--          ALCATEL NOTE:
--              ACCESS:   NA                  USAGE:    NA
--              PERSIST:  NO                  INSRVMOD: NA
--              RANGE:    0..310              DEFVALUE: 0
--              UNITS:    dB / 10             SPARSE:   NA
--              DESCR:    NA
--         "
-- ::= { xdslLinkUpEntry 17 }
-- 
-- xdslLinkUpTargetNoiseMarginDownstream  OBJECT-TYPE
--         SYNTAX          INTEGER 
--         ACCESS          read-only
--         STATUS          mandatory
--         DESCRIPTION
--         "This object contains the configured target noise margin for the 
--          downstream data flow. 
--          It corresponds with the data configured in 
--          xdslLineTargetNoiseMarginDownstream of the 
--          xdslLineSpectrumProfileTable in the XDSL-MIB.
--          It is represented as 1/10 * xdslLinkUpTargetNoiseMarginDownstream,
--          with a range of (0..31 dB).
--          A value 0 means that no data is available.
-- 
--          ALCATEL NOTE:
--              ACCESS:   NA                  USAGE:    NA
--              PERSIST:  NO                  INSRVMOD: NA
--              RANGE:    0..310              DEFVALUE: 0
--              UNITS:    dB / 10             SPARSE:   NA
--              DESCR:    NA
--         "
-- ::= { xdslLinkUpEntry 18 }
-- 
-- xdslLinkUpTimestamp     OBJECT-TYPE
--         SYNTAX          Gauge 
--         ACCESS          read-write
--         STATUS          mandatory
--         DESCRIPTION
--         "This object contains the timestamp set by the manager.
--          The manager sets this timestamp to the time of the previous collection
--          period. 
--          The timestamp is expressed as the number of seconds encountered since
--          January 1, 1900.  
-- 
--          ALCATEL NOTE:
--              ACCESS:   NA                  USAGE:    NA
--              PERSIST:  NO                  INSRVMOD: YES
--              RANGE:    NA                  DEFVALUE: NA
--              UNITS:    seconds             SPARSE:   NA
--              DESCR:    NA
--         "
-- ::= { gxdslLinkUp  2 }
-- 
-- xdslLinkUpLineBitmapTable              OBJECT-TYPE
--         SYNTAX          SEQUENCE OF XdslLinkUpLineBitmapEntry
--         ACCESS          not-accessible
--         STATUS          mandatory
--         DESCRIPTION
--         "The xDSL Link-up Line Bitmap table has an entry for each xDSL board.
--          It gives for each board a bitmap with the lines for which an entry is
--          changed in the xdslLinkUpTable in the time span between the 
--          time provided by the manager (xdslLinkUpTimestamp) and the actual
--          time.
-- 
--          ALCATEL NOTE:
--              TABLESIZE: DEP [number of XDSL boards]                    
--              DESCR:     NA                  
--         
--          FGU4.4:  THIS TABLE IS NOT SUPPORTED "
-- ::= { gxdslLinkUp  3 }
-- 
-- xdslLinkUpLineBitmapEntry              OBJECT-TYPE
--         SYNTAX  XdslLinkUpLineBitmapEntry
--         ACCESS  not-accessible
--         STATUS  mandatory
--         DESCRIPTION
--         "An entry in the xDSL Link-up Line Bitmap table.
-- 
--          Row creation : An entry for a board is created when the board becomes
--                         operational.
--          Row deletion : The entry for a board is deleted when the board becomes
--                         unavailable.
--         "
--         INDEX          {eqptSlotId}
-- ::= { xdslLinkUpLineBitmapTable  1 }
-- 
-- XdslLinkUpLineBitmapEntry ::=
--         SEQUENCE {   
--             xdslLinkUpLineBitmap                 OCTET STRING
--         }
-- 
-- xdslLinkUpLineBitmap OBJECT-TYPE
--         SYNTAX          OCTET STRING  
--         ACCESS          read-only
--         STATUS          mandatory
--         DESCRIPTION
--         "Bitmap whereby each bit represents a line on an xDSL board.
 -- 
 --         A bit is set for a line, when the timestamp provided by the manager 
 --         (xdslLinkUpTimestamp) is lower (earlier in time) than the link up or 
 --         link down timestamp recorded in xdslLinkUpTimestampUp or
 --         xdslLinkUpTimestampDown of the xdslLinkUpTable for that line.
 -- 
 --         The lines are identified in the bitmap as follows :   
 --                      MSB                         LSB
 --           octet  1 :   8   7   6   5   4   3   2   1
 --           octet  2 :  16  15  14  13  12  11   10  9
 --           octet  3 :  24  ..  ..          
 --           ...
 --           octet  6 :  48  47  46  45  44  43  42  41 
-- 
--          ALCATEL NOTE:
--              ACCESS:   NA                  USAGE:    NA
--              PERSIST:  NO                  INSRVMOD: NA
--              RANGE:    6                   DEFVALUE: NA
--              UNITS:    octets              SPARSE:   NA
--              DESCR:    NA
--         "
-- ::= { xdslLinkUpLineBitmapEntry  1 }


-- gxdslDpboProfile Group

gxdslDpboProfileIndexNext       OBJECT-TYPE
        SYNTAX          AsamNextProfileIndex
        ACCESS          read-only
        STATUS          mandatory
        DESCRIPTION     
        "This object contains an appropriate value to be used for 
         gxdslDpboProfileIndex when creating entries in the
         gxdslDpboProfileTable. 
         The value 0 indicates that no unassigned entries are available. To 
         obtain the gxdslDpboProfileIndex value for a new entry, the
         manager issues a management protocol retrieval operation to obtain the
         current value of this object.  After each retrieval, the agent should
         modify the value to the next unassigned index.

         ALCATEL NOTE:
             ACCESS:   NA                  USAGE:    NA
             PERSIST:  NO                  INSRVMOD: NA
             RANGE:    0..50               DEFVALUE: 1
             UNITS:    NA                  SPARSE:   NA
             DESCR:    NA
        "
        ::= {gxdslDpboProfile 1}

gxdslDpboProfileMaxIndex        OBJECT-TYPE
        SYNTAX          AsamMaxProfileIndex
        ACCESS          read-only
        STATUS          mandatory
        DESCRIPTION
        "This object represents the maximum number of gxdslDpboProfiles
         that can be created. The object gxdslDpboProfileIndexNext will
         have values ranging from 0 to the value represented by this object.

         ALCATEL NOTE:
             ACCESS:   NA                  USAGE:    NA
             PERSIST:  NO                  INSRVMOD: NA
             RANGE:    50..50            	 DEFVALUE: 50
             UNITS:    NA                  SPARSE:   NA
             DESCR:    NA
        "
        ::= {gxdslDpboProfile 2}

gxdslDpboProfileTable           OBJECT-TYPE
        SYNTAX          SEQUENCE OF GxdslDpboProfileEntry
        ACCESS          not-accessible
        STATUS          mandatory
        DESCRIPTION     
        "This table contains the Dpbo related parameters of the ONT XDSL Line 
         configuration. One entry in this table reflects a profile which
         can be used to configure the XDSL Line(s) on the ONT.

         ALCATEL NOTE:
             TABLESIZE: 50                   
             DESCR:     NA                  
        "
        ::= {gxdslDpboProfile 3}

gxdslDpboProfileEntry           OBJECT-TYPE
        SYNTAX          GxdslDpboProfileEntry
        ACCESS          not-accessible
        STATUS          mandatory
        DESCRIPTION     
        "Each entry consists of a list of line related parameters that serve 
         to configure Dpbo. A profile can be created in one step with
         all necessary parameter values and gxdslDpboProfileRowStatus
         set to createAndGo.
         It can also be created in several steps by specifying values of a few
         objects in each step. The gxdslDpboProfileRowStatus is set to
         createAndWait in the first step and to Active in the last step.

         Row creation : An entry is created when the manager requests to create
                        a Dpbo profile.
         Row deletion : An entry is deleted when the manager requests to delete
                        a Dpbo profile.
	"
        INDEX          {gxdslDpboProfileIndex}
        ::= {gxdslDpboProfileTable 1}

GxdslDpboProfileEntry ::=
        SEQUENCE {
            gxdslDpboProfileIndex                AsamProfileIndex,
            gxdslDpboProfileName                 AsamProfileName,
            gxdslDpboProfileVersionNbr           INTEGER,
            gxdslDpboProfileUsedStatus           AsamProfileRefCount,
            gxdslDpboElectricalLength            INTEGER,
            gxdslDpboCableModelParamA            INTEGER,
            gxdslDpboCableModelParamB            INTEGER,
            gxdslDpboCableModelParamC            INTEGER,
            gxdslDpboMinUsableSignalLevel        INTEGER,
            gxdslDpboMinFrequency                INTEGER,
            gxdslDpboMaxFrequency                INTEGER,
            gxdslDpboAssumedExchangePsdMask      GExchangePsdShapeType,
            gxdslDpboCustomPsdMaskDownstream     GDpboCustomPsdShapeType,
            gxdslDpboProfileRowStatus            RowStatus            
        }

gxdslDpboProfileIndex           OBJECT-TYPE
        SYNTAX          AsamProfileIndex
        ACCESS          not-accessible
        STATUS          mandatory
        DESCRIPTION     
        "This object is used to uniquely identify an entry in this table.
         It is used by the ONT XDSL Line configuration table and by the ONT 
         Configuration table to identify a row of the table. The max value of
         this object is limited to gxdslDpboProfileMaxIndex value.

         ALCATEL NOTE:
             ACCESS:   NA                  USAGE:    NA
             PERSIST:  YES                 INSRVMOD: NA
             RANGE:    1..50               DEFVALUE: NA
             UNITS:    NA                  SPARSE:   NA
             DESCR:    NA
        "
        ::= {gxdslDpboProfileEntry 1}

gxdslDpboProfileName            OBJECT-TYPE
        SYNTAX          AsamProfileName
        ACCESS          read-write
        STATUS          mandatory
        DESCRIPTION     
        "A textual name identifying this profile. This name has to be unique.

         ALCATEL NOTE:
             ACCESS:   NA                  USAGE:    MAND
             PERSIST:  YES                 INSRVMOD: YES
             RANGE:    NA                  DEFVALUE: NA
             UNITS:    NA                  SPARSE:   NA
             DESCR:    NA
        "
        ::= {gxdslDpboProfileEntry 2}

gxdslDpboProfileVersionNbr      OBJECT-TYPE
        SYNTAX          INTEGER (1..65535)
        ACCESS          read-write
        STATUS          mandatory
        DESCRIPTION     
        "The manager can associate a version number to the profile. It is set
         to 1 when the profile is first created and will be incremented by the
         manager when the profile is modified.

         ALCATEL NOTE:
             ACCESS:   NA                  USAGE:    OPT
             PERSIST:  YES                 INSRVMOD: YES
             RANGE:    1..65535            DEFVALUE: 1
             UNITS:    NA                  SPARSE:   NA
             DESCR:    NA

        Only allowed value is 1 and cannot be incremented.
        "
        DEFVAL          {1}
        ::= {gxdslDpboProfileEntry 3}

gxdslDpboProfileUsedStatus      OBJECT-TYPE
        SYNTAX          AsamProfileRefCount
        ACCESS          read-only
        STATUS          mandatory
        DESCRIPTION
        "Indicates the number of entities using this profile. If the reference
         count is greater than 0, then this profile is 'in use', and may NOT be
         deleted. If the value is 0, then this profile is 'not in use', and can
         be deleted.

         ALCATEL NOTE:
             ACCESS:   NA                  USAGE:    NA
             PERSIST:  NO                  INSRVMOD: NA
             RANGE:    0..65535            DEFVALUE: 0
             UNITS:    NA                  SPARSE:   NA
             DESCR:    NA
        "
        DEFVAL          {0}
        ::= {gxdslDpboProfileEntry 4}

gxdslDpboElectricalLength       OBJECT-TYPE
        SYNTAX          INTEGER (0..65535)
        ACCESS          read-write   
        STATUS          mandatory
        DESCRIPTION
        "Specifies the electrical length of the loop segment from the exchange
         to the remote flexibility point. If set to 0 dB, all DPBO parameters
         are ignored except gxdslDpboCustomPsdMaskDownstream. This parameter
         matches the DPBOESEL parameter described in ITU-T G.997.1
         Range:  0 to 255.5 dB with 0,1 dB steps. 
         The electrical length is represented as
         1/10 * gxdslDpboElectricalLength.

         ALCATEL NOTE:
             ACCESS:   NA                  USAGE:    OPT
             PERSIST:  YES                 INSRVMOD: YES
             RANGE:    0..2555             DEFVALUE: 0
             UNITS:    dB / 10             SPARSE:   NA
             DESCR:    NA
        "
        DEFVAL          {0}
        ::= {gxdslDpboProfileEntry 5}

gxdslDpboCableModelParamA       OBJECT-TYPE
        SYNTAX          INTEGER
        ACCESS          read-write   
        STATUS          mandatory
        DESCRIPTION
        "Specifies the DPBO Cable Model parameter A. This parameter matches the
         DPBOESCMA parameter described in ITU-T G.997.1
         Range: -1 to 1.5 with 2^-8 steps.
         The cable model parameter A is represented as
         2^-8 * xdslDpboCableModelParamA. 

         ALCATEL NOTE:
             ACCESS:   NA                  USAGE:    OPT
             PERSIST:  YES                 INSRVMOD: YES
             RANGE:    -256..384           DEFVALUE: 0
             UNITS:    1/2^8               SPARSE:   NA
             DESCR:    NA
        "
        DEFVAL          {0}           
        ::= {gxdslDpboProfileEntry 6}

gxdslDpboCableModelParamB       OBJECT-TYPE
        SYNTAX          INTEGER
        ACCESS          read-write   
        STATUS          mandatory
        DESCRIPTION
        "Specifies the DPBO Cable Model parameter B. This parameter matches the
         DPBOESCMB parameter described in ITU-T G.997.1
         Range: -1 to 1.5 with 2^-8 steps.
         The cable model parameter B is represented as
         2^-8 * xdslDpboCableModelParamB. 


         ALCATEL NOTE:
             ACCESS:   NA                  USAGE:    OPT
             PERSIST:  YES                 INSRVMOD: YES
             RANGE:    -256..384           DEFVALUE: 0
             UNITS:    1/2^8               SPARSE:   NA
             DESCR:    NA
        "
        DEFVAL          {0}           
        ::= {gxdslDpboProfileEntry 7}

gxdslDpboCableModelParamC       OBJECT-TYPE
        SYNTAX          INTEGER
        ACCESS          read-write   
        STATUS          mandatory
        DESCRIPTION
        "Specifies the DPBO Cable Model parameter C. This parameter matches the
         DPBOESCMC parameter described in ITU-T G.997.1
         Range: -1 to 1.5 with 2^-8 steps.
         The cable model parameter C is represented as
         2^-8 * xdslDpboCableModelParamC. 


         ALCATEL NOTE:
             ACCESS:   NA                  USAGE:    OPT
             PERSIST:  YES                 INSRVMOD: YES
             RANGE:    -256..384           DEFVALUE: 0
             UNITS:     1/2^8              SPARSE:   NA
             DESCR:    NA
        "
        DEFVAL          {0}           
        ::= {gxdslDpboProfileEntry 8}

gxdslDpboMinUsableSignalLevel       OBJECT-TYPE
        SYNTAX          INTEGER
        ACCESS          read-write   
        STATUS          mandatory
        DESCRIPTION
        "Specifies the DPBO_minimum usable signal level. This parameter is used
         to determine the maximum usable frequency. Above this frequency DPBO
         shaping is not applied anymore. This parameter matches the DPBOMUS
         parameter described in ITU-T G.997.1
         Note: this parameter refers to a mask level.
         Range: -127.5 to 0 dBm/Hz with 0,1 dBm/Hz steps.
         The minimum usable signal is represented as
         1/10 * gxdslDpboMinUsableSignalLevel.

         ALCATEL NOTE:
             ACCESS:   NA                  USAGE:    OPT
             PERSIST:  YES                 INSRVMOD: YES
             RANGE:    -1275..0			 DEFVALUE: NA
             UNITS:    dBm/Hz / 10         SPARSE:   NA
             DESCR:    NA
        "
        DEFVAL          {-1275}
        ::= {gxdslDpboProfileEntry 9}

gxdslDpboMinFrequency       OBJECT-TYPE
        SYNTAX          INTEGER (0..65535)
        ACCESS          read-write   
        STATUS          mandatory
        DESCRIPTION
        "Specifies the frequency range over which DPBO shaping is applied. If
         gxdslDpboMinFrequency is equal to gxdslDpboMaxFrequency all DBPO
         parameters are ignored except  gxdslDpboCustomPsdMaskDownstream. This
         parameter matches the DPBOFMIN parameter described in ITU-T G.997.1
         Limitation: Minimum Frequency <= Maximum Frequency
         Range: 0 to 8832 kHz with 1 kHz steps. 

         ALCATEL NOTE:
             ACCESS:   NA                  USAGE:    OPT
             PERSIST:  YES                 INSRVMOD: YES
             RANGE:    0..8832             DEFVALUE: NA
             UNITS:    kHz                 SPARSE:   NA
             DESCR:    NA
        "
        DEFVAL          {0}           
        ::= {gxdslDpboProfileEntry 10}

gxdslDpboMaxFrequency       OBJECT-TYPE
        SYNTAX          INTEGER (0..65535)
        ACCESS          read-write
        STATUS          mandatory
        DESCRIPTION
        "Specifies the frequency range over which DPBO shaping is applied.If
         gxdslDpboMinFrequency is equal to gxdslDpboMaxFrequency all DBPO
         parameters are ignored except  gxdslDpboCustomPsdMaskDownstream. This
         parameter matches the DPBOFMAX parameter described in ITU-T G.997.1
         Limitation: Minimum Frequency <= Maximum Frequency
         Range: 138 to 30000 kHz with 1 kHz steps.

		ALCATEL NOTE:
             ACCESS:   NA                  USAGE:    OPT
             PERSIST:  YES                 INSRVMOD: YES
             RANGE:    138..30000		     DEFVALUE: NA
             UNITS:    kHz                 SPARSE:   NA
             DESCR:    NA
        "
        DEFVAL          {30000}
        ::= {gxdslDpboProfileEntry 11}

gxdslDpboAssumedExchangePsdMask       OBJECT-TYPE
        SYNTAX          GExchangePsdShapeType
        ACCESS          read-write   
        STATUS          mandatory
        DESCRIPTION
        "Specifies the Assumed Exchange PSD mask to be protected by the DPBO
         shaping mechanism at the remote flexibility point. This parameter
         matches the DPBOEPSD parameter described in ITU-T G.997.1
         A number of 2 to 16 PSD points can be specified.
         The successive PSD points must have increasing (>/=) frequencies.
         It is allowed that for two successive PSD points, different PSD
         levels are defined at a same frequency (brickwall).
         The custom PSD Shape is coded as a variable length octet string
         defined as follows:
         OCTET 0: reserved (set to 0)
         OCTETS 1..2: INTEGER (0..30000), frequency of the first PSD point
         expressed in kHz. The value is defined as MSB-LSB (big-endian).
         OCTETS 3..4: INTEGER (0..950), -10*PSD level (in dBm/Hz) of the
         first PSD point. The value is defined as MSB-LSB (big-endian).

         OCTETS 5..8: define the frequency and PSD level of PSD point 2.
         ...        up to
         OCTETS 4*N-3..4*N: define the frequency and PSD level of the last PSD
         point N with N<=16.

         ALCATEL NOTE:
             ACCESS:   NA                  USAGE:    OPT
             PERSIST:  YES                 INSRVMOD: YES
             RANGE:    0..65               DEFVALUE: NA
             UNITS:    OCTETS              SPARSE:   NA
             DESCR:    NA
        "

        DEFVAL              {'00000003B6000403B60004039D005002D5008A01BA008A016D0450016D065601D108A001DE09C402520BBA03200C3C03B6753003B6'H}
        ::= {gxdslDpboProfileEntry 12} 

gxdslDpboCustomPsdMaskDownstream       OBJECT-TYPE
        SYNTAX          GDpboCustomPsdShapeType
        ACCESS          read-write   
        STATUS          mandatory
        DESCRIPTION
        "Specifies PSD breakpoints of DPBO Mode Independent Custom PSD Mask.
         A number of 2 to 32 PSD breakpoints can be specified. This parameter
         matches the PSDMASKds parameter described in ITU-T G.997.1
         This set of breakpoints may contain two subsets :
         The first sub-set defines the DPBO Custom PSD Mask. It matches the
         DPBOPSDMASKds parameter described in ITU-T G.997.1
         The second sub-set (if any), defines the DPBO Minimum Override Mask.
         It matches the DPBOLFO parameter described in ITU-T G.997.1
         The successive PSD points of each sub-set must have
         increasing (>/=) frequencies.
         It is allowed that for two successive PSD points, different PSD
         levels are defined at a same frequency (brickwall).
         The second sub-set starts at the first breakpoint whose frequency is
         lower than the frequency of the previous breakpoint.
         The DPBO Mode Independent Custom PSD Shape is coded as a variable
         length octet string defined as follows:
         OCTET 0: reserved (set to 0)
         OCTETS 1..2: INTEGER (0..30000), frequency of the first PSD point
         expressed in kHz. The value is defined as MSB-LSB (big-endian).
         OCTETS 3..4: INTEGER (0..950), -10*PSD level (in dBm/Hz) of the first
         PSD point. The value is defined as MSB-LSB (big-endian).
         
         OCTETS 5..8: define the frequency and PSD level of PSD point 2.
         ...        up to
         OCTETS 4*N-3..4*N: define the frequency and PSD level of the last PSD
         point N with N<=32.

         ALCATEL NOTE:
             ACCESS:   NA                  USAGE:    OPT
             PERSIST:  YES                 INSRVMOD: YES
             RANGE:    0..129              DEFVALUE: NA
             UNITS:    OCTETS              SPARSE:   NA
             DESCR:    NA
        "
        DEFVAL              {''H}
        ::= {gxdslDpboProfileEntry 13}

gxdslDpboProfileRowStatus       OBJECT-TYPE
        SYNTAX          RowStatus
        ACCESS          read-write
        STATUS          mandatory
        DESCRIPTION 
        "This object is used to create a new row or delete an existing row in
         this table. The usage is as per standard semantics of 'RowStatus'
         defined in SNMPv2-TC.
            o Both 'createAndGo' and 'createAndWait' options of row creation
              are supported.
            o The entry associated with a Profile that is being used may
              not be deleted.

         ALCATEL NOTE:
             ACCESS:   NA                  USAGE:    MAND
             PERSIST:  YES                 INSRVMOD: YES
             RANGE:    NA                  DEFVALUE: NA
             UNITS:    NA                  SPARSE:   NA
             DESCR:    NA
        "
        ::= {gxdslDpboProfileEntry 14}

gxdslDpboProfileMappingTable    OBJECT-TYPE
        SYNTAX          SEQUENCE OF GxdslDpboProfileMappingEntry
        ACCESS          not-accessible
        STATUS          mandatory
        DESCRIPTION
        "The (conceptual) listing the profile name to profile Index
         Mapping.

         ALCATEL NOTE:
             TABLESIZE: 50                    
             DESCR:     NA                          
        " 
        ::= {gxdslDpboProfile 4}

gxdslDpboProfileMappingEntry    OBJECT-TYPE
      SYNTAX            GxdslDpboProfileMappingEntry
      ACCESS            not-accessible
      STATUS            mandatory
      DESCRIPTION
        "An entry (conceptual row) representing the profile Name to Index
         Mapping.

         Row creation : When an entry is created in the 
                        gxdslDpboProfileTable, an entry is created in
                        this table.
         Row deletion : When an entry is deleted from the
                        gxdslDpboProfileTable, the entry is deleted from
                        this table.
        "
        INDEX            {gxdslDpboProfileMappingName}
        ::= { gxdslDpboProfileMappingTable 1 }

GxdslDpboProfileMappingEntry ::=
        SEQUENCE {
            gxdslDpboProfileMappingName        AsamProfileName,
            gxdslDpboProfileMappingIndex       AsamProfileIndex
        }

gxdslDpboProfileMappingName     OBJECT-TYPE
        SYNTAX          AsamProfileName
        ACCESS          not-accessible
        STATUS          mandatory
        DESCRIPTION
        "The Dpbo profile name.

         ALCATEL NOTE:
             ACCESS:   NA                  USAGE:    NA
             PERSIST:  NO                  INSRVMOD: NA
             RANGE:    NA                  DEFVALUE: NA
             UNITS:    NA                  SPARSE:   NA
             DESCR:    NA
        "
        ::= { gxdslDpboProfileMappingEntry 1 }

gxdslDpboProfileMappingIndex    OBJECT-TYPE
        SYNTAX          AsamProfileIndex
        ACCESS          read-only
        STATUS          mandatory
        DESCRIPTION
        "The Index of the corresponding Dpbo profile.

         ALCATEL NOTE:
             ACCESS:   NA                  USAGE:    NA
             PERSIST:  NO                  INSRVMOD: NA
             RANGE:    1..50               DEFVALUE: NA
             UNITS:    NA                  SPARSE:   NA
             DESCR:    NA
        "
        ::= { gxdslDpboProfileMappingEntry 2 }


-- GPON Ont config table . XDSL configuration at the GPON ONT level


gxdslGponOntConfTable   OBJECT-TYPE
        SYNTAX          SEQUENCE OF GxdslGponOntConfEntry
        ACCESS          not-accessible
        STATUS          mandatory
        DESCRIPTION
        "XDSL configuration at the GPON ont level.

         ALCATEL NOTE:
             TABLESIZE: NA                    
             DESCR:     NA                          
        " 
        ::= {gxdslGponOnt 1}

gxdslGponOntConfEntry   OBJECT-TYPE
      SYNTAX            GxdslGponOntConfEntry   
      ACCESS            not-accessible
      STATUS            mandatory
      DESCRIPTION
        "An entry represents the XDSL configuration associated with a single GPON ONT.

         Row creation : An entry is auto-created when a GPON ONT is provisioned.

         Row deletion : An entry is auto-deleted when a GPON ONT is un.provisioned.
        "
        INDEX            {gxdslGponOntIndex}
        ::= { gxdslGponOntConfTable 1 }

GxdslGponOntConfEntry ::=
        SEQUENCE {
            gxdslGponOntIndex                IfIndex,
            gxdslGponOntDpboProfileNbr       AsamProfilePointer
        }

gxdslGponOntIndex   OBJECT-TYPE
        SYNTAX          IfIndex
        ACCESS          not-accessible
        STATUS          mandatory
        DESCRIPTION
        "Interface Index of the GPON ONT. This is unique and has to conform to the format specified by ITFM, for the ONT level.

         ALCATEL NOTE:
             ACCESS:   NA                  USAGE:    NA
             PERSIST:  YES                 INSRVMOD: NA
             RANGE:    NA                  DEFVALUE: NA
             UNITS:    NA                  SPARSE:   NA
             DESCR:    NA
        "
        ::= { gxdslGponOntConfEntry 1 }

gxdslGponOntDpboProfileNbr       OBJECT-TYPE
        SYNTAX          AsamProfilePointer
        ACCESS          read-write
        STATUS          mandatory
        DESCRIPTION
        "The Index of the corresponding Dpbo profile. This profile will be used for a Line, if the Line level Dpbo profile to use is not specified.

         ALCATEL NOTE:
             ACCESS:   NA                  USAGE:    NA
             PERSIST:  YES                 INSRVMOD: NA
             RANGE:    0..50               DEFVALUE: 0
             UNITS:    NA                  SPARSE:   NA
             DESCR:    NA
        "

     DEFVAL {0}
        ::= { gxdslGponOntConfEntry 2 }

-- gxdslRtxProfile Group

gxdslRtxProfileIndexNext       OBJECT-TYPE
        SYNTAX          AsamNextProfileIndex
        ACCESS          read-only
        STATUS          mandatory
        DESCRIPTION     
        "This object contains an appropriate value to be used for 
         gxdslRtxProfileIndex when creating entries in the gxdslRtxProfileTable. 
         The value 0 indicates that no unassigned entries are available. To 
         obtain the gxdslRtxProfileIndex value for a new entry, the
         manager issues a management protocol retrieval operation to obtain the
         current value of this object.  After each retrieval, the agent should
         modify the value to the next unassigned index.

         ALCATEL NOTE:
             ACCESS:   NA                  USAGE:    NA
             PERSIST:  NO                  INSRVMOD: NA
             RANGE:    0..128              DEFVALUE: 1
             UNITS:    NA                  SPARSE:   NA
             DESCR:    NA

        Introduced in ISAM5.3.01 MIB for MIB readiness
        For GPON - SUPPORTED as of ISAM5.3.02
        For XG-PON1 - NOT SUPPORTED as of ISAM5.3.02
        For NG-PON2 - NOT SUPPORTED as of ISAM5.3.02
        "
::= {gxdslLine 12}					 
					 
gxdslRtxProfileMaxIndex        OBJECT-TYPE
        SYNTAX          AsamMaxProfileIndex
        ACCESS          read-only
        STATUS          mandatory
        DESCRIPTION
        "This object represents the maximum number of gxdslRtxProfiles
         that can be created. The object gxdslRtxProfileIndexNext will 
         have values ranging from 0 to the value represented by this object.

         ALCATEL NOTE:
             ACCESS:   NA                  USAGE:    NA
             PERSIST:  NO                  INSRVMOD: NA
             RANGE:    128..128            DEFVALUE: 128
             UNITS:    NA                  SPARSE:   NA
             DESCR:    NA

        Introduced in ISAM5.3.01 MIB for MIB readiness
        For GPON - SUPPORTED as of ISAM5.3.02
        For XG-PON1 - NOT SUPPORTED as of ISAM5.3.02
        For NG-PON2 - NOT SUPPORTED as of ISAM5.3.02
        "
::= {gxdslLine 13}

gxdslRtxProfileTable           OBJECT-TYPE
        SYNTAX          SEQUENCE OF GxdslRtxProfileEntry
        ACCESS          not-accessible
        STATUS          mandatory
        DESCRIPTION     
        "This table contains the RTX(Retransmission) related parameters of the modem
         configuration. One entry in this table reflects a profile which
         can be used to configure the modem for a physical line.
         The profiles in this table are not applicable for G.Fast.

         ALCATEL NOTE:
             TABLESIZE: 128                   
             DESCR:     NA                  

        Introduced in ISAM5.3.01 MIB for MIB readiness
        For GPON - SUPPORTED as of ISAM5.3.02
        For XG-PON1 - NOT SUPPORTED as of ISAM5.3.02
        For NG-PON2 - NOT SUPPORTED as of ISAM5.3.02
        "
::= {gxdslRtxProfile 3}

gxdslRtxProfileEntry           OBJECT-TYPE
        SYNTAX          GxdslRtxProfileEntry
        ACCESS          not-accessible
        STATUS          mandatory
        DESCRIPTION     
        "Each entry consists of a list of line related parameters that serve 
         to configure RTX(Retransmission). A profile can be created in one step with
         all necessary parameter values and gxdslRtxProfileRowStatus
         set to createAndGo.
         It can also be created in several steps by specifying values of a few
         objects in each step. The gxdslRtxProfileRowStatus is set to
         createAndWait in the first step and to Active in the last step.

         Row creation : An entry is created when the manager requests to create
                        a Rtx profile.
         Row deletion : An entry is deleted when the manager requests to delete
                        a Rtx profile.
        "
        INDEX          {gxdslRtxProfileIndex}
::= {gxdslRtxProfileTable 1}

GxdslRtxProfileEntry ::=
        SEQUENCE {
            gxdslRtxProfileIndex           AsamProfileIndex,
            gxdslRtxProfileName            AsamProfileName,
            gxdslRtxProfileVersionNbr      INTEGER,
            gxdslRtxProfileUsedStatus      AsamProfileRefCount,
            gxdslRtxMode                   GRtxMode,
            gxdslRtxMinExpThrpt            INTEGER,
            gxdslRtxPlanExpThrpt           INTEGER,
            gxdslRtxMaxExpThrpt            INTEGER,
            gxdslRtxMaxNetDataRate         INTEGER,
            gxdslRtxMinDelay               INTEGER,
            gxdslRtxMaxDelay               INTEGER,
            gxdslRtxMinInpShine            INTEGER,
            gxdslRtxMinInpRein             INTEGER,
            gxdslRtxReinInterArrTime       INTEGER,
            gxdslRtxShineRatio             INTEGER,
            gxdslRtxLeftrThreshold         INTEGER,
            gxdslRtxProfileRowStatus       RowStatus
        }

gxdslRtxProfileIndex           OBJECT-TYPE
        SYNTAX          AsamProfileIndex
        ACCESS          not-accessible
        STATUS          mandatory
        DESCRIPTION     
        "This object is used to uniquely identify an entry in this table.
         It is used by the line configuration table to identify a row of 
         the table. The max value of this object is limited to 
         gxdslRtxProfileMaxIndex value.

         ALCATEL NOTE:
             ACCESS:   NA                  USAGE:    NA
             PERSIST:  YES                 INSRVMOD: NO
             RANGE:    1..128              DEFVALUE: NA
             UNITS:    NA                  SPARSE:   NA
             DESCR:    NA
        "
::= {gxdslRtxProfileEntry 1}

gxdslRtxProfileName            OBJECT-TYPE
        SYNTAX          AsamProfileName
        ACCESS          read-write
        STATUS          mandatory
        DESCRIPTION     
        "A textual name identifying this profile. This name has to be unique.

         ALCATEL NOTE:
             ACCESS:   NA                  USAGE:    MAND
             PERSIST:  YES                 INSRVMOD: NO
             RANGE:    NA                  DEFVALUE: NA
             UNITS:    NA                  SPARSE:   NA
             DESCR:    NA
        "
::= {gxdslRtxProfileEntry 2}

gxdslRtxProfileVersionNbr      OBJECT-TYPE
        SYNTAX          INTEGER
        ACCESS          read-write
        STATUS          mandatory
        DESCRIPTION     
        "The manager can associate a version number to the profile. It is set
         to 1 when the profile is first created and will be incremented by the
         manager when the profile is modified.

         ALCATEL NOTE:
             ACCESS:   NA                  USAGE:    OPT
             PERSIST:  YES                 INSRVMOD: NO
             RANGE:    NA                  DEFVALUE: NA
             UNITS:    NA                  SPARSE:   NA
             DESCR:    NA
        "
        DEFVAL          {1}
::= {gxdslRtxProfileEntry 3}

gxdslRtxProfileUsedStatus      OBJECT-TYPE
        SYNTAX          AsamProfileRefCount
        ACCESS          read-only
        STATUS          mandatory
        DESCRIPTION
        "Indicates the number of entities using this profile. If the reference
         count is greater than 0, then this profile is 'in use', and may NOT be
         deleted. If the value is 0, then this profile is 'not in use', and can
         be deleted.

         ALCATEL NOTE:
             ACCESS:   NA                  USAGE:    NA
             PERSIST:  NO                  INSRVMOD: NO
             RANGE:    NA                  DEFVALUE: 0
             UNITS:    NA                  SPARSE:   NA
             DESCR:    NA
        "
::= {gxdslRtxProfileEntry 4}

gxdslRtxMode OBJECT-TYPE
        SYNTAX      GRtxMode 
        ACCESS      read-write
        STATUS      mandatory
        DESCRIPTION
        "This parameter allows the manager to enable the RTX(Retransmission)
	 feature on lines (only VDSL2) supporting RTX.  As long as the feature 
	 has not been enabled, the other RTX parameters will have no effect on this line.

         ALCATEL NOTE:
             ACCESS:   NA                  USAGE:    NA
             PERSIST:  YES                 INSRVMOD: NO
             RANGE:    1,2,3,4             DEFVALUE: rtxPreferred
             UNITS:    NA                  SPARSE:   NA
             DESCR:    NA
         "
::= { gxdslRtxProfileEntry 5}

gxdslRtxMinExpThrpt OBJECT-TYPE
        SYNTAX      INTEGER 
        ACCESS      read-write
        STATUS      mandatory
        DESCRIPTION
        "This object contains the minimum expected throughput (bitrate)
         when gxdslRtxMode is different from rtxForbidden.

         ALCATEL NOTE:
             ACCESS:   NA                  USAGE:    NA
             PERSIST:  YES                 INSRVMOD: NO
             RANGE:    0..2147483647       DEFVALUE: 64
             UNITS:    kbits/sec           SPARSE:   NA
             DESCR:    NA
         "
::= { gxdslRtxProfileEntry 6}

gxdslRtxPlanExpThrpt OBJECT-TYPE
        SYNTAX      INTEGER 
        ACCESS      read-write
        STATUS      mandatory
        DESCRIPTION
        "This object contains the planned expected throughput (bitrate)
         when gxdslRtxMode is different from rtxForbidden.

         ALCATEL NOTE:
             ACCESS:   NA                  USAGE:    NA
             PERSIST:  YES                 INSRVMOD: NO
             RANGE:    0..2147483647       DEFVALUE: 128
             UNITS:    kbits/sec           SPARSE:   NA
             DESCR:    NA

        Introduced in ISAM5.3.01 MIB for MIB readiness
        For GPON – NOT SUPPORTED as of ISAM5.3.02
        For XG-PON1 - NOT SUPPORTED as of ISAM5.3.02
        For NG-PON2 - NOT SUPPORTED as of ISAM5.3.02
        "
::= { gxdslRtxProfileEntry 7}

gxdslRtxMaxExpThrpt OBJECT-TYPE
        SYNTAX      INTEGER 
        ACCESS      read-write
        STATUS      mandatory
        DESCRIPTION
        "This object contains the maximum expected throughput (bitrate)
         when gxdslRtxMode is different from rtxForbidden.

         ALCATEL NOTE:
             ACCESS:   NA                  USAGE:    NA
             PERSIST:  YES                 INSRVMOD: NO
             RANGE:    0..2147483647       DEFVALUE: 262143
             UNITS:    kbits/sec           SPARSE:   NA
             DESCR:    NA
         "
::= { gxdslRtxProfileEntry 8}

gxdslRtxMaxNetDataRate OBJECT-TYPE
        SYNTAX      INTEGER 
        ACCESS      read-write
        STATUS      mandatory
        DESCRIPTION
        "This object contains the maximum net data rate 
	 when gxdslRtxMode is different from rtxForbidden.

         ALCATEL NOTE:
             ACCESS:   NA                  USAGE:    NA
             PERSIST:  YES                 INSRVMOD: NO
             RANGE:    0..2147483647       DEFVALUE: 262143
             UNITS:    kbits/sec           SPARSE:   NA
             DESCR:    NA
         "
::= { gxdslRtxProfileEntry 9}

gxdslRtxMinDelay OBJECT-TYPE
        SYNTAX      INTEGER 
        ACCESS      read-write
        STATUS      mandatory
        DESCRIPTION
        "This object contains the minimum instantaneous delay allowed (only due 
         to the effect of the retransmission) when gxdslRtxMode is different from rtxForbidden.

         ALCATEL NOTE:
             ACCESS:   NA                  USAGE:    NA
             PERSIST:  YES                 INSRVMOD: NO
             RANGE:    0..63               DEFVALUE: 0
             UNITS:    milliseconds        SPARSE:   NA
             DESCR:    NA
         "
::= { gxdslRtxProfileEntry 10}

gxdslRtxMaxDelay OBJECT-TYPE
        SYNTAX      INTEGER 
        ACCESS      read-write
        STATUS      mandatory
        DESCRIPTION
        "This object contains the maximum instantaneous delay allowed (only due 
         to the effect of the retransmission) when gxdslRtxMode is different from rtxForbidden. 
         When RTX is used in upstream or downstream direction, it invalidates the corresponding
	 gxdslMaxInterleavingDelayUpstream or gxdslMaxInterleavingDelayDownstream parameter of the Service profile.

         ALCATEL NOTE:
             ACCESS:   NA                  USAGE:    NA
             PERSIST:  YES                 INSRVMOD: NO
             RANGE:    2..63               DEFVALUE: 12
             UNITS:    milliseconds        SPARSE:   NA
             DESCR:    NA
         "
::= { gxdslRtxProfileEntry 11}

gxdslRtxMinInpShine OBJECT-TYPE
        SYNTAX      INTEGER 
        ACCESS      read-write
        STATUS      mandatory
        DESCRIPTION
        "This object defines the minimum impulse noise protection against 
         SHINE (single high impulse noise event) when gxdslRtxMode is different from rtxForbidden.
         It is expressed in DMT symbols with a subcarrier spacing of 4.3125kHz.

         ALCATEL NOTE:
             ACCESS:   NA                  USAGE:    NA
             PERSIST:  YES                 INSRVMOD: NO
             RANGE:    0..63               DEFVALUE: 8
             UNITS:    symbols             SPARSE:   NA
             DESCR:    NA
         "
::= { gxdslRtxProfileEntry 12}

gxdslRtxMinInpRein OBJECT-TYPE
        SYNTAX      INTEGER 
        ACCESS      read-write
        STATUS      mandatory
        DESCRIPTION
        "This object defines the minimum impulse noise protection against REIN
         (repetitive electrical impulse noise) when gxdslRtxMode is different from rtxForbidden.
         It is expressed in DMT symbols with a subcarrier spacing of 4.3125kHz.

         ALCATEL NOTE:
             ACCESS:   NA                  USAGE:    NA
             PERSIST:  YES                 INSRVMOD: NO
             RANGE:    0..7                DEFVALUE: 0
             UNITS:    symbols             SPARSE:   NA
             DESCR:    NA
         "
::= { gxdslRtxProfileEntry 13}

gxdslRtxReinInterArrTime OBJECT-TYPE
        SYNTAX      INTEGER 
                    {
                      derivedFrom100Hz (1),
                      derivedFrom120Hz (2)
                    }
        ACCESS      read-write
        STATUS      mandatory
        DESCRIPTION
        "This object specifies the inter-arrival time that shall be assumed for 
         REIN (repetitive electrical impulse noise)protection when gxdslRtxMode 
	       is different from rtxForbidden.

         ALCATEL NOTE:
             ACCESS:   NA                  USAGE:    NA
             PERSIST:  YES                 INSRVMOD: NO
             RANGE:    1,2                 DEFVALUE: 1
             UNITS:    NA                  SPARSE:   NA
             DESCR:    NA
         "
::= { gxdslRtxProfileEntry 14}

gxdslRtxShineRatio OBJECT-TYPE
        SYNTAX      INTEGER 
        ACCESS      read-write
        STATUS      mandatory
        DESCRIPTION
        " This object specifies the SHINE ratio when gxdslRtxMode is different from rtxForbidden.
         The value ranges from 0 to 0.100 with increments of 0.001.

         ALCATEL NOTE:
             ACCESS:   NA                  USAGE:    NA
             PERSIST:  YES                 INSRVMOD: NO
             RANGE:    0..100              DEFVALUE: 10
             UNITS:    1/1000              SPARSE:   NA
             DESCR:    NA
         "
::= { gxdslRtxProfileEntry 15}

gxdslRtxLeftrThreshold        OBJECT-TYPE
        SYNTAX          INTEGER
        ACCESS          read-write
        STATUS          mandatory
        DESCRIPTION     
        "This parameter specifies the threshold for declaring a near-end 'leftr' 
         defect when gxdslRtxMode is different from rtxForbidden.
         The value ranges from 0.01 to 0.99 with increments of 0.01.
         The special value 0 means the ETR shall be used as the default threshold
         for declaring a 'leftr' defect.    

         ALCATEL NOTE:
             ACCESS:   NA                  USAGE:    OPT
             PERSIST:  YES                 INSRVMOD: NO
             RANGE:    0..99               DEFVALUE: 0
             UNITS:    1/100               SPARSE:   NA
             DESCR:    NA
        "
::= { gxdslRtxProfileEntry 16}

gxdslRtxProfileRowStatus       OBJECT-TYPE
        SYNTAX          RowStatus
        ACCESS          read-write
        STATUS          mandatory
        DESCRIPTION 
        "This object is used to create a new row or delete an existing row in
         this table. The usage is as per standard semantics of 'RowStatus'
         defined in SNMPv2-TC.
            o Both 'createAndGo' and 'createAndWait' options of row creation
              are supported.
            o The entry associated with a Profile that is being used may
              not be deleted.

         ALCATEL NOTE:
             ACCESS:   NA                  USAGE:    MAND
             PERSIST:  YES                 INSRVMOD: YES
             RANGE:    NA                  DEFVALUE: NA
             UNITS:    NA                  SPARSE:   NA
             DESCR:    NA
        "
::= { gxdslRtxProfileEntry 17}

gxdslRtxProfileMappingTable    OBJECT-TYPE
        SYNTAX          SEQUENCE OF GxdslRtxProfileMappingEntry
        ACCESS          not-accessible
        STATUS          mandatory
        DESCRIPTION
        "The (conceptual) listing the profile name to profile Index
         Mapping.

         ALCATEL NOTE:
             TABLESIZE: 128                    
             DESCR:     NA                          
        " 
        ::= {gxdslRtxProfile 4}

gxdslRtxProfileMappingEntry    OBJECT-TYPE
      SYNTAX            GxdslRtxProfileMappingEntry
      ACCESS            not-accessible
      STATUS            mandatory
      DESCRIPTION
        "An entry (conceptual row) representing the profile Name to Index
         Mapping.

         Row creation : When an entry is created in the 
                        gxdslRtxProfileTable, an entry is created in
                        this table.
         Row deletion : When an entry is deleted from the
                        gxdslRtxProfileTable, the entry is deleted from
                        this table.
        "
        INDEX            {gxdslRtxProfileMappingName}
        ::= { gxdslRtxProfileMappingTable 1 }

GxdslRtxProfileMappingEntry ::=
        SEQUENCE {
            gxdslRtxProfileMappingName        AsamProfileName,
            gxdslRtxProfileMappingIndex       AsamProfileIndex
        }

gxdslRtxProfileMappingName     OBJECT-TYPE
        SYNTAX          AsamProfileName
        ACCESS          not-accessible
        STATUS          mandatory
        DESCRIPTION
        "The RTX(Retransmission) profile name.

         ALCATEL NOTE:
             ACCESS:   NA                  USAGE:    NA
             PERSIST:  NO                  INSRVMOD: NA
             RANGE:    NA                  DEFVALUE: NA
             UNITS:    NA                  SPARSE:   NA
             DESCR:    NA
        "
        ::= { gxdslRtxProfileMappingEntry 1 }

gxdslRtxProfileMappingIndex    OBJECT-TYPE
        SYNTAX          AsamProfileIndex
        ACCESS          read-only
        STATUS          mandatory
        DESCRIPTION
        "The Index of the corresponding RTX(Retransmission) profile.

         ALCATEL NOTE:
             ACCESS:   NA                  USAGE:    NA
             PERSIST:  NO                  INSRVMOD: NA
             RANGE:    1..128              DEFVALUE: NA
             UNITS:    NA                  SPARSE:   NA
             DESCR:    NA
        "
        ::= { gxdslRtxProfileMappingEntry 2 }




END
