ALU-CFM-MIB DEFINITIONS ::= BEGIN

-- CFM Proprietary MIB Table
-- ========================================================================
-- This specification is published by Alcatel-Lucent under Non-Disclosure
-- Agreement(s) (NDA) with specific parties and has to be considered as
-- Confidential Information as defined in such NDA.
-- Alcatel-Lucent reserves the right to revise this document for any reason
-- including but not limited to conformity with standards promulgated by
-- various agencies, utilisation of advances in the state of the technical
-- areas, or the reflection of changes in the design of any equipment,
-- techniques, or procedures described or referred to herein.
-- The product specifications and other technical or performance
-- information contained herein are subject to change without notice.
-- Updates of this document will be issued under the above NDA's.
-- Alcatel-Lucent makes no representation or warranty, expressed or 
-- implied, with respect to the sufficiency, accuracy, or utility of any 
-- information or opinion contained herein. Alcatel-Lucent expressly 
-- advises that any use of for any purpose or reliance upon this technical 
-- reference is at the risk of the user and that Alcatel-Lucent shall not 
-- be liable for any damage or injury incurred by any person arising out of 
-- the sufficiency, accuracy, or utility of any information or opinion 
-- contained herein.
-- This document is not to be construed as a suggestion to any manufacturer
-- to modify or change any of its products, nor does this document
-- represent any commitment by Alcatel-Lucent to sell or purchase any 
-- product. Nothing contained herein shall be construed as conferring by 
-- implication, estoppel, or otherwise any license or right under any 
-- patent, whether or not the use of any information herein necessarily 
-- employs an invention of any existing or later issued patent.
-- Alcatel-Lucent reserves the right not to offer any or all of these 
-- products and to withdraw any or all of them at any future time.
--
-- Copyright (C) 2007 Alcatel-Lucent. All Rights Reserved.
-- ========================================================================
--     REVISION    "20150421"
--     DESCRIPTION
--           Version: 3FE60148EAAA_V5.3
--           Editor: zhenzhow 
--           Changes: 
--           Updated the table extendAluCfmStackTable and the table members:
--				extendAluCfmStackEntry
--			extendAluCfmStackifIndex           
--			extendAluCfmStackEquipment		   
--			extendAluCfmStackVlanIndex        
--			extendAluCfmStackMdLevel          
--			extendAluCfmStackDirection      
--			extendAluCfmStackMdIndex         
--			extendAluCfmStackMaIndex           
--			extendAluCfmStackMepId             
--			extendAluCfmStackMacAddress  
--			Corrected enum values	
--			 AluCfmMepEquipmentType
--	Updated the table extendAluCfmMepTable , add members:
--			extendAluCfmMepAISEnable	
--		      	extendAluCfmMepAISMegLevel
--		      	extendAluCfmMepAISPeriod	
--		      	extendAluCfmMepAISPriority	
--		      	extendAluCfmMepEquipment	
--
-- ========================================================================== 
-- MODULE-IDENTITY
--     LAST-UPDATED "201503180000Z"
--     ORGANIZATION "Alcatel-Lucent"
--     CONTACT-INFO 
--          E-mail: asam.mibsupport@alcatel-lucent.be"
--     DESCRIPTION 
--         "Connectivity Fault Management module for managing IEEE 802.1ag"
-- ==========================================================================    
--     REVISION    "20150318"
--     DESCRIPTION
--           Version: 3FE60148EAAA_V5.2
--           Editor: Arunkumar Nandakumar 
--           Changes: 
--           Updated the description for the object extendAluCfmMaDualTagAware
-- ========================================================================
--   REVISION    "20141127"
--      DESCRIPTION
--           Version: 3FE60148EBAA_V5.2
--           Editor: Sowrirajan Padmanabhan 
--           Changes:
--                   Updates for the following mib readiness RCRs
--                   ALU02020863 & ALU02019863 
--                   For RCR ALU01752271 , added extendAluCfmMaLtmFilter 
--                                         in extendAluCfmMaTable
--                   For RCR ALU01990245 , added extendAluCfmMaDualTagAware
--                                         in extendAluCfmMaTable
--                   For RCR ALU02022535 , in extendAluCfmMepOamCtlTable
--                                         Corrected enum values and default value of 
--                                           extendAluCfmMepOamCtlTransmitLbmTestBitPattern
--                                         Corrected description of 
--                                           extendAluCfmMepOamCtlTransmitLbmTestBitPattern
--                                           extendAluCfmMepOamCtlLbrBitErrorRatio
--                                           extendAluCfmMepOamCtlLbrCrcError
--                                         Added 
--                                           extendAluCfmMepOamCtlLbrBitError
-- ==========================================================================    
--   REVISION    "20140602"
--      DESCRIPTION
--           Version: 3FE60148EBAA_V5.1
--           Editor: PradeepKumar Keshapaga
--           Changes:
--                   Updated the description of extendAluCfmPMProactiveConfigInterval  
--                   Changed the order of following oid's in its corresponding table            
--                        extendAluCfmPMProactiveCurrent15MinPDUDiscarded
--                        extendAluCfmPMProactiveCurrent1DayPDUDiscarded
--                        extendAluCfmPMProactivePrevious15MinPDUDiscarded
--                        extendAluCfmPMProactivePrevious1DayPDUDiscarded
-- ==========================================================================    
-- REVISION    "20140502"
--     DESCRIPTION
--           Version: 3FE60148EAAA_V5.0
--           Editor: Sowrirajan Padmanabhan
--           Changes:
--           Updated the description of extendAluCfmPMProactiveConfigInterval  
--           Changed the description of following oid's in its corresponding table.
--                     extendAluCfmPMProactiveCurrent15MinPDUDiscarded
--                     extendAluCfmPMProactiveCurrent1DayPDUDiscarded
--                     extendAluCfmPMProactivePrevious15MinPDUDiscarded
--                     extendAluCfmPMProactivePrevious1DayPDUDiscarded  
-- ==========================================================================    
-- REVISION    "20140502"
--     DESCRIPTION
--           Version: 3FE60148EAAA_V5.0
--           Editor: Sowrirajan Padmanabhan
--           Changes:
--           Increased the range of extendAluCfmSlmInitiatorOnDemandRemoteMepId by 
--           changing its syntax from 'Dot1agCfmMepId' to 'Dot1agCfmMepIdOrNA'
-- ==========================================================================     
--REVISION    20140403
--	   DESCRIPTION
--           Version: 3FE60148EAAA_V5.1 
--           Editor: Sowrirajan Padmanabhan
--           Changes: 
--	    For RCR ALU01851497
--	    Modified range,description and removed default value for 
--		 extendAluCfmPMProactiveConfigMeasurementInterval.
--		 extendAluCfmPMProactiveConfigDataSize

--          Modified range for 
--		 extendAluCfmPMProactiveConfigInterval

--	    Modified description of 
--               extendAluCfmPmMepLmSingleEndedResponder
--		 extendAluCfmPmMepLmSingleEndedInitiator 
--		 extendAluCfmPMProactiveConfigPriority
--		 extendAluCfmPMProactiveConfigRowStatus
--		 extendAluCfmPMProactiveCurrent15MinUnack 
--		 extendAluCfmPMProactiveCurrent1DayUnack 
--		 extendAluCfmPMProactivePrevious15MinUnack 
--		 extendAluCfmPMProactivePrevious1DayUnack
-- ========================================================================
--     REVISION    "20140310"
--     DESCRIPTION
--           Version: 3FE60148EAAA_V5.0 
--           Editor: Murugan Balraj 
--           Changes: 
--                   Changed the order of following oid's in its corresponding table.   
--                       
-- 		          extendAluCfmPMProactiveCurrent15MinPDUDiscarded
-- 			  extendAluCfmPMProactiveCurrent1DayPDUDiscarded
--  			  extendAluCfmPMProactivePrevious15MinPDUDiscarded
--                        extendAluCfmPMProactivePrevious1DayPDUDiscarded
-- ========================================================================
--     REVISION    "20140227"
--     DESCRIPTION
--           Version: 3FE60148EAAA_V5.0 
--           Editor: Arunkumar Nandakumar
--           Changes: 
--                   Changed the definition of Dot1agCfmMepIdOrNA 
--                       
--                   From Dot1agCfmMepIdOrNA(1..8191 | 65535)
--                   To   Dot1agCfmMepIdOrNA(0..8191 | 65535)
--                   Added 
--                        extendAluCfmPMProactiveCurrent15MinPDUDiscarded
--                        extendAluCfmPMProactiveCurrent1DayPDUDiscarded
--                        extendAluCfmPMProactivePrevious15MinPDUDiscarded
--                        extendAluCfmPMProactivePrevious1DayPDUDiscarded
-- ========================================================================
--     REVISION    "20140206"
--     DESCRIPTION
--           Version: 3FE60148EAAA_V5.0 
--           Editor: Arunkumar Nandakumar
--           Changes: 
--			 Removed the range for the following MIB objects
--				extendAluCfmPMProactiveCurrent15MinTimeElapsed
--				extendAluCfmPMProactiveCurrent15MinTimeMeasured
--				extendAluCfmPMProactiveCurrent1DayTimeElapsed       
--               	        extendAluCfmPMProactiveCurrent1DayTimeMeasured   
--				extendAluCfmPMProactivePrevious15MinTimeMeasured
--				extendAluCfmPMProactivePrevious1DayTimeMeasured
-- ========================================================================
--     REVISION    "20140124"
--     DESCRIPTION
--           Version: 3FE60148EAAA_V5.0 
--           Editor: Sowrirajan Padmanabhan
--           Changes: 
--           Updated the description,range and unit for all objects of type
--              ExtendAluCfmHundrethsOfPercentage
-- ========================================================================
--     REVISION    "20140115"
--     DESCRIPTION
--           Version: 3FE60148EAAA_V5.0 
--           Editor: Sowrirajan Padmanabhan
--           Changes: 
--           Modified the range of
--              ExtendAluCfmHundrethsOfPercentage

--           Added the following objects
--              extendAluCfmPMProactiveCurrent15MinTestId
--              extendAluCfmPMProactiveCurrent1DayTestId
--              extendAluCfmPMProactivePrevious15MinTestId
--              extendAluCfmPMProactivePrevious1DayTestId
-- ========================================================================
--     REVISION    "20140109"
--     DESCRIPTION
--           Version: 3FE60148EAAA_V5.0 
--           Editor: Sowrirajan Padmanabhan
--           Changes: 
--           Added Table size for extendAluCfmPMProactiveConfigTable.
--          
--           Modified the range and description of
--              extendAluCfmPMProactiveConfigSessionIndex

--           Added the following objects
--              extendAluCfmPMProactiveCurrent15MinRemoteMepId
--              extendAluCfmPMProactiveCurrent15MinUnack
--              extendAluCfmPMProactiveCurrent1DayRemoteMepId
--              extendAluCfmPMProactiveCurrent1DayMinUnack
--              extendAluCfmPMProactivePrevious15MinRemoteMepId
--              extendAluCfmPMProactivePrevious15MinUnack
--              extendAluCfmPMProactivePrevious1DayRemoteMepId
--              extendAluCfmPMProactivePrevious1DayUnack
-- ========================================================================
--     REVISION    "20140102"
--     DESCRIPTION
--           Version: 3FE60148EAAA_V5.0 
--           Editor: Sowrirajan Padmanabhan
--           Changes:
--		* Updated description of 
--              extendAluCfmPMProactiveConfigRowStatus
--              extendAluCfmPMProactiveCurrent15MinPDURecv
--	        extendAluCfmPMProactiveCurrent1DayPDURecv
--              extendAluCfmPMProactivePrevious15MinPDURecv
--		extendAluCfmPMProactivePrevious1DayPDURecv
-- ========================================================================
--     REVISION    "20131213"
--     DESCRIPTION
--           Version: 3FE60148EAAA_V5.0 
--           Editor: Sowrirajan Padmanabhan
--           Changes:
--              * Added 4294967295 as a possible value for ExtendAluCfmHundrethsOfPercentage 
--		* Updated description of 
--                      extendAluCfmLmInitiatorOnDemandTestTable
--		        extendAluCfmPMProactiveConfigAdminStatus 
--			extendAluCfmPMProactiveConfigInterval
--		* Updated SYNTAX as Counter for
--			extendAluCfmPMProactiveCurrent15MinPDUSent
--                      extendAluCfmPMProactiveCurrent15MinPDURecv
--			extendAluCfmPMProactiveCurrent1DayPDUSent
--		        extendAluCfmPMProactiveCurrent1DayPDURecv
--			extendAluCfmPMProactivePrevious15MinPDUSent
--                      extendAluCfmPMProactivePrevious15MinPDURecv
--			extendAluCfmPMProactivePrevious1DayPDUSent
--		        extendAluCfmPMProactivePrevious1DayPDURecv
--
-- ========================================================================
--     REVISION    "20131029"
--     DESCRIPTION
--           Version: 3FE60148EAAA_V5.0 
--           Editor: Murugan Balraj 
--           Changes:
--             * Modified OBJECT-TYPE SYNTAX for 
--                extendAluCfmSlmInitiatorOnDemandUnack. 
--                 
-- ========================================================================
--     REVISION    "20131022"
--     DESCRIPTION
--           Version: 3FE60148EAAA_V5.0 
--           Editor: Senthil Kumar Palani
--           Changes:
--             * Modified description for object 
--                extendAluCfmPmMepLmSingleEndedResponder. 
-- ========================================================================
--     REVISION    "20131005"
--     DESCRIPTION
--           Version: 3FE60148EAAA_V5.0
--           Editor:  Sowrirajan P
--           Changes:
--		Added On demand LM table - extendAluCfmLmInitiatorOnDemandTestTable 
-- ========================================================================
-- ========================================================================
--     REVISION    "20130807"
--     DESCRIPTION
--           Version: 3FE60148EAAA_V5.0 
--           Editor: Arunkumar Nandakumar 
--           Changes:
--             * Added new object extendAluCfmPmMepLmSingleEndedInitiator Loss Measurement(R5.0). 
-- ========================================================================
--     REVISION    "20131005"
--     DESCRIPTION
--           Version: 3FE60148EAAA_V5.0
--           Editor:  Iswarya V
--           Changes:
--		Update to On demand SLM table - extendAluCfmSlmInitiatorOnDemandTestTable 
-- ========================================================================
--     REVISION    "20130923"
--     DESCRIPTION
--           Version: 3FE60148EAAA_V5.0 
--           Editor: Senthil Kumar Palani
--           Changes:
--             * Modified description for object
--                 extendAluCfmPmMepLmSingleEndedResponder.
-- ========================================================================
-- ========================================================================
--     REVISION    "20130830"
--     DESCRIPTION
--           Version: 3FE60148EAAA_V5.0
--           Editor: Sowrirajan P
--           Changes: ALU01851488 
--              On demand SLM configuration table updated
--              On Demand Result tale removed
-- ========================================================================

-- ========================================================================
--     REVISION    "20130819"
--     DESCRIPTION
--           Version: 3FE60148EAAA_V5.0
--           Editor: Sowrirajan P
--           Changes: ALU01851488  
--              On demand SLM configuration and result tables
--              Proactive SLM/LM configuration and result tables
-- ========================================================================
--     REVISION    "20130812"
--     DESCRIPTION
--           Version: 3FE60148EAAA_V5.0
--           Editor: Iswarya V
--           Changes: ALU01851488
--              Added new object extendAluCfmPmMepSlmSingleEndedInitiator(R5.0)
-- ========================================================================
--     REVISION    "20130806"
--     DESCRIPTION
--           Version: 3FE60148EAAA_V5.0 
--           Editor: Senthil Kumar Palani
--           Changes:
--             * Added new object extendAluCfmPmMepLmSingleEndedResponder Loss Measurement(R5.0). 
 --======================================================================
--     REVISION    "20130412"
--     DESCRIPTION
--           Version: 3FE60148EAAA_V4.6
--           Editor: Senthil kumar Palani
--           Changes:
--             * Updates for SLM Responder.(R4.6). Modified description
--               of extendAluCfmMaCcmAware and extendAluCfmMaCcmAdminState
--               extendAluCfmPmMepSlmSingleEndedResponder related to license
--               counter.
-- ========================================================================
-- ========================================================================
--     REVISION    "20130213"
--     DESCRIPTION
--           Version: 3FE60148EAAA_V4.6.0.0.0
--           Editor:  Sowrirajan.P
--           Changes:
--             * Updates for Synthetic Loss Measurement(SLM) and 
--               Delay Measurement(DM).
-- ========================================================================
-- ========================================================================
--     REVISION    "20130213"
--     DESCRIPTION
--           Version: 3FE60148EAAA_V4.5.0.0.2
--           Editor: Karthik Chandra Bose S
--           Changes:
--             * Updates for Active CCM.(R4.5.0.2). Modified description
--               of extendAluCfmMaCcmAware related to license counter, 
--               extendAluCfmMaCcmAdminState related to lock scenario 
--               and extendAluCfmMaTable related to table size.
--               
-- ========================================================================
--     REVISION    "20121121"
--     DESCRIPTION
--           Version: 3FE60148EAAA_V4.5.0.0.1 
--           Editor: Karthik Chandra Bose S
--           Changes:
--             * Updates for Active CCM.(R4.5.0.2). Modified descriptions
-- ========================================================================
--     REVISION    "20120829"
--     DESCRIPTION
--           Version: 3FE60148EAAA_V4.5.0.0.0 
--           Editor: Karthik Chandra Bose S
--           Changes:
--             * Support for Active CCM.(R4.5.0.2)
-- ========================================================================
--     REVISION    "20120508"
--     DESCRIPTION
--           Version: 3FE60148EAAA_V4.4.0.2.0 
--           Editor: Sabine Denies
--           Changes:
--             * ALU01788440 (R4.4.02)
--== ========================================================================
--     REVISION    "20111010"
--     DESCRIPTION
--           Version: 3FE60148EAAA_V4.4.0.0.0 
--           Editor: Rommy Volders, Philippe Belet
--           Changes:
--             * Active LBM/LTM from DSL up-MEP.(R4.4)
--
-- ========================================================================
--     REVISION    "20070723"
--     DESCRIPTION
--           Version: 3FE60148EAAA_V4.2.0.0.0 
--           Editor: Gopal Surya
--           Changes:
--             * Introduction of CFM-802.1ag to GPON LTs and ONTs. 
--
-- ========================================================================
--     REVISION    "20070524"
--     DESCRIPTION 
--           Version: 3FE60148EAAA_V3.5.0.0.0
--           Editor: Lucien Marcotte
--           Changes: 
--             * Introduction of extension to CFM-802.1ag.
-- ==================================================================

IMPORTS
      asam
                FROM SYSTEM-MIB 
      InterfaceIndex, InterfaceIndexOrZero
                FROM ITF-MIB 
      RowStatus, TruthValue, MacAddress, TDomain, TAddress
                FROM SNMPv2-TC
      Counter, Gauge                      
                FROM RFC1155-SMI 
      VlanId, VlanIndex --,VlanIdOrNone
                FROM Q-BRIDGE-MIB
      OBJECT-TYPE
                FROM RFC-1212
      dot1agCfmMdIndex, dot1agCfmMaIndex, dot1agCfmMepIdentifier, Dot1agCfmMepId, 
      Dot1agCfmRelayActionFieldValue, Dot1afCfmIndexIntegerNextFree,
      LldpChassisId, LldpPortId,
      Dot1agCfmMDLevel,Dot1agCfmMpDirection,Dot1agCfmMepIdOrZero
                FROM IEEE8021-CFM-MIB; 
            
             
-- ************************************************************************
-- GENERAL NOTES:
-- (1) There are NO traps in this MIB.
--
-- (2) There are NO alarms in this MIB.
-- 
-- ************************************************************************
-- .iso.org.dod.internet.private.enterprises.alcatel.asd.asam.cfmMIB
-- (.1.3.6.1.4.1.637.61.1.76)

extendAluCfmMIB OBJECT IDENTIFIER ::= {asam 76}

AluCfmMaCcmAdminState ::=
    INTEGER { unlock(1), lock(2) }


AluCfmMepEquipmentType ::=
		INTEGER { default(0), olt(1),onu(2)}
		
AluCfmMaMhfLocationType ::=
		INTEGER { default(1), ltuplink(2), vbp(3), onu(4), ltuplink-vbp(5), ltuplink-onu(6), vbp-onu(7), ltuplink-vbp-onu(8)}		
		
-- Based upon LldpChassisIdSubtype definition FROM IEEE8021-CFM-MIB
AluLldpChassisIdSubtype ::=
	INTEGER {notApplicable(0), chassisComponent(1), interfaceAlias(2), portComponent(3),
             macAddress(4), networkAddress(5), interfaceName(6),
             local(7)}

-- Based upon Dot1agCfmIngressActionFieldValue definition FROM IEEE8021-CFM-MIB
AluDot1agCfmIngressActionFieldValue ::=
    INTEGER { ingNoTlv(0), ingOk(1), ingDown(2), ingBlocked(3), ingVid(4) }

-- Based upon LldpPortIdSubtype definition FROM IEEE8021-CFM-MIB
AluLldpPortIdSubtype ::=
	INTEGER {none(0), interfaceAlias(1), portComponent(2), macAddress(3),
             networkAddress(4), interfaceName(5), agentCircuitId(6),
             local(7)}

-- Based upon Dot1agCfmEgressActionFieldValue definition FROM IEEE8021-CFM-MIB
AluDot1agCfmEgressActionFieldValue ::=
    INTEGER { egrNoTlv(0), egrOK(1), egrDown(2), egrBlocked(3), egrVid(4) }


--A value expressed in Hundreths of Percentage defined to two decimal places.
--For eg:where 1 = 0.01 , 2=0.02 ..100=1 10000=100
--If value is 65535, it means that the percentage is invalid (greater than 100 or less than 0)
ExtendAluCfmHundrethsOfPercentage ::=
    INTEGER (0..10000 | 65535)    

--Type of the Y1731 test.
ExtendAluCfmY1731TestType ::=
    INTEGER {
             single-ended-slm (1),
		     single-ended-lm  (2)                    
            }
--A valid mep ID or 65535 if it is not applicable.
-- 0 if Unavailable 
Dot1agCfmMepIdOrNA ::=
    Gauge (0..8191 | 65535)
-- ***********************************************************************
--    Extend CFM MEP Table
-- ***********************************************************************
extendAluCfmMepTable OBJECT-TYPE
        SYNTAX SEQUENCE OF ExtendAluCfmMepEntry
        ACCESS not-accessible
        STATUS mandatory
        DESCRIPTION
                "This table contains the proprietary MEP objects"
        ::= { extendAluCfmMIB 2 }

extendAluCfmMepEntry OBJECT-TYPE
        SYNTAX ExtendAluCfmMepEntry
        ACCESS not-accessible
        STATUS mandatory
        DESCRIPTION "This list contains the proprietary objects for a MEP."
--      AUGMENTS { dot1agCfmMepEntry }
        INDEX { dot1agCfmMdIndex, dot1agCfmMaIndex, dot1agCfmMepIdentifier }
        ::= { extendAluCfmMepTable 1}

ExtendAluCfmMepEntry ::=
        SEQUENCE {
                extendAluCfmMepSvlanId INTEGER,
                extendAluCfmMepPbits INTEGER,
                extendAluCfmMepCvlanId INTEGER,
                extendAluCfmPmMepSlmSingleEndedResponder TruthValue,
                extendAluCfmPmMepDmSingleEndedResponder TruthValue,
	        			extendAluCfmPmMepLmSingleEndedResponder INTEGER,
	        			extendAluCfmPmMepSlmSingleEndedInitiator TruthValue,
	      			  extendAluCfmPmMepLmSingleEndedInitiator INTEGER,
	      			  extendAluCfmMepAISEnable	TruthValue,
	      			  extendAluCfmMepAISMegLevel INTEGER,
	      			  extendAluCfmMepAISPeriod	 INTEGER,
	      			  extendAluCfmMepAISPriority	INTEGER,
	      			  extendAluCfmMepEquipment	AluCfmMepEquipmentType
	      	  
        }

extendAluCfmMepSvlanId OBJECT-TYPE
        SYNTAX INTEGER (0..4095)
        ACCESS read-write
        STATUS mandatory
        DESCRIPTION
                "This is the S-VLAN ID to be used in LBM or LTM packets
                 from the MEP. If the S-VLAN ID is 4095, untagged packets
                 will be transmitted.
         ALCATEL NOTE:
                ACCESS:     NA       USAGE:      NA
                PERSIST:    NA       INSRVMOD:   NA
                RANGE:      NA       DEFVALUE:   NA
                UNITS:      NA       SPARSE:     NA
                DESCR:      This object is not supported by ISAM"
        DEFVAL {4095}
        ::={ extendAluCfmMepEntry 1}

extendAluCfmMepPbits OBJECT-TYPE
        SYNTAX INTEGER (0..7)
        ACCESS read-write
        STATUS mandatory
        DESCRIPTION
                "This is the pbits to be used in S-VLAN and C-VLAN tags.
         ALCATEL NOTE:
                ACCESS:     NA       USAGE:      NA
                PERSIST:    NA       INSRVMOD:   NA
                RANGE:      NA       DEFVALUE:   NA
                UNITS:      NA       SPARSE:     NA
                DESCR:      This object is not supported by ISAM"

        DEFVAL {0}
        ::={ extendAluCfmMepEntry 2}

extendAluCfmMepCvlanId OBJECT-TYPE
        SYNTAX INTEGER (0..4095)
        ACCESS read-write
        STATUS mandatory
        DESCRIPTION
              "This is the C-VLAN ID to be used in LBM or LTM packets from
               the MEP. The p-bits will be the same as in the outer VLAN 
               tag. If the C-VLAN ID is 4095, the inner VLAN tag is not
               transmitted.
         ALCATEL NOTE:
                ACCESS:     NA       USAGE:      NA
                PERSIST:    NA       INSRVMOD:   NA
                RANGE:      NA       DEFVALUE:   NA
                UNITS:      NA       SPARSE:     NA
                DESCR:      This object is not supported by ISAM"
        DEFVAL {4095}
        ::={ extendAluCfmMepEntry 3}

extendAluCfmPmMepSlmSingleEndedResponder OBJECT-TYPE	
    SYNTAX TruthValue
	ACCESS read-write
	STATUS mandatory
	DESCRIPTION
		
         "This object specifies whether the Synthetic Loss Measurement (SLM)
		 single-ended Responder is enabled.

		 The value 'true' indicates the single-ended SLM Responder is enabled and
		 if a SLM message is received a SLR will be sent in reply.
		 The value 'false' indicates the single-ended SLM Responder is disabled.
		 If a SLM message is received no response will be sent and the message
		 will be discarded.

		 A MEP can be both a single-ended Responder and Controller simultaneously.
		 
                 ALCATEL NOTE:
                            ACCESS:     RW       USAGE:      OPT
                            PERSIST:    YES      INSRVMOD:   NA
                            RANGE:      NA       DEFVALUE:   NA
                            UNITS:      NA       SPARSE:     NA
                "
	 DEFVAL { false }
  ::={ extendAluCfmMepEntry 4}

extendAluCfmPmMepDmSingleEndedResponder OBJECT-TYPE
	 SYNTAX TruthValue
	 ACCESS read-write
	 STATUS mandatory
	 DESCRIPTION
		 "This object specifies whether the Delay Measurement (DMM) single
		 ended Responder for a two-way delay measurement is enabled.

		 The value 'true' indicates the single-ended Delay Measurement Responder
		 is enabled and if a DMM message is received a DMR will be sent in reply.

		 The value 'false' indicates the single-ended Delay Measurement Responder
		 is disabled. If a DMM message is received no response will be sent and
		 the message will be discarded.

		 A MEP can be both a single-ended Responder and Controller simultaneously.

 		  ALCATEL NOTE:
                            ACCESS:     RW       USAGE:      OPT
                            PERSIST:    YES      INSRVMOD:   NA
                            RANGE:      NA       DEFVALUE:   NA
                            UNITS:      NA       SPARSE:     NA
                 "
	 DEFVAL { false }
::= { extendAluCfmMepEntry 5 }

extendAluCfmPmMepLmSingleEndedResponder OBJECT-TYPE
         SYNTAX  INTEGER 
    		{
                 disable (0),
                 enablePerVlan (1),
                 enablePerVlanPerPbit (2)
                }
	 ACCESS read-write
	 STATUS mandatory
	 DESCRIPTION
                "This object specifies whether the Loss Measurement single
		 ended Responder for a two-way loss measurement is 
		 enabled per vlan (or) enabled per vlan per priority bit (or)
                 disabled.

		 The value 'disable' indicates the single-ended Loss Measurement Responder
		 is disabled. If a LMM message is received no response will be sent and
		 the message will be discarded.
		 A MEP can be both a single-ended Responder and Initiator 
		 simultaneously.
                 
		 1)This object can be set to either enablePerVlan or 
		    enablePerVlanPerPbit, only when the mep is associated to a
		    cross-connect vlan, which is already created

		 2)This object can be set to either enablePerVlan or
		    enablePerVlanPerPbit, only when the mep is associated to CATAN
		    based LTs

		 3)The limit for the maximum number of MEPs with this object set
		   to either enablePerVlan or enablePerVlanPerPbit in a specified
		   LT is the value of the capability key CFM_MAX_LMRESPONDER_ENABLED_MEPS  
           	   for that LT.

		 4)MEPs in all the domain levels associated to the same vlan in a
		   specified LT, should be set to the same value for this object,
		   when this object is enabled

         	 5) The value of this object and extendAluCfmPmMepLmSingleEndedInitiator 
            	    must be same for all the MEPs in the same vlan.
                 
		 Error mib will be updated with appropriate error codes, when any
		 of the above conditions is not satisfied.

 		 ALCATEL NOTE:
                            ACCESS:     RW       USAGE:      OPT
                            PERSIST:    YES      INSRVMOD:   NA
                            RANGE:      NA       DEFVALUE:   NA 
                            UNITS:      NA       SPARSE:     NA
                 "
	 DEFVAL { disable }
::= { extendAluCfmMepEntry 6 }
extendAluCfmPmMepSlmSingleEndedInitiator OBJECT-TYPE	
    	SYNTAX TruthValue
	ACCESS read-write
	STATUS mandatory
	DESCRIPTION
		
         	"This object specifies whether the Synthetic Loss Measurement (SLM)
		 single-ended Initiator is enabled.

		 The value 'true' indicates that the single-ended SLM Initiator is enabled 
         and an SLM message can be sent from this MEP
		 
         The value 'false' indicates that the single-ended SLM Initiator is 
         disabled and an SLM message cannot be sent from this MEP.
		  
		 A MEP can be both a single-ended initiator and responder simultaneously.
                 ALCATEL NOTE:
                            ACCESS:     RW       USAGE:      OPT
                            PERSIST:    YES      INSRVMOD:   NA
                            RANGE:      NA       DEFVALUE:   NA
                            UNITS:      NA       SPARSE:     NA
                "
	 DEFVAL { false }
  ::={ extendAluCfmMepEntry 7}

extendAluCfmPmMepLmSingleEndedInitiator OBJECT-TYPE
         SYNTAX  INTEGER 
    		{
                 disable (0),
                 enablePerVlan (1),
                 enablePerVlanPerPbit (2)
                }
	 ACCESS read-write
	 STATUS mandatory
	 DESCRIPTION
         "This object specifies whether the Loss Measurement single
		 ended initiator for a two-way loss measurement is 
		 enabled per vlan or per vlan per priority bit or disabled.

		 The value 'disable' indicates the single-ended Loss Measurement Initiator
		 is disabled and an LMM message cannot be sent from this mep.

		 A MEP can be both a single-ended Responder and Initiator 
		 simultaneously.
		 1)This object can be set to either enablePerVlan or 
		    enablePerVlanPerPbit, only when the mep is associated to a
		    cross-connect vlan, which is already created

		 2)This object can be set to either enablePerVlan or
		    enablePerVlanPerPbit, only when the mep is associated to CATAN
		    based  LTs

		 3)The limit for the maximum number of MEPs with this object set
		   to either enablePerVlan or enablePerVlanPerPbit in a specified
		   LT is the value of the capability key CFM_MAX_LMINITIATOR_ENABLED_MEPS  
           	   for that LT

		 4)MEPs in all the domain levels associated to the same vlan in a
		   specified LT, should be set to the same value for this object,
		   when this object is enabled

         	5) The value of this object and extendAluCfmPmMepLmSingleEndedResponder 
                   Must be same for MEPs in the same vlan.
                 
		 Error mib will be updated with appropriate error codes, when any
		 of the above conditions is not satisfied.

 		 ALCATEL NOTE:
                            ACCESS:     RW       USAGE:      OPT
                            PERSIST:    YES      INSRVMOD:   NA
                            RANGE:      NA       DEFVALUE:   NA 
                            UNITS:      NA       SPARSE:     NA
                 "
	 DEFVAL { disable }
::= { extendAluCfmMepEntry 8 }

      	  
	      	  
extendAluCfmMepAISEnable OBJECT-TYPE
   SYNTAX  TruthValue
   ACCESS read-write
	 STATUS mandatory
	 DESCRIPTION
         " This flag is used to enable/disable AIS generation for the ONT UNI MEP, not editable once the MP is created

 					 1 (true)    2(false)  , default is false

 		 ALCATEL NOTE:
                            ACCESS:     RW       USAGE:      OPT
                            PERSIST:    YES      INSRVMOD:   NA
                            RANGE:      NA       DEFVALUE:   false 
                            UNITS:      NA       SPARSE:     NA
                 "
	 DEFVAL { false }
::= { extendAluCfmMepEntry 9 }

extendAluCfmMepAISMegLevel OBJECT-TYPE
   SYNTAX  INTEGER (0..7)
   ACCESS read-write
	 STATUS mandatory
	 DESCRIPTION
         "   MEG level at which the most immediate client layer MIPs and MEPs exist, only valid when AIS is enabled

 		 ALCATEL NOTE:
                            ACCESS:     RW       USAGE:      OPT
                            PERSIST:    YES      INSRVMOD:   NA
                            RANGE:      0..7     DEFVALUE:   0 
                            UNITS:      NA       SPARSE:     NA
    DEFVAL { 0 }              "
::= { extendAluCfmMepEntry 10 }

extendAluCfmMepAISPeriod OBJECT-TYPE
   SYNTAX  INTEGER 	 
   ACCESS read-write
	 STATUS mandatory
	 DESCRIPTION
         "Determines transmission periodicity of frames with ETH?AIS information, only valid when AIS is enabled
        0 (per second) , 1 (per minute)

 		 ALCATEL NOTE:
                            ACCESS:     RW       USAGE:      OPT
                            PERSIST:    YES      INSRVMOD:   NA
                            RANGE:      0..1     DEFVALUE:   0 
                            UNITS:      NA       SPARSE:     NA
              "
  DEFVAL { 0 } 
	::= { extendAluCfmMepEntry 11 }

extendAluCfmMepAISPriority OBJECT-TYPE
   SYNTAX  INTEGER (0..7)
   ACCESS read-write
	 STATUS mandatory
	 DESCRIPTION
         " Identifies the priority of frames with ETH-AIS information, only valid when AIS is enabled

 		 ALCATEL NOTE:
                            ACCESS:     RW       USAGE:      OPT
                            PERSIST:    YES      INSRVMOD:   NA
                            RANGE:      0..7     DEFVALUE:   7 
                            UNITS:      NA       SPARSE:     NA
                 "
  DEFVAL { 7 }
	::= { extendAluCfmMepEntry 12 }

extendAluCfmMepEquipment OBJECT-TYPE
   SYNTAX AluCfmMepEquipmentType
   ACCESS read-write
	 STATUS mandatory
	 DESCRIPTION
         " Identifies the equpment type of mep ;
         	0 is for Gpon onu and Dsl ;
         	1 is for Gpon Lt ;
			2 is for Gpon onu;
         	
 		 ALCATEL NOTE:
                            ACCESS:     RW       USAGE:      OPT
                            PERSIST:    YES      INSRVMOD:   NA
                            RANGE:      NA       DEFVALUE:   NA 
                            UNITS:      NA       SPARSE:     NA
                 "
  DEFVAL { default}
	::= { extendAluCfmMepEntry 13 }

-- ************************************************************************
--     Extend CFM Eqpt Table
-- ************************************************************************

extendAluCfmEqptMepTable OBJECT-TYPE
        SYNTAX SEQUENCE OF ExtendAluCfmEqptMepEntry
        ACCESS not-accessible
        STATUS mandatory
        DESCRIPTION
            "This table contains the proprietary MEP objects for ONT UNIs
         ALCATEL NOTE:
                DESCR:      This table is not supported by ISAM"
        ::= { extendAluCfmMIB 3 }

extendAluCfmEqptMepEntry OBJECT-TYPE
        SYNTAX ExtendAluCfmEqptMepEntry
        ACCESS not-accessible
        STATUS mandatory
        DESCRIPTION 
            "This list contains the MEPIDs and other information for a
             ONT UNI. ONT UNI includes Ethernet, MoCA, VoIP UNIs."

        INDEX { extendAluCfmEqptMepIndex } 
        ::= { extendAluCfmEqptMepTable 1}

ExtendAluCfmEqptMepEntry ::=
        SEQUENCE {
                extendAluCfmEqptMepIndex InterfaceIndex, 
                extendAluCfmEqptMdIndex   Gauge, 
                extendAluCfmEqptMaIndex   Gauge, 
                extendAluCfmEqptMepIdentifier Dot1agCfmMepId, 
                extendAluCfmEqptMepOrMip INTEGER,
                extendAluCfmEqptMacAddress MacAddress,
                extendAluCfmEqptRowStatus RowStatus
}

extendAluCfmEqptMepIndex OBJECT-TYPE
        SYNTAX InterfaceIndex
        ACCESS not-accessible
        STATUS mandatory
        DESCRIPTION
                "This is the interface index of the ONT UNI such as
                 Ethernetport, Moca Port, VoIP client.
         ALCATEL NOTE:
                ACCESS:     NA       USAGE:      NA
                PERSIST:    NA       INSRVMOD:   NA
                RANGE:      NA       DEFVALUE:   NA
                UNITS:      NA       SPARSE:     NA
                DESCR:      This object is not supported by ISAM"
        ::={ extendAluCfmEqptMepEntry 1}

extendAluCfmEqptMdIndex OBJECT-TYPE
        SYNTAX Gauge (1..4294967295)
        ACCESS read-write
        STATUS mandatory
        DESCRIPTION 
                "This is the Maintenance Domain index of the ONT UNI.
         ALCATEL NOTE:
                ACCESS:     NA       USAGE:      NA
                PERSIST:    NA       INSRVMOD:   NA
                RANGE:      NA       DEFVALUE:   NA
                UNITS:      NA       SPARSE:     NA
                DESCR:      This object is not supported by ISAM"
        ::={ extendAluCfmEqptMepEntry 2}

extendAluCfmEqptMaIndex OBJECT-TYPE
        SYNTAX Gauge (1..4094 | 16777217..4294967295)
        ACCESS read-write
        STATUS mandatory
        DESCRIPTION 
              "This is the Maintenance Association index of the ONT UNI.
         ALCATEL NOTE:
                ACCESS:     NA       USAGE:      NA
                PERSIST:    NA       INSRVMOD:   NA
                RANGE:      NA       DEFVALUE:   NA
                UNITS:      NA       SPARSE:     NA
                DESCR:      This object is not supported by ISAM"
        ::={ extendAluCfmEqptMepEntry 3}

extendAluCfmEqptMepIdentifier OBJECT-TYPE
        SYNTAX Dot1agCfmMepId -- KM dot1agCfmMepIdentifier
        ACCESS read-write
        STATUS mandatory
        DESCRIPTION
                "This is the MEP ID of the ONT UNI.
         ALCATEL NOTE:
                ACCESS:     NA       USAGE:      NA
                PERSIST:    NA       INSRVMOD:   NA
                RANGE:      NA       DEFVALUE:   NA
                UNITS:      NA       SPARSE:     NA
                DESCR:      This object is not supported by ISAM"
        ::={ extendAluCfmEqptMepEntry 4}

extendAluCfmEqptMepOrMip OBJECT-TYPE
        SYNTAX INTEGER (0..2)
        ACCESS read-write
        STATUS mandatory
        DESCRIPTION
                "This is an indication whether the ONT UNI is a MEP/MIP or
                 none. 0 = NONE, 1 = MEP, 2 = MIP.
         ALCATEL NOTE:
                ACCESS:     NA       USAGE:      NA
                PERSIST:    NA       INSRVMOD:   NA
                RANGE:      NA       DEFVALUE:   NA
                UNITS:      NA       SPARSE:     NA
                DESCR:      This object is not supported by ISAM"
        ::={ extendAluCfmEqptMepEntry 5}

extendAluCfmEqptMacAddress OBJECT-TYPE
       SYNTAX MacAddress
       ACCESS read-only
       STATUS mandatory
       DESCRIPTION
               "This is the MAC address of the ONT that is read from CCMs
                and kept in the MepDbTable. It is copied here for
                convenience.
         ALCATEL NOTE:
                ACCESS:     NA       USAGE:      NA
                PERSIST:    NA       INSRVMOD:   NA
                RANGE:      NA       DEFVALUE:   NA
                UNITS:      NA       SPARSE:     NA
                DESCR:      This object is not supported by ISAM"
       ::={ extendAluCfmEqptMepEntry 6}

extendAluCfmEqptRowStatus OBJECT-TYPE
        SYNTAX RowStatus
        ACCESS read-write
        STATUS mandatory
        DESCRIPTION
                "This is the row status.
         ALCATEL NOTE:
                ACCESS:     NA       USAGE:      NA
                PERSIST:    NA       INSRVMOD:   NA
                RANGE:      NA       DEFVALUE:   NA
                UNITS:      NA       SPARSE:     NA
                DESCR:      This object is not supported by ISAM"
        ::={ extendAluCfmEqptMepEntry 7}


-- ************************************************************************
--     Extend CFM Bulk Table
-- ************************************************************************

extendAluCfmBulkTable OBJECT-TYPE
        SYNTAX SEQUENCE OF ExtendAluCfmBulkEntry
        ACCESS not-accessible
        STATUS mandatory
        DESCRIPTION
            "This table contains the proprietary objects for
             Bulk MAs and MEPs creation and removal.
         ALCATEL NOTE:
                Table size: 1
                DESCR:  This table contains a single row which is created at the  
                        system startup. Only Bulk MEPs commands are supported.
			This object is not supported by ISAM."

        ::= { extendAluCfmMIB 4 }

extendAluCfmBulkEntry OBJECT-TYPE
        SYNTAX ExtendAluCfmBulkEntry
        ACCESS not-accessible
        STATUS mandatory
        DESCRIPTION 
            "This list contains the objects for the bulk MAs and MEPs 
             processing. This is a single row table for which the row
             is always present; it is created at system initialization."
        INDEX { extendAluCfmBulkMdIndex } 
        ::= { extendAluCfmBulkTable 1}

ExtendAluCfmBulkEntry ::=
        SEQUENCE {
                extendAluCfmBulkMdIndex        Gauge, 
                extendAluCfmBulkStartMepId     Dot1agCfmMepId, 
                extendAluCfmBulkStartIfIndex   InterfaceIndex, 
                extendAluCfmBulkEndIfIndex     InterfaceIndex, 
                extendAluCfmBulkStartMaIndex   Gauge, 
                extendAluCfmBulkEndMaIndex     Gauge, 
                extendAluCfmBulkMhfCreation    INTEGER, 
                extendAluCfmBulkStartVlanId    VlanIndex,
                extendAluCfmBulkEndVlanId      VlanIndex,
                extendAluCfmBulkType           INTEGER,
                extendAluCfmBulkStatus         INTEGER
}

extendAluCfmBulkMdIndex OBJECT-TYPE
        SYNTAX Gauge (1..4294967295)
        ACCESS read-write
        STATUS mandatory
        DESCRIPTION 
                "This object is the Maintenance Domain index for which the 
                 bulk creation or deletion of MAs/MEPs is applied.
         ALCATEL NOTE:
                ACCESS:     RW       USAGE:      NA
                PERSIST:    No       INSRVMOD:   No
                RANGE:      NA       DEFVALUE:   1
                UNITS:      NA       SPARSE:     NA
                DESCR:      This object is not supported by ISAM "
        ::={ extendAluCfmBulkEntry 1}

extendAluCfmBulkStartMepId OBJECT-TYPE
        SYNTAX Dot1agCfmMepId
        ACCESS read-write
        STATUS optional
        DESCRIPTION
                "This object is the start MEP ID for MEPs creation. 
         ALCATEL NOTE:
                ACCESS:     RW       USAGE:      NA
                PERSIST:    No       INSRVMOD:   No
                RANGE:      NA       DEFVALUE:   1
                UNITS:      NA       SPARSE:     NA
                DESCR:      This object is mandatory for create MEP only.
			    This object is not supported by ISAM."	
        ::={ extendAluCfmBulkEntry 2}

extendAluCfmBulkStartIfIndex OBJECT-TYPE
        SYNTAX InterfaceIndex
        ACCESS read-write
        STATUS mandatory
        DESCRIPTION
                "This object is the start of the range of the interface 
                 index to be applied to the MEPs created or deleted.
         ALCATEL NOTE:
                ACCESS:     RW       USAGE:      NA
                PERSIST:    No       INSRVMOD:   No
                RANGE:      NA       DEFVALUE:   1
                UNITS:      NA       SPARSE:     NA
                DESCR:      This object is not supported by ISAM."
        ::={ extendAluCfmBulkEntry 3}

extendAluCfmBulkEndIfIndex OBJECT-TYPE
        SYNTAX InterfaceIndex
        ACCESS read-write
        STATUS mandatory
        DESCRIPTION
                "This object is the end of the range of interface index to  
                 be applied to the MEPs created or deleted.
         ALCATEL NOTE:
                ACCESS:     RW       USAGE:      NA
                PERSIST:    No       INSRVMOD:   No
                RANGE:      NA       DEFVALUE:   1
                UNITS:      NA       SPARSE:     NA
                DESCR:      This object is not supported by ISAM."
        ::={ extendAluCfmBulkEntry 4}

extendAluCfmBulkStartMaIndex OBJECT-TYPE
        SYNTAX Gauge (1..4294967295)
        ACCESS read-write
        STATUS mandatory
        DESCRIPTION 
              "This object is the start of the range of the Maintenance
               Association index to be applied to the MEPs created or
               deleted or the MAs to be created or deleted.
         ALCATEL NOTE:
                ACCESS:     RW       USAGE:      NA
                PERSIST:    No       INSRVMOD:   No
                RANGE:      NA       DEFVALUE:   1
                UNITS:      NA       SPARSE:     NA
                DESCR:      This object is not supported by ISAM."
        ::={ extendAluCfmBulkEntry 5}

extendAluCfmBulkEndMaIndex OBJECT-TYPE
        SYNTAX Gauge (1..4294967295)
        ACCESS read-write
        STATUS mandatory
        DESCRIPTION 
              "This object is the end of the range of the Maintenance
               Association index to be applied to the MEPs created or
               deleted or the MAs to be created or deleted.
         ALCATEL NOTE:
                ACCESS:     RW       USAGE:      NA
                PERSIST:    No       INSRVMOD:   No
                RANGE:      NA       DEFVALUE:   1
                UNITS:      NA       SPARSE:     NA
                DESCR:      This object is not supported by ISAM."
        ::={ extendAluCfmBulkEntry 6}

extendAluCfmBulkMhfCreation OBJECT-TYPE
         SYNTAX  INTEGER {
                             none    (1),
                             default (2)
                         }
        ACCESS read-write
        STATUS mandatory
        DESCRIPTION
                "This object is an indication whether the MAs are created 
                 with or without MIPs creation enabled or disabled.
         ALCATEL NOTE:
                ACCESS:     RW       USAGE:      NA
                PERSIST:    No       INSRVMOD:   No
                RANGE:      NA       DEFVALUE:   1
                UNITS:      NA       SPARSE:     NA
                DESCR:      This object is not supported by ISAM."
        ::={ extendAluCfmBulkEntry 7}

extendAluCfmBulkStartVlanId OBJECT-TYPE
       SYNTAX VlanIndex
       ACCESS read-write
       STATUS mandatory
       DESCRIPTION
               "This object is the start of the range of the VLAN ID
               to be applied to the MAs created or deleted.
         ALCATEL NOTE:
                ACCESS:     RW       USAGE:      NA
                PERSIST:    No       INSRVMOD:   No
                RANGE:      NA       DEFVALUE:   1
                UNITS:      NA       SPARSE:     NA
                DESCR:      This object is not supported by ISAM."
       ::={ extendAluCfmBulkEntry 8}

extendAluCfmBulkEndVlanId OBJECT-TYPE
       SYNTAX VlanIndex
       ACCESS read-write
       STATUS mandatory
       DESCRIPTION
               "This object is the start of the range of the VLAN ID
               to be applied to the MAs created or deleted.
         ALCATEL NOTE:
                ACCESS:     RW       USAGE:      NA
                PERSIST:    No       INSRVMOD:   No
                RANGE:      NA       DEFVALUE:   1
                UNITS:      NA       SPARSE:     NA
                DESCR:      This object is not supported by ISAM."
       ::={ extendAluCfmBulkEntry 9}

extendAluCfmBulkType OBJECT-TYPE
         SYNTAX  INTEGER {
                             mepCreate (1),
                             mepDelete (2),
                             maCreate  (3),
                             maDelete  (4)
                         }
        ACCESS read-write
        STATUS mandatory
        DESCRIPTION
                "This object represent the action for the bulk process
         ALCATEL NOTE:
                ACCESS:     RW       USAGE:      NA
                PERSIST:    No       INSRVMOD:   No
                RANGE:      1..2     DEFVALUE:   1
                UNITS:      NA       SPARSE:     NA
                DESCR:      This object is not supported by ISAM."
        ::={ extendAluCfmBulkEntry 10}

extendAluCfmBulkStatus OBJECT-TYPE
         SYNTAX  INTEGER {
                             init             (1),
                             inProgress       (2),
                             parseFailed      (3),
                             operationFailed  (4),
                             successful       (5)
                         }
        ACCESS read-only
        STATUS mandatory
        DESCRIPTION
                "This object represent the status of the bulk command.
                 While the value is inProgress, the bulk process is in 
                 operation and a new CFM request (bulk or not) is rejected. 
                 A new request can be issued for all the other status.
         ALCATEL NOTE:
                ACCESS:     RO       USAGE:      NA
                PERSIST:    No       INSRVMOD:   NA
                RANGE:      1..5     DEFVALUE:   1
                UNITS:      NA       SPARSE:     NA
                DESCR: This object is not supported by ISAM."
        ::={ extendAluCfmBulkEntry 11}

-- ***********************************************************************
--     Extend CFM MA Table
-- ***********************************************************************

extendAluCfmMaTable OBJECT-TYPE
    	SYNTAX      SEQUENCE OF ExtendAluCfmMaEntry
    	ACCESS      not-accessible
    	STATUS      mandatory
    	DESCRIPTION 
        	"The ALU exension to the standard Maintenance Association 
		 table.  Each row in the table represents an MA. 
		 An MA is a set of MEPs, each configured with a single 
		 service instance. A row in this table is automatically 
		 created/ deleted when a corresponding row in 
		 dot1agCfmMaTable is created/ deleted. 
         ALCATEL NOTE:
        	TABLESIZE: 20000
             	DESCR: ISAM supports at most 20000 MAs, except for SHUB 
             	based NTs, where the table size is 2700. Active CCM would 
                be supported from ISR4.5.0.2 onwards."
 	REFERENCE   
 		"802.1ag clause 18.2"
	::={ extendAluCfmMIB 5}

extendAluCfmMaEntry OBJECT-TYPE
    	SYNTAX      ExtendAluCfmMaEntry
    	ACCESS      not-accessible
    	STATUS      mandatory
    	DESCRIPTION 
        	"The MA table entry.
         ALCATEL NOTE:
            	Row creation : Instantiated as a result of an MA creation.
            	Row deletion : Deleted as a result of an MA deletion. 
            	Index usage  : See INDEX below.
            	lexicographical order : Sorted on MdIndex and then MaIndex."
    	INDEX { dot1agCfmMdIndex, dot1agCfmMaIndex }
    	::={ extendAluCfmMaTable 1}

ExtendAluCfmMaEntry ::= 
	SEQUENCE {
    		extendAluCfmMaBridgeport    InterfaceIndexOrZero,
	        extendAluCfmMaCcmAware      TruthValue,
	        extendAluCfmMaCcmAdminState AluCfmMaCcmAdminState,
            extendAluCfmMaLtmFilter     TruthValue,
            extendAluCfmMaDualTagAware  TruthValue,
            extendAluCfmMaMhfLocation   AluCfmMaMhfLocationType
}

extendAluCfmMaBridgeport OBJECT-TYPE
    	SYNTAX      InterfaceIndexOrZero
    	ACCESS      read-write
    	STATUS      mandatory
    	DESCRIPTION 
        	"The Bridgeport corresponding the UNI where only an outward 
	  	 facing MEP may be created. If the value of this object 
		 is 0 (default), it is an MA where a MIP or inward facing MEP 
		 at the UNI can be created, or where an outward facing MEP 
		 at an LT's NT interface can be created. If an non-zero 
		 IfIndex is provided, then it must be the ifIndex of a 
		 BridgePort on a UNI and it means this is an access link MA 
		 and only an outward facing MEP can be created on one 
		 particular UNI whose IfIndex is provided. If the value of 
		 this object is 0, it means it is a generic MA for which 
		 multiple MEPs on multiple ONTs can be created or where 
		 outward facing MEPs at an LT-NT interface can be created. 
		 The value of this object cannot be modified after the row 
		 is created. 
         ALCATEL NOTE:
                ACCESS:     NA       USAGE:      OPT 
                PERSIST:    YES      INSRVMOD:   NO 
                RANGE:      NA       DEFVALUE:   0
                UNITS:      NA       SPARSE:     NA
                DESCR:      NA"
        DEFVAL {0}
    	::={ extendAluCfmMaEntry 1}

extendAluCfmMaCcmAware OBJECT-TYPE
    	SYNTAX      TruthValue
    	ACCESS      read-write
    	STATUS      mandatory
    	DESCRIPTION 
          "This object is used in order to enable CCM configuration
           within the related MA.
          ALCATEL NOTE:
            ACCESS:     NA       USAGE:      OPT 
            PERSIST:    YES      INSRVMOD:   YES 
            RANGE:      NA       DEFVALUE:   NA
            UNITS:      NA       SPARSE:     NA
            DESCR:
              A CCM aware MA is one with:
              extendAluCfmMaCcmAware equal to true.
              Any change in this object is only possible for a 
              CCM locked MA (see extendAluCfmMaCcmAdminState).
              A transition of this object from true to false 
              will stop processing the received CCM frames. 
              A transition of this object from false to true 
              will start processing of the received CCM frames."
        DEFVAL {false}
    	::={ extendAluCfmMaEntry 2}

extendAluCfmMaCcmAdminState OBJECT-TYPE
    	SYNTAX      AluCfmMaCcmAdminState
    	ACCESS      read-write
    	STATUS      mandatory
    	DESCRIPTION 
          "This object is used in order to activate CCM
           for the related MA (transmitting and receiving CCM).
          ALCATEL NOTE:
            ACCESS:     NA       USAGE:      OPT 
            PERSIST:    YES      INSRVMOD:   YES 
            RANGE:      NA       DEFVALUE:   NA
            UNITS:      NA       SPARSE:     NA
            DESCR:
              A locked CCM MA is one with:
              extendAluCfmMaCcmAdminState equal to lock.
              In the lock state, configuration settings for CCM
              can be done inside :
              dot1agCfmMdTable, dot1agCfmMaTable, dot1agCfmMepTable, 
              dot1agCfmMaMepListTable.
              A transition of this object from unlock to lock
              will
              0/freeze all CCM processing within the MA
              (transmitting, monitoring, alarm generation)
              1/clear outstanding CCM alarms
              For all CCI enabled local MEPS, it will cause:
              2/clearing all available CCM transmit information, i.e. 
              dot1agCfmMepCciSentCcms, etc.
              3/clearing all available CCM receive information, i.e. 
              dot1agCfmMepErrorCcmLastFailure, dot1agCfmMepXconCcmLastFailure, 
              dot1agCfmMepFngState, dot1agCfmMepHighestPrDefect, dot1agCfmMepDefects, 
              dot1agCfmMepCcmSequenceErrors, etc.
              4/clearing entries inside dot1agCfmMepDbTable.
              A transition of this object from lock to unlock
              will start all CCM processing and result reporting within the MA."
        DEFVAL {lock}
    	::={ extendAluCfmMaEntry 3}

extendAluCfmMaLtmFilter OBJECT-TYPE
         SYNTAX      TruthValue
         ACCESS      read-write
         STATUS      mandatory
         DESCRIPTION 
            "This object is used in order to filter out upstream LTM messages
             within the related MA.
         ALCATEL NOTE:
                 ACCESS:     NA       USAGE:      OPT 
                 PERSIST:    YES      INSRVMOD:   YES 
                 RANGE:      NA       DEFVALUE:   NA
                 UNITS:      NA       SPARSE:     NA
                 DESCR:
                   Upstream LTM messages at the same level as a MIP 
                   are filtered (dropped) by default 
                   within the ISAM as the CPE is generally considered a 
                   non-trusted device. When a customer uses authenticated 
                   CPEs,upstream LTM message filtering can be disabled within 
                   the related MA.This object is not applicable for GPON EPON
                   NELT-B NNI HC-UNI."
         DEFVAL {true}
         ::= { extendAluCfmMaEntry 4}

extendAluCfmMaDualTagAware OBJECT-TYPE
         SYNTAX      TruthValue
         ACCESS      read-write
         STATUS      mandatory
         DESCRIPTION 
            "This object is used in order to enable the processing of
             dual tagged CFM messages on single tag vlan cross connect 
             model within the related MA.
         ALCATEL NOTE:
                 ACCESS:     NA       USAGE:      OPT 
                 PERSIST:    YES      INSRVMOD:   YES 
                 RANGE:      NA       DEFVALUE:   NA
                 UNITS:      NA       SPARSE:     NA
                 DESCR:
                   When enabled, CFM processing will occur for messages whose 
                   outer (Svlan) tag has a related MA, regardless of the 
                   presence of an inner Cvlan tag. CFM message processing 
                   will occur against the combination of the Svlan and any 
                   Cvlan tag.
                   When disabled, CFM packets with two vlan tags in a C-VLAN CC
                   will not be processed.
		   Configurable on all forwarding models, but applicable only  
		   for C-Vlan CC.
                   Not applicable to GPON EPON NELT-B NNI HC-UNI"
         DEFVAL {false}
         ::= { extendAluCfmMaEntry 5}
         
extendAluCfmMaMhfLocation OBJECT-TYPE
	    SYNTAX AluCfmMaMhfLocationType
	    ACCESS read-write
		STATUS mandatory
		DESCRIPTION
	         " Identifies the mhf location type of ma ;
	         	1 : default value, for Gpon, MIP is set on onu; for DSL, MIP is set on lt uplink;
	         	2 : MIP is set on lt uplink;
				3 : MIP is set on lt virtual bridge port;
				4 : MIP is set on gpon onu
				5 : MIP is set on both Lt uplink and virtual bridgeport
				6 : MIP is set on both Lt uplink and ONU
				7 : MIP is set on both lt virtual bridgeport and ONU
				8 : MIP is set on lt uplink, virtual bridgeport and ONU
	         	
	 		 ALCATEL NOTE:
	                            ACCESS:     RW       USAGE:      OPT
	                            PERSIST:    YES      INSRVMOD:   NA
	                            RANGE:      NA       DEFVALUE:   NA 
	                            UNITS:      NA       SPARSE:     NA
	                 "
	    DEFVAL { default}
		::= { extendAluCfmMaEntry 6} 
         

-- ***********************************************************************
--     CFM MEP OamCtlTable
-- ***********************************************************************
extendAluCfmMepOamCtlTableNextIndex OBJECT-TYPE
    SYNTAX      Dot1afCfmIndexIntegerNextFree
    ACCESS      read-only
    STATUS      mandatory
    DESCRIPTION 
      "This object contains an unused value for extendAluCfmMepOamCtlTestIndex 
       in the extendAluCfmMepOamCtlTable,
       or a zero to indicate that none exist.
       ALCATEL NOTE:
          ACCESS:      NA            USAGE:       NA
          PERSIST:     NO            INSRVMOD:    NA
          RANGE:       NA            DEFVALUE:    NA
          UNITS:       NA            SPARSE:      NA
          DESCR:       NA" 
      ::= { extendAluCfmMIB 6 }

extendAluCfmMepOamCtlTable OBJECT-TYPE
        SYNTAX SEQUENCE OF ExtendAluCfmMepOamCtlEntry
        ACCESS not-accessible
        STATUS mandatory
        DESCRIPTION
          "Primary controls and status for the OAM capabilities of a MEP.
          It replaces managed objects of dot1agCfmMepTable for
          configuring, activating, result monitoring of following 
          oam protocol operations:
            uc LBM: unicast Loopback Message
            mc LBM: multicast Loopback Message
            LTM: Linktrace Message
          The results of a completed uc LBM and LTM (partially) test are
	  also contained in this table.
          Entries are created to initiate transmission of either uc LBM,
          mc LBM or of LTM with particular test settings.
          Availability of test results can be monitored via the
          extendAluCfmMepOamCtlResult. If this variable indicates
          test completion:
          * uc LBM results can be retrieved in this table
          * mc LBM results can be retrieved in extendAluCfmMepMcLbrTable
          * LTM results can be retrieved in extendAluCfmMepLtrTable and
	    in this table
          Modifying settings for an ongoing test is not possible.
          Deleting an entry for a test in this table will clear
          associated results. 
		  This table is supported only from ISR4.4 onwards.
          ALCATEL NOTE:
           TABLESIZE:     1..16(simultaneous number of OAM sessions)"
        ::= { extendAluCfmMIB 7 }

extendAluCfmMepOamCtlEntry OBJECT-TYPE
        SYNTAX ExtendAluCfmMepOamCtlEntry
        ACCESS not-accessible
        STATUS mandatory
        DESCRIPTION 
              "An entry in the table models a test activated on a
               particular MEP.
               Only one oam test can be active on a MEP.
	       Only two oam tests can be active on an LT."
        INDEX { extendAluCfmMepOamCtlTestIndex } 
        ::= { extendAluCfmMepOamCtlTable 1}

ExtendAluCfmMepOamCtlEntry ::= SEQUENCE {
    extendAluCfmMepOamCtlTestIndex                    Gauge,
    extendAluCfmMepOamCtlMdIndex                      Gauge, 
    extendAluCfmMepOamCtlMaIndex                      Gauge, 
    extendAluCfmMepOamCtlMepIdentifier                Dot1agCfmMepId, 
    extendAluCfmMepOamCtlTestType                     INTEGER,
    extendAluCfmMepOamCtlTransmitTargetMacAddress     MacAddress,
    extendAluCfmMepOamCtlTransmitLbmMessages          INTEGER,
    extendAluCfmMepOamCtlTransmitLbmTlvType           INTEGER,
    extendAluCfmMepOamCtlTransmitLbmDataLen           INTEGER,
    extendAluCfmMepOamCtlTransmitLbmDataBitPattern    OCTET STRING,
    extendAluCfmMepOamCtlTransmitLbmTestBitPattern    INTEGER,
    extendAluCfmMepOamCtlTransmitVlanPriority         INTEGER,
    extendAluCfmMepOamCtlTransmitLbmVlanDropEnable    INTEGER,
    extendAluCfmMepOamCtlTransmitLbmVlanDropPcp       INTEGER,
    extendAluCfmMepOamCtlTransmitLtmTtl               Gauge,
    extendAluCfmMepOamCtlTransmitLtmUseFdbOnly	      TruthValue,
    extendAluCfmMepOamCtlTransmitLtmEgressIdentifier  OCTET STRING,
    extendAluCfmMepOamCtlTransmitLtmSeqNumber	      Counter,
    extendAluCfmMepOamCtlResult                       INTEGER,
    extendAluCfmMepOamCtlLbrIn                        Counter,
    extendAluCfmMepOamCtlLbrInOutOfOrder              Counter,
    extendAluCfmMepOamCtlLbrBadMsdu                   Counter,
    extendAluCfmMepOamCtlLbrBitErrorRatio             INTEGER,
    extendAluCfmMepOamCtlLbrCrcError                  Counter,
    extendAluCfmMepOamCtlUnexpLtrIn		      Counter,
    extendAluCfmMepOamCtlValidResults                 Counter,
    extendAluCfmMepOamCtlRowStatus                    RowStatus,
    extendAluCfmMepOamCtlLbrBitError                  Counter
}

extendAluCfmMepOamCtlTestIndex OBJECT-TYPE
    SYNTAX      Gauge (1..4294967295)
    ACCESS      not-accessible
    STATUS      mandatory
    DESCRIPTION 
      "This is a unique test index.
      extendAluCfmMepOamCtlTableNextIndex can be inspected to find an
      available index for row-creation.
      
      ALCATEL NOTE:
        ACCESS:     NA       USAGE:      MAND
        PERSIST:    NO       INSRVMOD:   NO
        RANGE:      (1..16)  DEFVALUE:   NA
        UNITS:      NA       SPARSE:     NA
        DESCR:      NA"
    ::= { extendAluCfmMepOamCtlEntry  1 }

extendAluCfmMepOamCtlMdIndex OBJECT-TYPE
    SYNTAX      Gauge (1..4294967295)
    ACCESS      read-write
    STATUS      mandatory
    DESCRIPTION 
      "This is the Maintenance Domain index.
       
       ALCATEL NOTE:
         ACCESS:     NA       USAGE:      MAND
         PERSIST:    NO       INSRVMOD:   NO
         RANGE:      NA       DEFVALUE:   NA
         UNITS:      NA       SPARSE:     NA
         DESCR:      NA"
    ::= { extendAluCfmMepOamCtlEntry  2 }

extendAluCfmMepOamCtlMaIndex OBJECT-TYPE
    SYNTAX      Gauge (1..4294967295)
    ACCESS      read-write
    STATUS      mandatory
    DESCRIPTION 
      "This is the Maintenance Association index.
      
       ALCATEL NOTE:
         ACCESS:     NA       USAGE:      MAND
         PERSIST:    NO       INSRVMOD:   NO
         RANGE:      NA       DEFVALUE:   NA
         UNITS:      NA       SPARSE:     NA
         DESCR:      NA"
    ::= { extendAluCfmMepOamCtlEntry 3 }

extendAluCfmMepOamCtlMepIdentifier OBJECT-TYPE
    SYNTAX      Dot1agCfmMepId
    ACCESS      read-write
    STATUS      mandatory
    DESCRIPTION 
      "This is the MEP Identifier.
      ALCATEL NOTE:
        ACCESS:     NA       USAGE:      MAND
        PERSIST:    NO       INSRVMOD:   NO
        RANGE:      NA       DEFVALUE:   NA
        UNITS:      NA       SPARSE:     NA
        DESCR:      NA"
    ::= { extendAluCfmMepOamCtlEntry 4 }

extendAluCfmMepOamCtlTestType  OBJECT-TYPE
    SYNTAX      INTEGER {
                      ucLbm(1),
                      mcLbm(2),
                      ltm(3)
    }
    ACCESS      read-write
    STATUS      mandatory
    DESCRIPTION 
      "ALCATEL NOTE:
         ACCESS:      NA            USAGE:       MAND
         PERSIST:     NO            INSRVMOD:    NO
         RANGE:       NA            DEFVALUE:    NA
         UNITS:       NA            SPARSE:      NA
         DESCR:       
           Specifies the type of OAM test:
             ucLbm: unicast Loopback Message
             mcLbm: multicast Loopback Message
             ltm:   Linktrace Message"
    ::= { extendAluCfmMepOamCtlEntry 5 }

extendAluCfmMepOamCtlTransmitTargetMacAddress OBJECT-TYPE
    SYNTAX      MacAddress
    ACCESS      read-write
    STATUS      mandatory
    DESCRIPTION 

      "The MAC Address for the OAM target: a unicast destination
      MAC address.
      ALCATEL NOTE:
        ACCESS:      NA            USAGE:       OPT
        PERSIST:     NO            INSRVMOD:    NO
        RANGE:       NA            DEFVALUE:    NA
        UNITS:       NA            SPARSE:      NO
        DESCR:
          For extendAluCfmMepOamCtlTestType mcLbm(see ITU-T Y.1731 Table 10-1),  
          as a predefined Multicast address is always used as destination
          MAC address(calculated by the system), this object is NA
          (and default value is filled out).
          For extendAluCfmMepOamCtlTestType ucLbm,
          (see 802.1ag clause 12.14.7.3.2:b)it is used as destination 
          MAC address in the LBM.
          For extendAluCfmMepOamCtlTestType ltm,
          (see 802.1ag clause 12.14.7.4.2:c) it is used for target
          MAC address within the payload of the LTM. The destination
          MAC address is calculated by the system."
     REFERENCE   
       "802.1ag clause 12.14.7.3.2:b
       802.1ag clause 12.14.7.4.2:c"
    DEFVAL { '000000000000'H }
    ::= { extendAluCfmMepOamCtlEntry 6 }

extendAluCfmMepOamCtlTransmitLbmMessages  OBJECT-TYPE
    SYNTAX      INTEGER
    ACCESS      read-write
    STATUS      mandatory
    DESCRIPTION 
      "The number of Loopback messages to be transmitted.
      ALCATEL NOTE:
        ACCESS:      NA            USAGE:       OPT
        PERSIST:     NO            INSRVMOD:    NO
        RANGE:       (1..5)        DEFVALUE:    NA
        UNITS:       NA            SPARSE:      NO
        DESCR:       
          Applicable only for uc LBM operation. 
	  Applicable for all extendAluCfmMepOamCtlTransmitLbmTlvType.
          Default value is filled out if NA.
          The interval between subsequent transmitted LBMs
          is fixed: 250ms."

      REFERENCE   
          "802.1ag clause 12.14.7.3.2:c"
    DEFVAL      { 1 }
    ::= { extendAluCfmMepOamCtlEntry 7 }

extendAluCfmMepOamCtlTransmitLbmTlvType	  OBJECT-TYPE
    SYNTAX      INTEGER {
		      none(1),
		      dataTlv(2),
		      testTlv(3)
    }
    ACCESS      read-write
    STATUS      mandatory
    DESCRIPTION
      "Specifies which TLV type is to be used for LBM.
      ALCATEL NOTE:
        ACCESS:      NA            USAGE:       OPT
        PERSIST:     NO            INSRVMOD:    NO
        RANGE:       NA            DEFVALUE:    NA
        UNITS:       NA            SPARSE:      NO
        DESCR:
          Only applicable for extendAluCfmMepOamCtlTestType ucLbm and mcLbm.
	  ucLbm supports all TLV types. mcLbm supports only none(1) and dataTlv(2).
          To be interpreted w.r.t. extendAluCfmMepOamCtlTransmitLbmMessages.
	  The value testTlv is not supported in ISAM."
	REFERENCE
	    "ITU-T Y.1731 clause 9.3.2"
    DEFVAL      { 1 }
    ::= { extendAluCfmMepOamCtlEntry 8 }

extendAluCfmMepOamCtlTransmitLbmDataLen OBJECT-TYPE
    SYNTAX      INTEGER
    ACCESS      read-write
    STATUS      mandatory
    DESCRIPTION 
      "For dataTlv, the length specifies the size in octets of the 
       value field. For testTlv, the length specifies the size in octets 
       of the Test pattern and CRC-32 field.
       If CRC-32 is used with the testTlv, the length must be at least 4.
       Default value is filled out if NA.
      ALCATEL NOTE:
        ACCESS:      NA            USAGE:       OPT
        PERSIST:     NO            INSRVMOD:    NO
        RANGE:       (1..1488)     DEFVALUE:    NA
        UNITS:       bytes         SPARSE:      NO
        DESCR: 
	  Only applicable for extendAluCfmMepOamCtlTestType ucLbm, mcLbm and
          extendAluCfmMepOamCtlTransmitLbmTlvType dataTlv, testTlv."
     REFERENCE   
         "802.1ag clause 12.14.7.3.2:d"
    DEFVAL      { 64 }
    ::= { extendAluCfmMepOamCtlEntry 9 }

extendAluCfmMepOamCtlTransmitLbmDataBitPattern OBJECT-TYPE
    SYNTAX      OCTET STRING (SIZE(8))
    ACCESS      read-write
    STATUS      mandatory
    DESCRIPTION 
      "This 64 bit pattern is used repetitively to fillup Data TLV,
       if the Data TLV is selected to be sent.
       Most significant bits are used first.
       Applicable only for LBM operation for non zero value of
       extendAluCfmMepOamCtlTransmitLbmDataLen. Applicable only
       for extendAluCfmMepOamCtlTransmitLbmTlvType dataTlv(2).
       Default value is filled out if NA.
      ALCATEL NOTE:
        ACCESS:      NA            USAGE:       OPT
        PERSIST:     NO            INSRVMOD:    NO
        RANGE:       NA            DEFVALUE:    NA
        UNITS:       bytes         SPARSE:      NO
        DESCR: "      
     REFERENCE   
         "802.1ag clause 12.14.7.3.2:d"
    DEFVAL          {'0000000000000000'H }
    ::= { extendAluCfmMepOamCtlEntry 10 }

extendAluCfmMepOamCtlTransmitLbmTestBitPattern	OBJECT-TYPE
    SYNTAX	INTEGER {
		      allZerosNoCrc(0),
		      allZerosCrc(1),
		      prbsNoCrc(2),
		      prbsCrc(3),
		      allOnesNoCrc(4),
		      allOnesCrc(5)
    }
    ACCESS	read-write
    STATUS	mandatory
    DESCRIPTION
      "Range of accepted bit pattern types for the Test TLV. 
       prbsNoCrc and prbsCrc make use of 
       ITU-T O.150 PRBS (2^31)-1.
      ALCATEL NOTE:
   	ACCESS:      NA            USAGE:       OPT
        PERSIST:     NO            INSRVMOD:    NO
        RANGE:       3             DEFVALUE:    3
        UNITS:       NA            SPARSE:      NO
        DESCR:
           Only applicable for extendAluCfmMepOamCtlTestType ucLbm and 
	       extendAluCfmMepOamCtlLbmTlvType testTlv. Default value is
	       filled out if NA.Only prbsCrc is supported.
           This object is not supported."
      REFERENCE
	  "ITU-T Y.1731 clause 9.3.2"
    DEFVAL      { 3 }
    ::= { extendAluCfmMepOamCtlEntry 11 }

extendAluCfmMepOamCtlTransmitVlanPriority OBJECT-TYPE
    SYNTAX      INTEGER (0..7)
    ACCESS      read-write
    STATUS      mandatory
    DESCRIPTION 
        "Priority. 3 bit value to be used in the VLAN tag, if present
         in the transmitted frame.
         
--         The default value is CCM priority.
         ALCATEL NOTE:
            ACCESS:      NA            USAGE:       OPT
            PERSIST:     NO            INSRVMOD:    NO
            RANGE:       NA            DEFVALUE:    DEP (see DESCR)
            UNITS:       bytes         SPARSE:      NO
            DESCR:       
              Applicable for both LBM and LTM operation.
              Default value is filled out if NA, i.e. highest priority { 7 }
              (from ISR4.4).
              For LTM, dot1agCfmMepCcmLtmPriority setting is never used.
	      For ucLBM, to be configured with respect to
	      extendAluCfmMepOamCtlTransmitLbmVlanDropEnable and
              extendAluCfmMepOamCtlTransmitLbmVlanDropPcp."
     REFERENCE   
         "802.1ag clause 12.14.7.3.2:e"
    ::= { extendAluCfmMepOamCtlEntry 12 }

extendAluCfmMepOamCtlTransmitLbmVlanDropEnable OBJECT-TYPE
    SYNTAX      INTEGER {
	              noDrop(1),
                      pcp(2),
                      dei(3)
    }
    ACCESS      read-write
    STATUS      mandatory
    DESCRIPTION 
      "Parameter indicating whether the packet must be marked as drop
       eligible. pcp points out that Priority Code Point encoding must
       be used. dei points out that the drop eligible indicator must be
       used. dei can only be used in the context of an S-vlan.
       Default value is used if NA.
      ALCATEL NOTE:
          ACCESS:      NA            USAGE:       OPT
          PERSIST:     NO            INSRVMOD:    NO
          RANGE:       NA            DEFVALUE:    NA
          UNITS:       NA            SPARSE:      NO
          DESCR:       
	      Applicable for ucLbm. To be configured with respect to
              extendAluCfmMepOamCtlTransmitVlanPriority and
              extendAluCfmMepOamCtlTransmitLbmVlanDropPcp.
              This object is not supported"
    REFERENCE
        "802.1ad clause 6.7.3 and 802.1ag clause 12.14.7.3.2:e"
    DEFVAL	{ 1 }
    ::= { extendAluCfmMepOamCtlEntry 13 }

extendAluCfmMepOamCtlTransmitLbmVlanDropPcp	OBJECT-TYPE
    SYNTAX	INTEGER {
                      pcp8P0D(1),
                      pcp7P1D(2),
                      pcp6P2D(3),
                      pcp5P3D(4)
    }
    ACCESS      read-write
    STATUS      mandatory
    DESCRIPTION
      "Defines the Priority Code Point encoding rule used. 
       Applicable only for extendAluCfmMepOamCtlTransmitLbmVlanDropEnable
       noDrop(1) and pcp(2).
       Default value is used if NA.
      ALCATEL NOTE:
        ACCESS:      NA            USAGE:       OPT
        PERSIST:     NO            INSRVMOD:    NO
        RANGE:       NA            DEFVALUE:    NA
        UNITS:       NA            SPARSE:      NO
        DESCR:       
              Applicable only for ucLbm operation.
	      Table 6-3 of 802.1ad (2005) explains the difference 
              between the different encoding rules.
              This object is not supported "
    REFERENCE
        "802.1ad clause 6.7.3"
    DEFVAL       { 1 }
    ::={ extendAluCfmMepOamCtlEntry 14 }

extendAluCfmMepOamCtlTransmitLtmTtl OBJECT-TYPE
    SYNTAX      Gauge (0..255)
    ACCESS      read-write
    STATUS      mandatory
    DESCRIPTION 
        "The LTM TTL field. Default value, if not specified, is 64.
         The TTL field indicates the number of hops remaining to the
         LTM.  Decremented by 1 by each Linktrace Responder that
         handles the LTM.  The value received in the LTM is returned
         in the LTR.  If 0 on input, the LTM is not transmitted to the
         next hop.
         ALCATEL NOTE:
            ACCESS:      NA            USAGE:       OPT
            PERSIST:     NO            INSRVMOD:    NO
            RANGE:       NA            DEFVALUE:    NA
            UNITS:       NA            SPARSE:      NO
            DESCR:       Only applicable for extendAluCfmMepOamCtlTestType 
			 ltm. Default value is filled out if NA."
     REFERENCE   
         "802.1ag clause 12.14.7.4.2:d and 21.8.4"
    DEFVAL      { 64 }
    ::= { extendAluCfmMepOamCtlEntry 15 }

extendAluCfmMepOamCtlTransmitLtmUseFdbOnly	OBJECT-TYPE
    SYNTAX	TruthValue
    ACCESS	read-write
    STATUS	mandatory
    DESCRIPTION
	"Only the bit 'UseFDBonly' can be configured in the flags fields for
         LTMs transmitted by the MEP. The ISAM operates independent
	 of this bit value. The bridge filtering database is used to
	 determine the egress port (which corresponds with the bit value
	 true). Configuring this bit value as false will not change the 
	 behaviour of the ISAM.
	 This field was made configurable since it is copied from
	 LTM to LTM during the Linktrace protocol. If a device along the
	 route supports the use of this bit value, it can act accordingly.
	ALCATEL NOTE:
            ACCESS:      NA            USAGE:       OPT
            PERSIST:     NO            INSRVMOD:    NO
            RANGE:       NA            DEFVALUE:    NA
            UNITS:       NA            SPARSE:      NO
            DESCR:       Only applicable for extendAluCfmMepOamCtlTestType 
			 ltm. Default value is filled out if NA."
    REFERENCE
	"802.1ag clause 12.14.7.4.2:b and 20.37.1"
    DEFVAL	{ true }
    ::= { extendAluCfmMepOamCtlEntry 16 }

extendAluCfmMepOamCtlTransmitLtmEgressIdentifier  OBJECT-TYPE
    SYNTAX	OCTET STRING (SIZE(8))
    ACCESS	read-only
    STATUS	mandatory
    DESCRIPTION
	"Identifies the MEP that is originating this LTM. The low-order 
	 (highest numbered) octets contain a 48-bit IEEE MAC address unique 
	 to the system in which the MEP resides. The high-order (lowest
	 numbered) two octets are set to zero. (Only one Linktrace Initiator 
	 and Linktrace Responder exist).
	 The value returned is undefined if the test was not sent out.
        ALCATEL NOTE:
	   ACCESS:	NA		USAGE:	    NA
	   PERSIST:	NO		INSRVMOD:   NO
	   RANGE:	NA		DEFVALUE:   NA
	   UNITS:	NA		SPARSE:	    NO
	   DESCR:       Only applicable for extendAluCfmMepOamCtlTestType 
			ltm, otherwise value 0."
    REFERENCE
	"802.1q clause 12.14.7.4.3:c"
    ::= { extendAluCfmMepOamCtlEntry 17 }

extendAluCfmMepOamCtlTransmitLtmSeqNumber  OBJECT-TYPE
    SYNTAX 	Counter
    ACCESS	read-only
    STATUS	mandatory
    DESCRIPTION
	"The LTM Transaction Identifier of the LTM sent.
	ALCATEL NOTE:
	   ACCESS:	NA		USAGE:	    NA
	   PERSIST:	NO		INSRVMOD:   NA
	   RANGE:	NA		DEFVALUE:   NA
	   UNITS:	NA		SPARSE:	    NA
	   DESCR:       Only applicable for extendAluCfmMepOamCtlTestType 
			ltm, otherwise value 0."
    REFERENCE
	"802.1q clause 12.14.7.4.3:b and clause 20.41.1"
    ::= { extendAluCfmMepOamCtlEntry 18 }

extendAluCfmMepOamCtlResult  OBJECT-TYPE
    SYNTAX  INTEGER {
                      done(1),
                      inProgress(2),
		      failed(3)
    }
    ACCESS      read-only
    STATUS      mandatory
    DESCRIPTION 
        "Can be used to monitor the progress of the OAM operation.
         
         ALCATEL NOTE:
            ACCESS:      NA            USAGE:       NA
            PERSIST:     NO            INSRVMOD:    NA
            RANGE:       NA            DEFVALUE:    NA
            UNITS:       NA            SPARSE:      NA
            DESCR:
              Indicates availability of OAM operation results.
              For LBM/LTM, it replaces monitoring on
              dot1agCfmMepTransmitLbmStatus/dot1agCfmMepTransmitLtmStatus
              (in combination with 802.1ag clause 20.5.5 timeout/5s timeout).
              done(1) - For uc LBM :results are available in this table.
                      - For mc LBM :results are available in
                        extendAluCfmMepMcLbrTable.
                      - For LTM :results are available in extendAluCfmLtrTable
	                         and this table.
              inProgress(2) - Operation successfully started, not yet completed.
	      failed(3) - Operation succesfully started, but unable to finish.
              Following table indicates time boundaries in seconds within which 
              this object will reach value done or failed for each test type:
              TestType Max (in seconds)
              'ucLbm'  (extendAluCfmMepOamCtlTransmitLbmMessages)*(0,25)+5.75 
              'mcLbm'  6   
              'ltm'    6
              A worst case (TestType independent) value of 7s can be taken."
     REFERENCE   
         "802.1ag clause 12.14.7.3.3:a,
          802.1ag clause 12.14.7.4.3:a"
    ::= { extendAluCfmMepOamCtlEntry 19 }

extendAluCfmMepOamCtlLbrIn  OBJECT-TYPE
    SYNTAX      Counter
    ACCESS      read-only
    STATUS      mandatory
    DESCRIPTION 
        "Total number of valid, in-order Loopback Replies received.
         ALCATEL NOTE:
            ACCESS:      NA            USAGE:       NA
            PERSIST:     NO            INSRVMOD:    NA
            RANGE:       NA            DEFVALUE:    NA
            UNITS:       NA            SPARSE:      NA
            DESCR:
              Only applicable for extendAluCfmMepOamCtlTestType ucLbm, otherwise value 0.
              To be interpreted w.r.t. extendAluCfmMepOamCtlTransmitLbmMessages."
     REFERENCE   
         "802.1ag clause 12.14.7.1.3:y and 20.31.1"
    ::= { extendAluCfmMepOamCtlEntry  20 }

extendAluCfmMepOamCtlLbrInOutOfOrder OBJECT-TYPE
    SYNTAX      Counter
    ACCESS      read-only
    STATUS      mandatory
    DESCRIPTION 
        "The total number of valid, out-of-order Loopback Replies
         received.
         ALCATEL NOTE:
            ACCESS:      NA            USAGE:       NA
            PERSIST:     NO            INSRVMOD:    NA
            RANGE:       NA            DEFVALUE:    NA
            UNITS:       NA            SPARSE:      NA
            DESCR:
              Only applicable for extendAluCfmMepOamCtlTestType ucLbm, otherwise value 0.
              To be interpreted w.r.t. extendAluCfmMepOamCtlTransmitLbmMessages."
     REFERENCE   
         "802.1ag clause 12.14.7.1.3:z and 20.31.1"
    ::= { extendAluCfmMepOamCtlEntry  21 }

extendAluCfmMepOamCtlLbrBadMsdu OBJECT-TYPE
    SYNTAX      Counter
    ACCESS      read-only
    STATUS      mandatory
    DESCRIPTION 
        "(optional) The total number of LBRs received whose
         mac_service_data_unit did not match (except for the OpCode)
         that of the corresponding LBM (20.2.3).
         ALCATEL NOTE:
            ACCESS:      NA            USAGE:       NA
            PERSIST:     NO            INSRVMOD:    NA
            RANGE:       NA            DEFVALUE:    NA
            UNITS:       NA            SPARSE:      NA
            DESCR:
              This count is applicable for extendAluCfmMepOamCtlTestType
              ucLbm (taking into account extendAluCfmMepOamCtlTransmitLbmMessages)
              and mcLbm."
     REFERENCE   
         "802.1ag clause 12.14.7.1.3:aa  20.2.3"
    ::= { extendAluCfmMepOamCtlEntry  22 }

extendAluCfmMepOamCtlLbrBitErrorRatio	OBJECT-TYPE
    SYNTAX	INTEGER
    ACCESS	read-only
    STATUS	mandatory
    DESCRIPTION
	"The bit error ratio measured between the Test TLVs send out with 
	 LBM versus the Test TLVs received through LBR. A BER falls 
	 traditionally in the range (0..1), the INTEGER value is this range 
	 multiplied by a constant. An extra division by this constant is required 
         in order to restore the INTEGER value to the original range.
	ALCATEL NOTE:
	   ACCESS:      NA             USAGE:       NA
           PERSIST:     NO             INSRVMOD:    NA
           RANGE:       (0..100000000) DEFVALUE:    NA
           UNITS:       10^(-8)        SPARSE:      NA
           DESCR:
             Only applicable for extendAluCfmMepOamCtlTestType ucLbm and 
	     extendAluCfmMepOamCtlLbmTlvType testTLV, otherwise value 0. 
	     To be interpreted w.r.t. extendAluCfmMepOamCtlTransmitLbmMessages.
	     The constant used for the calculations is 10^8. An extra division
             by 10^8 is required to restore the INTEGER value to the original
             range. An extra division by 10^6 is required to express the bit
             error ratio as a percentage.
             If there are missing LBRs w.r.t. the amount of LBMs transmitted,
             then these missing LBRs will be excluded from the bit error ratio
             calculations.
	     This object is not supported."
    REFERENCE
	 "ITU-T Y.1731 clause 9.3.2"
    ::= { extendAluCfmMepOamCtlEntry 23 }

extendAluCfmMepOamCtlLbrCrcError	OBJECT-TYPE
    SYNTAX	Counter
    ACCESS      read-only
    STATUS	mandatory
    DESCRIPTION		
	"Counter indicating whether the CRC for the Test TLVs received through LBR 
	 are invalid. For each Test TLV send out, the counter value is increased if
	 a fault was detected.
	ALCATEL NOTE:
	   ACCESS:      NA            USAGE:       NA
           PERSIST:     NO            INSRVMOD:    NA
           RANGE:       NA            DEFVALUE:    NA
           UNITS:       NA            SPARSE:      NA
           DESCR:
              Only applicable for: 
	      extendAluCfmMepOamCtlTestType ucLbm and
	      extendAluCfmMepOamCtlTransmitLbmTestBitPattern allZerosCrc, prbsCrc,
	      allOnesCrc and 
	      extendAluCfmMepOamCtlLbmTlvType testTLV, otherwise value 0.
              To be interpreted w.r.t. extendAluCfmMepOamCtlTransmitLbmMessages.
              This object is not supported."
    REFERENCE
	 "ITU-T Y.1731 clause 9.3.2"
    ::= { extendAluCfmMepOamCtlEntry 24 }	

extendAluCfmMepOamCtlUnexpLtrIn		OBJECT-TYPE
    SYNTAX	Counter
    ACCESS	read-only
    STATUS	mandatory
    DESCRIPTION
	"The total number of unexpected LTRs received during the duration of
	of the LTM test.
	ALCATEL NOTE:
	   ACCESS:      NA            USAGE:       NA
           PERSIST:     NO            INSRVMOD:    NA
           RANGE:       NA            DEFVALUE:    NA
           UNITS:       NA            SPARSE:      NA
           DESCR:
              Only applicable for extendAluCfmMepOamCtlTestType ltm,
	      otherwise value 0." 
    REFERENCE
	"802.1q clause 20.44.1"
    ::= { extendAluCfmMepOamCtlEntry 25 }

extendAluCfmMepOamCtlValidResults  OBJECT-TYPE
    SYNTAX      Counter
    ACCESS      read-only
    STATUS      mandatory
    DESCRIPTION 
      "Total number of valid replies received
       for test extendAluCfmMepOamCtlTestIndex.
       Valid means that protocol interpretation of reply is present
       in corresponding result table.
      ALCATEL NOTE:
        ACCESS:      NA            USAGE:       NA
        PERSIST:     NO            INSRVMOD:    NA
        RANGE:       NA            DEFVALUE:    NA
        UNITS:       NA            SPARSE:      NA
        DESCR:
          For extendAluCfmMepOamCtlTestType ucLbm results are in this table.
          For extendAluCfmMepOamCtlTestType mcLbm,
          results are in extendAluCfmMepMcLbrTable.
          For extendAluCfmMepOamCtlTestType ltm, 
          results are in extendAluCfmLtrTable and this table.
          Valid keys in result table are:
          extendAluCfmMepOamCtlTestIndex.1 up and including
          extendAluCfmMepOamCtlTestIndex.extendAluCfmMepOamCtlValidResults."
     REFERENCE   
         "802.1ag clause 12.14.7.1.3:y and 20.31.1"
    ::= { extendAluCfmMepOamCtlEntry  26 }

extendAluCfmMepOamCtlRowStatus OBJECT-TYPE
    SYNTAX      RowStatus
    ACCESS      read-write
    STATUS      mandatory
    DESCRIPTION 
        "The status of the row.
         Activation of an oam operation of type
         extendAluCfmMepOamCtlTestType is controlled
         by changing this object's value to create&go(4).
         This RowStatus replaces dot1agCfmMepTransmitLbmResultOK.
         The values for configuration objects required for the type of
         test specified in extendAluCfmMepOamCtlTestType MUST be specified
         prior in order to get a transition to active(1) state.
         Deletion of an entry in this table results in deleting all corresponding
         test results.        
         ALCATEL NOTE:
                ACCESS:     NA       USAGE:      MAND 
                PERSIST:    NO       INSRVMOD:   YES
                RANGE:      1|4|6    DEFVALUE:   NA
                UNITS:      NA       SPARSE:     NA
                DESCR:      NA"
    ::= { extendAluCfmMepOamCtlEntry 27 }

extendAluCfmMepOamCtlLbrBitError OBJECT-TYPE
    SYNTAX     Counter
    ACCESS     read-only
    STATUS     mandatory
    DESCRIPTION
        "The total number of loopback replies with bit errors received
     ALCATEL NOTE:
           ACCESS:      NA            USAGE:       NA
           PERSIST:     NO            INSRVMOD:    NA
           RANGE:       NA            DEFVALUE:    NA
           UNITS:       NA            SPARSE:      NA
           DESCR:
              Only applicable for: extendAluCfmMepOamCtlTestType ucLbm
              and extendAluCfmMepOamCtlTransmitLbmTlvType testTlv.
              This object is not supported.
          "
   ::= { extendAluCfmMepOamCtlEntry 28 }


-- ***********************************************************************
--     CFM MEP MC LBRTable
-- ***********************************************************************
extendAluCfmMepMcLbrTable OBJECT-TYPE
        SYNTAX SEQUENCE OF ExtendAluCfmMepMcLbrEntry
        ACCESS not-accessible
        STATUS mandatory
        DESCRIPTION
          "This table contains the results of Mc LBM tests.
          More specifically, it contains one or multiple results 
          (amount of results can be read in extendAluCfmMepOamCtlValidResults)
          for each MC LBM operation.
          The availability of results can be monitored via the value
          of extendAluCfmMepOamCtlResult.
          All results of a MC LBM operation are updated at once
          when it indicates done.
          Entries in this table are cleared when
          corresponding MC LBM test  
          in extendAluCfmMepOamCtlTable is cleared. 
		  This table is not supported in ISAM.
        ALCATEL NOTE:
         TABLESIZE: N/A
         DESCR: ISAM supports 16 MC LBM operations in progress,
                multiplied by amount of peer MEPS"

        ::= { extendAluCfmMIB 8 }

extendAluCfmMepMcLbrEntry OBJECT-TYPE
    SYNTAX      ExtendAluCfmMepMcLbrEntry
    ACCESS      not-accessible
    STATUS      mandatory
    DESCRIPTION 
        "The Mc Loopback Reply table entry."
    INDEX       { extendAluCfmMepOamCtlTestIndex, extendAluCfmMepMcLbrReplyNumber}
    ::= { extendAluCfmMepMcLbrTable 1 }

ExtendAluCfmMepMcLbrEntry ::= SEQUENCE {
    extendAluCfmMepMcLbrReplyNumber         Counter,
    extendAluCfmMepMcLbrMdIndex             Gauge, 
    extendAluCfmMepMcLbrMaIndex             Gauge, 
    extendAluCfmMepMcLbrMepIdentifier       Dot1agCfmMepId, 
    extendAluCfmMepMcLbrMacAddress          MacAddress
}

extendAluCfmMepMcLbrReplyNumber  OBJECT-TYPE
    SYNTAX      Counter
    ACCESS      not-accessible
    STATUS      mandatory
    DESCRIPTION 
        "An index to distinguish among multiple LBRs on one MC LBM.
         This number is assigned sequentially from 1,
         in the order that the Loopback Initiator received the LBRs,
         up to and including extendAluCfmMepOamCtlValidResults.
         ALCATEL NOTE:
            ACCESS:      NA            USAGE:       NA
            PERSIST:     NO            INSRVMOD:    NA
            RANGE:       NA            DEFVALUE:    NA
            UNITS:       NA            SPARSE:      NA
            DESCR:"
     REFERENCE   
         "ITU-T Y.1731 7.2.2.3"
    ::= {extendAluCfmMepMcLbrEntry  1 }

extendAluCfmMepMcLbrMdIndex  OBJECT-TYPE
    SYNTAX      Gauge (1..4294967295)
    ACCESS      read-only
    STATUS      mandatory
    DESCRIPTION 
      "This is the Maintenance Domain index of the MEP initiating the LBM.
       
       ALCATEL NOTE:
         ACCESS:     NA       USAGE:      NA
         PERSIST:    NO       INSRVMOD:   NA
         RANGE:      NA       DEFVALUE:   NA
         UNITS:      NA       SPARSE:     NA
         DESCR:      NA"
    ::= {extendAluCfmMepMcLbrEntry  2 }

extendAluCfmMepMcLbrMaIndex OBJECT-TYPE
    SYNTAX      Gauge (1..4294967295)
    ACCESS      read-only
    STATUS      mandatory
    DESCRIPTION 
      "This is the Maintenance Association index of the MEP initiating the LBM.
      
       ALCATEL NOTE:
         ACCESS:     NA       USAGE:      NA
         PERSIST:    NO       INSRVMOD:   NA
         RANGE:      NA       DEFVALUE:   NA
         UNITS:      NA       SPARSE:     NA
         DESCR:      NA"
    ::= {extendAluCfmMepMcLbrEntry  3 }

extendAluCfmMepMcLbrMepIdentifier OBJECT-TYPE
    SYNTAX      Dot1agCfmMepId
    ACCESS      read-only
    STATUS      mandatory
    DESCRIPTION 
      "This is the MEP Identifier of the MEP initiating the LBM.
      ALCATEL NOTE:
        ACCESS:     NA       USAGE:      NA
        PERSIST:    NO       INSRVMOD:   NA
        RANGE:      NA       DEFVALUE:   NA
        UNITS:      NA       SPARSE:     NA
        DESCR:      NA"
     ::= {extendAluCfmMepMcLbrEntry  4 }

extendAluCfmMepMcLbrMacAddress OBJECT-TYPE
    SYNTAX      MacAddress
    ACCESS      read-only
    STATUS      mandatory
    DESCRIPTION 
        "MAC address of the peer MEP that sent the LBR message.
         ALCATEL NOTE:
           ACCESS:     NA       USAGE:      NA
           PERSIST:    NO       INSRVMOD:   NA
           RANGE:      NA       DEFVALUE:   NA
           UNITS:      NA       SPARSE:     NA
           DESCR:      "
     REFERENCE   
         "TR-101 R-287"
    ::= { extendAluCfmMepMcLbrEntry   5}

-- ***********************************************************************
--     CFM MEP Linktrace Reply Table 
-- ***********************************************************************
extendAluCfmMepLtrTable OBJECT-TYPE
    SYNTAX      SEQUENCE OF ExtendAluCfmMepLtrEntry
    ACCESS      not-accessible
    STATUS      mandatory
    DESCRIPTION 
        "This table contains a list of
         Linktrace replies received by a specific MEP in response to
         a linktrace message.
	 More specifically, it contains one or multiple results (amount
	 of results can be read in extendAluCfmMepOamCtlValidResults)
	 for each LTM operation. The availability of results can be 
	 monitored via the value of extendAluCfmpMepOamCtlResult. All 
	 results of a LTM operation are updated at once when it 
	 indicates done.
	 Entries in this table are cleared when corresponding LTM test
	 in extendAluCfmMepOamCtlTable is cleared.
         
        ALCATEL NOTE:
           TABLESIZE: N/A 
           DESCR:     ISAM supports 16 LTM operations in progress, multiplied 
	              by max number of hops."
    REFERENCE   
         "802.1ag clause 12.14.7.5"
    ::= { extendAluCfmMIB 9 }

extendAluCfmMepLtrEntry OBJECT-TYPE
    SYNTAX      ExtendAluCfmMepLtrEntry
    ACCESS      not-accessible
    STATUS      mandatory
    DESCRIPTION 
        "The Linktrace Reply table entry."
    INDEX       { extendAluCfmMepOamCtlTestIndex, extendAluCfmMepLtrReceiveOrder }
    ::= { extendAluCfmMepLtrTable 1 }

ExtendAluCfmMepLtrEntry ::= SEQUENCE {
    extendAluCfmMepLtrReceiveOrder          	Counter, 
    extendAluCfmMepLtrMdIndex               	Gauge, 
    extendAluCfmMepLtrMaIndex               	Gauge, 
    extendAluCfmMepLtrMepIdentifier         	Dot1agCfmMepId, 
    extendAluCfmMepLtrTtl		    	Gauge,
    extendAluCfmMepLtrForwarded		    	TruthValue,
    extendAluCfmMepLtrTerminalMep	    	TruthValue,
    extendAluCfmMepLtrLastEgressIdentifier  	OCTET STRING,
    extendAluCfmMepLtrNextEgressIdentifier  	OCTET STRING,
    extendAluCfmMepLtrRelay		    	Dot1agCfmRelayActionFieldValue,
    extendAluCfmMepLtrChassisIdSubtype	    	AluLldpChassisIdSubtype,
    extendAluCfmMepLtrChassisId		    	LldpChassisId,
    extendAluCfmMepLtrManAddressDomain	    	TDomain,
    extendAluCfmMepLtrManAddress	    	TAddress,
    extendAluCfmMepLtrIngress		    	AluDot1agCfmIngressActionFieldValue,
    extendAluCfmMepLtrIngressMac	    	MacAddress,
    extendAluCfmMepLtrIngressPortIdSubtype  	AluLldpPortIdSubtype,
    extendAluCfmMepLtrIngressPortId         	LldpPortId,
    extendAluCfmMepLtrEgress		    	AluDot1agCfmEgressActionFieldValue,
    extendAluCfmMepLtrEgressMac		    	MacAddress,
    extendAluCfmMepLtrEgressPortIdSubtype   	AluLldpPortIdSubtype,
    extendAluCfmMepLtrEgressPortId	    	LldpPortId,
    extendAluCfmMepLtrOrganizationSpecificTlv   OCTET STRING
}

extendAluCfmMepLtrReceiveOrder	OBJECT-TYPE
    SYNTAX	Counter
    ACCESS	not-accessible
    STATUS	mandatory
    DESCRIPTION
       	"An index to distinguish among multiple LTRs on one LTM. This number
	 is sequentially assigned from 1 in the order that the Linktrace
	 Initiator received the LTRs, up to and including 
	 extendAluCfmMepOamCtlValidResults.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.2:c"
    ::= { extendAluCfmMepLtrEntry 1 }

extendAluCfmMepLtrMdIndex	OBJECT-TYPE
    SYNTAX	Gauge (1..4294967295)
    ACCESS	read-only
    STATUS	mandatory
    DESCRIPTION
	"This is the Maintenance Domain index of the MEP initiating the LTM. 
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.2:a"
    ::= { extendAluCfmMepLtrEntry 2 }

extendAluCfmMepLtrMaIndex	OBJECT-TYPE
    SYNTAX	Gauge (1..4294967295)
    ACCESS	read-only
    STATUS 	mandatory
    DESCRIPTION
	"This is the Maintenance Association index of the MEP initiating
	 the LTM.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.2:a"
    ::= { extendAluCfmMepLtrEntry 3 }	

extendAluCfmMepLtrMepIdentifier	OBJECT-TYPE
    SYNTAX	Dot1agCfmMepId
    ACCESS	read-only
    STATUS	mandatory
    DESCRIPTION
	"This is the Maintenance association End Point identifier of the MEP
	initiating the LTM.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.2:a"
    ::= { extendAluCfmMepLtrEntry 4 }

extendAluCfmMepLtrTtl		OBJECT-TYPE
    SYNTAX	Gauge (0..255)
    ACCESS	read-only
    STATUS	mandatory
    DESCRIPTION
	"TTL field value for a returned LTR.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.3:b and clause 20.41.2.2"
    ::= { extendAluCfmMepLtrEntry 5 }

extendAluCfmMepLtrForwarded	OBJECT-TYPE
    SYNTAX	TruthValue
    ACCESS	read-only
    STATUS	mandatory
    DESCRIPTION
	"Boolean value which indicates if a LTM was forwarded 
	 by the responding MP, as returned in the 'FwdYes' flag 
	 of the flags field.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.3:c and clause 20.41.2.1"
    ::= { extendAluCfmMepLtrEntry 6 }

extendAluCfmMepLtrTerminalMep	OBJECT-TYPE
    SYNTAX	TruthValue
    ACCESS	read-only
    STATUS	mandatory
    DESCRIPTION
	"Boolean value which indicates if a LTM reached a MEP
	 enclosing its MA, as returned in the 'TerminalMEP' flag of
	 the flags fields.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.3:d and clause 20.41.2.1"
    ::= { extendAluCfmMepLtrEntry 7 }

extendAluCfmMepLtrLastEgressIdentifier	OBJECT-TYPE
    SYNTAX	OCTET STRING (SIZE(8))
    ACCESS	read-only
    STATUS	mandatory
    DESCRIPTION
	"An octet field holding the Last Egress Identifier returned
	 in the LTR Egress Identifier TLV of the LTR. This identifier
	 identifies the MEP Linktrace Initiator that originated, or the
	 Linktrace Responder that forwarded, the LTM to which this LTR
	 is the response. This is the same value as the Egress Identifier
	 TLV of that LTM.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.3:e and clause 20.41.2.3"
    ::= { extendAluCfmMepLtrEntry 8 }

extendAluCfmMepLtrNextEgressIdentifier	OBJECT-TYPE
    SYNTAX	OCTET STRING (SIZE(8))
    ACCESS	read-only
    STATUS	mandatory
    DESCRIPTION
	"An octet field holding the Next Egress Identifier returned
	 in the LTR Egress Identifier TLV of the LTR. This identifier
	 identifies the Linktrace Responder that transmitted this LTR, 
	 and can forward the LTM to the next hop. This is the same value
	 as the Egress Identifier TLV of the forwarded LTM, if any.
	 If the 'FwdYes' bit of the flags field is false, then the
	 contents of this field are undefined, i.e. any value can be
	 transmitted, and the field is ignored by the receiver.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.3:f and clause 20.41.2.4"
    ::= { extendAluCfmMepLtrEntry 9 }

extendAluCfmMepLtrRelay		OBJECT-TYPE
    SYNTAX	Dot1agCfmRelayActionFieldValue
    ACCESS	read-only
    STATUS	mandatory
    DESCRIPTION
	"Value returned in the Relay Action field.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.3:g and clause 20.41.2.5"
    ::= { extendAluCfmMepLtrEntry 10 }

extendAluCfmMepLtrChassisIdSubtype	OBJECT-TYPE
    SYNTAX	AluLldpChassisIdSubtype
    ACCESS	read-only
    STATUS	mandatory
    DESCRIPTION
	"This object specifies the format of the Chassis ID returned
	 in the Sender ID TLV of the LTR, if present. This value is 
	 meaningless if extendAluCfmMepLtrChassisId has a length of 0.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.3:h and clause 21.5.3.2
	 802.1ab clause 8.5.2.2"
    ::= { extendAluCfmMepLtrEntry 11 }

extendAluCfmMepLtrChassisId	OBJECT-TYPE
    SYNTAX	LldpChassisId
    ACCESS	read-only
    STATUS	mandatory
    DESCRIPTION
	"The Chassis ID returned in the Sender ID TLV of the LTR, if
	 present. The format of this object is determined by the value
	 of extendAluCfmMepLtrChassisIdSubtype.
	ALCATEL NOTE:
	      ACCESS:     NA                         USAGE:      NA
          PERSIST:    NO                         INSRVMOD:   NA
          RANGE:      OCTET STRING (SIZE(0..16)) DEFVALUE:   NA
          UNITS:      bytes                      SPARSE:     NA
          DESCR:      NA"
    REFERENCE
	"802.1q clause 12.14.7.5.3:i and clause 21.5.3.3
	 802.1ab clause 8.5.2.3"
    ::= { extendAluCfmMepLtrEntry 12 }

extendAluCfmMepLtrManAddressDomain	OBJECT-TYPE
    SYNTAX	TDomain
    ACCESS	read-only
    STATUS	mandatory
    DESCRIPTION
	"The TDomain that identifies the type and format of
         the related dot1agCfmMepDbManAddress object, used to access
         the SNMP agent of the system transmitting the LTR.  Received
         in the LTR Sender ID TLV from that system.
         
         Typical values will be one of (not all inclusive) list:
         
            snmpUDPDomain          (from SNMPv2-TM, RFC3417)
            snmpIeee802Domain      (from SNMP-IEEE802-TM-MIB, RFC4789)
         
         The value 'zeroDotZero' (from RFC2578) indicates 'no LTR
         Sender ID TLV received', in which case the related object
         extendAluCfmMepLtrManAddress must have a zero-length OCTET STRING
         as a value.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.3:j and clause 21.5.3.7"
    ::= { extendAluCfmMepLtrEntry 13 }

extendAluCfmMepLtrManAddress	OBJECT-TYPE
    SYNTAX	TAddress
    ACCESS	read-only
    STATUS	mandatory
    DESCRIPTION
	"The TAddress that can be used to access the SNMP
         agent of the system transmitting the LTR. If the 
	 related object extendAluCfmMepLtrManAddressDomain 
	 contains the value 'zeroDotZero', this object
         must have a zero-length OCTET STRING as a value.
	ALCATEL NOTE:
	  ACCESS:     NA                               USAGE:      NA
          PERSIST:    NO                           INSRVMOD:   NA
          RANGE:      OCTET STRING (SIZE (0..50))  DEFVALUE:   NA
          UNITS:      bytes                        SPARSE:     NA
          DESCR:      NA"
    REFERENCE
	"802.1q clause 12.14.7.5.3:j and clause 21.5.3.7"
    ::= { extendAluCfmMepLtrEntry 14 }

extendAluCfmMepLtrIngress	OBJECT-TYPE
    SYNTAX	AluDot1agCfmIngressActionFieldValue
    ACCESS	read-only
    STATUS	mandatory
    DESCRIPTION
	"The value returned in the Ingress Action Field of the Reply
	 Ingress TLV of the LTR. The value ingNoTlv(0) indicates that
         no Reply Ingress TLV was returned in the LTM.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.3:k and clause 20.41.2.6"
    ::= { extendAluCfmMepLtrEntry 15 }

extendAluCfmMepLtrIngressMac	OBJECT-TYPE
    SYNTAX	MacAddress
    ACCESS	read-only
    STATUS	mandatory
    DESCRIPTION
	"MAC address returned in the ingress MAC address field 
	 of the Reply ingress TLV of the LTR. If the extendAluCfmMepLtrIngress
	 object contains the value ingNoTlv(0), then the contents of this
	 object are meaningless.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.3:l and clause 20.41.2.7"
    ::= { extendAluCfmMepLtrEntry 16 }

extendAluCfmMepLtrIngressPortIdSubtype	OBJECT-TYPE
    SYNTAX	AluLldpPortIdSubtype
    ACCESS	read-only
    STATUS	mandatory
    DESCRIPTION
	"Format of the value extendAluCfmMepLtrIngressPortId. If the
	 Reply Ingress TLV 'Length' field indicates a length smaller 
	 than 8, then no 'Ingress Port ID Subtype' field is present
	 in the Reply Ingress TLV. In this case, the value of this
	 object is set to 0. If the extendAluCfmMepLtrIngress object
	 contains the value ingNoTlv(0), then the contents of this
	 object are meaningless.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.3:m and clause 20.41.2.8
	 802.1ab clause 8.5.3.2"
    ::= { extendAluCfmMepLtrEntry 17 }
	
extendAluCfmMepLtrIngressPortId	OBJECT-TYPE
    SYNTAX	LldpPortId
    ACCESS	read-only
    STATUS	mandatory
    DESCRIPTION
	"The Ingress port ID, the format is determined by the value
	 of extendAluCfmMepLtrIngressPortIdSubtype. If the
	 Reply Ingress TLV 'Length' field indicates a length smaller 
	 than 8, then no 'Ingress Port ID' field is present
	 in the Reply Ingress TLV. In this case, the value of this
	 object is set to 0. If the extendAluCfmMepLtrIngress object
	 contains the value ingNoTlv(0), then the contents of this
	 object are meaningless.
	ALCATEL NOTE:
	  ACCESS:     NA                              USAGE:      NA
          PERSIST:    NO                          INSRVMOD:   NA
          RANGE:      OCTET STRING (SIZE(0..16))  DEFVALUE:   NA
          UNITS:      bytes                       SPARSE:     NA
          DESCR:      NA"
    REFERENCE
	"802.1q clause 12.14.7.5.3:n and clause 20.41.2.9
	 802.1ab clause 8.5.3.3"
    ::= { extendAluCfmMepLtrEntry 18 }

extendAluCfmMepLtrEgress	OBJECT-TYPE
    SYNTAX	AluDot1agCfmEgressActionFieldValue
    ACCESS	read-only
    STATUS	mandatory
    DESCRIPTION
	"The value returned in the Egress Action Field of the Reply
	 Egress TLV of the LTR. The value egrNoTlv(0) indicates that
	 no Reply Egress TLV was returned in the LTM.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.3:o and clause 20.41.2.10"
    ::= { extendAluCfmMepLtrEntry 19 }

extendAluCfmMepLtrEgressMac	OBJECT-TYPE
    SYNTAX	MacAddress
    ACCESS	read-only
    STATUS	mandatory
    DESCRIPTION
	"MAC address returned in the egress MAC address field 
	 of the Reply Egress TLV of the LTR. If the 
	 extendAluCfmMepLtrEgress object contains the value
	 egrNoTlv(0), then the contents of this object are 
	 meaningless.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.3:p and clause 20.41.2.11"
    ::= { extendAluCfmMepLtrEntry 20 }

extendAluCfmMepLtrEgressPortIdSubtype	OBJECT-TYPE
    SYNTAX	AluLldpPortIdSubtype
    ACCESS	read-only
    STATUS	mandatory
    DESCRIPTION
	"Format of the value extendAluCfmMepLtrEgressPortId. If the
	 Reply Egress TLV 'Length' field indicates a length smaller 
	 than 8, then no 'Egress Port ID Subtype' field is present
	 in the Reply Egress TLV. In this case, the value of this
	 object is set to 0. If the extendAluCfmMepLtrEgress object 
	 contains the value egrNoTlv(0), then the contents of this 
	 object are meaningless.
	ALCATEL NOTE:
	  ACCESS:     NA       USAGE:      NA
          PERSIST:    NO       INSRVMOD:   NA
          RANGE:      NA       DEFVALUE:   NA
          UNITS:      NA       SPARSE:     NA
          DESCR:      NA"
    REFERENCE
	"802.1q clause 12.14.7.5.3:q and clause 20.41.2.12
	 802.1ab clause 8.5.3.2"
    ::= { extendAluCfmMepLtrEntry 21 }
 
extendAluCfmMepLtrEgressPortId		OBJECT-TYPE
    SYNTAX	LldpPortId
    ACCESS 	read-only
    STATUS	mandatory
    DESCRIPTION
	"The Egress port ID, the format is determined by the value
	 of extendAluCfmMepLtrIngressPortIdSubtype. If the
	 Reply Egress TLV 'Length' field indicates a length smaller 
	 than 8, then no 'Egress Port ID' field is present
	 in the Reply Egress TLV. In this case, the value of this
	 object is set to 0. If the extendAluCfmMepLtrEgress object 
	 contains the value egrNoTlv(0), then the contents of this 
	 object are meaningless.
	ALCATEL NOTE:
	  ACCESS:     NA                              USAGE:      NA
          PERSIST:    NO                          INSRVMOD:   NA
          RANGE:      OCTET STRING (SIZE(0..16))  DEFVALUE:   NA
          UNITS:      bytes                       SPARSE:     NA
          DESCR:      NA"
    REFERENCE
	"802.1q clause 12.14.7.5.3:r and clause 20.41.2.13
	 clause 8.5.3.3"
    ::= { extendAluCfmMepLtrEntry 22 }

extendAluCfmMepLtrOrganizationSpecificTlv	OBJECT-TYPE
    SYNTAX	OCTET STRING
    ACCESS	read-only
    STATUS	mandatory
    DESCRIPTION
	"All Orginzation specific TLVs returned in the LTR, if any.
	 Includes all octets including and following the TLV
	 'Length' field of each TLV, concatenated together.
	ALCATEL NOTE:
	  ACCESS:     NA                              USAGE:      NA
          PERSIST:    NO                          INSRVMOD:   NA
          RANGE:      OCTET STRING (SIZE(0..7))   DEFVALUE:   NA
          UNITS:      bytes    SPARSE:     NA
          DESCR:      NA"
    REFERENCE
	"802.1q clause 12.14.7.5.3:s and clause 21.5.2"
    ::= { extendAluCfmMepLtrEntry 23 }

extendAluCfmGlobalObjects   OBJECT IDENTIFIER ::= {extendAluCfmMIB 10}
extendAluCfmSLMConfigGroup  OBJECT IDENTIFIER ::= {extendAluCfmGlobalObjects 1}


extendAluCfmPMProactiveConfigTableNextSessionIndex OBJECT-TYPE
    SYNTAX      Dot1afCfmIndexIntegerNextFree
    ACCESS      read-only
    STATUS      mandatory
    DESCRIPTION 
      "This object contains an unused value for extendAluCfmPMProactiveConfigSessionIndex 
       in the extendAluCfmPMProactiveConfigTable,or a zero to indicate that none exist.
       ALCATEL NOTE:
          ACCESS:      NA            USAGE:       NA
          PERSIST:     NO            INSRVMOD:    NA
          RANGE:       1..960        DEFVALUE:    NA
          UNITS:       NA            SPARSE:      NA
          DESCR:       NA" 
      ::= { extendAluCfmGlobalObjects 2 }

extendAluCfmSLMInactivityTimer  OBJECT-TYPE
    SYNTAX      INTEGER (10..100)
    ACCESS   read-write
    STATUS      mandatory
    DESCRIPTION
        "The value of extendAluCfmSLMInactivityTimer specifies the duration,
         in seconds, that the system will maintain Synthetic Loss Measurement
         (SLM) reply (SLR) data for individual two-way tests in the absence of
         receiving SLM frames.

         The system may be blocked in responding to new two-way SLM tests due to
         an excessive inactive timer duration. In this case, reducing this
         object's value, thus reducing the retention time for existing latent
         SLR test data, will help free test resources allowing the system to
         respond to new two-way SLM tests.
          
          ALCATEL NOTE:
	  ACCESS:     NA                          USAGE:      NA
          PERSIST:    NO                          INSRVMOD:   NA
          RANGE:      10...100                    DEFVALUE:   100
          UNITS:      seconds                     SPARSE:     NA
          DESCR:      NA"
    REFERENCE "ITU-T Y.1731 Ethernet Synthetic Frame Loss Measurement (ETH-SLM)
               Section 8.4 Note 2."
    DEFVAL {  100 }
    ::= { extendAluCfmSLMConfigGroup 1 }

extendAluCfmPMObjects OBJECT IDENTIFIER ::= {extendAluCfmMIB 11}

-- ***********************************************************************
--    Extend CFM SLM Responder Stats Table
-- ***********************************************************************
extendAluCfmSlmResponderStatsTable OBJECT-TYPE
        SYNTAX SEQUENCE OF ExtendAluCfmSlmResponderStatsEntry
        ACCESS not-accessible
        STATUS mandatory
        DESCRIPTION
                "This table contains the proprietary objects for SLM responder"
        ::= { extendAluCfmPMObjects 1 }

extendAluCfmSlmResponderStatsEntry OBJECT-TYPE
        SYNTAX ExtendAluCfmSlmResponderStatsEntry
        ACCESS not-accessible
        STATUS mandatory
        DESCRIPTION "This list contains the proprietary objects for SLM responder."
        INDEX { dot1agCfmMdIndex, dot1agCfmMaIndex, dot1agCfmMepIdentifier,
                extendAluCfmSlmResponderRemoteMepIdentifer,extendAluCfmSlmResponderRemoteMepMacAddress,
                extendAluCfmSlmResponderRemoteMepTestIdentifier }
        ::= { extendAluCfmSlmResponderStatsTable 1}

ExtendAluCfmSlmResponderStatsEntry ::=
        SEQUENCE {
               extendAluCfmSlmResponderRemoteMepIdentifer Dot1agCfmMepId,
               extendAluCfmSlmResponderRemoteMepMacAddress MacAddress,
               extendAluCfmSlmResponderRemoteMepTestIdentifier Gauge,
               extendAluCfmSlmResponderRemoteMepTxFCf Gauge,
               extendAluCfmSlmResponderTxFCb Gauge
}

extendAluCfmSlmResponderRemoteMepIdentifer OBJECT-TYPE
        SYNTAX Dot1agCfmMepId 
        ACCESS read-only
        STATUS mandatory
        DESCRIPTION
                "This is the MEP ID of the remote MEP which initiated the SLM.
         ALCATEL NOTE:
                ACCESS:     NA       USAGE:      NA
                PERSIST:    NO       INSRVMOD:   NA
                RANGE:      NA       DEFVALUE:   NA
                UNITS:      NA       SPARSE:     NA
               "
        ::={ extendAluCfmSlmResponderStatsEntry 1}

extendAluCfmSlmResponderRemoteMepMacAddress OBJECT-TYPE
       SYNTAX MacAddress
       ACCESS read-only
       STATUS mandatory
       DESCRIPTION
               "This is the MAC address of the remote MEP which initiated the SLM
         ALCATEL NOTE:
                ACCESS:     NA       USAGE:      NA
                PERSIST:    NO       INSRVMOD:   NA
                RANGE:      NA       DEFVALUE:   NA
                UNITS:      NA       SPARSE:     NA"
       ::={ extendAluCfmSlmResponderStatsEntry 2}

extendAluCfmSlmResponderRemoteMepTestIdentifier OBJECT-TYPE
        SYNTAX Gauge (1..4294967295)
        ACCESS read-only
        STATUS mandatory
        DESCRIPTION 
                "This test identifier in the SLM message sent by the remote MEP.
         ALCATEL NOTE:
                ACCESS:     NA       USAGE:      NA
                PERSIST:    NO      INSRVMOD:   NA
                RANGE:      NA       DEFVALUE:   NA
                UNITS:      NA       SPARSE:     NA"
        ::={ extendAluCfmSlmResponderStatsEntry 3}

extendAluCfmSlmResponderRemoteMepTxFCf OBJECT-TYPE
        SYNTAX Gauge (1..4294967295)
        ACCESS read-only
        STATUS mandatory
        DESCRIPTION 
                 " The number of synthetic frames(SLM) transmitted by the SLM 
                   initiator as part of a given test ID.The value is obtained 
                   from the SLM packet sent by the initiator.
         ALCATEL NOTE:
                ACCESS:     NA       USAGE:      NA
                PERSIST:    NO      INSRVMOD:   NA
                RANGE:      NA       DEFVALUE:   NA
                UNITS:      NA       SPARSE:     NA"
        ::={ extendAluCfmSlmResponderStatsEntry 4}

extendAluCfmSlmResponderTxFCb OBJECT-TYPE
        SYNTAX Gauge (1..4294967295)
        ACCESS read-only
        STATUS mandatory
        DESCRIPTION 
                " The number of synthetic frames(SLR) transmitted by the SLM 
                  responder as part of a given test ID.The value is a local counter 
                  maintained by the responder.
         ALCATEL NOTE:
                ACCESS:     NA       USAGE:      NA
                PERSIST:    NO      INSRVMOD:   NA
                RANGE:      NA       DEFVALUE:   NA
                UNITS:      NA       SPARSE:     NA"

         REFERENCE "ITU-T Y.1731 Ethernet Synthetic Frame Loss Measurement (ETH-SLM)
               Section 8.4"

        ::={ extendAluCfmSlmResponderStatsEntry 5}

--
-- MEP Synthetic Loss Measurement Test Config Table
--
extendAluCfmSlmInitiatorOnDemandTestTable   OBJECT-TYPE
    SYNTAX      SEQUENCE OF ExtendAluCfmSlmInitiatorOnDemandTestEntry
    ACCESS      not-accessible
    STATUS      mandatory
    DESCRIPTION
        "This table is for initating and viewing results of on demand Synthetic Loss Measurement tests.
         Steps to initiate on demand SLM test
         ====================================
         Pre-requisites
         ==============
         1)extendAluCfmPmMepSlmSingleEndedInitiator must be set to 'true' for the MEP from which
         the on-demand SLM test has to be initiated.
	 2)LT should be reachable when initiating the SLM on-demand test.
         
         Steps
         =====
         1) Create an entry in this table with a valid unicast MAC address as the 
            remote MEP MAC address.
         2) Optionally specify interval,timeout,data size and number of packets to send
         3) The Test status will be in-progress if the test has been successfully initiated. 
            The time taken for the test depends on the timeout,sendcount and the interval.          
            Wait till the test completion time ( ((sendcount-1) *interval) + timeout + 3 sec).
         4) Wait for the test status to change to 'done'. Then read the values of in loss,out loss
            and unacknowledged packets.
         Note:
         1) If the test status is 'failed' it means that the test was not successfully completed 
         2) The values of interval,timeout,datasize and sendcount cannot be modified after row creation
         ALCATEL-NOTE - TABLESIZE 16 "
    REFERENCE "ITU-T Y.1731 Ethernet Synthetic Frame Loss Measurement (ETH-SLM)"
    ::= { extendAluCfmPMObjects 2 }

extendAluCfmSlmInitiatorOnDemandTestEntry   OBJECT-TYPE
    SYNTAX      ExtendAluCfmSlmInitiatorOnDemandTestEntry
    ACCESS      not-accessible
    STATUS      mandatory
    DESCRIPTION
        "An entry in this table contains the configuration and results
         for on demand single-ended two-way Synthetic Loss Measurement (SLM) Tests. "
    INDEX {
              dot1agCfmMdIndex,
              dot1agCfmMaIndex,
              dot1agCfmMepIdentifier,
              extendAluCfmSlmInitiatorOnDemandRemoteMepMacAddress
          }

    ::= { extendAluCfmSlmInitiatorOnDemandTestTable 1 }

ExtendAluCfmSlmInitiatorOnDemandTestEntry   ::= SEQUENCE {
--Test Input
    extendAluCfmSlmInitiatorOnDemandRemoteMepMacAddress  MacAddress,
    extendAluCfmSlmInitiatorOnDemandPriority             INTEGER,
    extendAluCfmSlmInitiatorOnDemandInterval             INTEGER,
    extendAluCfmSlmInitiatorOnDemandTimeout              INTEGER,
    extendAluCfmSlmInitiatorOnDemandDataSize             INTEGER,
    extendAluCfmSlmInitiatorOnDemandSendCount            INTEGER,
--Test Result
    extendAluCfmSlmInitiatorOnDemandTestStatus           INTEGER,
    extendAluCfmSlmInitiatorOnDemandTestId               Gauge,
    extendAluCfmSlmInitiatorOnDemandRemoteMepId          Dot1agCfmMepIdOrNA,
    extendAluCfmSlmInitiatorOnDemandSlmPacketOut         Counter,
    extendAluCfmSlmInitiatorOnDemandSlrPacketIn          Counter, 
    extendAluCfmSlmInitiatorOnDemandLossIn  	         INTEGER, 
    extendAluCfmSlmInitiatorOnDemandLossOut 	         INTEGER,
    extendAluCfmSlmInitiatorOnDemandUnack   	         INTEGER,
    extendAluCfmSlmInitiatorOnDemandLastTxSeqF           Counter,    
--Row creation/Test initiation
    extendAluCfmSlmInitiatorOnDemandRowStatus            RowStatus
}

extendAluCfmSlmInitiatorOnDemandRemoteMepMacAddress  OBJECT-TYPE
    SYNTAX      MacAddress
    ACCESS      read-write
    STATUS      mandatory
    DESCRIPTION
        "The value of this object specifies the MAC address  
         used as a target for the two-way Synthetic Loss Measurement (SLM) test.

         This object MUST be set to a valid unicast MAC Address for proper execution of
         the two-way SLM test.
		ALCATEL NOTE:
         ACCESS:     NA       USAGE:      NA
         PERSIST:    NO       INSRVMOD:   NA
         RANGE:      NA       DEFVALUE:   NA
         UNITS:      NA       SPARSE:     NA
         DESCR:      NA"
    ::= { extendAluCfmSlmInitiatorOnDemandTestEntry 1 }

extendAluCfmSlmInitiatorOnDemandPriority   OBJECT-TYPE
    SYNTAX     INTEGER (0..7)
    ACCESS     read-write
    STATUS     mandatory
    DESCRIPTION
        "The value of this object specifies the priority used
         in the generated test frame for the two-way Synthetic Loss Measurement
         (SLM) test.
		ALCATEL NOTE:
         ACCESS:     NA       USAGE:      NA
         PERSIST:    NO       INSRVMOD:   NA
         RANGE:      NA       DEFVALUE:   NA
         UNITS:      NA       SPARSE:     NA
         DESCR:      NA"
    DEFVAL { 7 }
	::= { extendAluCfmSlmInitiatorOnDemandTestEntry 2 }

extendAluCfmSlmInitiatorOnDemandInterval OBJECT-TYPE
    SYNTAX      INTEGER (1..10)
    ACCESS  read-write
    STATUS      mandatory
    DESCRIPTION
        "The value of this object specifies 
	 the interval in seconds between Synthetic Loss Measurement (SLM) messages sent 
	 by the two-way SLM test.

	ALCATEL NOTE:
         ACCESS:     NA       USAGE:      NA
         PERSIST:    NO       INSRVMOD:   NA
         RANGE:      NA       DEFVALUE:   NA
         UNITS:      seconds  SPARSE:     NA
         DESCR:      NA"
    DEFVAL { 5 }
    ::= { extendAluCfmSlmInitiatorOnDemandTestEntry 3 }

extendAluCfmSlmInitiatorOnDemandTimeout     OBJECT-TYPE
    SYNTAX      INTEGER (5..10)
    ACCESS      read-write
    STATUS      mandatory
    DESCRIPTION
        "The value of this object specifies the time-out value,
         in seconds, to wait for a Synthetic Loss Measurement Reply (SLR) message 
         for each SLM message in the two-way SLM test. Upon expiration of the timeout period,
         the MEP assumes that the message response will not be received. Any
         response received after the timeout period has expired is silently
         discarded.
		ALCATEL NOTE:
         ACCESS:     NA       USAGE:      NA
         PERSIST:    NO       INSRVMOD:   NA
         RANGE:      NA       DEFVALUE:   NA
         UNITS:      seconds  SPARSE:     NA
         DESCR:      NA"
    DEFVAL { 5 }
    ::= { extendAluCfmSlmInitiatorOnDemandTestEntry 4 }

extendAluCfmSlmInitiatorOnDemandDataSize    OBJECT-TYPE
    SYNTAX      INTEGER (0..1500)
    ACCESS      read-write
    STATUS      mandatory
    DESCRIPTION
        "The value of this object specifies the data size,
         in bytes, contained in the padding TLV for the two-way Synthetic Loss
         Measurement (SLM) test. A value of zero (0) specifies that no padding
         TLV is inserted in the SLM packet. Any non-zero value will increase
         the packet size by the specified data size plus 3 bytes for the TLV
         header.
		ALCATEL NOTE:
         ACCESS:     NA       USAGE:      NA
         PERSIST:    NO       INSRVMOD:   NA
         RANGE:      NA       DEFVALUE:   NA
         UNITS:      bytes    SPARSE:     NA
         DESCR:      NA"
    DEFVAL { 0 }
    ::= { extendAluCfmSlmInitiatorOnDemandTestEntry 5 }

extendAluCfmSlmInitiatorOnDemandSendCount   OBJECT-TYPE
    SYNTAX      INTEGER(1..100)
    ACCESS  read-write
    STATUS      mandatory
    DESCRIPTION
        "The value of this object specifies the number of
         Synthetic Loss Measurement (SLM) packets to send during the two-way
         SLM test.
		ALCATEL NOTE:
         ACCESS:     NA       USAGE:      NA
         PERSIST:    NO       INSRVMOD:   NA
         RANGE:      NA       DEFVALUE:   NA
         UNITS:      packets  SPARSE:     NA
         DESCR:      NA"
    DEFVAL { 1 }
    ::= { extendAluCfmSlmInitiatorOnDemandTestEntry 6 }

extendAluCfmSlmInitiatorOnDemandTestStatus OBJECT-TYPE
    SYNTAX  INTEGER {
                      done(1),
                      inProgress(2),
		      failed(3)
    }
    ACCESS      read-only
    STATUS      mandatory
    DESCRIPTION 
        "This object can be used to monitor the progress of the SLM test.

         done - The test is complete and the result is available in the result fields such as
                in loss, out loss , unacknowledged packets etc.
         in-progress - The test has been successfully initiated.
         failed -  The test could not be initiated and hence the results will not 
                    be available in the result table
     
         ALCATEL NOTE:
            ACCESS:      NA            USAGE:       NA
            PERSIST:     NO            INSRVMOD:    NA
            RANGE:       NA            DEFVALUE:    NA
            UNITS:       NA            SPARSE:      NA"
   ::= { extendAluCfmSlmInitiatorOnDemandTestEntry 7 }

extendAluCfmSlmInitiatorOnDemandTestId      OBJECT-TYPE
    SYNTAX      Gauge 
    ACCESS      read-only
    STATUS      mandatory
    DESCRIPTION
        "The value of this object indicates the test identifier
         used in the two-way Synthetic Loss Measurement (SLM) message.
	 
        ALCATEL NOTE:
         ACCESS:     NA       USAGE:      NA
         PERSIST:    NO       INSRVMOD:   NA
         RANGE:      NA       DEFVALUE:   NA
         UNITS:      NA       SPARSE:     NA
         DESCR:      NA"
    ::= { extendAluCfmSlmInitiatorOnDemandTestEntry 8 }

extendAluCfmSlmInitiatorOnDemandRemoteMepId   OBJECT-TYPE
    SYNTAX      Dot1agCfmMepIdOrNA
    ACCESS      read-only
    STATUS      mandatory
    DESCRIPTION
        "The value of this object indicates the MEP 
         Identifier of the remote node corresponding to the 
         extendAluCfmSlmInitiatorOnDemandRemoteMepMacAddress
         from which the Synthetic Loss Measurement Reply (SLR) is received.
		ALCATEL NOTE:
         ACCESS:     NA       USAGE:      NA
         PERSIST:    NO       INSRVMOD:   NA
         RANGE:      NA       DEFVALUE:   NA
         UNITS:      NA       SPARSE:     NA
         DESCR:      NA"    
    ::= { extendAluCfmSlmInitiatorOnDemandTestEntry 9 }

extendAluCfmSlmInitiatorOnDemandSlmPacketOut     OBJECT-TYPE
    SYNTAX      Counter
    ACCESS      read-only
    STATUS      mandatory
    DESCRIPTION
        "The value of this object indicates the actual number of
         SLM packets sent during the execution of the test.
		ALCATEL NOTE:
         ACCESS:     NA       USAGE:      NA
         PERSIST:    NO       INSRVMOD:   NA
         RANGE:      NA       DEFVALUE:   NA
         UNITS:      packets  SPARSE:     NA
         DESCR:      NA"
    ::= { extendAluCfmSlmInitiatorOnDemandTestEntry 10 }

extendAluCfmSlmInitiatorOnDemandSlrPacketIn      OBJECT-TYPE
    SYNTAX      Counter
    ACCESS      read-only
    STATUS      mandatory
    DESCRIPTION
        "The value of this object indicates the number of
         SLR packets received during the execution of the test.
		ALCATEL NOTE:
         ACCESS:     NA       USAGE:      NA
         PERSIST:    NO       INSRVMOD:   NA
         RANGE:      NA       DEFVALUE:   NA
         UNITS:      packets  SPARSE:     NA
         DESCR:      NA"
    ::= { extendAluCfmSlmInitiatorOnDemandTestEntry 11 }

extendAluCfmSlmInitiatorOnDemandLossIn		OBJECT-TYPE
    SYNTAX      INTEGER
    ACCESS      read-only
    STATUS      mandatory
    DESCRIPTION
        "The value of this object indicates the number of
         packets transmitted from the remote node but not received on the local
         node during the execution of the test.
		ALCATEL NOTE:
         ACCESS:     NA       USAGE:      NA
         PERSIST:    NO       INSRVMOD:   NA
         RANGE:      NA       DEFVALUE:   NA
         UNITS:      packets  SPARSE:     NA
         DESCR:      NA"
    ::= { extendAluCfmSlmInitiatorOnDemandTestEntry 12 }

extendAluCfmSlmInitiatorOnDemandLossOut OBJECT-TYPE
    SYNTAX      INTEGER
    ACCESS     read-only
    STATUS      mandatory
    DESCRIPTION
        "The value of this object indicates the number of
         packets transmitted from the local node but not received on the remote
         node during the execution of the test.
		ALCATEL NOTE:
         ACCESS:     NA       USAGE:      NA
         PERSIST:    NO       INSRVMOD:   NA
         RANGE:      NA       DEFVALUE:   NA
         UNITS:      packets  SPARSE:     NA
         DESCR:      NA"
    ::= { extendAluCfmSlmInitiatorOnDemandTestEntry 13 }

extendAluCfmSlmInitiatorOnDemandUnack   OBJECT-TYPE
    SYNTAX      INTEGER 
    ACCESS      read-only
    STATUS      mandatory
    DESCRIPTION
        "The value of this object indicates the number of
         unacknowledged packets during the execution of the test.

	 ALCATEL NOTE:
         ACCESS:     NA       USAGE:      NA
         PERSIST:    NO       INSRVMOD:   NA
         RANGE:      NA       DEFVALUE:   NA
         UNITS:      packets  SPARSE:     NA
         DESCR:      NA"
    ::= { extendAluCfmSlmInitiatorOnDemandTestEntry 14 }

extendAluCfmSlmInitiatorOnDemandLastTxSeqF    OBJECT-TYPE
    SYNTAX      Counter
    ACCESS      read-only
    STATUS      mandatory
    DESCRIPTION
        "The value of this object indicates the last
         received sequence number on the local node, transmitted by the
         remote node.
		ALCATEL NOTE:
         ACCESS:     NA       USAGE:      NA
         PERSIST:    NO       INSRVMOD:   NA
         RANGE:      NA       DEFVALUE:   NA
         UNITS:      NA       SPARSE:     NA
         DESCR:      NA"
    ::= { extendAluCfmSlmInitiatorOnDemandTestEntry 15 }

extendAluCfmSlmInitiatorOnDemandRowStatus OBJECT-TYPE
      SYNTAX RowStatus
      ACCESS read-write
      STATUS mandatory
      DESCRIPTION
                "This is the row status. A set to 'createAndGo' with a valid value for
                 extendAluCfmSlmInitiatorOnDemandRemoteMepMacAddress will result in 
                 the state transition to 'active' and the SLM test will be initiated.The value of
                 extendAluCfmSlmInitiatorOnDemandTestStatus will be set to 'in-progress'.

                 The result of the test can be obtained from extendAluCfmSlmInitiatorOnDemandTestStatus
         ALCATEL NOTE:
                ACCESS:     NA       USAGE:      NA
                PERSIST:    NA       INSRVMOD:   NA
                RANGE:      1,4,6    DEFVALUE:   NA
                UNITS:      NA       SPARSE:     NA"
      ::={ extendAluCfmSlmInitiatorOnDemandTestEntry 16}


--
-- MEP Loss Measurement Test Config Table
--
extendAluCfmLmInitiatorOnDemandTestTable   OBJECT-TYPE
    SYNTAX      SEQUENCE OF ExtendAluCfmLmInitiatorOnDemandTestEntry
    ACCESS      not-accessible
    STATUS      mandatory
    DESCRIPTION
        "This table is for initating and viewing results of on demand  Loss Measurement tests. 
         Steps to initiate on demand Lm test 
         ====================================
         Pre-requisites 
         ============== 
         1)extendAluCfmPmMepLmSingleEndedInitiator must be set to 'enablePerVlan' 
           or 'enablePerVlanPerPbit' for the MEP from which the on-demand Lm test 
           has to be initiated. 

	     2)LT should be reachable when initiating the Lm on-demand test.
         
         Steps
         =====
         1) Create an entry in this table with a valid unicast MAC address as the 
            remote MEP MAC address.
         2) Optionally specify interval,priority and number of packets to send
         3) The Test status will be in-progress if the test has been successfully initiated.             
		    The duration of the test depends on the sendcount and interval
         4) Wait till the test completion time ( ((sendcount-1) *interval) + 5sec).
         5) Then read the test status 
              if status is done read the near-end loss/far-end loss
              else the test has not succeeded.
            
         Note:
         1) If the test status is 'failed' it means that the test was not successfully completed 
         2) The values of interval ,sendcount and priority cannot be modified after row creation
         ALCATEL-NOTE - TABLESIZE 16 "
    REFERENCE "ITU-T Y.1731 Ethernet  Frame Loss Measurement (ETH-Lm)"
    ::= { extendAluCfmPMObjects 3 }

extendAluCfmLmInitiatorOnDemandTestEntry   OBJECT-TYPE
    SYNTAX      ExtendAluCfmLmInitiatorOnDemandTestEntry
    ACCESS      not-accessible
    STATUS      mandatory
    DESCRIPTION
        "An entry in this table contains the configuration and results
         for on demand single-ended two-way  Loss Measurement (Lm) Tests. "
    INDEX {
              dot1agCfmMdIndex,
              dot1agCfmMaIndex,
              dot1agCfmMepIdentifier,
              extendAluCfmLmInitiatorOnDemandRemoteMepMacAddress
          }

    ::= { extendAluCfmLmInitiatorOnDemandTestTable 1 }

ExtendAluCfmLmInitiatorOnDemandTestEntry   ::= SEQUENCE {
--Test Input
    extendAluCfmLmInitiatorOnDemandRemoteMepMacAddress MacAddress,
    extendAluCfmLmInitiatorOnDemandPriority            INTEGER,
    extendAluCfmLmInitiatorOnDemandInterval            INTEGER,
    extendAluCfmLmInitiatorOnDemandSendCount           INTEGER,
--Test Result
    extendAluCfmLmInitiatorOnDemandTestStatus          INTEGER,
    extendAluCfmLmInitiatorOnDemandPduSent             INTEGER,
    extendAluCfmLmInitiatorOnDemandPduReceived         INTEGER,
    extendAluCfmLmInitiatorOnDemandFramesRxNearEnd     OCTET STRING,
    extendAluCfmLmInitiatorOnDemandFramesRxFarEnd      OCTET STRING,  
    extendAluCfmLmInitiatorOnDemandFramesTxNearEnd     OCTET STRING,
    extendAluCfmLmInitiatorOnDemandFramesTxFarEnd      OCTET STRING,
    extendAluCfmLmInitiatorOnDemandFramesLossNearEnd   OCTET STRING,
    extendAluCfmLmInitiatorOnDemandFramesLossFarEnd    OCTET STRING, 
    extendAluCfmLmInitiatorOnDemandLossRatioNearEnd    ExtendAluCfmHundrethsOfPercentage, 
    extendAluCfmLmInitiatorOnDemandLossRatioFarEnd     ExtendAluCfmHundrethsOfPercentage,
    extendAluCfmLmInitiatorOnDemandPrevTxNearEnd       Counter,
    extendAluCfmLmInitiatorOnDemandPrevRxNearEnd       Counter,
    extendAluCfmLmInitiatorOnDemandPrevTxFarEnd        Counter,
    extendAluCfmLmInitiatorOnDemandPrevRxFarEnd        Counter,
    extendAluCfmLmInitiatorOnDemandCurrTxNearEnd       Counter,
    extendAluCfmLmInitiatorOnDemandCurrRxNearEnd       Counter,
    extendAluCfmLmInitiatorOnDemandCurrTxFarEnd        Counter,
    extendAluCfmLmInitiatorOnDemandCurrRxFarEnd        Counter,	
--Row creation/Test initiation
    extendAluCfmLmInitiatorOnDemandRowStatus            RowStatus
}

extendAluCfmLmInitiatorOnDemandRemoteMepMacAddress  OBJECT-TYPE
    SYNTAX      MacAddress
    ACCESS      read-write
    STATUS      mandatory
    DESCRIPTION
        "The value of this object specifies the MAC address  
         used as a target for the two-way  Loss Measurement (Lm) test.

         This object MUST be set to a valid unicast MAC Address for proper execution of
         the two-way Lm test.
		ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 1 }

extendAluCfmLmInitiatorOnDemandPriority   OBJECT-TYPE
    SYNTAX     INTEGER (0..7)
    ACCESS     read-write
    STATUS     mandatory
    DESCRIPTION
        "The value of this object specifies the priority used
         in the generated LMM PDU for the two-way  Loss Measurement
         (Lm) test.
		ALCATEL NOTE:
         ACCESS:     NA       USAGE:      NA
         PERSIST:    NO       INSRVMOD:   NA
         RANGE:      NA       DEFVALUE:   NA
         UNITS:      NA       SPARSE:     NA
         DESCR:      NA"
    DEFVAL { 7 }
	::= { extendAluCfmLmInitiatorOnDemandTestEntry 2 }

extendAluCfmLmInitiatorOnDemandInterval OBJECT-TYPE
    SYNTAX      INTEGER (1)
    ACCESS      read-write
    STATUS      mandatory
    DESCRIPTION
        "The value of this object specifies 
	 the interval in seconds between  Loss Measurement (Lm) messages sent 
	 by the two-way Lm test.

	ALCATEL NOTE:
         ACCESS:     NA       USAGE:      NA
         PERSIST:    NO       INSRVMOD:   NA
         RANGE:      NA       DEFVALUE:   NA
         UNITS:      seconds  SPARSE:     NA
         DESCR:      NA"
    DEFVAL { 1 }
    ::= { extendAluCfmLmInitiatorOnDemandTestEntry 3 }

extendAluCfmLmInitiatorOnDemandSendCount   OBJECT-TYPE
    SYNTAX      INTEGER(2..5)
    ACCESS      read-write
    STATUS      mandatory
    DESCRIPTION
        "The value of this object specifies the number of
          Loss Measurement (Lm) packets to send during the two-way
         Lm test.
		ALCATEL NOTE:
         ACCESS:     NA       USAGE:      NA
         PERSIST:    NO       INSRVMOD:   NA
         RANGE:      NA       DEFVALUE:   NA
         UNITS:      packets  SPARSE:     NA
         DESCR:      NA"
    DEFVAL { 2 }
    ::= { extendAluCfmLmInitiatorOnDemandTestEntry 4 }

extendAluCfmLmInitiatorOnDemandTestStatus OBJECT-TYPE
    SYNTAX     INTEGER {
                         done(1),
                         inProgress(2),
	                 failed(3)
                       }
    ACCESS     read-only
    STATUS     mandatory
    DESCRIPTION 
        "This object can be used to monitor the progress of the Lm test.

         done - The test is complete and the result is available in the result fields such as
                near-end loss, far-end loss etc.
         in-progress - The test has been successfully initiated.
         failed -  The test could not be initiated and hence the results will not 
                    be available in the result table
     
         ALCATEL NOTE:
            ACCESS:      NA            USAGE:       NA
            PERSIST:     NO            INSRVMOD:    NA
            RANGE:       NA            DEFVALUE:    NA
            UNITS:       NA            SPARSE:      NA"
   ::= { extendAluCfmLmInitiatorOnDemandTestEntry 5 }


extendAluCfmLmInitiatorOnDemandPduSent  OBJECT-TYPE
    SYNTAX     INTEGER
    ACCESS     read-only
    STATUS     mandatory
    DESCRIPTION
    	 "This object indicates the number of LMM PDUs sent
		 ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 6 }
    
extendAluCfmLmInitiatorOnDemandPduReceived OBJECT-TYPE
    SYNTAX      INTEGER
    ACCESS      read-only
    STATUS      mandatory
    DESCRIPTION
    	 "This object indicates the number of LMR PDUs received
		 ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 7 }
    
extendAluCfmLmInitiatorOnDemandFramesRxNearEnd   OBJECT-TYPE
    SYNTAX     OCTET STRING (SIZE(8))
    ACCESS     read-only
    STATUS     mandatory
    DESCRIPTION
        "The value of this object is the accumulated number of 
        frames received at the local service endpoint of this MEP, and within the 
        loss test duration
		ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 8 }
          
extendAluCfmLmInitiatorOnDemandFramesRxFarEnd   OBJECT-TYPE
    SYNTAX     OCTET STRING (SIZE(8))
    ACCESS     read-only
    STATUS     mandatory
    DESCRIPTION
        "The value of this object is the accumulated number of 
        frames received at the far-end service endpoint associated with 
        extendAluCfmLmInitiatorOnDemandMacAddr, and within the loss test duration.
		ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 9 }

extendAluCfmLmInitiatorOnDemandFramesTxNearEnd   OBJECT-TYPE
    SYNTAX     OCTET STRING (SIZE(8))
    ACCESS     read-only
    STATUS     mandatory
    DESCRIPTION
        "The value of this object is the accumulated number of 
        frames transmitted at the local service endpoint of this MEP, and within 
        the loss test duration.
		ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 10 }
          
extendAluCfmLmInitiatorOnDemandFramesTxFarEnd   OBJECT-TYPE
    SYNTAX     OCTET STRING (SIZE(8))
    ACCESS     read-only
    STATUS     mandatory
    DESCRIPTION
        "The value of this object is the accumulated number of 
        frames transmitted at the far-end service endpoint associated with 
        extendAluCfmLmInitiatorOnDemandMacAddr, and within the loss test duration.
		ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 11 }
    
extendAluCfmLmInitiatorOnDemandFramesLossNearEnd   OBJECT-TYPE
    SYNTAX     OCTET STRING (SIZE(8))
    ACCESS     read-only
    STATUS     mandatory
    DESCRIPTION
        "The value of this object is the accumulated number of
        loss frames at the local service endpoint of this MEP, and within the loss 
        test duration.
		ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 12 }   

extendAluCfmLmInitiatorOnDemandFramesLossFarEnd   OBJECT-TYPE
    SYNTAX     OCTET STRING (SIZE(8))
    ACCESS     read-only
    STATUS     mandatory
    DESCRIPTION
        "The value of this object is the accumulated number of 
        loss frames at the far-end service endpoint associated with       
        extendAluCfmLmInitiatorOnDemandMacAddr, and within the loss test duration.
		ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 13 }

extendAluCfmLmInitiatorOnDemandLossRatioNearEnd   OBJECT-TYPE
    SYNTAX     ExtendAluCfmHundrethsOfPercentage
    ACCESS     read-only
    STATUS     mandatory
    DESCRIPTION
        "The value of this object is the accumulated Loss Ratio, 
        at the local service endpoint of this MEP, and within the loss test 
        duration.

        extendAluCfmLmInitiatorOnDemandLossRatioNearEnd is expressed in hundredth of a percent 
        accuracy.  
        It is calculated as follows:  
        (extendAluCfmLmInitiatorOnDemandFramesLossNearEnd * 10000) / extendAluCfmLmInitiatorOnDemandFramesTxFarEnd).
        If value is 65535, it means that the percentage is invalid (greater than 100 or less than 0).
		ALCATEL NOTE:
         ACCESS:     NA       USAGE:      NA
         PERSIST:    NO       INSRVMOD:   NA
         RANGE:      0..10000 | 65535          DEFVALUE:   NA
         UNITS:      Hundreths of percentage   SPARSE:     NA
         DESCR:      NA"

    ::= { extendAluCfmLmInitiatorOnDemandTestEntry 14 }
          
extendAluCfmLmInitiatorOnDemandLossRatioFarEnd   OBJECT-TYPE
    SYNTAX     ExtendAluCfmHundrethsOfPercentage
    ACCESS     read-only
    STATUS     mandatory
    DESCRIPTION
        "The value of this object is the accumulated Loss Ratio, 
        at the far-end service endpoint associated with extendAluCfmLmInitiatorOnDemandMacAddr, 
        and within the loss test duration.
        
        extendAluCfmLmInitiatorOnDemandLossRatioFarEnd is expressed in hundredth of a percent 
        accuracy.  
        It is calculated as follows:
        (extendAluCfmLmInitiatorOnDemandFramesLossFarEnd * 10000) / extendAluCfmLmInitiatorOnDemandFramesTxNearEnd).
        If value is 65535, it means that the percentage is invalid (greater than 100 or less than 0).
 
		ALCATEL NOTE:
         ACCESS:     NA       USAGE:      NA
         PERSIST:    NO       INSRVMOD:   NA
         RANGE:      0..10000 | 65535            DEFVALUE:   NA
         UNITS:      Hundreths of percentage     SPARSE:     NA
         DESCR:      NA"
    ::= { extendAluCfmLmInitiatorOnDemandTestEntry 15 }

extendAluCfmLmInitiatorOnDemandPrevTxNearEnd   OBJECT-TYPE
    SYNTAX     Counter
    ACCESS     read-only
    STATUS     mandatory
    DESCRIPTION
        "The value of this object is the value of TxFCf 
        in the second latest ETH-LMR frame this local MEP has received.
		ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 16 }
    
extendAluCfmLmInitiatorOnDemandPrevRxNearEnd   OBJECT-TYPE
    SYNTAX     Counter
    ACCESS     read-only
    STATUS     mandatory
    DESCRIPTION
        "The value of this object is the counter of frames 
        received at the service end point of this local MEP(RxFCl) at the time the second latest ETH-LMR frame is
        received and being processed.
		ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 17 }

extendAluCfmLmInitiatorOnDemandPrevTxFarEnd   OBJECT-TYPE
    SYNTAX     Counter
    ACCESS     read-only
    STATUS     mandatory
    DESCRIPTION
        "The value of this object is the value of TxFCb 
        in the second latest ETH-LMR frame this local MEP has received.
		ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 18 }
    
extendAluCfmLmInitiatorOnDemandPrevRxFarEnd   OBJECT-TYPE
    SYNTAX     Counter
    ACCESS     read-only
    STATUS     mandatory
    DESCRIPTION
        "The value of this object is the value of 'RxFCf' 
        in the second latest ETH-LMR frame this local MEP has received.
		ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 19 }

extendAluCfmLmInitiatorOnDemandCurrTxNearEnd   OBJECT-TYPE
    SYNTAX     Counter
    ACCESS     read-only
    STATUS     mandatory
    DESCRIPTION
        "The value of this object is the value of 'TxFCf' 
        in the latest ETH-LMR frame this local MEP has received.
		ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 20 }
    
extendAluCfmLmInitiatorOnDemandCurrRxNearEnd   OBJECT-TYPE
    SYNTAX     Counter
    ACCESS     read-only
    STATUS     mandatory
    DESCRIPTION
        "The value of this object is the counter of frames received at the 
        service end point of this local MEP(RxFCl) at the time the latest ETH-LMR frame is
        received and being processed.
		ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 21 }

extendAluCfmLmInitiatorOnDemandCurrTxFarEnd   OBJECT-TYPE
    SYNTAX     Counter
    ACCESS     read-only
    STATUS     mandatory
    DESCRIPTION
        "The value of this object is the value of 'TxFCb' in the latest ETH-LMR 
        frame this local MEP has received.
		ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 22 }
    
extendAluCfmLmInitiatorOnDemandCurrRxFarEnd   OBJECT-TYPE
    SYNTAX     Counter
    ACCESS     read-only
    STATUS     mandatory
    DESCRIPTION
        "The value of this object is the value of 'RxFCf' in the latest ETH-LMR 
        frame this local MEP has received.
		ALCATEL NOTE:
         ACCESS:     NA       USAGE:      NA
         PERSIST:    NO       INSRVMOD:   NA
         RANGE:      NA       DEFVALUE:   NA
         UNITS:      NA       SPARSE:     NA
         DESCR:      NA"
    ::= { extendAluCfmLmInitiatorOnDemandTestEntry 23 }

extendAluCfmLmInitiatorOnDemandRowStatus OBJECT-TYPE
      SYNTAX      RowStatus
      ACCESS      read-write
      STATUS      mandatory
      DESCRIPTION
                "This is the row status. A set to 'createAndGo' with a valid value for
                 extendAluCfmLmInitiatorOnDemandRemoteMepMacAddress will result in 
                 the state transition to 'active' and the Lm test will be initiated.The value of
                 extendAluCfmLmInitiatorOnDemandTestStatus will be set to 'in-progress'.

                 The result of the test can be obtained from extendAluCfmLmInitiatorOnDemandTestStatus
         ALCATEL NOTE:
                ACCESS:     NA       USAGE:      NA
                PERSIST:    NA       INSRVMOD:   NA
                RANGE:      1,4,6    DEFVALUE:   NA
                UNITS:      NA       SPARSE:     NA"
    ::={ extendAluCfmLmInitiatorOnDemandTestEntry 24}


--Proactive SLM/LM  configuration table

extendAluCfmPMProactiveConfigTable OBJECT-TYPE
    SYNTAX      SEQUENCE OF ExtendAluCfmPMProactiveConfigEntry
    ACCESS      not-accessible
    STATUS      mandatory
    DESCRIPTION 
        "Defines the Y1731 CFM PM Configuration Table for initiating 
         proactive performance monitoring tests
         using ETH-SLM and ETH-LM. The results of these tests are stored in following result tables.
			extendAluCfmPMProactiveLossCurrent15MinIntervalTable,
			extendAluCfmPMProactiveLossCurrent1DayIntervalTable,
			extendAluCfmPMProactiveLossPrevious15MinIntervalTable,
			extendAluCfmPMProactiveLossPrevious1DayIntervalTable			
         ALCATEL NOTE:
        	TABLESIZE: MAX-NUMBER-OF-LTs possible in the shelf * 40
         "
    ::=	{ extendAluCfmPMObjects 4 }

extendAluCfmPMProactiveConfigEntry OBJECT-TYPE
    SYNTAX      ExtendAluCfmPMProactiveConfigEntry
    ACCESS      not-accessible
    STATUS      mandatory
    DESCRIPTION
        "Defines an entry in the ExtendAluCfmPMProactiveConfigTable. " 
    INDEX {
            dot1agCfmMdIndex,
            dot1agCfmMaIndex,
            dot1agCfmMepIdentifier,
            extendAluCfmPMProactiveConfigSessionIndex
          }
    ::= { extendAluCfmPMProactiveConfigTable 1 }

ExtendAluCfmPMProactiveConfigEntry ::=
    SEQUENCE {
	    extendAluCfmPMProactiveConfigSessionIndex         INTEGER,   
	    extendAluCfmPMProactiveConfigTestType             ExtendAluCfmY1731TestType,		
            extendAluCfmPMProactiveConfigRemoteMepMacAddress  MacAddress,            
            extendAluCfmPMProactiveConfigAdminStatus          INTEGER,
	    extendAluCfmPMProactiveConfigPriority             INTEGER,
	    extendAluCfmPMProactiveConfigInterval	      INTEGER,
	    extendAluCfmPMProactiveConfigDataSize             INTEGER,
	    extendAluCfmPMProactiveConfigMeasurementInterval  INTEGER,		
	    extendAluCfmPMProactiveConfigRowStatus            RowStatus
    }

extendAluCfmPMProactiveConfigSessionIndex      OBJECT-TYPE
    SYNTAX      INTEGER (1..960)
    ACCESS      read-write
    STATUS      mandatory
    DESCRIPTION
        "The value of extendAluCfmPMProactiveConfigSessionIndex indicates the session identifier
         used to initiate the Y1731 PM test. This session index must be unique across the system.
		 
         ALCATEL NOTE:
                ACCESS:     NA       USAGE:      NA
                PERSIST:    YES      INSRVMOD:   NA
                RANGE:      NA       DEFVALUE:   NA
                UNITS:      NA       SPARSE:     NA
        "
    ::= { extendAluCfmPMProactiveConfigEntry 1 }

extendAluCfmPMProactiveConfigTestType           OBJECT-TYPE
    SYNTAX      ExtendAluCfmY1731TestType
    ACCESS      read-write
    STATUS      mandatory
    DESCRIPTION
        "The value of this object indicates the type of test.
	     This object is a mandatory parameter to create an entry in this table 
         and cannot be modified later
         ALCATEL NOTE:
                ACCESS:     NA       USAGE:      NA
                PERSIST:    YES      INSRVMOD:   NA
                RANGE:      NA       DEFVALUE:   NA
                UNITS:      NA       SPARSE:     NA
        "
    ::= { extendAluCfmPMProactiveConfigEntry 2 }

extendAluCfmPMProactiveConfigRemoteMepMacAddress OBJECT-TYPE
    SYNTAX      MacAddress
    ACCESS      read-write
    STATUS      mandatory
    DESCRIPTION
       "The value of this object specifies the target MAC
        address for the test.
        
        The MAC address must be a unicast mac-address.		
	    This object is a mandatory parameter to create an entry in this table
        and cannot be modified later
         ALCATEL NOTE:
                ACCESS:     NA       USAGE:      NA
                PERSIST:    YES      INSRVMOD:   NA
                RANGE:      NA       DEFVALUE:   NA
                UNITS:      NA       SPARSE:     NA
        "
    ::= { extendAluCfmPMProactiveConfigEntry 3 }

extendAluCfmPMProactiveConfigAdminStatus OBJECT-TYPE
    SYNTAX      INTEGER 
					{ 
					  enabled  (1),
					  disabled (2)
					}
    ACCESS      read-write
    STATUS      mandatory
    DESCRIPTION
        "The value of extendAluCfmPMProactiveConfigAdminStatus indicates the desired
         administrative state of the Y1731 CFM PM test.

	 The proactive monitoring is started when the value of this object is set to 'enabled'.

         The object extendAluCfmPMProactiveConfigDataSize can be modified when this object has the value 'enabled' or 'disabled'
		 
	 When this object has the value 'disabled' the following parameters can be modified
            extendAluCfmPMProactiveConfigPriority, 
            extendAluCfmPMProactiveConfigInterval, 
            extendAluCfmPMProactiveConfigMeasurementInterval 
         
	 When the value of this object is set from enabled to disabled, 
        all the historical and current interval data collected for this test will be cleared.

         ALCATEL NOTE:
                ACCESS:     NA       USAGE:      NA
                PERSIST:    YES      INSRVMOD:   NA
                RANGE:      NA       DEFVALUE:   NA
                UNITS:      NA       SPARSE:     NA
        "
    DEFVAL { disabled }
    ::= { extendAluCfmPMProactiveConfigEntry 4 }

extendAluCfmPMProactiveConfigPriority     OBJECT-TYPE
    SYNTAX     INTEGER (0..7)
    ACCESS     read-write
    STATUS     mandatory
    DESCRIPTION
        "The value specifies the vlan priority used in
        the generated test frame for the Y1731 PM test.
	For single-ended-lm,this is also the priority for which the 
        counters are being counted for loss calculation.
	
	This object cannot be modified when extendAluCfmPMProactiveConfigAdminStatus
	has the value 'enabled'
         ALCATEL NOTE:
                ACCESS:     NA       USAGE:      NA
                PERSIST:    YES      INSRVMOD:   NA
                RANGE:      NA       DEFVALUE:   NA
                UNITS:      NA       SPARSE:     NA
        "
    DEFVAL { 7 }
    ::= { extendAluCfmPMProactiveConfigEntry 5 }

extendAluCfmPMProactiveConfigInterval     OBJECT-TYPE
    SYNTAX      INTEGER (1..10 | 60 | 300)
    ACCESS      read-write
    STATUS      mandatory
    DESCRIPTION
        "The value of extendAluCfmPMProactiveConfigInterval specifies the time to 
         wait between the transmission of one OAM request and the next. 

         This object cannot be modified when extendAluCfmPMProactiveConfigAdminStatus
         has the value 'enabled'. 

         For single-ended-slm, the minimum value is 1 and maximum value is 10. 
         For single-ended-lm the only allowed values are 60 and 300.

         The default value of this object varies with extendAluCfmPMProactiveConfigTestType,
         as shown in the following table
	     
        extendAluCfmPMProactiveConfigTestType      Default 		 
           
	single-ended-slm	               	   1
	single-ended-lm                            60

         ALCATEL NOTE:
                ACCESS:     NA       USAGE:      NA
                PERSIST:    YES      INSRVMOD:   NA
                RANGE:      NA       DEFVALUE:   NA
                UNITS:      seconds  SPARSE:     NA
        "
    
    ::= { extendAluCfmPMProactiveConfigEntry 6 }	
	
extendAluCfmPMProactiveConfigDataSize OBJECT-TYPE
    SYNTAX      INTEGER (0..1500 | 65535)
    ACCESS      read-write
    STATUS      mandatory
    DESCRIPTION
        "The value of this object specifies the data size,
         in bytes, contained in the Data TLV for the single-ended Synthetic Loss
         Measurement (SLM) test. A value of zero (0) specifies that no Data
         TLV is inserted in the SLM packet. Any non-zero value will increase
         the packet size by the specified data size plus 3 bytes for the TLV
         header.
         
  	 This object is valid only for SLM (i.e) only when the value of
	 extendAluCfmPMProactiveConfigTestType is single-ended-slm.
         For single-ended-lm,the value of this object is 65535,
         which means it is not-applicable
    
	 extendAluCfmPMProactiveConfigTestType   Default
           
	single-ended-slm	                    0
	single-ended-lm                           65535

         ALCATEL NOTE:
                ACCESS:     NA       USAGE:      NA
                PERSIST:    YES      INSRVMOD:   NA
                RANGE:      NA       DEFVALUE:   NA
                UNITS:      octets       SPARSE:     NA
        "
    ::= { extendAluCfmPMProactiveConfigEntry 7 }
	
extendAluCfmPMProactiveConfigMeasurementInterval      OBJECT-TYPE
    SYNTAX      INTEGER (0 | 60 | 300)
    ACCESS      read-write
    STATUS      mandatory
    DESCRIPTION
        "The value of extendAluCfmPMProactiveConfigMeasurementInterval specifies  
         the time for which the synthetic loss 	calculation is made periodically.
		
    	 If the value of this object is set to 'X' seconds, 
         SLM Loss measurement calculations are done after every 'X' seconds.
	
	 In other words the result objects in the Current 15mins/1day result table 
         will get updated for every 'X' seconds. 
		
	 This measurement interval includes the default SLM timeout of 5 seconds 
         during which no SLM PDUs will be transmitted and the SLM initiator 
         will wait for the reply (SLR)  from remote node.Upon the expiration of the timeout, 
         the SLM initiator assumes that the response will not be received.Any response received 
         after the timeout period has expired is ignored and silently discarded.

	 This object is valid only for SLM (i.e) only when the value of
	 extendAluCfmPMProactiveConfigTestType is single-ended-slm.
         For single-ended-lm,the value of this object is 0,
         which means it is not-applicable
		 
         This object cannot be modified when extendAluCfmPMProactiveConfigAdminStatus
	 has the value 'enabled'
    
	 extendAluCfmPMProactiveConfigTestType   Default
           
	single-ended-slm	                  300
	single-ended-lm                             0
         
         ALCATEL NOTE:
                ACCESS:     NA       USAGE:      NA
                PERSIST:    YES      INSRVMOD:   NA
                RANGE:      NA       DEFVALUE:   NA
                UNITS:      seconds  SPARSE:     NA
        "
    ::= { extendAluCfmPMProactiveConfigEntry 8 }

extendAluCfmPMProactiveConfigRowStatus OBJECT-TYPE
    SYNTAX      RowStatus
    ACCESS      read-write
    STATUS      mandatory
    DESCRIPTION
        "This object allows entries to be created and deleted
         in the extendAluCfmPMProactiveConfigTable.
         To create an entry in this table, it is mandatory to 
         specify the following also 
              extendAluCfmPMProactiveConfigTestType
              extendAluCfmPMProactiveConfigRemoteMepMacAddress

         An entry in this table with extendAluCfmPMProactiveConfigTestType as 
         single-ended-slm can be created for a mep
         only if extendAluCfmPmMepSlmSingleEndedInitiator is enabled in that mep
         Similarly an entry in this table with 
         extendAluCfmPMProactiveConfigTestType as 
         single-ended-lm can be created for a mep
         only if extendAluCfmPmMepLmSingleEndedInitiator is enabled in that mep

         ALCATEL NOTE:
                ACCESS:     NA       USAGE:      NA
                PERSIST:    YES      INSRVMOD:   NA
                RANGE:      NA       DEFVALUE:   NA
                UNITS:      NA       SPARSE:     NA
        "
    ::= { extendAluCfmPMProactiveConfigEntry  9}

--Current Result tables	
--Current 15 min result	
extendAluCfmPMProactiveLossCurrent15MinIntervalTable OBJECT-TYPE
    SYNTAX      SEQUENCE OF ExtendAluCfmPMProactiveLossCurrent15MinIntervalEntry
    ACCESS      not-accessible
    STATUS      mandatory
    DESCRIPTION
        "The extendAluCfmPMProactiveCurrent15MinIntervalTable contains the
         current 15 minute interval loss statistics per Y1731 PM loss(SLM/LM) test."
    ::= { extendAluCfmPMObjects 5 }

extendAluCfmPMProactiveLossCurrent15MinIntervalEntry OBJECT-TYPE
    SYNTAX      ExtendAluCfmPMProactiveLossCurrent15MinIntervalEntry
    ACCESS      not-accessible
    STATUS      mandatory
    DESCRIPTION
        "Table entry for the current 15 minute interval loss statistics per Y1731 PM loss(SLM/LM) test."
    INDEX {
            dot1agCfmMdIndex,
            dot1agCfmMaIndex,
            dot1agCfmMepIdentifier,
            extendAluCfmPMProactiveConfigSessionIndex
          }
    ::= { extendAluCfmPMProactiveLossCurrent15MinIntervalTable 1 }

ExtendAluCfmPMProactiveLossCurrent15MinIntervalEntry ::= SEQUENCE {
    extendAluCfmPMProactiveCurrent15MinTimeElapsed       	INTEGER,
    extendAluCfmPMProactiveCurrent15MinTimeMeasured    		INTEGER,
    extendAluCfmPMProactive15MinValidIntervals         	        INTEGER,  
    extendAluCfmPMProactiveCurrent15MinInvalidDataFlag          INTEGER,
    extendAluCfmPMProactiveCurrent15MinTestType   		ExtendAluCfmY1731TestType,
    extendAluCfmPMProactiveCurrent15MinTestId                   Gauge,
    extendAluCfmPMProactiveCurrent15MinRemoteMepId              Dot1agCfmMepIdOrNA,
    extendAluCfmPMProactiveCurrent15MinPDUSent			Counter,
    extendAluCfmPMProactiveCurrent15MinPDURecv			Counter,
    extendAluCfmPMProactiveCurrent15MinRxNearEnd 		OCTET STRING, 
    extendAluCfmPMProactiveCurrent15MinRxFarEnd 		OCTET STRING,
    extendAluCfmPMProactiveCurrent15MinTxNearEnd 		OCTET STRING,
    extendAluCfmPMProactiveCurrent15MinTxFarEnd 		OCTET STRING,
    extendAluCfmPMProactiveCurrent15MinLossNearEnd 		OCTET STRING,
    extendAluCfmPMProactiveCurrent15MinLossFarEnd 		OCTET STRING,
    extendAluCfmPMProactiveCurrent15MinUnack                    OCTET STRING,
    extendAluCfmPMProactiveCurrent15MinLossRatioMinNearEnd      ExtendAluCfmHundrethsOfPercentage,
    extendAluCfmPMProactiveCurrent15MinLossRatioMaxNearEnd      ExtendAluCfmHundrethsOfPercentage,
    extendAluCfmPMProactiveCurrent15MinLossRatioAvgNearEnd      ExtendAluCfmHundrethsOfPercentage,
    extendAluCfmPMProactiveCurrent15MinLossRatioMinFarEnd       ExtendAluCfmHundrethsOfPercentage,
    extendAluCfmPMProactiveCurrent15MinLossRatioMaxFarEnd       ExtendAluCfmHundrethsOfPercentage,
    extendAluCfmPMProactiveCurrent15MinLossRatioAvgFarEnd       ExtendAluCfmHundrethsOfPercentage,
    extendAluCfmPMProactiveCurrent15MinPDUDiscarded    		Counter
}

extendAluCfmPMProactiveCurrent15MinTimeElapsed OBJECT-TYPE
    SYNTAX      INTEGER 
    ACCESS      read-only
    STATUS      mandatory
    DESCRIPTION
        "The amount of time, measured in seconds, 
         that has elapsed since the beginning of the current 15 minute interval.
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent15MinIntervalEntry 1 }

extendAluCfmPMProactiveCurrent15MinTimeMeasured OBJECT-TYPE
    SYNTAX      INTEGER 
    ACCESS      read-only
    STATUS      mandatory
    DESCRIPTION
        "The amount of time, measured in seconds, that statistics for this entry
         have been actually counted for the current 15 minute interval.
	 This value will be the same as the elapsed duration except 
         in a situation where performance monitoring data could not be collected 
	 for this test for some reason.
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent15MinIntervalEntry 2 }

extendAluCfmPMProactive15MinValidIntervals OBJECT-TYPE
    SYNTAX      INTEGER (0..96)
    ACCESS      read-only
    STATUS      mandatory
    DESCRIPTION
        "The number of previous 15 min intervals for which valid data was collected for this test. 
	 This is equal to the number of entries in the
         extendAluCfmPMProactivePrevious15MinIntervalTable for this entry.
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent15MinIntervalEntry 3 }

extendAluCfmPMProactiveCurrent15MinInvalidDataFlag OBJECT-TYPE
        SYNTAX      INTEGER (0..1)
        ACCESS      read-only
        STATUS      mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    NA                  DEFVALUE: NA
             UNITS:    NA                  SPARSE:   NA
             DESCR:    NA
        "
    ::= { extendAluCfmPMProactiveLossCurrent15MinIntervalEntry 4 }

extendAluCfmPMProactiveCurrent15MinTestType           OBJECT-TYPE
    SYNTAX     ExtendAluCfmY1731TestType
    ACCESS     read-only
    STATUS     mandatory
    DESCRIPTION
        "The value of this object indicates the type
         of test this row details.
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent15MinIntervalEntry 5 }

extendAluCfmPMProactiveCurrent15MinTestId OBJECT-TYPE
    SYNTAX      Gauge
    ACCESS      read-only
    STATUS      mandatory
    DESCRIPTION
        "The value of this object indicates the test id used in the SLM packet
         in the current 15 minutes.
         This object is valid only if  the value of 
         extendAluCfmPMProactiveCurrent15MinTestType is single-ended-slm.
         For single-ended-lm, the value of this object is not-applicable (0).
		ALCATEL NOTE:
         ACCESS:     NA       USAGE:      NA
         PERSIST:    NO       INSRVMOD:   NA
         RANGE:      NA       DEFVALUE:   NA
         UNITS:      NA       SPARSE:     NA
         DESCR:      NA"    
    ::= { extendAluCfmPMProactiveLossCurrent15MinIntervalEntry 6}

extendAluCfmPMProactiveCurrent15MinRemoteMepId        OBJECT-TYPE
    SYNTAX      Dot1agCfmMepIdOrNA
    ACCESS      read-only
    STATUS      mandatory
    DESCRIPTION
        "The value of this object indicates the MEP  
         Identifier of the remote node corresponding to the 
         extendAluCfmPMProactiveConfigRemoteMepMacAddress
         from which the Synthetic Loss Measurement Reply (SLR) is received 
         in the current 15 minutes.

         This object is valid only if  the value of 
         extendAluCfmPMProactiveCurrent15MinTestType is single-ended-slm.
         A value 0 indicates that the remote mep id is unknown.     
         For single-ended-lm, the value of this object is not-applicable (65535)
		
         ALCATEL NOTE:
         ACCESS:     NA       USAGE:      NA
         PERSIST:    NO       INSRVMOD:   NA
         RANGE:      NA       DEFVALUE:   NA
         UNITS:      NA       SPARSE:     NA
         DESCR:      NA"    
    ::= { extendAluCfmPMProactiveLossCurrent15MinIntervalEntry 7}

extendAluCfmPMProactiveCurrent15MinPDUSent OBJECT-TYPE
        SYNTAX      Counter
	ACCESS      read-only
	STATUS      mandatory
	DESCRIPTION
	"This object indicates the number of SLM/LM PDUs sent by this MEP in the current 15 minutes.
         ALCATEL NOTE:
                ACCESS:     NA       USAGE:      NA
                PERSIST:    NO       INSRVMOD:   NA
                RANGE:      NA       DEFVALUE:   NA
                UNITS:      NA       SPARSE:     NA
        "
	::= { extendAluCfmPMProactiveLossCurrent15MinIntervalEntry 8}

extendAluCfmPMProactiveCurrent15MinPDURecv OBJECT-TYPE
        SYNTAX      Counter
	ACCESS      read-only
	STATUS      mandatory
	DESCRIPTION
	"This object indicates the number of SLR/LMR PDUs received from peer in the current 15 minutes.
         ALCATEL NOTE:
                ACCESS:     NA       USAGE:      NA
                PERSIST:    NO       INSRVMOD:   NA
                RANGE:      NA       DEFVALUE:   NA
                UNITS:      NA       SPARSE:     NA
        "
	::= { extendAluCfmPMProactiveLossCurrent15MinIntervalEntry 9}

extendAluCfmPMProactiveCurrent15MinRxNearEnd   OBJECT-TYPE
    SYNTAX      OCTET STRING (SIZE(8))
    ACCESS      read-only
    STATUS      mandatory
    DESCRIPTION
        "The value of this object is the accumulated number of frames received
         within the test duration of 15 minutes at this MEP (RxFCl).
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent15MinIntervalEntry 10 }
          
extendAluCfmPMProactiveCurrent15MinRxFarEnd   OBJECT-TYPE
    SYNTAX      OCTET STRING (SIZE(8))
    ACCESS      read-only
    STATUS      mandatory
    DESCRIPTION
        "The value of this object is the accumulated number of frames received
         within the test duration of 15 minutes at the far-end MEP,
       	 whose MAC address is configured in this session.(RxFCf).
         For SLM, this is the value of TxFCb.
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent15MinIntervalEntry 11 }

extendAluCfmPMProactiveCurrent15MinTxNearEnd   OBJECT-TYPE
    SYNTAX     OCTET STRING (SIZE(8))
    ACCESS     read-only
    STATUS     mandatory
    DESCRIPTION
        "The value of this object is the accumulated number of frames transmitted
         within the test duration of 15 minutes by this MEP (TxFCf).
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent15MinIntervalEntry 12 }
          
extendAluCfmPMProactiveCurrent15MinTxFarEnd   OBJECT-TYPE
    SYNTAX     OCTET STRING (SIZE(8))
    ACCESS     read-only
    STATUS     mandatory
    DESCRIPTION
        "The value of this object is the accumulated number of frames transmitted
	 within the test duration of 15 minutes by far-end MEP,
    	 whose MAC address is configured in this session.(TxFCb)
          
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent15MinIntervalEntry 13 }
    
extendAluCfmPMProactiveCurrent15MinLossNearEnd   OBJECT-TYPE
    SYNTAX     OCTET STRING (SIZE(8))
    ACCESS     read-only
    STATUS     mandatory
    DESCRIPTION
        "The value of this object is the accumulated number of frames 
         transmitted from the remote node but not received at the local
         node within the test duration of 15 minutes.
         
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent15MinIntervalEntry 14 }
          
extendAluCfmPMProactiveCurrent15MinLossFarEnd   OBJECT-TYPE
    SYNTAX      OCTET STRING (SIZE(8))
    ACCESS      read-only
    STATUS      mandatory
    DESCRIPTION
        "The value of this object is the accumulated number of frames
         transmitted from the local node but not received at the remote
         node within the test duration of 15 minutes.
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent15MinIntervalEntry 15 }

extendAluCfmPMProactiveCurrent15MinUnack OBJECT-TYPE
    SYNTAX     OCTET STRING (SIZE(8))
    ACCESS     read-only
    STATUS     mandatory
    DESCRIPTION
        "The value of this object is the accumulated number of SLM frames
         that are unacknowledged within the test duration of 15 minutes.
         This object is valid only if the value of 
         extendAluCfmPMProactiveCurrent15MinTestType is single-ended-slm.
         For single-ended-lm, the value of this object is 
         18446744073709551615 ((2^64)-1), which means it is not-applicable.         
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent15MinIntervalEntry 16 }

extendAluCfmPMProactiveCurrent15MinLossRatioMinNearEnd   OBJECT-TYPE
    SYNTAX      ExtendAluCfmHundrethsOfPercentage
    ACCESS      read-only
    STATUS      mandatory
    DESCRIPTION
        "The value of this object is the minimum value of 
         accumulated Loss Ratio within the test duration of 15 minutes,
	 at this MEP.It is expressed in hundredth of a percent accuracy.  
        
	It is calculated as followed:        
        MIN [(extendAluCfmPMProactiveCurrent15MinLossNearEnd * 10000) / extendAluCfmPMProactiveCurrent15MinTxFarEnd].
        If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "

    ::= { extendAluCfmPMProactiveLossCurrent15MinIntervalEntry 17 }

extendAluCfmPMProactiveCurrent15MinLossRatioMaxNearEnd   OBJECT-TYPE
    SYNTAX      ExtendAluCfmHundrethsOfPercentage
    ACCESS      read-only
    STATUS      mandatory
    DESCRIPTION
        "The value of this object is the maximum value of accumulated Loss Ratio 
         within the test duration of 15 minutes,at this MEP.
         It is expressed in hundredth of a percent accuracy.  
        
	 It is calculated as followed:  

         MAX [(extendAluCfmPMProactiveCurrent15MinLossNearEnd * 10000) / extendAluCfmPMProactiveCurrent15MinTxFarEnd].
         If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "

    ::= { extendAluCfmPMProactiveLossCurrent15MinIntervalEntry 18 }

extendAluCfmPMProactiveCurrent15MinLossRatioAvgNearEnd   OBJECT-TYPE
    SYNTAX      ExtendAluCfmHundrethsOfPercentage
    ACCESS      read-only
    STATUS      mandatory
    DESCRIPTION
        "The value of this object is the average value of accumulated Loss Ratio 
         within the test duration of 15 minutes,at this MEP.
         It is expressed in hundredth of a percent accuracy.  
        
	 It is calculated as followed:  
         AVG [(extendAluCfmPMProactiveCurrent15MinLossNearEnd * 10000) / extendAluCfmPMProactiveCurrent15MinTxFarEnd].
	 If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "

    ::= { extendAluCfmPMProactiveLossCurrent15MinIntervalEntry 19 }
	
extendAluCfmPMProactiveCurrent15MinLossRatioMinFarEnd   OBJECT-TYPE
    SYNTAX      ExtendAluCfmHundrethsOfPercentage
    ACCESS      read-only
    STATUS      mandatory
    DESCRIPTION
        "The value of this object is the minimum of accumulated Loss Ratio 
         within the test duration of 15 minutes, at the far-end MEP, 
         whose MAC address is configured in this session.
         
         It is expressed in hundredth of a percent accuracy.  
         It is calculated as followed:

         MIN [(extendAluCfmPMProactiveCurrent15MinLossFarEnd * 10000) / extendAluCfmPMProactiveCurrent15MinTxNearEnd].
         If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "
    ::= { extendAluCfmPMProactiveLossCurrent15MinIntervalEntry 20 }

extendAluCfmPMProactiveCurrent15MinLossRatioMaxFarEnd   OBJECT-TYPE
    SYNTAX      ExtendAluCfmHundrethsOfPercentage
    ACCESS      read-only
    STATUS      mandatory
    DESCRIPTION
        "The value of this object is the maximum of accumulated Loss Ratio
         within the test duration of 15 minutes, at 
         the far-end MEP, whose MAC address is configured in this session.
         
         It is expressed in hundredth of a percent accuracy.  
        
	 It is calculated as followed:
         MAX [(extendAluCfmPMProactiveCurrent15MinLossFarEnd * 10000) / extendAluCfmPMProactiveCurrent15MinTxNearEnd].
         If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "
    ::= { extendAluCfmPMProactiveLossCurrent15MinIntervalEntry 21 }

extendAluCfmPMProactiveCurrent15MinLossRatioAvgFarEnd   OBJECT-TYPE
    SYNTAX      ExtendAluCfmHundrethsOfPercentage
    ACCESS      read-only
    STATUS      mandatory
    DESCRIPTION
        "The value of this object is the average of accumulated Loss Ratio
         within the test duration of 15 minutes, at the far-end MEP,
         whose MAC address is configured in this session.It is expressed in hundredth of a percent accuracy.  
        
	It is calculated as followed:
        AVG [(extendAluCfmPMProactiveCurrent15MinLossFarEnd * 10000) / extendAluCfmPMProactiveCurrent15MinTxNearEnd].
	If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        " 
    ::= { extendAluCfmPMProactiveLossCurrent15MinIntervalEntry 22 }

extendAluCfmPMProactiveCurrent15MinPDUDiscarded OBJECT-TYPE
        SYNTAX      Counter
        ACCESS      read-only
        STATUS      mandatory
        DESCRIPTION
        "This object indicates the number of SLR/LMR PDUs discarded by this MEP in the current 15 minutes.
         This will be incremented for every invalid SLR/LMR received from the Peer. 
         Conditions:
            SLR :
              1. Late SLR - Not received within timeout (5 Secs). 
              2. Data TLV Validation Failure.
              3. Invalid firstTlvOffset.
              4. SLR received for the previous Measurement Interval.
              5. Received SLR Src MAC does not match with configured target MAC.
              6. Invalid Initiator/Responder MEPId range in SLR.
              7. txFcf/txFcb/testId in SLR is zero.
              8. SLR contains unknown TLV other than dataTlv.
              9. SLR destination MacAddress does not match with received mep MacAddress. 
             10. SLR source MacAddress match with receiving Mep MacAddress.
             11. SLR source Mac address is a multicast/broadcast Mac address. 
             12. SLR responder MEP id is equal to Initiator MEP Id. 
             13. Initiator MEP id int SLR packet does not match with the MEP id on which the SLM test is configured.
            LMR : 
              1. Invalid firstTlvOffset. 
              2. LMR destMacAddr does not match with mepMacAddress.
              3. LMR source Mac address matches with received MEP Mac Address.
              4. LMR source Mac address is a multicast/broadcast Mac address. 
              5. LMR sourceMac and configured targetMac mismatch.
              6. LMR version value is not equal to 1.
              7. LMR Flags field (LSB) value is not equal to 1.
              8. Duplicate LMR.ie.LMR already received for the LMM Sent.
              9. LMR contains any valid/invalid TLV.

         ALCATEL NOTE:
                ACCESS:     NA       USAGE:      NA
                PERSIST:    NO       INSRVMOD:   NA
                RANGE:      NA       DEFVALUE:   NA
                UNITS:      NA       SPARSE:     NA
        "
        ::= { extendAluCfmPMProactiveLossCurrent15MinIntervalEntry 23 }


--Current 1 day result	
extendAluCfmPMProactiveLossCurrent1DayIntervalTable OBJECT-TYPE
    SYNTAX      SEQUENCE OF ExtendAluCfmPMProactiveLossCurrent1DayIntervalEntry
    ACCESS      not-accessible
    STATUS      mandatory
    DESCRIPTION
        "The extendAluCfmPMProactiveCurrent1DayIntervalTable contains the
         current 1 day interval loss statistics per Y1731 PM loss(SLM/LM) test."
    ::= { extendAluCfmPMObjects 6 }

extendAluCfmPMProactiveLossCurrent1DayIntervalEntry OBJECT-TYPE
    SYNTAX      ExtendAluCfmPMProactiveLossCurrent1DayIntervalEntry
    ACCESS      not-accessible
    STATUS      mandatory
    DESCRIPTION
        "Table entry for the current 1 day interval loss statistics per Y1731 PM loss(SLM/LM) test."
    INDEX {
            dot1agCfmMdIndex,
            dot1agCfmMaIndex,
            dot1agCfmMepIdentifier,
            extendAluCfmPMProactiveConfigSessionIndex
          }
    ::= { extendAluCfmPMProactiveLossCurrent1DayIntervalTable 1 }

ExtendAluCfmPMProactiveLossCurrent1DayIntervalEntry ::= SEQUENCE {
    extendAluCfmPMProactiveCurrent1DayTimeElapsed       	INTEGER,
    extendAluCfmPMProactiveCurrent1DayTimeMeasured    		INTEGER,
    extendAluCfmPMProactive1DayValidIntervals         	        INTEGER,  
    extendAluCfmPMProactiveCurrent1DayInvalidDataFlag           INTEGER,
    extendAluCfmPMProactiveCurrent1DayTestType   		ExtendAluCfmY1731TestType,
    extendAluCfmPMProactiveCurrent1DayTestId                    Gauge,
    extendAluCfmPMProactiveCurrent1DayRemoteMepId               Dot1agCfmMepIdOrNA,
    extendAluCfmPMProactiveCurrent1DayPDUSent			Counter,
    extendAluCfmPMProactiveCurrent1DayPDURecv			Counter,
    extendAluCfmPMProactiveCurrent1DayRxNearEnd 		OCTET STRING, 
    extendAluCfmPMProactiveCurrent1DayRxFarEnd 		        OCTET STRING,
    extendAluCfmPMProactiveCurrent1DayTxNearEnd 		OCTET STRING,
    extendAluCfmPMProactiveCurrent1DayTxFarEnd 		        OCTET STRING,
    extendAluCfmPMProactiveCurrent1DayLossNearEnd 		OCTET STRING,
    extendAluCfmPMProactiveCurrent1DayLossFarEnd 		OCTET STRING,
    extendAluCfmPMProactiveCurrent1DayUnack                     OCTET STRING,
    extendAluCfmPMProactiveCurrent1DayLossRatioMinNearEnd      ExtendAluCfmHundrethsOfPercentage,
    extendAluCfmPMProactiveCurrent1DayLossRatioMaxNearEnd      ExtendAluCfmHundrethsOfPercentage,
    extendAluCfmPMProactiveCurrent1DayLossRatioAvgNearEnd      ExtendAluCfmHundrethsOfPercentage,
    extendAluCfmPMProactiveCurrent1DayLossRatioMinFarEnd       ExtendAluCfmHundrethsOfPercentage,
    extendAluCfmPMProactiveCurrent1DayLossRatioMaxFarEnd       ExtendAluCfmHundrethsOfPercentage,
    extendAluCfmPMProactiveCurrent1DayLossRatioAvgFarEnd       ExtendAluCfmHundrethsOfPercentage,
    extendAluCfmPMProactiveCurrent1DayPDUDiscarded     	       Counter
}

extendAluCfmPMProactiveCurrent1DayTimeElapsed OBJECT-TYPE
    SYNTAX      INTEGER 
    ACCESS      read-only
    STATUS      mandatory
    DESCRIPTION
        "The amount of time, measured in seconds, 
         that has elapsed since the beginning of the current 1 day interval.
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent1DayIntervalEntry 1 }

extendAluCfmPMProactiveCurrent1DayTimeMeasured OBJECT-TYPE
    SYNTAX      INTEGER 
    ACCESS      read-only
    STATUS      mandatory
    DESCRIPTION
        "The amount of time, measured in seconds, that statistics for this entry
         have been actually counted for the current 1 day interval.
	 This value will be the same as the elapsed duration except 
         in a situation where performance monitoring data could not be collected 
	 for this test for some reason.
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent1DayIntervalEntry 2 }

extendAluCfmPMProactive1DayValidIntervals OBJECT-TYPE
    SYNTAX      INTEGER (0..7)
    ACCESS      read-only
    STATUS      mandatory
    DESCRIPTION
        "The number of previous 1 day intervals for which valid data was collected for this test. 
	 This is equal to the number of entries in the
         extendAluCfmPMProactivePrevious1DayIntervalTable for this entry.
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent1DayIntervalEntry 3 }

extendAluCfmPMProactiveCurrent1DayInvalidDataFlag OBJECT-TYPE
        SYNTAX      INTEGER (0..1)
        ACCESS      read-only
        STATUS      mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    NA                  DEFVALUE: NA
             UNITS:    NA                  SPARSE:   NA
             DESCR:    NA
        "
    ::= { extendAluCfmPMProactiveLossCurrent1DayIntervalEntry 4 }

extendAluCfmPMProactiveCurrent1DayTestType           OBJECT-TYPE
    SYNTAX      ExtendAluCfmY1731TestType
    ACCESS      read-only
    STATUS      mandatory
    DESCRIPTION
        "The value of this object indicates the type
         of test this row details.
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent1DayIntervalEntry 5 }

extendAluCfmPMProactiveCurrent1DayTestId OBJECT-TYPE
    SYNTAX      Gauge
    ACCESS      read-only
    STATUS      mandatory
    DESCRIPTION
        "The value of this object indicates the test id used in the SLM packet
         in the current 1 day.
         This object is valid only if  the value of 
         extendAluCfmPMProactiveCurrent1DayTestType is single-ended-slm. 
         For single-ended-lm, the value of this object is not-applicable (0).
		ALCATEL NOTE:
         ACCESS:     NA       USAGE:      NA
         PERSIST:    NO       INSRVMOD:   NA
         RANGE:      NA       DEFVALUE:   NA
         UNITS:      NA       SPARSE:     NA
         DESCR:      NA"    
    ::= { extendAluCfmPMProactiveLossCurrent1DayIntervalEntry 6}

extendAluCfmPMProactiveCurrent1DayRemoteMepId        OBJECT-TYPE
    SYNTAX      Dot1agCfmMepIdOrNA
    ACCESS      read-only
    STATUS      mandatory
    DESCRIPTION
        "The value of this object indicates the MEP  
         Identifier of the remote node corresponding to the 
         extendAluCfmPMProactiveConfigRemoteMepMacAddress
         from which the Synthetic Loss Measurement Reply (SLR) is received
         in the current 1 day.

         This object is valid only if  the value of 
         extendAluCfmPMProactiveCurrent1DayTestType is single-ended-slm.
         For single-ended-lm, the value of this object is not-applicable (65535).
         A value 0 indicates that the remote mep id is unknown.
		ALCATEL NOTE:
         ACCESS:     NA       USAGE:      NA
         PERSIST:    NO       INSRVMOD:   NA
         RANGE:      NA       DEFVALUE:   NA
         UNITS:      NA       SPARSE:     NA
         DESCR:      NA"    
    ::= { extendAluCfmPMProactiveLossCurrent1DayIntervalEntry 7}

extendAluCfmPMProactiveCurrent1DayPDUSent OBJECT-TYPE
        SYNTAX      Counter
	ACCESS      read-only
	STATUS      mandatory
	DESCRIPTION
	"This object indicates the number of SLM/LM PDUs sent by this MEP in the current 1 day.
         ALCATEL NOTE:
                ACCESS:     NA       USAGE:      NA
                PERSIST:    NO       INSRVMOD:   NA
                RANGE:      NA       DEFVALUE:   NA
                UNITS:      NA       SPARSE:     NA
        "
	::= { extendAluCfmPMProactiveLossCurrent1DayIntervalEntry 8}

extendAluCfmPMProactiveCurrent1DayPDURecv OBJECT-TYPE
        SYNTAX     Counter
	ACCESS     read-only
	STATUS     mandatory
	DESCRIPTION
	"This object indicates the number of SLR/LMR PDUs received from peer in the current 1 day.
         ALCATEL NOTE:
                ACCESS:     NA       USAGE:      NA
                PERSIST:    NO       INSRVMOD:   NA
                RANGE:      NA       DEFVALUE:   NA
                UNITS:      NA       SPARSE:     NA
        "
	::= { extendAluCfmPMProactiveLossCurrent1DayIntervalEntry 9}


extendAluCfmPMProactiveCurrent1DayRxNearEnd   OBJECT-TYPE
    SYNTAX      OCTET STRING (SIZE(8))
    ACCESS      read-only
    STATUS      mandatory
    DESCRIPTION
        "The value of this object is the accumulated number of frames received
         within the test duration of 1 day at this MEP (RxFCl).
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent1DayIntervalEntry 10 }
          
extendAluCfmPMProactiveCurrent1DayRxFarEnd   OBJECT-TYPE
    SYNTAX      OCTET STRING (SIZE(8))
    ACCESS      read-only
    STATUS      mandatory
    DESCRIPTION
        "The value of this object is the accumulated number of frames received
         within the test duration of 1 day at the far-end MEP,
       	 whose MAC address is configured in this session.(RxFCf).
         For SLM, this is the value of TxFCb.
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent1DayIntervalEntry 11 }

extendAluCfmPMProactiveCurrent1DayTxNearEnd   OBJECT-TYPE
    SYNTAX      OCTET STRING (SIZE(8))
    ACCESS      read-only
    STATUS      mandatory
    DESCRIPTION
        "The value of this object is the accumulated number of frames transmitted
         within the test duration of 1 day by this MEP (TxFCf).
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent1DayIntervalEntry 12 }
          
extendAluCfmPMProactiveCurrent1DayTxFarEnd   OBJECT-TYPE
    SYNTAX      OCTET STRING (SIZE(8))
    ACCESS      read-only
    STATUS      mandatory
    DESCRIPTION
        "The value of this object is the accumulated number of frames transmitted
	 within the test duration of 1 day by far-end MEP,
    	 whose MAC address is configured in this session.(TxFCb)
          
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent1DayIntervalEntry 13 }
    
extendAluCfmPMProactiveCurrent1DayLossNearEnd   OBJECT-TYPE
    SYNTAX      OCTET STRING (SIZE(8))
    ACCESS      read-only
    STATUS      mandatory
    DESCRIPTION
        "The value of this object is the accumulated number of frames 
         transmitted from the remote node but not received at the local
         node within the test duration of 1 day.
         
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent1DayIntervalEntry 14 }
          
extendAluCfmPMProactiveCurrent1DayLossFarEnd   OBJECT-TYPE
    SYNTAX      OCTET STRING (SIZE(8))
    ACCESS      read-only
    STATUS      mandatory
    DESCRIPTION
        "The value of this object is the accumulated number of frames
         transmitted from the local node but not received at the remote
         node within the test duration of 1 day.
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent1DayIntervalEntry 15 }

extendAluCfmPMProactiveCurrent1DayUnack OBJECT-TYPE
    SYNTAX      OCTET STRING (SIZE(8))
    ACCESS      read-only
    STATUS      mandatory
    DESCRIPTION
        "The value of this object is the accumulated number of SLM frames
         that are unacknowledged within the test duration of 1 day.
         This object is valid only if the value of 
         extendAluCfmPMProactiveCurrent1DayTestType is single-ended-slm.
         For single-ended-lm, the value of this object is 
         18446744073709551615 ((2^64)-1), which means it is not-applicable.         
         ALCATEL NOTE:
                ACCESS:     NA       USAGE:      NA
                PERSIST:    NO       INSRVMOD:   NA
                RANGE:      NA       DEFVALUE:   NA
                UNITS:      NA       SPARSE:     NA
        "
    ::= { extendAluCfmPMProactiveLossCurrent1DayIntervalEntry 16 }

extendAluCfmPMProactiveCurrent1DayLossRatioMinNearEnd   OBJECT-TYPE
    SYNTAX      ExtendAluCfmHundrethsOfPercentage
    ACCESS      read-only
    STATUS      mandatory
    DESCRIPTION
        "The value of this object is the minimum value of 
         accumulated Loss Ratio within the test duration of 1 day,
	 at this MEP.It is expressed in hundredth of a percent accuracy.  
        
	It is calculated as followed:        
        MIN [(extendAluCfmPMProactiveCurrent1DayLossNearEnd * 10000) / extendAluCfmPMProactiveCurrent1DayTxFarEnd].
        If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "

    ::= { extendAluCfmPMProactiveLossCurrent1DayIntervalEntry 17 }

extendAluCfmPMProactiveCurrent1DayLossRatioMaxNearEnd   OBJECT-TYPE
    SYNTAX      ExtendAluCfmHundrethsOfPercentage
    ACCESS      read-only
    STATUS      mandatory
    DESCRIPTION
        "The value of this object is the maximum value of accumulated Loss Ratio 
         within the test duration of 1 day,at this MEP.
         It is expressed in hundredth of a percent accuracy.  
        
	 It is calculated as followed:  

         MAX [(extendAluCfmPMProactiveCurrent1DayLossNearEnd * 10000) / extendAluCfmPMProactiveCurrent1DayTxFarEnd].
 	 If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "

    ::= { extendAluCfmPMProactiveLossCurrent1DayIntervalEntry 18 }

extendAluCfmPMProactiveCurrent1DayLossRatioAvgNearEnd   OBJECT-TYPE
    SYNTAX      ExtendAluCfmHundrethsOfPercentage
    ACCESS      read-only
    STATUS      mandatory
    DESCRIPTION
        "The value of this object is the average value of accumulated Loss Ratio 
         within the test duration of 1 day,at this MEP.
         It is expressed in hundredth of a percent accuracy.  
        
	 It is calculated as followed:  
         AVG [(extendAluCfmPMProactiveCurrent1DayLossNearEnd * 10000) / extendAluCfmPMProactiveCurrent1DayTxFarEnd].
         If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "

    ::= { extendAluCfmPMProactiveLossCurrent1DayIntervalEntry 19 }
	
extendAluCfmPMProactiveCurrent1DayLossRatioMinFarEnd   OBJECT-TYPE
    SYNTAX      ExtendAluCfmHundrethsOfPercentage
    ACCESS      read-only
    STATUS      mandatory
    DESCRIPTION
        "The value of this object is the minimum of accumulated Loss Ratio 
         within the test duration of 1 day, at the far-end MEP, 
         whose MAC address is configured in this session.
         
         It is expressed in hundredth of a percent accuracy.  
         It is calculated as followed:

         MIN [(extendAluCfmPMProactiveCurrent1DayLossFarEnd * 10000) / extendAluCfmPMProactiveCurrent1DayTxNearEnd].
	 If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "
    ::= { extendAluCfmPMProactiveLossCurrent1DayIntervalEntry 20 }

extendAluCfmPMProactiveCurrent1DayLossRatioMaxFarEnd   OBJECT-TYPE
    SYNTAX      ExtendAluCfmHundrethsOfPercentage
    ACCESS      read-only
    STATUS      mandatory
    DESCRIPTION
        "The value of this object is the maximum of accumulated Loss Ratio
         within the test duration of 1 day, at 
         the far-end MEP, whose MAC address is configured in this session.
         
         It is expressed in hundredth of a percent accuracy.  
        
	 It is calculated as followed:
         MAX [(extendAluCfmPMProactiveCurrent1DayLossFarEnd * 10000) / extendAluCfmPMProactiveCurrent1DayTxNearEnd].
	 If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "
    ::= { extendAluCfmPMProactiveLossCurrent1DayIntervalEntry 21 }

extendAluCfmPMProactiveCurrent1DayLossRatioAvgFarEnd   OBJECT-TYPE
    SYNTAX      ExtendAluCfmHundrethsOfPercentage
    ACCESS      read-only
    STATUS      mandatory
    DESCRIPTION
        "The value of this object is the average of accumulated Loss Ratio
         within the test duration of 1 day, at the far-end MEP,
         whose MAC address is configured in this session.It is expressed in hundredth of a percent accuracy.  
        
	 It is calculated as followed:
         AVG [(extendAluCfmPMProactiveCurrent1DayLossFarEnd * 10000) / extendAluCfmPMProactiveCurrent1DayTxNearEnd].
	 If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        " 
    ::= { extendAluCfmPMProactiveLossCurrent1DayIntervalEntry 22 }

extendAluCfmPMProactiveCurrent1DayPDUDiscarded OBJECT-TYPE
        SYNTAX      Counter
        ACCESS      read-only
        STATUS      mandatory
        DESCRIPTION
        "This object indicates the number of SLR/LMR PDUs discarded by this MEP in the current 1 Day.
         This will be incremented for every invalid SLR/LMR received. 
         Conditions:
            SLR :
              1. Late SLR - Not received within timeout (5 Secs). 
              2. Data TLV Validation Failure.
	      3. Invalid firstTlvOffset.
              4. SLR received for the previous Measurement Interval.
              5. Received SLR Src MAC does not match with configured target MAC.
	      6. Invalid Initiator/Responder MEPId range in SLR.
	      7. txFcf/txFcb/testId in SLR is zero.
	      8. SLR contains unknown TLV other than dataTlv.
	      9. SLR destination MacAddress does not match with received mep MacAddress. 
	     10. SLR source MacAddress match with receiving Mep MacAddress.
	     11. SLR source Mac address is a multicast/broadcast Mac address. 
	     12. SLR responder MEP id is equal to Initiator MEP Id. 
	     13. Initiator MEP id int SLR packet does not match with the MEP id on which the SLM test is configured.
            LMR : 
              1. Invalid firstTlvOffset. 
              2. LMR destMacAddr does not match with mepMacAddress.
              3. LMR source Mac address matches with received MEP Mac Address.
	      4. LMR source Mac address is a multicast/broadcast Mac address. 
	      5. LMR sourceMac and configured targetMac mismatch.
	      6. LMR version value is not equal to 1.
	      7. LMR Flags field (LSB) value is not equal to 1.
	      8. Duplicate LMR.ie.LMR already received for the LMM Sent.
	      9. LMR contains any valid/invalid TLV.

         ALCATEL NOTE:
                ACCESS:     NA       USAGE:      NA
                PERSIST:    NO       INSRVMOD:   NA
                RANGE:      NA       DEFVALUE:   NA
                UNITS:      NA       SPARSE:     NA
        "
        ::= { extendAluCfmPMProactiveLossCurrent1DayIntervalEntry 23}


--Previous 15 minutes result	

extendAluCfmPMProactiveLossPrevious15MinIntervalTable OBJECT-TYPE
    SYNTAX      SEQUENCE OF ExtendAluCfmPMProactiveLossPrevious15MinIntervalEntry
    ACCESS      not-accessible
    STATUS      mandatory
    DESCRIPTION
        "The extendAluCfmPMProactivePrevious15MinIntervalTable contains the
         previous 15 minute interval loss statistics per Y1731 PM loss(SLM/LM) test."
    ::= { extendAluCfmPMObjects 7 }

extendAluCfmPMProactiveLossPrevious15MinIntervalEntry OBJECT-TYPE
    SYNTAX      ExtendAluCfmPMProactiveLossPrevious15MinIntervalEntry
    ACCESS      not-accessible
    STATUS      mandatory
    DESCRIPTION
        "Table entry for the previous 15 minute interval loss statistics per Y1731 PM loss(SLM/LM) test."
    INDEX {
            dot1agCfmMdIndex,
            dot1agCfmMaIndex,
            dot1agCfmMepIdentifier,
            extendAluCfmPMProactiveConfigSessionIndex,
            extendAluCfmPMProactivePrevious15MinIntervalNumber
          }
    ::= { extendAluCfmPMProactiveLossPrevious15MinIntervalTable 1 }

ExtendAluCfmPMProactiveLossPrevious15MinIntervalEntry ::= SEQUENCE {
    extendAluCfmPMProactivePrevious15MinIntervalNumber           INTEGER,
    extendAluCfmPMProactivePrevious15MinTimeMeasured    		INTEGER,
    extendAluCfmPMProactivePrevious15MinInvalidDataFlag          INTEGER,
    extendAluCfmPMProactivePrevious15MinTestType   		ExtendAluCfmY1731TestType,
    extendAluCfmPMProactivePrevious15MinTestId                  Gauge,
    extendAluCfmPMProactivePrevious15MinRemoteMepId             Dot1agCfmMepIdOrNA,
    extendAluCfmPMProactivePrevious15MinPDUSent			Counter,
    extendAluCfmPMProactivePrevious15MinPDURecv			Counter,
    extendAluCfmPMProactivePrevious15MinRxNearEnd 		OCTET STRING, 
    extendAluCfmPMProactivePrevious15MinRxFarEnd 		OCTET STRING,
    extendAluCfmPMProactivePrevious15MinTxNearEnd 		OCTET STRING,
    extendAluCfmPMProactivePrevious15MinTxFarEnd 		OCTET STRING,
    extendAluCfmPMProactivePrevious15MinLossNearEnd 		OCTET STRING,
    extendAluCfmPMProactivePrevious15MinLossFarEnd 		OCTET STRING,
    extendAluCfmPMProactivePrevious15MinUnack                   OCTET STRING,
    extendAluCfmPMProactivePrevious15MinLossRatioMinNearEnd      ExtendAluCfmHundrethsOfPercentage,
    extendAluCfmPMProactivePrevious15MinLossRatioMaxNearEnd      ExtendAluCfmHundrethsOfPercentage,
    extendAluCfmPMProactivePrevious15MinLossRatioAvgNearEnd      ExtendAluCfmHundrethsOfPercentage,
    extendAluCfmPMProactivePrevious15MinLossRatioMinFarEnd       ExtendAluCfmHundrethsOfPercentage,
    extendAluCfmPMProactivePrevious15MinLossRatioMaxFarEnd       ExtendAluCfmHundrethsOfPercentage,
    extendAluCfmPMProactivePrevious15MinLossRatioAvgFarEnd       ExtendAluCfmHundrethsOfPercentage,
    extendAluCfmPMProactivePrevious15MinPDUDiscarded       Counter

}

extendAluCfmPMProactivePrevious15MinIntervalNumber OBJECT-TYPE
    SYNTAX      INTEGER (1..96)
    ACCESS      not-accessible
    STATUS      mandatory
    DESCRIPTION
        "A number,which identifies the interval for which the set of 
         statistics is available. The interval identified by 1 is the most recently 
         completed 15 minutes interval, and the interval identified by N is the
         interval immediately preceding the one identified by N-1. The number of 
         available intervals is specified by extendAluCfmPMProactive15MinValidIntervals.
     
         ALCATEL NOTE:
                ACCESS:     NA       USAGE:      NA
                PERSIST:    NO       INSRVMOD:   NA
                RANGE:      NA       DEFVALUE:   NA
                UNITS:      NA       SPARSE:     NA
        "

    ::= { extendAluCfmPMProactiveLossPrevious15MinIntervalEntry 1 }

extendAluCfmPMProactivePrevious15MinTimeMeasured OBJECT-TYPE
    SYNTAX      INTEGER 
    ACCESS      read-only
    STATUS      mandatory
    DESCRIPTION
        "The amount of time, measured in seconds, that statistics for this entry
         have been actually counted for the previous 15 minute interval.
    	 This value will be the same as the elapsed duration except 
         in a situation where performance monitoring data could not be collected 
	     for this test for some reason.
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious15MinIntervalEntry 2 }

extendAluCfmPMProactivePrevious15MinInvalidDataFlag OBJECT-TYPE
        SYNTAX      INTEGER (0..1)
        ACCESS      read-only
        STATUS      mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    NA                  DEFVALUE: NA
             UNITS:    NA                  SPARSE:   NA
             DESCR:    NA
        "
    ::= { extendAluCfmPMProactiveLossPrevious15MinIntervalEntry 3 }

extendAluCfmPMProactivePrevious15MinTestType           OBJECT-TYPE
    SYNTAX      ExtendAluCfmY1731TestType
    ACCESS      read-only
    STATUS      mandatory
    DESCRIPTION
        "The value of this object indicates the type
         of test this row details.
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious15MinIntervalEntry 4 }

extendAluCfmPMProactivePrevious15MinTestId OBJECT-TYPE
    SYNTAX      Gauge
    ACCESS      read-only
    STATUS      mandatory
    DESCRIPTION
        "The value of this object indicates the test id used in the SLM packet 
         in this previous 15 minute interval.
         This object is valid only if  the value of 
         extendAluCfmPMProactivePrevious15MinTestType is single-ended-slm.
         For single-ended-lm, the value of this object is not-applicable (0).
		ALCATEL NOTE:
         ACCESS:     NA       USAGE:      NA
         PERSIST:    NO       INSRVMOD:   NA
         RANGE:      NA       DEFVALUE:   NA
         UNITS:      NA       SPARSE:     NA
         DESCR:      NA"    
    ::= { extendAluCfmPMProactiveLossPrevious15MinIntervalEntry 5}

extendAluCfmPMProactivePrevious15MinRemoteMepId        OBJECT-TYPE
    SYNTAX      Dot1agCfmMepIdOrNA
    ACCESS      read-only
    STATUS      mandatory
    DESCRIPTION
        "The value of this object indicates the MEP  
         Identifier of the remote node corresponding to the 
         extendAluCfmPMProactiveConfigRemoteMepMacAddress
         from which the Synthetic Loss Measurement Reply (SLR) is received
         in this previous 15 minute interval.

         This object is valid only if  the value of 
         extendAluCfmPMProactivePrevious15MinTestType is single-ended-slm.
         For single-ended-lm, the value of this object is not-applicable (65535).
         A value 0 indicates that the remote mep id is unknown.       
		ALCATEL NOTE:
         ACCESS:     NA       USAGE:      NA
         PERSIST:    NO       INSRVMOD:   NA
         RANGE:      NA       DEFVALUE:   NA
         UNITS:      NA       SPARSE:     NA
         DESCR:      NA"    
    ::= { extendAluCfmPMProactiveLossPrevious15MinIntervalEntry 6}

extendAluCfmPMProactivePrevious15MinPDUSent OBJECT-TYPE
        SYNTAX      Counter
	ACCESS      read-only
	STATUS      mandatory
	DESCRIPTION
	"This object indicates the number of SLM/LM PDUs sent by this MEP in this previous 15 minute interval.
         ALCATEL NOTE:
                ACCESS:     NA       USAGE:      NA
                PERSIST:    NO       INSRVMOD:   NA
                RANGE:      NA       DEFVALUE:   NA
                UNITS:      NA       SPARSE:     NA
        "
	::= { extendAluCfmPMProactiveLossPrevious15MinIntervalEntry 7}

extendAluCfmPMProactivePrevious15MinPDURecv OBJECT-TYPE
        SYNTAX      Counter
	ACCESS      read-only
	STATUS      mandatory
	DESCRIPTION
	"This object indicates the number of SLR/LMR PDUs received from peer in this previous 15 minute interval.
         ALCATEL NOTE:
                ACCESS:     NA       USAGE:      NA
                PERSIST:    NO       INSRVMOD:   NA
                RANGE:      NA       DEFVALUE:   NA
                UNITS:      NA       SPARSE:     NA
        "
	::= { extendAluCfmPMProactiveLossPrevious15MinIntervalEntry 8}


extendAluCfmPMProactivePrevious15MinRxNearEnd   OBJECT-TYPE
    SYNTAX      OCTET STRING (SIZE(8))
    ACCESS      read-only
    STATUS      mandatory
    DESCRIPTION
        "The value of this object is the accumulated number of frames received
         within the test duration of 15 minutes at this MEP (RxFCl).
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious15MinIntervalEntry 9 }
          
extendAluCfmPMProactivePrevious15MinRxFarEnd   OBJECT-TYPE
    SYNTAX      OCTET STRING (SIZE(8))
    ACCESS      read-only
    STATUS      mandatory
    DESCRIPTION
        "The value of this object is the accumulated number of frames received
         within the test duration of 15 minutes at the far-end MEP,
       	 whose MAC address is configured in this session.(RxFCf).
         For SLM, this is the value of TxFCb.
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious15MinIntervalEntry 10 }

extendAluCfmPMProactivePrevious15MinTxNearEnd   OBJECT-TYPE
    SYNTAX      OCTET STRING (SIZE(8))
    ACCESS      read-only
    STATUS      mandatory
    DESCRIPTION
        "The value of this object is the accumulated number of frames transmitted
         within the test duration of 15 minutes by this MEP (TxFCf).
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious15MinIntervalEntry 11 }
          
extendAluCfmPMProactivePrevious15MinTxFarEnd   OBJECT-TYPE
    SYNTAX      OCTET STRING (SIZE(8))
    ACCESS      read-only
    STATUS      mandatory
    DESCRIPTION
        "The value of this object is the accumulated number of frames transmitted
	 within the test duration of 15 minutes by far-end MEP,
    	 whose MAC address is configured in this session.(TxFCb)
          
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious15MinIntervalEntry 12 }
    
extendAluCfmPMProactivePrevious15MinLossNearEnd   OBJECT-TYPE
    SYNTAX      OCTET STRING (SIZE(8))
    ACCESS      read-only
    STATUS      mandatory
    DESCRIPTION
        "The value of this object is the accumulated number of frames 
         transmitted from the remote node but not received at the local
         node within the test duration of 15 minutes.
         
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious15MinIntervalEntry 13 }
          
extendAluCfmPMProactivePrevious15MinLossFarEnd   OBJECT-TYPE
    SYNTAX      OCTET STRING (SIZE(8))
    ACCESS      read-only
    STATUS      mandatory
    DESCRIPTION
        "The value of this object is the accumulated number of frames
         transmitted from the local node but not received at the remote
         node within the test duration of 15 minutes.
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious15MinIntervalEntry 14 }

extendAluCfmPMProactivePrevious15MinUnack OBJECT-TYPE
    SYNTAX      OCTET STRING (SIZE(8))
    ACCESS      read-only
    STATUS      mandatory
    DESCRIPTION
        "The value of this object is the accumulated number of SLM frames
         that are unacknowledged within the test duration of 15 minutes.
         This object is valid only if the value of 
         extendAluCfmPMProactivePrevious15MinTestType is single-ended-slm.
         For single-ended-lm, the value of this object is 
         18446744073709551615 ((2^64)-1), which means it is not-applicable.         
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious15MinIntervalEntry 15 }

extendAluCfmPMProactivePrevious15MinLossRatioMinNearEnd   OBJECT-TYPE
    SYNTAX      ExtendAluCfmHundrethsOfPercentage
    ACCESS      read-only
    STATUS      mandatory
    DESCRIPTION
        "The value of this object is the minimum value of 
         accumulated Loss Ratio within the test duration of 15 minutes,
	 at this MEP.It is expressed in hundredth of a percent accuracy.  
        
	It is calculated as followed:        
        MIN [(extendAluCfmPMProactivePrevious15MinLossNearEnd * 10000) / extendAluCfmPMProactivePrevious15MinTxFarEnd].
	  If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "

    ::= { extendAluCfmPMProactiveLossPrevious15MinIntervalEntry 16 }

extendAluCfmPMProactivePrevious15MinLossRatioMaxNearEnd   OBJECT-TYPE
    SYNTAX      ExtendAluCfmHundrethsOfPercentage
    ACCESS      read-only
    STATUS      mandatory
    DESCRIPTION
        "The value of this object is the maximum value of accumulated Loss Ratio 
         within the test duration of 15 minutes,at this MEP.
         It is expressed in hundredth of a percent accuracy.  
        
	 It is calculated as followed:  

         MAX [(extendAluCfmPMProactivePrevious15MinLossNearEnd * 10000) / extendAluCfmPMProactivePrevious15MinTxFarEnd].
	   If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "

    ::= { extendAluCfmPMProactiveLossPrevious15MinIntervalEntry 17 }

extendAluCfmPMProactivePrevious15MinLossRatioAvgNearEnd   OBJECT-TYPE
    SYNTAX      ExtendAluCfmHundrethsOfPercentage
    ACCESS      read-only
    STATUS      mandatory
    DESCRIPTION
        "The value of this object is the average value of accumulated Loss Ratio 
         within the test duration of 15 minutes,at this MEP.
         It is expressed in hundredth of a percent accuracy.  
        
	 It is calculated as followed:  
         AVG [(extendAluCfmPMProactivePrevious15MinLossNearEnd * 10000) / extendAluCfmPMProactivePrevious15MinTxFarEnd].
	 If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "

    ::= { extendAluCfmPMProactiveLossPrevious15MinIntervalEntry 18 }
	
extendAluCfmPMProactivePrevious15MinLossRatioMinFarEnd   OBJECT-TYPE
    SYNTAX      ExtendAluCfmHundrethsOfPercentage
    ACCESS      read-only
    STATUS      mandatory
    DESCRIPTION
        "The value of this object is the minimum of accumulated Loss Ratio 
         within the test duration of 15 minutes, at the far-end MEP, 
         whose MAC address is configured in this session.
         
         It is expressed in hundredth of a percent accuracy.  
         It is calculated as followed:

         MIN [(extendAluCfmPMProactivePrevious15MinLossFarEnd * 10000) / extendAluCfmPMProactivePrevious15MinTxNearEnd].
         If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "
    ::= { extendAluCfmPMProactiveLossPrevious15MinIntervalEntry 19 }

extendAluCfmPMProactivePrevious15MinLossRatioMaxFarEnd   OBJECT-TYPE
    SYNTAX      ExtendAluCfmHundrethsOfPercentage
    ACCESS      read-only
    STATUS      mandatory
    DESCRIPTION
        "The value of this object is the maximum of accumulated Loss Ratio
         within the test duration of 15 minutes, at 
         the far-end MEP, whose MAC address is configured in this session.
         
         It is expressed in hundredth of a percent accuracy.  
        
	 It is calculated as followed:
         MAX [(extendAluCfmPMProactivePrevious15MinLossFarEnd * 10000) / extendAluCfmPMProactivePrevious15MinTxNearEnd].
	 If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "
    ::= { extendAluCfmPMProactiveLossPrevious15MinIntervalEntry 20 }

extendAluCfmPMProactivePrevious15MinLossRatioAvgFarEnd   OBJECT-TYPE
    SYNTAX      ExtendAluCfmHundrethsOfPercentage
    ACCESS      read-only
    STATUS      mandatory
    DESCRIPTION
        "The value of this object is the average of accumulated Loss Ratio
         within the test duration of 15 minutes, at the far-end MEP,
         whose MAC address is configured in this session.It is expressed in hundredth of a percent accuracy.  
        
	 It is calculated as followed:
         AVG [(extendAluCfmPMProactivePrevious15MinLossFarEnd * 10000) / extendAluCfmPMProactivePrevious15MinTxNearEnd].
         If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        " 
    ::= { extendAluCfmPMProactiveLossPrevious15MinIntervalEntry 21 }

extendAluCfmPMProactivePrevious15MinPDUDiscarded OBJECT-TYPE
        SYNTAX      Counter
        ACCESS      read-only
        STATUS      mandatory
        DESCRIPTION
        "This object indicates the number of SLR/LMR PDUs discarded by this MEP in the previous 15 minutes.
         This will be incremented for every invalid SLR/LMR received. 
         Conditions:
            SLR :
              1. Late SLR - Not received within timeout (5 Secs). 
              2. Data TLV Validation Failure.
              3. Invalid firstTlvOffset.
              4. SLR received for the previous Measurement Interval.
              5. Received SLR Src MAC does not match with configured target MAC.
              6. Invalid Initiator/Responder MEPId range in SLR.
              7. txFcf/txFcb/testId in SLR is zero.
              8. SLR contains unknown TLV other than dataTlv.
              9. SLR destination MacAddress does not match with received mep MacAddress. 
             10. SLR source MacAddress match with receiving Mep MacAddress.
             11. SLR source Mac address is a multicast/broadcast Mac address. 
             12. SLR responder MEP id is equal to Initiator MEP Id. 
             13. Initiator MEP id int SLR packet does not match with the MEP id on which the SLM test is configured.
            LMR : 
              1. Invalid firstTlvOffset. 
              2. LMR destMacAddr does not match with mepMacAddress.
              3. LMR source Mac address matches with received MEP Mac Address.
              4. LMR source Mac address is a multicast/broadcast Mac address. 
              5. LMR sourceMac and configured targetMac mismatch.
              6. LMR version value is not equal to 1.
              7. LMR Flags field (LSB) value is not equal to 1.
              8. Duplicate LMR.ie.LMR already received for the LMM Sent.
              9. LMR contains any valid/invalid TLV.

         ALCATEL NOTE:
                ACCESS:     NA       USAGE:      NA
                PERSIST:    NO       INSRVMOD:   NA
                RANGE:      NA       DEFVALUE:   NA
                UNITS:      NA       SPARSE:     NA
        "
        ::= { extendAluCfmPMProactiveLossPrevious15MinIntervalEntry 22 }

--Previous 1 day result	
extendAluCfmPMProactiveLossPrevious1DayIntervalTable OBJECT-TYPE
    SYNTAX     SEQUENCE OF ExtendAluCfmPMProactiveLossPrevious1DayIntervalEntry
    ACCESS     not-accessible
    STATUS     mandatory
    DESCRIPTION
        "The extendAluCfmPMProactivePrevious1DayIntervalTable contains the
         previous 1 day interval loss statistics per Y1731 PM loss(SLM/LM) test."
    ::= { extendAluCfmPMObjects 8 }

extendAluCfmPMProactiveLossPrevious1DayIntervalEntry OBJECT-TYPE
    SYNTAX     ExtendAluCfmPMProactiveLossPrevious1DayIntervalEntry
    ACCESS     not-accessible
    STATUS     mandatory
    DESCRIPTION
        "Table entry for the previous 1 day interval loss statistics per Y1731 PM loss(SLM/LM) test."
    INDEX {
            dot1agCfmMdIndex,
            dot1agCfmMaIndex,
            dot1agCfmMepIdentifier,
            extendAluCfmPMProactiveConfigSessionIndex,
			extendAluCfmPMProactivePrevious1DayIntervalNumber
          }
    ::= { extendAluCfmPMProactiveLossPrevious1DayIntervalTable 1 }

ExtendAluCfmPMProactiveLossPrevious1DayIntervalEntry ::= SEQUENCE {
    extendAluCfmPMProactivePrevious1DayIntervalNumber           INTEGER,
    extendAluCfmPMProactivePrevious1DayTimeMeasured    		INTEGER,
    extendAluCfmPMProactivePrevious1DayInvalidDataFlag          INTEGER,
    extendAluCfmPMProactivePrevious1DayTestType   		ExtendAluCfmY1731TestType,
    extendAluCfmPMProactivePrevious1DayTestId                   Gauge,
    extendAluCfmPMProactivePrevious1DayRemoteMepId              Dot1agCfmMepIdOrNA,
    extendAluCfmPMProactivePrevious1DayPDUSent			Counter,
    extendAluCfmPMProactivePrevious1DayPDURecv			Counter,
    extendAluCfmPMProactivePrevious1DayRxNearEnd 		OCTET STRING, 
    extendAluCfmPMProactivePrevious1DayRxFarEnd 		OCTET STRING,
    extendAluCfmPMProactivePrevious1DayTxNearEnd 		OCTET STRING,
    extendAluCfmPMProactivePrevious1DayTxFarEnd 		OCTET STRING,
    extendAluCfmPMProactivePrevious1DayLossNearEnd 		OCTET STRING,
    extendAluCfmPMProactivePrevious1DayLossFarEnd 		OCTET STRING,
    extendAluCfmPMProactivePrevious1DayUnack                    OCTET STRING,
    extendAluCfmPMProactivePrevious1DayLossRatioMinNearEnd      ExtendAluCfmHundrethsOfPercentage,
    extendAluCfmPMProactivePrevious1DayLossRatioMaxNearEnd      ExtendAluCfmHundrethsOfPercentage,
    extendAluCfmPMProactivePrevious1DayLossRatioAvgNearEnd      ExtendAluCfmHundrethsOfPercentage,
    extendAluCfmPMProactivePrevious1DayLossRatioMinFarEnd       ExtendAluCfmHundrethsOfPercentage,
    extendAluCfmPMProactivePrevious1DayLossRatioMaxFarEnd       ExtendAluCfmHundrethsOfPercentage,
    extendAluCfmPMProactivePrevious1DayLossRatioAvgFarEnd       ExtendAluCfmHundrethsOfPercentage,
    extendAluCfmPMProactivePrevious1DayPDUDiscarded    	        Counter
}

extendAluCfmPMProactivePrevious1DayIntervalNumber OBJECT-TYPE
    SYNTAX      INTEGER (1..7)
    ACCESS      not-accessible
    STATUS      mandatory
    DESCRIPTION
        "A number,which identifies the interval for which the set of 
         statistics is available. The interval identified by 1 is the most recently 
         completed 1 day interval, and the interval identified by N is the
         interval immediately preceding the one identified by N-1. The number of 
         available intervals is specified by extendAluCfmPMProactive1DayValidIntervals.
     
         ALCATEL NOTE:
                ACCESS:     NA       USAGE:      NA
                PERSIST:    NO       INSRVMOD:   NA
                RANGE:      NA       DEFVALUE:   NA
                UNITS:      NA       SPARSE:     NA
        "

    ::= { extendAluCfmPMProactiveLossPrevious1DayIntervalEntry 1 }

extendAluCfmPMProactivePrevious1DayTimeMeasured OBJECT-TYPE
    SYNTAX      INTEGER 
    ACCESS      read-only
    STATUS      mandatory
    DESCRIPTION
        "The amount of time, measured in seconds, that statistics for this entry
         have been actually counted for the previous 1 day interval.
    	 This value will be the same as the elapsed duration except 
         in a situation where performance monitoring data could not be collected 
	 for this test for some reason.
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious1DayIntervalEntry 2 }

extendAluCfmPMProactivePrevious1DayInvalidDataFlag OBJECT-TYPE
        SYNTAX      INTEGER (0..1)
        ACCESS      read-only
        STATUS      mandatory
        DESCRIPTION     
        "This object indicates the validity of the corresponding PM data.
         It is set to 1 when the PM data is incomplete or invalid and set to 0
         when the PM data is complete and valid.

         ALCATEL NOTE:
             ACCESS:   NA                  USAGE:    NA
             PERSIST:  NO                  INSRVMOD: NA
             RANGE:    NA                  DEFVALUE: NA
             UNITS:    NA                  SPARSE:   NA
             DESCR:    NA
        "
    ::= { extendAluCfmPMProactiveLossPrevious1DayIntervalEntry 3 }

extendAluCfmPMProactivePrevious1DayTestType           OBJECT-TYPE
    SYNTAX      ExtendAluCfmY1731TestType
    ACCESS      read-only
    STATUS      mandatory
    DESCRIPTION
        "The value of this object indicates the type
         of test this row details.
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious1DayIntervalEntry 4 }

extendAluCfmPMProactivePrevious1DayTestId OBJECT-TYPE
    SYNTAX      Gauge
    ACCESS      read-only
    STATUS      mandatory
    DESCRIPTION
        "The value of this object indicates the test id used in the SLM packet 
         in this previous 1 day interval.
         This object is valid only if  the value of 
         extendAluCfmPMProactivePrevious1DayTestType is single-ended-slm.
         For single-ended-lm, the value of this object is not-applicable (0).
		ALCATEL NOTE:
         ACCESS:     NA       USAGE:      NA
         PERSIST:    NO       INSRVMOD:   NA
         RANGE:      NA       DEFVALUE:   NA
         UNITS:      NA       SPARSE:     NA
         DESCR:      NA"    
    ::= { extendAluCfmPMProactiveLossPrevious1DayIntervalEntry 5}

extendAluCfmPMProactivePrevious1DayRemoteMepId        OBJECT-TYPE
    SYNTAX      Dot1agCfmMepIdOrNA
    ACCESS      read-only
    STATUS      mandatory
    DESCRIPTION
        "The value of this object indicates the MEP  
         Identifier of the remote node corresponding to the 
         extendAluCfmPMProactiveConfigRemoteMepMacAddress
         from which the Synthetic Loss Measurement Reply (SLR) is received
         in this previous 1 day interval.

         This object is valid only if  the value of 
         extendAluCfmPMProactivePrevious1DayTestType is single-ended-slm.
         For single-ended-lm, the value of this object is not-applicable (65535).
         A value 0 indicates that the remote mep id is unknown.         
		ALCATEL NOTE:
         ACCESS:     NA       USAGE:      NA
         PERSIST:    NO       INSRVMOD:   NA
         RANGE:      NA       DEFVALUE:   NA
         UNITS:      NA       SPARSE:     NA
         DESCR:      NA"    
    ::= { extendAluCfmPMProactiveLossPrevious1DayIntervalEntry 6}

extendAluCfmPMProactivePrevious1DayPDUSent OBJECT-TYPE
        SYNTAX      Counter
	ACCESS      read-only
	STATUS      mandatory
	DESCRIPTION
	"This object indicates the number of SLM/LM PDUs sent by this MEP in this previous 1 day interval.
         ALCATEL NOTE:
                ACCESS:     NA       USAGE:      NA
                PERSIST:    NO       INSRVMOD:   NA
                RANGE:      NA       DEFVALUE:   NA
                UNITS:      NA       SPARSE:     NA
        "
	::= { extendAluCfmPMProactiveLossPrevious1DayIntervalEntry 7}

extendAluCfmPMProactivePrevious1DayPDURecv OBJECT-TYPE
        SYNTAX      Counter
	ACCESS      read-only
	STATUS      mandatory
	DESCRIPTION
	"This object indicates the number of SLR/LMR PDUs received from peer in this previous 1 day interval.
         ALCATEL NOTE:
                ACCESS:     NA       USAGE:      NA
                PERSIST:    NO       INSRVMOD:   NA
                RANGE:      NA       DEFVALUE:   NA
                UNITS:      NA       SPARSE:     NA
        "
	::= { extendAluCfmPMProactiveLossPrevious1DayIntervalEntry 8}


extendAluCfmPMProactivePrevious1DayRxNearEnd   OBJECT-TYPE
    SYNTAX      OCTET STRING (SIZE(8))
    ACCESS      read-only
    STATUS      mandatory
    DESCRIPTION
        "The value of this object is the accumulated number of frames received
         within the test duration of 1 day at this MEP (RxFCl).
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious1DayIntervalEntry 9 }
          
extendAluCfmPMProactivePrevious1DayRxFarEnd   OBJECT-TYPE
    SYNTAX      OCTET STRING (SIZE(8))
    ACCESS      read-only
    STATUS      mandatory
    DESCRIPTION
        "The value of this object is the accumulated number of frames received
         within the test duration of 1 day at the far-end MEP,
       	 whose MAC address is configured in this session.(RxFCf).
         For SLM, this is the value of TxFCb.
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious1DayIntervalEntry 10 }

extendAluCfmPMProactivePrevious1DayTxNearEnd   OBJECT-TYPE
    SYNTAX      OCTET STRING (SIZE(8))
    ACCESS      read-only
    STATUS      mandatory
    DESCRIPTION
        "The value of this object is the accumulated number of frames transmitted
         within the test duration of 1 day by this MEP (TxFCf).
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious1DayIntervalEntry 11 }
          
extendAluCfmPMProactivePrevious1DayTxFarEnd   OBJECT-TYPE
    SYNTAX      OCTET STRING (SIZE(8))
    ACCESS      read-only
    STATUS      mandatory
    DESCRIPTION
        "The value of this object is the accumulated number of frames transmitted
	 within the test duration of 1 day by far-end MEP,
    	 whose MAC address is configured in this session.(TxFCb)
          
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious1DayIntervalEntry 12 }
    
extendAluCfmPMProactivePrevious1DayLossNearEnd   OBJECT-TYPE
    SYNTAX      OCTET STRING (SIZE(8))
    ACCESS      read-only
    STATUS      mandatory
    DESCRIPTION
        "The value of this object is the accumulated number of frames 
         transmitted from the remote node but not received at the local
         node within the test duration of 1 day.
         
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious1DayIntervalEntry 13 }
          
extendAluCfmPMProactivePrevious1DayLossFarEnd   OBJECT-TYPE
    SYNTAX      OCTET STRING (SIZE(8))
    ACCESS      read-only
    STATUS      mandatory
    DESCRIPTION
        "The value of this object is the accumulated number of frames
         transmitted from the local node but not received at the remote
         node within the test duration of 1 day.
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious1DayIntervalEntry 14 }

extendAluCfmPMProactivePrevious1DayUnack OBJECT-TYPE
    SYNTAX      OCTET STRING (SIZE(8))
    ACCESS      read-only
    STATUS      mandatory
    DESCRIPTION
        "The value of this object is the accumulated number of SLM frames
         that are unacknowledged within the test duration of 1 day.
         This object is valid only if the value of 
         extendAluCfmPMProactivePrevious1DayTestType is single-ended-slm.
         For single-ended-lm, the value of this object is 
         18446744073709551615 ((2^64)-1), which means it is not-applicable.         
         ALCATEL NOTE:
                ACCESS:     NA       USAGE:      NA
                PERSIST:    NO       INSRVMOD:   NA
                RANGE:      NA       DEFVALUE:   NA
                UNITS:      NA       SPARSE:     NA
        "
    ::= { extendAluCfmPMProactiveLossPrevious1DayIntervalEntry 15 }

extendAluCfmPMProactivePrevious1DayLossRatioMinNearEnd   OBJECT-TYPE
    SYNTAX      ExtendAluCfmHundrethsOfPercentage
    ACCESS      read-only
    STATUS      mandatory
    DESCRIPTION
        "The value of this object is the minimum value of 
         accumulated Loss Ratio within the test duration of 1 day,
	 at this MEP.It is expressed in hundredth of a percent accuracy.  
        
	It is calculated as followed:        
        MIN [(extendAluCfmPMProactivePrevious1DayLossNearEnd * 10000) / extendAluCfmPMProactivePrevious1DayTxFarEnd].
	If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "

    ::= { extendAluCfmPMProactiveLossPrevious1DayIntervalEntry 16 }

extendAluCfmPMProactivePrevious1DayLossRatioMaxNearEnd   OBJECT-TYPE
    SYNTAX      ExtendAluCfmHundrethsOfPercentage
    ACCESS      read-only
    STATUS      mandatory
    DESCRIPTION
        "The value of this object is the maximum value of accumulated Loss Ratio 
         within the test duration of 1 day,at this MEP.
         It is expressed in hundredth of a percent accuracy.  
        
	 It is calculated as followed:  

         MAX [(extendAluCfmPMProactivePrevious1DayLossNearEnd * 10000) / extendAluCfmPMProactivePrevious1DayTxFarEnd].
	 If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "

    ::= { extendAluCfmPMProactiveLossPrevious1DayIntervalEntry 17 }

extendAluCfmPMProactivePrevious1DayLossRatioAvgNearEnd   OBJECT-TYPE
    SYNTAX      ExtendAluCfmHundrethsOfPercentage
    ACCESS      read-only
    STATUS      mandatory
    DESCRIPTION
        "The value of this object is the average value of accumulated Loss Ratio 
         within the test duration of 1 day,at this MEP.
         It is expressed in hundredth of a percent accuracy.  
        
	 It is calculated as followed:  
         AVG [(extendAluCfmPMProactivePrevious1DayLossNearEnd * 10000) / extendAluCfmPMProactivePrevious1DayTxFarEnd].
	 If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "

    ::= { extendAluCfmPMProactiveLossPrevious1DayIntervalEntry 18 }
	
extendAluCfmPMProactivePrevious1DayLossRatioMinFarEnd   OBJECT-TYPE
    SYNTAX      ExtendAluCfmHundrethsOfPercentage
    ACCESS      read-only
    STATUS      mandatory
    DESCRIPTION
        "The value of this object is the minimum of accumulated Loss Ratio 
         within the test duration of 1 day, at the far-end MEP, 
         whose MAC address is configured in this session.
         
         It is expressed in hundredth of a percent accuracy.  
         It is calculated as followed:

         MIN [(extendAluCfmPMProactivePrevious1DayLossFarEnd * 10000) / extendAluCfmPMProactivePrevious1DayTxNearEnd].
         If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "
    ::= { extendAluCfmPMProactiveLossPrevious1DayIntervalEntry 19 }

extendAluCfmPMProactivePrevious1DayLossRatioMaxFarEnd   OBJECT-TYPE
    SYNTAX      ExtendAluCfmHundrethsOfPercentage
    ACCESS      read-only
    STATUS      mandatory
    DESCRIPTION
        "The value of this object is the maximum of accumulated Loss Ratio
         within the test duration of 1 day, at 
         the far-end MEP, whose MAC address is configured in this session.
         
         It is expressed in hundredth of a percent accuracy.  
        
	 It is calculated as followed:
         MAX [(extendAluCfmPMProactivePrevious1DayLossFarEnd * 10000) / extendAluCfmPMProactivePrevious1DayTxNearEnd].
         If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        "
    ::= { extendAluCfmPMProactiveLossPrevious1DayIntervalEntry 20 }

extendAluCfmPMProactivePrevious1DayLossRatioAvgFarEnd   OBJECT-TYPE
    SYNTAX      ExtendAluCfmHundrethsOfPercentage
    ACCESS      read-only
    STATUS      mandatory
    DESCRIPTION
        "The value of this object is the average of accumulated Loss Ratio
         within the test duration of 1 day, at the far-end MEP,
         whose MAC address is configured in this session.It is expressed in hundredth of a percent accuracy.  
        
	 It is calculated as followed:
         AVG [(extendAluCfmPMProactivePrevious1DayLossFarEnd * 10000) / extendAluCfmPMProactivePrevious1DayTxNearEnd].
	 If value is 65535, it means that the percentage is invalid (greater than 100 or less than 0).

         ALCATEL NOTE:
                ACCESS:     NA       USAGE:      NA
                PERSIST:    NO       INSRVMOD:   NA
                RANGE:      0..10000 | 65535              DEFVALUE:   NA
                UNITS:      Hundreths of percentage      SPARSE:     NA
        " 
    ::= { extendAluCfmPMProactiveLossPrevious1DayIntervalEntry 21 }

extendAluCfmPMProactivePrevious1DayPDUDiscarded OBJECT-TYPE
        SYNTAX      Counter
        ACCESS      read-only
        STATUS      mandatory
        DESCRIPTION
        "This object indicates the number of SLR/LMR PDUs discarded by this MEP in the previous 1 Day.
         This will be incremented for every invalid SLR/LMR received. 
         Conditions:
            SLR :
              1. Late SLR - Not received within timeout (5 Secs). 
              2. Data TLV Validation Failure.
              3. Invalid firstTlvOffset.
              4. SLR received for the previous Measurement Interval.
              5. Received SLR Src MAC does not match with configured target MAC.
              6. Invalid Initiator/Responder MEPId range in SLR.
              7. txFcf/txFcb/testId in SLR is zero.
              8. SLR contains unknown TLV other than dataTlv.
              9. SLR destination MacAddress does not match with received mep MacAddress. 
             10. SLR source MacAddress match with receiving Mep MacAddress.
             11. SLR source Mac address is a multicast/broadcast Mac address. 
             12. SLR responder MEP id is equal to Initiator MEP Id. 
             13. Initiator MEP id int SLR packet does not match with the MEP id on which the SLM test is configured.
            LMR : 
              1. Invalid firstTlvOffset. 
              2. LMR destMacAddr does not match with mepMacAddress.
              3. LMR source Mac address matches with received MEP Mac Address.
              4. LMR source Mac address is a multicast/broadcast Mac address. 
              5. LMR sourceMac and configured targetMac mismatch.
              6. LMR version value is not equal to 1.
              7. LMR Flags field (LSB) value is not equal to 1.
              8. Duplicate LMR.ie.LMR already received for the LMM Sent.
              9. LMR contains any valid/invalid TLV.

         ALCATEL NOTE:
                ACCESS:     NA       USAGE:      NA
                PERSIST:    NO       INSRVMOD:   NA
                RANGE:      NA       DEFVALUE:   NA
                UNITS:      NA       SPARSE:     NA
        "
        ::= { extendAluCfmPMProactiveLossPrevious1DayIntervalEntry 22 }



-- ***********************************************************************
--    Extend CFM CFM Stack Table
-- ***********************************************************************


extendAluCfmStackTable OBJECT-TYPE
    SYNTAX      SEQUENCE OF ExtendAluCfmStackEntry
    ACCESS      not-accessible
    STATUS      mandatory
    DESCRIPTION 
        "Extend dot1agCfmStackTable:
        There is one CFM Stack table per bridge. It permits
         the retrieval of information about the Maintenance Points
         configured on any given interface.
         Add support to mep lt bridgeport, add equipment as index.
         ALCATEL NOTE:
             TABLESIZE: NA
             DESCR: The stack table lists all the MEPs and MIPs of the 
                   operational LTs in the system. There is no fixed limits;                 
                   it is dependent on the number of MEPs configured and the 
                   number of MIPs applied."
--     REFERENCE   
--         "extend 802.1ag clauses 12.14.2"
    ::= { extendAluCfmMIB 12 }

extendAluCfmStackEntry OBJECT-TYPE
    SYNTAX      ExtendAluCfmStackEntry
    ACCESS      not-accessible
    STATUS      mandatory
    DESCRIPTION 
     "Extend dot1agCfmStackTable:
		The Stack table entry.
       ALCATEL NOTE:
       Row creation : Auto-instantiated as a result of an MP creation.
       Row deletion : Auto-deleted as a result of an MP deletion. 
       Index usage  : See INDEX below.
       lexicographical order : Sorted on StackifIndex,then equipment, then StackVlanIndex,
                               then StackMdLevel, and then StackDirection.
            dot1agCfmStackVlanIdOrNone has been replaced with 
            dot1agCfmStackVlanIndex in order to support S+C notation."
    INDEX { extendAluCfmStackifIndex,extendAluCfmStackEquipment, extendAluCfmStackVlanIndex, 
                  extendAluCfmStackMdLevel, extendAluCfmStackDirection }
    ::= { extendAluCfmStackTable 1 }

    ExtendAluCfmStackEntry ::= SEQUENCE {
    extendAluCfmStackifIndex          InterfaceIndex,
    extendAluCfmStackEquipment		   AluCfmMepEquipmentType,
    extendAluCfmStackVlanIndex        VlanIndex,
    extendAluCfmStackMdLevel          Dot1agCfmMDLevel,
    extendAluCfmStackDirection        Dot1agCfmMpDirection,
    extendAluCfmStackMdIndex          Gauge,
    extendAluCfmStackMaIndex          Gauge,
    extendAluCfmStackMepId            Dot1agCfmMepIdOrZero,
    extendAluCfmStackMacAddress       MacAddress
}

extendAluCfmStackifIndex OBJECT-TYPE
    SYNTAX      InterfaceIndex
    ACCESS      not-accessible
    STATUS      mandatory
    DESCRIPTION 
        "Extend dot1agCfmStackTable:
		This object represents the  Bridge Port or aggregated port
         on which MEPs or MHFs might be configured.
         ALCATEL NOTE:
                ACCESS:     NA       USAGE:      NA
                PERSIST:    NO       INSRVMOD:   NO
                RANGE:      NA       DEFVALUE:   NA
                UNITS:      NA       SPARSE:     NA
                DESCR:      NA"
--     REFERENCE   
--         "802.1ag clause 12.14.2.1.2:a"
    ::= { extendAluCfmStackEntry 1 }

extendAluCfmStackEquipment OBJECT-TYPE
   SYNTAX AluCfmMepEquipmentType
   ACCESS read-write
	 STATUS mandatory
	 DESCRIPTION
         " Identifies the equpment type of mep ;
         	0 is for Gpon onu and Dsl ;
         	1 is for Gpon Lt ;
			2 is for Gpon onu;
         	
 		 ALCATEL NOTE:
                            ACCESS:     RW       USAGE:      OPT
                            PERSIST:    YES      INSRVMOD:   NA
                            RANGE:      NA       DEFVALUE:   NA 
                            UNITS:      NA       SPARSE:     NA
                 "
  DEFVAL { default}
	::= { extendAluCfmStackEntry 2 }
	
 extendAluCfmStackVlanIndex OBJECT-TYPE
    SYNTAX      VlanIndex
    ACCESS      not-accessible
    STATUS      mandatory
    DESCRIPTION 
        "Extend dot1agCfmStackTable:
        VLAN ID to which the MP is attached.
         ALCATEL NOTE:
                ACCESS:     NA       USAGE:      NA
                PERSIST:    NO       INSRVMOD:   NO
                RANGE:      NA       DEFVALUE:   NA
                UNITS:      NA       SPARSE:     NA
                DESCR:      dot1agCfmStackVlanIdOrNone has been replaced to
                            dot1agCfmStackVlanIndex in order to support
                            S+C notation."
--     REFERENCE   
--         "802.1ag clause 12.14.2.1.2:d"
    ::= { extendAluCfmStackEntry 3 }

extendAluCfmStackMdLevel OBJECT-TYPE
    SYNTAX      Dot1agCfmMDLevel
    ACCESS      not-accessible
    STATUS      mandatory
    DESCRIPTION 
        "Extend dot1agCfmStackTable:
        MD Level of the Maintenance Point.
         ALCATEL NOTE:
                ACCESS:     NA       USAGE:      NA
                PERSIST:    NO       INSRVMOD:   NO
                RANGE:      NA       DEFVALUE:   NA
                UNITS:      NA       SPARSE:     NA
                DESCR:      NA"
--     REFERENCE   
--         "802.1ag clause 12.14.2.1.2:b"
    ::= { extendAluCfmStackEntry 4 }

extendAluCfmStackDirection OBJECT-TYPE
    SYNTAX      Dot1agCfmMpDirection
    ACCESS      not-accessible
    STATUS      mandatory
    DESCRIPTION 
        "Extend dot1agCfmStackTable:
        Direction in which the MP faces on the Bridge Port.
         ALCATEL NOTE:
                ACCESS:     NA       USAGE:      NA
                PERSIST:    NO       INSRVMOD:   NO
                RANGE:      NA       DEFVALUE:   NA
                UNITS:      NA       SPARSE:     NA
                DESCR:      NA"
--     REFERENCE   
--         "802.1ag clause 12.14.2.1.2:c"
    ::= { extendAluCfmStackEntry 5 }
  

  extendAluCfmStackMdIndex OBJECT-TYPE
    SYNTAX      Gauge
    ACCESS      read-only
    STATUS      mandatory
    DESCRIPTION 
        "Extend dot1agCfmStackTable:
         The index of the Maintenance Domain in the dot1agCfmMdTable
         to which the MP is associated, or 0, if none.
         ALCATEL NOTE:
                ACCESS:     NA       USAGE:      NA
                PERSIST:    NO       INSRVMOD:   NO
                RANGE:      NA       DEFVALUE:   NA
                UNITS:      NA       SPARSE:     NA
                DESCR:      NA"
--     REFERENCE   
--         "802.1ag clause 12.14.2.1.3:b"
    ::= { extendAluCfmStackEntry 6 }

 extendAluCfmStackMaIndex OBJECT-TYPE
    SYNTAX      Gauge
    ACCESS      read-only
    STATUS      mandatory
    DESCRIPTION 
        "Extend dot1agCfmStackTable:
         The index of the MA in the dot1agCfmMaTable to which the MP
         is associated, or 0, if none.
         ALCATEL NOTE:
                ACCESS:     NA       USAGE:      NA
                PERSIST:    NO       INSRVMOD:   NO
                RANGE:      NA       DEFVALUE:   NA
                UNITS:      NA       SPARSE:     NA
                DESCR:      NA"
--     REFERENCE   
--         "802.1ag clause 12.14.2.1.3:c"
    ::= { extendAluCfmStackEntry 7 }

extendAluCfmStackMepId OBJECT-TYPE
    SYNTAX      Dot1agCfmMepIdOrZero
    ACCESS      read-only
    STATUS      mandatory
    DESCRIPTION 
        "Extend dot1agCfmStackTable:
        If an MEP is configured, the MEPID, the value 0 indicates a MIP.
        ALCATEL NOTE:
                ACCESS:     NA       USAGE:      NA
                PERSIST:    NO       INSRVMOD:   NO
                RANGE:      NA       DEFVALUE:   NA
                UNITS:      NA       SPARSE:     NA
                DESCR:      NA"
--     REFERENCE   
--         "802.1ag clause 12.14.2.1.3:d"
    ::= { extendAluCfmStackEntry 8 }

extendAluCfmStackMacAddress OBJECT-TYPE
    SYNTAX      MacAddress
    ACCESS      read-only
    STATUS      mandatory
    DESCRIPTION 
        "Extend dot1agCfmStackTable:
         MAC address of the MP.
         ALCATEL NOTE:
                ACCESS:     NA       USAGE:      NA
                PERSIST:    NO       INSRVMOD:   NO
                RANGE:      NA       DEFVALUE:   NA
                UNITS:      NA       SPARSE:     NA
                DESCR:      NA"
--     REFERENCE   
--         "802.1ag clause 12.14.2.1.3:e"
    ::= { extendAluCfmStackEntry 9 }



END
