IACM-DIST-MPLS-MIB DEFINITIONS ::= BEGIN
-- =============================================================================
--  This specification is published by Alcatel-Lucent under Non-Disclosure
--  Agreement(s) (NDA) with specific parties and has to be considered as
--  Confidential Information as defined in such NDA.
--  Alcatel-Lucent reserves the right to revise this document for any reason,
--  including but not limited to conformity with standards promulgated by
--  various agencies, utilisation of advances in the state of the technical
--  areas, or the reflection of changes in the design of any equipment,
--  techniques, or procedures described or referred to herein.
--  The product specifications and other technical or performance information
--  contained herein are subject to change without notice.
--  Updates of this document will be issued under the above NDA's.
--  Alcatel-Lucent makes no representation or warranty, expressed or implied, with
--  respect to the sufficiency, accuracy, or utility of any information or
--  opinion contained herein. Alcatel-Lucent expressly advises that any use of for 
--  any purpose or reliance upon this technical reference is at the risk of
--  the user and that Alcatel-Lucent shall not be liable for any damage or injury
--  incurred by any person arising out of the sufficiency, accuracy, or
--  utility of any information or opinion contained herein.
--  This document is not to be construed as a suggestion to any manufacturer
--  to modify or change any of its products, nor does this document represent
--  any commitment by Alcatel-Lucent to sell or purchase any product.
--  Nothing contained herein shall be construed as conferring by implication,
--  estoppel, or otherwise any license or right under any patent, whether or
--  not the use of any information herein necessarily employs an invention of
--  any existing or later issued patent.
--  Alcatel-Lucent reserves the right not to offer any or all of these products and
--  to withdraw any or all of them at any future time.
--  Copyright (C) 2010, Alcatel-Lucent. All Rights Reserved.
-- =============================================================================

-- MODULE-IDENTITY 
--       LAST-UPDATED "201010260900Z"
--       ORGANIZATION "Alcatel-Lucent"
--       CONTACT-INFO
--
--            "Email:  asam.mibsupport@alcatel.be" 
--
-- DESCRIPTION "This MIB module supports extended configuration and    
--              performance parameters for the Mpls facilities."

--  REVISION "201010260900Z"
--  DESCRIPTION
--        "Version: <MIB identification>
--         Editor: <name of document author>
--         Changes:  Initial Version"



IMPORTS

	asam
		FROM SYSTEM-MIB

	OBJECT-TYPE
		FROM RFC-1212

	InterfaceIndexOrZero
		FROM ITF-MIB

	InetAddress, InetAddressType, InetAddressPrefixLength 
		FROM INET-ADDRESS-MIB

	vrfIndex
		FROM VRF-MIB

	RowStatus 
		FROM SNMPv2-TC;


iacmDistMplsMIB OBJECT IDENTIFIER ::= { asam  96 } 

-- Groups in iacmDistMplsMIB

iacmDistMplsObjects  OBJECT IDENTIFIER ::= { iacmDistMplsMIB 1 }

       IacmDistMplsLabel ::= INTEGER (0..4294967295)
--          TEXTUAL-CONVENTION
--          STATUS        mandatory
--          DESCRIPTION
--             "
--              The label contents are specific to the label being
--              represented, such as:
--
--              * The label carried in an MPLS shim header
--                (for LDP this is the Generic Label) is a 20-bit
--                number represented by 4 octets.  Bits 0-19 contain
--                a label or a reserved label value.  Bits 20-31
--                MUST be zero.
--
--                The following is quoted directly from [RFC3032].
--                There are several reserved label values:
--
--                   i. A value of 0 represents the
--                      'IPv4 Explicit NULL Label'.  This label
--                      value is only legal at the bottom of the
--                      label stack.  It indicates that the label
--                      stack must be popped, and the forwarding
--                      of the packet must then be based on the
--                      IPv4 header.
--
--                  ii. A value of 1 represents the
--                      'Router Alert Label'.  This label value is
--                      legal anywhere in the label stack except at
--                      the bottom.  When a received packet
--                      contains this label value at the top of
--                      the label stack, it is delivered to a
--                      local software module for processing.
--                      The actual forwarding of the packet
--                      is determined by the label beneath it
--                      in the stack.  However, if the packet is
--                      forwarded further, the Router Alert Label
--                      should be pushed back onto the label stack
--                      before forwarding.  The use of this label
--                      is analogous to the use of the
--                      'Router Alert Option' in IP packets
--                      [RFC2113].  Since this label
--                      cannot occur at the bottom of the stack,
--                      it is not associated with a
--                      particular network layer protocol.
--
--                 iii. A value of 2 represents the
--                      'IPv6 Explicit NULL Label'.  This label
--                      value is only legal at the bottom of the
--                      label stack.  It indicates that the label
--                      stack must be popped, and the forwarding
--                      of the packet must then be based on the
--                      IPv6 header.
--
--                  iv. A value of 3 represents the
--                      'Implicit NULL Label'.
--                      This is a label that an LSR may assign and
--                      distribute, but which never actually
--                      appears in the encapsulation.  When an
--                      LSR would otherwise replace the label
--                      at the top of the stack with a new label,
--                      but the new label is 'Implicit NULL',
--                      the LSR will pop the stack instead of
--                      doing the replacement.  Although
--                      this value may never appear in the
--                      encapsulation, it needs to be specified in
--                      the Label Distribution Protocol, so a value
--                      is reserved.

--                   v. Values 4-15 are reserved.
--
--              * The frame relay label can be either 10-bits or
--                23-bits depending on the DLCI field size and the
--                upper 22-bits or upper 9-bits must be zero,
--                respectively.
--
--              * For an ATM label the lower 16-bits represents the
--                VCI, the next 12-bits represents the VPI and the
--                remaining bits MUST be zero.
--
--              * The Generalized-MPLS (GMPLS) label contains a
--                value greater than 2^24-1 and used in GMPLS
--                as defined in [RFC3471]."
--          SYNTAX  Unsigned32 (0..4294967295)

-- in-segment table.
iacmDistMplsInSegTable  OBJECT-TYPE
   SYNTAX        SEQUENCE OF IacmDistMplsInSegEntry
   ACCESS        not-accessible
   STATUS        mandatory
   DESCRIPTION
       "This table contains the description of the incoming MPLS         
	segments (labels) to LSR and their associated parameters."
      ::= { iacmDistMplsObjects 1 }

iacmDistMplsInSegEntry  OBJECT-TYPE
   SYNTAX        IacmDistMplsInSegEntry
   ACCESS        not-accessible
   STATUS        mandatory
   DESCRIPTION
       "An entry in this table represents one incoming
        segment for an mpls enabled ip interface.
        An entry can be created by a network
        administrator or an SNMP agent.
	The value of mplsInSegRowStatus cannot be active(1)
        unless the ifTable entry corresponding to
        iacmDistMplsInSegInterface exists."
   INDEX { iacmDistMplsInSegIfIndex,
	   iacmDistMplsInSegLabel }
   ::= { iacmDistMplsInSegTable 1 }

IacmDistMplsInSegEntry ::= SEQUENCE {
  iacmDistMplsInSegIfIndex		InterfaceIndexOrZero,
  iacmDistMplsInSegLabel		IacmDistMplsLabel,
  iacmDistMplsInSegRowStatus		RowStatus
}

iacmDistMplsInSegIfIndex OBJECT-TYPE
   SYNTAX        InterfaceIndexOrZero
   ACCESS        not-accessible
   STATUS        mandatory
   DESCRIPTION
       "This index of the in-segment entry represents the 
	interface ifIndex associated to the corresponding MPLS 
	enabled ip interface.

	ALCATEL NOTE:
            ACCESS:      NA           USAGE:       NA
            PERSIST:     YES          INSRVMOD:    NO
            RANGE:       NA           DEFVALUE:    NA
            UNITS:       NA           SPARSE:      NA
            DESCR:       NA
	"

   ::= { iacmDistMplsInSegEntry 1 }

iacmDistMplsInSegLabel OBJECT-TYPE
   SYNTAX        IacmDistMplsLabel
   ACCESS   	 not-accessible
   STATUS        mandatory 
   DESCRIPTION
	"The incoming label associated with this MPLS in-segment entry.
	 This value should be unique in the system and shall not be modified
	 once the entry is active.

	ALCATEL NOTE:
            ACCESS:      NA           USAGE:       NA
            PERSIST:     YES          INSRVMOD:    NO
            RANGE:       32..1023     DEFVALUE:    NA
            UNITS:       NA           SPARSE:      NA
            DESCR:       NA
	"

   ::= { iacmDistMplsInSegEntry 2 }

iacmDistMplsInSegRowStatus OBJECT-TYPE
   SYNTAX        RowStatus
   ACCESS        read-write
   STATUS        mandatory
   DESCRIPTION
       "This variable is used to create and delete
        a row in this table. When a row in this
        table has a row in the active(1) state, no
        objects in this row can be modified except the
        iacmDistmplsInSegRowStatus.

	ALCATEL NOTE:
            ACCESS:      NA           USAGE:       MAND
            PERSIST:     NO           INSRVMOD:    YES
            RANGE:       1,4,6        DEFVALUE:    NA
            UNITS:       NA           SPARSE:      NA
            DESCR:       NA
	"

   ::= { iacmDistMplsInSegEntry 3 }

--
--  The Virtual Router MPLS Labeled Switch Path (LSP) Table
--

iacmDistVRtrMplsLspIndexNext OBJECT-TYPE
   SYNTAX        INTEGER (0..65535)
   ACCESS   	 read-only
   STATUS        mandatory
   DESCRIPTION
       "This object contains the next available value to
        be used for iacmDistVRtrMplsLspIndex when creating entries
        in the mplsOutSegTable. A value of '0' indicates 
	that no new entries can be created in this table."
   ::= { iacmDistMplsObjects 2 }

iacmDistVRtrMplsLspTable    OBJECT-TYPE
    SYNTAX      SEQUENCE OF IacmDistVRtrMplsLspEntry
    ACCESS 	not-accessible
    STATUS      mandatory
    DESCRIPTION
        "The iacmDistVRtrMplsLspTable has an entry for each Labeled
         Switch Path (LSP) configured for a virtual router in the system."
    ::= { iacmDistMplsObjects 3 }

iacmDistVRtrMplsLspEntry    OBJECT-TYPE
    SYNTAX      IacmDistVRtrMplsLspEntry
    ACCESS  	not-accessible
    STATUS      mandatory
    DESCRIPTION
        "Each row entry represents a Labeled Switch Path (LSP) configured.
	 for a virtual router in the system. Entries can be created and 
	 deleted via SNMP SET operations."

    INDEX { vrfIndex, iacmDistVRtrMplsLspIndex }
    ::= { iacmDistVRtrMplsLspTable 1 }

IacmDistVRtrMplsLspEntry ::= SEQUENCE {
	iacmDistVRtrMplsLspIndex                INTEGER,
	iacmDistVRtrMplsLspName                 OCTET STRING,
	iacmDistMplsOutSegInterface		InterfaceIndexOrZero,
	iacmDistMplsOutSegTopLabel             	IacmDistMplsLabel,
	iacmDistMplsOutSegNextHopIpAddrType    	InetAddressType, 
	iacmDistMplsOutSegNextHopIpv4Addr      	InetAddress,    
	iacmDistVRtrMplsLspRowStatus            RowStatus
	}

iacmDistVRtrMplsLspIndex OBJECT-TYPE
   SYNTAX        INTEGER (0..65535)
   ACCESS    	 not-accessible
   STATUS        mandatory
   DESCRIPTION
       "The unique value which identifies this Labeled Switch
         Path (LSP) for this virtual router system.  It is a 
	 unique value among entries with the same value of vrfIndex.
        
	ALCATEL NOTE:
            ACCESS:      NA           USAGE:       NA
            PERSIST:     YES          INSRVMOD:    NO
            RANGE:       1..992       DEFVALUE:    NA
            UNITS:       NA           SPARSE:      NA
            DESCR:       NA
	"
   ::= { iacmDistVRtrMplsLspEntry 1 }

iacmDistVRtrMplsLspName     OBJECT-TYPE
    SYNTAX      OCTET STRING (SIZE (0 | 1..32))
    ACCESS 	read-write
    STATUS      mandatory
    DESCRIPTION
        "Administrative name for this Labeled Switch Path.
         The iacmDistVRtrMplsLspName must be unique unique within 
         a virtual router instance.

	ALCATEL NOTE:
            ACCESS:      NA           USAGE:       NA
            PERSIST:     YES          INSRVMOD:    NO
            RANGE:       1..32        DEFVALUE:    NA
            UNITS:       NA           SPARSE:      NA
            DESCR:       NA
	"
    ::= { iacmDistVRtrMplsLspEntry 2 }

iacmDistMplsOutSegInterface OBJECT-TYPE
   SYNTAX        InterfaceIndexOrZero
   ACCESS    	 read-write
   STATUS        mandatory
   DESCRIPTION
       "This value must contain the interface index of the
        outgoing interface. This object cannot be modified
        if iacmDistVRtrMplsLspRowStatus is active(1). The
        iacmDistVRtrMplsLspRowStatus cannot be set to active(1)
        until this object is set to a value corresponding to
        a valid ifEntry.

	ALCATEL NOTE:
            ACCESS:      NA           USAGE:       NA
            PERSIST:     YES          INSRVMOD:    NO
            RANGE:       NA           DEFVALUE:    NA
            UNITS:       NA           SPARSE:      NA
            DESCR:       NA
	"

   ::= { iacmDistVRtrMplsLspEntry 3 }

iacmDistMplsOutSegTopLabel OBJECT-TYPE
   SYNTAX        IacmDistMplsLabel
   ACCESS        read-write
   STATUS        mandatory
   DESCRIPTION
       "Represents the label that should be pushed onto the
        top of the outgoing packet's label stack.

	ALCATEL NOTE:
            ACCESS:      NA           USAGE:       NA
            PERSIST:     YES          INSRVMOD:    NO
            RANGE:       1..1048575   DEFVALUE:    NA
            UNITS:       NA           SPARSE:      NA
            DESCR:       NA
	"
   ::= { iacmDistVRtrMplsLspEntry 4 }

iacmDistMplsOutSegNextHopIpAddrType OBJECT-TYPE
   SYNTAX        InetAddressType
   ACCESS    	 read-write
   STATUS        optional
   DESCRIPTION
       "Indicates the next hop Internet address type.
        Only values ipv4(1) or ipv6(2) have to be supported.

        If any other unsupported values are attempted in a set
        operation, the agent MUST return an inconsistentValue
        error.

	ALCATEL NOTE:
            ACCESS:      NA           USAGE:       OPT
            PERSIST:     YES          INSRVMOD:    NO
            RANGE:       1            DEFVALUE:    1
            UNITS:       NA           SPARSE:      NA
            DESCR:       Only ipv4 is supported.
	"

   DEFVAL	{ 1 }
   ::= { iacmDistVRtrMplsLspEntry 5 }

iacmDistMplsOutSegNextHopIpv4Addr OBJECT-TYPE
   SYNTAX        InetAddress
   ACCESS    	 read-write
   STATUS        mandatory
   DESCRIPTION
       "The internet address of the next hop. The type of
        this address is determined by the value of the
        iacmDistMplsOutSegNextHopIpAddrType object.

	ALCATEL NOTE:
            ACCESS:      NA           USAGE:       NA
            PERSIST:     YES          INSRVMOD:    NO
            RANGE:       NA           DEFVALUE:    NA
            UNITS:       NA           SPARSE:      NA
            DESCR:       NA
	"

   ::= { iacmDistVRtrMplsLspEntry 6 }

iacmDistVRtrMplsLspRowStatus OBJECT-TYPE
   SYNTAX        RowStatus
   ACCESS   	 read-write
   STATUS        mandatory
   DESCRIPTION
       "For creating and deleting this row. When
        a row in this table has a row in the active(1)
        state, no objects in this row can be modified
        except the iacmDistVRtrMplsLspRowStatus.

	ALCATEL NOTE:
            ACCESS:      NA           USAGE:       MAND
            PERSIST:     NO           INSRVMOD:    YES
            RANGE:       1,4,6        DEFVALUE:    NA
            UNITS:       NA           SPARSE:      NA
            DESCR:       NA
	"

   ::= { iacmDistVRtrMplsLspEntry 7 }

iacmDistMplsLspNameToIndexMapTable OBJECT-TYPE
	SYNTAX		SEQUENCE OF IacmDistMplsLspNameToIndexMapEntry
	ACCESS		not-accessible
	STATUS		mandatory
	DESCRIPTION	
		"This table contains the iacmDistVRtrMplsLspMapIndex for the 
	corresponding iacmDistVRtrMplsLspMapName." 
	::= { iacmDistMplsObjects 4 }

iacmDistMplsLspNameToIndexMapEntry OBJECT-TYPE
	SYNTAX		IacmDistMplsLspNameToIndexMapEntry			
        ACCESS		not-accessible
        STATUS		mandatory	
        DESCRIPTION	
		"A reverse table shall be automatically created
         upon creation of iacmDistVRtrMplsLspEntry entry by the manager."

	INDEX { vrfIndex, iacmDistVRtrMplsLspMapName }
	::= { iacmDistMplsLspNameToIndexMapTable 1 }

IacmDistMplsLspNameToIndexMapEntry ::= SEQUENCE {
		iacmDistVRtrMplsLspMapName		OCTET STRING,
		iacmDistVRtrMplsLspMapIndex		INTEGER	
			}

iacmDistVRtrMplsLspMapName     OBJECT-TYPE
    SYNTAX      OCTET STRING (SIZE (0 | 1..32))
    ACCESS  	not-accessible
    STATUS      mandatory
    DESCRIPTION
        "Administrative name for the Labeled Switch Path.
         The iacmDistVRtrMplsLspMapName must be unique within 
	 the virtual router instance.

	ALCATEL NOTE:
            ACCESS:      NA           USAGE:       NA
            PERSIST:     NO           INSRVMOD:    NO
            RANGE:       1..32        DEFVALUE:    NA
            UNITS:       NA           SPARSE:      NA
            DESCR:       NA
	"
    ::= { iacmDistMplsLspNameToIndexMapEntry 1 }

iacmDistVRtrMplsLspMapIndex OBJECT-TYPE
   SYNTAX        INTEGER (0..65535)
   ACCESS   	 read-only
   STATUS        mandatory
   DESCRIPTION
       "This value contains the index for the given
		iacmDistVRtrMplsLspMapName.

ALCATEL NOTE:
            ACCESS:      NA           USAGE:       NA
            PERSIST:     NO           INSRVMOD:    NO
            RANGE:       1..992       DEFVALUE:    NA
            UNITS:       NA           SPARSE:      NA
            DESCR:       NA
	"
   ::= { iacmDistMplsLspNameToIndexMapEntry 2 }

END
