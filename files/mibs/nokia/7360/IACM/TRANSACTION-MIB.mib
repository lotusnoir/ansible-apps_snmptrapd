TRANSACTION-MIB DEFINITIONS ::= BEGIN

-- ===========================================================================
--  This specification is published by Alcatel under Non-Disclosure
--  Agreement(s) (NDA) with specific parties and has to be considered as
--  Confidential Information as defined in such NDA.
--  Alcatel reserves the right to revise this document for any reason,
--  including but not limited to conformity with standards promulgated by
--  various agencies, utilisation of advances in the state of the technical
--  areas, or the reflection of changes in the design of any equipment,
--  techniques, or procedures described or referred to herein.
--  The product specifications and other technical or performance information
--  contained herein are subject to change without notice.
--  Updates of this document will be issued under the above NDA's.
--  Alcatel makes no representation or warranty, expressed or implied, with
--  respect to the sufficiency, accuracy, or utility of any information or
--  opinion contained herein. Alcatel expressly advises that any use of for 
--  any purpose or reliance upon this technical reference is at the risk of
--  the user and that Alcatel shall not be liable for any damage or injury
--  incurred by any person arising out of the sufficiency, accuracy, or
--  utility of any information or opinion contained herein.
--  This document is not to be construed as a suggestion to any manufacturer
--  to modify or change any of its products, nor does this document represent
--  any commitment by Alcatel to sell or purchase any product.
--  Nothing contained herein shall be construed as conferring by implication,
--  estoppel, or otherwise any license or right under any patent, whether or
--  not the use of any information herein necessarily employs an invention of
--  any existing or later issued patent.
--  Alcatel reserves the right not to offer any or all of these products and
--  to withdraw any or all of them at any future time.
--  Copyright (C) 1997, Alcatel. All Rights Reserved.
-- ===========================================================================

--  MODULE-IDENTITY
--  LAST-UPDATED   "200812080000Z"
--  ORGANIZATION   "Alcatel-Lucent"
--  CONTACT-INFO
--
--          Email:  asam.mibsupport@alcatel-lucent.com"
--
--  DESCRIPTION
--        "This MIB module defines objects for transaction management.
--
--  REVISION 201205180000Z
--  DESCRIPTION
--        "Version:  3EC15597EAAA_V4.4.0.0.1
--         Editor:   Tom Batsele
--         Changes:  Attribute added in object asamSetLogContext to allow logging
--                   of context ai_nt_1, ai_nta_1, ai_ntb_1 ( application intelligence)"
--
--  REVISION 201204180000Z
--  DESCRIPTION
--        "Version:  3EC15597EAAA_V4.4.0.0.0
--         Editor:   Tom Batsele
--         Changes:  Attribute added in object asamSetLogContext to allow logging
--                   of context ai ( application intelligence)"
--
--  REVISION 200812080000Z
--  DESCRIPTION
--        "Version:  3EC15597EAAA_V3.7.1.0.1
--         Editor:   Karel Meijfroidt
--         Changes:  Attribute added in object asamSetLogContext to allow logging
--                   of dynamic contexts (like vprn) and added extra column in
--                   table to hold the asamSetLogContextName"
--
--  REVISION 200808100000Z
--  DESCRIPTION
--        "Version:  3EC15597EAAA_V3.7.1.0.0
--         Editor:   Karel Meijfroidt
--         Changes:  Attribute added in object asamSetLogContext to allow logging
--                   of context ihub"
--
--  REVISION 200807100000Z
--  DESCRIPTION
--        "Version:  3EC15597EAAA_V3.7.0.0.0
--         Editor:   Zhang Tinghui
--         Changes:  Attribute added in object asamSetLogContext to allow logging
--                   of context xvps"
--
--  REVISION 200607100000Z
--  DESCRIPTION
--        "Version:  3EC15597EAAA_V3.2.0.0.0
--         Editor:   Marc Van Vlimmeren
--         Changes:  Updates for PB template conformance"
--
--  REVISION 200601240000Z
--  DESCRIPTION
--        "Version:  3EC15597EAAA_V2.4.0.0.1
--         Editor:   Bart Bogaert
--         Changes:  Implemented BDFhw70643: strict syntax checks (smilint)"
--
--  REVISION 200510260000Z
--  DESCRIPTION
--        "Version:  3EC15584AAAA_V2.4.0.0.0
--         Editor:   Praveena Achar
--         Changes:  Object asamSetLogContext added in asamSetLogTable to allow
--                   logging of context(nt or shub)"
--
--  REVISION 199904300000Z
--  DESCRIPTION
--        "Version:  3EC15597AAAA_R1.1.0
--         Editor:
--         Changes:  Object asamTransactionTimeout added to allow configuration
--                   of the transaction timeout"
-- ============================================================================

IMPORTS

    OBJECT-TYPE
        FROM RFC-1212
    NetworkTimeInSeconds
	FROM ASAM-TC-MIB
    IpAddress, TimeTicks
	FROM RFC1155-SMI
    asam
        FROM SYSTEM-MIB
    DisplayString
       FROM RFC1213-MIB;

asamTransactionMIB OBJECT IDENTIFIER ::= { asam 11 }

asamTransactionOwnerIpAddress	OBJECT-TYPE
    SYNTAX		IpAddress
    ACCESS		read-write
    STATUS		mandatory
    DESCRIPTION
        "To get unique write access to the ASAM MIB, a Manager needs to set
        this object to his IP Address.
        If asamTransactionOwnerIpAddress is 0.0.0.0, the SET will be accepted
        and a transaction granted to the Manager.
        During the Transaction, only SETs from the Manager who owns
        the Transaction (identified through checking the IP address in the
        SET with the IP Address in asamTransactionOwnerIpAddress) are accepted.
        The Manager can release a Transaction through setting
        asamTransactionOwnerIpAddress to 0.0.0.0.
        A Manager does not need to get a Transaction to do SETs on objects
        in the MIB as long as asamTransactionOwnerIpAddress is 0.0.0.0
        ALCATEL NOTE:
            ACCESS:      NA           USAGE:       NA
            PERSIST:     YES          INSRVMOD:    YES
            RANGE:       NA           DEFVALUE:    0.0.0.0
            UNITS:       NA           SPARSE:      NA
            DESCR:       NA"
::= { asamTransactionMIB 1}

asamSetLogLastEntry	OBJECT-TYPE
    SYNTAX		INTEGER
    ACCESS		read-only
    STATUS		mandatory
    DESCRIPTION
        "This object gives the index of the last entry
        that has been added to the SET log table.
        ALCATEL NOTE:
            ACCESS:      NA            USAGE:       NA
            PERSIST:     NO            INSRVMOD:    NA
            RANGE:       1..2147483647 DEFVALUE:    0
            UNITS:       NA            SPARSE:      NA
            DESCR:       NA"
::= { asamTransactionMIB 2}

asamSetLogTableReset	OBJECT-TYPE
    SYNTAX		INTEGER {
				resetCompleted (1),
				reset (2)
			}
    ACCESS		read-write
    STATUS		mandatory
    DESCRIPTION
        "This object is a button-like object to reset the SET log table.
        When it is set to Reset value, all logs are cleared,
        and logging restarts from index 1.
        When the resetting action is completed, the agent sets the value to
        ResetCompleted. If SNMP Manager sets this object to resetCompleted,
        the agent does not take any action.
        ALCATEL NOTE:
            ACCESS:      NA            USAGE:       NA
            PERSIST:     NO            INSRVMOD:    YES
            RANGE:       NA            DEFVALUE:    1
            UNITS:       NA            SPARSE:      NA
            DESCR:       NA"
::= { asamTransactionMIB 3}

asamSetLogResetTime	OBJECT-TYPE
    SYNTAX		NetworkTimeInSeconds
    ACCESS		read-only
    STATUS		mandatory
    DESCRIPTION
        "Time when SET log has been reset
        ALCATEL NOTE:
            ACCESS:      NA            USAGE:       NA
            PERSIST:     NO            INSRVMOD:    NA
            RANGE:       NA            DEFVALUE:    0
            UNITS:       seconds       SPARSE:      NA
            DESCR:       NA"
::= { asamTransactionMIB 4}

asamSetLogFullAction	OBJECT-TYPE
    SYNTAX		INTEGER {
				wrap (1),
				halt (2)
			}
    ACCESS		read-write
    STATUS		mandatory
    DESCRIPTION
        "This object defines which action the Agent will take when
        the SET log buffer is completely full.
        If its value is set to 'wrap', the older log records are overwritten
        by recent ones. If it is set to 'halt', then logging is stopped until
        the log buffer is reset by the Manager.
        ALCATEL NOTE:
            ACCESS:      NA            USAGE:       NA
            PERSIST:     YES           INSRVMOD:    YES
            RANGE:       NA            DEFVALUE:    1
            UNITS:       NA            SPARSE:      NA
            DESCR:       NA"
::= { asamTransactionMIB 5}

asamSetLogOverflowed	OBJECT-TYPE
    SYNTAX		INTEGER {
				notOverflowed (1),
				overflowed (2)
			}
    ACCESS		read-only
    STATUS		mandatory
    DESCRIPTION
        "This object gives an indication if the log buffer is overflowed.
        When the log buffer is reset, this object is set to Notoverflowed
        by the agent. This object is not useful when FullAction is set to
        wrap around.
        ALCATEL NOTE:
            ACCESS:      NA            USAGE:       NA
            PERSIST:     NO            INSRVMOD:    NA
            RANGE:       NA            DEFVALUE:    1
            UNITS:       NA            SPARSE:      NA
            DESCR:       NA"
::= { asamTransactionMIB 6}

asamSetLogBufferSize	OBJECT-TYPE
    SYNTAX		INTEGER
    ACCESS		read-only
    STATUS		mandatory
    DESCRIPTION
        "This object gives the size of the SET log buffer. This object value
        is useful to inform when an overflow in log buffer may occur.
        ALCATEL NOTE:
            ACCESS:      NA            USAGE:       NA
            PERSIST:     NA            INSRVMOD:    NA
            RANGE:       NA            DEFVALUE:    1000
            UNITS:       NA            SPARSE:      NA
            DESCR:       NA"
::= { asamTransactionMIB 7}

asamSetLogTable		OBJECT-TYPE
    SYNTAX		SEQUENCE OF AsamSetLogTableEntry
    ACCESS		not-accessible
    STATUS		mandatory
    DESCRIPTION
        "The SET Log Table logs all object identifiers which have
        been successfully changed through SNMP SET operations.
        ALCATEL NOTE:
            TABLESIZE: 1000
            DESCR: NA"
::= { asamTransactionMIB 8}

asamSetLogTableEntry	OBJECT-TYPE
    SYNTAX		AsamSetLogTableEntry
    ACCESS		not-accessible
    STATUS		mandatory
    DESCRIPTION
        "An entry in the SET Log Table
        Row creation : An entry is created by the system when an SNMP SET
            operation on a MIB instance was successfull.
        Row deletion : All entries are deleted when a manager resets
            the table (via asamSetLogTableReset).
        Index usage : the index is the asamSetLogTableIndex.
        Note that entries will be presented to the SNMP manager in full
        lexicographical order :  sorted on entry number."
    INDEX		{asamSetLogTableIndex}
::= { asamSetLogTable 1}

AsamSetLogTableEntry ::= SEQUENCE {
        asamSetLogTableIndex            INTEGER,
        asamSetLogIpAddress             IpAddress,
        asamSetLogChangedObjectID	OBJECT IDENTIFIER,
        asamSetLogContext               INTEGER,
        asamSetLogContextName           DisplayString
	}

asamSetLogTableIndex	OBJECT-TYPE
    SYNTAX		INTEGER
    ACCESS		read-only
    STATUS		mandatory
    DESCRIPTION
        "The key in the SET Log Table.
        ALCATEL NOTE:
            ACCESS:      NA            USAGE:       NA
            PERSIST:     NA            INSRVMOD:    NA
            RANGE:       NA            DEFVALUE:    NA
            UNITS:       NA            SPARSE:      NA
            DESCR:       NA"
::= { asamSetLogTableEntry 1}

asamSetLogIpAddress	OBJECT-TYPE
    SYNTAX		IpAddress
    ACCESS		read-only
    STATUS		mandatory
    DESCRIPTION
        "The IP Address of the Manager who changed the object identified
        by asamSetLogChangedObjectID.
        ALCATEL NOTE:
            ACCESS:      NA            USAGE:       NA
            PERSIST:     NA            INSRVMOD:    NA
            RANGE:       NA            DEFVALUE:    NA
            UNITS:       NA            SPARSE:      NO
            DESCR:       NA"
::= { asamSetLogTableEntry 2}

asamSetLogChangedObjectID	OBJECT-TYPE
    SYNTAX		OBJECT IDENTIFIER
    ACCESS		read-only
    STATUS		mandatory
    DESCRIPTION
        "The Object Identifier of an object which has been changed.
        Remark that the Logging does not contain the value to which this object
        has been changed.
        ALCATEL NOTE:
            ACCESS:      NA            USAGE:       NA
            PERSIST:     NA            INSRVMOD:    NA
            RANGE:       NA            DEFVALUE:    NA
            UNITS:       NA            SPARSE:      NO
            DESCR:       NA"
::= { asamSetLogTableEntry 3}

asamSetLogContext 	OBJECT-TYPE
    SYNTAX	    INTEGER {
                            nt (1),
                            shub (2),
                            xvps1 (3),
                            xvps2 (4),
                            xvps3 (5),
                            xvps4 (6),
                            xvps5 (7),
                            xvps6 (8),
                            xvps7 (9),
                            xvps8 (10),
                            ihub (11),
                            dynamic (12),
			    aiNt1 (13),
			    aiNta1 (14),
			    aiNtb1 (15),
                            dpoe  (16)
                    }
    ACCESS		read-only
    STATUS		mandatory
    DESCRIPTION
        "The context in which the Object Identifier has been changed.
        ALCATEL NOTE:
            ACCESS:      NA            USAGE:       NA
            PERSIST:     NA            INSRVMOD:    NA
            RANGE:       NA            DEFVALUE:    NA
            UNITS:       NA            SPARSE:      NO
            DESCR:       NA"
::= { asamSetLogTableEntry 4}

asamSetLogContextName   OBJECT-TYPE
    SYNTAX              DisplayString (SIZE (0..16))
    ACCESS              read-only
    STATUS              mandatory
    DESCRIPTION
        "In case of context dynamic it is the full context name when available
         e.g. for vprn the context name is as follows vprn<serviceid>.
         For all other contexts this string is empty.
        ALCATEL NOTE:
            ACCESS:      NA            USAGE:       NA
            PERSIST:     NA            INSRVMOD:    NA
            RANGE:       NA            DEFVALUE:    NA
            UNITS:       NA            SPARSE:      NO
            DESCR:       NA"
::= { asamSetLogTableEntry 5}
        
asamNumberOfSets	OBJECT-TYPE
    SYNTAX		INTEGER
    ACCESS		read-only
    STATUS		mandatory
    DESCRIPTION
        "The number of successfull SETs since sysUpTime.
        ALCATEL NOTE:
            ACCESS:      NA            USAGE:       NA
            PERSIST:     NO            INSRVMOD:    NA
            RANGE:       NA            DEFVALUE:    NA
            UNITS:       NA            SPARSE:      NA
            DESCR:       NA"
::= { asamTransactionMIB 9}

asamTransactionTimeout  OBJECT-TYPE
    SYNTAX      TimeTicks
    ACCESS      read-write
    STATUS      mandatory
    DESCRIPTION
        "The timeout of the transaction, expressed in 1/100 s.
        If no SET or GET request is issued by the transaction owner within
        the timeframe specified by this object, the transaction is released.
        If this object is set to value 0, the transaction timeout will be
        infinite.
        ALCATEL NOTE:
            ACCESS:      NA            USAGE:       NA
            PERSIST:     YES           INSRVMOD:    YES
            RANGE:       NA            DEFVALUE:    6000
            UNITS:       1/100 of secs SPARSE:      NA
            DESCR:       NA"
::= { asamTransactionMIB 10 }

END
