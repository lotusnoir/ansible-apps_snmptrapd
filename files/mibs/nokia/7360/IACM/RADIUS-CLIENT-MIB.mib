-- =========================================================================
--  This specification is published by Alcatel under Non-Disclosure
--  Agreement(s) (NDA) with specific parties and has to be considered as
--  Confidential Information as defined in such NDA.
--  Alcatel reserves the right to revise this document for any reason,
--  including but not limited to conformity with standards promulgated by
--  various agencies, utilisation of advances in the state of the technical
--  areas, or the reflection of changes in the design of any equipment,
--  techniques, or procedures described or referred to herein.
--  The product specifications and other technical or performance
--  information contained herein are subject to change without notice.
--  Updates of this document will be issued under the above NDA's.
--  Alcatel makes no representation or warranty, expressed or implied, with
--  respect to the sufficiency, accuracy, or utility of any information or
--  opinion contained herein. Alcatel expressly advises that any use of for 
--  any purpose or reliance upon this technical reference is at the risk of
--  the user and that Alcatel shall not be liable for any damage or injury
--  incurred by any person arising out of the sufficiency, accuracy, or
--  utility of any information or opinion contained herein.
--  This document is not to be construed as a suggestion to any
--  manufacturer to modify or change any of its products, nor does this
--  document represent any commitment by Alcatel to sell or purchase any
--  product. Nothing contained herein shall be construed as conferring by
--  implication, estoppel, or otherwise any license or right under any 
--  patent, whether or not the use of any information herein necessarily
--  employs an invention of any existing or later issued patent.
--  Alcatel reserves the right not to offer any or all of these products 
--  and to withdraw any or all of them at any future time.
--  Copyright (C) 2004, Alcatel. All Rights Reserved.
-- =========================================================================


RADIUS-CLIENT-MIB DEFINITIONS ::= BEGIN


--  MODULE-IDENTITY
--  LAST-UPDATED 20081010
--  ORGANIZATION "Alcatel-Lucent"
--  CONTACT-INFO
--
--          Email:  asam.mibsupport@alcatel-lucent.com"
--
--  DESCRIPTION  MIB of Radius Client engine
--
--  REVISION 201411250000Z
--  DESCRIPTION
--        "Version  3FE22800EAAA_V5.2.0.0.0
--         Editor:  Jakir Rehman Samsudeen
--         Changes:  The MIB object attributes 'radAuthServerTimeoutLimit' and  
--                   'radAuthServerDeadInterval' descriptions in ALCATEL NOTEs are 
--                    aligned with CLI behavior.
--
--  REVISION 201303280000Z
--  DESCRIPTION
--        “Version  3FE22800EAAA_V4.6.0.0.0
--         Editor: L.Pauwels
--         Changes:  Updates for documenting MIB applicability for ISAMs of the
-- 	             NGVR family. (i.e. the usage of the VRF object)
--
--  REVISION 200910020000Z
--  DESCRIPTION
--        “Version  3FE22800EAAA_V4.0.1.0.0
--         Editor: M. Todd
--         Changes:  Updates for porting FTTU features, RCR BDFam52637
-- 			add radAuthServNoRespStatus and radAuthServerUnreachAction”
--
--  REVISION 200810100000Z
--  DESCRIPTION
--        "Version: 3FE22800EAAA_V3.7.1.0.0
--         Editor: Karel Meijfroidt
--         Changes:  Updates for RCR ANTms79790 IPD Stack porting"
--
--  REVISION 200605310000Z
--  DESCRIPTION
--        "Version: 3FE22800EAAA_V3.1.0.0.0
--         Editor: Katrien SCHARRE
--         Changes:  Adding ALCATEL NOTE for every object"
--
--  REVISION 200603180000Z
--  DESCRIPTION
--        "Version: 3FE22800EAAA_V3.0.0.0.1
--         Editor: Katrien SCHARRE
--         Changes: updates for ISAM R3.0 "
--
--  REVISION 200601180000Z
--  DESCRIPTION
--        "Version: 3FE22800EAAA_V2.4.1.0.1
--         Editor: Katrien SCHARRE
--         Changes: updates for ISAM R2.4 "
--
--
--
-- =========================================================================

IMPORTS

    TimeTicks, Counter, Gauge
        FROM RFC1155-SMI
    OBJECT-TYPE
        FROM RFC-1212
    asam
        FROM SYSTEM-MIB
	RowStatus, TruthValue
		FROM SNMPv2-TC
    InetAddress, InetAddressType, InetPortNumber
        FROM INET-ADDRESS-MIB
    DisplayString
        FROM RFC1213-MIB;

aaaMIB  OBJECT IDENTIFIER ::= { asam 42 }

radiusClientMIB   OBJECT IDENTIFIER ::= { aaaMIB 1 }

-- Textual conventions

RadiusTimeout   ::= INTEGER (1..2147483647)

RadiusDeadInterval   ::= INTEGER (0..2147483647)

RadiusRetryLimit   ::= INTEGER (0..100)

RouterIndex   ::= INTEGER (0..2147483647)

radAuthClientInvalidServerAddresses  OBJECT-TYPE
    SYNTAX  Counter
    ACCESS  read-only
    STATUS  mandatory
    DESCRIPTION
    "The number of RADIUS Access-Response packets
    received from unknown addresses.
          ALCATEL NOTE:
             ACCESS: NA
             USAGE: NA
             PERSIST:  	NO
             INSRVMOD: 	NA
             RANGE:	NA
             DEFVALUE: 	NA
             UNITS:	PACKETS
             DESCR:	NA"
    ::= {radiusClientMIB 1}

radAccClientInvalidServerAddresses  OBJECT-TYPE
    SYNTAX  Counter
    ACCESS  read-only
    STATUS  mandatory
    DESCRIPTION
    "The number of RADIUS Accounting-Response packets
    received from unknown addresses.
          ALCATEL NOTE:
             ACCESS: NA
             USAGE: NA
             PERSIST:  	NO
             INSRVMOD: 	NA
             RANGE:	NA
             DEFVALUE: 	NA
             UNITS:	PACKETS 
             DESCR:	NA"
    ::= {radiusClientMIB 2}

radDynAuthServerInvalidClientAddresses  OBJECT-TYPE
    SYNTAX  Counter
    ACCESS  read-only
    STATUS  mandatory
    DESCRIPTION
    "The number of RADIUS Disconnect-Request packets
    received from unknown addresses.
          ALCATEL NOTE:
             ACCESS: NA
             USAGE: NA
             PERSIST:  	NO
             INSRVMOD: 	NA
             RANGE:	NA
             DEFVALUE: 	NA
             UNITS:	PACKETS 
             DESCR:	NA "
    ::= {radiusClientMIB 3}

radAuthServerGetNextFreeIndex  OBJECT-TYPE
    SYNTAX  INTEGER
    ACCESS  read-only
    STATUS  mandatory
    DESCRIPTION
         "The next Free Index value that can be used for creating
	     a new entry in the Radius Auth Server Table.
         This object contains an appropriate value to be used for 
         radAuthServerIndex when creating entries in the radAuthServerTable. 
         The value 0 indicates that no unassigned entries are available. To 
         obtain the radAuthServerIndex value for a new entry, the
         manager issues a management protocol retrieval operation to obtain the
         current-value of this object. After each retrieval, the agent should
         modify the value to the next unassigned index.
          ALCATEL NOTE:
             ACCESS: NA
             USAGE: NA
             PERSIST:  	NO
             INSRVMOD: 	NA
             RANGE:	RANGE(0..256)
             DEFVALUE: 	NA
             UNITS:	NA 
             DESCR:	NA "
    ::= { radiusClientMIB 4 }

-- Start of RadiusAuthServerTable

radAuthServerTable OBJECT-TYPE
      SYNTAX     SEQUENCE OF RadAuthServerEntry
      ACCESS     not-accessible
      STATUS     mandatory
      DESCRIPTION
            "The (conceptual) table listing the RADIUS authentication
             servers with its configurable parameters.
             If a entry (server) has to be deleted, then it must not be
             associated with any radius Policy. If so, the deletion is
             not allowed.

            ALCATEL NOTE :
              TABLESIZE : 256 
              DESCR : NA "
      ::= { radiusClientMIB 5 }

radAuthServerEntry OBJECT-TYPE
      SYNTAX     RadAuthServerEntry
      ACCESS	 not-accessible
      STATUS     mandatory
      DESCRIPTION
            "An entry (conceptual row) representing the configuration 
             of a RADIUS server."
      INDEX { radAuthServerIndex }
      ::= { radAuthServerTable 1 }

RadAuthServerEntry ::=
    SEQUENCE {
      radAuthServerIndex            INTEGER,
      radAuthServerName             DisplayString,
	  radAuthServerVrfIndex			RouterIndex,
      radAuthServerAddrType         InetAddressType,
	  radAuthServerAddress			InetAddress,
	  radAuthServerPort  			InetPortNumber,
	  radAuthServerSecret			DisplayString,
	  radAuthServerRetryLimit		RadiusRetryLimit,
	  radAuthServerTimeoutLimit		RadiusTimeout,
	  radAuthServerAdminState	    INTEGER,
	  radAuthServerOperState		INTEGER,
	  radAuthServerDeadInterval		RadiusDeadInterval,
	  radAuthServerRowStatus		RowStatus
      }

radAuthServerIndex	 OBJECT-TYPE
	  SYNTAX		INTEGER
	  ACCESS		not-accessible
	  STATUS		mandatory
	  DESCRIPTION
             "Index used to uniquely identify an entry in this table.
          ALCATEL NOTE
             ACCESS: NA / INDEX
             USAGE: NA
             PERSIST:  	YES
             INSRVMOD: 	NA
             RANGE:	RANGE(1..256)
             DEFVALUE: 	NA
             UNITS:	NA 
             SPARSE:	NO 
             DESCR:	NA "
	  ::= { radAuthServerEntry 1 }

radAuthServerName	 OBJECT-TYPE
	  SYNTAX		DisplayString (SIZE (1..64))
	  ACCESS		read-write
	  STATUS		mandatory
	  DESCRIPTION
         "The Name associated with this Radius Auth Server Entry. It should be  
          unique among the different Auth Servers configured.
          ALCATEL NOTE:
             ACCESS: NA
             USAGE: MAND
             PERSIST:  	YES
             INSRVMOD: 	NO
             RANGE:	NA
             DEFVALUE: 	NA
             UNITS:	NA 
             SPARSE:	NO 
             DESCR:	NA "
	  ::= { radAuthServerEntry 2 }

radAuthServerVrfIndex	 OBJECT-TYPE
	  SYNTAX		RouterIndex
	  ACCESS		read-write
	  STATUS		mandatory
	  DESCRIPTION
		"The RouterIndex to which this RADIUS Authentication server belongs.
          In case of NE with SHUB, this is the Vrf. In case of NE with IHUB
          this is the Service Id of the VPRN or the base router when 0.
	  In case of NE of the NGVR family (not containing SHUB, not containing IHUB)
	  it is 0.
          ALCATEL NOTE:
             ACCESS: NA
             USAGE: MAND
             PERSIST:  	YES
             INSRVMOD: 	NO
             RANGE: DEP (1..127) in case of NE with SHUB,
                        (0..2147483647) in case of NE with IHUB
                        (0) in case of NE with NGVR
             DEFVALUE: 	NA
             UNITS:	NA 
             SPARSE:	NO 
             DESCR:	NA "
	  ::= { radAuthServerEntry 3 }

radAuthServerAddrType  OBJECT-TYPE
	  SYNTAX		InetAddressType
	  ACCESS		read-write
	  STATUS		mandatory
	  DESCRIPTION
		" A value representing the type of Internet Address.
          ALCATEL NOTE:
             ACCESS: NA
             USAGE: OPT
             PERSIST:  	YES
             INSRVMOD: 	NO
             RANGE:	NA
             DEFVALUE: 	1(ipv4)
             UNITS:	NA 
             SPARSE:	NO 
             DESCR:	NA "
	  ::= { radAuthServerEntry 4 }

radAuthServerAddress  OBJECT-TYPE
	  SYNTAX		InetAddress
	  ACCESS		read-write
	  STATUS		mandatory
	  DESCRIPTION
		"The IP address of this RADIUS Authentication server. The Type of 
          this Ip Address (IPv4/Ipv6/...) is determined by the value of the 
          object radAuthServerAddrType.
          ALCATEL NOTE:
             ACCESS: NA
             USAGE: MAND
             PERSIST:  	YES
             INSRVMOD: 	YES
             RANGE: NA
             DEFVALUE: 	NA
             UNITS:	NA
             SPARSE:	NO 
             DESCR:	NA "
	  ::= { radAuthServerEntry 5 }

radAuthServerPort    OBJECT-TYPE
	  SYNTAX            InetPortNumber
	  ACCESS            read-write
	  STATUS            mandatory
	  DESCRIPTION
		"The UDP port number to which RADIUS authentication messages should  
		 be sent.
          ALCATEL NOTE:
             ACCESS: NA
             USAGE: OPT
             PERSIST:  	YES
             INSRVMOD: 	YES
             RANGE: NA
             DEFVALUE: 	1812
             UNITS:	NA 
             SPARSE:	NO 
             DESCR:	NA "
	  DEFVAL  {1812}
	  ::= { radAuthServerEntry 6 }

radAuthServerSecret  OBJECT-TYPE
	  SYNTAX		DisplayString (SIZE (6..64))
	  ACCESS		read-write
	  STATUS		mandatory
	  DESCRIPTION
		"The secret used in encrypting the packets passed between the RADIUS 
		 server and the client.
          For security reasons, the secret wont be displayed to the users.
          ALCATEL NOTE:
             ACCESS: NA
             USAGE: MAND
             PERSIST:  	YES
             INSRVMOD: 	YES
             RANGE: NA
             DEFVALUE: 	NA
             UNITS:	NA 
             SPARSE:	NO 
             DESCR:	NA "
	  ::= { radAuthServerEntry 7 }

radAuthServerRetryLimit      OBJECT-TYPE
	  SYNTAX		RadiusRetryLimit
	  ACCESS		read-write
	  STATUS		mandatory
	  DESCRIPTION
		"Indicates the maximum number of times to resend a 
          request to this server (in addition to the original request), before 
          giving up on the server.
          ALCATEL NOTE:
             ACCESS: NA
             USAGE: OPT
             PERSIST:  	YES
             INSRVMOD: 	YES
             RANGE: RANGE(0..100)
             DEFVALUE: 	3
             UNITS:	NA 
             SPARSE:	NO 
             DESCR:	NA "
	  DEFVAL  {3}
	  ::= { radAuthServerEntry 8 }

radAuthServerTimeoutLimit    OBJECT-TYPE
	  SYNTAX		RadiusTimeout
	  ACCESS		read-write
	  STATUS		mandatory
	  DESCRIPTION
		"This is the time in seconds between retransmissions to the RADIUS 
		 server.
          ALCATEL NOTE:
             ACCESS: NA
             USAGE: OPT
             PERSIST:  	YES
             INSRVMOD: 	YES
             RANGE: RANGE(1..2147483647)
             DEFVALUE: 	3
             UNITS:	time in seconds 
             SPARSE:	NO 
             DESCR:	Currently the maximum timeout can be 60 seconds"
	  DEFVAL  {3}
	  ::= { radAuthServerEntry 9 }

radAuthServerAdminState      OBJECT-TYPE
	  SYNTAX		INTEGER {
                            up(1),
                            down(2)
                            }
	  ACCESS		read-write
	  STATUS		mandatory
	  DESCRIPTION
		" The Administrative State of the Authentication Server.
          ALCATEL NOTE:
             ACCESS: NA
             USAGE: OPT
             PERSIST:  	YES
             INSRVMOD: 	YES
             RANGE: NA
             DEFVALUE: up
             UNITS:	NA
             SPARSE:	NO 
             DESCR:	NA "
 	  DEFVAL  { up }
	  ::= { radAuthServerEntry 10 }

radAuthServerOperState       OBJECT-TYPE
	  SYNTAX		INTEGER {
                         up(1),
                         down(2),
  						 unknown(3)
                         }
	  ACCESS		read-only
	  STATUS		mandatory
	  DESCRIPTION
		" The Operational State of the Authentication Server.
          Initially the oper state of a server is in unknown. When
          the first user authenticates using this server and if 
          a reply is received, then the state of this server is
          moved to up state. When the server doesnt get a response 
          and goes to down state then the deadinterval timer is 
          started and when it expires, the state again moves to
          unknown. When a user has to be authenticated using this
          server, then the state goes to up state after receiving
          a reply from this server.
          ALCATEL NOTE:
             ACCESS: NA
             USAGE: NA
             PERSIST:  	NO
             INSRVMOD: 	NA
             RANGE: NA
             DEFVALUE: 	NA
             UNITS:	NA
             SPARSE:	NO 
             DESCR:	NA "
	  ::= { radAuthServerEntry 11 }

radAuthServerDeadInterval     OBJECT-TYPE
	  SYNTAX		RadiusDeadInterval
	  ACCESS		read-write
	  STATUS		mandatory
	  DESCRIPTION
		"Indicates the number of seconds before setting the operational state
		 of this authentication server to
         unknown from down state. A write to this object will immediately
         trigger the above mentioned action. If this Interval is set to zero,
         then the dead interval timer won't be started.
         ALCATEL NOTE:
             ACCESS: NA
             USAGE: OPT
             PERSIST:  	YES
             INSRVMOD: 	YES
             RANGE: RANGE(0..2147483647)
             DEFVALUE: 	600
             UNITS:	in seconds 
             SPARSE:	NO 
             DESCR:	Currently the maximum dead interval can be 3600 seconds"
	  DEFVAL  {600}
	  ::= { radAuthServerEntry 12 }

radAuthServerRowStatus       OBJECT-TYPE
	  SYNTAX		RowStatus
	  ACCESS		read-write
	  STATUS		mandatory
	  DESCRIPTION
		"This is used for Row creation/Deletion.
          ALCATEL NOTE:
             ACCESS: NA
             USAGE: MAND
             PERSIST:  	YES
             INSRVMOD: 	YES
             RANGE: 1,4,6
             DEFVALUE: 	NA
             UNITS:	NA
             SPARSE:	NO 
             DESCR:	NA "
	  ::= { radAuthServerEntry 13 }

-- End of radAuthServerTable


-- Start of radAuthServerMappingTable

radAuthServerMappingTable OBJECT-TYPE
      SYNTAX     SEQUENCE OF RadAuthServerMappingEntry
      ACCESS     not-accessible
      STATUS     mandatory
      DESCRIPTION
            "The (conceptual) table is a Mapping Table listing the RADIUS
            Auth Server Names within a Vrf with their equivalent Radius Auth
            Server Index used in the RADIUS Auth Server Table.
	        This is a Read-Only Table and for each entry in the Radius Auth
            Server Table, an corresponding entry is created in this table.

            ALCATEL NOTE :
              TABLESIZE : DEP on the number of rows in the radAuthServerTable 
              DESCR : NA"     
      ::= { radiusClientMIB 6 }

radAuthServerMappingEntry OBJECT-TYPE
      SYNTAX     RadAuthServerMappingEntry
      ACCESS 	 not-accessible
      STATUS     mandatory
      DESCRIPTION
            "An entry (conceptual row) representing the Radius Auth Server Name
            (Within a Vrf) to Index Mapping."
      INDEX      { radAuthServerMappingVrf, radAuthServerMappingName }
      ::= { radAuthServerMappingTable 1 }

RadAuthServerMappingEntry ::= SEQUENCE {
	  radAuthServerMappingVrf				RouterIndex,
	  radAuthServerMappingName				DisplayString,
	  radAuthServerMappingIndex				INTEGER
    }

radAuthServerMappingVrf OBJECT-TYPE
      SYNTAX     RouterIndex
      ACCESS 	 not-accessible
      STATUS     mandatory
      DESCRIPTION
         "The RouterIndex to which the RADIUS Auth Server belongs.
          In case of NE with SHUB, this is the Vrf. In case of NE with IHUB
          this is the Service Id of the VPRN or the base router when 0.
	  In case of NE of the NGVR family (not containing SHUB, not containing IHUB)
	  it is 0.
          ALCATEL NOTE
             ACCESS: NA / INDEX
             USAGE: NA
             PERSIST:  	YES
             INSRVMOD: 	NA
             RANGE:	DEP (1..127) in case of NE with SHUB,
                        (0..2147483647) in case of NE with IHUB
                        (0) in case of NE with NGVR
             DEFVALUE: 	NA
             UNITS:	NA 
             SPARSE:	NO 
             DESCR:	NA "
      ::= { radAuthServerMappingEntry 1 }

radAuthServerMappingName OBJECT-TYPE
      SYNTAX     DisplayString (SIZE (1..64))
      ACCESS 	 not-accessible
      STATUS     mandatory
      DESCRIPTION
         "A name uniquely identifying a RADIUS Auth Server.
          ALCATEL NOTE
             ACCESS: NA / INDEX
             USAGE: NA
             PERSIST:  	YES
             INSRVMOD: 	NA
             RANGE:	NA
             DEFVALUE: 	NA
             UNITS:	NA 
             SPARSE:	NO 
             DESCR:	NA "
      ::= { radAuthServerMappingEntry 2 }

radAuthServerMappingIndex OBJECT-TYPE
      SYNTAX     INTEGER
      ACCESS 	 read-only
      STATUS     mandatory
      DESCRIPTION
         "The corresponding Index associated with this Name.
          ALCATEL NOTE
             ACCESS: NA
             USAGE: NA
             PERSIST:  	NO
             INSRVMOD: 	NA
             RANGE:	RANGE(1..256)
             DEFVALUE: 	NA
             UNITS:	NA 
             SPARSE:	NO 
             DESCR:	NA "
      ::= { radAuthServerMappingEntry 3 }

-- End of radAuthServerMappingTable


-- Start of radAuthServerStatisticsTable

radAuthServerStatsTable OBJECT-TYPE
    SYNTAX  SEQUENCE OF RadAuthServerStatsEntry
    ACCESS  not-accessible
    STATUS  mandatory
    DESCRIPTION
    "The (conceptual) table listing the RADIUS authentication
    server's statistics, with which the client shares a secret.
            ALCATEL NOTE :
              TABLESIZE : DEP on the number of rows in the radAuthServerTable 
              DESCR : NA"
    ::= { radiusClientMIB 7 }

radAuthServerStatsEntry OBJECT-TYPE
    SYNTAX  RadAuthServerStatsEntry
    ACCESS  not-accessible
    STATUS  mandatory
    DESCRIPTION
    "An entry (conceptual row) representing a RADIUS
    authentication server with which the client shares
    a secret."
    INDEX { radAuthServerIndex }
    ::= { radAuthServerStatsTable 1 }

RadAuthServerStatsEntry ::= SEQUENCE {
	  radAuthClientRoundTripTime				TimeTicks,
	  radAuthClientAccessRequests				Counter,
	  radAuthClientAccessRetransmissions		Counter,
	  radAuthClientAccessAccepts				Counter,
	  radAuthClientAccessRejects				Counter,
	  radAuthClientAccessChallenges			    Counter,
	  radAuthClientMalformedAccessResponses	    Counter,
	  radAuthClientBadAuthenticators			Counter,
	  radAuthClientPendingRequests				Gauge,
	  radAuthClientTimeouts					    Counter,
	  radAuthClientUnknownTypes				    Counter,
	  radAuthClientPacketsDropped				Counter
}

radAuthClientRoundTripTime OBJECT-TYPE
    SYNTAX TimeTicks
    ACCESS read-only
    STATUS mandatory
    DESCRIPTION
    "The time interval (in hundredths of a second) between
    the most recent Access-Reply/Access-Challenge and the
    Access-Request that matched it from this RADIUS
    authentication server.
          ALCATEL NOTE
             ACCESS: NA
             USAGE: NA
             PERSIST:  	NO
             INSRVMOD: 	NA
             RANGE:	NA
             DEFVALUE: 	NA
             UNITS:	NA 
             SPARSE:	NO 
             DESCR:	NA "
    ::= { radAuthServerStatsEntry 1 }

-- Request/Response statistics
--
-- TotalIncomingPackets = Accepts + Rejects + Challenges + UnknownTypes
--
-- TotalIncomingPackets - MalformedResponses - BadAuthenticators -
-- UnknownTypes - PacketsDropped = Successfully received
--
-- AccessRequests + PendingRequests + ClientTimeouts =
-- Successfully Received
--
--

radAuthClientAccessRequests OBJECT-TYPE
    SYNTAX Counter
    ACCESS read-only
    STATUS mandatory
    DESCRIPTION
    "The number of RADIUS Access-Request packets sent
    to this server. This does not include retransmissions.
          ALCATEL NOTE
             ACCESS: NA
             USAGE: NA
             PERSIST:  	NO
             INSRVMOD: 	NA
             RANGE:	NA
             DEFVALUE: 	NA
             UNITS:	NA 
             SPARSE:	NO 
             DESCR:	NA "
    ::= { radAuthServerStatsEntry 2 }

radAuthClientAccessRetransmissions OBJECT-TYPE
    SYNTAX Counter
    ACCESS read-only
    STATUS mandatory
    DESCRIPTION
    "The number of RADIUS Access-Request packets
    retransmitted to this RADIUS authentication server.
          ALCATEL NOTE
             ACCESS: NA
             USAGE: NA
             PERSIST:  	NO
             INSRVMOD: 	NA
             RANGE:	NA
             DEFVALUE: 	NA
             UNITS:	NA 
             SPARSE:	NO 
             DESCR:	NA "
    ::= { radAuthServerStatsEntry 3 }

radAuthClientAccessAccepts OBJECT-TYPE
    SYNTAX Counter
    ACCESS read-only
    STATUS mandatory
    DESCRIPTION
    "The number of RADIUS Access-Accept packets
    (valid or invalid) received from this server.
          ALCATEL NOTE
             ACCESS: NA
             USAGE: NA
             PERSIST:  	NO
             INSRVMOD: 	NA
             RANGE:	NA
             DEFVALUE: 	NA
             UNITS:	NA 
             SPARSE:	NO 
             DESCR:	NA "
    ::= { radAuthServerStatsEntry 4 }

radAuthClientAccessRejects OBJECT-TYPE
    SYNTAX Counter
    ACCESS read-only
    STATUS mandatory
    DESCRIPTION
    "The number of RADIUS Access-Reject packets
    (valid or invalid) received from this server.
          ALCATEL NOTE
             ACCESS: NA
             USAGE: NA
             PERSIST:  	NO
             INSRVMOD: 	NA
             RANGE:	NA
             DEFVALUE: 	NA
             UNITS:	NA 
             SPARSE:	NO 
             DESCR:	NA "
    ::= { radAuthServerStatsEntry 5 }

radAuthClientAccessChallenges OBJECT-TYPE
    SYNTAX Counter
    ACCESS read-only
    STATUS mandatory
    DESCRIPTION
    "The number of RADIUS Access-Challenge packets
    (valid or invalid) received from this server.
          ALCATEL NOTE
             ACCESS: NA
             USAGE: NA
             PERSIST:  	NO
             INSRVMOD: 	NA
             RANGE:	NA
             DEFVALUE: 	NA
             UNITS:	NA 
             SPARSE:	NO 
             DESCR:	NA "
    ::= { radAuthServerStatsEntry 6 }

-- "Access-Response" includes an Access-Accept, Access-Challenge
-- or Access-Reject

radAuthClientMalformedAccessResponses OBJECT-TYPE
    SYNTAX Counter
    ACCESS read-only
    STATUS mandatory
    DESCRIPTION
    "The number of malformed RADIUS Access-Response
    packets received from this server.
    Malformed packets include packets with
    an invalid length. Bad authenticators or
    Signature attributes or unknown types are not
    included as malformed access responses.
          ALCATEL NOTE
             ACCESS: NA
             USAGE: NA
             PERSIST:  	NO
             INSRVMOD: 	NA
             RANGE:	NA
             DEFVALUE: 	NA
             UNITS:	NA 
             SPARSE:	NO 
             DESCR:	NA "
    ::= { radAuthServerStatsEntry 7 }

radAuthClientBadAuthenticators OBJECT-TYPE
    SYNTAX Counter
    ACCESS read-only
    STATUS mandatory
    DESCRIPTION
    "The number of RADIUS Access-Response packets
    containing invalid authenticators or Signature
    attributes received from this server.
          ALCATEL NOTE
             ACCESS: NA
             USAGE: NA
             PERSIST:  	NO
             INSRVMOD: 	NA
             RANGE:	NA
             DEFVALUE: 	NA
             UNITS:	NA 
             SPARSE:	NO 
             DESCR:	NA "
    ::= { radAuthServerStatsEntry 8 }

radAuthClientPendingRequests OBJECT-TYPE
    SYNTAX Gauge
    ACCESS read-only
    STATUS mandatory
    DESCRIPTION
    "The number of RADIUS Access-Request packets
    destined for this server that have not yet timed out
    or received a response. This variable is incremented
    when an Access-Request is sent and decremented due to
    receipt of an Acess-Accept, Access-Reject or
    Access-Challenge, a timeout or retransmission.
          ALCATEL NOTE
             ACCESS: NA
             USAGE: NA
             PERSIST:  	NO
             INSRVMOD: 	NA
             RANGE:	NA
             DEFVALUE: 	NA
             UNITS:	NA 
             SPARSE:	NO 
             DESCR:	NA "
    ::= { radAuthServerStatsEntry 9 }

radAuthClientTimeouts OBJECT-TYPE
    SYNTAX Counter
    ACCESS read-only
    STATUS mandatory
    DESCRIPTION
    "The number of authentication timeouts to this server.
    After a timeout the client may retry to the same
    server, send to a different server, or
    give up. A retry to the same server is counted as a
    retransmit as well as a timeout. A send to a different
    server is counted as a Request as well as a timeout.
          ALCATEL NOTE
             ACCESS: NA
             USAGE: NA
             PERSIST:  	NO
             INSRVMOD: 	NA
             RANGE:	NA
             DEFVALUE: 	NA
             UNITS:	NA 
             SPARSE:	NO 
             DESCR:	NA "
    ::= { radAuthServerStatsEntry 10 }

radAuthClientUnknownTypes OBJECT-TYPE
    SYNTAX Counter
    ACCESS read-only
    STATUS mandatory
    DESCRIPTION
    "The number of RADIUS packets of unknown type which
    were received from this server on the authentication port.
          ALCATEL NOTE
             ACCESS: NA
             USAGE: NA
             PERSIST:  	NO
             INSRVMOD: 	NA
             RANGE:	NA
             DEFVALUE: 	NA
             UNITS:	NA 
             SPARSE:	NO 
             DESCR:	NA "
    ::= { radAuthServerStatsEntry 11 }

radAuthClientPacketsDropped OBJECT-TYPE
    SYNTAX Counter
    ACCESS read-only
    STATUS mandatory
    DESCRIPTION
    "The number of RADIUS packets of which were
    received from this server on the authentication port
    and dropped for some other reason.
          ALCATEL NOTE
             ACCESS: NA
             USAGE: NA
             PERSIST:  	NO
             INSRVMOD: 	NA
             RANGE:	NA
             DEFVALUE: 	NA
             UNITS:	NA 
             SPARSE:	NO 
             DESCR:	NA "
    ::= { radAuthServerStatsEntry 12 }


-- End of radAuthServerStatisticsTable

radAccServerGetNextFreeIndex  OBJECT-TYPE
    SYNTAX  INTEGER
    ACCESS  read-only
    STATUS  mandatory
    DESCRIPTION
         "The next Free Index value that can be used for creating
	     a new entry in the Radius Accounting Server Table.
         This object contains an appropriate value to be used for 
         radAccServerIndex when creating entries in the radAccServerTable. 
         The value 0 indicates that no unassigned entries are available. To 
         obtain the radAccServerIndex value for a new entry, the
         manager issues a management protocol retrieval operation to obtain the
         current-value of this object. After each retrieval, the agent should
         modify the value to the next unassigned index.
          ALCATEL NOTE
             ACCESS: NA
             USAGE: NA
             PERSIST:  	NO
             INSRVMOD: 	NA
             RANGE:	RANGE(0..256) 
             DEFVALUE: 	NA
             UNITS:	NA 
             DESCR:	NA"
    ::= { radiusClientMIB 8 }


-- Start of  RadAccServerTable

radAccServerTable OBJECT-TYPE
      SYNTAX     SEQUENCE OF RadAccServerEntry
      ACCESS     not-accessible
      STATUS     mandatory
      DESCRIPTION
            "The (conceptual) table listing the RADIUS accounting
             servers with its configurable parameters.

             If a entry (server) has to be deleted, then it must not be
             associated with any radius Policy. If so, the deletion is
             not allowed. 
            ALCATEL NOTE :
              TABLESIZE : 256 
              DESCR : NA"
      ::= { radiusClientMIB 9 }

radAccServerEntry OBJECT-TYPE
      SYNTAX     RadAccServerEntry
      ACCESS     not-accessible
      STATUS     mandatory
      DESCRIPTION
            "An entry (conceptual row) representing the configuration 
             of a RADIUS server."
      INDEX { radAccServerIndex }
      ::= { radAccServerTable 1 }

RadAccServerEntry ::=
    SEQUENCE {
	  radAccServerIndex 		    INTEGER,
      radAccServerName              DisplayString,
	  radAccServerVrfIndex		    RouterIndex,
	  radAccServerAddrType		    InetAddressType,
	  radAccServerAddress		    InetAddress,
	  radAccServerPort   		    InetPortNumber,
	  radAccServerSecret			DisplayString,
	  radAccServerRetryLimit		RadiusRetryLimit,
	  radAccServerTimeoutLimit		RadiusTimeout,
	  radAccServerAdminState		INTEGER,
	  radAccServerOperState		    INTEGER,
	  radAccServerDeadInterval		RadiusDeadInterval,
	  radAccServerRowStatus		    RowStatus
}

radAccServerIndex     OBJECT-TYPE
	  SYNTAX		INTEGER
	  ACCESS		not-accessible
	  STATUS		mandatory
	  DESCRIPTION
             "Index used to uniquely identify an entry in this table.
          ALCATEL NOTE
             ACCESS: NA / INDEX
             USAGE: NA
             PERSIST:  	YES
             INSRVMOD: 	NA
             RANGE:	RANGE(1..256)
             DEFVALUE: 	NA
             UNITS:	NA 
             SPARSE:	NO 
             DESCR:	NA "
	  ::= { radAccServerEntry 1 }

radAccServerName     OBJECT-TYPE
	  SYNTAX		DisplayString (SIZE (1..64))
	  ACCESS		read-write
	  STATUS		mandatory
	  DESCRIPTION
         "A name uniquely identifying a RADIUS Acc Server within a Vrf. It 
          should be unique among the different Auth Servers configured.
          ALCATEL NOTE
             ACCESS: NA
             USAGE: MAND
             PERSIST:  	YES
             INSRVMOD: 	NO
             RANGE:	NA
             DEFVALUE: 	NA
             UNITS:	NA 
             SPARSE:	NO 
             DESCR:	NA "
	  ::= { radAccServerEntry 2 }

radAccServerVrfIndex     OBJECT-TYPE
	  SYNTAX		RouterIndex
	  ACCESS		read-write
	  STATUS		mandatory
	  DESCRIPTION
			"The RouterIndex to which the RADIUS Accounting server belongs.
              In case of NE with SHUB, this is the Vrf. In case of NE with IHUB
              this is the Service Id of the VPRN or the base router when 0.
	      In case of NE of the NGVR family (not containing SHUB, not containing IHUB)
	      it is 0.
          ALCATEL NOTE
             ACCESS: NA
             USAGE: MAND
             PERSIST:  	YES
             INSRVMOD: 	NO
             RANGE:	DEP (1..127) in case of NE with SHUB,
                        (0..2147483647) in case of NE with IHUB
                        (0) in case of NE with NGVR
             DEFVALUE: 	NA
             UNITS:	NA 
             SPARSE:	NO 
             DESCR:	NA "
	  ::= { radAccServerEntry 3 }

radAccServerAddrType        OBJECT-TYPE
	  SYNTAX		InetAddressType
	  ACCESS		read-write
	  STATUS		mandatory
	  DESCRIPTION
			" A value representing the type of Internet Address.
          ALCATEL NOTE:
             ACCESS: NA
             USAGE: OPT
             PERSIST:  	YES
             INSRVMOD: 	NO
             RANGE:	NA
             DEFVALUE: 	1(ipv4)
             UNITS:	NA 
             SPARSE:	NO 
             DESCR:	NA "
	  ::= { radAccServerEntry 4 }

radAccServerAddress        OBJECT-TYPE
	  SYNTAX		InetAddress
	  ACCESS		read-write
	  STATUS		mandatory
	  DESCRIPTION
		"The IP address of this RADIUS Accounting Server. The Type of 
          this Ip Address (IPv4/Ipv6/...) is determined by the value of the 
          object radAccServerAddrType.
          ALCATEL NOTE:
             ACCESS: NA
             USAGE: MAND
             PERSIST:  	YES
             INSRVMOD: 	YES
             RANGE: NA
             DEFVALUE: 	NA
             UNITS:	NA 
             SPARSE:	NO 
             DESCR:	NA "
	  ::= { radAccServerEntry 5 }

radAccServerPort OBJECT-TYPE
	  SYNTAX		InetPortNumber
	  ACCESS		read-write
	  STATUS		mandatory
	  DESCRIPTION
		"The UDP port number to which RADIUS accounting messages should be 
		 sent.
          ALCATEL NOTE:
             ACCESS: NA
             USAGE: OPT
             PERSIST:  	YES
             INSRVMOD: 	YES
             RANGE: NA
             DEFVALUE: 	1813
             UNITS:	NA 
             SPARSE:	NO 
             DESCR:	NA "
	  DEFVAL  {1813}
	  ::= { radAccServerEntry 6 }

radAccServerSecret   OBJECT-TYPE
	  SYNTAX		DisplayString (SIZE (6..64))
	  ACCESS		read-write
	  STATUS		mandatory
	  DESCRIPTION
		"The secret used in encrypting the packets passed between the RADIUS 
	      server and the client.
          For security reasons, the secret wont be displayed to the users.
          ALCATEL NOTE:
             ACCESS: NA
             USAGE: MAND
             PERSIST:  	YES
             INSRVMOD: 	YES
             RANGE: NA
             DEFVALUE: 	NA
             UNITS:	NA 
             SPARSE:	NO 
             DESCR:	NA "
	  ::= { radAccServerEntry 7 }

radAccServerRetryLimit       OBJECT-TYPE
	  SYNTAX		RadiusRetryLimit
	  ACCESS		read-write
	  STATUS		mandatory
	  DESCRIPTION
		"Indicates the  maximum number of times to resend a 
          request to this server (in addition to the original request), before
          giving up on the server.
          ALCATEL NOTE:
             ACCESS: NA
             USAGE: OPT
             PERSIST:  	YES
             INSRVMOD: 	YES
             RANGE: NA
             DEFVALUE: 	10
             UNITS:	NA 
             SPARSE:	NO 
             DESCR:	NA "
	  DEFVAL  {10}
	  ::= { radAccServerEntry 8 }

radAccServerTimeoutLimit     OBJECT-TYPE
	  SYNTAX		RadiusTimeout
	  ACCESS		read-write
	  STATUS		mandatory
	  DESCRIPTION
		"This is the time in seconds between retransmissions to the RADIUS 
		 server.
          ALCATEL NOTE:
             ACCESS: NA
             USAGE: OPT
             PERSIST:  	YES
             INSRVMOD: 	YES
             RANGE: NA
             DEFVALUE: 	15
             UNITS:	time in seconds 
             SPARSE:	NO 
             DESCR:	NA "
	  DEFVAL  {15}
	  ::= { radAccServerEntry 9 }

radAccServerAdminState       OBJECT-TYPE
	  SYNTAX		INTEGER {
                       	    up(1),
                            down(2)
                            }
	  ACCESS		read-write
	  STATUS		mandatory
	  DESCRIPTION
			" The Admin State of the Accounting Server.
          ALCATEL NOTE:
             ACCESS: NA
             USAGE: OPT
             PERSIST:  	YES
             INSRVMOD: 	YES
             RANGE: NA
             DEFVALUE: 	up
             UNITS:	NA 
             SPARSE:	NO 
             DESCR:	NA "
	  DEFVAL  { up }
	  ::= { radAccServerEntry 10 }

radAccServerOperState                OBJECT-TYPE
	  SYNTAX		INTEGER {
                            up(1),
                            down(2),
						    unknown(3)
                        }
	  ACCESS		read-only
	  STATUS		mandatory
	  DESCRIPTION
			" The Operational State of the Accounting Server.
            Initially the oper state of a server is unknown. When
            the first user sends accounting request to this server
            and if a reply is received, then the state of this server is
            moved to up state. When the server doesn't get a response 
            and goes to down state then the dead-interval timer is 
            started and when it expires, the state again moves to
            unknown. When a user has to be ccounted using this
            server, then the state goes to up state after receiving
            a reply from this server.
          ALCATEL NOTE:
             ACCESS: NA
             USAGE: NA
             PERSIST:  	NO
             INSRVMOD: 	NA
             RANGE: NA
             DEFVALUE: 	NA
             UNITS:	NA 
             SPARSE:	NO 
             DESCR:	NA "
	  ::= { radAccServerEntry 11 }

radAccServerDeadInterval     OBJECT-TYPE
	  SYNTAX		RadiusDeadInterval
	  ACCESS		read-write
	  STATUS		mandatory
	  DESCRIPTION
		"Indicates the number of seconds before setting the operational state
		 of this accounting server to
          unknown state from down state. A write to this object will immediately
          trigger the above mentioned action. If this Interval is set to zero,
          then the dead interval timer won't be started.
          ALCATEL NOTE:
             ACCESS: NA
             USAGE: OPT
             PERSIST:  	YES
             INSRVMOD: 	YES
             RANGE: NA
             DEFVALUE: 	600
             UNITS:	number of seconds 
             SPARSE:	NO 
             DESCR:	NA "
      DEFVAL  {600}
::= { radAccServerEntry 12 }

radAccServerRowStatus        OBJECT-TYPE
	  SYNTAX		RowStatus
	  ACCESS		read-write
	  STATUS		mandatory
	  DESCRIPTION
			"This is used for Row creation/Deletion.
          ALCATEL NOTE:
             ACCESS: NA
             USAGE: MAND
             PERSIST:  	YES
             INSRVMOD: 	YES
             RANGE: 1,4,6
             DEFVALUE: 	NA
             UNITS:	NA 
             SPARSE:	NO 
             DESCR:	NA " 
	  ::= { radAccServerEntry 13 }

-- End of RadAccServerTable

-- Start of radAccServerMappingTable

radAccServerMappingTable OBJECT-TYPE
      SYNTAX     SEQUENCE OF RadAccServerMappingEntry
      ACCESS     not-accessible
      STATUS     mandatory
      DESCRIPTION
            "The (conceptual) table ia a Mapping Table listing the RADIUS
            Acc Server Names within a Vrf with their equivalent Radius Acc
            Server Index used in the RADIUS Acc Server Table.
	        This is a Read-Only Table and for each entry in the Radius Acc
            Server Table, an corresponding entry is created in this table.

            ALCATEL NOTE :
              TABLESIZE : DEP on number of rows in radAccServerTable
              DESCR : NA"             
      ::= { radiusClientMIB 10 }

radAccServerMappingEntry OBJECT-TYPE
      SYNTAX     RadAccServerMappingEntry
      ACCESS 	 not-accessible
      STATUS     mandatory
      DESCRIPTION
            "An entry (conceptual row) representing the Radius Acc Server Name
            (Within a Vrf) to Index Mapping."
      INDEX      { radAccServerMappingVrf, radAccServerMappingName }
      ::= { radAccServerMappingTable 1 }

RadAccServerMappingEntry ::= SEQUENCE {
	  radAccServerMappingVrf				RouterIndex,
	  radAccServerMappingName				DisplayString,
	  radAccServerMappingIndex				INTEGER
    }

radAccServerMappingVrf OBJECT-TYPE
      SYNTAX     RouterIndex
      ACCESS 	 not-accessible
      STATUS     mandatory
      DESCRIPTION
             "The RouterIndex to which the RADIUS Acc Server belongs. 
              In case of NE with SHUB, this is the Vrf. In case of NE with IHUB
              this is the Service Id of the VPRN or the base router when 0.
	      In case of NE of the NGVR family (not containing SHUB, not containing IHUB)
	      it is 0.
          ALCATEL NOTE:
             ACCESS: NA / INDEX
             USAGE: NA
             PERSIST:  	YES
             INSRVMOD: 	NA
             RANGE: DEP (1..127) in case of NE with SHUB,
                        (0..2147483647) in case of NE with IHUB
                        (0) in case of NE with NGVR
             DEFVALUE: 	NA
             UNITS:	NA 
             SPARSE:	NO 
             DESCR:	NA "
      ::= { radAccServerMappingEntry 1 }

radAccServerMappingName OBJECT-TYPE
      SYNTAX     DisplayString (SIZE (1..64))
      ACCESS 	 not-accessible
      STATUS     mandatory
      DESCRIPTION
             "A name uniquely identifying a RADIUS Acc Server.
          ALCATEL NOTE:
             ACCESS: NA / INDEX
             USAGE: NA
             PERSIST:  	YES
             INSRVMOD: 	NA
             RANGE: NA
             DEFVALUE: 	NA
             UNITS:	NA 
             SPARSE:	NO 
             DESCR:	NA "
      ::= { radAccServerMappingEntry 2 }

radAccServerMappingIndex OBJECT-TYPE
      SYNTAX     INTEGER
      ACCESS 	 read-only
      STATUS     mandatory
      DESCRIPTION
             "The corresponding Index associated with this Name.
          ALCATEL NOTE:
             ACCESS: NA
             USAGE: NA
             PERSIST:  	NO
             INSRVMOD: 	NA
             RANGE: NA
             DEFVALUE: 	NA
             UNITS:	NA 
             SPARSE:	NO 
             DESCR:	NA "
      ::= { radAccServerMappingEntry 3 }

-- End of radAccServerMappingTable


-- Start of RadAccServerStatsTable

radAccServerStatsTable OBJECT-TYPE
      SYNTAX SEQUENCE OF RadAccServerStatsEntry
      ACCESS not-accessible
      STATUS mandatory
      DESCRIPTION
            "The (conceptual) table listing the RADIUS accounting
             servers with which the client shares a secret.

            ALCATEL NOTE :
              TABLESIZE : DEP on number of rows in radAccServerTable 
              DESCR : NA"
      ::= { radiusClientMIB 11 }

radAccServerStatsEntry OBJECT-TYPE
      SYNTAX     RadAccServerStatsEntry
      ACCESS     not-accessible
      STATUS     mandatory
      DESCRIPTION
            "An entry (conceptual row) representing a RADIUS
             accounting server with which the client shares a secret."
      INDEX      { radAccServerIndex }
      ::= { radAccServerStatsTable 1 }

RadAccServerStatsEntry ::= 
    SEQUENCE {
	  radAccClientRoundTripTime				TimeTicks,
	  radAccClientRequests						Counter,
	  radAccClientRetransmissions				Counter,
	  radAccClientResponses					Counter,
	  radAccClientMalformedResponses			Counter,
	  radAccClientBadAuthenticators			Counter,
	  radAccClientPendingRequests				Gauge,
	  radAccClientTimeouts						Counter,
	  radAccClientUnknownTypes					Counter,
	  radAccClientPacketsDropped				Counter
    }

radAccClientRoundTripTime  OBJECT-TYPE
      SYNTAX TimeTicks
      ACCESS read-only
      STATUS mandatory
      DESCRIPTION
             "The time interval between the most recent
             Accounting-Response and the Accounting-Request that
             matched it from this RADIUS accounting server.
          ALCATEL NOTE
             ACCESS: NA
             USAGE: NA
             PERSIST:  	NO
             INSRVMOD: 	NA
             RANGE:	NA
             DEFVALUE: 	NA
             UNITS:	NA 
             SPARSE:	NO 
             DESCR:	NA "
      ::= { radAccServerStatsEntry 1 }

-- Request/Response statistics
--
-- Requests = Responses + PendingRequests + ClientTimeouts
--
-- Responses - MalformedResponses - BadAuthenticators -
-- UnknownTypes - PacketsDropped = Successfully received

radAccClientRequests OBJECT-TYPE
      SYNTAX Counter
      ACCESS read-only
      STATUS mandatory
      DESCRIPTION
            "The number of RADIUS Accounting-Request packets
             sent. This does not include retransmissions.
          ALCATEL NOTE
             ACCESS: NA
             USAGE: NA
             PERSIST:  	NO
             INSRVMOD: 	NA
             RANGE:	NA
             DEFVALUE: 	NA
             UNITS:	NA 
             SPARSE:	NO 
             DESCR:	NA "
      ::= { radAccServerStatsEntry 2 }

radAccClientRetransmissions OBJECT-TYPE
      SYNTAX Counter
      ACCESS read-only
      STATUS mandatory
      DESCRIPTION
            "The number of RADIUS Accounting-Request packets
             retransmitted to this RADIUS accounting server.
             Retransmissions include retries where the
             Identifier and Acct-Delay have been updated, as
             well as those in which they remain the same.
          ALCATEL NOTE
             ACCESS: NA
             USAGE: NA
             PERSIST:  	NO
             INSRVMOD: 	NA
             RANGE:	NA
             DEFVALUE: 	NA
             UNITS:	NA 
             SPARSE:	NO 
             DESCR:	NA "
      ::= { radAccServerStatsEntry 3 }

radAccClientResponses OBJECT-TYPE
      SYNTAX Counter
      ACCESS read-only
      STATUS mandatory
      DESCRIPTION
            "The number of RADIUS packets received on the
             accounting port from this server.
          ALCATEL NOTE
             ACCESS: NA
             USAGE: NA
             PERSIST:  	NO
             INSRVMOD: 	NA
             RANGE:	NA
             DEFVALUE: 	NA
             UNITS:	NA 
             SPARSE:	NO 
             DESCR:	NA "
      ::= { radAccServerStatsEntry 4 }

radAccClientMalformedResponses OBJECT-TYPE
      SYNTAX Counter
      ACCESS read-only
      STATUS mandatory
      DESCRIPTION
             "The number of malformed RADIUS Accounting-Response
              packets received from this server. Malformed packets
             include packets with an invalid length. Bad
             authenticators and unknown types are not included as
             malformed accounting responses.
          ALCATEL NOTE
             ACCESS: NA
             USAGE: NA
             PERSIST:  	NO
             INSRVMOD: 	NA
             RANGE:	NA
             DEFVALUE: 	NA
             UNITS:	NA 
             SPARSE:	NO 
             DESCR:	NA "
      ::= { radAccServerStatsEntry 5 }

radAccClientBadAuthenticators OBJECT-TYPE
      SYNTAX Counter
      ACCESS read-only
      STATUS mandatory
      DESCRIPTION
            "The number of RADIUS Accounting-Response
             packets which contained invalid authenticators
             received from this server.
          ALCATEL NOTE
             ACCESS: NA
             USAGE: NA
             PERSIST:  	NO
             INSRVMOD: 	NA
             RANGE:	NA
             DEFVALUE: 	NA
             UNITS:	NA 
             SPARSE:	NO 
             DESCR:	NA "
      ::= { radAccServerStatsEntry 6 }

radAccClientPendingRequests OBJECT-TYPE
      SYNTAX Gauge
      ACCESS read-only
      STATUS mandatory
      DESCRIPTION
            "The number of RADIUS Accounting-Request packets
             sent to this server that have not yet timed out or
             received a response. This variable is incremented when an
             Accounting-Request is sent and decremented due to
             receipt of an Accounting-Response, a timeout or
             a retransmission.
          ALCATEL NOTE
             ACCESS: NA
             USAGE: NA
             PERSIST:  	NO
             INSRVMOD: 	NA
             RANGE:	NA
             DEFVALUE: 	NA
             UNITS:	NA 
             SPARSE:	NO 
             DESCR:	NA "
      ::= { radAccServerStatsEntry 7 }

radAccClientTimeouts OBJECT-TYPE
     SYNTAX Counter
     ACCESS read-only
     STATUS mandatory
     DESCRIPTION
          "The number of accounting timeouts to this server.
           After a timeout the client may retry to the same
           server, send to a different server, or give up.
           A retry to the same server is counted as a
           retransmit as well as a timeout. A send to a different
           server is counted as an Accounting-Request as well as
           a timeout.
          ALCATEL NOTE
             ACCESS: NA
             USAGE: NA
             PERSIST:  	NO
             INSRVMOD: 	NA
             RANGE:	NA
             DEFVALUE: 	NA
             UNITS:	NA 
             SPARSE:	NO 
             DESCR:	NA "
      ::= { radAccServerStatsEntry  8 }

radAccClientUnknownTypes OBJECT-TYPE
      SYNTAX Counter
      ACCESS read-only
      STATUS mandatory
      DESCRIPTION
            "The number of RADIUS packets of unknown type which
             were received from this server on the accounting port.
          ALCATEL NOTE
             ACCESS: NA
             USAGE: NA
             PERSIST:  	NO
             INSRVMOD: 	NA
             RANGE:	NA
             DEFVALUE: 	NA
             UNITS:	NA 
             SPARSE:	NO 
             DESCR:	NA "
      ::= { radAccServerStatsEntry  9 }

radAccClientPacketsDropped OBJECT-TYPE
      SYNTAX Counter
      ACCESS read-only
      STATUS mandatory
      DESCRIPTION
            "The number of RADIUS packets which were received from
             this server on the accounting port and dropped for some
             other reason.
          ALCATEL NOTE
             ACCESS: NA
             USAGE: NA
             PERSIST:  	NO
             INSRVMOD: 	NA
             RANGE:	NA
             DEFVALUE: 	NA
             UNITS:	NA 
             SPARSE:	NO 
             DESCR:	NA "
      ::= { radAccServerStatsEntry  10 }

-- End of RadAccServerStatisticsTable

radDynAuthClientGetNextFreeIndex  OBJECT-TYPE
    SYNTAX  INTEGER
    ACCESS  read-only
    STATUS  mandatory
    DESCRIPTION
         "The next Free Index value that can be used for creating
	     a new entry in the Radius Dyn Auth Client Table.
         This object contains an appropriate value to be used for 
         radDynAuthClientIndex when creating entries in the radDynAuthClientTable. 
         The value 0 indicates that no unassigned entries are available. To 
         obtain the radDynAuthClientIndex value for a new entry, the
         manager issues a management protocol retrieval operation to obtain the
         current-value of this object. After each retrieval, the agent should
         modify the value to the next unassigned index.
          ALCATEL NOTE
             ACCESS: NA
             USAGE: NA
             PERSIST:  	NO
             INSRVMOD: 	NA
             RANGE:	RANGE(0..256)
             DEFVALUE: 	NA
             UNITS:	NA 
             DESCR:	NA "
    ::= { radiusClientMIB 12 }

-- Start of radDynAuthClientTable

radDynAuthClientTable OBJECT-TYPE
      SYNTAX     SEQUENCE OF RadDynAuthClientEntry
      ACCESS     not-accessible
      STATUS     mandatory
      DESCRIPTION
            "The (conceptual) table listing the RADIUS Dynamic
             Authorization Clients with its configurable parameters.

            ALCATEL NOTE :
              TABLESIZE : 128 
              DESCR : NA"
      ::= { radiusClientMIB 13 }

radDynAuthClientEntry OBJECT-TYPE
      SYNTAX     RadDynAuthClientEntry
      ACCESS     not-accessible
      STATUS     mandatory
      DESCRIPTION
            "An entry (conceptual row) representing the configuration 
             of a RADIUS Dynamic Authorization Client."
      INDEX { radDynAuthClientIndex }
      ::= { radDynAuthClientTable 1 }

RadDynAuthClientEntry ::=
    SEQUENCE {
	  radDynAuthClientIndex		    INTEGER,
	  radDynAuthClientName		    DisplayString,
	  radDynAuthClientVrfIndex		RouterIndex,
	  radDynAuthClientAddrType		InetAddressType,
	  radDynAuthClientAddress		InetAddress,
	  radDynAuthClientSecret		DisplayString,
	  radDynAuthClientAdminState	INTEGER,
	  radDynAuthClientRowStatus		RowStatus
}

radDynAuthClientIndex     OBJECT-TYPE
	  SYNTAX		INTEGER
	  ACCESS		not-accessible
	  STATUS		mandatory
	  DESCRIPTION
             "Index used to uniquely identify an entry in this table.
          ALCATEL NOTE
             ACCESS: NA / INDEX
             USAGE: NA
             PERSIST:  	YES
             INSRVMOD: 	NA
             RANGE:	RANGE(1..128)
             DEFVALUE: 	NA
             UNITS:	NA 
             SPARSE:	NO 
             DESCR:	NA "
	  ::= { radDynAuthClientEntry 1 }

radDynAuthClientName     OBJECT-TYPE
	  SYNTAX		DisplayString (SIZE (1..64))
	  ACCESS		read-write
	  STATUS		mandatory
	  DESCRIPTION
             "A name uniquely identifying a RADIUS Dynamic Authorisation Server.
          ALCATEL NOTE
             ACCESS: NA
             USAGE: MAND
             PERSIST:  	YES
             INSRVMOD: 	NO
             RANGE:	NA
             DEFVALUE: 	NA
             UNITS:	NA 
             SPARSE:	NO 
             DESCR:	NA "
	  ::= { radDynAuthClientEntry 2 }

radDynAuthClientVrfIndex     OBJECT-TYPE
	  SYNTAX		RouterIndex
	  ACCESS		read-write
	  STATUS		mandatory
	  DESCRIPTION
			"The RouterIndex to which the RADIUS Dynamic Authorization Client
              belongs. 
              In case of NE with SHUB, this is the Vrf. In case of NE with IHUB
              this is the Service Id of the VPRN or the base router when 0.
	      In case of NE of the NGVR family (not containing SHUB, not containing IHUB)
	      it is 0.
          ALCATEL NOTE
             ACCESS: NA
             USAGE: MAND
             PERSIST:  	YES
             INSRVMOD: 	NO
             RANGE:	DEP (1..127) in case of NE with SHUB,
                        (0..2147483647) in case of NE with IHUB
                        (0) in case of NE with NGVR
             DEFVALUE: 	NA
             UNITS:	NA 
             SPARSE:	NO 
             DESCR:	NA "
	  ::= { radDynAuthClientEntry 3 }

radDynAuthClientAddrType        OBJECT-TYPE
	  SYNTAX		InetAddressType
	  ACCESS		read-write
	  STATUS		mandatory
	  DESCRIPTION
			" A value representing the type of Internet Address.
          ALCATEL NOTE:
             ACCESS: NA
             USAGE: OPT
             PERSIST:  	YES
             INSRVMOD: 	NO
             RANGE:	NA
             DEFVALUE: 	1(ipv4)
             UNITS:	NA 
             SPARSE:	NO 
             DESCR:	NA "
	  ::= { radDynAuthClientEntry 4 }

radDynAuthClientAddress        OBJECT-TYPE
	  SYNTAX		InetAddress
	  ACCESS		read-write
	  STATUS		mandatory
	  DESCRIPTION
		"The IP address of the RADIUS Dynamic Authorization Client. The Type of
          this Ip Address (IPv4/Ipv6/...) is determined by the value of the 
          object radDynAuthClientAddrType.
          ALCATEL NOTE
             ACCESS: NA
             USAGE: MAND
             PERSIST:  	YES
             INSRVMOD: 	NO
             RANGE:	NA
             DEFVALUE: 	NA
             UNITS:	NA 
             SPARSE:	NO 
             DESCR:	NA "
	  ::= { radDynAuthClientEntry 5 }

radDynAuthClientSecret   OBJECT-TYPE
	  SYNTAX		DisplayString (SIZE (6..64))
	  ACCESS		read-write
	  STATUS		mandatory
	  DESCRIPTION
			"The secret used in encrypting the packets passed between the
            RADIUS Dynamic Authorization Client and the server.
            For security reasons the secret wont be displayed to the users.
          ALCATEL NOTE
             ACCESS: NA
             USAGE: MAND
             PERSIST:  	YES
             INSRVMOD: 	YES
             RANGE:	NA
             DEFVALUE: 	NA
             UNITS:	NA 
             SPARSE:	NO 
             DESCR:	NA "
	  ::= { radDynAuthClientEntry 6 }

radDynAuthClientAdminState       OBJECT-TYPE
	  SYNTAX		INTEGER {
                       	    up(1),
                            down(2)
                            }
	  ACCESS		read-write
	  STATUS		mandatory
	  DESCRIPTION
			" The Admin State of the RADIUS Dynamic Authorization Client.
          ALCATEL NOTE
             ACCESS: NA
             USAGE: OPT
             PERSIST:  	YES
             INSRVMOD: 	YES
             RANGE:	NA
             DEFVALUE: 	up
             UNITS:	NA 
             SPARSE:	NO 
             DESCR:	NA "
	  DEFVAL  { up }
	  ::= { radDynAuthClientEntry 7 }

radDynAuthClientRowStatus       OBJECT-TYPE
	  SYNTAX		RowStatus
	  ACCESS		read-write
	  STATUS		mandatory
	  DESCRIPTION
			" Used for Row Creation/Deletion.
          ALCATEL NOTE
             ACCESS: NA
             USAGE: MAND
             PERSIST:  	YES
             INSRVMOD: 	YES
             RANGE:	1,4,6
             DEFVALUE: 	NA
             UNITS:	NA 
             SPARSE:	NO 
             DESCR:	NA "
	  ::= { radDynAuthClientEntry 8 }

-- End of radDynAuthClientTable

-- Start of radDynAuthClientMappingTable

radDynAuthClientMappingTable OBJECT-TYPE
      SYNTAX     SEQUENCE OF RadDynAuthClientMappingEntry
      ACCESS     not-accessible
      STATUS     mandatory
      DESCRIPTION
         "The (conceptual) table ia a Mapping Table listing the RADIUS
          Dynamic Authorisation Client Names within a Vrf with their equivalent
          Radius Dynamic Auth Client Index used in the RADIUS Dyn Auth Client
          Table.
          This is a Read-Only Table and for each entry in the Radius Dyn Auth
          Client Table, an corresponding entry is created in this table.

            ALCATEL NOTE :
              TABLESIZE : DEP on number of rown in radDynAuthClientTable
              DESCR : NA "             
      ::= { radiusClientMIB 14 }

radDynAuthClientMappingEntry OBJECT-TYPE
      SYNTAX     RadDynAuthClientMappingEntry
      ACCESS 	 not-accessible
      STATUS     mandatory
      DESCRIPTION
        "An entry (conceptual row) representing the Radius Dyn Auth Client Name
         (Within a Vrf) to Index Mapping."
      INDEX      { radDynAuthClientMappingVrf, radDynAuthClientMappingName }
      ::= { radDynAuthClientMappingTable 1 }

RadDynAuthClientMappingEntry ::= SEQUENCE {
	  radDynAuthClientMappingVrf    			RouterIndex,
	  radDynAuthClientMappingName				DisplayString,
	  radDynAuthClientMappingIndex				INTEGER
    }

radDynAuthClientMappingVrf OBJECT-TYPE
      SYNTAX     RouterIndex
      ACCESS 	 not-accessible
      STATUS     mandatory
      DESCRIPTION
             "The RouterIndex to which the RADIUS Dyn Auth Client belongs. 
              In case of NE with SHUB, this is the Vrf. In case of NE with IHUB
              this is the Service Id of the VPRN or the base router when 0.
	      In case of NE of the NGVR family (not containing SHUB, not containing IHUB)
	      it is 0.
          ALCATEL NOTE
             ACCESS: NA / INDEX
             USAGE: NA
             PERSIST:  	YES
             INSRVMOD: 	NA
             RANGE:	DEP (1..127) in case of NE with SHUB,
                        (0..2147483647) in case of NE with IHUB 
                        (0) in case of NE with NGVR
             DEFVALUE: 	NA
             UNITS:	NA 
             SPARSE:	NO 
             DESCR:	NA "
      ::= { radDynAuthClientMappingEntry 1 }

radDynAuthClientMappingName OBJECT-TYPE
      SYNTAX     DisplayString (SIZE (1..64))
      ACCESS 	 not-accessible
      STATUS     mandatory
      DESCRIPTION
             "A name uniquely identifying a RADIUS Dyn Auth Client.
          ALCATEL NOTE
             ACCESS: NA / INDEX
             USAGE: NA
             PERSIST:  	YES
             INSRVMOD: 	NA
             RANGE:	NA
             DEFVALUE: 	NA
             UNITS:	NA 
             SPARSE:	NO 
             DESCR:	NA "
      ::= { radDynAuthClientMappingEntry 2 }

radDynAuthClientMappingIndex OBJECT-TYPE
      SYNTAX     INTEGER
      ACCESS 	 read-only
      STATUS     mandatory
      DESCRIPTION
             "The corresponding Index associated with this Name.
          ALCATEL NOTE
             ACCESS: NA
             USAGE: NA
             PERSIST:  	NO
             INSRVMOD: 	NA
             RANGE:	NA
             DEFVALUE: 	NA
             UNITS:	NA 
             SPARSE:	NO 
             DESCR:	NA "
      ::= { radDynAuthClientMappingEntry 3 }

-- End of radDynAuthClientMappingTable


-- Start of radDynAuthClientStatisticsTable

radDynAuthClientStatsTable OBJECT-TYPE
      SYNTAX SEQUENCE OF RadDynAuthClientStatsEntry
      ACCESS not-accessible
      STATUS mandatory
      DESCRIPTION
            "The (conceptual) table listing the statistics of the RADIUS
            Dynamic Authorization Clients with which the Server shares a secret.

            ALCATEL NOTE :
              TABLESIZE : DEP on number of rows in the radDynAuthClientTable
              DESCR : NA "
      ::= { radiusClientMIB 15 }

radDynAuthClientStatsEntry OBJECT-TYPE
      SYNTAX     RadDynAuthClientStatsEntry
      ACCESS     not-accessible
      STATUS     mandatory
      DESCRIPTION
            "An entry (conceptual row) representing a RADIUS
             Dynamic Authorization Clients statistics with which the Server shares a secret."
      INDEX      { radDynAuthClientIndex }
      ::= { radDynAuthClientStatsTable 1 }

RadDynAuthClientStatsEntry ::= 
    SEQUENCE {
	  radDynAuthServerDisconRequests				Counter,
	  radDynAuthServerDisconAcks        			Counter,
	  radDynAuthServerDisconNaks					Counter,
	  radDynAuthServerDisconMalformedRequests		Counter,
	  radDynAuthServerDisconBadAuthenticators		Counter,
	  radDynAuthServerDisconPacketsDropped		    Counter,
	  radDynAuthServerUnknownTypes			        Counter
    }

radDynAuthServerDisconRequests OBJECT-TYPE
      SYNTAX    Counter
      ACCESS    read-only
      STATUS    mandatory
      DESCRIPTION
            "The number of RADIUS Disconnect-Request packets
             recieved from this Dynamic Authorization Client.
          ALCATEL NOTE
             ACCESS: NA
             USAGE: NA
             PERSIST:  	NO
             INSRVMOD: 	NA
             RANGE:	NA
             DEFVALUE: 	NA
             UNITS:	NA 
             SPARSE:	NO 
             DESCR:	NA "
      ::= { radDynAuthClientStatsEntry 1 }

radDynAuthServerDisconAcks OBJECT-TYPE
      SYNTAX    Counter
      ACCESS    read-only
      STATUS    mandatory
      DESCRIPTION
            "The number of RADIUS Disconnect-ACK packets
             sent to this Dynamic Authorization Client.
          ALCATEL NOTE
             ACCESS: NA
             USAGE: NA
             PERSIST:  	NO
             INSRVMOD: 	NA
             RANGE:	NA
             DEFVALUE: 	NA
             UNITS:	NA 
             SPARSE:	NO 
             DESCR:	NA "
      ::= { radDynAuthClientStatsEntry 2 }

radDynAuthServerDisconNaks OBJECT-TYPE
      SYNTAX    Counter
      ACCESS    read-only
      STATUS    mandatory
      DESCRIPTION
            "The number of RADIUS Disconnect-NAK packets
             sent to this Dynamic Authorization Client.
          ALCATEL NOTE
             ACCESS: NA
             USAGE: NA
             PERSIST:  	NO
             INSRVMOD: 	NA
             RANGE:	NA
             DEFVALUE: 	NA
             UNITS:	NA 
             SPARSE:	NO 
             DESCR:	NA "
      ::= { radDynAuthClientStatsEntry 3 }

radDynAuthServerDisconMalformedRequests OBJECT-TYPE
      SYNTAX    Counter
      ACCESS    read-only
      STATUS    mandatory
      DESCRIPTION
             "The number of malformed RADIUS Disconnect-Request
              packets received from this Dynamic Authorization client.
              Bad authenticators and unknown types are not included as
              malformed Disconnect-Requests. Malformed packets
              include packets with an invalid length.
          ALCATEL NOTE
             ACCESS: NA
             USAGE: NA
             PERSIST:  	NO
             INSRVMOD: 	NA
             RANGE:	NA
             DEFVALUE: 	NA
             UNITS:	NA 
             SPARSE:	NO 
             DESCR:	NA "
      ::= { radDynAuthClientStatsEntry 4 }

radDynAuthServerDisconBadAuthenticators OBJECT-TYPE
      SYNTAX    Counter
      ACCESS    read-only
      STATUS    mandatory
      DESCRIPTION
             "The number of RADIUS Disconnect-Request packets
              which contained invalid Signature attributes received
              from this Dynamic Authorization Client.
          ALCATEL NOTE
             ACCESS: NA
             USAGE: NA
             PERSIST:  	NO
             INSRVMOD: 	NA
             RANGE:	NA
             DEFVALUE: 	NA
             UNITS:	NA 
             SPARSE:	NO 
             DESCR:	NA "
      ::= { radDynAuthClientStatsEntry 5 }

radDynAuthServerDisconPacketsDropped OBJECT-TYPE
      SYNTAX    Counter
      ACCESS    read-only
      STATUS    mandatory
      DESCRIPTION
            "The number of incoming Disconnect-Requests from this Dynamic Authorization
            Client silently discarded for some reason other than malformed, bad authenticators
            or unknown types.
          ALCATEL NOTE
             ACCESS: NA
             USAGE: NA
             PERSIST:  	NO
             INSRVMOD: 	NA
             RANGE:	NA
             DEFVALUE: 	NA
             UNITS:	NA 
             SPARSE:	NO 
             DESCR:	NA "
      ::= { radDynAuthClientStatsEntry  6 }

radDynAuthServerUnknownTypes OBJECT-TYPE
      SYNTAX    Counter
      ACCESS    read-only
      STATUS    mandatory
      DESCRIPTION
            "The number of incoming packets of unknown types which
             were received on the Dynamic Authorization port.
          ALCATEL NOTE
             ACCESS: NA
             USAGE: NA
             PERSIST:  	NO
             INSRVMOD: 	NA
             RANGE:	NA
             DEFVALUE: 	NA
             UNITS:	NA 
             SPARSE:	NO 
             DESCR:	NA "
      ::= { radDynAuthClientStatsEntry  7 }

-- End of radDynAuthClientStatsTable


-- Start of radPolicyTable

radPolicyGetNextFreeIndex OBJECT-TYPE
      SYNTAX    INTEGER
      ACCESS    read-only
      STATUS    mandatory
      DESCRIPTION
         "The next Free Index value that can be used for creating
	     a new entry in the Radius Policy Table.
         This object contains an appropriate value to be used for 
         radPolicyIndex when creating entries in the radPolicyTable. 
         The value 0 indicates that no unassigned entries are available. To 
         obtain the radPolicyIndex value for a new entry, the
         manager issues a management protocol retrieval operation to obtain the
         current-value of this object. After each retrieval, the agent should
         modify the value to the next unassigned index.
          ALCATEL NOTE
             ACCESS: NA
             USAGE: NA
             PERSIST:  	NO
             INSRVMOD: 	NA
             RANGE:	RANGE(0..128)
             DEFVALUE: 	NA
             UNITS:	NA  
             DESCR:	NA "
      ::= { radiusClientMIB 16 }

radPolicyTable OBJECT-TYPE
      SYNTAX     SEQUENCE OF RadPolicyEntry
      ACCESS     not-accessible
      STATUS     mandatory
      DESCRIPTION
            "The (conceptual) table listing the RADIUS policies 
             together with the parameters applicable globally for 
             the RADIUS policy.
             
             An entry in this table (policy) can be deleted only if it is not
             associated with any of the domains.
             
			 If a row in this table is deleted, then also the corresponding rows in
		     the radServerSetTable will also be deleted.

            ALCATEL NOTE :
              TABLESIZE : 128 
              DESCR : NA"
      ::= { radiusClientMIB 17 }

radPolicyEntry OBJECT-TYPE
      SYNTAX     RadPolicyEntry
      ACCESS 	 not-accessible
      STATUS     mandatory
      DESCRIPTION
            "An entry (conceptual row) representing the global
             configuration parameters of a RADIUS policy."
      INDEX      { radPolicyIndex }
      ::= { radPolicyTable 1 }

RadPolicyEntry ::= SEQUENCE {
	  radPolicyIndex					INTEGER,
	  radPolicyName					    DisplayString,
	  radPolicyNasId					DisplayString,
      radPolicyNasIpAddrType            InetAddressType,
	  radPolicyNasIpAddress				InetAddress,
	  radPolicyStrippingDomain			TruthValue,
	  radPolicyBootFlag					TruthValue,
  	  radPolicyAccInterim				INTEGER,
	  radPolicyEap					    TruthValue,
	  radPolicyRowStatus				RowStatus
    }

radPolicyIndex OBJECT-TYPE
      SYNTAX     INTEGER
      ACCESS 	 not-accessible
      STATUS     mandatory
      DESCRIPTION
             "Index used to uniquely identify an entry in this table.
          ALCATEL NOTE
             ACCESS: NA / INDEX
             USAGE: NA
             PERSIST:  	YES
             INSRVMOD: 	NA
             RANGE:	RANGE(1..128)
             DEFVALUE: 	NA
             UNITS:	NA 
             SPARSE:	NO 
             DESCR:	NA "
      ::= { radPolicyEntry 1 }

radPolicyName OBJECT-TYPE
      SYNTAX     DisplayString (SIZE (1..64))
      ACCESS 	 read-write
      STATUS     mandatory
      DESCRIPTION
             "A name uniquely identifying a RADIUS policy.
          ALCATEL NOTE
             ACCESS: NA
             USAGE: MAND
             PERSIST:  	YES
             INSRVMOD: 	NO
             RANGE:	NA
             DEFVALUE: 	NA
             UNITS:	NA 
             SPARSE:	NO 
             DESCR:	NA "
      ::= { radPolicyEntry 2 }

radPolicyNasId           OBJECT-TYPE
	  SYNTAX		DisplayString
	  ACCESS		read-write
	  STATUS		mandatory
	  DESCRIPTION
             "The NAS-Identifier used in messages towards the Radius servers. An 
             empty string means that no NAS-Identifier is put in the Radius 
             messages. Either NasId or NasIpAddress (or both) must be configured for a profile.
          ALCATEL NOTE
             ACCESS: NA
             USAGE: MAND
             PERSIST:  	YES
             INSRVMOD: 	YES
             RANGE:	NA
             DEFVALUE: 	NA
             UNITS:	NA 
             SPARSE:	NO 
             DESCR:	NA"
	  DEFVAL  {""}
      ::= { radPolicyEntry 3 }

radPolicyNasIpAddrType OBJECT-TYPE
      SYNTAX     InetAddressType
      ACCESS 	 read-write
      STATUS     mandatory
      DESCRIPTION
			" A value representing the type of Internet Address used for Nas Ip
            Address associated with this Radius Policy.
          ALCATEL NOTE:
             ACCESS: NA
             USAGE: OPT
             PERSIST:  	YES
             INSRVMOD: 	NO
             RANGE:	NA
             DEFVALUE: 	1(ipv4)
             UNITS:	NA 
             SPARSE:	NO 
             DESCR:	NA "
      ::= { radPolicyEntry 4 }
 
radPolicyNasIpAddress       OBJECT-TYPE
	  SYNTAX		InetAddress
	  ACCESS		read-write
	  STATUS		mandatory
	  DESCRIPTION
		"The NAS-IP-Address used in messages towards the Radius servers. A 
		 zero value (0.0.0.0) means that no NAS-IP-Address is put in the Radius 
		 messages if a radPolicyNasId has been configured different from 
		 the default. Either NasId or NasIpAddress (or both) must be configured
		 for a profile.
         The Type of this InetAddress (IPv4/Ipv6/..) is identified by the
         value of the radPolicyAddrType.
         ALCATEL NOTE
             ACCESS: NA
             USAGE: OPT
             PERSIST:  	YES
             INSRVMOD: 	YES
             RANGE:	NA
             DEFVALUE: 0.0.0.0
             UNITS:	NA 
             SPARSE:	NO 
             DESCR:	NA "
	  DEFVAL {'00000000'H} -- 0.0.0.0
	  ::= { radPolicyEntry 5 }

radPolicyStrippingDomain    OBJECT-TYPE
	  SYNTAX		TruthValue
	  ACCESS		read-write
	  STATUS		mandatory
	  DESCRIPTION
		"When set to True the domain name is stripped off when sending to the 
		 Radius server. But this flag is applicable only for users using any  
          Non-EAP authentication methods.
          ALCATEL NOTE
             ACCESS: NA
             USAGE: OPT
             PERSIST:  	YES
             INSRVMOD: 	YES
             RANGE:	NA
             DEFVALUE: 	TRUE
             UNITS:	NA 
             SPARSE:	NO 
             DESCR:	NA "
	  DEFVAL  {true}
	  ::= { radPolicyEntry 6 }

radPolicyBootFlag           OBJECT-TYPE
	  SYNTAX		TruthValue
	  ACCESS		read-write
	  STATUS		mandatory
	  DESCRIPTION
		" When set to TRUE, the system will send accounting-on message
          after the reboot. 
          When Set to False, the system will send no accounting on messages
		  when it is rebooted.
          ALCATEL NOTE
             ACCESS: NA
             USAGE: OPT
             PERSIST:  	YES
             INSRVMOD: 	YES
             RANGE:	NA
             DEFVALUE: 	TRUE
             UNITS:	NA 
             SPARSE:	NO 
             DESCR:	NA "
	  DEFVAL {true}
	  ::= { radPolicyEntry 7 }

radPolicyAccInterim OBJECT-TYPE
      SYNTAX		INTEGER (0|60..2147483647)
      ACCESS		read-write
      STATUS		mandatory
      DESCRIPTION
             " This is the Interim Accounting Interval in seconds and the value 
             zero specifies that no Interim accounting is necessary, except if 
             the Radius authentication server gives a value. The minimum value is at
             least 60 seconds (see RFC 2869). If it is set to any other value than
             zero then it takes precedence over the one returned by the RADIUS 
             server (See section 2.1 in RFC 2869).
          ALCATEL NOTE
             ACCESS: NA
             USAGE: OPT
             PERSIST:  	YES
             INSRVMOD: 	YES
             RANGE:	RANGE(0, 60..2147483647)
             DEFVALUE: 	0
             UNITS:	NA 
             SPARSE:	NO 
             DESCR:	NA "
      DEFVAL {0}
      ::= { radPolicyEntry 8 }

radPolicyEap	   OBJECT-TYPE
      SYNTAX		TruthValue
      ACCESS		read-write
      STATUS		mandatory
      DESCRIPTION
             "When set to False, the system will not use the EAP attribute 
             whenever EAP is used at the user interface (in case of 802.1x). 
             If set to True, the EAP attribute will be used.
          ALCATEL NOTE
             ACCESS: NA
             USAGE: OPT
             PERSIST:  	YES
             INSRVMOD: 	YES
             RANGE:	NA
             DEFVALUE: 	TRUE
             UNITS:	NA 
             SPARSE:	NO 
             DESCR:	NA "         
      DEFVAL {true}
      ::= { radPolicyEntry 9 }

radPolicyRowStatus  OBJECT-TYPE
	  SYNTAX		RowStatus
	  ACCESS		read-write
	  STATUS		mandatory
	  DESCRIPTION
			" Used for Row Creation/Deletion.
          ALCATEL NOTE
             ACCESS: NA
             USAGE: MAND
             PERSIST:  	YES
             INSRVMOD: 	YES
             RANGE:	1,4,6
             DEFVALUE: 	NA
             UNITS:	NA 
             SPARSE:	NO 
             DESCR:	NA "
	  ::= { radPolicyEntry 10 }

-- End of radPolicyTable

radPolicyMappingTable OBJECT-TYPE
      SYNTAX     SEQUENCE OF RadPolicyMappingEntry
      ACCESS     not-accessible
      STATUS     mandatory
      DESCRIPTION
            "The (conceptual) table ia a Mapping Table listing the RADIUS
            policy Names with their equivalent Radius Policy Index used in the RADIUS 
            Policy Table.
	        This is a Read-Only Table and for each entry in the Radius policy Table,
	        an corresponding entry is created in this table.

            ALCATEL NOTE :
              TABLESIZE : DEP on number of rows in radPolicyTable
              DESCR : NA "             
      ::= { radiusClientMIB 18 }

radPolicyMappingEntry OBJECT-TYPE
      SYNTAX     RadPolicyMappingEntry
      ACCESS 	 not-accessible
      STATUS     mandatory
      DESCRIPTION
            "An entry (conceptual row) representing the Radius Name to Index Mapping."
      INDEX      { radPolicyMappingName }
      ::= { radPolicyMappingTable 1 }

RadPolicyMappingEntry ::= SEQUENCE {
	  radPolicyMappingName					DisplayString,
	  radPolicyMappingIndex					INTEGER
    }

radPolicyMappingName OBJECT-TYPE
      SYNTAX     DisplayString (SIZE (1..64))
      ACCESS 	 not-accessible
      STATUS     mandatory
      DESCRIPTION
             "A name uniquely identifying a RADIUS policy.
          ALCATEL NOTE
             ACCESS: NA / INDEX
             USAGE: NA
             PERSIST:  	YES
             INSRVMOD: 	NA
             RANGE:	NA
             DEFVALUE: 	NA
             UNITS:	NA 
             SPARSE:	NO 
             DESCR:	NA "
      ::= { radPolicyMappingEntry 1 }

radPolicyMappingIndex OBJECT-TYPE
      SYNTAX     INTEGER
      ACCESS 	 read-only
      STATUS     mandatory
      DESCRIPTION
             "The corresponding Index associated with this Name.
          ALCATEL NOTE
             ACCESS: NA
             USAGE: NA
             PERSIST:  	NO
             INSRVMOD: 	NA
             RANGE:	NA
             DEFVALUE: 	NA
             UNITS:	NA 
             SPARSE:	NO 
             DESCR:	NA "
      ::= { radPolicyMappingEntry 2 }

-- End of radPolicyMappingTable


-- Start of radServerSetGetNextIndexTable

radServerSetGetNextIndexTable OBJECT-TYPE
      SYNTAX     SEQUENCE OF RadServerSetGetNextIndexEntry
      ACCESS 	 not-accessible
      STATUS     mandatory
      DESCRIPTION
            "The (conceptual) table used for getting the Free Index
            that can be used for creating a new entry in the 
            radServerSetTable.

            ALCATEL NOTE :
              TABLESIZE : 1 
              DESCR : NA"
      ::= { radiusClientMIB 19 }

radServerSetGetNextIndexEntry OBJECT-TYPE
      SYNTAX 	RadServerSetGetNextIndexEntry
      ACCESS 	not-accessible
      STATUS    mandatory
      DESCRIPTION
            "An entry (conceptual row) representing a value that
            can be used for creating a new entry in the 
            radServerSetTable."
      INDEX      { radPolicyIndex }
      ::= { radServerSetGetNextIndexTable 1 }

RadServerSetGetNextIndexEntry ::= SEQUENCE {
	  radServerSetNextFreeIndex			INTEGER
}

radServerSetNextFreeIndex OBJECT-TYPE
      SYNTAX     INTEGER
      ACCESS     read-only
      STATUS     mandatory
      DESCRIPTION
         "A unique number within a Radius Policy that can
          be used for creating a new entry in the radServerSetTable.
          The value 0 indicates that no unassigned entries are available. To 
          obtain the radServerSetIndex value for a new entry, the
          manager issues a management protocol retrieval operation to obtain the
          current value of this object.  After each retrieval, the agent should
          modify the value to the next unassigned index.
          ALCATEL NOTE
             ACCESS: NA
             USAGE: NA
             PERSIST:  	NO
             INSRVMOD: 	NA
             RANGE:	NA
             DEFVALUE: 	NA
             UNITS:	NA 
             SPARSE:	NO 
             DESCR:	NA "
      ::= { radServerSetGetNextIndexEntry 1 }

-- End of radServerSetGetNextIndexTable

--Start of radServerSetTable

radServerSetTable OBJECT-TYPE
      SYNTAX     SEQUENCE OF RadServerSetEntry
      ACCESS 	 not-accessible
      STATUS     mandatory
      DESCRIPTION
            "The (conceptual) table listing the set of RADIUS servers, together
			with the parameters of that set. The servers that are put in a set 
			using this table first have to be defined in radAuthServerTable 
            and radAccServerTable.

            The value returned by the radServerSetGetNextIndexTable is used
            by the management station as the value for the index radServerSetIndex,
            while creating a new entry in this table.

            ALCATEL NOTE :
              TABLESIZE : DEP on the number of rows in radPolicyTable 
              DESCR : NA"
      ::= { radiusClientMIB 20 }

radServerSetEntry OBJECT-TYPE
      SYNTAX     RadServerSetEntry
      ACCESS 	 not-accessible
      STATUS     mandatory
      DESCRIPTION
            "An entry (conceptual row) representing a set of Radius servers."
      INDEX      { radPolicyIndex, radServerSetIndex }
      ::= { radServerSetTable 1 }

RadServerSetEntry ::= SEQUENCE {
	  radServerSetIndex				INTEGER,
	  radServerSetAuthServerIndex 	INTEGER,
	  radServerSetAccServerIndex    INTEGER,
	  radServerSetPriority			INTEGER,
	  radServerSetRowStatus			RowStatus
      }

radServerSetIndex OBJECT-TYPE
      SYNTAX     INTEGER
      ACCESS 	 not-accessible
      STATUS     mandatory
      DESCRIPTION
             "A number uniquely identifying a set within a RADIUS profile.
          ALCATEL NOTE
             ACCESS: NA / INDEX
             USAGE: NA
             PERSIST:  	YES
             INSRVMOD: 	NA
             RANGE:	NA
             DEFVALUE: 	NA
             UNITS:	NA 
             SPARSE:	NO 
             DESCR:	NA "
      ::= { radServerSetEntry 1 }

radServerSetAuthServerIndex        OBJECT-TYPE
      SYNTAX     INTEGER
      ACCESS 	 read-write
      STATUS     mandatory
      DESCRIPTION
             "The Index of the Authentication Radius server 
             defined in the radiusAuthServerTable.
          ALCATEL NOTE
             ACCESS: NA
             USAGE: MAND
             PERSIST:  	YES
             INSRVMOD: 	YES
             RANGE:	RANGE(1..256)
             DEFVALUE: 	NA
             UNITS:	NA 
             SPARSE:	NO 
             DESCR:	NA "
      ::= { radServerSetEntry 2 }

radServerSetAccServerIndex         OBJECT-TYPE
      SYNTAX	 INTEGER
      ACCESS 	 read-write
      STATUS     mandatory
      DESCRIPTION
             "The Index of the Radius Accounting server 
             defined in the radiusAccServerTable. This object is optional
             and is used only when Accounting is required by the Domains using
             the Radius Policy linked with this Set.
          ALCATEL NOTE
             ACCESS: NA
             USAGE: OPT
             PERSIST:  	YES
             INSRVMOD: 	YES
             RANGE:	RANGE(0..256)
             DEFVALUE: 	0
             UNITS:	NA 
             SPARSE:	NO 
             DESCR:	NA "
	  DEFVAL {0}
      ::= { radServerSetEntry 3 }

radServerSetPriority         OBJECT-TYPE
      SYNTAX     INTEGER (1..256)
      ACCESS	 read-write
      STATUS     mandatory
      DESCRIPTION
             "This object defines the priority of the set relative to the 
             other sets defined within the same radPolicy. Lesser the
             Priority when this value is higher.
          ALCATEL NOTE
             ACCESS: NA
             USAGE: MAND
             PERSIST:  	YES
             INSRVMOD: 	YES
             RANGE:	RANGE(1..256)
             DEFVALUE: 	NA
             UNITS:	NA 
             SPARSE:	NO 
             DESCR:	NA "
      ::= { radServerSetEntry 4 }

 radServerSetRowStatus       OBJECT-TYPE
      SYNTAX     RowStatus
      ACCESS 	 read-write
      STATUS     mandatory
      DESCRIPTION
             " Used for Row Creation/Deletion.
          ALCATEL NOTE
             ACCESS: NA
             USAGE: MAND
             PERSIST:  	YES
             INSRVMOD: 	YES
             RANGE:	1,4,6
             DEFVALUE: 	NA
             UNITS:	NA 
             SPARSE:	NO 
             DESCR:	NA "
      ::= { radServerSetEntry 5 }

-- End of radServerSetTable


   radAuthServNoRespStatus OBJECT-TYPE
      SYNTAX	OCTET STRING (SIZE (32))
      ACCESS	read-only
      STATUS	mandatory
      DESCRIPTION
             "The octet string represents a bit map of all possibe
             Authentication Servers. The least significant bit of the
             last octet corresponds to server index 1, the next least
             significant bit corresponds to server index 2, and so
             until the most signicant bit of the first octet, which
             corresponds to server index 256. A 1 in a bit position
             means that the server did not respond to the last
             authentication request. A 0 means that the server
             responded to the last request, or the server is not used."
      DEFVAL { "0" }
      ::= { radiusClientMIB 21 }

  radAuthServerUnreachAction  OBJECT-TYPE
    SYNTAX    INTEGER
              {
                 rejectall (1),
                 acceptall (2)
              }
    ACCESS    read-write
    STATUS    mandatory
    DESCRIPTION
        "Specifies the behaviour of the radius client towards 802.1x users
         if no authentication server responds for them.
         rejectall(1) specifies that the radius client will send failure
         to the 802.1x users if no authentication server responds.
         acceptall(2) specifies that the radius client will accept the user
         for 30 minutes and send success to the 802.1x users if no
         authentication server responds."
    DEFVAL { rejectall }
    ::= { radiusClientMIB 22 }



END
