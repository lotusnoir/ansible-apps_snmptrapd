--
-- This SMIv1 module has been generated by smidump 0.4.8. Do not edit.
--

HC-RMON-MIB DEFINITIONS ::= BEGIN

IMPORTS
    CounterBasedGauge64, ZeroBasedCounter64
        FROM HCNUM-TC
    OBJECT-TYPE
        FROM RFC-1212
    Counter, Gauge
        FROM RFC1155-SMI
    OwnerString, capture, captureBufferControlIndex, captureBufferIndex, 
    etherHistoryIndex, etherHistorySampleIndex, etherStatsIndex, history, 
    hostAddress, hostIndex, hostTimeCreationOrder, hostTimeIndex, 
    hostTopN, hostTopNIndex, hostTopNReport, hosts, matrix, 
    matrixDSDestAddress, matrixDSIndex, matrixDSSourceAddress, 
    matrixSDDestAddress, matrixSDIndex, matrixSDSourceAddress, rmon, 
    statistics
        FROM RMON-MIB
    ZeroBasedCounter32, addressMapGroup, alHost, alHostGroup, 
    alHostTimeMark, alMatrix, alMatrixDSTimeMark, alMatrixGroup, 
    alMatrixSDTimeMark, alMatrixTopNControlIndex, alMatrixTopNIndex, 
    hlHostControlIndex, hlMatrixControlIndex, nlHost, nlHostAddress, 
    nlHostGroup, nlHostTimeMark, nlMatrix, nlMatrixDSDestAddress, 
    nlMatrixDSSourceAddress, nlMatrixDSTimeMark, nlMatrixGroup, 
    nlMatrixSDDestAddress, nlMatrixSDSourceAddress, nlMatrixSDTimeMark, 
    nlMatrixTopNControlIndex, nlMatrixTopNIndex, probeConfig, 
    probeInformationGroup, protocolDirLocalIndex, protocolDirectoryGroup, 
    protocolDist, protocolDistControlIndex, protocolDistributionGroup, 
    rmon1EnhancementGroup, rmonConformance, usrHistory, 
    usrHistoryControlIndex, usrHistoryGroup, usrHistoryObjectIndex, 
    usrHistorySampleIndex
        FROM RMON2-MIB
    RowStatus, TimeStamp
        FROM SNMPv2-TC;

hcRMON OBJECT IDENTIFIER
    ::= { rmonConformance 5 }

-- hcRMON MODULE-IDENTITY
--     LAST-UPDATED "201304260000Z"
--     ORGANIZATION 
--         "IETF RMON MIB Working Group"
--     CONTACT-INFO 
--         "Steve Waldbusser
--          
--          Phone: +1-650-948-6500
--          Fax:   +1-650-745-0671
--          Email: waldbusser@nextbeacon.com
--          
--          Andy Bierman
--          WG Chair
--          abierman@cisco.com
--          
--          RMONMIB WG Mailing List
--          rmonmib@ietf.org
--          http://www.ietf.org/mailman/listinfo/rmonmib"
--     DESCRIPTION 
--         "The MIB module for managing remote monitoring
--          device implementations. This MIB module
--          augments the original RMON MIB as specified in
--          RFC 2819 and RFC 1513 and RMON-2 MIB as specified in
--          RFC 2021."
--     REVISION    "200205080000Z"
--     DESCRIPTION 
--         "The original version of this MIB, published as RFC3273."
--     ::= { rmonConformance 5 }


Counter64bit ::=
    OCTET STRING (SIZE(8))

etherStatsHighCapacityTable OBJECT-TYPE
    SYNTAX      SEQUENCE OF EtherStatsHighCapacityEntry
    ACCESS      not-accessible
    STATUS      mandatory
    DESCRIPTION 
        "Contains the High Capacity RMON extensions to the RMON-1
         etherStatsTable."
    ::= { statistics 7 }

etherStatsHighCapacityEntry OBJECT-TYPE
    SYNTAX      EtherStatsHighCapacityEntry
    ACCESS      not-accessible
    STATUS      mandatory
    DESCRIPTION 
        "Contains the High Capacity RMON extensions to the RMON-1
         etherStatsEntry. These objects will be created by the agent
         for all etherStatsEntries it deems appropriate."
    INDEX       { etherStatsIndex }
    ::= { etherStatsHighCapacityTable 1 }

EtherStatsHighCapacityEntry ::= SEQUENCE {
    etherStatsHighCapacityOverflowPkts                  Counter,
    etherStatsHighCapacityPkts                          Counter64bit,
    etherStatsHighCapacityOverflowOctets                Counter,
    etherStatsHighCapacityOctets                        Counter64bit,
    etherStatsHighCapacityOverflowPkts64Octets          Counter,
    etherStatsHighCapacityPkts64Octets                  Counter64bit,
    etherStatsHighCapacityOverflowPkts65to127Octets     Counter,
    etherStatsHighCapacityPkts65to127Octets             Counter64bit,
    etherStatsHighCapacityOverflowPkts128to255Octets    Counter,
    etherStatsHighCapacityPkts128to255Octets            Counter64bit,
    etherStatsHighCapacityOverflowPkts256to511Octets    Counter,
    etherStatsHighCapacityPkts256to511Octets            Counter64bit,
    etherStatsHighCapacityOverflowPkts512to1023Octets   Counter,
    etherStatsHighCapacityPkts512to1023Octets           Counter64bit,
    etherStatsHighCapacityOverflowPkts1024to1518Octets  Counter,
    etherStatsHighCapacityPkts1024to1518Octets          Counter64bit
}

etherStatsHighCapacityOverflowPkts OBJECT-TYPE
    SYNTAX      Counter
--     UNITS       "Packets"
    ACCESS      read-only
    STATUS      mandatory
    DESCRIPTION 
        "The number of times the associated etherStatsPkts
         counter has overflowed.
         ALCATEL NOTE: the ALCATEL ISAM does not support this object."
    ::= { etherStatsHighCapacityEntry 1 }

etherStatsHighCapacityPkts OBJECT-TYPE
    SYNTAX      Counter64bit
--     UNITS       "Packets"
    ACCESS      read-only
    STATUS      mandatory
    DESCRIPTION 
        "The total number of packets (including bad packets,
         broadcast packets, and multicast packets) received."
    ::= { etherStatsHighCapacityEntry 2 }

etherStatsHighCapacityOverflowOctets OBJECT-TYPE
    SYNTAX      Counter
--     UNITS       "Octets"
    ACCESS      read-only
    STATUS      mandatory
    DESCRIPTION 
        "The number of times the associated etherStatsOctets
         counter has overflowed.
         ALCATEL NOTE: the ALCATEL ISAM does not support this object."
    ::= { etherStatsHighCapacityEntry 3 }

etherStatsHighCapacityOctets OBJECT-TYPE
    SYNTAX      Counter64bit
--     UNITS       "Octets"
    ACCESS      read-only
    STATUS      mandatory
    DESCRIPTION 
        "The total number of octets of data (including
         those in bad packets) received on the
         network (excluding framing bits but including
         FCS octets).
         
         If the network is half-duplex Fast Ethernet, this
         object can be used as a reasonable estimate of
         utilization. If greater precision is desired, the
         etherStatsHighCapacityPkts and
         etherStatsHighCapacityOctets objects should be sampled
         before and after a common interval.  The differences
         in the sampled values are Pkts and Octets,
         respectively, and the number of seconds in the
         interval is Interval.  These values
         are used to calculate the Utilization as follows:
         
                         Pkts * (.96 + .64) + (Octets * .08)
         Utilization = =====================================
                                 Interval * 10,000
         
         The result of this equation is the value Utilization
         which is the percent utilization of the ethernet
         segment on a scale of 0 to 100 percent.
         
         This table is not appropriate for monitoring full-duplex
         ethernets. If the network is a full-duplex ethernet and the
         mediaIndependentTable is monitoring that network, the
         utilization can be calculated as follows:
         
         1) Determine the utilization of the inbound path by using
            the appropriate equation (for ethernet or fast ethernet)
            to determine the utilization, substituting
            mediaIndependentInPkts for etherStatsHighCapacityPkts, and
            mediaIndependentInOctets for etherStatsHighCapacityOctets.
            Call the resulting utilization inUtilization.
         
         2) Determine the utilization of the outbound path by using
            the same equation to determine the utilization, substituting
            mediaIndependentOutPkts for etherStatsHighCapacityPkts, and
            mediaIndependentOutOctets for etherStatsHighCapacityOctets.
            Call the resulting utilization outUtilization.
         
         3) The utilization is the maximum of inUtilization and
            outUtilization. This metric shows the amount of percentage
            of bandwidth that is left before congestion will be
            experienced on the link."
    ::= { etherStatsHighCapacityEntry 4 }

etherStatsHighCapacityOverflowPkts64Octets OBJECT-TYPE
    SYNTAX      Counter
--     UNITS       "Packets"
    ACCESS      read-only
    STATUS      mandatory
    DESCRIPTION 
        "The number of times the associated etherStatsPkts64Octets
         counter has overflowed.
         ALCATEL NOTE: the ALCATEL ISAM does not support this object."
    ::= { etherStatsHighCapacityEntry 5 }

etherStatsHighCapacityPkts64Octets OBJECT-TYPE
    SYNTAX      Counter64bit
--     UNITS       "Packets"
    ACCESS      read-only
    STATUS      mandatory
    DESCRIPTION 
        "The total number of packets (including bad
         packets) received that were 64 octets in length
         (excluding framing bits but including FCS octets)."
    ::= { etherStatsHighCapacityEntry 6 }

etherStatsHighCapacityOverflowPkts65to127Octets OBJECT-TYPE
    SYNTAX      Counter
--     UNITS       "Packets"
    ACCESS      read-only
    STATUS      mandatory
    DESCRIPTION 
        "The number of times the associated etherStatsPkts65to127Octets
         counter has overflowed.
         ALCATEL NOTE: the ALCATEL ISAM does not support this object."
    ::= { etherStatsHighCapacityEntry 7 }

etherStatsHighCapacityPkts65to127Octets OBJECT-TYPE
    SYNTAX      Counter64bit
--     UNITS       "Packets"
    ACCESS      read-only
    STATUS      mandatory
    DESCRIPTION 
        "The total number of packets (including bad
         packets) received that were between
         65 and 127 octets in length inclusive
         (excluding framing bits but including FCS octets)."
    ::= { etherStatsHighCapacityEntry 8 }

etherStatsHighCapacityOverflowPkts128to255Octets OBJECT-TYPE
    SYNTAX      Counter
--     UNITS       "Packets"
    ACCESS      read-only
    STATUS      mandatory
    DESCRIPTION 
        "The number of times the associated etherStatsPkts128to255Octets
         counter has overflowed.
         ALCATEL NOTE: the ALCATEL ISAM does not support this object."
    ::= { etherStatsHighCapacityEntry 9 }

etherStatsHighCapacityPkts128to255Octets OBJECT-TYPE
    SYNTAX      Counter64bit
--     UNITS       "Packets"
    ACCESS      read-only
    STATUS      mandatory
    DESCRIPTION 
        "The total number of packets (including bad
         packets) received that were between
         128 and 255 octets in length inclusive
         (excluding framing bits but including FCS octets)."
    ::= { etherStatsHighCapacityEntry 10 }

etherStatsHighCapacityOverflowPkts256to511Octets OBJECT-TYPE
    SYNTAX      Counter
--     UNITS       "Packets"
    ACCESS      read-only
    STATUS      mandatory
    DESCRIPTION 
        "The number of times the associated etherStatsPkts256to511Octets
         counter has overflowed.
         ALCATEL NOTE: the ALCATEL ISAM does not support this object."
    ::= { etherStatsHighCapacityEntry 11 }

etherStatsHighCapacityPkts256to511Octets OBJECT-TYPE
    SYNTAX      Counter64bit
--     UNITS       "Packets"
    ACCESS      read-only
    STATUS      mandatory
    DESCRIPTION 
        "The total number of packets (including bad
         packets) received that were between
         256 and 511 octets in length inclusive
         (excluding framing bits but including FCS octets)."
    ::= { etherStatsHighCapacityEntry 12 }

etherStatsHighCapacityOverflowPkts512to1023Octets OBJECT-TYPE
    SYNTAX      Counter
--     UNITS       "Packets"
    ACCESS      read-only
    STATUS      mandatory
    DESCRIPTION 
        "The number of times the associated
         etherStatsPkts512to1023Octets counter has overflowed.
         ALCATEL NOTE: the ALCATEL ISAM does not support this object."
    ::= { etherStatsHighCapacityEntry 13 }

etherStatsHighCapacityPkts512to1023Octets OBJECT-TYPE
    SYNTAX      Counter64bit
--     UNITS       "Packets"
    ACCESS      read-only
    STATUS      mandatory
    DESCRIPTION 
        "The total number of packets (including bad
         packets) received that were between
         512 and 1023 octets in length inclusive
         (excluding framing bits but including FCS octets)."
    ::= { etherStatsHighCapacityEntry 14 }

etherStatsHighCapacityOverflowPkts1024to1518Octets OBJECT-TYPE
    SYNTAX      Counter
--     UNITS       "Packets"
    ACCESS      read-only
    STATUS      mandatory
    DESCRIPTION 
        "The number of times the associated
         etherStatsPkts1024to1518Octets counter has overflowed.
         ALCATEL NOTE: the ALCATEL ISAM does not support this object."
    ::= { etherStatsHighCapacityEntry 15 }

etherStatsHighCapacityPkts1024to1518Octets OBJECT-TYPE
    SYNTAX      Counter64bit
--     UNITS       "Packets"
    ACCESS      read-only
    STATUS      mandatory
    DESCRIPTION 
        "The total number of packets (including bad
         packets) received that were between
         1024 and 1518 octets in length inclusive
         (excluding framing bits but including FCS octets)."
    ::= { etherStatsHighCapacityEntry 16 }

etherHistoryHighCapacityTable OBJECT-TYPE
    SYNTAX      SEQUENCE OF EtherHistoryHighCapacityEntry
    ACCESS      not-accessible
    STATUS      mandatory
    DESCRIPTION 
        "Contains the High Capacity RMON extensions to the RMON-1
         etherHistoryTable.
         ALCATEL NOTE: the ALCATEL ISAM does not support this object."
    ::= { history 6 }

etherHistoryHighCapacityEntry OBJECT-TYPE
    SYNTAX      EtherHistoryHighCapacityEntry
    ACCESS      not-accessible
    STATUS      mandatory
    DESCRIPTION 
        "Contains the High Capacity RMON extensions to the RMON-1
         etherHistoryEntry. These objects will be created by the agent
         for all etherHistoryEntries associated with whichever
         historyControlEntries it deems appropriate. (i.e., either all
         etherHistoryHighCapacityEntries associated with a particular
         historyControlEntry will be created, or none of them will
         be.)
         ALCATEL NOTE: the ALCATEL ISAM does not support this object."
    INDEX       { etherHistoryIndex, etherHistorySampleIndex }
    ::= { etherHistoryHighCapacityTable 1 }

EtherHistoryHighCapacityEntry ::= SEQUENCE {
    etherHistoryHighCapacityOverflowPkts    Gauge,
    etherHistoryHighCapacityPkts            CounterBasedGauge64,
    etherHistoryHighCapacityOverflowOctets  Gauge,
    etherHistoryHighCapacityOctets          CounterBasedGauge64
}

etherHistoryHighCapacityOverflowPkts OBJECT-TYPE
    SYNTAX      Gauge
--     UNITS       "Packets"
    ACCESS      read-only
    STATUS      mandatory
    DESCRIPTION 
        "The number of times the associated etherHistoryPkts
         Gauge overflowed during this sampling interval.
         ALCATEL NOTE: the ALCATEL ISAM does not support this object."
    ::= { etherHistoryHighCapacityEntry 1 }

etherHistoryHighCapacityPkts OBJECT-TYPE
    SYNTAX      CounterBasedGauge64
--     UNITS       "Packets"
    ACCESS      read-only
    STATUS      mandatory
    DESCRIPTION 
        "The total number of packets (including bad packets,
         broadcast packets, and multicast packets) received during
         this sampling interval.
         ALCATEL NOTE: the ALCATEL ISAM does not support this object."
    ::= { etherHistoryHighCapacityEntry 2 }

etherHistoryHighCapacityOverflowOctets OBJECT-TYPE
    SYNTAX      Gauge
--     UNITS       "Octets"
    ACCESS      read-only
    STATUS      mandatory
    DESCRIPTION 
        "The number of times the associated etherHistoryOctets
         counter has overflowed during this sampling interval.
         ALCATEL NOTE: the ALCATEL ISAM does not support this object."
    ::= { etherHistoryHighCapacityEntry 3 }

etherHistoryHighCapacityOctets OBJECT-TYPE
    SYNTAX      CounterBasedGauge64
--     UNITS       "Octets"
    ACCESS      read-only
    STATUS      mandatory
    DESCRIPTION 
        "The total number of octets of data (including
         those in bad packets) received on the
         network (excluding framing bits but including
         FCS octets) during this sampling interval.
         ALCATEL NOTE: the ALCATEL ISAM does not support this object."
    ::= { etherHistoryHighCapacityEntry 4 }

hostHighCapacityTable OBJECT-TYPE
    SYNTAX      SEQUENCE OF HostHighCapacityEntry
    ACCESS      not-accessible
    STATUS      mandatory
    DESCRIPTION 
        "Contains the High Capacity RMON extensions to the RMON-1
         hostTable.
         ALCATEL NOTE: the ALCATEL ISAM does not support this object."
    ::= { hosts 5 }

hostHighCapacityEntry OBJECT-TYPE
    SYNTAX      HostHighCapacityEntry
    ACCESS      not-accessible
    STATUS      mandatory
    DESCRIPTION 
        "Contains the High Capacity RMON extensions to the RMON-1
         hostEntry. These objects will be created by the agent
         for all hostEntries associated with whichever
         hostControlEntries it deems appropriate. (i.e., either all
         hostHighCapacityEntries associated with a particular
         hostControlEntry will be created, or none of them will
         be.)
         ALCATEL NOTE: the ALCATEL ISAM does not support this object."
    INDEX       { hostIndex, hostAddress }
    ::= { hostHighCapacityTable 1 }

HostHighCapacityEntry ::= SEQUENCE {
    hostHighCapacityInOverflowPkts      Counter,
    hostHighCapacityInPkts              Counter,
    hostHighCapacityOutOverflowPkts     Counter,
    hostHighCapacityOutPkts             Counter,
    hostHighCapacityInOverflowOctets    Counter,
    hostHighCapacityInOctets            Counter,
    hostHighCapacityOutOverflowOctets   Counter,
    hostHighCapacityOutOctets           Counter
}

hostHighCapacityInOverflowPkts OBJECT-TYPE
    SYNTAX      Counter
--     UNITS       "Packets"
    ACCESS      read-only
    STATUS      mandatory
    DESCRIPTION 
        "The number of times the associated hostInPkts
         counter has overflowed.
         ALCATEL NOTE: the ALCATEL ISAM does not support this object."
    ::= { hostHighCapacityEntry 1 }

hostHighCapacityInPkts OBJECT-TYPE
    SYNTAX      Counter
--     UNITS       "Packets"
    ACCESS      read-only
    STATUS      mandatory
    DESCRIPTION 
        "The number of good packets transmitted to
         this address since it was added to the
         hostHighCapacityTable.
         ALCATEL NOTE: the ALCATEL ISAM does not support this object."
    ::= { hostHighCapacityEntry 2 }

hostHighCapacityOutOverflowPkts OBJECT-TYPE
    SYNTAX      Counter
--     UNITS       "Packets"
    ACCESS      read-only
    STATUS      mandatory
    DESCRIPTION 
        "The number of times the associated hostOutPkts
         counter has overflowed.
         ALCATEL NOTE: the ALCATEL ISAM does not support this object."
    ::= { hostHighCapacityEntry 3 }

hostHighCapacityOutPkts OBJECT-TYPE
    SYNTAX      Counter
--     UNITS       "Packets"
    ACCESS      read-only
    STATUS      mandatory
    DESCRIPTION 
        "The number of packets, including bad packets, transmitted
         by this address since it was added to the
         hostHighCapacityTable.
         ALCATEL NOTE: the ALCATEL ISAM does not support this object."
    ::= { hostHighCapacityEntry 4 }

hostHighCapacityInOverflowOctets OBJECT-TYPE
    SYNTAX      Counter
--     UNITS       "Octets"
    ACCESS      read-only
    STATUS      mandatory
    DESCRIPTION 
        "The number of times the associated hostInOctets
         counter has overflowed.
         ALCATEL NOTE: the ALCATEL ISAM does not support this object."
    ::= { hostHighCapacityEntry 5 }

hostHighCapacityInOctets OBJECT-TYPE
    SYNTAX      Counter
--     UNITS       "Octets"
    ACCESS      read-only
    STATUS      mandatory
    DESCRIPTION 
        "The number of octets transmitted to this address
         since it was added to the hostHighCapacityTable (excluding
         framing bits but including FCS octets), except for
         those octets in bad packets.
         ALCATEL NOTE: the ALCATEL ISAM does not support this object."
    ::= { hostHighCapacityEntry 6 }

hostHighCapacityOutOverflowOctets OBJECT-TYPE
    SYNTAX      Counter
--     UNITS       "Octets"
    ACCESS      read-only
    STATUS      mandatory
    DESCRIPTION 
        "The number of times the associated hostOutOctets
         counter has overflowed.
         ALCATEL NOTE: the ALCATEL ISAM does not support this object."
    ::= { hostHighCapacityEntry 7 }

hostHighCapacityOutOctets OBJECT-TYPE
    SYNTAX      Counter
--     UNITS       "Octets"
    ACCESS      read-only
    STATUS      mandatory
    DESCRIPTION 
        "The number of octets transmitted by this address
         since it was added to the hostHighCapacityTable (excluding
         framing bits but including FCS octets), including
         those octets in bad packets.
         ALCATEL NOTE: the ALCATEL ISAM does not support this object."
    ::= { hostHighCapacityEntry 8 }

hostTimeHighCapacityTable OBJECT-TYPE
    SYNTAX      SEQUENCE OF HostTimeHighCapacityEntry
    ACCESS      not-accessible
    STATUS      mandatory
    DESCRIPTION 
        "Contains the High Capacity RMON extensions to the RMON-1
         hostTimeTable.
         ALCATEL NOTE: the ALCATEL ISAM does not support this object."
    ::= { hosts 6 }

hostTimeHighCapacityEntry OBJECT-TYPE
    SYNTAX      HostTimeHighCapacityEntry
    ACCESS      not-accessible
    STATUS      mandatory
    DESCRIPTION 
        "Contains the High Capacity RMON extensions to the RMON-1
         hostTimeEntry. These objects will be created by the agent
         for all hostTimeEntries associated with whichever
         hostControlEntries it deems appropriate. (i.e., either all
         hostTimeHighCapacityEntries associated with a particular
         hostControlEntry will be created, or none of them will
         be.)
         ALCATEL NOTE: the ALCATEL ISAM does not support this object."
    INDEX       { hostTimeIndex, hostTimeCreationOrder }
    ::= { hostTimeHighCapacityTable 1 }

HostTimeHighCapacityEntry ::= SEQUENCE {
    hostTimeHighCapacityInOverflowPkts      Counter,
    hostTimeHighCapacityInPkts              Counter,
    hostTimeHighCapacityOutOverflowPkts     Counter,
    hostTimeHighCapacityOutPkts             Counter,
    hostTimeHighCapacityInOverflowOctets    Counter,
    hostTimeHighCapacityInOctets            Counter,
    hostTimeHighCapacityOutOverflowOctets   Counter,
    hostTimeHighCapacityOutOctets           Counter
}

hostTimeHighCapacityInOverflowPkts OBJECT-TYPE
    SYNTAX      Counter
--     UNITS       "Packets"
    ACCESS      read-only
    STATUS      mandatory
    DESCRIPTION 
        "The number of times the associated hostTimeInPkts
         counter has overflowed.
         ALCATEL NOTE: the ALCATEL ISAM does not support this object."
    ::= { hostTimeHighCapacityEntry 1 }

hostTimeHighCapacityInPkts OBJECT-TYPE
    SYNTAX      Counter
--     UNITS       "Packets"
    ACCESS      read-only
    STATUS      mandatory
    DESCRIPTION 
        "The number of good packets transmitted to this address
         since it was added to the hostTimeHighCapacityTable.
         ALCATEL NOTE: the ALCATEL ISAM does not support this object."
    ::= { hostTimeHighCapacityEntry 2 }

hostTimeHighCapacityOutOverflowPkts OBJECT-TYPE
    SYNTAX      Counter
--     UNITS       "Packets"
    ACCESS      read-only
    STATUS      mandatory
    DESCRIPTION 
        "The number of times the associated hostTimeOutPkts
         counter has overflowed.
         ALCATEL NOTE: the ALCATEL ISAM does not support this object."
    ::= { hostTimeHighCapacityEntry 3 }

hostTimeHighCapacityOutPkts OBJECT-TYPE
    SYNTAX      Counter
--     UNITS       "Packets"
    ACCESS      read-only
    STATUS      mandatory
    DESCRIPTION 
        "The number of packets, including bad packets, transmitted
         by this address since it was added to the
         hostTimeHighCapacityTable.
         ALCATEL NOTE: the ALCATEL ISAM does not support this object."
    ::= { hostTimeHighCapacityEntry 4 }

hostTimeHighCapacityInOverflowOctets OBJECT-TYPE
    SYNTAX      Counter
--     UNITS       "Octets"
    ACCESS      read-only
    STATUS      mandatory
    DESCRIPTION 
        "The number of times the associated hostTimeInOctets
         counter has overflowed.
         ALCATEL NOTE: the ALCATEL ISAM does not support this object."
    ::= { hostTimeHighCapacityEntry 5 }

hostTimeHighCapacityInOctets OBJECT-TYPE
    SYNTAX      Counter
--     UNITS       "Octets"
    ACCESS      read-only
    STATUS      mandatory
    DESCRIPTION 
        "The number of octets transmitted to this address
         since it was added to the hostTimeHighCapacityTable
         (excluding framing bits but including FCS octets),
         except for those octets in bad packets.
         ALCATEL NOTE: the ALCATEL ISAM does not support this object."
    ::= { hostTimeHighCapacityEntry 6 }

hostTimeHighCapacityOutOverflowOctets OBJECT-TYPE
    SYNTAX      Counter
--     UNITS       "Octets"
    ACCESS      read-only
    STATUS      mandatory
    DESCRIPTION 
        "The number of times the associated hostTimeOutOctets
         counter has overflowed.
         ALCATEL NOTE: the ALCATEL ISAM does not support this object."
    ::= { hostTimeHighCapacityEntry 7 }

hostTimeHighCapacityOutOctets OBJECT-TYPE
    SYNTAX      Counter
--     UNITS       "Octets"
    ACCESS      read-only
    STATUS      mandatory
    DESCRIPTION 
        "The number of octets transmitted by this address since
         it was added to the hostTimeTable (excluding framing
         bits but including FCS octets), including those
         octets in bad packets.
         ALCATEL NOTE: the ALCATEL ISAM does not support this object."
    ::= { hostTimeHighCapacityEntry 8 }

hostTopNHighCapacityTable OBJECT-TYPE
    SYNTAX      SEQUENCE OF HostTopNHighCapacityEntry
    ACCESS      not-accessible
    STATUS      mandatory
    DESCRIPTION 
        "Contains the High Capacity RMON extensions to the RMON-1
         hostTopNTable when hostTopNRateBase specifies a High Capacity
         TopN Report.
         ALCATEL NOTE: the ALCATEL ISAM does not support this object."
    ::= { hostTopN 3 }

hostTopNHighCapacityEntry OBJECT-TYPE
    SYNTAX      HostTopNHighCapacityEntry
    ACCESS      not-accessible
    STATUS      mandatory
    DESCRIPTION 
        "Contains the High Capacity RMON extensions to the RMON-1
         hostTopNEntry when hostTopNRateBase specifies a High Capacity
         TopN Report. These objects will be created by the agent
         for all hostTopNEntries associated with whichever
         hostTopNControlEntries have a hostTopNRateBase that specify
         a high capacity report.
         ALCATEL NOTE: the ALCATEL ISAM does not support this object."
    INDEX       { hostTopNReport, hostTopNIndex }
    ::= { hostTopNHighCapacityTable 1 }

HostTopNHighCapacityEntry ::= SEQUENCE {
    hostTopNHighCapacityAddress         OCTET STRING,
    hostTopNHighCapacityBaseRate        Gauge,
    hostTopNHighCapacityOverflowRate    Gauge,
    hostTopNHighCapacityRate            CounterBasedGauge64
}

hostTopNHighCapacityAddress OBJECT-TYPE
    SYNTAX      OCTET STRING
    ACCESS      read-only
    STATUS      mandatory
    DESCRIPTION 
        "The physical address of this host.
         ALCATEL NOTE: the ALCATEL ISAM does not support this object."
    ::= { hostTopNHighCapacityEntry 1 }

hostTopNHighCapacityBaseRate OBJECT-TYPE
    SYNTAX      Gauge
    ACCESS      read-only
    STATUS      mandatory
    DESCRIPTION 
        "The amount of change in the selected variable
         during this sampling interval, modulo 2^32.  The
         selected variable is this host's instance of the
         object selected by hostTopNRateBase.
         ALCATEL NOTE: the ALCATEL ISAM does not support this object."
    ::= { hostTopNHighCapacityEntry 2 }

hostTopNHighCapacityOverflowRate OBJECT-TYPE
    SYNTAX      Gauge
    ACCESS      read-only
    STATUS      mandatory
    DESCRIPTION 
        "The amount of change in the selected variable
         during this sampling interval, divided by 2^32, truncating
         fractions (i.e., X DIV 2^32).  The selected variable is
         this host's instance of the object selected by
         hostTopNRateBase.
         ALCATEL NOTE: the ALCATEL ISAM does not support this object."
    ::= { hostTopNHighCapacityEntry 3 }

hostTopNHighCapacityRate OBJECT-TYPE
    SYNTAX      CounterBasedGauge64
    ACCESS      read-only
    STATUS      mandatory
    DESCRIPTION 
        "The amount of change in the selected variable
         during this sampling interval.  The selected
         variable is this host's instance of the object
         selected by hostTopNRateBase.
         ALCATEL NOTE: the ALCATEL ISAM does not support this object."
    ::= { hostTopNHighCapacityEntry 4 }

matrixSDHighCapacityTable OBJECT-TYPE
    SYNTAX      SEQUENCE OF MatrixSDHighCapacityEntry
    ACCESS      not-accessible
    STATUS      mandatory
    DESCRIPTION 
        "Contains the High Capacity RMON extensions to the RMON-1
         matrixSDTable.
         ALCATEL NOTE: the ALCATEL ISAM does not support this object."
    ::= { matrix 5 }

matrixSDHighCapacityEntry OBJECT-TYPE
    SYNTAX      MatrixSDHighCapacityEntry
    ACCESS      not-accessible
    STATUS      mandatory
    DESCRIPTION 
        "Contains the High Capacity RMON extensions to the RMON-1
         matrixSDEntry. These objects will be created by the agent
         for all matrixSDEntries associated with whichever
         matrixControlEntries it deems appropriate. (i.e., either all
         matrixSDHighCapacityEntries associated with a particular
         matrixControlEntry will be created, or none of them will
         be.)
         ALCATEL NOTE: the ALCATEL ISAM does not support this object."
    INDEX       { matrixSDIndex, matrixSDSourceAddress, 
                  matrixSDDestAddress }
    ::= { matrixSDHighCapacityTable 1 }

MatrixSDHighCapacityEntry ::= SEQUENCE {
    matrixSDHighCapacityOverflowPkts    Counter,
    matrixSDHighCapacityPkts            Counter,
    matrixSDHighCapacityOverflowOctets  Counter,
    matrixSDHighCapacityOctets          Counter
}

matrixSDHighCapacityOverflowPkts OBJECT-TYPE
    SYNTAX      Counter
--     UNITS       "Packets"
    ACCESS      read-only
    STATUS      mandatory
    DESCRIPTION 
        "The number of times the associated matrixSDPkts
         counter has overflowed.
         ALCATEL NOTE: the ALCATEL ISAM does not support this object."
    ::= { matrixSDHighCapacityEntry 1 }

matrixSDHighCapacityPkts OBJECT-TYPE
    SYNTAX      Counter
--     UNITS       "Packets"
    ACCESS      read-only
    STATUS      mandatory
    DESCRIPTION 
        "The number of packets transmitted from the source
         address to the destination address (this number
         includes bad packets).
         ALCATEL NOTE: the ALCATEL ISAM does not support this object."
    ::= { matrixSDHighCapacityEntry 2 }

matrixSDHighCapacityOverflowOctets OBJECT-TYPE
    SYNTAX      Counter
--     UNITS       "Octets"
    ACCESS      read-only
    STATUS      mandatory
    DESCRIPTION 
        "The number of times the associated matrixSDOctets
         counter has overflowed.
         ALCATEL NOTE: the ALCATEL ISAM does not support this object."
    ::= { matrixSDHighCapacityEntry 3 }

matrixSDHighCapacityOctets OBJECT-TYPE
    SYNTAX      Counter
--     UNITS       "Octets"
    ACCESS      read-only
    STATUS      mandatory
    DESCRIPTION 
        "The number of octets (excluding framing bits but
         including FCS octets) contained in all packets
         transmitted from the source address to the
         destination address.
         ALCATEL NOTE: the ALCATEL ISAM does not support this object."
    ::= { matrixSDHighCapacityEntry 4 }

matrixDSHighCapacityTable OBJECT-TYPE
    SYNTAX      SEQUENCE OF MatrixDSHighCapacityEntry
    ACCESS      not-accessible
    STATUS      mandatory
    DESCRIPTION 
        "Contains the High Capacity RMON extensions to the RMON-1
         matrixDSTable.
         ALCATEL NOTE: the ALCATEL ISAM does not support this object."
    ::= { matrix 6 }

matrixDSHighCapacityEntry OBJECT-TYPE
    SYNTAX      MatrixDSHighCapacityEntry
    ACCESS      not-accessible
    STATUS      mandatory
    DESCRIPTION 
        "Contains the High Capacity RMON extensions to the RMON-1
         matrixDSEntry. These objects will be created by the agent
         for all matrixDSEntries associated with whichever
         matrixControlEntries it deems appropriate. (i.e., either all
         matrixDSHighCapacityEntries associated with a particular
         matrixControlEntry will be created, or none of them will
         be.)
         ALCATEL NOTE: the ALCATEL ISAM does not support this object."
    INDEX       { matrixDSIndex, matrixDSDestAddress, 
                  matrixDSSourceAddress }
    ::= { matrixDSHighCapacityTable 1 }

MatrixDSHighCapacityEntry ::= SEQUENCE {
    matrixDSHighCapacityOverflowPkts    Counter,
    matrixDSHighCapacityPkts            Counter,
    matrixDSHighCapacityOverflowOctets  Counter,
    matrixDSHighCapacityOctets          Counter
}

matrixDSHighCapacityOverflowPkts OBJECT-TYPE
    SYNTAX      Counter
--     UNITS       "Packets"
    ACCESS      read-only
    STATUS      mandatory
    DESCRIPTION 
        "The number of times the associated matrixDSPkts
         counter has overflowed.
         ALCATEL NOTE: the ALCATEL ISAM does not support this object."
    ::= { matrixDSHighCapacityEntry 1 }

matrixDSHighCapacityPkts OBJECT-TYPE
    SYNTAX      Counter
--     UNITS       "Packets"
    ACCESS      read-only
    STATUS      mandatory
    DESCRIPTION 
        "The number of packets transmitted from the source
         address to the destination address (this number
         includes bad packets).
         ALCATEL NOTE: the ALCATEL ISAM does not support this object."
    ::= { matrixDSHighCapacityEntry 2 }

matrixDSHighCapacityOverflowOctets OBJECT-TYPE
    SYNTAX      Counter
--     UNITS       "Octets"
    ACCESS      read-only
    STATUS      mandatory
    DESCRIPTION 
        "The number of times the associated matrixDSOctets
         counter has overflowed.
         ALCATEL NOTE: the ALCATEL ISAM does not support this object."
    ::= { matrixDSHighCapacityEntry 3 }

matrixDSHighCapacityOctets OBJECT-TYPE
    SYNTAX      Counter
--     UNITS       "Octets"
    ACCESS      read-only
    STATUS      mandatory
    DESCRIPTION 
        "The number of octets (excluding framing bits
         but including FCS octets) contained in all packets
         transmitted from the source address to the
         destination address.
         ALCATEL NOTE: the ALCATEL ISAM does not support this object."
    ::= { matrixDSHighCapacityEntry 4 }

captureBufferHighCapacityTable OBJECT-TYPE
    SYNTAX      SEQUENCE OF CaptureBufferHighCapacityEntry
    ACCESS      not-accessible
    STATUS      mandatory
    DESCRIPTION 
        "Contains the High Capacity RMON extensions to the RMON-1
         captureBufferTable.
         ALCATEL NOTE: the ALCATEL ISAM does not support this object."
    ::= { capture 3 }

captureBufferHighCapacityEntry OBJECT-TYPE
    SYNTAX      CaptureBufferHighCapacityEntry
    ACCESS      not-accessible
    STATUS      mandatory
    DESCRIPTION 
        "Contains the High Capacity RMON extensions to the RMON-1
         captureBufferEntry. These objects will be created by the agent
         for all captureBufferEntries associated with whichever
         bufferControlEntries it deems appropriate. (i.e., either all
         captureBufferHighCapacityEntries associated with a particular
         bufferControlEntry will be created, or none of them will
         be.)
         ALCATEL NOTE: the ALCATEL ISAM does not support this object."
    INDEX       { captureBufferControlIndex, captureBufferIndex }
    ::= { captureBufferHighCapacityTable 1 }

CaptureBufferHighCapacityEntry ::= SEQUENCE {
    captureBufferPacketHighCapacityTime     INTEGER
}

captureBufferPacketHighCapacityTime OBJECT-TYPE
    SYNTAX      INTEGER (0..999999)
--     UNITS       "nanoseconds"
    ACCESS      read-only
    STATUS      mandatory
    DESCRIPTION 
        "The number of nanoseconds that had passed since this capture
         buffer was first turned on when this packet was captured,
         modulo 10^6.
         
         This object is used in conjunction with the
         captureBufferPacketTime object. This object returns the
         number of nano-seconds to be added to to number of
         milli-seconds obtained from the captureBufferPacketTime
         object, to obtain more accurate inter packet arrival time.
         ALCATEL NOTE: the ALCATEL ISAM does not support this object."
    ::= { captureBufferHighCapacityEntry 1 }

protocolDistStatsHighCapacityTable OBJECT-TYPE
    SYNTAX      SEQUENCE OF ProtocolDistStatsHighCapacityEntry
    ACCESS      not-accessible
    STATUS      mandatory
    DESCRIPTION 
        "Contains the High Capacity RMON extensions to the RMON-2
         protocolDistStatsTable.
         ALCATEL NOTE: the ALCATEL ISAM does not support this object."
    ::= { protocolDist 3 }

protocolDistStatsHighCapacityEntry OBJECT-TYPE
    SYNTAX      ProtocolDistStatsHighCapacityEntry
    ACCESS      not-accessible
    STATUS      mandatory
    DESCRIPTION 
        "Contains the High Capacity RMON extensions to the RMON-2
         protocolDistStatsTable. These objects will be created by the
         agent for all protocolDistStatsEntries associated with
         whichever protocolDistControlEntries it deems appropriate.
         (i.e., either all protocolDistStatsHighCapacityEntries
         associated with a particular protocolDistControlEntry will be
         created, or none of them will be.)
         ALCATEL NOTE: the ALCATEL ISAM does not support this object."
    INDEX       { protocolDistControlIndex, protocolDirLocalIndex }
    ::= { protocolDistStatsHighCapacityTable 1 }

ProtocolDistStatsHighCapacityEntry ::= SEQUENCE {
    protocolDistStatsHighCapacityOverflowPkts       ZeroBasedCounter32,
    protocolDistStatsHighCapacityPkts               ZeroBasedCounter64,
    protocolDistStatsHighCapacityOverflowOctets     ZeroBasedCounter32,
    protocolDistStatsHighCapacityOctets             ZeroBasedCounter64
}

protocolDistStatsHighCapacityOverflowPkts OBJECT-TYPE
    SYNTAX      ZeroBasedCounter32
--     UNITS       "Packets"
    ACCESS      read-only
    STATUS      mandatory
    DESCRIPTION 
        "The number of times the associated protocolDistStatsPkts
         counter has overflowed.
         ALCATEL NOTE: the ALCATEL ISAM does not support this object."
    ::= { protocolDistStatsHighCapacityEntry 1 }

protocolDistStatsHighCapacityPkts OBJECT-TYPE
    SYNTAX      ZeroBasedCounter64
--     UNITS       "Packets"
    ACCESS      read-only
    STATUS      mandatory
    DESCRIPTION 
        "The number of packets without errors received of this
         protocol type.  Note that this is the number of link-layer
         packets, so if a single network-layer packet is fragmented
         into several link-layer frames, this counter is incremented
         several times.
         ALCATEL NOTE: the ALCATEL ISAM does not support this object."
    ::= { protocolDistStatsHighCapacityEntry 2 }

protocolDistStatsHighCapacityOverflowOctets OBJECT-TYPE
    SYNTAX      ZeroBasedCounter32
--     UNITS       "Octets"
    ACCESS      read-only
    STATUS      mandatory
    DESCRIPTION 
        "The number of times the associated protocolDistStatsOctets
         counter has overflowed.
         ALCATEL NOTE: the ALCATEL ISAM does not support this object."
    ::= { protocolDistStatsHighCapacityEntry 3 }

protocolDistStatsHighCapacityOctets OBJECT-TYPE
    SYNTAX      ZeroBasedCounter64
--     UNITS       "Octets"
    ACCESS      read-only
    STATUS      mandatory
    DESCRIPTION 
        "The number of octets in packets received of this protocol
         type since it was added to the protocolDistStatsTable
         (excluding framing bits but including FCS octets), except for
         those octets in packets that contained errors.
         
         Note this doesn't count just those octets in the particular
         protocol frames, but includes the entire packet that contained
         the protocol.
         ALCATEL NOTE: the ALCATEL ISAM does not support this object."
    ::= { protocolDistStatsHighCapacityEntry 4 }

nlHostHighCapacityTable OBJECT-TYPE
    SYNTAX      SEQUENCE OF NlHostHighCapacityEntry
    ACCESS      not-accessible
    STATUS      mandatory
    DESCRIPTION 
        "Contains the High Capacity RMON extensions to the RMON-2
         nlHostTable.
         ALCATEL NOTE: the ALCATEL ISAM does not support this object."
    ::= { nlHost 3 }

nlHostHighCapacityEntry OBJECT-TYPE
    SYNTAX      NlHostHighCapacityEntry
    ACCESS      not-accessible
    STATUS      mandatory
    DESCRIPTION 
        "Contains the High Capacity RMON extensions to the RMON-2
         nlHostEntry. These objects will be created by the agent
         for all nlHostEntries associated with whichever
         hlHostControlEntries it deems appropriate. (i.e., either all
         nlHostHighCapacityEntries associated with a particular
         hlHostControlEntry will be created, or none of them will
         be.)
         ALCATEL NOTE: the ALCATEL ISAM does not support this object."
    INDEX       { hlHostControlIndex, nlHostTimeMark, 
                  protocolDirLocalIndex, nlHostAddress }
    ::= { nlHostHighCapacityTable 1 }

NlHostHighCapacityEntry ::= SEQUENCE {
    nlHostHighCapacityInOverflowPkts        ZeroBasedCounter32,
    nlHostHighCapacityInPkts                ZeroBasedCounter64,
    nlHostHighCapacityOutOverflowPkts       ZeroBasedCounter32,
    nlHostHighCapacityOutPkts               ZeroBasedCounter64,
    nlHostHighCapacityInOverflowOctets      ZeroBasedCounter32,
    nlHostHighCapacityInOctets              ZeroBasedCounter64,
    nlHostHighCapacityOutOverflowOctets     ZeroBasedCounter32,
    nlHostHighCapacityOutOctets             ZeroBasedCounter64
}

nlHostHighCapacityInOverflowPkts OBJECT-TYPE
    SYNTAX      ZeroBasedCounter32
--     UNITS       "Packets"
    ACCESS      read-only
    STATUS      mandatory
    DESCRIPTION 
        "The number of times the associated nlHostInPkts
         counter has overflowed.
         ALCATEL NOTE: the ALCATEL ISAM does not support this object."
    ::= { nlHostHighCapacityEntry 1 }

nlHostHighCapacityInPkts OBJECT-TYPE
    SYNTAX      ZeroBasedCounter64
--     UNITS       "Packets"
    ACCESS      read-only
    STATUS      mandatory
    DESCRIPTION 
        "The number of packets without errors transmitted to
         this address since it was added to the nlHostHighCapacityTable.
         Note that this is the number of link-layer packets, so if a
         single network-layer packet is fragmented into several
         link-layer frames, this counter is incremented several times.
         ALCATEL NOTE: the ALCATEL ISAM does not support this object."
    ::= { nlHostHighCapacityEntry 2 }

nlHostHighCapacityOutOverflowPkts OBJECT-TYPE
    SYNTAX      ZeroBasedCounter32
--     UNITS       "Packets"
    ACCESS      read-only
    STATUS      mandatory
    DESCRIPTION 
        "The number of times the associated nlHostOutPkts
         counter has overflowed.
         ALCATEL NOTE: the ALCATEL ISAM does not support this object."
    ::= { nlHostHighCapacityEntry 3 }

nlHostHighCapacityOutPkts OBJECT-TYPE
    SYNTAX      ZeroBasedCounter64
--     UNITS       "Packets"
    ACCESS      read-only
    STATUS      mandatory
    DESCRIPTION 
        "The number of packets without errors transmitted by
         this address since it was added to the nlHostHighCapacityTable.
         Note that this is the number of link-layer packets, so if a
         single network-layer packet is fragmented into several
         link-layer frames, this counter is incremented several times.
         ALCATEL NOTE: the ALCATEL ISAM does not support this object."
    ::= { nlHostHighCapacityEntry 4 }

nlHostHighCapacityInOverflowOctets OBJECT-TYPE
    SYNTAX      ZeroBasedCounter32
--     UNITS       "Octets"
    ACCESS      read-only
    STATUS      mandatory
    DESCRIPTION 
        "The number of times the associated nlHostInOctets
         counter has overflowed.
         ALCATEL NOTE: the ALCATEL ISAM does not support this object."
    ::= { nlHostHighCapacityEntry 5 }

nlHostHighCapacityInOctets OBJECT-TYPE
    SYNTAX      ZeroBasedCounter64
--     UNITS       "Octets"
    ACCESS      read-only
    STATUS      mandatory
    DESCRIPTION 
        "The number of octets transmitted to this address
         since it was added to the nlHostHighCapacityTable
         (excluding framing bits but including FCS octets),
         excluding those octets in packets that contained
         errors.
         
         Note this doesn't count just those octets in the
         particular protocol frames, but includes the entire
         packet that contained the protocol.
         ALCATEL NOTE: the ALCATEL ISAM does not support this object."
    ::= { nlHostHighCapacityEntry 6 }

nlHostHighCapacityOutOverflowOctets OBJECT-TYPE
    SYNTAX      ZeroBasedCounter32
--     UNITS       "Octets"
    ACCESS      read-only
    STATUS      mandatory
    DESCRIPTION 
        "The number of times the associated nlHostOutOctets
         counter has overflowed.
         ALCATEL NOTE: the ALCATEL ISAM does not support this object."
    ::= { nlHostHighCapacityEntry 7 }

nlHostHighCapacityOutOctets OBJECT-TYPE
    SYNTAX      ZeroBasedCounter64
--     UNITS       "Octets"
    ACCESS      read-only
    STATUS      mandatory
    DESCRIPTION 
        "The number of octets transmitted by this address
         since it was added to the nlHostHighCapacityTable
         (excluding framing bits but including FCS octets),
         excluding those octets in packets that contained
         errors.
         
         Note this doesn't count just those octets in the
         particular protocol frames, but includes the entire
         packet that contained the protocol.
         ALCATEL NOTE: the ALCATEL ISAM does not support this object."
    ::= { nlHostHighCapacityEntry 8 }

nlMatrixSDHighCapacityTable OBJECT-TYPE
    SYNTAX      SEQUENCE OF NlMatrixSDHighCapacityEntry
    ACCESS      not-accessible
    STATUS      mandatory
    DESCRIPTION 
        "Contains the High Capacity RMON extensions to the RMON-2
         nlMatrixTable.
         ALCATEL NOTE: the ALCATEL ISAM does not support this object."
    ::= { nlMatrix 6 }

nlMatrixSDHighCapacityEntry OBJECT-TYPE
    SYNTAX      NlMatrixSDHighCapacityEntry
    ACCESS      not-accessible
    STATUS      mandatory
    DESCRIPTION 
        "Contains the High Capacity RMON extensions to the RMON-2
         nlMatrixEntry. These objects will be created by the agent
         for all nlMatrixSDEntries associated with whichever
         hlMatrixControlEntries it deems appropriate. (i.e., either all
         nlMatrixSDHighCapacityEntries associated with a particular
         hlMatrixControlEntry will be created, or none of them will
         be.)
         ALCATEL NOTE: the ALCATEL ISAM does not support this object."
    INDEX       { hlMatrixControlIndex, nlMatrixSDTimeMark, 
                  protocolDirLocalIndex, nlMatrixSDSourceAddress, 
                  nlMatrixSDDestAddress }
    ::= { nlMatrixSDHighCapacityTable 1 }

NlMatrixSDHighCapacityEntry ::= SEQUENCE {
    nlMatrixSDHighCapacityOverflowPkts      ZeroBasedCounter32,
    nlMatrixSDHighCapacityPkts              ZeroBasedCounter64,
    nlMatrixSDHighCapacityOverflowOctets    ZeroBasedCounter32,
    nlMatrixSDHighCapacityOctets            ZeroBasedCounter64
}

nlMatrixSDHighCapacityOverflowPkts OBJECT-TYPE
    SYNTAX      ZeroBasedCounter32
--     UNITS       "Packets"
    ACCESS      read-only
    STATUS      mandatory
    DESCRIPTION 
        "The number of times the associated nlMatrixSDPkts
         counter has overflowed.
         ALCATEL NOTE: the ALCATEL ISAM does not support this object."
    ::= { nlMatrixSDHighCapacityEntry 1 }

nlMatrixSDHighCapacityPkts OBJECT-TYPE
    SYNTAX      ZeroBasedCounter64
--     UNITS       "Packets"
    ACCESS      read-only
    STATUS      mandatory
    DESCRIPTION 
        "The number of packets without errors transmitted from the
         source address to the destination address since this entry was
         added to the nlMatrixSDHighCapacityTable.  Note that this is
         the number of link-layer packets, so if a single network-layer
         packet is fragmented into several link-layer frames, this
         counter is incremented several times.
         ALCATEL NOTE: the ALCATEL ISAM does not support this object."
    ::= { nlMatrixSDHighCapacityEntry 2 }

nlMatrixSDHighCapacityOverflowOctets OBJECT-TYPE
    SYNTAX      ZeroBasedCounter32
--     UNITS       "Octets"
    ACCESS      read-only
    STATUS      mandatory
    DESCRIPTION 
        "The number of times the associated nlMatrixSDOctets
         counter has overflowed.
         ALCATEL NOTE: the ALCATEL ISAM does not support this object."
    ::= { nlMatrixSDHighCapacityEntry 3 }

nlMatrixSDHighCapacityOctets OBJECT-TYPE
    SYNTAX      ZeroBasedCounter64
--     UNITS       "Octets"
    ACCESS      read-only
    STATUS      mandatory
    DESCRIPTION 
        "The number of octets transmitted from the source address to
         the destination address since this entry was added to the
         nlMatrixSDHighCapacityTable (excluding framing bits but
         including FCS octets), excluding those octets in packets that
         contained errors.
         
         Note this doesn't count just those octets in the particular
         protocol frames, but includes the entire packet that contained
         the protocol.
         ALCATEL NOTE: the ALCATEL ISAM does not support this object."
    ::= { nlMatrixSDHighCapacityEntry 4 }

nlMatrixDSHighCapacityTable OBJECT-TYPE
    SYNTAX      SEQUENCE OF NlMatrixDSHighCapacityEntry
    ACCESS      not-accessible
    STATUS      mandatory
    DESCRIPTION 
        "Contains the High Capacity RMON extensions to the RMON-2
         nlMatrixDSTable.
         ALCATEL NOTE: the ALCATEL ISAM does not support this object."
    ::= { nlMatrix 7 }

nlMatrixDSHighCapacityEntry OBJECT-TYPE
    SYNTAX      NlMatrixDSHighCapacityEntry
    ACCESS      not-accessible
    STATUS      mandatory
    DESCRIPTION 
        "Contains the High Capacity RMON extensions to the RMON-2
         nlMatrixDSEntry. These objects will be created by the agent
         for all nlMatrixDSEntries associated with whichever
         hlmatrixControlEntries it deems appropriate. (i.e., either all
         nlMatrixDSHighCapacityEntries associated with a particular
         hlMatrixControlEntry will be created, or none of them will
         be.)
         ALCATEL NOTE: the ALCATEL ISAM does not support this object."
    INDEX       { hlMatrixControlIndex, nlMatrixDSTimeMark, 
                  protocolDirLocalIndex, nlMatrixDSDestAddress, 
                  nlMatrixDSSourceAddress }
    ::= { nlMatrixDSHighCapacityTable 1 }

NlMatrixDSHighCapacityEntry ::= SEQUENCE {
    nlMatrixDSHighCapacityOverflowPkts      ZeroBasedCounter32,
    nlMatrixDSHighCapacityPkts              ZeroBasedCounter64,
    nlMatrixDSHighCapacityOverflowOctets    ZeroBasedCounter32,
    nlMatrixDSHighCapacityOctets            ZeroBasedCounter64
}

nlMatrixDSHighCapacityOverflowPkts OBJECT-TYPE
    SYNTAX      ZeroBasedCounter32
--     UNITS       "Packets"
    ACCESS      read-only
    STATUS      mandatory
    DESCRIPTION 
        "The number of times the associated nlMatrixDSPkts
         counter has overflowed.
         ALCATEL NOTE: the ALCATEL ISAM does not support this object."
    ::= { nlMatrixDSHighCapacityEntry 1 }

nlMatrixDSHighCapacityPkts OBJECT-TYPE
    SYNTAX      ZeroBasedCounter64
--     UNITS       "Packets"
    ACCESS      read-only
    STATUS      mandatory
    DESCRIPTION 
        "The number of packets without errors transmitted from the
         source address to the destination address since this entry was
         added to the nlMatrixDSHighCapacityTable.  Note that this is
         the number of link-layer packets, so if a single network-layer
         packet is fragmented into several link-layer frames, this
         counter is incremented several times.
         ALCATEL NOTE: the ALCATEL ISAM does not support this object."
    ::= { nlMatrixDSHighCapacityEntry 2 }

nlMatrixDSHighCapacityOverflowOctets OBJECT-TYPE
    SYNTAX      ZeroBasedCounter32
--     UNITS       "Octets"
    ACCESS      read-only
    STATUS      mandatory
    DESCRIPTION 
        "The number of times the associated nlMatrixDSOctets
         counter has overflowed.
         ALCATEL NOTE: the ALCATEL ISAM does not support this object."
    ::= { nlMatrixDSHighCapacityEntry 3 }

nlMatrixDSHighCapacityOctets OBJECT-TYPE
    SYNTAX      ZeroBasedCounter64
--     UNITS       "Octets"
    ACCESS      read-only
    STATUS      mandatory
    DESCRIPTION 
        "The number of octets transmitted from the source address
         to the destination address since this entry was added to the
         nlMatrixDSHighCapacityTable (excluding framing bits but
         including FCS octets), excluding those octets in packets that
         contained errors.
         
         Note this doesn't count just those octets in the particular
         protocol frames, but includes the entire packet that contained
         the protocol.
         ALCATEL NOTE: the ALCATEL ISAM does not support this object."
    ::= { nlMatrixDSHighCapacityEntry 4 }

nlMatrixTopNHighCapacityTable OBJECT-TYPE
    SYNTAX      SEQUENCE OF NlMatrixTopNHighCapacityEntry
    ACCESS      not-accessible
    STATUS      mandatory
    DESCRIPTION 
        "Contains the High Capacity RMON extensions to the RMON-2
         nlMatrixTopNTable when nlMatrixTopNControlRateBase specifies
         a High Capacity TopN Report.
         ALCATEL NOTE: the ALCATEL ISAM does not support this object."
    ::= { nlMatrix 8 }

nlMatrixTopNHighCapacityEntry OBJECT-TYPE
    SYNTAX      NlMatrixTopNHighCapacityEntry
    ACCESS      not-accessible
    STATUS      mandatory
    DESCRIPTION 
        "Contains the High Capacity RMON extensions to the RMON-2
         nlMatrixTopNEntry when nlMatrixTopNControlRateBase specifies
         a High Capacity TopN Report. These objects will be created by
         the agent for all nlMatrixTopNEntries associated with whichever
         nlMatrixTopNControlEntries have a nlMatrixTopNControlRateBase
         that specify a high capacity report.
         ALCATEL NOTE: the ALCATEL ISAM does not support this object."
    INDEX       { nlMatrixTopNControlIndex, nlMatrixTopNIndex }
    ::= { nlMatrixTopNHighCapacityTable 1 }

NlMatrixTopNHighCapacityEntry ::= SEQUENCE {
    nlMatrixTopNHighCapacityProtocolDirLocalIndex       INTEGER,
    nlMatrixTopNHighCapacitySourceAddress               OCTET STRING,
    nlMatrixTopNHighCapacityDestAddress                 OCTET STRING,
    nlMatrixTopNHighCapacityBasePktRate                 Gauge,
    nlMatrixTopNHighCapacityOverflowPktRate             Gauge,
    nlMatrixTopNHighCapacityPktRate                     CounterBasedGauge64,
    nlMatrixTopNHighCapacityReverseBasePktRate          Gauge,
    nlMatrixTopNHighCapacityReverseOverflowPktRate      Gauge,
    nlMatrixTopNHighCapacityReversePktRate              CounterBasedGauge64,
    nlMatrixTopNHighCapacityBaseOctetRate               Gauge,
    nlMatrixTopNHighCapacityOverflowOctetRate           Gauge,
    nlMatrixTopNHighCapacityOctetRate                   CounterBasedGauge64,
    nlMatrixTopNHighCapacityReverseBaseOctetRate        Gauge,
    nlMatrixTopNHighCapacityReverseOverflowOctetRate    Gauge,
    nlMatrixTopNHighCapacityReverseOctetRate            CounterBasedGauge64
}

nlMatrixTopNHighCapacityProtocolDirLocalIndex OBJECT-TYPE
    SYNTAX      INTEGER (1..2147483647)
    ACCESS      read-only
    STATUS      mandatory
    DESCRIPTION 
        "The protocolDirLocalIndex of the network layer protocol of
         this entry's network address.
         ALCATEL NOTE: the ALCATEL ISAM does not support this object."
    ::= { nlMatrixTopNHighCapacityEntry 1 }

nlMatrixTopNHighCapacitySourceAddress OBJECT-TYPE
    SYNTAX      OCTET STRING
    ACCESS      read-only
    STATUS      mandatory
    DESCRIPTION 
        "The network layer address of the source host in this
         conversation.
         
         This is represented as an octet string with
         specific semantics and length as identified
         by the associated nlMatrixTopNProtocolDirLocalIndex.
         
         For example, if the protocolDirLocalIndex indicates an
         encapsulation of ip, this object is encoded as a length
         octet of 4, followed by the 4 octets of the ip address,
         in network byte order.
         ALCATEL NOTE: the ALCATEL ISAM does not support this object."
    ::= { nlMatrixTopNHighCapacityEntry 2 }

nlMatrixTopNHighCapacityDestAddress OBJECT-TYPE
    SYNTAX      OCTET STRING
    ACCESS      read-only
    STATUS      mandatory
    DESCRIPTION 
        "The network layer address of the destination host in this
         conversation.
         
         This is represented as an octet string with
         specific semantics and length as identified
         by the associated nlMatrixTopNProtocolDirLocalIndex.
         
         For example, if the nlMatrixTopNProtocolDirLocalIndex
         indicates an encapsulation of ip, this object is encoded as a
         length octet of 4, followed by the 4 octets of the ip address,
         in network byte order.
         ALCATEL NOTE: the ALCATEL ISAM does not support this object."
    ::= { nlMatrixTopNHighCapacityEntry 3 }

nlMatrixTopNHighCapacityBasePktRate OBJECT-TYPE
    SYNTAX      Gauge
--     UNITS       "Packets"
    ACCESS      read-only
    STATUS      mandatory
    DESCRIPTION 
        "The number of packets seen from the source host
         to the destination host during this sampling interval,
         modulo 2^32, counted using the rules for counting the
         nlMatrixSDPkts object.
         ALCATEL NOTE: the ALCATEL ISAM does not support this object."
    ::= { nlMatrixTopNHighCapacityEntry 4 }

nlMatrixTopNHighCapacityOverflowPktRate OBJECT-TYPE
    SYNTAX      Gauge
--     UNITS       "Packets"
    ACCESS      read-only
    STATUS      mandatory
    DESCRIPTION 
        "The number of packets seen from the source host
         to the destination host during this sampling interval,
         divided by 2^32, truncating fractions (i.e., X DIV 2^32),
         and counted using the rules for counting the
         nlMatrixSDPkts object.
         ALCATEL NOTE: the ALCATEL ISAM does not support this object."
    ::= { nlMatrixTopNHighCapacityEntry 5 }

nlMatrixTopNHighCapacityPktRate OBJECT-TYPE
    SYNTAX      CounterBasedGauge64
--     UNITS       "Packets"
    ACCESS      read-only
    STATUS      mandatory
    DESCRIPTION 
        "The number of packets seen from the source host to the
         destination host during this sampling interval, counted
         using the rules for counting the nlMatrixSDPkts object.
         If the value of nlMatrixTopNControlRateBase is
         nlMatrixTopNHighCapacityPkts, this variable will be
         used to sort this report.
         ALCATEL NOTE: the ALCATEL ISAM does not support this object."
    ::= { nlMatrixTopNHighCapacityEntry 6 }

nlMatrixTopNHighCapacityReverseBasePktRate OBJECT-TYPE
    SYNTAX      Gauge
--     UNITS       "Packets"
    ACCESS      read-only
    STATUS      mandatory
    DESCRIPTION 
        "The number of packets seen from the destination host to the
         source host during this sampling interval, modulo 2^32, counted
         using the rules for counting the nlMatrixSDPkts object (note
         that the corresponding nlMatrixSDPkts object selected is the
         one whose source address is equal to nlMatrixTopNDestAddress
         and whose destination address is equal to
         nlMatrixTopNSourceAddress.)
         
         Note that if the value of nlMatrixTopNControlRateBase is equal
         to nlMatrixTopNHighCapacityPkts, the sort of topN entries is
         based entirely on nlMatrixTopNHighCapacityPktRate, and not on
         the value of this object.
         ALCATEL NOTE: the ALCATEL ISAM does not support this object."
    ::= { nlMatrixTopNHighCapacityEntry 7 }

nlMatrixTopNHighCapacityReverseOverflowPktRate OBJECT-TYPE
    SYNTAX      Gauge
--     UNITS       "Packets"
    ACCESS      read-only
    STATUS      mandatory
    DESCRIPTION 
        "The number of packets seen from the destination host to the
         source host during this sampling interval, divided by 2^32,
         truncating fractions (i.e., X DIV 2^32), and counted
         using the rules for counting the nlMatrixSDPkts object (note
         that the corresponding nlMatrixSDPkts object selected is the
         one whose source address is equal to nlMatrixTopNDestAddress
         and whose destination address is equal to
         nlMatrixTopNSourceAddress.)
         
         Note that if the value of nlMatrixTopNControlRateBase is equal
         to nlMatrixTopNHighCapacityPkts, the sort of topN entries is
         based entirely on nlMatrixTopNHighCapacityPktRate, and not on
         the value of this object.
         ALCATEL NOTE: the ALCATEL ISAM does not support this object."
    ::= { nlMatrixTopNHighCapacityEntry 8 }

nlMatrixTopNHighCapacityReversePktRate OBJECT-TYPE
    SYNTAX      CounterBasedGauge64
--     UNITS       "Packets"
    ACCESS      read-only
    STATUS      mandatory
    DESCRIPTION 
        "The number of packets seen from the destination host to the
         source host during this sampling interval, counted
         using the rules for counting the nlMatrixSDPkts object (note
         that the corresponding nlMatrixSDPkts object selected is the
         one whose source address is equal to nlMatrixTopNDestAddress
         and whose destination address is equal to
         nlMatrixTopNSourceAddress.)
         
         Note that if the value of nlMatrixTopNControlRateBase is equal
         to nlMatrixTopNHighCapacityPkts, the sort of topN entries is
         based entirely on nlMatrixTopNHighCapacityPktRate, and not on
         the value of this object.
         ALCATEL NOTE: the ALCATEL ISAM does not support this object."
    ::= { nlMatrixTopNHighCapacityEntry 9 }

nlMatrixTopNHighCapacityBaseOctetRate OBJECT-TYPE
    SYNTAX      Gauge
--     UNITS       "Octets"
    ACCESS      read-only
    STATUS      mandatory
    DESCRIPTION 
        "The number of octets seen from the source host to the
         destination host during this sampling interval, modulo 2^32,
         counted using the rules for counting the nlMatrixSDOctets
         object.
         ALCATEL NOTE: the ALCATEL ISAM does not support this object."
    ::= { nlMatrixTopNHighCapacityEntry 10 }

nlMatrixTopNHighCapacityOverflowOctetRate OBJECT-TYPE
    SYNTAX      Gauge
--     UNITS       "Octets"
    ACCESS      read-only
    STATUS      mandatory
    DESCRIPTION 
        "The number of octets seen from the source host
         to the destination host during this sampling interval,
         divided by 2^32, truncating fractions (i.e., X DIV 2^32),
         and counted using the rules for counting the
         nlMatrixSDOctets object.
         ALCATEL NOTE: the ALCATEL ISAM does not support this object."
    ::= { nlMatrixTopNHighCapacityEntry 11 }

nlMatrixTopNHighCapacityOctetRate OBJECT-TYPE
    SYNTAX      CounterBasedGauge64
--     UNITS       "Octets"
    ACCESS      read-only
    STATUS      mandatory
    DESCRIPTION 
        "The number of octets seen from the source host
         to the destination host during this sampling interval,
         counted using the rules for counting the
         nlMatrixSDOctets object.
         If the value of nlMatrixTopNControlRateBase is
         nlMatrixTopNHighCapacityOctets, this variable will be used
         to sort this report.
         ALCATEL NOTE: the ALCATEL ISAM does not support this object."
    ::= { nlMatrixTopNHighCapacityEntry 12 }

nlMatrixTopNHighCapacityReverseBaseOctetRate OBJECT-TYPE
    SYNTAX      Gauge
--     UNITS       "Octets"
    ACCESS      read-only
    STATUS      mandatory
    DESCRIPTION 
        "The number of octets seen from the destination host to the
         source host during this sampling interval, modulo 2^32, counted
         using the rules for counting the nlMatrixSDOctets object (note
         that the corresponding nlMatrixSDOctets object selected is the
         one whose source address is equal to nlMatrixTopNDestAddress
         and whose destination address is equal to
         nlMatrixTopNSourceAddress.)
         
         Note that if the value of nlMatrixTopNControlRateBase is equal
         to nlMatrixTopNHighCapacityOctets, the sort of topN entries is
         based entirely on nlMatrixTopNHighCapacityOctetRate, and not on
         the value of this object.
         ALCATEL NOTE: the ALCATEL ISAM does not support this object."
    ::= { nlMatrixTopNHighCapacityEntry 13 }

nlMatrixTopNHighCapacityReverseOverflowOctetRate OBJECT-TYPE
    SYNTAX      Gauge
--     UNITS       "Octets"
    ACCESS      read-only
    STATUS      mandatory
    DESCRIPTION 
        "The number of octets seen from the destination host to the
         source host during this sampling interval, divided by 2^32,
         truncating fractions (i.e., X DIV 2^32), and counted
         using the rules for counting the nlMatrixSDOctets object (note
         that the corresponding nlMatrixSDOctets object selected is the
         one whose source address is equal to nlMatrixTopNDestAddress
         and whose destination address is equal to
         nlMatrixTopNSourceAddress.)
         
         Note that if the value of nlMatrixTopNControlRateBase is equal
         to nlMatrixTopNHighCapacityOctets, the sort of topN entries is
         based entirely on nlMatrixTopNHighCapacityOctetRate, and not on
         the value of this object.
         ALCATEL NOTE: the ALCATEL ISAM does not support this object."
    ::= { nlMatrixTopNHighCapacityEntry 14 }

nlMatrixTopNHighCapacityReverseOctetRate OBJECT-TYPE
    SYNTAX      CounterBasedGauge64
--     UNITS       "Octets"
    ACCESS      read-only
    STATUS      mandatory
    DESCRIPTION 
        "The number of octets seen from the destination host to the
         source host during this sampling interval, counted
         using the rules for counting the nlMatrixSDOctets object (note
         that the corresponding nlMatrixSDOctets object selected is the
         one whose source address is equal to nlMatrixTopNDestAddress
         and whose destination address is equal to
         nlMatrixTopNSourceAddress.)
         
         Note that if the value of nlMatrixTopNControlRateBase is equal
         to nlMatrixTopNHighCapacityOctets, the sort of topN entries is
         based entirely on nlMatrixTopNHighCapacityOctetRate, and not on
         the value of this object.
         ALCATEL NOTE: the ALCATEL ISAM does not support this object."
    ::= { nlMatrixTopNHighCapacityEntry 15 }

alHostHighCapacityTable OBJECT-TYPE
    SYNTAX      SEQUENCE OF AlHostHighCapacityEntry
    ACCESS      not-accessible
    STATUS      mandatory
    DESCRIPTION 
        "Contains the High Capacity RMON extensions to the RMON-2
         alHostTable.
         ALCATEL NOTE: the ALCATEL ISAM does not support this object."
    ::= { alHost 2 }

alHostHighCapacityEntry OBJECT-TYPE
    SYNTAX      AlHostHighCapacityEntry
    ACCESS      not-accessible
    STATUS      mandatory
    DESCRIPTION 
        "Contains the High Capacity RMON extensions to the RMON-2
         alHostEntry. These objects will be created by the agent
         for all alHostEntries associated with whichever
         hlHostControlEntries it deems appropriate. (i.e., either all
         alHostHighCapacityEntries associated with a particular
         hlHostControlEntry will be created, or none of them will
         be.)
         ALCATEL NOTE: the ALCATEL ISAM does not support this object."
    INDEX       { hlHostControlIndex, alHostTimeMark, 
                  protocolDirLocalIndex, nlHostAddress, 
                  protocolDirLocalIndex }
    ::= { alHostHighCapacityTable 1 }

AlHostHighCapacityEntry ::= SEQUENCE {
    alHostHighCapacityInOverflowPkts        ZeroBasedCounter32,
    alHostHighCapacityInPkts                ZeroBasedCounter64,
    alHostHighCapacityOutOverflowPkts       ZeroBasedCounter32,
    alHostHighCapacityOutPkts               ZeroBasedCounter64,
    alHostHighCapacityInOverflowOctets      ZeroBasedCounter32,
    alHostHighCapacityInOctets              ZeroBasedCounter64,
    alHostHighCapacityOutOverflowOctets     ZeroBasedCounter32,
    alHostHighCapacityOutOctets             ZeroBasedCounter64
}

alHostHighCapacityInOverflowPkts OBJECT-TYPE
    SYNTAX      ZeroBasedCounter32
--     UNITS       "Packets"
    ACCESS      read-only
    STATUS      mandatory
    DESCRIPTION 
        "The number of times the associated alHostInPkts
         counter has overflowed.
         ALCATEL NOTE: the ALCATEL ISAM does not support this object."
    ::= { alHostHighCapacityEntry 1 }

alHostHighCapacityInPkts OBJECT-TYPE
    SYNTAX      ZeroBasedCounter64
--     UNITS       "Packets"
    ACCESS      read-only
    STATUS      mandatory
    DESCRIPTION 
        "The number of packets of this protocol type without errors
         transmitted to this address since it was added to the
         alHostHighCapacityTable.  Note that this is the number of
         link-layer packets, so if a single network-layer packet
         is fragmented into several link-layer frames, this counter
         is incremented several times.
         ALCATEL NOTE: the ALCATEL ISAM does not support this object."
    ::= { alHostHighCapacityEntry 2 }

alHostHighCapacityOutOverflowPkts OBJECT-TYPE
    SYNTAX      ZeroBasedCounter32
--     UNITS       "Packets"
    ACCESS      read-only
    STATUS      mandatory
    DESCRIPTION 
        "The number of times the associated alHostOutPkts
         counter has overflowed.
         ALCATEL NOTE: the ALCATEL ISAM does not support this object."
    ::= { alHostHighCapacityEntry 3 }

alHostHighCapacityOutPkts OBJECT-TYPE
    SYNTAX      ZeroBasedCounter64
--     UNITS       "Packets"
    ACCESS      read-only
    STATUS      mandatory
    DESCRIPTION 
        "The number of packets of this protocol type without errors
         transmitted by this address since it was added to the
         alHostHighCapacityTable.  Note that this is the number of
         link-layer packets, so if a single network-layer packet
         is fragmented into several link-layer frames, this counter
         is incremented several times.
         ALCATEL NOTE: the ALCATEL ISAM does not support this object."
    ::= { alHostHighCapacityEntry 4 }

alHostHighCapacityInOverflowOctets OBJECT-TYPE
    SYNTAX      ZeroBasedCounter32
--     UNITS       "Octets"
    ACCESS      read-only
    STATUS      mandatory
    DESCRIPTION 
        "The number of times the associated alHostInOctets
         counter has overflowed.
         ALCATEL NOTE: the ALCATEL ISAM does not support this object."
    ::= { alHostHighCapacityEntry 5 }

alHostHighCapacityInOctets OBJECT-TYPE
    SYNTAX      ZeroBasedCounter64
--     UNITS       "Octets"
    ACCESS      read-only
    STATUS      mandatory
    DESCRIPTION 
        "The number of octets transmitted to this address
         of this protocol type since it was added to the
         alHostHighCapacityTable (excluding framing bits but
         including FCS octets), excluding those octets in
         packets that contained errors.
         
         Note this doesn't count just those octets in the particular
         protocol frames, but includes the entire packet that contained
         the protocol.
         ALCATEL NOTE: the ALCATEL ISAM does not support this object."
    ::= { alHostHighCapacityEntry 6 }

alHostHighCapacityOutOverflowOctets OBJECT-TYPE
    SYNTAX      ZeroBasedCounter32
--     UNITS       "Octets"
    ACCESS      read-only
    STATUS      mandatory
    DESCRIPTION 
        "The number of times the associated alHostOutOctets
         counter has overflowed.
         ALCATEL NOTE: the ALCATEL ISAM does not support this object."
    ::= { alHostHighCapacityEntry 7 }

alHostHighCapacityOutOctets OBJECT-TYPE
    SYNTAX      ZeroBasedCounter64
--     UNITS       "Octets"
    ACCESS      read-only
    STATUS      mandatory
    DESCRIPTION 
        "The number of octets transmitted by this address
         of this protocol type since it was added to the
         alHostHighCapacityTable (excluding framing bits but
         including FCS octets), excluding those octets in
         packets that contained errors.
         
         Note this doesn't count just those octets in the particular
         protocol frames, but includes the entire packet that contained
         the protocol.
         ALCATEL NOTE: the ALCATEL ISAM does not support this object."
    ::= { alHostHighCapacityEntry 8 }

alMatrixSDHighCapacityTable OBJECT-TYPE
    SYNTAX      SEQUENCE OF AlMatrixSDHighCapacityEntry
    ACCESS      not-accessible
    STATUS      mandatory
    DESCRIPTION 
        "Contains the High Capacity RMON extensions to the RMON-2
         alMatrixSDTable.
         ALCATEL NOTE: the ALCATEL ISAM does not support this object."
    ::= { alMatrix 5 }

alMatrixSDHighCapacityEntry OBJECT-TYPE
    SYNTAX      AlMatrixSDHighCapacityEntry
    ACCESS      not-accessible
    STATUS      mandatory
    DESCRIPTION 
        "Contains the High Capacity RMON extensions to the RMON-2
         alMatrixSDEntry. These objects will be created by the agent
         for all alMatrixSDEntries associated with whichever
         hlMatrixControlEntries it deems appropriate. (i.e., either all
         alMatrixSDHighCapacityEntries associated with a particular
         hlMatrixControlEntry will be created, or none of them will
         be.)
         ALCATEL NOTE: the ALCATEL ISAM does not support this object."
    INDEX       { hlMatrixControlIndex, alMatrixSDTimeMark, 
                  protocolDirLocalIndex, nlMatrixSDSourceAddress, 
                  nlMatrixSDDestAddress, protocolDirLocalIndex }
    ::= { alMatrixSDHighCapacityTable 1 }

AlMatrixSDHighCapacityEntry ::= SEQUENCE {
    alMatrixSDHighCapacityOverflowPkts      ZeroBasedCounter32,
    alMatrixSDHighCapacityPkts              ZeroBasedCounter64,
    alMatrixSDHighCapacityOverflowOctets    ZeroBasedCounter32,
    alMatrixSDHighCapacityOctets            ZeroBasedCounter64
}

alMatrixSDHighCapacityOverflowPkts OBJECT-TYPE
    SYNTAX      ZeroBasedCounter32
--     UNITS       "Packets"
    ACCESS      read-only
    STATUS      mandatory
    DESCRIPTION 
        "The number of times the associated alMatrixSDPkts
         counter has overflowed.
         ALCATEL NOTE: the ALCATEL ISAM does not support this object."
    ::= { alMatrixSDHighCapacityEntry 1 }

alMatrixSDHighCapacityPkts OBJECT-TYPE
    SYNTAX      ZeroBasedCounter64
--     UNITS       "Packets"
    ACCESS      read-only
    STATUS      mandatory
    DESCRIPTION 
        "The number of good packets of this protocol type
         transmitted from the source address to the destination address
         since this entry was added to the alMatrixSDHighCapacityTable.
         Note that this is the number of link-layer packets, so if a
         single network-layer packet is fragmented into several
         link-layer frames, this counter is incremented several times.
         ALCATEL NOTE: the ALCATEL ISAM does not support this object."
    ::= { alMatrixSDHighCapacityEntry 2 }

alMatrixSDHighCapacityOverflowOctets OBJECT-TYPE
    SYNTAX      ZeroBasedCounter32
--     UNITS       "Octets"
    ACCESS      read-only
    STATUS      mandatory
    DESCRIPTION 
        "The number of times the associated alMatrixSDOctets
         counter has overflowed.
         ALCATEL NOTE: the ALCATEL ISAM does not support this object."
    ::= { alMatrixSDHighCapacityEntry 3 }

alMatrixSDHighCapacityOctets OBJECT-TYPE
    SYNTAX      ZeroBasedCounter64
--     UNITS       "Octets"
    ACCESS      read-only
    STATUS      mandatory
    DESCRIPTION 
        "The number of octets in good packets of this protocol type
         transmitted from the source address to the destination address
         since this entry was added to the alMatrixSDHighCapacityTable
         (excluding framing bits but including FCS octets).
         
         Note this doesn't count just those octets in the particular
         protocol frames, but includes the entire packet that contained
         the protocol.
         ALCATEL NOTE: the ALCATEL ISAM does not support this object."
    ::= { alMatrixSDHighCapacityEntry 4 }

alMatrixDSHighCapacityTable OBJECT-TYPE
    SYNTAX      SEQUENCE OF AlMatrixDSHighCapacityEntry
    ACCESS      not-accessible
    STATUS      mandatory
    DESCRIPTION 
        "Contains the High Capacity RMON extensions to the RMON-2
         alMatrixDSTable.
         ALCATEL NOTE: the ALCATEL ISAM does not support this object."
    ::= { alMatrix 6 }

alMatrixDSHighCapacityEntry OBJECT-TYPE
    SYNTAX      AlMatrixDSHighCapacityEntry
    ACCESS      not-accessible
    STATUS      mandatory
    DESCRIPTION 
        "Contains the High Capacity RMON extensions to the RMON-2
         alMatrixSDTable. These objects will be created by the agent
         for all alMatrixDSEntries associated with whichever
         hlMatrixControlEntries it deems appropriate. (i.e., either all
         alMatrixDSHighCapacityEntries associated with a particular
         hlMatrixControlEntry will be created, or none of them will
         be.)
         ALCATEL NOTE: the ALCATEL ISAM does not support this object."
    INDEX       { hlMatrixControlIndex, alMatrixDSTimeMark, 
                  protocolDirLocalIndex, nlMatrixDSDestAddress, 
                  nlMatrixDSSourceAddress, protocolDirLocalIndex }
    ::= { alMatrixDSHighCapacityTable 1 }

AlMatrixDSHighCapacityEntry ::= SEQUENCE {
    alMatrixDSHighCapacityOverflowPkts      ZeroBasedCounter32,
    alMatrixDSHighCapacityPkts              ZeroBasedCounter64,
    alMatrixDSHighCapacityOverflowOctets    ZeroBasedCounter32,
    alMatrixDSHighCapacityOctets            ZeroBasedCounter64
}

alMatrixDSHighCapacityOverflowPkts OBJECT-TYPE
    SYNTAX      ZeroBasedCounter32
--     UNITS       "Packets"
    ACCESS      read-only
    STATUS      mandatory
    DESCRIPTION 
        "The number of times the associated alMatrixDSPkts
         counter has overflowed.
         ALCATEL NOTE: the ALCATEL ISAM does not support this object."
    ::= { alMatrixDSHighCapacityEntry 1 }

alMatrixDSHighCapacityPkts OBJECT-TYPE
    SYNTAX      ZeroBasedCounter64
--     UNITS       "Packets"
    ACCESS      read-only
    STATUS      mandatory
    DESCRIPTION 
        "The number of good packets of this protocol type
         transmitted from the source address to the destination address
         since this entry was added to the alMatrixDSHighCapacityTable.
         Note that this is the number of link-layer packets, so if a
         single network-layer packet is fragmented into several
         link-layer frames, this counter is incremented several times.
         ALCATEL NOTE: the ALCATEL ISAM does not support this object."
    ::= { alMatrixDSHighCapacityEntry 2 }

alMatrixDSHighCapacityOverflowOctets OBJECT-TYPE
    SYNTAX      ZeroBasedCounter32
--     UNITS       "Octets"
    ACCESS      read-only
    STATUS      mandatory
    DESCRIPTION 
        "The number of times the associated alMatrixDSOctets
         counter has overflowed.
         ALCATEL NOTE: the ALCATEL ISAM does not support this object."
    ::= { alMatrixDSHighCapacityEntry 3 }

alMatrixDSHighCapacityOctets OBJECT-TYPE
    SYNTAX      ZeroBasedCounter64
--     UNITS       "Octets"
    ACCESS      read-only
    STATUS      mandatory
    DESCRIPTION 
        "The number of octets in good packets of this protocol type
         transmitted from the source address to the destination address
         since this entry was added to the alMatrixDSHighCapacityTable
         (excluding framing bits but including FCS octets).
         
         Note this doesn't count just those octets in the particular
         protocol frames, but includes the entire packet that contained
         the protocol.
         ALCATEL NOTE: the ALCATEL ISAM does not support this object."
    ::= { alMatrixDSHighCapacityEntry 4 }

alMatrixTopNHighCapacityTable OBJECT-TYPE
    SYNTAX      SEQUENCE OF AlMatrixTopNHighCapacityEntry
    ACCESS      not-accessible
    STATUS      mandatory
    DESCRIPTION 
        "Contains the High Capacity RMON extensions to the RMON-2
         alMatrixTopNTable when alMatrixTopNControlRateBase specifies
         a High Capacity TopN Report.
         ALCATEL NOTE: the ALCATEL ISAM does not support this object."
    ::= { alMatrix 7 }

alMatrixTopNHighCapacityEntry OBJECT-TYPE
    SYNTAX      AlMatrixTopNHighCapacityEntry
    ACCESS      not-accessible
    STATUS      mandatory
    DESCRIPTION 
        "Contains the High Capacity RMON extensions to the RMON-2
         alMatrixTopNEntry when alMatrixTopNControlRateBase specifies
         a High Capacity TopN Report. These objects will be created by
         the agent for all alMatrixTopNEntries associated with whichever
         alMatrixTopNControlEntries have a alMatrixTopNControlRateBase
         that specify a high capacity report.
         ALCATEL NOTE: the ALCATEL ISAM does not support this object."
    INDEX       { alMatrixTopNControlIndex, alMatrixTopNIndex }
    ::= { alMatrixTopNHighCapacityTable 1 }

AlMatrixTopNHighCapacityEntry ::= SEQUENCE {
    alMatrixTopNHighCapacityProtocolDirLocalIndex       INTEGER,
    alMatrixTopNHighCapacitySourceAddress               OCTET STRING,
    alMatrixTopNHighCapacityDestAddress                 OCTET STRING,
    alMatrixTopNHighCapacityAppProtocolDirLocalIndex    INTEGER,
    alMatrixTopNHighCapacityBasePktRate                 Gauge,
    alMatrixTopNHighCapacityOverflowPktRate             Gauge,
    alMatrixTopNHighCapacityPktRate                     CounterBasedGauge64,
    alMatrixTopNHighCapacityReverseBasePktRate          Gauge,
    alMatrixTopNHighCapacityReverseOverflowPktRate      Gauge,
    alMatrixTopNHighCapacityReversePktRate              CounterBasedGauge64,
    alMatrixTopNHighCapacityBaseOctetRate               Gauge,
    alMatrixTopNHighCapacityOverflowOctetRate           Gauge,
    alMatrixTopNHighCapacityOctetRate                   CounterBasedGauge64,
    alMatrixTopNHighCapacityReverseBaseOctetRate        Gauge,
    alMatrixTopNHighCapacityReverseOverflowOctetRate    Gauge,
    alMatrixTopNHighCapacityReverseOctetRate            CounterBasedGauge64
}

alMatrixTopNHighCapacityProtocolDirLocalIndex OBJECT-TYPE
    SYNTAX      INTEGER (1..2147483647)
    ACCESS      read-only
    STATUS      mandatory
    DESCRIPTION 
        "The protocolDirLocalIndex of the network layer protocol of
         this entry's network address.
         ALCATEL NOTE: the ALCATEL ISAM does not support this object."
    ::= { alMatrixTopNHighCapacityEntry 1 }

alMatrixTopNHighCapacitySourceAddress OBJECT-TYPE
    SYNTAX      OCTET STRING
    ACCESS      read-only
    STATUS      mandatory
    DESCRIPTION 
        "The network layer address of the source host in this
         conversation.
         
         This is represented as an octet string with
         specific semantics and length as identified
         by the associated alMatrixTopNProtocolDirLocalIndex.
         
         For example, if the alMatrixTopNProtocolDirLocalIndex
         indicates an encapsulation of ip, this object is encoded as a
         length octet of 4, followed by the 4 octets of the ip address,
         in network byte order.
         ALCATEL NOTE: the ALCATEL ISAM does not support this object."
    ::= { alMatrixTopNHighCapacityEntry 2 }

alMatrixTopNHighCapacityDestAddress OBJECT-TYPE
    SYNTAX      OCTET STRING
    ACCESS      read-only
    STATUS      mandatory
    DESCRIPTION 
        "The network layer address of the destination host in this
         conversation.
         
         This is represented as an octet string with
         specific semantics and length as identified
         by the associated alMatrixTopNProtocolDirLocalIndex.
         
         For example, if the alMatrixTopNProtocolDirLocalIndex
         indicates an encapsulation of ip, this object is encoded as a
         length octet of 4, followed by the 4 octets of the ip address,
         in network byte order.
         ALCATEL NOTE: the ALCATEL ISAM does not support this object."
    ::= { alMatrixTopNHighCapacityEntry 3 }

alMatrixTopNHighCapacityAppProtocolDirLocalIndex OBJECT-TYPE
    SYNTAX      INTEGER
    ACCESS      read-only
    STATUS      mandatory
    DESCRIPTION 
        "The type of the protocol counted by this entry.
         ALCATEL NOTE: the ALCATEL ISAM does not support this object."
    ::= { alMatrixTopNHighCapacityEntry 4 }

alMatrixTopNHighCapacityBasePktRate OBJECT-TYPE
    SYNTAX      Gauge
--     UNITS       "Packets"
    ACCESS      read-only
    STATUS      mandatory
    DESCRIPTION 
        "The number of packets seen of this protocol from the
         source host to the destination host during this sampling
         interval, modulo 2^32, counted using the rules for counting
         the alMatrixSDPkts object.
         ALCATEL NOTE: the ALCATEL ISAM does not support this object."
    ::= { alMatrixTopNHighCapacityEntry 5 }

alMatrixTopNHighCapacityOverflowPktRate OBJECT-TYPE
    SYNTAX      Gauge
--     UNITS       "Packets"
    ACCESS      read-only
    STATUS      mandatory
    DESCRIPTION 
        "The number of packets seen of this protocol from the source
         host to the destination host during this sampling interval,
         divided by 2^32, truncating fractions (i.e., X DIV 2^32),
         and counted using the rules for counting the
         alMatrixSDPkts object.
         ALCATEL NOTE: the ALCATEL ISAM does not support this object."
    ::= { alMatrixTopNHighCapacityEntry 6 }

alMatrixTopNHighCapacityPktRate OBJECT-TYPE
    SYNTAX      CounterBasedGauge64
--     UNITS       "Packets"
    ACCESS      read-only
    STATUS      mandatory
    DESCRIPTION 
        "The number of packets seen of this protocol from the source
         host to the destination host during this sampling interval,
         counted using the rules for counting the
         alMatrixSDPkts object.
         If the value of alMatrixTopNControlRateBase is
         alMatrixTopNTerminalsPkts, alMatrixTopNAllPkts,
         alMatrixTopNTerminalsHighCapacityPkts, or
         alMatrixTopNAllHighCapacityPkts, this variable will be used
         to sort this report.
         ALCATEL NOTE: the ALCATEL ISAM does not support this object."
    ::= { alMatrixTopNHighCapacityEntry 7 }

alMatrixTopNHighCapacityReverseBasePktRate OBJECT-TYPE
    SYNTAX      Gauge
--     UNITS       "Packets"
    ACCESS      read-only
    STATUS      mandatory
    DESCRIPTION 
        "The number of packets seen of this protocol from the
         destination host to the source host during this sampling
         interval, modulo 2^32, counted using the rules for counting
         the alMatrixSDPkts object (note that the corresponding
         alMatrixSDPkts object selected is the one whose source address
         is equal to alMatrixTopNDestAddress and whose destination
         address is equal to alMatrixTopNSourceAddress.)
         ALCATEL NOTE: the ALCATEL ISAM does not support this object."
    ::= { alMatrixTopNHighCapacityEntry 8 }

alMatrixTopNHighCapacityReverseOverflowPktRate OBJECT-TYPE
    SYNTAX      Gauge
--     UNITS       "Packets"
    ACCESS      read-only
    STATUS      mandatory
    DESCRIPTION 
        "The number of packets seen of this protocol from the
         destination host to the source host during this sampling
         interval, divided by 2^32, truncating fractions
         (i.e., X DIV 2^32), and counted using the rules for
         counting the alMatrixSDPkts object (note that the
         corresponding alMatrixSDPkts object selected is the
         one whose source address is equal to alMatrixTopNDestAddress
         and whose destination address is equal to
         alMatrixTopNSourceAddress.)
         ALCATEL NOTE: the ALCATEL ISAM does not support this object."
    ::= { alMatrixTopNHighCapacityEntry 9 }

alMatrixTopNHighCapacityReversePktRate OBJECT-TYPE
    SYNTAX      CounterBasedGauge64
--     UNITS       "Packets"
    ACCESS      read-only
    STATUS      mandatory
    DESCRIPTION 
        "The number of packets seen of this protocol from the
         destination host to the source host during this sampling
         interval, counted using the rules for counting the
         alMatrixSDPkts object (note that the corresponding
         alMatrixSDPkts object selected is the one whose source address
         is equal to alMatrixTopNDestAddress and whose destination
         address is equal to alMatrixTopNSourceAddress.)
         ALCATEL NOTE: the ALCATEL ISAM does not support this object."
    ::= { alMatrixTopNHighCapacityEntry 10 }

alMatrixTopNHighCapacityBaseOctetRate OBJECT-TYPE
    SYNTAX      Gauge
--     UNITS       "Octets"
    ACCESS      read-only
    STATUS      mandatory
    DESCRIPTION 
        "The number of octets seen of this protocol from the source host
         to the destination host during this sampling interval,
         modulo 2^32, counted using the rules for counting the
         alMatrixSDOctets object.
         ALCATEL NOTE: the ALCATEL ISAM does not support this object."
    ::= { alMatrixTopNHighCapacityEntry 11 }

alMatrixTopNHighCapacityOverflowOctetRate OBJECT-TYPE
    SYNTAX      Gauge
--     UNITS       "Octets"
    ACCESS      read-only
    STATUS      mandatory
    DESCRIPTION 
        "The number of octets seen of this protocol from the source host
         to the destination host during this sampling interval,
         divided by 2^32, truncating fractions (i.e., X DIV 2^32),
         and counted using the rules for counting the
         alMatrixSDOctets object.
         ALCATEL NOTE: the ALCATEL ISAM does not support this object."
    ::= { alMatrixTopNHighCapacityEntry 12 }

alMatrixTopNHighCapacityOctetRate OBJECT-TYPE
    SYNTAX      CounterBasedGauge64
--     UNITS       "Octets"
    ACCESS      read-only
    STATUS      mandatory
    DESCRIPTION 
        "The number of octets seen of this protocol from the source host
         to the destination host during this sampling interval,
         counted using the rules for counting the
         alMatrixSDOctets object.
         If the value of alMatrixTopNControlRateBase is
         alMatrixTopNTerminalsOctets, alMatrixTopNAllOctets,
         alMatrixTopNTerminalsHighCapacityOctets, or
         alMatrixTopNAllHighCapacityOctets, this variable will be used
         to sort this report.
         ALCATEL NOTE: the ALCATEL ISAM does not support this object."
    ::= { alMatrixTopNHighCapacityEntry 13 }

alMatrixTopNHighCapacityReverseBaseOctetRate OBJECT-TYPE
    SYNTAX      Gauge
--     UNITS       "Octets"
    ACCESS      read-only
    STATUS      mandatory
    DESCRIPTION 
        "The number of octets seen of this protocol from the
         destination host to the source host during this sampling
         interval, modulo 2^32, counted using the rules for counting
         the alMatrixSDOctets object (note that the corresponding
         alMatrixSDOctets object selected is the one whose source
         address is equal to alMatrixTopNDestAddress and whose
         destination address is equal to alMatrixTopNSourceAddress.)
         ALCATEL NOTE: the ALCATEL ISAM does not support this object."
    ::= { alMatrixTopNHighCapacityEntry 14 }

alMatrixTopNHighCapacityReverseOverflowOctetRate OBJECT-TYPE
    SYNTAX      Gauge
--     UNITS       "Octets"
    ACCESS      read-only
    STATUS      mandatory
    DESCRIPTION 
        "The number of octets seen of this protocol from the
         destination host to the source host during this sampling
         interval, divided by 2^32, truncating fractions (i.e., X DIV
         2^32), and counted using the rules for counting the
         alMatrixSDOctets object (note that the corresponding
         alMatrixSDOctets object selected is the one whose source
         address is equal to alMatrixTopNDestAddress and whose
         destination address is equal to alMatrixTopNSourceAddress.)
         ALCATEL NOTE: the ALCATEL ISAM does not support this object."
    ::= { alMatrixTopNHighCapacityEntry 15 }

alMatrixTopNHighCapacityReverseOctetRate OBJECT-TYPE
    SYNTAX      CounterBasedGauge64
--     UNITS       "Octets"
    ACCESS      read-only
    STATUS      mandatory
    DESCRIPTION 
        "The number of octets seen of this protocol from the
         destination host to the source host during this sampling
         interval, counted using the rules for counting the
         alMatrixSDOctets object (note that the corresponding
         alMatrixSDOctets object selected is the one whose source
         address is equal to alMatrixTopNDestAddress and whose
         destination address is equal to alMatrixTopNSourceAddress.)
         ALCATEL NOTE: the ALCATEL ISAM does not support this object."
    ::= { alMatrixTopNHighCapacityEntry 16 }

usrHistoryHighCapacityTable OBJECT-TYPE
    SYNTAX      SEQUENCE OF UsrHistoryHighCapacityEntry
    ACCESS      not-accessible
    STATUS      mandatory
    DESCRIPTION 
        "Contains the High Capacity RMON extensions to the RMON-2
         usrHistoryTable.
         ALCATEL NOTE: the ALCATEL ISAM does not support this object."
    ::= { usrHistory 4 }

usrHistoryHighCapacityEntry OBJECT-TYPE
    SYNTAX      UsrHistoryHighCapacityEntry
    ACCESS      not-accessible
    STATUS      mandatory
    DESCRIPTION 
        "Contains the High Capacity RMON extensions to the RMON-2
         usrHistoryEntry. These objects will be created by the agent
         for all usrHistoryEntries associated with whichever
         usrHistoryControlEntries it deems appropriate. (i.e., either all
         usrHistoryHighCapacityEntries associated with a particular
         usrHistoryControlEntry will be created, or none of them will
         be.)
         ALCATEL NOTE: the ALCATEL ISAM does not support this object."
    INDEX       { usrHistoryControlIndex, usrHistorySampleIndex, 
                  usrHistoryObjectIndex }
    ::= { usrHistoryHighCapacityTable 1 }

UsrHistoryHighCapacityEntry ::= SEQUENCE {
    usrHistoryHighCapacityOverflowAbsValue  Gauge,
    usrHistoryHighCapacityAbsValue          CounterBasedGauge64
}

usrHistoryHighCapacityOverflowAbsValue OBJECT-TYPE
    SYNTAX      Gauge
    ACCESS      read-only
    STATUS      mandatory
    DESCRIPTION 
        "The absolute value (i.e. unsigned value) of the
         user-specified statistic during the last sampling period,
         divided by 2^32, truncating fractions (i.e., X DIV 2^32).
         The value during the current sampling period is not made
         available until the period is completed.
         
         To obtain the true value for this sampling interval, the
         associated instance of usrHistoryValStatus should be checked,
         and usrHistoryAbsValue adjusted as necessary.
         
         If the MIB instance could not be accessed during the sampling
         interval, then this object will have a value of zero and the
         associated instance of usrHistoryValStatus will be set to
         'valueNotAvailable(1)'.
         ALCATEL NOTE: the ALCATEL ISAM does not support this object."
    ::= { usrHistoryHighCapacityEntry 1 }

usrHistoryHighCapacityAbsValue OBJECT-TYPE
    SYNTAX      CounterBasedGauge64
    ACCESS      read-only
    STATUS      mandatory
    DESCRIPTION 
        "The absolute value (i.e. unsigned value) of the
         user-specified statistic during the last sampling period. The
         value during the current sampling period is not made available
         until the period is completed.
         
         To obtain the true value for this sampling interval, the
         associated instance of usrHistoryValStatus should be checked,
         and usrHistoryHighCapacityAbsValue adjusted as necessary.
         
         If the MIB instance could not be accessed during the sampling
         interval, then this object will have a value of zero and the
         associated instance of usrHistoryValStatus will be set to
         'valueNotAvailable(1)'.
         ALCATEL NOTE: the ALCATEL ISAM does not support this object."
    ::= { usrHistoryHighCapacityEntry 2 }

hcRMONCapabilities OBJECT-TYPE
    SYNTAX      OCTET STRING
--                   { mediaIndependentGroup(0), 
--                     etherStatsHighCapacityGroup(1), 
--                     etherHistoryHighCapacityGroup(2), 
--                     hostHighCapacityGroup(3), 
--                     hostTopNHighCapacityGroup(4), 
--                     matrixHighCapacityGroup(5), 
--                     captureBufferHighCapacityGroup(6), 
--                     protocolDistributionHighCapacityGroup(7), 
--                     nlHostHighCapacityGroup(8), 
--                     nlMatrixHighCapacityGroup(9), 
--                     nlMatrixTopNHighCapacityGroup(10), 
--                     alHostHighCapacityGroup(11), 
--                     alMatrixHighCapacityGroup(12), 
--                     alMatrixTopNHighCapacityGroup(13), 
--                     usrHistoryHighCapacityGroup(14) }
    ACCESS      read-only
    STATUS      mandatory
    DESCRIPTION 
        "An indication of the High Capacity RMON MIB groups supported
         on at least one interface by this probe.
         ALCATEL NOTE: the ALCATEL ISAM does not support this object."
    ::= { probeConfig 16 }

hcRmonMIBCompliances OBJECT IDENTIFIER
    ::= { rmonConformance 6 }

hcRmonMIBGroups OBJECT IDENTIFIER
    ::= { rmonConformance 7 }

mediaIndependentStats OBJECT IDENTIFIER
    ::= { rmon 21 }

mediaIndependentTable OBJECT-TYPE
    SYNTAX      SEQUENCE OF MediaIndependentEntry
    ACCESS      not-accessible
    STATUS      mandatory
    DESCRIPTION 
        "Media independent statistics for promiscuous monitoring of
         any media.
         
         The following table defines media independent statistics that
         provide information for full and/or half-duplex links as well
         as high capacity links.
         
         For half-duplex links, or full-duplex-capable links operating
         in half-duplex mode, the mediaIndependentIn* objects shall be
         used and the mediaIndependentOut* objects shall not increment.
         
         For full-duplex links, the mediaIndependentOut* objects shall
         be present and shall increment. Whenever possible, the probe
         should count packets moving away from the closest terminating
         equipment as output packets. Failing that, the probe should
         count packets moving away from the DTE as output packets.
         ALCATEL NOTE: the ALCATEL ISAM does not support this object."
    ::= { mediaIndependentStats 1 }

mediaIndependentEntry OBJECT-TYPE
    SYNTAX      MediaIndependentEntry
    ACCESS      not-accessible
    STATUS      mandatory
    DESCRIPTION 
        "Media independent statistics for promiscuous monitoring of
         any media.
         ALCATEL NOTE: the ALCATEL ISAM does not support this object."
    INDEX       { mediaIndependentIndex }
    ::= { mediaIndependentTable 1 }

MediaIndependentEntry ::= SEQUENCE {
    mediaIndependentIndex                       INTEGER,
    mediaIndependentDataSource                  OBJECT IDENTIFIER,
    mediaIndependentDropEvents                  Counter,
    mediaIndependentDroppedFrames               Counter,
    mediaIndependentInPkts                      Counter,
    mediaIndependentInOverflowPkts              Counter,
    mediaIndependentInHighCapacityPkts          Counter,
    mediaIndependentOutPkts                     Counter,
    mediaIndependentOutOverflowPkts             Counter,
    mediaIndependentOutHighCapacityPkts         Counter,
    mediaIndependentInOctets                    Counter,
    mediaIndependentInOverflowOctets            Counter,
    mediaIndependentInHighCapacityOctets        Counter,
    mediaIndependentOutOctets                   Counter,
    mediaIndependentOutOverflowOctets           Counter,
    mediaIndependentOutHighCapacityOctets       Counter,
    mediaIndependentInNUCastPkts                Counter,
    mediaIndependentInNUCastOverflowPkts        Counter,
    mediaIndependentInNUCastHighCapacityPkts    Counter,
    mediaIndependentOutNUCastPkts               Counter,
    mediaIndependentOutNUCastOverflowPkts       Counter,
    mediaIndependentOutNUCastHighCapacityPkts   Counter,
    mediaIndependentInErrors                    Counter,
    mediaIndependentOutErrors                   Counter,
    mediaIndependentInputSpeed                  Gauge,
    mediaIndependentOutputSpeed                 Gauge,
    mediaIndependentDuplexMode                  INTEGER,
    mediaIndependentDuplexChanges               Counter,
    mediaIndependentDuplexLastChange            TimeStamp,
    mediaIndependentOwner                       OwnerString,
    mediaIndependentStatus                      RowStatus
}

mediaIndependentIndex OBJECT-TYPE
    SYNTAX      INTEGER (1..65535)
    ACCESS      not-accessible
    STATUS      mandatory
    DESCRIPTION 
        "The value of this object uniquely identifies this
         mediaIndependent entry.
         ALCATEL NOTE: the ALCATEL ISAM does not support this object."
    ::= { mediaIndependentEntry 1 }

mediaIndependentDataSource OBJECT-TYPE
    SYNTAX      OBJECT IDENTIFIER
    ACCESS      read-write
    STATUS      mandatory
    DESCRIPTION 
        "This object identifies the source of the data that
         this mediaIndependent entry is configured to analyze.  This
         source can be any interface on this device.
         In order to identify a particular interface, this
         object shall identify the instance of the ifIndex
         object, defined in RFC 1213 and RFC 2233 [16,17], for
         the desired interface.  For example, if an entry
         were to receive data from interface #1, this object
         would be set to ifIndex.1.
         
         The statistics in this group reflect all packets
         on the local network segment attached to the
         identified interface.
         
         An agent may or may not be able to tell if
         fundamental changes to the media of the interface
         have occurred and necessitate a deletion of
         this entry.  For example, a hot-pluggable ethernet
         card could be pulled out and replaced by a
         token-ring card.  In such a case, if the agent has
         such knowledge of the change, it is recommended that
         it delete this entry.
         
         This object may not be modified if the associated
         mediaIndependentStatus object is equal to active(1).
         ALCATEL NOTE: the ALCATEL ISAM does not support this object."
    ::= { mediaIndependentEntry 2 }

mediaIndependentDropEvents OBJECT-TYPE
    SYNTAX      Counter
--     UNITS       "Events"
    ACCESS      read-only
    STATUS      mandatory
    DESCRIPTION 
        "The total number of events in which packets
         were dropped by the probe due to lack of resources.
         Note that this number is not necessarily the number of
         packets dropped; it is just the number of times this
         condition has been detected.
         ALCATEL NOTE: the ALCATEL ISAM does not support this object."
    ::= { mediaIndependentEntry 3 }

mediaIndependentDroppedFrames OBJECT-TYPE
    SYNTAX      Counter
--     UNITS       "Packets"
    ACCESS      read-only
    STATUS      mandatory
    DESCRIPTION 
        "The total number of frames which were received by the probe
         and therefore not accounted for in the
         mediaIndependentDropEvents, but for which the probe chose not
         to count for this entry for whatever reason.  Most often, this
         event occurs when the probe is out of some resources and
         decides to shed load from this collection.
         
         This count does not include packets that were not counted
         because they had MAC-layer errors.
         
         Note that, unlike the dropEvents counter, this number is the
         exact number of frames dropped.
         ALCATEL NOTE: the ALCATEL ISAM does not support this object."
    ::= { mediaIndependentEntry 4 }

mediaIndependentInPkts OBJECT-TYPE
    SYNTAX      Counter
--     UNITS       "Packets"
    ACCESS      read-only
    STATUS      mandatory
    DESCRIPTION 
        "The total number of packets (including bad packets,
         broadcast packets, and multicast packets) received
         on a half-duplex link or on the inbound connection of a
         full-duplex link.
         ALCATEL NOTE: the ALCATEL ISAM does not support this object."
    ::= { mediaIndependentEntry 5 }

mediaIndependentInOverflowPkts OBJECT-TYPE
    SYNTAX      Counter
--     UNITS       "Packets"
    ACCESS      read-only
    STATUS      mandatory
    DESCRIPTION 
        "The number of times the associated
         mediaIndependentInPkts counter has overflowed.
         ALCATEL NOTE: the ALCATEL ISAM does not support this object."
    ::= { mediaIndependentEntry 6 }

mediaIndependentInHighCapacityPkts OBJECT-TYPE
    SYNTAX      Counter
--     UNITS       "Packets"
    ACCESS      read-only
    STATUS      mandatory
    DESCRIPTION 
        "The total number of packets (including bad packets,
         broadcast packets, and multicast packets) received
         on a half-duplex link or on the inbound connection of a
         full-duplex link.
         ALCATEL NOTE: the ALCATEL ISAM does not support this object."
    ::= { mediaIndependentEntry 7 }

mediaIndependentOutPkts OBJECT-TYPE
    SYNTAX      Counter
--     UNITS       "Packets"
    ACCESS      read-only
    STATUS      mandatory
    DESCRIPTION 
        "The total number of packets (including bad packets,
         broadcast packets, and multicast packets) received on a
         full-duplex link in the direction of the network.
         ALCATEL NOTE: the ALCATEL ISAM does not support this object."
    ::= { mediaIndependentEntry 8 }

mediaIndependentOutOverflowPkts OBJECT-TYPE
    SYNTAX      Counter
--     UNITS       "Packets"
    ACCESS      read-only
    STATUS      mandatory
    DESCRIPTION 
        "The number of times the associated
         mediaIndependentOutPkts counter has overflowed.
         ALCATEL NOTE: the ALCATEL ISAM does not support this object."
    ::= { mediaIndependentEntry 9 }

mediaIndependentOutHighCapacityPkts OBJECT-TYPE
    SYNTAX      Counter
--     UNITS       "Packets"
    ACCESS      read-only
    STATUS      mandatory
    DESCRIPTION 
        "The total number of packets (including bad packets,
         broadcast packets, and multicast packets) received on a
         full-duplex link in the direction of the network.
         ALCATEL NOTE: the ALCATEL ISAM does not support this object."
    ::= { mediaIndependentEntry 10 }

mediaIndependentInOctets OBJECT-TYPE
    SYNTAX      Counter
--     UNITS       "Octets"
    ACCESS      read-only
    STATUS      mandatory
    DESCRIPTION 
        "The total number of octets of data (including those in bad
         packets) received (excluding framing bits but including FCS
         octets) on a half-duplex link or on the inbound connection of
         a full-duplex link.
         ALCATEL NOTE: the ALCATEL ISAM does not support this object."
    ::= { mediaIndependentEntry 11 }

mediaIndependentInOverflowOctets OBJECT-TYPE
    SYNTAX      Counter
--     UNITS       "Octets"
    ACCESS      read-only
    STATUS      mandatory
    DESCRIPTION 
        "The number of times the associated
         mediaIndependentInOctets counter has overflowed.
         ALCATEL NOTE: the ALCATEL ISAM does not support this object."
    ::= { mediaIndependentEntry 12 }

mediaIndependentInHighCapacityOctets OBJECT-TYPE
    SYNTAX      Counter
--     UNITS       "Octets"
    ACCESS      read-only
    STATUS      mandatory
    DESCRIPTION 
        "The total number of octets of data (including those in bad
         packets) received (excluding framing bits but
         including FCS octets) on a half-duplex link or on the inbound
         connection of a full-duplex link.
         ALCATEL NOTE: the ALCATEL ISAM does not support this object."
    ::= { mediaIndependentEntry 13 }

mediaIndependentOutOctets OBJECT-TYPE
    SYNTAX      Counter
--     UNITS       "Octets"
    ACCESS      read-only
    STATUS      mandatory
    DESCRIPTION 
        "The total number of octets of data (including those in bad
         packets) received on a full-duplex link in the direction of
         the network (excluding framing bits but including FCS
         octets).
         ALCATEL NOTE: the ALCATEL ISAM does not support this object."
    ::= { mediaIndependentEntry 14 }

mediaIndependentOutOverflowOctets OBJECT-TYPE
    SYNTAX      Counter
--     UNITS       "Octets"
    ACCESS      read-only
    STATUS      mandatory
    DESCRIPTION 
        "The number of times the associated
         mediaIndependentOutOctets counter has overflowed.
         ALCATEL NOTE: the ALCATEL ISAM does not support this object."
    ::= { mediaIndependentEntry 15 }

mediaIndependentOutHighCapacityOctets OBJECT-TYPE
    SYNTAX      Counter
--     UNITS       "Octets"
    ACCESS      read-only
    STATUS      mandatory
    DESCRIPTION 
        "The total number of octets of data (including those in bad
         packets) received on a full-duplex link in the direction of
         the network (excluding framing bits but including FCS
         octets).
         ALCATEL NOTE: the ALCATEL ISAM does not support this object."
    ::= { mediaIndependentEntry 16 }

mediaIndependentInNUCastPkts OBJECT-TYPE
    SYNTAX      Counter
--     UNITS       "Packets"
    ACCESS      read-only
    STATUS      mandatory
    DESCRIPTION 
        "The total number of non-unicast packets (including bad
         packets) received on a half-duplex link or on the inbound
         connection of a full-duplex link.
         ALCATEL NOTE: the ALCATEL ISAM does not support this object."
    ::= { mediaIndependentEntry 17 }

mediaIndependentInNUCastOverflowPkts OBJECT-TYPE
    SYNTAX      Counter
--     UNITS       "Packets"
    ACCESS      read-only
    STATUS      mandatory
    DESCRIPTION 
        "The number of times the associated
         mediaIndependentInNUCastPkts counter has overflowed.
         ALCATEL NOTE: the ALCATEL ISAM does not support this object."
    ::= { mediaIndependentEntry 18 }

mediaIndependentInNUCastHighCapacityPkts OBJECT-TYPE
    SYNTAX      Counter
--     UNITS       "Packets"
    ACCESS      read-only
    STATUS      mandatory
    DESCRIPTION 
        "The total number of non-unicast packets (including bad
         packets) received on a half-duplex link or on the inbound
         connection of a full-duplex link.
         ALCATEL NOTE: the ALCATEL ISAM does not support this object."
    ::= { mediaIndependentEntry 19 }

mediaIndependentOutNUCastPkts OBJECT-TYPE
    SYNTAX      Counter
--     UNITS       "Packets"
    ACCESS      read-only
    STATUS      mandatory
    DESCRIPTION 
        "The total number of non-unicast packets (including bad
         packets) received on a full-duplex link in the direction of
         the network.
         ALCATEL NOTE: the ALCATEL ISAM does not support this object."
    ::= { mediaIndependentEntry 20 }

mediaIndependentOutNUCastOverflowPkts OBJECT-TYPE
    SYNTAX      Counter
--     UNITS       "Packets"
    ACCESS      read-only
    STATUS      mandatory
    DESCRIPTION 
        "The number of times the associated
         mediaIndependentOutNUCastPkts counter has overflowed.
         ALCATEL NOTE: the ALCATEL ISAM does not support this object."
    ::= { mediaIndependentEntry 21 }

mediaIndependentOutNUCastHighCapacityPkts OBJECT-TYPE
    SYNTAX      Counter
--     UNITS       "Packets"
    ACCESS      read-only
    STATUS      mandatory
    DESCRIPTION 
        "The total number of packets (including bad packets)
         received on a full-duplex link in the direction of the
         network.
         ALCATEL NOTE: the ALCATEL ISAM does not support this object."
    ::= { mediaIndependentEntry 22 }

mediaIndependentInErrors OBJECT-TYPE
    SYNTAX      Counter
--     UNITS       "Packets"
    ACCESS      read-only
    STATUS      mandatory
    DESCRIPTION 
        "The total number of bad packets received on a
         half-duplex link or on the inbound connection of a
         full-duplex link.
         ALCATEL NOTE: the ALCATEL ISAM does not support this object."
    ::= { mediaIndependentEntry 23 }

mediaIndependentOutErrors OBJECT-TYPE
    SYNTAX      Counter
--     UNITS       "Packets"
    ACCESS      read-only
    STATUS      mandatory
    DESCRIPTION 
        "The total number of bad packets received on a full-duplex
         link in the direction of the network.
         ALCATEL NOTE: the ALCATEL ISAM does not support this object."
    ::= { mediaIndependentEntry 24 }

mediaIndependentInputSpeed OBJECT-TYPE
    SYNTAX      Gauge
--     UNITS       "Kilobits per Second"
    ACCESS      read-only
    STATUS      mandatory
    DESCRIPTION 
        "The nominal maximum speed in kilobits per second of this
         half-duplex link or on the inbound connection of this
         full-duplex link. If the speed is unknown or there is no fixed
         maximum (e.g. a compressed link), this value shall be zero.
         ALCATEL NOTE: the ALCATEL ISAM does not support this object."
    ::= { mediaIndependentEntry 25 }

mediaIndependentOutputSpeed OBJECT-TYPE
    SYNTAX      Gauge
--     UNITS       "Kilobits per Second"
    ACCESS      read-only
    STATUS      mandatory
    DESCRIPTION 
        "The nominal maximum speed in kilobits per second of this
         full-duplex link in the direction of the network. If the speed
         is unknown, the link is half-duplex, or there is no fixed
         maximum (e.g. a compressed link), this value shall be zero.
         ALCATEL NOTE: the ALCATEL ISAM does not support this object."
    ::= { mediaIndependentEntry 26 }

mediaIndependentDuplexMode OBJECT-TYPE
    SYNTAX      INTEGER { halfduplex(1), fullduplex(2) }
    ACCESS      read-only
    STATUS      mandatory
    DESCRIPTION 
        "The current mode of this link.
         
         Note that if the link has full-duplex capabilities but
         is operating in half-duplex mode, this value will be
         halfduplex(1).
         ALCATEL NOTE: the ALCATEL ISAM does not support this object."
    ::= { mediaIndependentEntry 27 }

mediaIndependentDuplexChanges OBJECT-TYPE
    SYNTAX      Counter
--     UNITS       "Events"
    ACCESS      read-only
    STATUS      mandatory
    DESCRIPTION 
        "The number of times this link has changed from full-duplex
         mode to half-duplex mode or from half-duplex mode to
         full-duplex mode.
         ALCATEL NOTE: the ALCATEL ISAM does not support this object."
    ::= { mediaIndependentEntry 28 }

mediaIndependentDuplexLastChange OBJECT-TYPE
    SYNTAX      TimeStamp
    ACCESS      read-only
    STATUS      mandatory
    DESCRIPTION 
        "The value of sysUpTime at the time the duplex status
         of this link last changed.
         ALCATEL NOTE: the ALCATEL ISAM does not support this object."
    ::= { mediaIndependentEntry 29 }

mediaIndependentOwner OBJECT-TYPE
    SYNTAX      OwnerString
    ACCESS      read-write
    STATUS      mandatory
    DESCRIPTION 
        "The entity that configured this entry and is
         therefore using the resources assigned to it.
         ALCATEL NOTE: the ALCATEL ISAM does not support this object."
    ::= { mediaIndependentEntry 30 }

mediaIndependentStatus OBJECT-TYPE
    SYNTAX      RowStatus
    ACCESS      read-write
    STATUS      mandatory
    DESCRIPTION 
        "The status of this media independent statistics entry.
         ALCATEL NOTE: the ALCATEL ISAM does not support this object."
    ::= { mediaIndependentEntry 31 }

mediaIndependentGroup OBJECT IDENTIFIER
    ::= { hcRmonMIBGroups 1 }

-- mediaIndependentGroup OBJECT-GROUP
--     OBJECTS     { mediaIndependentDataSource, 
--                   mediaIndependentDropEvents, 
--                   mediaIndependentDroppedFrames, 
--                   mediaIndependentInPkts, 
--                   mediaIndependentInOverflowPkts, 
--                   mediaIndependentInHighCapacityPkts, 
--                   mediaIndependentOutPkts, 
--                   mediaIndependentOutOverflowPkts, 
--                   mediaIndependentOutHighCapacityPkts, 
--                   mediaIndependentInOctets, 
--                   mediaIndependentInOverflowOctets, 
--                   mediaIndependentInHighCapacityOctets, 
--                   mediaIndependentOutOctets, 
--                   mediaIndependentOutOverflowOctets, 
--                   mediaIndependentOutHighCapacityOctets, 
--                   mediaIndependentInNUCastPkts, 
--                   mediaIndependentInNUCastOverflowPkts, 
--                   mediaIndependentInNUCastHighCapacityPkts, 
--                   mediaIndependentOutNUCastPkts, 
--                   mediaIndependentOutNUCastOverflowPkts, 
--                   mediaIndependentOutNUCastHighCapacityPkts, 
--                   mediaIndependentInErrors, mediaIndependentOutErrors, 
--                   mediaIndependentInputSpeed, 
--                   mediaIndependentOutputSpeed, 
--                   mediaIndependentDuplexMode, 
--                   mediaIndependentDuplexChanges, 
--                   mediaIndependentDuplexLastChange, 
--                   mediaIndependentOwner, mediaIndependentStatus }
--     STATUS      mandatory
--     DESCRIPTION 
--         "Collects utilization statistics for any type of network."
--     ::= { hcRmonMIBGroups 1 }

etherStatsHighCapacityGroup OBJECT IDENTIFIER
    ::= { hcRmonMIBGroups 2 }

-- etherStatsHighCapacityGroup OBJECT-GROUP
--     OBJECTS     { etherStatsHighCapacityOverflowPkts, 
--                   etherStatsHighCapacityPkts, 
--                   etherStatsHighCapacityOverflowOctets, 
--                   etherStatsHighCapacityOctets, 
--                   etherStatsHighCapacityOverflowPkts64Octets, 
--                   etherStatsHighCapacityPkts64Octets, 
--                   etherStatsHighCapacityOverflowPkts65to127Octets, 
--                   etherStatsHighCapacityPkts65to127Octets, 
--                   etherStatsHighCapacityOverflowPkts128to255Octets, 
--                   etherStatsHighCapacityPkts128to255Octets, 
--                   etherStatsHighCapacityOverflowPkts256to511Octets, 
--                   etherStatsHighCapacityPkts256to511Octets, 
--                   etherStatsHighCapacityOverflowPkts512to1023Octets, 
--                   etherStatsHighCapacityPkts512to1023Octets, 
--                   etherStatsHighCapacityOverflowPkts1024to1518Octets, 
--                   etherStatsHighCapacityPkts1024to1518Octets }
--     STATUS      mandatory
--     DESCRIPTION 
--         "Collects utilization statistics for ethernet networks."
--     ::= { hcRmonMIBGroups 2 }

etherHistoryHighCapacityGroup OBJECT IDENTIFIER
    ::= { hcRmonMIBGroups 3 }

-- etherHistoryHighCapacityGroup OBJECT-GROUP
--     OBJECTS     { etherHistoryHighCapacityOverflowPkts, 
--                   etherHistoryHighCapacityPkts, 
--                   etherHistoryHighCapacityOverflowOctets, 
--                   etherHistoryHighCapacityOctets }
--     STATUS      mandatory
--     DESCRIPTION 
--         "Collects utilization statistics for ethernet networks."
--     ::= { hcRmonMIBGroups 3 }

hostHighCapacityGroup OBJECT IDENTIFIER
    ::= { hcRmonMIBGroups 4 }

-- hostHighCapacityGroup OBJECT-GROUP
--     OBJECTS     { hostHighCapacityInOverflowPkts, 
--                   hostHighCapacityInPkts, 
--                   hostHighCapacityOutOverflowPkts, 
--                   hostHighCapacityOutPkts, 
--                   hostHighCapacityInOverflowOctets, 
--                   hostHighCapacityInOctets, 
--                   hostHighCapacityOutOverflowOctets, 
--                   hostHighCapacityOutOctets, 
--                   hostTimeHighCapacityInOverflowPkts, 
--                   hostTimeHighCapacityInPkts, 
--                   hostTimeHighCapacityOutOverflowPkts, 
--                   hostTimeHighCapacityOutPkts, 
--                   hostTimeHighCapacityInOverflowOctets, 
--                   hostTimeHighCapacityInOctets, 
--                   hostTimeHighCapacityOutOverflowOctets, 
--                   hostTimeHighCapacityOutOctets }
--     STATUS      mandatory
--     DESCRIPTION 
--         "Collects utilization and error statistics per host."
--     ::= { hcRmonMIBGroups 4 }

hostTopNHighCapacityGroup OBJECT IDENTIFIER
    ::= { hcRmonMIBGroups 5 }

-- hostTopNHighCapacityGroup OBJECT-GROUP
--     OBJECTS     { hostTopNHighCapacityAddress, 
--                   hostTopNHighCapacityBaseRate, 
--                   hostTopNHighCapacityOverflowRate, 
--                   hostTopNHighCapacityRate }
--     STATUS      mandatory
--     DESCRIPTION 
--         "Prepares sorted reports of utilization and error statistics
--          per host."
--     ::= { hcRmonMIBGroups 5 }

matrixHighCapacityGroup OBJECT IDENTIFIER
    ::= { hcRmonMIBGroups 6 }

-- matrixHighCapacityGroup OBJECT-GROUP
--     OBJECTS     { matrixSDHighCapacityOverflowPkts, 
--                   matrixSDHighCapacityPkts, 
--                   matrixSDHighCapacityOverflowOctets, 
--                   matrixSDHighCapacityOctets, 
--                   matrixDSHighCapacityOverflowPkts, 
--                   matrixDSHighCapacityPkts, 
--                   matrixDSHighCapacityOverflowOctets, 
--                   matrixDSHighCapacityOctets }
--     STATUS      mandatory
--     DESCRIPTION 
--         "Collects utilization statistics per conversation."
--     ::= { hcRmonMIBGroups 6 }

captureBufferHighCapacityGroup OBJECT IDENTIFIER
    ::= { hcRmonMIBGroups 7 }

-- captureBufferHighCapacityGroup OBJECT-GROUP
--     OBJECTS     { captureBufferPacketHighCapacityTime }
--     STATUS      mandatory
--     DESCRIPTION 
--         "Provides finer granularity time stamps."
--     ::= { hcRmonMIBGroups 7 }

protocolDistributionHighCapacityGroup OBJECT IDENTIFIER
    ::= { hcRmonMIBGroups 8 }

-- protocolDistributionHighCapacityGroup OBJECT-GROUP
--     OBJECTS     { protocolDistStatsHighCapacityOverflowPkts, 
--                   protocolDistStatsHighCapacityPkts, 
--                   protocolDistStatsHighCapacityOverflowOctets, 
--                   protocolDistStatsHighCapacityOctets }
--     STATUS      mandatory
--     DESCRIPTION 
--         "Collects the relative amounts of octets and packets for the
--          different protocols detected on a network segment."
--     ::= { hcRmonMIBGroups 8 }

nlHostHighCapacityGroup OBJECT IDENTIFIER
    ::= { hcRmonMIBGroups 9 }

-- nlHostHighCapacityGroup OBJECT-GROUP
--     OBJECTS     { nlHostHighCapacityInOverflowPkts, 
--                   nlHostHighCapacityInPkts, 
--                   nlHostHighCapacityOutOverflowPkts, 
--                   nlHostHighCapacityOutPkts, 
--                   nlHostHighCapacityInOverflowOctets, 
--                   nlHostHighCapacityInOctets, 
--                   nlHostHighCapacityOutOverflowOctets, 
--                   nlHostHighCapacityOutOctets }
--     STATUS      mandatory
--     DESCRIPTION 
--         "Counts the amount of traffic sent from and to each network
--          address discovered by the probe."
--     ::= { hcRmonMIBGroups 9 }

nlMatrixHighCapacityGroup OBJECT IDENTIFIER
    ::= { hcRmonMIBGroups 10 }

-- nlMatrixHighCapacityGroup OBJECT-GROUP
--     OBJECTS     { nlMatrixSDHighCapacityOverflowPkts, 
--                   nlMatrixSDHighCapacityPkts, 
--                   nlMatrixSDHighCapacityOverflowOctets, 
--                   nlMatrixSDHighCapacityOctets, 
--                   nlMatrixDSHighCapacityOverflowPkts, 
--                   nlMatrixDSHighCapacityPkts, 
--                   nlMatrixDSHighCapacityOverflowOctets, 
--                   nlMatrixDSHighCapacityOctets }
--     STATUS      mandatory
--     DESCRIPTION 
--         "Counts the amount of traffic sent between each pair of
--          network addresses discovered by the probe."
--     ::= { hcRmonMIBGroups 10 }

nlMatrixTopNHighCapacityGroup OBJECT IDENTIFIER
    ::= { hcRmonMIBGroups 11 }

-- nlMatrixTopNHighCapacityGroup OBJECT-GROUP
--     OBJECTS     { nlMatrixTopNHighCapacityProtocolDirLocalIndex, 
--                   nlMatrixTopNHighCapacitySourceAddress, 
--                   nlMatrixTopNHighCapacityDestAddress, 
--                   nlMatrixTopNHighCapacityBasePktRate, 
--                   nlMatrixTopNHighCapacityOverflowPktRate, 
--                   nlMatrixTopNHighCapacityPktRate, 
--                   nlMatrixTopNHighCapacityReverseBasePktRate, 
--                   nlMatrixTopNHighCapacityReverseOverflowPktRate, 
--                   nlMatrixTopNHighCapacityReversePktRate, 
--                   nlMatrixTopNHighCapacityBaseOctetRate, 
--                   nlMatrixTopNHighCapacityOverflowOctetRate, 
--                   nlMatrixTopNHighCapacityOctetRate, 
--                   nlMatrixTopNHighCapacityReverseBaseOctetRate, 
--                   nlMatrixTopNHighCapacityReverseOverflowOctetRate, 
--                   nlMatrixTopNHighCapacityReverseOctetRate }
--     STATUS      mandatory
--     DESCRIPTION 
--         "Prepares sorted reports of the amount of traffic sent between
--          each pair of network addresses discovered by the probe."
--     ::= { hcRmonMIBGroups 11 }

alHostHighCapacityGroup OBJECT IDENTIFIER
    ::= { hcRmonMIBGroups 12 }

-- alHostHighCapacityGroup OBJECT-GROUP
--     OBJECTS     { alHostHighCapacityInOverflowPkts, 
--                   alHostHighCapacityInPkts, 
--                   alHostHighCapacityOutOverflowPkts, 
--                   alHostHighCapacityOutPkts, 
--                   alHostHighCapacityInOverflowOctets, 
--                   alHostHighCapacityInOctets, 
--                   alHostHighCapacityOutOverflowOctets, 
--                   alHostHighCapacityOutOctets }
--     STATUS      mandatory
--     DESCRIPTION 
--         "Counts the amount of traffic, by protocol, sent from and to
--          each network address discovered by the probe."
--     ::= { hcRmonMIBGroups 12 }

alMatrixHighCapacityGroup OBJECT IDENTIFIER
    ::= { hcRmonMIBGroups 13 }

-- alMatrixHighCapacityGroup OBJECT-GROUP
--     OBJECTS     { alMatrixSDHighCapacityOverflowPkts, 
--                   alMatrixSDHighCapacityPkts, 
--                   alMatrixSDHighCapacityOverflowOctets, 
--                   alMatrixSDHighCapacityOctets, 
--                   alMatrixDSHighCapacityOverflowPkts, 
--                   alMatrixDSHighCapacityPkts, 
--                   alMatrixDSHighCapacityOverflowOctets, 
--                   alMatrixDSHighCapacityOctets }
--     STATUS      mandatory
--     DESCRIPTION 
--         "Counts the amount of traffic, by protocol, sent between each
--          pair of network addresses discovered by the
--          probe."
--     ::= { hcRmonMIBGroups 13 }

alMatrixTopNHighCapacityGroup OBJECT IDENTIFIER
    ::= { hcRmonMIBGroups 14 }

-- alMatrixTopNHighCapacityGroup OBJECT-GROUP
--     OBJECTS     { alMatrixTopNHighCapacityProtocolDirLocalIndex, 
--                   alMatrixTopNHighCapacitySourceAddress, 
--                   alMatrixTopNHighCapacityDestAddress, 
--                   alMatrixTopNHighCapacityAppProtocolDirLocalIndex, 
--                   alMatrixTopNHighCapacityBasePktRate, 
--                   alMatrixTopNHighCapacityOverflowPktRate, 
--                   alMatrixTopNHighCapacityPktRate, 
--                   alMatrixTopNHighCapacityReverseBasePktRate, 
--                   alMatrixTopNHighCapacityReverseOverflowPktRate, 
--                   alMatrixTopNHighCapacityReversePktRate, 
--                   alMatrixTopNHighCapacityBaseOctetRate, 
--                   alMatrixTopNHighCapacityOverflowOctetRate, 
--                   alMatrixTopNHighCapacityOctetRate, 
--                   alMatrixTopNHighCapacityReverseBaseOctetRate, 
--                   alMatrixTopNHighCapacityReverseOverflowOctetRate, 
--                   alMatrixTopNHighCapacityReverseOctetRate }
--     STATUS      mandatory
--     DESCRIPTION 
--         "Prepares sorted reports of the amount of traffic per protocol
--          sent between each pair of network addresses discovered by the
--          probe."
--     ::= { hcRmonMIBGroups 14 }

usrHistoryHighCapacityGroup OBJECT IDENTIFIER
    ::= { hcRmonMIBGroups 15 }

-- usrHistoryHighCapacityGroup OBJECT-GROUP
--     OBJECTS     { usrHistoryHighCapacityOverflowAbsValue, 
--                   usrHistoryHighCapacityAbsValue }
--     STATUS      mandatory
--     DESCRIPTION 
--         "Provides user-defined collection of historical information
--          from MIB objects on the probe with scalability to statistics
--          from high-capacity networks."
--     ::= { hcRmonMIBGroups 15 }

hcRMONInformationGroup OBJECT IDENTIFIER
    ::= { hcRmonMIBGroups 16 }

-- hcRMONInformationGroup OBJECT-GROUP
--     OBJECTS     { hcRMONCapabilities }
--     STATUS      mandatory
--     DESCRIPTION 
--         "An indication of the high capacity RMON groups supported on
--          at least one interface by this probe."
--     ::= { hcRmonMIBGroups 16 }

hcMediaIndependentCompliance OBJECT IDENTIFIER
    ::= { hcRmonMIBCompliances 1 }

-- hcMediaIndependentCompliance MODULE-COMPLIANCE
--     STATUS      mandatory
--     DESCRIPTION 
--         "Describes the requirements for conformance to the
--          High Capacity Media Independent Group."

--     MODULE      -- -- this module

--         MANDATORY-GROUPS        { mediaIndependentGroup, 
--                   hcRMONInformationGroup }

--     ::= { hcRmonMIBCompliances 1 }

hcRmon2MIBCompliance OBJECT IDENTIFIER
    ::= { hcRmonMIBCompliances 3 }

-- hcRmon2MIBCompliance MODULE-COMPLIANCE
--     STATUS      mandatory
--     DESCRIPTION 
--         "Describes the requirements for conformance to
--          the High Capacity RMON-2 MIB"

--     MODULE      -- -- this module

--         MANDATORY-GROUPS        { 
--                   protocolDistributionHighCapacityGroup, 
--                   nlHostHighCapacityGroup, nlMatrixHighCapacityGroup, 
--                   nlMatrixTopNHighCapacityGroup, 
--                   usrHistoryHighCapacityGroup, hcRMONInformationGroup }

--     MODULE      RMON2-MIB

--         MANDATORY-GROUPS        { protocolDirectoryGroup, 
--                   protocolDistributionGroup, addressMapGroup, 
--                   nlHostGroup, nlMatrixGroup, usrHistoryGroup, 
--                   probeInformationGroup }

--         GROUP   rmon1EnhancementGroup
--         DESCRIPTION   
--               "The rmon1EnhancementGroup is mandatory for systems which
--                implement RMON [RFC2819]"

--     ::= { hcRmonMIBCompliances 3 }

hcRmon2MIBApplicationLayerCompliance OBJECT IDENTIFIER
    ::= { hcRmonMIBCompliances 4 }

-- hcRmon2MIBApplicationLayerCompliance MODULE-COMPLIANCE
--     STATUS      mandatory
--     DESCRIPTION 
--         "Describes the requirements for conformance to
--          the High Capacity RMON-2 MIB with Application Layer
--          Enhancements."

--     MODULE      -- -- this module

--         MANDATORY-GROUPS        { 
--                   protocolDistributionHighCapacityGroup, 
--                   nlHostHighCapacityGroup, nlMatrixHighCapacityGroup, 
--                   nlMatrixTopNHighCapacityGroup, 
--                   alHostHighCapacityGroup, alMatrixHighCapacityGroup, 
--                   alMatrixTopNHighCapacityGroup, 
--                   usrHistoryHighCapacityGroup, hcRMONInformationGroup }

--     MODULE      RMON2-MIB

--         MANDATORY-GROUPS        { protocolDirectoryGroup, 
--                   protocolDistributionGroup, addressMapGroup, 
--                   nlHostGroup, nlMatrixGroup, alHostGroup, 
--                   alMatrixGroup, usrHistoryGroup, 
--                   probeInformationGroup }

--         GROUP   rmon1EnhancementGroup
--         DESCRIPTION   
--               "The rmon1EnhancementGroup is mandatory for systems which
--                implement RMON [RFC2819]"

--     ::= { hcRmonMIBCompliances 4 }

END -- end of module HC-RMON-MIB.
