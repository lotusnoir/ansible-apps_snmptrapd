QOS-MIB DEFINITIONS ::= BEGIN
-- ===========================================================================
--  This specification is published by Alcatel-Lucent under Non-Disclosure
--  Agreement(s) (NDA) with specific parties and has to be considered as
--  Confidential Information as defined in such NDA.
--  Alcatel-Lucent reserves the right to revise this document for any reason,
--  including but not limited to conformity with standards promulgated by
--  various agencies, utilisation of advances in the state of the technical
--  areas, or the reflection of changes in the design of any equipment,
--  techniques, or procedures described or referred to herein.
--  The product specifications and other technical or performance information
--  contained herein are subject to change without notice.
--  Updates of this document will be issued under the above NDA's.
--  Alcatel-Lucent makes no representation or warranty, expressed or implied,
--  with respect to the sufficiency, accuracy, or utility of any information
--  or opinion contained herein. Alcatel-Lucent expressly advises that any use
--  of for any purpose or reliance upon this technical reference is at the
--  risk of the user and that Alcatel-Lucent shall not be liable for any
--  damage or injury incurred by any person arising out of the sufficiency,
--  accuracy, or utility of any information or opinion contained herein.
--  This document is not to be construed as a suggestion to any manufacturer
--  to modify or change any of its products, nor does this document represent
--  any commitment by Alcatel-Lucent to sell or purchase any product.
--  Nothing contained herein shall be construed as conferring by implication,
--  estoppel, or otherwise any license or right under any patent, whether or
--  not the use of any information herein necessarily employs an invention of
--  any existing or later issued patent.
--  Alcatel-Lucent reserves the right not to offer any or all of these
--  products and to withdraw any or all of them at any future time.
--  Copyright (C) 2004 Alcatel-Lucent. All Rights Reserved.
-- ===========================================================================

--  MODULE IDENTITY
--  LAST-UPDATED "201511270000Z"
--  ORGANIZATION "Alcatel-Lucent"
--  CONTACT-INFO "email:asam.mibsupport@alcatel-lucent.com"
--  DESCRIPTION
--     "The QOS MIB allows to manage all QOS settings in the ISAM"
--
--  REVISION "201704240000Z"
--  DESCRIPTION
--   "Version 3FE22870EAAA VX.X.Y.Y.Z
--  Editor: Koen Decroix
--  Comment:
--  FR ALU02349999: correct DEFVALUE in the Alcatel note of qosBandwidthProfileDBRu to be
--  consistent with the new default value introduced with ALU02335923.
--
--  REVISION "201702210000Z"
--  DESCRIPTION
--   "Version 3FE22870EAAA VX.X.Y.Y.Z
--   Editor: Koen Decroix
--   Comment:
--   Change the default value qosBandwidthProfileDBRu to 'enabled if supported' for enabling
--   the DBA DBRu algorithm on NG-PON2 by default (ALU02335923).  DBA DBRu is now an
--   officially supported feature on NG-PON2 starting from isr5601.
--
--  REVISION "201607180000Z"
--  DESCRIPTION
--    "Version: 3FE22870EAAA VX.X.Y.Y.Z
--    Editor: Huang jianfeng
--    Comment:
--    Add qosPolicyActionMirrorVlan to the QosPolicyActionEntry for supporting mirror vlan.
--    Add qosVlanPortColorTroubleshootTable to show QoS color aware counter.
--    for RCR ALU02093360.
--
--  REVISION "201605300000Z"
--  DESCRIPTION
--    "Version: 3FE22870EAAA VX.X.Y.Y.Z
--    Editor: Koen Decroix
--    Comment:
--    Add item qosBandwidthProfileDBRu to the qosBandwidthProfileEntry for supporting DBRu
--    on NG_PON2 (ALU02008407).
--
--  REVISION “201603300000Z”
--  DESCRIPTION
--     "Version: 3FE22870EAAA_VX.X.Y.Y.Z
--      Editor: Yang D Xu
--      Comment:
--      Add item qosDslRecordDsSchedulerPbitTag in qosDslRecordTable for S/C pbit scheduler.
--	Add new table qosLimColorBasedQueueStatsP15mTable and qosLimColorBasedQueueStatsC15mTable
--	for color based queue counter.
--
--  REVISION “201509070000Z”
--  DESCRIPTION
--     “Version: 3FE22870EAAA VX.X.Y.Y.Z
--      Editor: Pradeep Kumar Gajula
--      Comment:
--      Document updated for adding new OIDs for the RCR ALU02073522: Actual Queue 
--      Load monitoring and TCA alarm.
--      Following tables added with new OIDs:
--      qosLimQueueStatsP15mQueueMaxUsage, qosLimQueueStatsP15mValidIntervalFlag in 
--      the qosLimQueueStatsP15mTable, qosLimQueueStatsC15mQueueMaxUsage,  
--      qosLimQueueStatsC15mValidIntervalFlag in the qosLimQueueStatsC15mTable, 
--      qosQueueStatsQueuePeakUsageThreshold in the qosQueueStatsTcaTable, 
--      qosFanOutLoadStatsP15mValidIntervalFlag in the qosFanOutLoadStatsP15mTable, 
--      qosFanOutLoadStatsC15mValidIntervalFlag in the qosFanOutLoadStatsC15mTable, 
--      qosFanOutLoadStatsP1dValidIntervalFlag in the qosFanOutLoadStatsP1dTable, 
--      qosFanOutLoadStatsC1dValidIntervalFlag in the qosFanOutLoadStatsC1dTable, 
--      qosStatsP15mValidIntervalFlag in the qosStatsP15mTable, 
--      qosStatsC15mValidIntervalFlag in the qosStatsC15mTable, 
--      qosStatsP1dValidIntervalFlag in the qosStatsP1dTable, 
--      qosStatsC1dValidIntervalFlag in the qosStatsC1dTable.
--
--  REVISION “201506240000Z”
--  DESCRIPTION
--     "Version: 3FE22870EAAA_VX.X.Y.Y.Z
--      Editor: Feima Luo
--      Comment:
--      Modify the range for qosPolicerProfileGreenAction to 1,3,4 in policer profile 

--  REVISION "201506180000Z"
--  DESCRIPTION
--     "Version: 3FE22870EAAA_VX.X.Y.Y.Z
--      Editor: Siva S Reddy
--      Comment:
--      Added new table qosBandwidthProfileActualValuesTable to retrieve 
--      adjusted bandwidth profile values compared to configured values.
--      Refer to FR ALU02086934  for more information.  
--
--  REVISION "201505120000Z"
--  DESCRIPTION
--     "Version: 3FE22870EAAA_VX.X.Y.Y.Z
--      Editor: Feima Luo
--      Comment:
--      Delete the one parameter in session profile: qosSessionProfileOuterMarking.

--  REVISION "201411250000Z"
--  DESCRIPTION
--     "Version: 3FE22870EAAA_VX.X.Y.Y.Z
--      Editor: Feima Luo
--      Comment:
--      Extend the session profile with two parameters: qosSessionProfileIngOuterMarkerProfileId 
--      and qosSessionProfileOuterMarking. 
--      These two parameters define marking behavior of S+C forwarder.
--
--  REVISION "201409050000Z"
--  DESCRIPTION
--     "Version: 3FE22870EAAA_VX.X.Y.Y.Z
--      Editor: Feima Luo
--      Comment:
--      Add CoSThresholdProfile to configure tc0-tc7 threshold, 
--      extend ingress-qos profile with new parameter: qosIngressQoSProfileTc 
--      extend policer profile with new parameter: qosPolicerProfilePIR, qosPolicerProfilePBS
--      and qosPolicerProfileCoSThresholdProfileIndex.
--
--  REVISION "201407030000Z"
--  DESCRIPTION
--     "Version: 3FE22870EAAA_VX.X.Y.Y.Z
--      Editor: Karel Meijfroidt
--      Changes:
--      * Replace TimeTicks type with INTEGER type for MeasuredTime and
--        ElapseTime MIB objects since the values are expressed in seconds"
--
--  REVISION "201402270000Z"
--  DESCRIPTION
--     "Version: 3FE22870EAAA_VX.X.Y.Y.Z
--      Editor: karthikeyan visvanathan
--      Changes: RCR ALU01818095 for R5.1
--      * Add qosDslControlProtocolCtrl to qosGlobalDslPolicerSettings table."             
--
--  REVISION "201311180000Z"
--  DESCRIPTION
--     "Version: 3FE22870EAAA_VX.X.Y.Y.Z
--      Editor: xiangdong a wang
--      Changes: RCR ALU01908578.
--      * The following profile parameter is added in qosPolicerProfileTable
--        qosPolicerProfilePolicedFrameControl"            
--
--  REVISION "201309090000Z"
--  DESCRIPTION
--     "Version: 3FE22870EAAA_VX.X.Y.Y.Z
--      Editor: Sabine Denies
--      Changes: RCR ALU01777158
--      * ADDED qosResourceUsageTable .47.7.20"
--
--  REVISION "201303120000Z"
--  DESCRIPTION
--     "Version: 3FE22870EAAA_VX.X.Y.Y.Z
--      Editor: Sabine Denies
--      Changes: RCR ALU01794042
--      * Definition of qosL3FilterTable"
--
--  REVISION "201210310000Z"
--  DESCRIPTION
--     "Version: 3FE22870EAAA_VX.X.Y.Y.Z
--      Editor: Udaya Sivadanam
--      Changes: FR: ALU01811395
--      * Change the default value qosLimUpstreamQueueWeight from 10 to 1"
--
--  REVISION "201209110000Z"
--  DESCRIPTION
--     "Version: 3FE22870EAAA_VX.X.Y.Y.Z
--      Editor: Peter Barri
--      Changes:
--      * New objects within qosQueueProfileTable
--      * Update descriptions within qosLimQueueConfigTable
--        feature reference : ALU01234731"
--
--  REVISION "201209110000Z"
--  DESCRIPTION
--     "Version: 3FE22870EAAA_VX.X.Y.Y.Z
--      Editor: XiaoJuan Zhang
--      Changes:
--      * update for R4.5 ALU01630820, upstream stream rate limit control 
--        qosLimUpstreamQueueShaperProfileId added in QosLimUpstreamQueueConfigEntry"
--
--  REVISION "201208310000Z"
--  DESCRIPTION
--     "Version: 3FE22870EAAA_VX.X.Y.Y.Z
--      Editor: Udaya Sivadanam, John Boyle
--      Changes: For ISAM4.5 - RCR ALU01821388 MIB Readiness for RCR ALU00424117
--      * Support for multiple DSCP to pbit mapping profiles
--	    * Added qosDscpToDot1PAlignProfileTable at { qosProfiles 27 } OID
--	    * Added qosDscpToDot1PAlignProfileMappingTable at { qosProfiles 28 } OID
--	    * Added qosDscpToDot1PAlignProfileTableGetNextFree scalar at { qosSystemGroup 16 } OID
--	    * Added qosMarkerProfileDscpToDot1PAlignProfileId attribute to qosMarkerProfileTable
--        at { qosMarkerProfileEntry 11 } OID
--      * For qosMarkerProfileType attribute in qosMarkerProfileTable, supplemented existing
--        comments with following:
--        'The type 'DscpToDot1Palignment' means DSCP to Dot1P alignment should
--        be applied. The alignment strategy depends on the setting of
--        qosMarkerProfileDscpToDot1PAlignProfileId. If this pointer is null, then
--        sytem-wide qosDscpToDot1PAlignmentTable is used. Otherwise, the referenced
--        row in qosDscpToDot1PAlignProfileTable applies.'"
--
--  REVISION "201308310000Z"
--  DESCRIPTION
--     "Version: 3FE22870EAAA_VX.X.Y.Y.Z
--      Editor: Sireesha Kora
--      Changes: ISR45 - ALU01819721"
--
--  REVISION "201202170000Z"
--  DESCRIPTION
--     "Version: 3FE22870EAAA_VX.X.Y.Y.Z
--      Editor: Ting Shieh
--      Changes: ALU00204703 fix.
--      * The following profile parameters are not applicable to Single Token Bucket
--        Policer profile
--        qosPolicerProfileEIR            
--        qosPolicerProfileEBS            
--        qosPolicerProfileCF             
--        qosPolicerProfileCM             
--        qosPolicerProfileGreenAction    
--        qosPolicerProfileYellowAction   
--        qosPolicerProfileRedAction"     
--
--  REVISION "201110270000Z"
--  DESCRIPTION
--     "Version: 3FE22870EAAA_VX.X.Y.Y.Z
--      Editor: Udaya Sivadanam
--      Changes:
--      * Add a new object qosOntUniGemSharingEnable in QosDslRecordEntry for ALU00204703."
--
--  REVISION "201102140000Z"
--  DESCRIPTION
--     "Version: 3FE22870EAAA_VX.X.Y.Y.Z
--      Editor: Pankaj Verma
--      Changes: Implemented RCR: ALU00205645 for ISR 4.3
--      * Add qosLimUpstreamQueueProfileId to qosLimUpstreamQueueConfigTable"
--
--  REVISION "201101260000Z"
--  DESCRIPTION
--     "Version: 3FE22870EAAA_VX.X.Y.Y.Z
--      Editor: Sun Baoping
--      Changes:
--      * for R4.2.20, in policer profile, remove dot1p and dscp which are never supported.
--        Replace them with markerProfileIndex."
--
--  REVISION "201006260000Z"
--  DESCRIPTION
--     "Version: 3FE22870EAAA_VX.X.Y.Y.Z
--      Editor: MA Liya
--      Changes: Updated for R4.2.20 EPON Convergency"
-- 
--  REVISION "201006170000Z"
--  DESCRIPTION
--     "Version: 3FE22870EAAA_VX.X.Y.Y.Z
--      Editor: Paul Reynders
--      Changes: Updated for RAC for unicast video"
-- 
--  REVISION "200912030000Z"
--  DESCRIPTION
--     "Version: 3FE22870EAAA_VX.X.Y.Y.Z
--      Editor: Wang Jinwang; Lv gang; Zhuzhaozhong
--      Changes: Updated for ISR 4.2"
-- 
--  REVISION "200908280000Z"
--  DESCRIPTION
--     "Version: 3FE22870EAAA_VX.X.Y.Y.Z
--      Editor: Gopal Surya
--      Changes: Updated for ISR 4.0.10"
-- 
--  REVISION "200905040000Z"
--  DESCRIPTION
--     "Version: 3FE22870EAAA_VX.X.Y.Y.Z
--      Editor: MA Liya
--      Changes:
--      * Implemented ANTmt30916: 8 Queue support on IFX"
--
--  REVISION "200708270000Z"
--  DESCRIPTION
--     "Version: 3FE22870EAAA_VX.X.Y.Y.Z
--      Editor: Liu Li
--      Changes: ANTms13608
--      * Add a new uniform flow type for all IPoA forwarders including IPoA E-IBridge,
--        IPoA CC and IPoA Termination"
--
--  REVISION "200601230000Z"
--  DESCRIPTION
--     "Version: 3FE22870EAAA_VX.X.Y.Y.Z
--      Editor: Bart Bogaert
--      Changes:
--      * Implemented BDFhw70643: strict syntax checks (smilint)"
--
--  REVISION "200505010000Z"
--  DESCRIPTION
--     "Version: 3FE22870EAAA_VX.X.Y.Y.Z
--      Editor: Lu Shun
--      Changes: BDFhw27332"
--
--  REVISION "200410150000Z"
--  DESCRIPTION
--     "Version: 3FE22870EAAA_VX.X.Y.Y.Z
--      Editor: Lu SHUN
--      Changes: BDFhw24610
--      * Qos Mark profile is extended to apply DSCP remark.
--      * New flow type ipSession is appended in QosLfDefinitionType
--      * add qosDscpDot1PAlignmentTable in qos MIB"
--

IMPORTS
	Gauge   	FROM RFC1155-SMI
        Counter  	FROM RFC1155-SMI
       	OBJECT-TYPE     FROM RFC-1212
       	asam 		FROM SYSTEM-MIB
       	RowStatus, TruthValue       FROM SNMPv2-TC
        --Unsigned32	FROM SNMPv2-SMI
       	InterfaceIndex  FROM ITF-MIB
        ifIndex  FROM ITF-MIB

        InetAddressIPv4 	FROM INET-ADDRESS-MIB
        InetAddressIPv6     	FROM INET-ADDRESS-MIB
        InetAddressPrefixLength  FROM INET-ADDRESS-MIB
        InetPortNumber           FROM INET-ADDRESS-MIB

	ExtendVlanSystemPriority FROM PLIM-ETHERNET-MIB
       	DisplayString        FROM RFC1213-MIB
	eqptSlotId           FROM ASAM-EQUIP-MIB
       	AsamProfileIndex     FROM ASAM-TC-MIB
        AsamProfilePointer   FROM ASAM-TC-MIB
       	AsamProfileName      FROM ASAM-TC-MIB
        AsamProfileRefCount  FROM ASAM-TC-MIB
        AsamProfileRefCount32  FROM ASAM-TC-MIB
        MacAddress	     FROM SNMPv2-TC 
	NetworkTimeInSeconds FROM ASAM-TC-MIB;  
		


-- Remove these definitions if conflicted
-- ExtendVlanSystemPriority ::= INTEGER (0..7)
DscpValue ::= INTEGER (0..63)
DscpOrAny ::= INTEGER (-1|0 .. 63)
Uint32 ::= Gauge (0..4294967295) -- a 32 bit unsigned integer

qosMIB       OBJECT IDENTIFIER ::= { asam 47 } 
-- qosSystemGroup containing next free index pointers
qosSystemGroup OBJECT IDENTIFIER ::= {qosMIB 1}

qosSessionProfileGetNextFree OBJECT-TYPE
	SYNTAX INTEGER
	ACCESS read-only
	STATUS mandatory
	DESCRIPTION
	"This object contains an appropriate value to
	be used for qosSessionProfileEntry when creating
	entries in the qosSessionProfileTable. The value
	0 indicates that no unassigned entries are
	available"
::= { qosSystemGroup 1 }
qosMarkerProfileGetNextFree OBJECT-TYPE
	SYNTAX INTEGER
	ACCESS read-only
	STATUS mandatory
	DESCRIPTION
	"This object contains an appropriate value to
	be used for qosMarkerProfileEntry when creating
	entries in the qosMarkerProfileTable. The value
	0 indicates that no unassigned entries are
	available"
::= { qosSystemGroup 2 }
qosPolicerProfileGetNextFree OBJECT-TYPE
	SYNTAX INTEGER
	ACCESS read-only
	STATUS mandatory
	DESCRIPTION
	"This object contains an appropriate value to
	be used for qosPolicerProfileEntry when creating
	entries in the qosPolicerProfileTable. The value
	0 indicates that no unassigned entries are
	available"
::= { qosSystemGroup 3 }

qosQueueProfileGetNextFree OBJECT-TYPE
	SYNTAX INTEGER
	ACCESS read-only
	STATUS mandatory
	DESCRIPTION
	"This object contains an appropriate value to
	be used for qosQueueProfileEntry when creating
	entries in the qosQueueProfileTable. The value
	0 indicates that no unassigned entries are
	available"
::= { qosSystemGroup 4 }

qosSchedulerProfileGetNextFree OBJECT-TYPE
	SYNTAX INTEGER
	ACCESS read-only
	STATUS mandatory
	DESCRIPTION
	"This object contains an appropriate value to
	be used for qosSchedulerProfileEntry when creating
	entries in the qosSchedulerProfileTable. The value
	0 indicates that no unassigned entries are
	available"
::= { qosSystemGroup 5 }

qosCacProfileGetNextFree OBJECT-TYPE
	SYNTAX INTEGER
	ACCESS read-only
	STATUS mandatory
	DESCRIPTION
	"This object contains an appropriate value to
	be used for qosCacProfileEntry when creating
	entries in the qosCacProfileTable. The value
	0 indicates that no unassigned entries are
	available"
::= { qosSystemGroup 6 }

-- ============================================================================

qosPolicyTableGetNextFree OBJECT-TYPE
    SYNTAX  INTEGER
    ACCESS  read-only
    STATUS  mandatory
    DESCRIPTION
           "This object contains an appropriate value to
            be used for qosPolicyEntry when creating
            entries in the qosPolicyTable. The value
            0 indicates that no unassigned entries are
            available"
    ::= {  qosSystemGroup 7 }

qosL2FilterTableGetNextFree OBJECT-TYPE
    SYNTAX  INTEGER
    ACCESS  read-only
    STATUS  mandatory
    DESCRIPTION
           "This object contains an appropriate value to
            be used for qosL2FilterEntry when creating
            entries in the qosL2FilterTable. The value
            0 indicates that no unassigned entries are
            available"
    ::= {  qosSystemGroup 8 }

qosL3FilterTableGetNextFree OBJECT-TYPE
    SYNTAX  INTEGER
    ACCESS  read-only
    STATUS  mandatory
    DESCRIPTION
           "This object contains an appropriate value to
            be used for qosL3FilterEntry when creating
            entries in the qosL3FilterTable. The value
            0 indicates that no unassigned entries are
            available"
    ::= {  qosSystemGroup 9 }

qosPolicyActionTableGetNextFree OBJECT-TYPE
    SYNTAX  INTEGER
    ACCESS  read-only
    STATUS  mandatory
    DESCRIPTION
           "This object contains an appropriate value to
            be used for qosPolicyActionEntry when creating
            entries in the qosPolicyActionTable. The value
            0 indicates that no unassigned entries are
            available"
::= {  qosSystemGroup 10 }

qosShaperProfileTableGetNextFree OBJECT-TYPE
    SYNTAX  INTEGER
    ACCESS  read-only
    STATUS  mandatory
    DESCRIPTION
           "This object contains an appropriate value to
            be used for qosShaperProfileEntry when creating
            entries in the qosShaperProfileTable. The value
            0 indicates that no unassigned entries are
            available
      ALCATEL NOTE:
                 ACCESS:     NA       USAGE:      NA
                 PERSIST:    NO       INSRVMOD:   NO
                 RANGE:      NA       DEFVALUE:   NA
                 UNITS:      NA       SPARSE:     NA
                 DESCR:      NA "
    ::= {  qosSystemGroup 11 }

qosBandwidthProfileTableGetNextFree OBJECT-TYPE
    SYNTAX  INTEGER
    ACCESS  read-only
    STATUS  mandatory
    DESCRIPTION
           "This object contains an appropriate value to
            be used for qosBandwidthProfileEntry when creating
            entries in the qosBandwidthProfileTable. The value
            0 indicates that no unassigned entries are
            available
      ALCATEL NOTE:
                 ACCESS:     NA       USAGE:      NA
                 PERSIST:    NO       INSRVMOD:   NO
                 RANGE:      NA       DEFVALUE:   NA
                 UNITS:      NA       SPARSE:     NA
                 DESCR:      NA "
    ::= {  qosSystemGroup 12 }

qosSchedulerNodeProfileTableGetNextFree OBJECT-TYPE
    SYNTAX  INTEGER
    ACCESS  read-only
    STATUS  mandatory
    DESCRIPTION
           "This object contains an appropriate value to
            be used for qosSchedulerNodeProfileEntry when creating
            entries in the qosSchedulerNodeProfileTable. The value
            0 indicates that no unassigned entries are
            available
      ALCATEL NOTE:
                 ACCESS:     NA       USAGE:      NA
                 PERSIST:    NO       INSRVMOD:   NO
                 RANGE:      NA       DEFVALUE:   NA
                 UNITS:      NA       SPARSE:     NA
                 DESCR:      NA "
    ::= {  qosSystemGroup 13 }

qosIngressQosProfileTableGetNextFree OBJECT-TYPE
    SYNTAX  INTEGER
    ACCESS  read-only
    STATUS  mandatory
    DESCRIPTION
           "This object contains an appropriate value to
            be used for qosIngressQosProfileEntry when creating
            entries in the qosIngressQosProfileTable. The value
            0 indicates that no unassigned entries are
            available
      ALCATEL NOTE:
                 ACCESS:     NA       USAGE:      NA
                 PERSIST:    NO       INSRVMOD:   NO
                 RANGE:      NA       DEFVALUE:   NA
                 UNITS:      NA       SPARSE:     NA
                 DESCR:      NA "
    ::= {  qosSystemGroup 14 }

qosRateLimitProfileTableGetNextFree OBJECT-TYPE
    SYNTAX  INTEGER
    ACCESS  read-only
    STATUS  mandatory
    DESCRIPTION
           "This object contains an appropriate value to
            be used for qosRateLimitProfileEntry when creating
            entries in the qosRateLimitProfileTable. The value
            0 indicates that no unassigned entries are
            available
      ALCATEL NOTE:
                 ACCESS:     NA       USAGE:      NA
                 PERSIST:    NO       INSRVMOD:   NO
                 RANGE:      NA       DEFVALUE:   NA
                 UNITS:      NA       SPARSE:     NA
                 DESCR:      NA "
    ::= {  qosSystemGroup 15 }
    
qosDscpToDot1PAlignProfileTableGetNextFree OBJECT-TYPE
    SYNTAX  INTEGER
    ACCESS  read-only
    STATUS  mandatory
    DESCRIPTION
           "This object contains an appropriate value to
            be used for qosDscpToDot1PAlignProfileEntry when creating
            entries in the qosDscpToDot1PAlignProfileTable. The value
            0 indicates that no unassigned entries are
            available
    ALCATEL NOTE:
                 ACCESS:     NA       USAGE:      NA
                 PERSIST:    NO       INSRVMOD:   NO
                 RANGE:      NA       DEFVALUE:   NA
                 UNITS:      NA       SPARSE:     NA
                 DESCR:      NA "
    ::= {  qosSystemGroup 16 }

qosResourceAllocMode OBJECT-TYPE
      SYNTAX INTEGER {
         ipv4 (1),
         ipv6 (2) 
                     }
      ACCESS  read-write
      STATUS  mandatory
      DESCRIPTION
         "This object allows the manager to configure the qos resource allocation mode with regard to ip addresses. 
Value 'ipv4' implies : only IPV4 addresses can be used.  
Value 'ipv6' implies : both IPV4 and IPV6 addresses can be used.
Usage is board type specific.
          ALCATEL NOTE:
             SUPPORT: YES   INSRVMOD: YES           RANGE: 1..2
             PERSIST: YES   DEFVALUE: 1     UNITS: NA
             DESCR: Only applicable for NELT-B. This parameter can be used to tweak the allocation mode for QoS policies. In Ipv6 mode you can configure IPV4-L3, IPV6-L3 and COMMON-L3 policies, while in Ipv4 mode you can configure IPv4-L3 and COMMON-L3 
policies. In Ipv4 mode the resource allocation allows for a higher dimensioning in terms of policies. In Ipv6 mode the resource allocation is restricted to a lower dimensioning"
      ::= { qosSystemGroup 17 }

-- Added by Luo Feima
qosCoSThresholdProfileGetNextFree   OBJECT-TYPE             
    SYNTAX INTEGER
    ACCESS read-only
    STATUS mandatory
    DESCRIPTION
        "This object contains an appropriate value to
        be used for qosCoSThresholdProfileEntry when
        creating entries in the qosCoSThresholdProfileTable. 
        The value 0 indicates that no unassigned entries
        are	available"
::= { qosSystemGroup 18 }
-- Added by Luo Feima end.

qosPolicerPerTcProfileGetNextFree   OBJECT-TYPE             
    SYNTAX INTEGER
    ACCESS read-only
    STATUS mandatory
    DESCRIPTION
        "This object contains an appropriate value to
        be used for qosTcPolicerListProfileEntry when
        creating entries in the qosPolicerPerTcProfileTable. 
        The value 0 indicates that no unassigned entries
        are available"
::= { qosSystemGroup 19 }
-- Added for RCR ALU01961528
-- ============================================================================

qosAggrQueuesConfigProfileTableGetNextFree OBJECT-TYPE
    SYNTAX  INTEGER
    ACCESS  read-only
    STATUS  mandatory
    DESCRIPTION
           "This object contains an appropriate value to
            be used for qosAggrQueuesConfigProfileEntry when creating
            entries in the qosAggrQueuesConfigProfileTable. The value
            0 indicates that no unassigned entries are available.
      ALCATEL NOTE:
                 ACCESS:     NA       USAGE:      NA
                 PERSIST:    NO       INSRVMOD:   NO
                 RANGE:      NA       DEFVALUE:   NA
                 UNITS:      NA       SPARSE:     NA
                 DESCR:      NA "
    ::= {  qosSystemGroup 20 }

-- Macro Profiles
qosMacroProfiles OBJECT IDENTIFIER ::= {qosMIB 2}
--Session Profiles

qosSessionProfileTable OBJECT-TYPE
	SYNTAX	SEQUENCE OF QosSessionProfileEntry
	ACCESS	not-accessible
	STATUS	mandatory
	DESCRIPTION
	"This object contains a table for creating and storing
	QoS Session Profiles. Session profiles contain information
	on the bandwidth, traffic class and marking applicable on
	the session. Most objects in this table are references to
	other profiles stored in other MIB tables"
::= { qosMacroProfiles 1 }
qosSessionProfileEntry OBJECT-TYPE
	SYNTAX 	QosSessionProfileEntry
	ACCESS	not-accessible
	STATUS mandatory
	DESCRIPTION
	"Each entry contains the data of one QoS session
	profile.Session profiles are also called macro profiles,
	because they also call on other profiles, not only plain
	objects."
	INDEX	{qosSessionProfileIndex }
	::= {qosSessionProfileTable 1}

QosLfDefinitionType ::= INTEGER (0..19)
--{
--	generic (0),
--	pvc (1),			
--	dot1XSession (2),
--	pvcVlanCombination (3),
--	pvcVlanDot1Pcombination (4),
--	pppSession (5),
--	ipSession (6),
--	ipoeVlanCC (7),
--	pppoeVlanCC (8),
--	IPoACC (9),
--      PPPoACC (10),
--	IPoEIBridge (11),
--	PPPoEIBridge (12),
--	PPPoARelay (13),
--	PPPoERelayWithMacConcentration (14),
--	IPoEIPAwareBridge (15),
--	IPoAIPAwareBridge (16),
--	PPPoETermination (17),
--	PPPoATermination (18),
--      IPoAForwarder(19)
--}

PolicyList ::= OCTET STRING ( SIZE (32))
--        "Each octet within this value specifies a set of eight
--        policies, with the first octet specifying policies 1 through
--        8, the second octet specifying polcies 9 through 16, etc.
--        Within each octet, the most significant bit represents
--        the lowest numbered policy, and the least significant bit
--        represents the highest numbered policy.  Thus, each policy
--        is represented by a single bit within the
--        value of this object.  If that bit has a value of '1'
--        then that policy is included in the set of policies; the policy
--        is not included if its bit has a value of '0'."


Counter64bit ::= OCTET STRING (SIZE (8))
--        "Within octet string, the most significant bit of highest byte represents
--        the most significant bit of a 64 bit integer, and the least significant  
--		  bit of lowest byte represents the least significant bit of a 64 bit     
--        integer. The value range is from 0 to 18446744073709551615"

QosColourType ::= INTEGER (0..2)
--{
--	green (0),
--	yellow (1),
--      red (2)
--}

SchedulerModeType::= INTEGER (1..3)
--{
--   subscriber-hierarchy(1),
--   service-hierarchy(2),
--   service-flat(3),
--}

SchedulerType::= INTEGER (1..3)
--{
--   cVLANTagbased(1),
--   sVLANTagbased(2),
--   egressOuterTag(3)
--}

DsQueueSharingType ::= INTEGER (1..3)
--{
--    ONT (1),
--    UNI (2),
--    VlanPort (3)
--}

QosGemSharing ::= INTEGER (1..3)
--{
--    Enabled (1)
--    Disabled (2)
--    notApplicable (3)
--}

PolicerPerTcList ::= OCTET STRING ( SIZE (16))
--        "The policerId corresponding to TC 0 is indicated in bytes 0-1, 
--        the policerId corresponding to TC 1 in indicated in bytes 2-3, 
--        etc... "

QosSessionProfileEntry ::=
     SEQUENCE { qosSessionProfileIndex 			AsamProfileIndex,
		qosSessionProfileName 			AsamProfileName,
		qosSessionProfileVersion		INTEGER,
		qosSessionProfileRefCount		AsamProfileRefCount32,
		qosSessionProfileLogFlowType		QosLfDefinitionType,
		qosSessionProfileUpPolProfileId 	AsamProfilePointer,
		qosSessionProfileDnPolProfileId 	AsamProfilePointer,
		qosSessionProfileUpMarkerProfileId	AsamProfilePointer,
--		qosSessionProfileDnMarkerProfileId  	AsamProfilePointer,
		qosSessionProfileRowStatus 		RowStatus,
		qosSessionProfilePolicyListUp		PolicyList,
		qosSessionProfilePolicyListDn		PolicyList,
		qosSessionProfileIngOuterMarkerProfileId AsamProfilePointer,
--		qosSessionProfileOuterMarking    INTEGER,
		qosSessionProfileUpPolPerTcProfileId  AsamProfilePointer,
		qosSessionProfileRemoteSideUpPolicyList	  PolicyList,
		qosSessionProfileRemoteSideDnPolicyList	  PolicyList		
				}

qosSessionProfileIndex OBJECT-TYPE
	SYNTAX	AsamProfileIndex
	ACCESS	not-accessible
	STATUS mandatory
	DESCRIPTION
	"This object is the index to the qosSessionProfileTable."
::= { qosSessionProfileEntry 1}
qosSessionProfileName OBJECT-TYPE
	SYNTAX	AsamProfileName
	ACCESS	read-write
	STATUS mandatory
	DESCRIPTION
	"A text string containing the operator-assigned name of
	this profile"
::= { qosSessionProfileEntry 2}
qosSessionProfileVersion OBJECT-TYPE
	SYNTAX	INTEGER
	ACCESS	read-write
	STATUS mandatory
	DESCRIPTION
	"Integer containing the version number of this profile."
::= { qosSessionProfileEntry 3}

qosSessionProfileRefCount OBJECT-TYPE
	SYNTAX	AsamProfileRefCount32
	ACCESS read-only
	STATUS	mandatory
	DESCRIPTION
	" Indicates the number of entities using this profile. If the
	reference count is greater than 0, then this profile is 'in use',
	and may NOT be deleted. If the value is 0, then this profile is
	'not in use', and can be deleted."
::= { qosSessionProfileEntry 4}
qosSessionProfileLogFlowType OBJECT-TYPE
	SYNTAX	QosLfDefinitionType
	ACCESS	read-write
	STATUS mandatory
	DESCRIPTION
	"Integer, which defines a logical flow. A logical flow is a
	traffic stream upon which a policy or a contract is made,
	such as all frames on an interface with a particular code point
	or all frames in a PPP session, etc..
	0 - Generic		- Applicable to any defined logical flow
	1 - PVC 		- All frames on a PVC.
	2 - 802.1X session	- All frames on a PVC except
				(port based)	  PPP frames.
	3 - PVC.VLAN		- Represents all frames on a .1D port
				  with the same VLAN ID.
	4 - PVC.VLAN.P (ns)	- Represents all frames on a .1D port
				  with the same VLAN ID and .1P bits.
				(not supported in R2.0)
	5 - PPP			- 	Represents all
					frames in a terminated PPP
					session/interface.		
	6 - IP            	- Represents all frames
				  in a terminated IP session/interface.
	7 - IPoE VLAN CC        - Represents all IPoE frames in a
				  VLAN CC interface.
	8 - PPPoE VLAN CC       -  Represents all PPPoE frames in
                                   a VLAN CC interface.
	9 - IPoA CC             -  Represents all IPoA frames in a IPoA CC 
				   interface.
	10 - PPPoA CC   	-  Represents all PPPoA frames in
				   a PPPoA CC interface.
	11 - IPoE I-Bridge      -  Represents all IPoE frames in I-Bridge 
				   interface.
	12 - PPPoE I-Bridge     -  Represents all PPPoE frames inI-Bridge 
				   interface.
	13 - PPPoA Relay        -  Represents all PPPoA frames in PPPoA relay 
	                           interface.
	14 - PPPoE Relay with MAC concentration   
	                        -  Represents all PPPoE 
	                           frames in PPPeE relay with MAC concentration
				   interface.
	15 - IPoE IP Aware Bridge   -	Represents all IPoE
				   frames in IP Aware Bridge interface.
	16 - IPoA IP Aware Bridge   -	Represents all IPoA
				   frames in IP Aware Bridge interface.
	17 - PPPoE termination   - Represents all PPPoE
                                   frames in PPPoE termination interface.
	18 - PPPoA termination   - Represents all PPPoA
                                   frames in PPPoA termination interface.
        19 -  IPoA Forwarder       - Represents all IPoA
                                   frames in all IPoA forwarders including IPoA E-IBridge, IPoA CC and IPoA Termination."
 
		
::= { qosSessionProfileEntry 5}
qosSessionProfileUpPolProfileId OBJECT-TYPE
	SYNTAX	AsamProfilePointer
	ACCESS	read-write
	STATUS mandatory
	DESCRIPTION
	"This object contains the ID of the applicable policer
	profile on this session upstream.
	The default (null entry) is no policing upstream."
::= { qosSessionProfileEntry 6}
qosSessionProfileDnPolProfileId OBJECT-TYPE
	SYNTAX	AsamProfilePointer
	ACCESS	read-write
	STATUS mandatory
	DESCRIPTION
	"This object contains the ID of the applicable policer
	profile on this session downstream. The
	default is no policing downstream"
::= { qosSessionProfileEntry 7}

qosSessionProfileUpMarkerProfileId OBJECT-TYPE
	SYNTAX	AsamProfilePointer
	ACCESS	read-write
	STATUS mandatory
	DESCRIPTION
	"This object contains the ID of the applicable marker
	profile on a session upstream. If not
	specified, then default markings will be applied."
::= { qosSessionProfileEntry 8}
-- qosSessionProfileDnMarkerProfileId OBJECT-TYPE
--	SYNTAX	AsamProfilePointer
--	ACCESS	read-write
--	STATUS mandatory
--	DESCRIPTION
--		"This object contains the ID of the applicable marker
--		 profile on a session downstream. If not
--		 specified, then default markings will be applied."
-- ::= { qosSessionProfileEntry 9}

qosSessionProfileRowStatus OBJECT-TYPE
	SYNTAX	RowStatus
	ACCESS	read-write
	STATUS mandatory
	DESCRIPTION
	"This object is used to create a new row or modify or
	delete an existing row in this table. The usage is as per
	standard semantics of 'RowStatus' defined in SNMPv2-TC, with
	following limitations:
	The entry associated with a Profile that is being used may
	not be deleted."
::= { qosSessionProfileEntry 10}

-- ============================================================================
--

qosSessionProfilePolicyListUp OBJECT-TYPE 
	SYNTAX	PolicyList
	ACCESS	read-write
	STATUS  mandatory
	DESCRIPTION
"A set of Policies that will be applied to the upstream direction of a subscriber interface. The amount of upstream policies that can be linked to one Session Profile is defined in Board Capability Manager."
::= { qosSessionProfileEntry 11}

qosSessionProfilePolicyListDn OBJECT-TYPE 
	SYNTAX	PolicyList
	ACCESS	read-write
	STATUS  mandatory
	DESCRIPTION
"A set of Policies that will be applied to the downstream direction of a subscriber interface. The amount of downstream policies that can be linked to one Session Profile is defined in Board Capability Manager."
::= { qosSessionProfileEntry 12}

qosSessionProfileIngOuterMarkerProfileId  OBJECT-TYPE
	SYNTAX	AsamProfilePointer
	ACCESS	read-write
	STATUS mandatory
	DESCRIPTION
	"This object contains the ID of the applicable marker profile on the ingress.
   It defines the marker in the outer VLAN tag in case the outer VLAN tag needs
   to be marked differently with the inner VLAN tag in case of S+C forwarder."
::= { qosSessionProfileEntry 13}

-- qosSessionProfileOuterMarking OBJECT-TYPE
--    SYNTAX  INTEGER
--    ACCESS  read-write
--    STATUS mandatory
--    DESCRIPTION
--    "This object defines the outer VLAN pbit marking behavior. It controls SAP
--     level marking behavior and does not control the marking via CCL. 
--    Cdefault (1): system default behavior.  Apply the calculated p-bit to the 
--   S-VLAN and C-VLAN, both are modified and identical in case of S+C forwarder.
--   Apply the calculated p-bit to the outer VLAN in case of S or C forwarder.
--    Cmarking(2):  Use the inner VLAN P-bit as the reference for regeneration.
--   Remarking the outer VLAN P-bit according to the configuration of the  
--   qosSessionProfileIngOuterMarkerProfileId. 
--    Ccopy(3): Copy the inner VLAN P-bit  to the outer VLAN P-bit. If the inner
--   VLAN P-bit is remarked, copy the remarked pbit to the outer VLAN tag.

--  ALCATEL NOTE:
--       ACCESS:     NA       USAGE:      NA
--       PERSIST:    YES      INSRVMOD:   NO
--       RANGE:      1,2,3     DEFVALUE:   1
--       UNITS:      NA       SPARSE:     NA
--       DESCR:      NA"
-- DEFVAL { 1}
-- ::= { qosSessionProfileEntry 14}	

qosSessionProfileUpPolPerTcProfileId OBJECT-TYPE
	SYNTAX	AsamProfilePointer
	ACCESS	read-write
	STATUS mandatory
	DESCRIPTION
	"This object contains the ID of the applicable policerPerTc
	profile on this session upstream.
	The default is no policing per TC on upstream."
::= { qosSessionProfileEntry 15}


qosSessionProfileRemoteSideUpPolicyList OBJECT-TYPE 
	SYNTAX	    PolicyList
	ACCESS     read-write
	STATUS      mandatory
	DESCRIPTION
    "A set of Policies that will be applied to the upstream direction of a subscriber interface on remote side. It is only relevant to Gpon Lt boards." 
::= { qosSessionProfileEntry 16} 

qosSessionProfileRemoteSideDnPolicyList OBJECT-TYPE 
    SYNTAX	PolicyList
    ACCESS 	read-write
    STATUS   mandatory
	DESCRIPTION
    "A set of Policies that will be applied to the downstream direction of a subscriber interface on remote side. It is only relevant to Gpon Lt boards." 
::= { qosSessionProfileEntry 17}



-- ============================================================================
--

-- qosSessionProfile name mapping table

qosSessionProfileMappingTable OBJECT-TYPE
	SYNTAX	SEQUENCE OF QosSessionProfileMappingEntry
	ACCESS	not-accessible
	STATUS	mandatory
	DESCRIPTION
			"This object contains a table for qosSessionProfile
name to index mapping"
::= { qosMacroProfiles 2 }

qosSessionProfileMappingEntry OBJECT-TYPE
	SYNTAX 	QosSessionProfileMappingEntry
	ACCESS	not-accessible
	STATUS mandatory
	DESCRIPTION
	" An entry (conceptual row) representing the qossession Profile Name to
	Index mapping. The system automatically creates an entry in this Table 
	for each corresponding entry (qosSession-profile) created
	in the qosSessionProfileTable.
	Similarly, when an qosSessionprofile is deleted, the
	corresponding entry in this
	table is also automatically deleted by the system."
	INDEX	{qosSessionProfileMappingName }
	::= {qosSessionProfileMappingTable  1}

QosSessionProfileMappingEntry ::=
	SEQUENCE { qosSessionProfileMappingName AsamProfileName,
		   qosSessionProfileMappingIndex AsamProfileIndex
			}

qosSessionProfileMappingName OBJECT-TYPE
	SYNTAX	AsamProfileName
	ACCESS	not-accessible
	STATUS  mandatory
	DESCRIPTION
		"A text string containing the name of
		this profile"
::= { qosSessionProfileMappingEntry 1}

qosSessionProfileMappingIndex OBJECT-TYPE
	SYNTAX	AsamProfileIndex
	ACCESS	read-only
	STATUS mandatory
	DESCRIPTION
		"This object is the Profile index."
::= { qosSessionProfileMappingEntry 2}

-- End of qosSessionProfile name mapping table



-- qosProfiles
qosProfiles OBJECT IDENTIFIER ::= {qosMIB 3}
-- qosMarkerProfile
qosMarkerProfileTable OBJECT-TYPE
	SYNTAX 	SEQUENCE OF QosMarkerProfileEntry
	ACCESS	not-accessible
	STATUS	mandatory
	DESCRIPTION
	" This object contains a table for creating and storing
	marker profiles. A marker profile contains marking
	information for frames within the session to which this
	marker profile is attached"
::= {qosProfiles 1 }
qosMarkerProfileEntry OBJECT-TYPE
	SYNTAX QosMarkerProfileEntry
	ACCESS not-accessible
	STATUS mandatory	
	DESCRIPTION
	"This table contains QoS Marker Profile settings"
	INDEX {qosMarkerProfileIndex}
::= {qosMarkerProfileTable 1}

QosMarkerProfileEntry ::=
       SEQUENCE { qosMarkerProfileIndex                     AsamProfileIndex,
                  qosMarkerProfileName                      AsamProfileName,
                  qosMarkerProfileType                      INTEGER,
                  qosMarkerProfileRefCount                  AsamProfileRefCount32,
                  qosMarkerProfileDot1P                     ExtendVlanSystemPriority,
                  qosMarkerProfileRowStatus                 RowStatus,
                  qosMarkerProfileDscp                      DscpValue,
                  qosMarkerProfileDscpContractTable         OCTET STRING,
                  qosMarkerProfileDscpToDot1PalignmentFlag  INTEGER,
                  qosMarkerProfileDot1PRemarkTable          OCTET STRING,
                  qosMarkerProfileDscpToDot1PAlignProfileId AsamProfilePointer
}

qosMarkerProfileIndex 	OBJECT-TYPE
	SYNTAX AsamProfileIndex
	ACCESS not-accessible
	STATUS mandatory
	DESCRIPTION
	 "This object is the index to the qosMarkerProfileTable."
::= { qosMarkerProfileEntry 1}

qosMarkerProfileName 	OBJECT-TYPE
	SYNTAX	AsamProfileName
	ACCESS read-write
	STATUS mandatory
	DESCRIPTION
	 "Octet string storing the operator-given name of the profile"
::= {qosMarkerProfileEntry 2}

qosMarkerProfileType 	OBJECT-TYPE
	SYNTAX INTEGER { singleDot1P (1),
--			 srTCM (2),
--		         trTCM (3),
                         singleDscp (4),
                         dscpContract (5),
                         dot1PandDscp (6),
                         dot1PandDscpContract (7),
                         dscpToDot1PAlignment (8),
                         dot1PRemarkType (9)
}
	ACCESS read-write
	STATUS mandatory
	DESCRIPTION
	 "The type field specifies the type of marking applied.
          the type 'singleDot1P'means a single Dot1P marking action.
          QosMarkerProfileDot1P field should be used.
          The type 'DscpContract' means a DSCP contract table will
          be applied, qosMarkerProfileDscpContractTable field
          should be used and qosMarkerProfileDscpToDot1PalignmentFlag
          field should be checked.
          The type 'Dot1PandDscp' means a default P-bits and DSCP
          marking action, so qosMarkerProfileDot1P and qosMarkerProfileDscp
          fields should be used and qosMarkerProfileDscpToDot1PalignmentFlag
          field should be checked.
          The type 'singleDscp' means a default DSCP marking action, so
          qosMarkerProfileDscp field should be used and
          qosMarkerProfileDscpToDot1PalignmentFlag field should be checked.
          The type 'dot1PandDscpContract'means a default P-bits and DSCP
          contract table marking action, so qosMarkerProfileDot1P field
          and qosMarkerProfileDscpContractTable field should be used and
          qosMarkerProfileDscpToDot1PalignmentFlag field should be checked.
          The type 'DscpToDot1Palignment' means DSCP to Dot1P alignment should
          be applied, and no other fields need to be checked anymore.
          The type 'dot1PRemarkType' means a remarking table is defined to
          provide mapping from ingress pbit to remarked pbits in the event a 
          policer action of remark is indicated , qosMarkerProfileDot1PRemarkTable 
          should be used.
          The type 'DscpToDot1Palignment' means DSCP to Dot1P alignment should
          be applied. The alignment strategy depends on the setting of 
          qosMarkerProfileDscpToDot1PAlignProfileId. If this pointer is null, then
          sytem-wide qosDscpToDot1PAlignmentTable is used. Otherwise, the referenced 
          row in qosDscpToDot1PAlignProfileTable applies.
          "
::= { qosMarkerProfileEntry 3}

qosMarkerProfileRefCount OBJECT-TYPE
	SYNTAX	AsamProfileRefCount32
	ACCESS read-only
	STATUS	mandatory
	DESCRIPTION
		" Indicates the number of entities using this profile. If the
reference count is greater than 0, then this profile is 'in use',
and may NOT be deleted. If the value is 0, then this profile is
'not in use', and can be deleted."
::= { qosMarkerProfileEntry 4}

qosMarkerProfileDot1P 	OBJECT-TYPE
	SYNTAX ExtendVlanSystemPriority
	ACCESS read-write
	STATUS mandatory
	DESCRIPTION
	 "This object stores the default .1P-value (3 bits) to be
	 applied on all frames in a given direction on the session
	 to which this marker profile was attached"
::= { qosMarkerProfileEntry 5}

qosMarkerProfileRowStatus OBJECT-TYPE
	SYNTAX	RowStatus
	ACCESS	read-write
	STATUS mandatory
	DESCRIPTION
		"This object is used to create a new row or modify or
delete an existing row in this table. The usage is as per
standard semantics of 'RowStatus' defined in SNMPv2-TC, with
following limitations:
o The entry associated with a Profile that is being used may
not be deleted."
::= { qosMarkerProfileEntry 6}

qosMarkerProfileDscp 	OBJECT-TYPE
	SYNTAX DscpValue
	ACCESS read-write
	STATUS mandatory
	DESCRIPTION
	"This object stores the default DSCP value (the six most
         significant bits of the 1-byte IP TOS field) to be applied on all
         frames in a given direction on the subscriber interface to which
         this marker profile was attached"
::= { qosMarkerProfileEntry  7}


qosMarkerProfileDscpContractTable OBJECT-TYPE
	SYNTAX	OCTET STRING
	ACCESS	read-write
	STATUS  mandatory
	DESCRIPTION
        " The following mapping applies: DSCP codepoint 0 corresponds
        to bit 0-7, codepoint 1 to bit 8-15,...The mapping goes from
        6 bit to 8 bit for implementation convenience.
        As a consequence, the most significant two bits of the new DSCP
        value is not used. Graphical representation of where to find the
        regenerated DSCP value in the string of a received DSCP codepoint
        Bit511-504 bit503-496 bit495-488 . . . bit31-bit24 bit23-16 bit15-8 bit7-0  
            CP63      CP62      CP61     . . .     CP3       CP2     CP1     CP0 "
::= { qosMarkerProfileEntry  8}

qosMarkerProfileDscpToDot1PalignmentFlag	OBJECT-TYPE
	SYNTAX INTEGER
			{
				enabled (1),
				disabled (2)
			}
	ACCESS read-write
	STATUS mandatory
	DESCRIPTION
	    " Setting the object to enabled enables the DSCP to P-bits
alignment on the subscriber interface"
	DEFVAL { disabled }
::= { qosMarkerProfileEntry  9}

qosMarkerProfileDot1PRemarkTable OBJECT-TYPE
	SYNTAX	OCTET STRING
	ACCESS	read-write
	STATUS mandatory
	DESCRIPTION
	 "The following mapping applies:
          The remark pbits corresponding to pbit 0 is indicated in bits 0-7, the  remark bpits
          corresponding to pbit 1 in indicated in bit 8-15, etc.. The mapping uses 8 bits for 
          implementation convenience. Graphical representation is given below :
           Bit63-56 bit55-48 bit47-40 bit39-32 bit31-bit24 bit23-16 bit15-8 bit7-0 
            pbit-7   pbit-6   pbit-5    pbit-4    pbit-3    pbit-2   pbit-1 pbit-0
             ALCATEL NOTE:
                 ACCESS:     NA       USAGE:      NA
                 PERSIST:    YES      INSRVMOD:   NO
                 RANGE:      NA       DEFVALUE:   NA
                 UNITS:      NA       SPARSE:     NA
                 DESCR:      NA."
::= { qosMarkerProfileEntry  10}

qosMarkerProfileDscpToDot1PAlignProfileId OBJECT-TYPE
	SYNTAX	AsamProfilePointer
	ACCESS	read-write
	STATUS mandatory
	DESCRIPTION
	        "This object contains a reference to a qosDscpToDot1PAlignProfileIndex.
	         If NOT zero (null), then a valid reference means that the DSCP-to-Dot1P alignments
	         specified in the associated qosDscpToDot1PAlignProfileTable will OVERRIDE 
	         any similar alignments specified in system-wide qosDscpToDot1PAlignmentTable.
          ALCATEL NOTE:
                 ACCESS:     NA       USAGE:      NA
                 PERSIST:    YES      INSRVMOD:   NO
                 RANGE:      NA       DEFVALUE:   0
                 UNITS:      NA       SPARSE:     NA
                 DESCR:      NA "
 DEFVAL { 0 }
::= { qosMarkerProfileEntry  11 }


-- qosPolicerProfile
qosPolicerProfileTable OBJECT-TYPE
	SYNTAX	SEQUENCE OF QosPolicerProfileEntry
	ACCESS	not-accessible
	STATUS	mandatory
	DESCRIPTION
	"This object contains a table for creating and storing
	policer profiles. A policer profile contains rate enforcement
	information for frames within the session to which
	this policer profile is attached.
			"
::= { qosProfiles 2 }
qosPolicerProfileEntry OBJECT-TYPE
	SYNTAX 	QosPolicerProfileEntry
	ACCESS	not-accessible
	STATUS	mandatory
	DESCRIPTION
		"Rows of this table contain QoS Policer Profiles"
	INDEX {qosPolicerProfileIndex }
::= {qosPolicerProfileTable 1}
QosPolicerProfileEntry ::=
     SEQUENCE { qosPolicerProfileIndex		AsamProfileIndex,
		qosPolicerProfileName		AsamProfileName,
		qosPolicerProfileRefCount	AsamProfileRefCount32,
		qosPolicerProfileType 		INTEGER,
		qosPolicerProfileCIR		INTEGER,
		qosPolicerProfileCBS		INTEGER,
		qosPolicerProfileRowStatus      RowStatus,
                qosPolicerProfileEIR		INTEGER,
		qosPolicerProfileEBS		INTEGER,
		qosPolicerProfileCF		INTEGER,
		qosPolicerProfileCM		INTEGER,
		qosPolicerProfileGreenAction	INTEGER,
		qosPolicerProfileGreenMarkerProfileIndex  INTEGER,
		qosPolicerProfileYellowAction	INTEGER,
		qosPolicerProfileYellowMarkerProfileIndex INTEGER,
		qosPolicerProfileRedAction	INTEGER,
		qosPolicerProfileRedMarkerProfileIndex    INTEGER,
		qosPolicerProfilePolicedFrameControl      INTEGER,
                qosPolicerProfilePIR                      INTEGER,
                qosPolicerProfilePBS                      INTEGER,
                qosPolicerProfileCoSThresholdProfileIndex INTEGER
				}
qosPolicerProfileIndex OBJECT-TYPE
	SYNTAX AsamProfileIndex
	ACCESS not-accessible
	STATUS mandatory
	DESCRIPTION
	 "This object is the index to the qosPolicerProfileTable."
::= { qosPolicerProfileEntry 1}
qosPolicerProfileName 	OBJECT-TYPE
	SYNTAX	AsamProfileName
	ACCESS read-write
	STATUS mandatory
	DESCRIPTION
	 "Octet string storing the operator-given name of the profile"
::= {qosPolicerProfileEntry 2}
qosPolicerProfileRefCount OBJECT-TYPE
	SYNTAX	AsamProfileRefCount32
	ACCESS read-only
	STATUS	mandatory
	DESCRIPTION
		" Indicates the number of entities using this profile. If the
reference count is greater than 0, then this profile is 'in use',
and may NOT be deleted. If the value is 0, then this profile is
'not in use', and can be deleted."
::= { qosPolicerProfileEntry 3}
qosPolicerProfileType OBJECT-TYPE
	SYNTAX INTEGER { singleTokenBucket (1), trTCM (2), trTCMwithCoSRFC2698(3), trTCMwithCoSRFC4115(4)}
	ACCESS read-write
	STATUS mandatory
	DESCRIPTION
	 "The policer profile type encodes a standardized policing
	algorithm with an integer value. Based on this type the
	hardware will know how to configure the policers, and which
	of the following fields are required.	
	1 - Single Token Bucket Policer
	2 - trTCM Policer
	3 - trTCMwithCoSRFC2698 policer
	4 - trTCMwithCoSRFC4115 policer
	Note that trTCMwithCoSRFC2698 and trTCMwithCoSRFC4115 are just added for FELT-B board, other boards
	do not supprt these two policing algorithms.
		"
::= { qosPolicerProfileEntry 4}
qosPolicerProfileCIR OBJECT-TYPE
	SYNTAX INTEGER
	ACCESS read-write
	STATUS mandatory
	DESCRIPTION
	 "This object stores the Committed Information Rate (CIR)
	of a policer in Kilobits per second. Cannot be negative."
::= { qosPolicerProfileEntry 5}
qosPolicerProfileCBS OBJECT-TYPE
	SYNTAX INTEGER
	ACCESS read-write
	STATUS mandatory
	DESCRIPTION
	 "This object stores the Committed Burst Size (CBS)
	of a policer in bytes. Cannot be negative.
	Some hardware might not be able to support this
	granularity level. If so, values are rounded in hardware always
	upwards.Range is: [<R4.2.03]64 to 256K/[R4.2.03]64 to 128M in
	terms of bytes.
		"
::= { qosPolicerProfileEntry 6}
qosPolicerProfileRowStatus OBJECT-TYPE
	SYNTAX	RowStatus
	ACCESS	read-write
	STATUS mandatory
	DESCRIPTION
"This object is used to create a new row or modify or
delete an existing row in this table. The usage is as per
standard semantics of 'RowStatus' defined in SNMPv2-TC, with
following limitations:
o The entry associated with a Profile that is being used may
not be deleted."
::= { qosPolicerProfileEntry 7}
qosPolicerProfileEIR OBJECT-TYPE
	SYNTAX INTEGER
	ACCESS read-write
	STATUS mandatory
	DESCRIPTION
	 "This object stores the Excess Information Rate (EIR)
	of a policer in Kilobits per second. Cannot be negative.
	Where policer type is singleTokenBucket(1), any attempt to change
	this item from the default value is ignored even if the Set request is accepted.	
        ALCATEL NOTE:
                 ACCESS:     NA       USAGE:      NA
                 PERSIST:    YES       INSRVMOD:   NO
                 RANGE:      NA      DEFVALUE:   NA
                 UNITS:      NA       SPARSE:     NA
                            DESCR:      NA "
DEFVAL { 0 }
::= { qosPolicerProfileEntry 8}

qosPolicerProfileEBS OBJECT-TYPE
	SYNTAX INTEGER
	ACCESS read-write
	STATUS mandatory
	DESCRIPTION
	 "This object stores the Excess Burst Size (EBS)
	of a policer in bytes. Cannot be negative.
	Some hardware might not be able to support this
	granularity level. If so, values are rounded in hardware always
        upwards.Range is: [<R4.2.04]64 to 256K/[R4.2.04]64 to 128M in terms of bytes.
	Where policer type is singleTokenBucket(1), any attempt to change
	this item from the default value is ignored even if the Set request is accepted.	
        ALCATEL NOTE:
                 ACCESS:     NA       USAGE:      NA
                 PERSIST:    YES       INSRVMOD:   NO
                 RANGE:      NA      DEFVALUE:   NA
                 UNITS:      NA       SPARSE:     NA
                                     DESCR:      NA"
        DEFVAL { 64 }
::= { qosPolicerProfileEntry 9}

qosPolicerProfileCF OBJECT-TYPE
	SYNTAX INTEGER { disable (1), enable (2)}
	ACCESS read-write
	STATUS mandatory
	DESCRIPTION
	 "This object stores the Coupling Flag (CF).
	The Coupling Flag CF is set to either 1 or 2. The choice 
	of the value of CF has the effect of controlling the volume 
	of the Service Frames that are declared Yellow. When CF is 
	set to 1, the long term average bit rate of Service Frames 
	that are declared Yellow. When CF is set to 1, the long 
	term average bit rate of Service Frames that are declared 
	Yellow is bounded by EIR. When CF is set to 2, the long 
	term average bit rate of Service Frames that are declared 
	Yellow is bounded by CIR + EIR depending on volume of the 
	offered Service Frames that are declared Green. In both 
	cases the burst size of the Service Frames that are declared 
	Yellow is bounded by EBS.
	Where policer type is singleTokenBucket(1), any attempt to change
	this item from the default value is ignored even if the Set request is accepted.	
        ALCATEL NOTE:
                 ACCESS:     NA       USAGE:      NA
                 PERSIST:    YES       INSRVMOD:   NO
                 RANGE:      NA      DEFVALUE:   1
                 UNITS:      NA       SPARSE:     NA
                                     DESCR:      NA"
	DEFVAL {1}
::= { qosPolicerProfileEntry 10}

qosPolicerProfileCM OBJECT-TYPE
	SYNTAX INTEGER { color-blind (1), color-aware (2)}
	ACCESS read-write
	STATUS mandatory
	DESCRIPTION
	 "This object stores the color mode.
	The color mode parameter indicates whether 
	the color-aware or color-blind property is 
	employed by the policer profile. It takes a 
	value of color-blind or color-aware only.
	Where policer type is singleTokenBucket(1), any attempt to change
	this item from the default value is ignored even if the Set request is accepted.	
        ALCATEL NOTE:
                 ACCESS:     NA       USAGE:      NA
                 PERSIST:    YES       INSRVMOD:   NO
                 RANGE:      NA      DEFVALUE:   1
                 UNITS:      NA      SPARSE:  NA
                                     DESCR:      NA"
	DEFVAL {1}
::= { qosPolicerProfileEntry 11}

qosPolicerProfileGreenAction OBJECT-TYPE
	SYNTAX INTEGER { pass (1), discard (2), remark(3), setOuterDEI(4)}
	ACCESS read-write
	STATUS mandatory
	DESCRIPTION
	 "This object stores the action for green packet.
	1 - pass
	2 - discard
        3 - remark
        4 - setOuterDEI
	Where policer type is singleTokenBucket(1), any attempt to change
	this item from the default value is ignored even if the Set request is accepted.	
	ALCATEL NOTE:
                 ACCESS:     NA       USAGE:      NA
                 PERSIST:    YES       INSRVMOD:   NO
                 RANGE:      1,3,4      DEFVALUE:   1
                 UNITS:      NA      SPARSE:     NA
                 DESCR:      The action discard is not allowed."
	DEFVAL {1}
::= { qosPolicerProfileEntry 12}

qosPolicerProfileGreenMarkerProfileIndex	 OBJECT-TYPE
	SYNTAX INTEGER (0..65535) 
	ACCESS read-write
	STATUS mandatory
	DESCRIPTION
	 "This object stores the marker Profile Index for green packet.
   A value of 0 indicate that no marker profile attached to this policer for green packet.       
	Where policer type is singleTokenBucket(1), any attempt to change
	this item from the default value is ignored even if the Set request is accepted.	
             ALCATEL NOTE:
                 ACCESS:     NA       USAGE:      NA
                 PERSIST:    YES      INSRVMOD:   NO
                 RANGE:      NA       DEFVALUE:   0
                 UNITS:      NA       SPARSE:     NA
                 		DESCR:      NA."
	 DEFVAL          { 0 }
::= { qosPolicerProfileEntry 13}

qosPolicerProfileYellowAction OBJECT-TYPE
	SYNTAX INTEGER { pass (1), discard (2), remark(3), setOuterDEI(4)}
	ACCESS read-write
	STATUS mandatory
	DESCRIPTION
	 "This object stores the action for yellow packet.
	1 - pass
	2 - discard
  3 - remark
  4 - setOuterDEI
	Where policer type is singleTokenBucket(1), any attempt to change
	this item from the default value is ignored even if the Set request is accepted.
	To support the DEI mark function for FELT-B, a new action called 'setOuterDEI' is added.
	Notice that if 'qosIngressQoSProfileUseDEI' in a ingress qos profile which is 
	attached to a vlan forwarder is set TRUTH, except the discard option, others will
	set DEI.
        ALCATEL NOTE:
                 ACCESS:     NA       USAGE:      NA
                 PERSIST:    YES       INSRVMOD:   NO
                 RANGE:      NA      DEFVALUE:   1
                 UNITS:      NA      SPARSE:     NA
                                     DESCR:      NA"
	DEFVAL {1}
::= { qosPolicerProfileEntry 15}

qosPolicerProfileYellowMarkerProfileIndex OBJECT-TYPE
	SYNTAX INTEGER (0..65535) 
	ACCESS read-write
	STATUS mandatory
	DESCRIPTION
	 "This object stores the marker profile index for yellow packet.
	 A value of 0 indicate that no marker profile attached to this policer for yellow packet.
	Where policer type is singleTokenBucket(1), any attempt to change
	this item from the default value is ignored even if the Set request is accepted.	
             ALCATEL NOTE:
                 ACCESS:     NA       USAGE:      NA
                 PERSIST:    YES      INSRVMOD:   NO
                 RANGE:      NA       DEFVALUE:   0
                 UNITS:      NA       SPARSE:     NA
                 		DESCR:      NA"
 DEFVAL          { 0 }
::= { qosPolicerProfileEntry 16}



qosPolicerProfileRedAction OBJECT-TYPE
   SYNTAX INTEGER { pass (1), discard (2), remark(3), setOuterDEI(4)}
   ACCESS read-write
   STATUS mandatory
   DESCRIPTION
    "This object stores the action for red packet.
   In R4.2 only pass and discard are supported
   1 - pass
   2 - discard
   3 - remark
   4 - setOuterDEI
	Where policer type is singleTokenBucket(1), any attempt to change
	this item from the default value is ignored even if the Set request is accepted.	
   ALCATEL NOTE:
                 ACCESS:     NA       USAGE:      NA
                 PERSIST:    YES       INSRVMOD:   NO
                 RANGE:      NA      DEFVALUE:   2
                 UNITS:      NA      SPARSE:     NA
                                     DESCR:      NA"
   DEFVAL {2}
::= { qosPolicerProfileEntry 18}

qosPolicerProfileRedMarkerProfileIndex OBJECT-TYPE
	SYNTAX INTEGER (0..65535) 
	ACCESS read-write
	STATUS mandatory
	DESCRIPTION
	 "This object stores the marker profile index for red packet. 
	 A value of 0 indicate that no marker profile attached to this policer for red packet.
	Where policer type is singleTokenBucket(1), any attempt to change
	this item from the default value is ignored even if the Set request is accepted.	
                 ALCATEL NOTE:
                 ACCESS:     NA       USAGE:      NA
                 PERSIST:    YES      INSRVMOD:   NO
                 RANGE:      NA       DEFVALUE:   0
                 UNITS:      NA       SPARSE:     NA
                 DESCR:      NA"
   DEFVAL          { 0 }
::= { qosPolicerProfileEntry 19}

qosPolicerProfilePolicedFrameControl OBJECT-TYPE
	SYNTAX INTEGER
			{
				auto-controlled (0),
				ingress-mode (1),
				egress-mode (2),
				rmv4b-ingress-mode (3)
			}
	ACCESS read-write
	STATUS mandatory
	DESCRIPTION
	"          0: auto-controlled, backward compatibility for all LTs.
               1: ingress-mode, policer working with ingress packet size.
               2: egress-mode, policer working with egress packet size.
               3: rmv4b-ingress-mode, policer working on packet size with 4 bytes removed from ingress.
	"
   DEFVAL          { 0 }
::= { qosPolicerProfileEntry 20}

qosPolicerProfilePIR                 OBJECT-TYPE
    SYNTAX INTEGER
    ACCESS read-write
    STATUS mandatory
    DESCRIPTION
    "This object stores the Peak Information Rate (PIR)	of a policer in Kilobits per second.
     Cannot be negative. Where policer type is not trTCMwithCoSRFC2698(3), any attempt to change
	   this item from the default value is ignored even if the Set request is accepted."
    DEFVAL           {0}
::= {qosPolicerProfileEntry  21}

qosPolicerProfilePBS                 OBJECT-TYPE
    SYNTAX INTEGER
    ACCESS read-write
    STATUS mandatory
    DESCRIPTION
    "This object stores the Peak Burst Size (PBS)	of a policer. Cannot be negative. 
     Where policer type is not trTCMwithCoSRFC2698(3), any attempt to change
	   this item from the default value is ignored even if the Set request is accepted."
    DEFVAL           {0}
::= {qosPolicerProfileEntry  22}

qosPolicerProfileCoSThresholdProfileIndex  OBJECT-TYPE
  	SYNTAX INTEGER (0..512) 
	  ACCESS read-write
	  STATUS mandatory
	  DESCRIPTION
	  "This object stores the cos threshold profile index. 
	  A value of 0 indicate that no cos threshold profile attached to this policer.
	  Where policer type is singleTokenBucket(1) or trtcm(2), any attempt to change
	  this item from the default value is ignored even if the Set request is accepted.	
                 ALCATEL NOTE:
                 ACCESS:     NA       USAGE:      NA
                 PERSIST:    YES      INSRVMOD:   NO
                 RANGE:      NA       DEFVALUE:   0
                 UNITS:      NA       SPARSE:     NA
                 DESCR:      NA"
   DEFVAL          { 0 }
::= { qosPolicerProfileEntry 23}

-- qosQueueProfile
qosQueueProfileTable OBJECT-TYPE
	SYNTAX	SEQUENCE OF QosQueueProfileEntry
	ACCESS	not-accessible
	STATUS	mandatory
	DESCRIPTION
	"This object contains a table for creating and storing
	queue (Buffer Acceptance Control)profiles.
	A queue profile contains queue buffer admission control
	information for frames arriving to the buffer."
::= {qosProfiles 3 }
qosQueueProfileEntry OBJECT-TYPE
	SYNTAX	QosQueueProfileEntry
	ACCESS	not-accessible
	STATUS	mandatory
	DESCRIPTION
	"This table contains as rows QoS Queue profiles."
	INDEX {qosQueueProfileIndex }
::= { qosQueueProfileTable 1}
QosQueueProfileEntry ::=
     SEQUENCE { qosQueueProfileIndex 		AsamProfileIndex,
		qosQueueProfileName		AsamProfileName,
		qosQueueProfileVersion 	INTEGER,
		qosQueueProfileRefCount	AsamProfileRefCount32,
		qosQueueProfileBacType		INTEGER,
		qosQueueProfileMinThGreen	INTEGER,
		qosQueueProfileMaxThGreen	INTEGER,
		qosQueueProfileMaxPrGreen	INTEGER,
		qosQueueProfileRowStatus 	RowStatus,
		qosQueueProfileMinThYellow 	INTEGER,
		qosQueueProfileMaxThYellow	INTEGER,
		qosQueueProfileMaxPrYellow	INTEGER,
		qosQueueProfileUnit		INTEGER,
		qosQueueProfileMinThRed		INTEGER,
		qosQueueProfileMaxThRed		INTEGER,
		qosQueueProfileMaxPrRed		INTEGER,
                qosQueueProfileMinQueueSize     INTEGER,
                qosQueueProfileMaxQueueSize     INTEGER,
                qosQueueProfileTailDropThGreen  INTEGER,
	        qosQueueProfileTailDropThYellow INTEGER,
	        qosQueueProfileTailDropThRed	INTEGER

				}
qosQueueProfileIndex OBJECT-TYPE
	SYNTAX	AsamProfileIndex
	ACCESS	not-accessible
	STATUS mandatory
	DESCRIPTION
	"This object is the key to the queue profile table."
::= { qosQueueProfileEntry 1}
qosQueueProfileName OBJECT-TYPE
	SYNTAX	AsamProfileName
	ACCESS	read-write
	STATUS mandatory
	DESCRIPTION
	"This object stores as an octet string the name of the BAC
	profile given by the operator"
::= { qosQueueProfileEntry 2}
qosQueueProfileVersion OBJECT-TYPE
	SYNTAX	INTEGER
	ACCESS	read-write
	STATUS mandatory
	DESCRIPTION
	"Integer containing the version number of this profile."
::= { qosQueueProfileEntry 3}

qosQueueProfileRefCount OBJECT-TYPE
	SYNTAX	AsamProfileRefCount32
	ACCESS read-only
	STATUS	mandatory
	DESCRIPTION
" Indicates the number of entities using this profile. If the
reference count is not 0, then this profile is 'in use',
and can NOT be deleted. If the value is 0, then this profile is
'not in use', and can be deleted."
::= { qosQueueProfileEntry 4}

qosQueueProfileBacType OBJECT-TYPE
	SYNTAX INTEGER { taildrop (1), red (2),twoColourTaildrop(3),twoColourRed(4), gpon(5),threeColourTaildrop(6),threeColourRed(7), gponThreeColorRed(8), taildropAndRed (9), twoColourTaildropAndTwoColourRed (10), threeColourTaildropAndThreeColourRed (11)}
	ACCESS read-write
	STATUS mandatory
	DESCRIPTION
	 "The queue profile type encodes a widely known buffer
	acceptance control (BAC) algorithm with an integer value.
	Based on this type the hardware will know how
	to configure the policers, and which
	of the following fields are required.
	The following values are defined:
			1 - Taildrop
			2 - RED (Random Early Detection)
			3 - twoColourTaildrop
			4 - twoColourRed
			5 - gpon
			6 - threeColourTaildrop
			7 - threeColourRed
			8 - gponThreeColourRed
                        9 - taildropAndRed
                       10 - twoColourTaildropAndTwoColourRed
                       11 - threeColourTaildropAndThreeColourRed


	Based on this values some fields of this row become
	active or don't care.
	Taildrop (1) only the qosQueueProfileMaxThGreen object (backward compatible management) and qosQueueProfileTailDropThGreen (native) object are active.
	RED (2)	qosQueueProfileMaxThGreen, qosQueueProfileMinThGreen, qosQueueProfileMaxPrGreen fields are active.
	twoColourTaildrop (3)  qosQueueProfileMaxThGreen and qosQueueProfileMaxThYellow fields are active and qosQueueProfileTailDropThGreen and qosQueueProfileTailDropThYellow (native) objects are active.
	twoColourRed (4) qosQueueProfileMaxThGreen,qosQueueProfileMinThGreen, qosQueueProfileMaxPrGreen, 
                         qosQueueProfileMaxThYellow, qosQueueProfileMinThYellow, qosQueueProfileMaxPrYellow fields are active.
	gpon (5) - GPON Tail Drop, qosQueueProfileMaxThGreen, qosQueueProfileMinThGreen fields are active
        threeColourTaildrop (6)  qosQueueProfileMaxThGreen, qosQueueProfileMaxThYellow and qosQueueProfileMaxThRed fields are active (backward compatible management) and qosQueueProfileTailDropThGreen, qosQueueProfileTailDropThYellow and qosQueueProfileTailDropThRed (native) objects are active .
	threeColourRed (7)  qosQueueProfileMaxThGreen, qosQueueProfileMinThGreen, qosQueueProfileMaxPrGreen, 
                            qosQueueProfileMaxThYellow, qosQueueProfileMinThYellow, qosQueueProfileMaxPrYellow, 
                            qosQueueProfileMaxThRed, qosQueueProfileMinThRed, and qosQueueProfileMaxPrRed fields are active.
	gponThreeColourRed (8) qosQueueProfileMaxThGreen, qosQueueProfileMinThGreen, qosQueueProfileMaxPrGreen, 
                            qosQueueProfileMaxThYellow, qosQueueProfileMinThYellow, qosQueueProfileMaxPrYellow, 
                            qosQueueProfileMaxThRed, qosQueueProfileMinThRed, qosQueueProfileMaxPrRed, 
                            qosQueueProfileMinQueueSize and qosQueueProfileMaxQueueSize fields are active.
        taildropAndRed (9) qosQueueProfileMaxThGreen, qosQueueProfileMinThGreen, qosQueueProfileMaxPrGreen and  
qosQueueProfileTailDropThGreen fields are active. RED parameters apply to TCP traffic, all other parameters apply for non-TCP traffic

	twoColourTaildropAndTwoColourRed (10) qosQueueProfileMaxThGreen, qosQueueProfileMinThGreen, qosQueueProfileMaxPrGreen, 
qosQueueProfileMaxThYellow, qosQueueProfileMinThYellow, qosQueueProfileMaxPrYellow, qosQueueProfileTailDropThGreen, and qosQueueProfileTailDropThYellow fields are active. RED parameters apply to TCP traffic, all other parameters apply for non-TCP traffic

	threeColourTaildropAndThreeColourRed (11) qosQueueProfileMaxThGreen, qosQueueProfileMinThGreen, qosQueueProfileMaxPrGreen, 
qosQueueProfileMaxThYellow, qosQueueProfileMinThYellow, qosQueueProfileMaxPrYellow, qosQueueProfileMaxThRed, qosQueueProfileMinThRed, qosQueueProfileMaxPrRed, 
qosQueueProfileTailDropThGreen, qosQueueProfileTailDropThYellow and qosQueueProfileTailDropThRed fields are active. RED parameters apply to TCP traffic, all other parameters apply for non-TCP traffic

                 ALCATEL NOTE:
                 ACCESS:     NA      USAGE:      NA
                 PERSIST:    YES     INSRVMOD:   NO
                 RANGE:      NA      DEFVALUE:   NA
                 UNITS:      NA      SPARSE:     NA
                 DESCR:      NA "
::= { qosQueueProfileEntry 5}
qosQueueProfileMinThGreen OBJECT-TYPE
	SYNTAX	INTEGER
	ACCESS	read-write
	STATUS mandatory
	DESCRIPTION
	 "This object stores the minimum threshold value in packets of
	green frames in a RED BAC mechanism, above
	which random discard of green frames is executed. 	
	 The Dot1P value represented by green is defined in 
	qosLimDot1PMappingTable. The value unit is set via qosQueueProfileUnit.
     ALCATEL NOTE:
                 ACCESS:     NA       USAGE:      NA
                 PERSIST:    YES       INSRVMOD:   NO
                 RANGE:      NA       DEFVALUE:   0
                 UNITS:      NA       SPARSE:     NA
                 DESCR:      NA "
::= { qosQueueProfileEntry 6}
qosQueueProfileMaxThGreen OBJECT-TYPE
	SYNTAX	INTEGER
	ACCESS	read-write
	STATUS mandatory
	DESCRIPTION
	 "This object stores the maximum threshold value in packets of
	green frames in a RED mechanism, above
	which deterministic discard of green frames is executed.
	This object may also be used as maximum threshold of a simple
	Taildrop queue (in packets) for all frames entering a queue
        (for taildrop case it is recommended to use qosQueueProfileTailDropThGreen)  
	 The Dot1P value represented by green is defined in 
	qosLimDot1PTcMappingTable. The value unit is set via qosQueueProfileUnit.
	
     ALCATEL NOTE:
                 ACCESS:     NA       USAGE:      NA
                 PERSIST:    YES       INSRVMOD:   NO
                 RANGE:      NA       DEFVALUE:   0
                 UNITS:      NA       SPARSE:     NA
                 DESCR:      In case of Taildrop, twoColourTaildrop 
        and threeColourTaildrop BAC profile :
        qosQueueProfileTailDropThGreen and qosQueueProfileMaxThGreen    
        object map to the same database entry. In case of conflict 
        in multi-varbind SNMP set, the value of    
        qosQueueProfileTailDropThGreen shall apply.  "
::= { qosQueueProfileEntry 7}
qosQueueProfileMaxPrGreen OBJECT-TYPE
	SYNTAX	INTEGER
	ACCESS	read-write
	STATUS mandatory
	DESCRIPTION
	 "This object stores the maximum discard probability
	of green frames in a RED BAC mechanism.
	The probability is defined as a real number between [0..1].
	The MIB represents it as an integer between 0 and 100, and
	The normalization to [0 .. 1]is done by the system.
     ALCATEL NOTE:
                 ACCESS:     NA       USAGE:      NA
                 PERSIST:    YES       INSRVMOD:   NO
                 RANGE:      0..100       DEFVALUE:   0
                 UNITS:     %       SPARSE:     NA
                 DESCR:      NA. "
::= { qosQueueProfileEntry 8}
qosQueueProfileRowStatus OBJECT-TYPE
	SYNTAX	RowStatus
	ACCESS	read-write
	STATUS mandatory
	DESCRIPTION
"This object is used to create a new row or modify or
delete an existing row in this table. The usage is as per
standard semantics of 'RowStatus' defined in SNMPv2-TC, with
following limitations:
o The entry associated with a Profile that is being used may
not be deleted.
     ALCATEL NOTE:
                 ACCESS:     NA       USAGE:      NA
                 PERSIST:    YES       INSRVMOD:   NO
                 RANGE:      1,4,6       DEFVALUE:   0
                 UNITS:      NA       SPARSE:     NA
                 DESCR:      NA. "
::= {qosQueueProfileEntry 9}
qosQueueProfileMinThYellow OBJECT-TYPE
	SYNTAX	INTEGER
	ACCESS	read-write
	STATUS mandatory
	DESCRIPTION
	 "This object stores the minimum threshold value of
	yellow frames in a RED BAC mechanism, above
	which random discard of yellow frames is executed. The Dot1P value represented by yellow is defined in qosLimDot1PMappingTable. The value unit is set via qosQueueProfileUnit. 
      ALCATEL NOTE:
                 ACCESS:     NA       USAGE:      NA
                 PERSIST:    YES       INSRVMOD:   NO
                 RANGE:      NA        DEFVALUE:   NA
                 UNITS:      NA       SPARSE:     NA
                 DESCR:     This parameter is optional when the queue profile is color-unware type: Red or taildrop. The value  always is 0 whatever the manager input or not. When the queue profile type is color-aware, this parameter is mandantory. "
::= { qosQueueProfileEntry 10}

qosQueueProfileMaxThYellow OBJECT-TYPE
	SYNTAX	INTEGER
	ACCESS	read-write
	STATUS mandatory
	DESCRIPTION
	 "This object stores the maximum threshold value in packets of
	yellow frames in a RED mechanism, above
	which deterministic discard of yellow frames is executed.
	This object may also be used as maximum threshold of a simple
	Taildrop queue (in packets) for yellow frames entering a queue.(in the
        taildrop case it is recommended to use qosQueueProfileTailDropThYellow)
        The Dot1P value represented by yellow is defined in qosLimDot1PTcMappingTable. The value unit is set via qosQueueProfileUnit.
      ALCATEL NOTE:
                 ACCESS:     NA       USAGE:      NA
                 PERSIST:    YES       INSRVMOD:   NO
                 RANGE:      NA       DEFVALUE:   0
                 UNITS:      NA       SPARSE:     NA
                 DESCR:      This parameter is optional when the queue profile is color-unware type: Red or taildrop. The value  always is 0 whatever the manager input or not. When the queue profile type is color-aware, this parameter is mandantory.
In case of twoColourTaildrop and threeColourTaildrop BAC profile :
qosQueueProfileTailDropThYellow and qosQueueProfileMaxThYellow object map to the same database entry. In case of conflict 
in multi-varbind SNMP set, the value of qosQueueProfileTailDropThYellow shall apply."
::= { qosQueueProfileEntry 11}

qosQueueProfileMaxPrYellow OBJECT-TYPE
	SYNTAX	INTEGER
	ACCESS	read-write
	STATUS mandatory
	DESCRIPTION
	 "This object stores the maximum discard probability
	of yellow frames in a RED BAC mechanism.
	The probability is defined as a real number between [0..1].
	The MIB represents it as an integer between 0 and 100, and
	The normalization to [0 .. 1]is done by the system. The Dot1P value represented by yellow is defined in qosLimDot1PMappingTable.
      ALCATEL NOTE:
                 ACCESS:     NA       USAGE:      NA
                 PERSIST:    YES       INSRVMOD:   NO
                 RANGE:      NA       DEFVALUE:   0
                 UNITS:      NA       SPARSE:     NA
                 DESCR:      This parameter is optional when the queue profile is color-unware type: Red or taildrop. The value  always is 0 whatever the manager input or not. When the queue profile type is color-aware, this parameter is mandantory."
::= { qosQueueProfileEntry 12}

qosQueueProfileUnit OBJECT-TYPE
	SYNTAX	INTEGER(0..1)
	ACCESS	read-write
	STATUS mandatory
	DESCRIPTION
	 "This object identify the unit of the maximum discard threshold and minimum discard threshold. It can be packet (0) or byte(1).
      ALCATEL NOTE:
                 ACCESS:     NA       USAGE:      NA
                 PERSIST:    YES       INSRVMOD:   NO
                 RANGE:      NA       DEFVALUE:   NA
                 UNITS:      NA       SPARSE:     NA
                 DESCR:      NA "
	DEFVAL {0}
::= { qosQueueProfileEntry 13}

qosQueueProfileMinThRed OBJECT-TYPE
	SYNTAX	INTEGER
	ACCESS	read-write
	STATUS mandatory
	DESCRIPTION
	 "This object stores the minimum threshold value of
	red frames in a RED BAC mechanism, above
	which random discard of red frames is executed. The Dot1P value represented by red is defined in qosLimDot1PMappingTable. The value unit is set via qosQueueProfileUnit. 
      ALCATEL NOTE:
                 ACCESS:     NA       USAGE:      NA
                 PERSIST:    YES       INSRVMOD:   NO
                 RANGE:      NA        DEFVALUE:   0
                 UNITS:      NA       SPARSE:     NA
                 DESCR:     This parameter is optional when the queue profile is color-unware type: Red or taildrop. The value  always is 0 whatever the manager input or not. When the queue profile type is color-aware, this parameter is mandantory. "
::= { qosQueueProfileEntry 14}

qosQueueProfileMaxThRed OBJECT-TYPE
	SYNTAX	INTEGER
	ACCESS	read-write
	STATUS mandatory
	DESCRIPTION
	 "This object stores the maximum threshold value in packets of
	red frames in a RED mechanism, above
	which deterministic discard of red frames is executed.
	This object may also be used as maximum threshold of a simple
	Taildrop queue (in packets) for red frames entering a queue. (in the 
        taildrop case it is recommended to use qosQueueProfileTailDropThRed)  
        The Dot1P value represented by red is defined in qosLimDot1PTcMappingTable. 
        The value unit is set via qosQueueProfileUnit.
      ALCATEL NOTE:
                 ACCESS:     NA       USAGE:      NA
                 PERSIST:    YES       INSRVMOD:   NO
                 RANGE:      NA       DEFVALUE:   0
                 UNITS:      NA       SPARSE:     NA
                 DESCR:      This parameter is optional when the queue profile is color-unware type: Red or taildrop. The value  always is 0 whatever the manager input or not. When the queue profile type is color-aware, this parameter is mandantory.
In case of threeColourTaildrop BAC profile :
qosQueueProfileTailDropThRed and qosQueueProfileMaxThRed object map to the same database entry. In case of conflict 
in multi-varbind SNMP set, the value of qosQueueProfileTailDropThRed shall apply."
::= { qosQueueProfileEntry 15}

qosQueueProfileMaxPrRed OBJECT-TYPE
	SYNTAX	INTEGER
	ACCESS	read-write
	STATUS mandatory
	DESCRIPTION
	 "This object stores the maximum discard probability
	of red frames in a RED BAC mechanism.
	The probability is defined as a real number between [0..1].
	The MIB represents it as an integer between 0 and 100, and
	The normalization to [0 .. 1]is done by the system. The Dot1P value represented by red is defined in qosLimDot1PMappingTable.
      ALCATEL NOTE:
                 ACCESS:     NA       USAGE:      NA
                 PERSIST:    YES       INSRVMOD:   NO
                 RANGE:      NA       DEFVALUE:   0
                 UNITS:      NA       SPARSE:     NA
                 DESCR:      This parameter is optional when the queue profile is color-unware type: Red or taildrop. The value  always is 0 whatever the manager input or not. When the queue profile type is color-aware, this parameter is mandantory."
::= { qosQueueProfileEntry 16}

qosQueueProfileMinQueueSize OBJECT-TYPE
	SYNTAX	INTEGER
	ACCESS	read-write
	STATUS mandatory
	DESCRIPTION
	 "This object stores the minimum guranteed buffer allocation for queue.
          The value unit is set via qosQueueProfileUnit.
      ALCATEL NOTE:
                 ACCESS:     NA       USAGE:      NA
                 PERSIST:    YES      INSRVMOD:   NO
                 RANGE:      NA       DEFVALUE:   0
                 UNITS:      NA       SPARSE:     NA
                 DESCR:      This parameter is mandatory when type: gponThreeColorRed. The value  always is 0 whatever the manager input or not. "
::= { qosQueueProfileEntry 17}

qosQueueProfileMaxQueueSize OBJECT-TYPE
	SYNTAX	INTEGER
	ACCESS	read-write
	STATUS mandatory
	DESCRIPTION
	 "This object stores the maximum buffer allocation for queue.
          The value unit is set via qosQueueProfileUnit.
      ALCATEL NOTE:
                 ACCESS:     NA       USAGE:      NA
                 PERSIST:    YES      INSRVMOD:   NO
                 RANGE:      NA       DEFVALUE:   0
                 UNITS:      NA       SPARSE:     NA
                 DESCR:      This parameter is mandatory when type: gponThreecolorRed. The value  always is 0 whatever the manager input or not. "
::= { qosQueueProfileEntry 18}

qosQueueProfileTailDropThGreen OBJECT-TYPE
	SYNTAX	INTEGER
	ACCESS	read-write
	STATUS mandatory
	DESCRIPTION
	 "This object stores the tail drop threshold value of
	green frames in a tail drop BAC mechanism, above
	which deterministic discard of green frames is executed. The Dot1P value represented by green is defined in qosLimDot1PTcMappingTable. The value unit is set via qosQueueProfileUnit. 
      
      ALCATEL NOTE:
                 ACCESS:     NA       USAGE:      NA
                 PERSIST:    YES       INSRVMOD:   NO
                 RANGE:      NA        DEFVALUE:   0
                 UNITS:      NA       SPARSE:     NA
                 DESCR:     This parameter is optional in the taildrop, twoColourTaildrop and threeColourTaildrop BAC profile. The parameter is mandatory in BAC profiles : 'Taildrop and RED', 'Two colour Taildrop and Two colour RED' and 'Three colour Taildrop and Three colour RED'. It is ignored in all other BAC profiles. In the latter case, the value always is 0 whatever the manager input or not."
::= { qosQueueProfileEntry 19}

qosQueueProfileTailDropThYellow OBJECT-TYPE
	SYNTAX	INTEGER
	ACCESS	read-write
	STATUS mandatory
	DESCRIPTION
	 "This object stores the tail drop threshold value of
	yellow frames in a tail drop BAC mechanism, above
	which deterministic discard of yellow frames is executed. The Dot1P  
        value represented by yellow is defined in 
        qosLimDot1PTcMappingTable. The value unit is set via 
        qosQueueProfileUnit. 
   
        ALCATEL NOTE:
                 ACCESS:     NA       USAGE:      NA
                 PERSIST:    YES       INSRVMOD:   NO
                 RANGE:      NA        DEFVALUE:   0
                 UNITS:      NA       SPARSE:     NA
                 DESCR:     This parameter is optional in the twoColourTaildrop and threeColourTaildrop BAC profile. The parameter is mandatory in BAC profiles : 'Two colour Taildrop and Two colour RED' and 'Three colour Taildrop and Three colour RED'. It is ignored in all other BAC profiles. In the latter case, the value  always is 0 whatever the manager input or not. "
::= { qosQueueProfileEntry 20}

qosQueueProfileTailDropThRed  OBJECT-TYPE
	SYNTAX	INTEGER
	ACCESS	read-write
	STATUS mandatory
	DESCRIPTION
	 "This object stores the tail drop threshold value of
	red frames in a tail drop BAC mechanism, above
	which deterministic discard of red frames is executed. The  
        Dot1P value represented by red is defined in 
        qosLimDot1PTcMappingTable. The value unit is set via  
        qosQueueProfileUnit. 
      
        ALCATEL NOTE:
                 ACCESS:     NA       USAGE:      NA
                 PERSIST:    YES       INSRVMOD:   NO
                 RANGE:      NA        DEFVALUE:   0
                 UNITS:      NA       SPARSE:     NA
                 DESCR:     This parameter is optional in the threeColourTaildrop BAC profile. The parameter is mandatory in BAC profile 'Three colour Taildrop and Three colour RED'. It is ignored in all other BAC profiles. In the latter case, the value  always is 0 whatever the manager input or not. "
::= { qosQueueProfileEntry 21}




-- qosSchedulerProfile
qosSchedulerProfileTable OBJECT-TYPE
	SYNTAX	SEQUENCE OF QosSchedulerProfileEntry
	ACCESS	not-accessible
	STATUS	mandatory
	DESCRIPTION
	"This object contains a table for creating and storing DSL
link scheduler profiles. A scheduler profile contains settings
for the WFQ scheduler of the DSL scheduler.
Presently only the weight of Queue1 can be set, while the
weight for Queue0 is auto-adjusted."
::= { qosProfiles 4 }
qosSchedulerProfileEntry OBJECT-TYPE
	SYNTAX QosSchedulerProfileEntry
	ACCESS	not-accessible
	STATUS mandatory
	DESCRIPTION
	"This table contains as row QoS Scheduler Profiles"
	INDEX {qosSchedulerProfileIndex}
::= {qosSchedulerProfileTable 1}
QosSchedulerProfileEntry 	::=
     SEQUENCE { qosSchedulerProfileIndex		AsamProfileIndex ,
		qosSchedulerProfileName			AsamProfileName,
		qosSchedulerProfileVersion 		INTEGER,
		qosSchedulerProfileRefCount		AsamProfileRefCount32,
		qosSchedulerProfileWfqQ1Weight		INTEGER,
		qosSchedulerProfileRowStatus 		RowStatus	
				}
qosSchedulerProfileIndex OBJECT-TYPE
	SYNTAX	AsamProfileIndex
	ACCESS	not-accessible
	STATUS mandatory
	DESCRIPTION
	"This object is the key in the Scheduler Profile table"
::= { qosSchedulerProfileEntry 1}
qosSchedulerProfileName OBJECT-TYPE
	SYNTAX	AsamProfileName
	ACCESS	read-write
	STATUS mandatory
	DESCRIPTION
	"This object stores as an octet string the name of the
Scheduler profile given by the operator."
::= {qosSchedulerProfileEntry 2}
qosSchedulerProfileVersion OBJECT-TYPE
	SYNTAX	INTEGER
	ACCESS	read-write
	STATUS mandatory
	DESCRIPTION
	"Integer containing the version number of this profile."
::= { qosSchedulerProfileEntry 3}
qosSchedulerProfileRefCount OBJECT-TYPE
	SYNTAX	AsamProfileRefCount32
	ACCESS read-only
	STATUS	mandatory
	DESCRIPTION
	" Indicates the number of entities using this profile. If the
reference count is greater than 0, then this profile is 'in use',
and may NOT be deleted. If the value is 0, then this profile is
'not in use', and can be deleted."
::= { qosSchedulerProfileEntry 4}

qosSchedulerProfileWfqQ1Weight OBJECT-TYPE
	SYNTAX	INTEGER
	ACCESS	read-write
	STATUS mandatory
	DESCRIPTION
	 "This object stores the weight of the DSL link WFQ scheduler for 
	Queue 1. It stores it as an Integer with values
	between 0 and 100. The weight of Queue0 is auto-adjusted
	such that the sum of the two is always 100"
::= {qosSchedulerProfileEntry 5}
qosSchedulerProfileRowStatus OBJECT-TYPE
	SYNTAX	RowStatus
	ACCESS	read-write
	STATUS mandatory
	DESCRIPTION
	"This object is used to create a new row or modify or
delete an existing row in this table. The usage is as per
standard semantics of 'RowStatus' defined in SNMPv2-TC, with
following limitations:
o The entry associated with a Profile that is being used may
not be deleted."
::= {qosSchedulerProfileEntry 6}

-- qosCacProfile
qosCacProfileTable OBJECT-TYPE
	SYNTAX	SEQUENCE OF QosCacProfileEntry
	ACCESS	not-accessible
	STATUS	mandatory
	DESCRIPTION
	"This object contains a table for creating and storing
	CAC (Connection Admission Control)profiles.
	A CAC profile contains rate parameters for:
the maximum allowed bandwidth for voice
the maximum allowed bandwidth for multicast video
the minimum reserved bandwidth for data traffic
The scope of a CAC profile is a DSL interface, downstream.
			"
::= { qosProfiles 5 }
qosCacProfileEntry OBJECT-TYPE
	SYNTAX QosCacProfileEntry
	ACCESS not-accessible
	STATUS mandatory
	DESCRIPTION
	"This table contains as rows QoS CAC Profiles."
	INDEX {qosCacProfileIndex }
::= {qosCacProfileTable 1}
QosCacProfileEntry ::=
	SEQUENCE { qosCacProfileIndex 		AsamProfileIndex ,
		qosCacProfileName		AsamProfileName,
		qosCacProfileVersion 		INTEGER,
		qosCacProfileRefCount		AsamProfileRefCount32,
		qosCacProfileResVoiceBw		INTEGER,
		qosCacProfileMaxMcastBw		INTEGER,
		qosCacProfileResDataBw		INTEGER,
		qosCacProfileRowStatus 		RowStatus,
		qosCacProfileType 		             INTEGER
	
				}
qosCacProfileIndex OBJECT-TYPE
	SYNTAX	AsamProfileIndex
	ACCESS	not-accessible
	STATUS mandatory
	DESCRIPTION
		"This object is the index in the CAC Profile table"
::= { qosCacProfileEntry 1}
qosCacProfileName OBJECT-TYPE
	SYNTAX	AsamProfileName
	ACCESS	read-write
	STATUS mandatory
	DESCRIPTION
		"This object stores as an octet string the name of the CAC
		 (Connection Admission Control) profile."
::= {qosCacProfileEntry 2}
qosCacProfileVersion OBJECT-TYPE
	SYNTAX	INTEGER
	ACCESS	read-write
	STATUS mandatory
	DESCRIPTION
		"Integer containing the version number of this profile."
::= { qosCacProfileEntry 3}
qosCacProfileRefCount OBJECT-TYPE
	SYNTAX	AsamProfileRefCount32
	ACCESS read-only
	STATUS	mandatory
	DESCRIPTION
	" Indicates the number of entities using this profile. If the
reference count is greater than 0, then this profile is 'in use',
and may NOT be deleted. If the value is 0, then this profile is
'not in use', and can be deleted."
::= { qosCacProfileEntry 4}

qosCacProfileResVoiceBw OBJECT-TYPE
	SYNTAX	INTEGER
	ACCESS	read-write
	STATUS mandatory
	DESCRIPTION
	 "This object stores the reserved bandwidth for the Voice service
	or services as an INTEGER in Kilobits/sec. Voice has the highest
	priority in the system. The reservation is such that in the
	absence of Voice traffic, data traffic can re-use this bandwidth.
	The scope of the reservation is one DSL link.
	There is no awareness of the number of voice sessions. This
	Object stores the bandwidth necessary to support all the voice
	Sessions that are contractually agreed for on one DSL link"
::= {qosCacProfileEntry 5}
qosCacProfileMaxMcastBw OBJECT-TYPE
	SYNTAX	INTEGER
	ACCESS	read-write
	STATUS mandatory
	DESCRIPTION
	"This object stores the maximum allowed bandwidth
	for the Multicast Video service as an INTEGER in
	Kilobits/sec. Upon a new IGMP join the CAC entity
	will check the available bandwidth on the DSL
	link against the bandwidth of the requested multicast
	video stream. The currently used multicast bandwidth is stored
	in the DSL record table qosDslRecordUsedMcastBw object.
	The actual check is executed against the smaller value
	of the qosCacProfileMaxMcastBw and
	qosDslRecordAvailableMcastBw, where
	qosDslRecordAvailableMcastBw is automatically calculated
	as the guaranteed frame bandwidth of the DSL link minus
	the provisioned bandwidths for Voice and Data services.
	Multicast CAC is executed only for known multicast streams.
	Known multicast streams are configured in the IGMP MIB."
::= { qosCacProfileEntry 6}
qosCacProfileResDataBw OBJECT-TYPE
	SYNTAX	INTEGER
	ACCESS	read-write
	STATUS mandatory
	DESCRIPTION
	"This object stores the reserved bandwidth for all
	data services on a DSL link in Kilobits/sec
	(always positive or null). It is useful in case
	the intention is to guarantee a minimum bandwidth
	for data services in case there is no hard-bound
	limitation intended for multicast services.
	This way a specified minimum is always reserved
	for data traffic."
::= { qosCacProfileEntry 7}
qosCacProfileRowStatus OBJECT-TYPE
	SYNTAX	RowStatus
	ACCESS	read-write
	STATUS mandatory
	DESCRIPTION
	"This object is used to create a new row or modify or
delete an existing row in this table. The usage is as per
standard semantics of 'RowStatus' defined in SNMPv2-TC, with
following limitations:
o The entry associated with a Profile that is being used may
not be deleted."
::= {qosCacProfileEntry 8}

qosCacProfileType OBJECT-TYPE
	SYNTAX	INTEGER (1..2)
	ACCESS	read-write
	STATUS mandatory
	DESCRIPTION
	"This object is used to indicate whether the profile applies to DSL lines or to PON interfaces. By default the profile applies to DSL lines for backward compatibility. Value 1 = DSL and value 2 = PON interface. If the value = 2 (PON), only the qosCacProfileMaxMcastBw  is used from this table and other parameters such as Voice BW and data BW will be ignored. This profile will be applied to UNI and PON levels. The default is 1, DSL."
	DEFVAL {1}

::= {qosCacProfileEntry 9}


-- ============================================================================
-- =======================
-- qosMarkerProfile name mapping table

qosMarkerProfileMappingTable OBJECT-TYPE
	SYNTAX	SEQUENCE OF QosMarkerProfileMappingEntry
	ACCESS	not-accessible
	STATUS	mandatory
	DESCRIPTION
	"This object contains a table for qosMarkerProfile name
to index mapping"
::= { qosProfiles 6 }

qosMarkerProfileMappingEntry OBJECT-TYPE
	SYNTAX 	QosMarkerProfileMappingEntry
	ACCESS	not-accessible
	STATUS mandatory
	DESCRIPTION
	" An entry (conceptual row) representing the qos Marker
Profile Name to Index mapping. The system automatically creates an
entry in this Table for each corresponding entry (qosMarker-profile)
created in the qosMarkerProfileTable.  Similarly, when an
qosMarkerprofile is deleted, the corresponding entry in this table is also
automatically deleted by thesystem."
	INDEX	{qosMarkerProfileMappingName }
	::= {qosMarkerProfileMappingTable  1}

QosMarkerProfileMappingEntry ::=
	SEQUENCE { qosMarkerProfileMappingName 	AsamProfileName,
		   qosMarkerProfileMappingIndex AsamProfileIndex
		 }

qosMarkerProfileMappingName OBJECT-TYPE
	SYNTAX	AsamProfileName
	ACCESS	not-accessible
	STATUS  mandatory
	DESCRIPTION
		"A text string containing the name of
		this profile"
::= { qosMarkerProfileMappingEntry 1}

qosMarkerProfileMappingIndex OBJECT-TYPE
	SYNTAX	AsamProfileIndex
	ACCESS	read-only
	STATUS mandatory
	DESCRIPTION
		"This object is the Profile index."
::= { qosMarkerProfileMappingEntry 2}

-- End of qosMarkerProfile name mapping table


-- qosPolicerProfile name mapping table

qosPolicerProfileMappingTable OBJECT-TYPE
	SYNTAX	SEQUENCE OF QosPolicerProfileMappingEntry
	ACCESS	not-accessible
	STATUS	mandatory
	DESCRIPTION
	"This object contains a table for qosPolicerProfile
name to index mapping"
::= { qosProfiles 7 }

qosPolicerProfileMappingEntry OBJECT-TYPE
	SYNTAX 	QosPolicerProfileMappingEntry
	ACCESS	not-accessible
	STATUS mandatory
	DESCRIPTION
	" An entry (conceptual row) representing the qos
Policer Profile Name to Index mapping. The system automatically creates an
entry in this Table for each corresponding entry (qosPolicer-profile) 
created in the qosPolicerProfileTable.  Similarly, when an
qosPolicerprofile is deleted, the corresponding entry in this table is also
automatically deleted by the system."
	INDEX	{qosPolicerProfileMappingName }
	::= {qosPolicerProfileMappingTable  1}

QosPolicerProfileMappingEntry ::=
	SEQUENCE { qosPolicerProfileMappingName AsamProfileName,
		   qosPolicerProfileMappingIndex AsamProfileIndex
			}

qosPolicerProfileMappingName OBJECT-TYPE
	SYNTAX	AsamProfileName
	ACCESS	not-accessible
	STATUS  mandatory
	DESCRIPTION
		"A text string containing the name of
		this profile"
::= { qosPolicerProfileMappingEntry 1}

qosPolicerProfileMappingIndex OBJECT-TYPE
	SYNTAX	AsamProfileIndex
	ACCESS	read-only
	STATUS mandatory
	DESCRIPTION
		"This object is the Profile index."
::= { qosPolicerProfileMappingEntry 2}

-- End of qosPolicerProfile name mapping table

-- qosQueueProfile name mapping table

qosQueueProfileMappingTable OBJECT-TYPE
	SYNTAX	SEQUENCE OF QosQueueProfileMappingEntry
	ACCESS	not-accessible
	STATUS	mandatory
	DESCRIPTION
	"This object contains a table for qosQueueProfile name
to index mapping"
        ::= { qosProfiles 8 }

qosQueueProfileMappingEntry OBJECT-TYPE
	SYNTAX 	QosQueueProfileMappingEntry
	ACCESS	not-accessible
	STATUS mandatory
	DESCRIPTION
	" An entry (conceptual row) representing the qos Queue
Profile Name to Index mapping. The system automatically creates an
entry in this Table for each corresponding entry (qosQueue-profile)
created in the qosQueueProfileTable.  Similarly, when an
qosQueueprofile is deleted, the corresponding entry in this table is also
automatically deleted by the system."
	INDEX	{qosQueueProfileMappingName}
	::= {qosQueueProfileMappingTable  1}

QosQueueProfileMappingEntry ::=
	SEQUENCE { qosQueueProfileMappingName 	AsamProfileName,
		   qosQueueProfileMappingIndex 	AsamProfileIndex
		 }

qosQueueProfileMappingName OBJECT-TYPE
	SYNTAX	AsamProfileName
	ACCESS	not-accessible
	STATUS  mandatory
	DESCRIPTION
		"A text string containing the name of
		this profile"
        ::= { qosQueueProfileMappingEntry 1}

qosQueueProfileMappingIndex OBJECT-TYPE
        SYNTAX	AsamProfileIndex
	ACCESS	read-only
	STATUS mandatory
	DESCRIPTION
		"This object is the Profile index."
        ::= { qosQueueProfileMappingEntry 2}

-- End of qosQueueProfile name mapping table
-- qosSchedulerProfile name mapping table

qosSchedulerProfileMappingTable OBJECT-TYPE
	SYNTAX	SEQUENCE OF QosSchedulerProfileMappingEntry
	ACCESS	not-accessible
	STATUS	mandatory
	DESCRIPTION
	"This object contains a table for qosSchedulerProfile
name to index mapping"
::= { qosProfiles 9 }

qosSchedulerProfileMappingEntry OBJECT-TYPE
	SYNTAX 	QosSchedulerProfileMappingEntry
	ACCESS	not-accessible
	STATUS mandatory
	DESCRIPTION
	" An entry (conceptual row) representing the qos
Scheduler Profile Name to Index mapping. The system automatically creates an
entry in this Table for each corresponding entry (qosScheduler-profile) created
in the qosSchedulerProfileTable. Similarly, when an qosSchedulerprofile is 
deleted, them corresponding entry in this table is also automatically deleted
 by the system."
	INDEX	{qosSchedulerProfileMappingName }
	::= {qosSchedulerProfileMappingTable  1}

QosSchedulerProfileMappingEntry ::=
	SEQUENCE { qosSchedulerProfileMappingName AsamProfileName,
		   qosSchedulerProfileMappingIndex AsamProfileIndex
			}

qosSchedulerProfileMappingName OBJECT-TYPE
	SYNTAX	AsamProfileName
	ACCESS	not-accessible
	STATUS  mandatory
	DESCRIPTION
		"A text string containing the name of
		this profile"
::= { qosSchedulerProfileMappingEntry 1}

qosSchedulerProfileMappingIndex OBJECT-TYPE
	SYNTAX	AsamProfileIndex
	ACCESS	read-only
	STATUS mandatory
	DESCRIPTION
		"This object is the Profile index."
::= { qosSchedulerProfileMappingEntry 2}

-- End of qosSchedulerProfile name mapping table

-- qosCacProfile name mapping table

qosCacProfileMappingTable OBJECT-TYPE
	SYNTAX	SEQUENCE OF QosCacProfileMappingEntry
	ACCESS	not-accessible
	STATUS	mandatory
	DESCRIPTION
	"This object contains a table for qosCacProfile name to
index mapping"
::= { qosProfiles 10 }

qosCacProfileMappingEntry OBJECT-TYPE
	SYNTAX 	QosCacProfileMappingEntry
	ACCESS	not-accessible
	STATUS mandatory
	DESCRIPTION
	" An entry (conceptual row) representing the qos Cac
Profile Name to Index mapping. The system automatically creates an
entry in this Table for each corresponding entry (qosCac-profile) created
in the qosCacProfileTable. Similarly, when an qosCacprofile is deleted, the
corresponding entry in this table is also automatically deleted by the 
system."
	INDEX	{qosCacProfileMappingName }
	::= {qosCacProfileMappingTable  1}

QosCacProfileMappingEntry ::=
	SEQUENCE { qosCacProfileMappingName 	AsamProfileName,
		   qosCacProfileMappingIndex 	AsamProfileIndex
			}

qosCacProfileMappingName OBJECT-TYPE
	SYNTAX	AsamProfileName
	ACCESS	not-accessible
	STATUS  mandatory
	DESCRIPTION
		"A text string containing the name of
		this profile"
::= { qosCacProfileMappingEntry 1}

qosCacProfileMappingIndex OBJECT-TYPE
	SYNTAX	AsamProfileIndex
	ACCESS	read-only
	STATUS mandatory
	DESCRIPTION
		"This object is the Profile index."
::= { qosCacProfileMappingEntry 2}

-- End of qosCacProfile name mapping table

-- ============================================================================
-- ========================
-- qosPolicyTable name mapping table

qosPolicyTableMappingTable OBJECT-TYPE
	SYNTAX	SEQUENCE OF QosPolicyTableMappingEntry
	ACCESS	not-accessible
	STATUS	mandatory
	DESCRIPTION
	"This object contains a table for qosPolicyTable name
to index mapping"
::= { qosProfiles 11 }

qosPolicyTableMappingEntry OBJECT-TYPE
	SYNTAX 	QosPolicyTableMappingEntry
	ACCESS	not-accessible
	STATUS mandatory
	DESCRIPTION
	" An entry (conceptual row) representing the qos Policy Table Name to
Index mapping. The system automatically creates an entry in this Table for each
corresponding entry (qosPolicyEntry) created in the qosPolicyTable.  Similarly,
when an qosPolicyEntry is deleted, the corresponding entry in this table is
also automatically deleted by the system."
	INDEX	{qosPolicyTableMappingName }
	::= {qosPolicyTableMappingTable  1}

QosPolicyTableMappingEntry ::=
SEQUENCE { qosPolicyTableMappingName 			AsamProfileName,
           qosPolicyTableMappingIndex 			AsamProfileIndex
		}

qosPolicyTableMappingName OBJECT-TYPE
	SYNTAX	AsamProfileName
	ACCESS	not-accessible
	STATUS  mandatory
	DESCRIPTION
	"A text string containing the name of
	this profile"
::= { qosPolicyTableMappingEntry 1}

qosPolicyTableMappingIndex OBJECT-TYPE
	SYNTAX	AsamProfileIndex
	ACCESS	read-only
	STATUS mandatory
	DESCRIPTION
	"This object is the Profile index."
::= { qosPolicyTableMappingEntry 2}

-- End of qosPolicyTable name mapping table


-- qosL2FilterTable name mapping table

qosL2FilterTableMappingTable OBJECT-TYPE
	SYNTAX	SEQUENCE OF QosL2FilterTableMappingEntry
	ACCESS	not-accessible
	STATUS	mandatory
	DESCRIPTION
	"This object contains a table for qosL2FilterTable name
to index mapping"
::= { qosProfiles 12 }

qosL2FilterTableMappingEntry OBJECT-TYPE
	SYNTAX 	QosL2FilterTableMappingEntry
	ACCESS	not-accessible
	STATUS mandatory
	DESCRIPTION
	" An entry (conceptual row) representing the qos L2
Filter Table Name to Index mapping. The system automatically creates an entry
in this Table for each corresponding entry (qosL2FilterEntry) created in the
qosL2FilterTable.  Similarly, when an qosL2FilterEntry is deleted, the
corresponding entry in this table is also automatically deleted by the system."
	INDEX	{qosL2FilterTableMappingName }
	::= {qosL2FilterTableMappingTable  1}

QosL2FilterTableMappingEntry ::=
SEQUENCE { qosL2FilterTableMappingName 		AsamProfileName,
           qosL2FilterTableMappingIndex 	AsamProfileIndex
			}

qosL2FilterTableMappingName OBJECT-TYPE
	SYNTAX	AsamProfileName
	ACCESS	not-accessible
	STATUS  mandatory
	DESCRIPTION
		"A text string containing the name of
		this profile"
::= { qosL2FilterTableMappingEntry 1}

qosL2FilterTableMappingIndex OBJECT-TYPE
	SYNTAX	AsamProfileIndex
	ACCESS	read-only
	STATUS mandatory
	DESCRIPTION
		"This object is the Profile index."
::= { qosL2FilterTableMappingEntry 2}

-- End of qosL2FilterTable name mapping table

-- qosL3FilterTable name mapping table

qosL3FilterTableMappingTable OBJECT-TYPE
	SYNTAX	SEQUENCE OF QosL3FilterTableMappingEntry
	ACCESS	not-accessible
	STATUS	mandatory
	DESCRIPTION
	"This object contains a table for qosL3FilterTable name
to index mapping"
::= { qosProfiles 13 }

qosL3FilterTableMappingEntry OBJECT-TYPE
	SYNTAX 	QosL3FilterTableMappingEntry
	ACCESS	not-accessible
	STATUS mandatory
	DESCRIPTION
	" An entry (conceptual row) representing the qos L3
Filter Table Name to Index mapping. The system automatically creates an entry
in this Table for each corresponding entry (qosL3FilterEntry) created in the
qosL3FilterTable.  Similarly, when an qosL3FilterEntry is deleted, the
corresponding entry in this table is also automatically deleted by the system."
	INDEX	{qosL3FilterTableMappingName }
	::= {qosL3FilterTableMappingTable  1}

QosL3FilterTableMappingEntry ::=
SEQUENCE { qosL3FilterTableMappingName 			AsamProfileName,
           qosL3FilterTableMappingIndex 		AsamProfileIndex
			}

qosL3FilterTableMappingName OBJECT-TYPE
	SYNTAX	AsamProfileName
	ACCESS	not-accessible
	STATUS  mandatory
	DESCRIPTION
		"A text string containing the name of
		this profile"
::= { qosL3FilterTableMappingEntry 1}

qosL3FilterTableMappingIndex OBJECT-TYPE
	SYNTAX	AsamProfileIndex
	ACCESS	read-only
	STATUS mandatory
	DESCRIPTION
		"This object is the Profile index."
::= { qosL3FilterTableMappingEntry 2}

-- End of qosL3FilterTable name mapping table


-- qosPolicyActionTable name mapping table

qosPolicyActionTableMappingTable OBJECT-TYPE
	SYNTAX	SEQUENCE OF QosPolicyActionTableMappingEntry
	ACCESS	not-accessible
	STATUS	mandatory
	DESCRIPTION
			"This object contains a table for qosPolicyActionTable
name to index mapping"
::= { qosProfiles 14 }

qosPolicyActionTableMappingEntry OBJECT-TYPE
	SYNTAX 	QosPolicyActionTableMappingEntry
	ACCESS	not-accessible
	STATUS mandatory
	DESCRIPTION
	" An entry (conceptual row) representing the qos Policy
Action Table Name to Index mapping. The system automatically creates an entry
in this Table for each corresponding entry (qosPolicyActionEntry) created in
the qosPolicyActionTable.  Similarly, when an qosPolicyActionEntry is deleted,
the corresponding entry in this table is also automatically deleted by the
system."
	INDEX	{qosPolicyActionTableMappingName }
	::= {qosPolicyActionTableMappingTable  1}

QosPolicyActionTableMappingEntry ::=
	SEQUENCE { qosPolicyActionTableMappingName 		AsamProfileName,
		   qosPolicyActionTableMappingIndex 		AsamProfileIndex
			}

qosPolicyActionTableMappingName OBJECT-TYPE
	SYNTAX	AsamProfileName
	ACCESS	not-accessible
	STATUS  mandatory
	DESCRIPTION
	"A text string containing the name of
	this profile"
::= { qosPolicyActionTableMappingEntry 1}

qosPolicyActionTableMappingIndex OBJECT-TYPE
	SYNTAX	AsamProfileIndex
	ACCESS	read-only
	STATUS mandatory
	DESCRIPTION
	"This object is the Profile index."
::= { qosPolicyActionTableMappingEntry 2}

-- End of qosPolicyActionTable name mapping table

-- ============================================================================
-- ========================
-- qosPolicyTable

qosPolicyTable OBJECT-TYPE
	SYNTAX	SEQUENCE OF QosPolicyEntry
	ACCESS	not-accessible
	STATUS	mandatory
	DESCRIPTION
	"This object contains a table for creating and storing
	QoS Policy Rules. A QoS Policy rule contains:
-	L2 or L3 filter pointer for sub-flow classifier
-	Policy Action pointer for QoS policy actions
These two pointer can be L2/L3 filter Index and Policy Action Index.
			"
::= { qosProfiles 15  }

qosPolicyEntry OBJECT-TYPE
	SYNTAX QosPolicyEntry
	ACCESS not-accessible
	STATUS mandatory
	DESCRIPTION
		"This table contains as rows QoS Policy rules."
	INDEX {qosPolicyIndex }
::= {qosPolicyTable 1}

QosPolicyEntry ::=
     SEQUENCE { qosPolicyIndex 		AsamProfileIndex ,
		qosPolicyName		AsamProfileName,
		qosPolicyVersion 	INTEGER,
		qosPolicyRefCount	AsamProfileRefCount32,
                qosPolicyFilterType	INTEGER,
		qosPolicyFilterId	AsamProfilePointer,
		qosPolicyActions	AsamProfilePointer,
		qosPolicyPrecedence	INTEGER,
		qosPolicyRowStatus 	RowStatus	
				}

qosPolicyIndex OBJECT-TYPE
	SYNTAX	AsamProfileIndex
	ACCESS	not-accessible
	STATUS  mandatory
	DESCRIPTION
		"This object is the index in the QoS Policy table"
::= { qosPolicyEntry 1}

qosPolicyName OBJECT-TYPE
	SYNTAX	AsamProfileName
	ACCESS	read-write
	STATUS  mandatory
	DESCRIPTION
"This object stores as an octet string the name of the Policy rule."
::= {qosPolicyEntry 2}

qosPolicyVersion OBJECT-TYPE
	SYNTAX	INTEGER
	ACCESS	read-write
	STATUS  mandatory
	DESCRIPTION
		"Integer containing the version number of this profile."
::= { qosPolicyEntry 3}

qosPolicyRefCount OBJECT-TYPE
	SYNTAX	AsamProfileRefCount32
	ACCESS read-only
	STATUS	mandatory
	DESCRIPTION
		" Indicates the number of entities using this profile. If the
          reference count is greater than 0, then this profile is 'in use',
          and may NOT be deleted. If the value is 0, then this profile is
          'not in use', and can be deleted."
::= { qosPolicyEntry 4}

qosPolicyFilterType OBJECT-TYPE
	SYNTAX	INTEGER {
				l2filter (1),
				l3filter (2)
			}

	ACCESS	read-write
	STATUS  mandatory
	DESCRIPTION
"This object stores the filter type of this policy rule. Value 1 means
qosPolicyFilterId refer to a L2 filter, value 2 means qosPolicyFilterId refer
to a L3 filter."
::= {qosPolicyEntry 5}

qosPolicyFilterId OBJECT-TYPE
	SYNTAX	AsamProfilePointer
	ACCESS	read-write
	STATUS  mandatory
	DESCRIPTION
	    "This object stores the object identifier of a filter id. The value
can refer to one of L2FilterIndex or L3FilterIndex. SW will deal with such
conversion between the operator input and the internal OBJECT IDENTIFIER. "
::= {qosPolicyEntry 6}

qosPolicyActions OBJECT-TYPE
	SYNTAX	AsamProfilePointer
	ACCESS	read-write
	STATUS  mandatory
	DESCRIPTION
	"This object stores the QoS Policy Action id as an INTEGER(0,65535).
The value can be one of qosPolicyActionIndex. Value 0 means no Policy Action Id
configured."
::= { qosPolicyEntry 7}

qosPolicyPrecedence OBJECT-TYPE
	SYNTAX	INTEGER (0..255)
	ACCESS	read-write
	STATUS  mandatory
	DESCRIPTION
		"This object stores precedence value of this policy rule. Value
255 is highest priority. The policy with higher priority configured in specific
interface and direction will be firstly executed. Policy rules on the same
interface and direction with same precedence value will be executed according
to operator's configuration order."
	DEFVAL		{10}
::= { qosPolicyEntry 8}

qosPolicyRowStatus OBJECT-TYPE
	SYNTAX	RowStatus
	ACCESS	read-write
	STATUS  mandatory
	DESCRIPTION
	"This object is used to create a new row or modify or
         delete an existing row in this table. The usage is as per
         standard semantics of 'RowStatus' defined in SNMPv2-TC, with
         following limitations:
         The entry associated with a Profile that is being used may
         not be deleted."
::= {qosPolicyEntry 9}

-- end of qosPolicyTable.

-- qosL2FilterTable

qosL2FilterTable OBJECT-TYPE
	SYNTAX	SEQUENCE OF QosL2FilterEntry
	ACCESS	not-accessible
	STATUS	mandatory
	DESCRIPTION
	"This object contains a table for creating and storing
	QoS L2 Filters.
	A QoS L2 Filter contains:
-	MAC destination address
-	MAC destination address prefix
-	MAC source address
-	MAC source address prefix
-	Ethtype, Ethernet type
-	Dot1P, 802.1p priority value, range from 0 to 7.
-	CFI
-	VLAN ID value.
			"
::= { qosProfiles 16  }

qosL2FilterEntry OBJECT-TYPE
	SYNTAX QosL2FilterEntry
	ACCESS not-accessible
	STATUS mandatory
	DESCRIPTION
	"This table contains as rows QoS L2 filters."
	INDEX {qosL2FilterIndex }
::= {qosL2FilterTable 1}

QosL2FilterEntry ::=
     SEQUENCE { qosL2FilterIndex 		AsamProfileIndex ,
		qosL2FilterName			AsamProfileName,
		qosL2FilterRowStatus 		RowStatus,
		qosL2FilterRefCount		AsamProfileRefCount32,
		qosL2FilterMacDa		MacAddress,
		qosL2FilterMacDaPrefix		Gauge,
		qosL2FilterMacSa		MacAddress,
		qosL2FilterMacSaPrefix		Gauge,
		qosL2FilterEthtype		INTEGER,
		qosL2FilterDot1P		INTEGER,
		qosL2FilterCFI			INTEGER,
		qosL2FilterVlanId		INTEGER
				}

qosL2FilterIndex OBJECT-TYPE
	SYNTAX	AsamProfileIndex
	ACCESS	not-accessible
	STATUS  mandatory
	DESCRIPTION
		"This object is the index in the QoS L2 Filter table"
::= { qosL2FilterEntry 1}

qosL2FilterName OBJECT-TYPE
	SYNTAX	AsamProfileName
	ACCESS	read-write
	STATUS  mandatory
	DESCRIPTION
"This object stores as an octet string the name of the L2 Filter."
::= {qosL2FilterEntry 2}

qosL2FilterRowStatus OBJECT-TYPE
	SYNTAX	RowStatus
	ACCESS	read-write
	STATUS  mandatory
	DESCRIPTION
		"This object is used to create a new row or modify or
         delete an existing row in this table. The usage is as per
         standard semantics of 'RowStatus' defined in SNMPv2-TC, with
         following limitations:
              The entry associated with a Profile that is being used may
              not be deleted."
::= {qosL2FilterEntry 3}

qosL2FilterRefCount OBJECT-TYPE
	SYNTAX	AsamProfileRefCount32
	ACCESS read-only
	STATUS	mandatory
	DESCRIPTION
		" Indicates the number of entities using this profile. If the
          reference count is greater than 0, then this profile is 'in use',
          and may NOT be deleted. If the value is 0, then this profile is
          'not in use', and can be deleted."
::= { qosL2FilterEntry 4}


qosL2FilterMacDa OBJECT-TYPE
	SYNTAX	MacAddress
	ACCESS	read-write
	STATUS  mandatory
	DESCRIPTION
	    "This object stores the destination MAC address. It is a 6 octet
string as defined in Bridge-MIB."
::= {qosL2FilterEntry 5}

qosL2FilterMacDaPrefix OBJECT-TYPE
	SYNTAX	Gauge
	ACCESS	read-write
	STATUS  mandatory
	DESCRIPTION
	"This object stores the destination MAC address prefix length as an
INTEGER(0..48). A length of 0 indicates a match of any MAC address; a length of
48 indicates a match of a single MAC address, and a length between 0 and 48
indicates the use of a qosL2FilterMacDa prefix, similar with the use of IP CIDR
prefix."
DEFVAL {0}
::= { qosL2FilterEntry 6}

qosL2FilterMacSa OBJECT-TYPE
	SYNTAX	MacAddress
	ACCESS	read-write
	STATUS  mandatory
	DESCRIPTION
	    "This object stores the source MAC address. It is a 6 octet string
as defined in Bridge-MIB."
::= {qosL2FilterEntry 7}

qosL2FilterMacSaPrefix OBJECT-TYPE
	SYNTAX	Gauge
	ACCESS	read-write
	STATUS  mandatory
	DESCRIPTION
	"This object stores the source MAC address prefix length as an
INTEGER(0..48). A length of 0 indicates a match of any MAC address; a length of
48 indicates a match of a single MAC address, and a length between 0 and 48
indicates the use of a qosL2FilterMacSa prefix, similar with the use of IP CIDR
prefix."
	DEFVAL {0}
::= { qosL2FilterEntry 8}

qosL2FilterEthtype OBJECT-TYPE
	SYNTAX	INTEGER (-1|0..65535)
	ACCESS	read-write
	STATUS  mandatory
	DESCRIPTION
		"This object stores Ethernet type value of this filter for both
Ethernet II-encoded frames and 802.3 encoded frames. A value of -1 indicates
that a specific Ether type has not been defined and thus all Ethtype values are
considered a match."
	DEFVAL {-1}
::= { qosL2FilterEntry 9}

qosL2FilterDot1P OBJECT-TYPE
	SYNTAX	INTEGER (-1|0..7)
	ACCESS	read-write
	STATUS  mandatory
	DESCRIPTION
		"This object stores 802.1p priority bits value of this filter.
A value of -1 indicates that a specific Dot1P has not been defined and thus all
Dot1P values are considered a match."
	DEFVAL {-1}
::= { qosL2FilterEntry 10}

qosL2FilterCFI OBJECT-TYPE
	SYNTAX	INTEGER (-1|0..1)
	ACCESS	read-write
	STATUS  mandatory
	DESCRIPTION
		"This object stores Canonical Format Indicator(CFI) bit of this
filter. A value of -1 indicates that a specific CFI has not been defined and
thus all CFI values are considered a match."
	DEFVAL {-1}
::= { qosL2FilterEntry 11}

qosL2FilterVlanId OBJECT-TYPE
	SYNTAX	INTEGER (-1..4095)
	ACCESS	read-write
	STATUS  mandatory
	DESCRIPTION
		"This object stores VLAN ID value of this filter. A value of -1
indicates that a specific VLAN ID has not been defined and thus all VLAN ID
values are considered a match."
	DEFVAL {-1}
::= { qosL2FilterEntry 12}

--		End of qosL2FilterTable


-- qosL3FilterTable

qosL3FilterTable OBJECT-TYPE
	SYNTAX	SEQUENCE OF QosL3FilterEntry
	ACCESS	not-accessible
	STATUS	mandatory
	DESCRIPTION
	"This object contains a table for creating and storing
	QoS L3 Filters.
        A L3 filter can be one of next types:
        	- Ipv4 l3 filter, i.e. L3 filter applicable only for ipv4 frames.
		- Ipv6 l3 filter, i.e. L3 filter applicable only for ipv6 frames.
		- Ipv4/ipv6 common l3 filter, i.e. L3 filter applicable on both ipv4 and ipv6 frames.
	A QoS L3 Filter can contain next qualifiers:
-	IP destination address
-	IP destination address prefix
-	IP source address
-	IP source address prefix
-	DSCP
-	Flow ID
-	Protocol
-	The minimum value that the layer-4 destination port number
-	The maximum value that the layer-4 destination port number
-	The minimum value that the layer-4 source port number
-	The maximum value that the layer-4 source port number
Note: dependant on the l3 filter type, some qualifiers are applicable or not. This is indicated within the description of the corresponding MIB objects.	
		"
::= { qosProfiles 17 }

L3FilterType ::= INTEGER {
	ipv4 (1),			
	ipv6 (2),
        common (3)   
}


qosL3FilterEntry OBJECT-TYPE
	SYNTAX QosL3FilterEntry
	ACCESS not-accessible
	STATUS mandatory
	DESCRIPTION
		"This table contains as rows QoS L3 filters."
	INDEX {qosL3FilterIndex }
::= {qosL3FilterTable 1}

QosL3FilterEntry ::=
     SEQUENCE { qosL3FilterIndex 		AsamProfileIndex ,
		qosL3FilterName			AsamProfileName,
		qosL3FilterRowStatus 		RowStatus,
		qosL3FilterRefCount		AsamProfileRefCount32,
		qosL3FilterType			L3FilterType,
		qosL3FilterIpDa			InetAddressIPv4,
		qosL3FilterIpDaPrefix		InetAddressPrefixLength,
		qosL3FilterIpSa			InetAddressIPv4,
		qosL3FilterIpSaPrefix		InetAddressPrefixLength,
		qosL3FilterDSCP			DscpOrAny,
		qosL3FilterFlowId		INTEGER,
		qosL3FilterProtocol		INTEGER,
		qosL3FilterDestPortMin		InetPortNumber,
		qosL3FilterDestPortMax		InetPortNumber,
		qosL3FilterSrcPortMin		InetPortNumber,
		qosL3FilterSrcPortMax		InetPortNumber,
                qosL3FilterIpv6Da               InetAddressIPv6,
                qosL3FilterIpv6DaPrefix	        InetAddressPrefixLength,
		qosL3FilterIpv6Sa		InetAddressIPv6,
		qosL3FilterIpv6SaPrefix		InetAddressPrefixLength
				}

qosL3FilterIndex OBJECT-TYPE
	SYNTAX	AsamProfileIndex
	ACCESS	not-accessible
	STATUS  mandatory
	DESCRIPTION
		"This object is the index in the QoS L3 Filter table"
::= { qosL3FilterEntry 1}

qosL3FilterName OBJECT-TYPE
	SYNTAX	AsamProfileName
	ACCESS	read-write
	STATUS  mandatory
	DESCRIPTION
"This object stores as an octet string the name of the L3 Filter."
::= {qosL3FilterEntry 2}

qosL3FilterRowStatus OBJECT-TYPE
	SYNTAX	RowStatus
	ACCESS	read-write
	STATUS  mandatory
	DESCRIPTION
		"This object is used to create a new row or modify or
         delete an existing row in this table. The usage is as per
         standard semantics of 'RowStatus' defined in SNMPv2-TC, with
         following limitations:
         The entry associated with a Profile that is being used may
         not be deleted."
::= {qosL3FilterEntry 3}

qosL3FilterRefCount OBJECT-TYPE
	SYNTAX	AsamProfileRefCount32
	ACCESS read-only
	STATUS	mandatory
	DESCRIPTION
	" Indicates the number of entities using this profile. If the
          reference count is greater than 0, then this profile is 'in use',
          and may NOT be deleted. If the value is 0, then this profile is
          'not in use', and can be deleted."
::= { qosL3FilterEntry 4}


qosL3FilterType OBJECT-TYPE
	SYNTAX	L3FilterType
	ACCESS	read-write
	STATUS  mandatory
	DESCRIPTION
	" Indicates the type of L3 filter, i.e. either L3 Filter is applicable for ipv4 (value 1) or ipv6 (value 2) or ipv4-and-ipv6(common, value 0) frames. Currently, only ipv4 and ipv6 are supported. Common is for future use.
The L3 Filter type is determined at creation time, and can't be modified.

	DEFVAL {1}
    ALCATEL NOTE:
          ACCESS      NA
          USAGE:      OPT
          INSRVMOD:   NO
          RANGE:      0..2 // 0 is not yet supported.
          PERSIST:    YES
          DEFVALUE:   1
          UNITS:      NA
          SPARSE:     NO
          DESCR:      NA
"
::= {qosL3FilterEntry 5}

qosL3FilterIpDa OBJECT-TYPE
	SYNTAX	InetAddressIPv4
	ACCESS	read-write
	STATUS  mandatory
	DESCRIPTION
	" The IPV4 address to match against the packet's destination IP      
Address within an IPV4 frame.
QosL3FilterIpDaPrefix indicates the number of bits that are relevant.
This object is only applicable in case qosL3FilterType = ipv4.
"
::= { qosL3FilterEntry 6}

qosL3FilterIpDaPrefix OBJECT-TYPE
	SYNTAX	InetAddressPrefixLength
	ACCESS	read-write
	STATUS  mandatory
	DESCRIPTION
" The length of the CIDR Prefix carried in qosL3FilterIpDa. In IPv4 addresses,
a length of 0 indicates a match of any address; a length of 32 indicates a
match of a single host address, and a length between 0 and 32 indicates the use
of a CIDR Prefix. 
This object is only applicable in case qosL3FilterType = ipv4.
"
	DEFVAL		{0}
::= {qosL3FilterEntry 7}

qosL3FilterIpSa OBJECT-TYPE
	SYNTAX	InetAddressIPv4
	ACCESS	read-write
	STATUS  mandatory
	DESCRIPTION
	" The IPV4 address to match against the packet's source IP address within an IPV4 frame.
QosL3FilterIpSaPrefix indicates the number of bits that are relevant.
This object is only applicable in case qosL3FilterType = ipv4.
"
::= { qosL3FilterEntry 8}

qosL3FilterIpSaPrefix OBJECT-TYPE
	SYNTAX	InetAddressPrefixLength
	ACCESS	read-write
	STATUS  mandatory
	DESCRIPTION
" The length of the CIDR Prefix carried in qosL3FilterIpSa. In IPv4 addresses,
a length of 0 indicates a match of any address; a length of 32 indicates a
match of a single host address, and a length between 0 and 32 indicates the use
of a CIDR Prefix. 
This object is only applicable in case qosL3FilterType = ipv4.
 "
	DEFVAL		{0}
::= {qosL3FilterEntry 9}


qosL3FilterDSCP OBJECT-TYPE
	SYNTAX	DscpOrAny
	ACCESS	read-write
	STATUS  mandatory
	DESCRIPTION
" The value that the DSCP in the packet must have to match this entry. A value
of -1 indicates that a specific DSCP value has not been defined and thus all
DSCP values are considered a match.
Applicable for all L3 Filter types.
"
	DEFVAL {-1}
::= { qosL3FilterEntry 10}

qosL3FilterFlowId OBJECT-TYPE
	SYNTAX	INTEGER (0..1048575)
	ACCESS	read-only
	STATUS  mandatory
	DESCRIPTION
		" The flow identifier in an IPv6 header. Currently not supported, i.e. this field will be ignored by NP u-Code.
Only applicable in case of L3 Filter type ipv6.
"
	DEFVAL {0}
::= { qosL3FilterEntry 11}

qosL3FilterProtocol OBJECT-TYPE
	SYNTAX	INTEGER (0..255)
	ACCESS	read-write
	STATUS  mandatory
	DESCRIPTION
" The IP protocol to match against the IPv4 protocol number or the IPv6 Next-
Header number in the packet. A value of 255 means match all.  Note the protocol
number of 255 is reserved by IANA, and Next-Header number of 0 is used in IPv6.
Applicable for all L3 Filter types.
"
	DEFVAL {255}
::= { qosL3FilterEntry 12}

qosL3FilterDestPortMin OBJECT-TYPE
	SYNTAX	InetPortNumber
	ACCESS	read-write
	STATUS  mandatory
	DESCRIPTION
" The minimum value that the layer-4 destination port number in the
packet must have in order to match this classifier entry.
Applicable for all L3 Filter types.
Note: If a packet with IPv6 Extension Header present comes in,  then L3 Filters with qualifiers as L4 Port (TCP or UDP Port number) will not be applied as ISAM will not parse the packet further when it hits an IPv6 Extension Header.
"
	DEFVAL {0}
::= { qosL3FilterEntry 13}


qosL3FilterDestPortMax OBJECT-TYPE
	SYNTAX	InetPortNumber
	ACCESS	read-write
	STATUS  mandatory
	DESCRIPTION
" The maximum value that the layer-4 destination port number in  the
packet must have in order to match this classifier entry. This value must
be equal to or greater than the value specified  for this entry in
qosL3FilterDestPortMin. If both qosL3FilterDestPortMin and
qosL3FilterDestPortMax is default, then destination port field will be
ignored.
Applicable for all L3 Filter types.
Note: If a packet with IPv6 Extension Header present comes in,  then L3 Filters with qualifiers as L4 Port (TCP or UDP Port number) will not be applied as ISAM will not parse the packet further when it hits an IPv6 Extension Header.
"
	DEFVAL {65535}
::= { qosL3FilterEntry 14}


qosL3FilterSrcPortMin OBJECT-TYPE
	SYNTAX	InetPortNumber
	ACCESS	read-write
	STATUS  mandatory
	DESCRIPTION
" The minimum value that the layer-4 source port number in the packet
must have in order to match this classifier entry.
Applicable for all L3 Filter types.
Note: If a packet with IPv6 Extension Header present comes in,  then L3 Filters with qualifiers as L4 Port (TCP or UDP Port number) will not be applied as ISAM will not parse the packet further when it hits an IPv6 Extension Header.
"
	DEFVAL {0}
::= { qosL3FilterEntry 15}


qosL3FilterSrcPortMax OBJECT-TYPE
	SYNTAX	InetPortNumber
	ACCESS	read-write
	STATUS  mandatory
	DESCRIPTION
" The maximum value that the layer-4 source port number in the packet
must have in order to match this classifier entry. This value must be
equal to or greater than the value specified for  this entry in
qosL3FilterSrcPortMin. If both qosL3FilterSrcPortMin and qosL3FilterSrcPortMax
is default, then source port field will be ignored.
Applicable for all L3 Filter types.
Note: If a packet with IPv6 Extension Header present comes in,  then L3 Filters with qualifiers as L4 Port (TCP or UDP Port number) will not be applied as ISAM will not parse the packet further when it hits an IPv6 Extension Header.
"
	DEFVAL {65535}
::= { qosL3FilterEntry 16}

qosL3FilterIpv6Da OBJECT-TYPE
	SYNTAX	InetAddressIPv6
	ACCESS	read-write
	STATUS  mandatory
	DESCRIPTION
	" The IPV6 address to match against the packet's destination IP      
Address within an IPV6 frame.
QosL3FilterIpDaPrefix indicates the number of bits that are relevant.
This object is only applicable in case qosL3FilterType = ipv6.
"
::= { qosL3FilterEntry 17}

qosL3FilterIpv6DaPrefix OBJECT-TYPE
	SYNTAX	InetAddressPrefixLength
	ACCESS	read-write
	STATUS  mandatory
	DESCRIPTION
" The length of the CIDR Prefix carried in qosL3FilterIpv6Da. In Ipv6 addresses, a length of 0 indicates a match of any address; a length of 128 indicates a match of a single host address, and a length between 0 and 128 indicates the use of a CIDR Prefix. 
This object is only applicable in case qosL3FilterType = ipv6
"
	DEFVAL		{0}
::= {qosL3FilterEntry 18}

qosL3FilterIpv6Sa OBJECT-TYPE
	SYNTAX	InetAddressIPv6
	ACCESS	read-write
	STATUS  mandatory
	DESCRIPTION
	" The IPV6 address to match against the packet's source IP address within an IPV6 frame.
QosL3FilterIpSaPrefix indicates the number of bits that are relevant.
This object is only applicable in case qosL3FilterType = ipv6.
"
::= { qosL3FilterEntry 19}

qosL3FilterIpv6SaPrefix OBJECT-TYPE
	SYNTAX	InetAddressPrefixLength
	ACCESS	read-write
	STATUS  mandatory
	DESCRIPTION
" The length of the CIDR Prefix carried in qosL3FilterIpSa. In Ipv6 addresses, a length of 0 indicates a match of any address; a length of 128 indicates a match of a single host address, and a length between 0 and 128 indicates the use of a CIDR Prefix. 
This object is only applicable in case qosL3FilterType = ipv6.
"
	DEFVAL		{0}
::= {qosL3FilterEntry 20}


-- end of qosL3FilterTable


-- qosPolicyActionTable

qosPolicyActionTable OBJECT-TYPE
	SYNTAX	SEQUENCE OF QosPolicyActionEntry
	ACCESS	not-accessible
	STATUS	mandatory
	DESCRIPTION
			"This object contains a table for creating and storing
			 QoS Policy Actions.
			 A QoS Policy Action contains:
-	Default discard/pass
-	Set a DSCP value
-	Set a Dot1P value
-	Policing with a policer
-	Policer sharing attribute
			"
::= { qosProfiles 18 }

qosPolicyActionEntry OBJECT-TYPE
	SYNTAX QosPolicyActionEntry
	ACCESS not-accessible
	STATUS mandatory
	DESCRIPTION
		"This table contains as rows QoS Policy Actions."
	INDEX {qosPolicyActionIndex }
::= {qosPolicyActionTable 1}

QosPolicyActionEntry ::=
	SEQUENCE { qosPolicyActionIndex 	AsamProfileIndex ,
		qosPolicyActionName		AsamProfileName,
		qosPolicyActionRowStatus 	RowStatus,	
		qosPolicyActionRefCount		AsamProfileRefCount32,
		qosPolicyActionDisposition	INTEGER,
		qosPolicyActionSetDSCP		DscpOrAny,
		qosPolicyActionSetDot1P		INTEGER,
		qosPolicyActionPolicerId 	AsamProfilePointer,
		qosPolicyActionSharing		INTEGER,
--		qosPolicyActionSetVlanId	INTEGER
	  qosPolicyActionCount            INTEGER,
	  qosPolicyActionMirrorVlan INTEGER

				}

qosPolicyActionIndex OBJECT-TYPE
	SYNTAX	AsamProfileIndex
	ACCESS	not-accessible
	STATUS  mandatory
	DESCRIPTION
		"This object is the index in the QoS Policy Action table"
::= { qosPolicyActionEntry 1}

qosPolicyActionName OBJECT-TYPE
	SYNTAX	AsamProfileName
	ACCESS	read-write
	STATUS  mandatory
	DESCRIPTION
"This object stores as an octet string the name of the Policy Action."
::= {qosPolicyActionEntry 2}

qosPolicyActionRowStatus OBJECT-TYPE
	SYNTAX	RowStatus
	ACCESS	read-write
	STATUS  mandatory
	DESCRIPTION
	"This object is used to create a new row or modify or
         delete an existing row in this table. The usage is as per
         standard semantics of 'RowStatus' defined in SNMPv2-TC, with
         following limitations:
         The entry associated with a Profile that is being used may
         not be deleted."
::= {qosPolicyActionEntry 3}

qosPolicyActionRefCount OBJECT-TYPE
	SYNTAX	AsamProfileRefCount32
	ACCESS read-only
	STATUS	mandatory
	DESCRIPTION
	" Indicates the number of entities using this profile. If the
          reference count is greater than 0, then this profile is 'in use',
          and may NOT be deleted. If the value is 0, then this profile is
          'not in use', and can be deleted."
::= { qosPolicyActionEntry 4}


qosPolicyActionDisposition OBJECT-TYPE
	SYNTAX	INTEGER {
				discard (1),
				pass (2)
 }
	ACCESS	read-write
	STATUS  mandatory
	DESCRIPTION
	    "This object stores the forwarding action. Forwarding action can be
discard or pass. The default forwarding action is pass. When the forwarding
action is discard, the other policy actions in this entry will not be checked,
the frame will be discarded immediately."
	DEFVAL {pass}
::= {qosPolicyActionEntry 5}

qosPolicyActionSetDSCP OBJECT-TYPE
	SYNTAX	DscpOrAny
	ACCESS	read-write
	STATUS  mandatory
	DESCRIPTION
	"This object stores the DSCP value as an INTEGER(-1|0..63). policy with
this policy action will set this DSCP value to matched frames. Default value is
-1, means not to change DSCP value in the frame."
	DEFVAL 	{-1}
::= { qosPolicyActionEntry 6}

qosPolicyActionSetDot1P OBJECT-TYPE
	SYNTAX	INTEGER ( -1|0 .. 7 )
	ACCESS	read-write
	STATUS  mandatory
	DESCRIPTION
	" This object stores the Dot1P value as an INTEGER(-1|0..7).
policy with this policy action will set this Dot1P value to matched frames.
Default value is -1, means not to change Dot1P value in the frame."
	DEFVAL		{-1}
::= { qosPolicyActionEntry 7}

qosPolicyActionPolicerId OBJECT-TYPE
	SYNTAX	AsamProfilePointer
	ACCESS	read-write
	STATUS  mandatory
	DESCRIPTION
	" This object stores the qosPolicerIndex value as an INTEGER.
policy with this policy action will policing matched frames according to a
Policer Profile. Default value is 0, means no policer."
	DEFVAL		{0}
::= { qosPolicyActionEntry 8}

qosPolicyActionSharing OBJECT-TYPE
	SYNTAX	INTEGER {
				enabled (1),
				disabled (2)
 }
	ACCESS	read-write
	STATUS  mandatory
	DESCRIPTION
		" This object stores the Policer sharing attributes as an
INTEGER. Enabled means the policies with same policer profile in a session
profile will create only one policer instance. disabled means the policies with
same policer profile in a session profile will create their own policer
instance separately. Default value is disabled."
	DEFVAL		{2}
::= { qosPolicyActionEntry 9}

--qosPolicyActionSetVlanId OBJECT-TYPE
--	SYNTAX	INTEGER ( -1|0 .. 4094 )
--	ACCESS	read-write
--	STATUS  mandatory
--	DESCRIPTION
--		" This object stores the VLAN ID value as an
-- INTEGER(-1|0..4095). -**- policy with this policy action will set this VLAN ID to
-- matched frames. -**- For pri-tagged frames, this VLAN ID will be added. For
-- vlan-tagged frames, -**- its VLAN ID will be replaced by this value. For
-- double-tagged frames, its -**- S-VLAN will be replaced by this value. Default
-- value is -1, means not to -**- add/change VLAN ID in the frame."
--	DEFVAL		{-1}
--::= { qosPolicyActionEntry 10}

qosPolicyActionCount OBJECT-TYPE
	SYNTAX	INTEGER {
                           enabled (1),
	                   disabled (2) 
}
	ACCESS	read-write
	STATUS  mandatory
	DESCRIPTION
	 "This object stores the traffic count attributes as an INTEGER.
	 Enabled means the traffic classified by filter needs to be counted. 
	 Disabled means the traffic classified by the filter does not need to be counted. 
	 Default value is disabled. It is only relevant to Gpon Lt boards."
	DEFVAL		{2}
::= { qosPolicyActionEntry 11}

qosPolicyActionMirrorVlan OBJECT-TYPE
  SYNTAX	INTEGER ( 0 .. 4093 )
  ACCESS	read-write
  STATUS  mandatory
  DESCRIPTION	
" This object stores the mirror VLAN ID as an INTEGER. 
( 0 .. 4093 ) indicates the VLAN ID to be inserted into mirrored packets.
Default value is 0, means no mirror. "	
  DEFVAL		{0}
::= { qosPolicyActionEntry 12}

-- end of qosPolicyTable.


-- ============================================================================
-- ==========================

-- qosShaperProfile
qosShaperProfileTable OBJECT-TYPE
	SYNTAX	SEQUENCE OF QosShaperProfileEntry
	ACCESS	not-accessible
	STATUS	mandatory
	DESCRIPTION
	"This object contains a table for creating and storing
	shaper profiles. A shaper profile contains rate enforcement
	information for frames  which this shaper profile is applied.
			"
::= { qosProfiles 19 }
qosShaperProfileEntry OBJECT-TYPE
	SYNTAX 	QosShaperProfileEntry
	ACCESS	not-accessible
	STATUS	mandatory
	DESCRIPTION
		"Rows of this table contain QoS Shaper Profiles"
	INDEX {qosShaperProfileIndex }
::= {qosShaperProfileTable 1}
QosShaperProfileEntry ::=
     SEQUENCE { 
qosShaperProfileIndex		AsamProfileIndex,
		qosShaperProfileName		AsamProfileName,
         qosShaperProfileRowStatus      RowStatus	,
		qosShaperProfileRefCount	AsamProfileRefCount32,
		qosShaperProfileType 		 INTEGER,
		qosShaperProfileCIR		INTEGER,
		qosShaperProfileCBS		INTEGER,
                qosShaperProfileEIR		INTEGER,
                qosShaperProfileAutoShapeEnable TruthValue

				}

qosShaperProfileIndex OBJECT-TYPE
	SYNTAX AsamProfileIndex
	ACCESS not-accessible
	STATUS mandatory
	DESCRIPTION
	 "This object is the index to the qosShaperProfileTable.
      ALCATEL NOTE:
                 ACCESS:     NA       USAGE:      NA
                 PERSIST:    YES       INSRVMOD:   NO
                 RANGE:      NA       DEFVALUE:   NA
                 UNITS:      NA       SPARSE:     NA
                 DESCR:      NA "
::= { qosShaperProfileEntry 1}

qosShaperProfileName 	OBJECT-TYPE
	SYNTAX	AsamProfileName
	ACCESS read-write
	STATUS mandatory
	DESCRIPTION
	 "Octet string storing the operator-given name of the profile.
      ALCATEL NOTE:
                 ACCESS:     NA       USAGE:      NA
                 PERSIST:    YES       INSRVMOD:   NO
                 RANGE:      NA       DEFVALUE:   NA
                 UNITS:      NA       SPARSE:     NA
                 DESCR:      NA "
::= {qosShaperProfileEntry 2}

qosShaperProfileRowStatus OBJECT-TYPE
	SYNTAX	RowStatus
	ACCESS	read-write
	STATUS mandatory
	DESCRIPTION
"This object is used to create a new row or modify or
delete an existing row in this table. The usage is as per
standard semantics of 'RowStatus' defined in SNMPv2-TC.
      ALCATEL NOTE:
                 ACCESS:     NA       USAGE:      NA
                 PERSIST:    YES       INSRVMOD:   NO
                 RANGE:      NA       DEFVALUE:   NA
                 UNITS:      NA       SPARSE:     NA
                 DESCR:      NA "
::= { qosShaperProfileEntry 3}

qosShaperProfileRefCount OBJECT-TYPE
	SYNTAX	AsamProfileRefCount32
	ACCESS read-only
	STATUS	mandatory
	DESCRIPTION
		" Indicates the number of entities using this profile. If the
reference count is greater than 0, then this profile is 'in use',
and may NOT be deleted. If the value is 0, then this profile is
'not in use', and can be deleted.
      ALCATEL NOTE:
                 ACCESS:     NA       USAGE:      NA
                 PERSIST:    YES       INSRVMOD:   NO
                 RANGE:      NA       DEFVALUE:   NA
                 UNITS:      NA       SPARSE:     NA
                 DESCR:      NA "
::= { qosShaperProfileEntry 4}

qosShaperProfileType OBJECT-TYPE
   SYNTAX INTEGER { singleTokenBucket (1), singleTokenBucketGpon (2), singleTokenTwoRate (3),twoTokenBucketTwoRate(4)}
   ACCESS read-write
   STATUS mandatory
   DESCRIPTION
    "The shaper profile type encodes a standardized shaping
   algorithm with an integer value. Based on this type the
   hardware will know how to configure the shapers, and which
   of the following fields are required.
      ALCATEL NOTE:
                 ACCESS:     NA       USAGE:      NA
                 PERSIST:    YES       INSRVMOD:   NO
                 RANGE:      NA       DEFVALUE:   singletokenbucket
                 UNITS:      NA       SPARSE:     NA
                 DESCR:      NA "
      DEFVAL { singleTokenBucket }

::= { qosShaperProfileEntry 5}

qosShaperProfileCIR OBJECT-TYPE
	SYNTAX INTEGER(0..2147483647)
	ACCESS read-write
	STATUS mandatory
	DESCRIPTION
	 "This object stores the Committed Information Rate (CIR)
	of a shaper in Kilobits per second. Cannot be negative.
        If the qosShaperProfileType is set to singleTokenBucket or
	singleTokenBucket, CIR can be used for shaper profile otherwise
	this object not be supported.            
      ALCATEL NOTE:
                 ACCESS:     NA       USAGE:      NA
                 PERSIST:    YES       INSRVMOD:   NO
                 RANGE:      NA       DEFVALUE:   0
                 UNITS:      NA       SPARSE:     NA
                 DESCR:      NA "
::= { qosShaperProfileEntry 6}

qosShaperProfileCBS OBJECT-TYPE
	SYNTAX INTEGER(0..2147483647)
	ACCESS read-write
	STATUS mandatory
	DESCRIPTION
	 "This object stores the Committed Burst Size (CBS)
	of a shaper in bytes. Cannot be negative.
      ALCATEL NOTE:
                 ACCESS:     NA       USAGE:      NA
                 PERSIST:    YES       INSRVMOD:   NO
                 RANGE:      NA       DEFVALUE:   NA
                 UNITS:      NA       SPARSE:     NA
                 DESCR:      NA "
::= { qosShaperProfileEntry 7}

qosShaperProfileEIR OBJECT-TYPE
	SYNTAX INTEGER(0..2147483647)
	ACCESS read-write
	STATUS mandatory
	DESCRIPTION
	 "This object stores the Excess Information Rate (CIR)
	of a shaper in Kilobits per second. Cannot be negative.
            The range of EIR will be 0..2400000 for GLT.
            The range of EIR will be 0..10000000 for FGXT.
      ALCATEL NOTE:
                 ACCESS:     NA       USAGE:      NA
                 PERSIST:    YES       INSRVMOD:   NO
                 RANGE:      NA       DEFVALUE:   NA
                 UNITS:      NA       SPARSE:     NA
                 DESCR:      NA "
::= { qosShaperProfileEntry 8}

qosShaperProfileAutoShapeEnable OBJECT-TYPE
	SYNTAX	TruthValue
	ACCESS	read-write
	STATUS mandatory
	DESCRIPTION
	 "This object enables derivation of rate limit value based on the greater of Max EIR of underlying queues or sum CIR of underlying queues.
      ALCATEL NOTE:
                 ACCESS:     NA       USAGE:      NA
                 PERSIST:    YES      INSRVMOD:   NO
                 RANGE:      yes,no   DEFVALUE:   no
                 UNITS:      NA       SPARSE:     NA
                 DESCR:      NA "
DEFVAL { false }
::= { qosShaperProfileEntry 9}

-- end of qosShaperProfileTable

-- qosShaperProfile name mapping table

qosShaperProfileMappingTable OBJECT-TYPE
	SYNTAX	SEQUENCE OF QosShaperProfileMappingEntry
	ACCESS	not-accessible
	STATUS	mandatory
	DESCRIPTION
	"This object contains a table for qosShaperProfile
name to index mapping"
::= { qosProfiles 20 }

qosShaperProfileMappingEntry OBJECT-TYPE
	SYNTAX 	QosShaperProfileMappingEntry
	ACCESS	not-accessible
	STATUS mandatory
	DESCRIPTION
	" An entry (conceptual row) representing the qos
Shaper Profile Name to Index mapping. The system automatically creates an
entry in this Table for each corresponding entry (qosShaper profile)created in the qosShaperProfileTable.  Similarly, when an qosShaper profile is deleted, the corresponding entry in this table is also automatically deleted by the system."
	INDEX	{qosShaperProfileMappingName }
	::= {qosShaperProfileMappingTable  1}

QosShaperProfileMappingEntry ::=
	SEQUENCE { 
qosShaperProfileMappingName     AsamProfileName,
		qosShaperProfileMappingIndex      AsamProfileIndex
			}

qosShaperProfileMappingName OBJECT-TYPE
	SYNTAX	AsamProfileName
	ACCESS	not-accessible
	STATUS  mandatory
	DESCRIPTION
		"A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { qosShaperProfileMappingEntry 1}

qosShaperProfileMappingIndex OBJECT-TYPE
	SYNTAX	AsamProfileIndex
	ACCESS	read-only
	STATUS mandatory
	DESCRIPTION
		"This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { qosShaperProfileMappingEntry 2}

-- End of qosShaperProfile name mapping table


qosSchedulerNodeProfileTable OBJECT-TYPE
	SYNTAX	SEQUENCE OF QosSchedulerNodeProfileEntry
	ACCESS	not-accessible
	STATUS	mandatory
	DESCRIPTION
	" It is pretty much the same as QoSSchedulerProfileTable but with new parameters added. QoSSchedulerProfileTable will not be supported on GLTs."
::= { qosProfiles 21 }

qosSchedulerNodeProfileEntry OBJECT-TYPE
	SYNTAX QosSchedulerNodeProfileEntry
	ACCESS	not-accessible
	STATUS mandatory
	DESCRIPTION
	"This table contains as row QoS Scheduler Profiles"
	INDEX {qosSchedulerNodeProfileIndex}
::= {qosSchedulerNodeProfileTable 1}

QosSchedulerNodeProfileEntry 	::=
     SEQUENCE { qosSchedulerNodeProfileIndex		AsamProfileIndex ,
		qosSchedulerNodeProfileName			AsamProfileName,
		qosSchedulerNodeProfileVersion 		INTEGER,
		qosSchedulerNodeProfileRefCount		AsamProfileRefCount32,
		qosSchedulerNodeProfileRowStatus 		RowStatus,
		qosSchedulerNodeProfileWeight		INTEGER,
		qosSchedulerNodeProfilePriority		INTEGER,
		qosSchedulerNodeProfileShaperProfile		AsamProfilePointer,
		qosSchedulerNodeProfileMulticastInclShaping     TruthValue,
		qosSchedulerNodeProfileShaperProfileExt		AsamProfilePointer
--		qosSchedulerNodeProfileShaperSharing	TruthValue
				}

qosSchedulerNodeProfileIndex OBJECT-TYPE
	SYNTAX	AsamProfileIndex
	ACCESS	not-accessible
	STATUS mandatory
	DESCRIPTION
	"This object is the key in the Scheduler Node Profile table. Values of 1..128 will be supported."
::= { qosSchedulerNodeProfileEntry 1}

qosSchedulerNodeProfileName OBJECT-TYPE
	SYNTAX	AsamProfileName
	ACCESS	read-write
	STATUS mandatory
	DESCRIPTION
	"This object stores as an octet string the name of the
Scheduler Node Profile given by the operator."
::= {qosSchedulerNodeProfileEntry 2}

qosSchedulerNodeProfileVersion OBJECT-TYPE
	SYNTAX	INTEGER
	ACCESS	read-write
	STATUS mandatory
	DESCRIPTION
	"Integer containing the version number of this profile."
::= { qosSchedulerNodeProfileEntry 3}

qosSchedulerNodeProfileRefCount OBJECT-TYPE
	SYNTAX	AsamProfileRefCount32
	ACCESS read-only
	STATUS	mandatory
	DESCRIPTION
	" Indicates the number of entities using this profile. If the
reference count is greater than 0, then this profile is 'in use',
and may NOT be deleted. If the value is 0, then this profile is
'not in use', and can be deleted."
::= { qosSchedulerNodeProfileEntry 4}

qosSchedulerNodeProfileRowStatus OBJECT-TYPE
	SYNTAX	RowStatus
	ACCESS	read-write
	STATUS mandatory
	DESCRIPTION
	"This object is used to create a new row or modify or
delete an existing row in this table. The usage is as per
standard semantics of 'RowStatus' defined in SNMPv2-TC, with
following limitations:
o The entry associated with a Profile that is being used may
not be deleted."
::= {qosSchedulerNodeProfileEntry 5}


qosSchedulerNodeProfileWeight OBJECT-TYPE
	SYNTAX	INTEGER
	ACCESS	read-write
	STATUS mandatory
	DESCRIPTION
	 "This object stores the relative weight of the scheduler. It stores it as an Integer with values 	between 0 and 127. "
	DEFVAL		{1}

::= {qosSchedulerNodeProfileEntry 6}

qosSchedulerNodeProfilePriority OBJECT-TYPE
	SYNTAX	INTEGER
	ACCESS	read-write
	STATUS mandatory
	DESCRIPTION
	 "This object stores the relative priority of the scheduler when multiple schedulers have the same weight.  It stores it as an Integer with values between 1 and 8 "
	DEFVAL		{1}

::= {qosSchedulerNodeProfileEntry 7}

qosSchedulerNodeProfileShaperProfile OBJECT-TYPE
	SYNTAX	AsamProfilePointer
	ACCESS	read-write
	STATUS mandatory
	DESCRIPTION
	 "This object stores the id  of the associated shaper profile.
	 For EPON OLT in downstream, this object used for LLID shaper on 1G PON bandwidth."
        DEFVAL   {0}

::= {qosSchedulerNodeProfileEntry 8}

qosSchedulerNodeProfileMulticastInclShaping OBJECT-TYPE
        SYNTAX  TruthValue
        ACCESS  read-write
        STATUS mandatory
        DESCRIPTION
  "This object indicates whether the UNI level shaper should rate-limit 
the aggregate of unicast + multicast traffic. The default is false (rate-limit unicast only).
ALCATEL NOTE:
                 ACCESS:     NA       USAGE:      NA
                 PERSIST:    YES      INSRVMOD:   NO
                 RANGE:      NA       DEFVALUE:   FALSE
                 UNITS:      NA       SPARSE:     NA
                 DESCR:      NA "
        DEFVAL { false }

  ::= {qosSchedulerNodeProfileEntry 9}

qosSchedulerNodeProfileShaperProfileExt OBJECT-TYPE
	SYNTAX	AsamProfilePointer
	ACCESS	read-write
	STATUS mandatory
	DESCRIPTION
	 "This object stores the id  of the associated shaper profile.
	 For EPON OLT in downstream, this object used for LLID shaper on 10G PON bandwidth. This object is not used on other types of boards."
        DEFVAL   {0}

::= {qosSchedulerNodeProfileEntry 10}


--qosSchedulerNodeProfileShaperSharing OBJECT-TYPE
--	SYNTAX	TruthValue
--	ACCESS	read-write
--	STATUS mandatory
--	DESCRIPTION
--  "This object indicates whether shaper has to be shared across UNIs or across ONTs."
-- 
--
--  ::= {qosSchedulerNodeProfileEntry 9}


qosSchedulerNodeProfileMappingTable OBJECT-TYPE
	SYNTAX	SEQUENCE OF QosSchedulerNodeProfileMappingEntry
	ACCESS	not-accessible
	STATUS	mandatory
	DESCRIPTION
	"This object contains a table for qosSchedulerNodeProfile
name to index mapping. "
::= { qosProfiles 22 }

qosSchedulerNodeProfileMappingEntry OBJECT-TYPE
	SYNTAX 	QosSchedulerNodeProfileMappingEntry
	ACCESS	not-accessible
	STATUS mandatory
	DESCRIPTION
	" An entry (conceptual row) representing the qos
Scheduler Node Profile Name to Index mapping. The system automatically creates an
entry in this Table for each corresponding entry (qosScheduler-Nodeprofile) created
in the qosSchedulerNodeProfileTable. Similarly, when an qosSchedulerNodeprofile is 
deleted, them corresponding entry in this table is also automatically deleted
 by the system."
	INDEX	{qosSchedulerNodeProfileMappingName }
	::= {qosSchedulerNodeProfileMappingTable  1}

QosSchedulerNodeProfileMappingEntry ::=
	SEQUENCE { qosSchedulerNodeProfileMappingName AsamProfileName,
		   qosSchedulerNodeProfileMappingIndex AsamProfileIndex
			}

qosSchedulerNodeProfileMappingName OBJECT-TYPE
	SYNTAX	AsamProfileName
	ACCESS	not-accessible
	STATUS  mandatory
	DESCRIPTION
		"A text string containing the name of
		this profile"
::= { qosSchedulerNodeProfileMappingEntry 1}

qosSchedulerNodeProfileMappingIndex OBJECT-TYPE
	SYNTAX	AsamProfileIndex
	ACCESS	read-only
	STATUS mandatory
	DESCRIPTION
		"This object is the Profile index."
::= { qosSchedulerNodeProfileMappingEntry 2}

-- End of qosSchedulerNodeProfile name mapping table

-- qosBandwidthProfile name mapping table

qosBandwidthProfileMappingTable OBJECT-TYPE
	SYNTAX	SEQUENCE OF QosBandwidthProfileMappingEntry
	ACCESS	not-accessible
	STATUS	mandatory
	DESCRIPTION
	"This object contains a table for qosBandwidthProfile
name to index mapping"
::= { qosProfiles 23 }

qosBandwidthProfileMappingEntry OBJECT-TYPE
	SYNTAX 	QosBandwidthProfileMappingEntry
	ACCESS	not-accessible
	STATUS mandatory
	DESCRIPTION
	" An entry (conceptual row) representing the qos
Bandwidth Profile Name to Index mapping. The system automatically creates an
entry in this Table for each corresponding entry (qosBandwidth profile)created in the qosShaperProfileTable.  Similarly, when an qosBandwidth profile is deleted, the corresponding entry in this table is also automatically deleted by the system."
	INDEX	{qosBandwidthProfileMappingName }
	::= {qosBandwidthProfileMappingTable  1}

QosBandwidthProfileMappingEntry ::=
	SEQUENCE { 
qosBandwidthProfileMappingName     AsamProfileName,
		qosBandwidthProfileMappingIndex      AsamProfileIndex
			}

qosBandwidthProfileMappingName OBJECT-TYPE
	SYNTAX	AsamProfileName
	ACCESS	not-accessible
	STATUS  mandatory
	DESCRIPTION
		"A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileMappingEntry 1}

qosBandwidthProfileMappingIndex OBJECT-TYPE
	SYNTAX	AsamProfileIndex
	ACCESS	read-only
	STATUS mandatory
	DESCRIPTION
		"This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileMappingEntry 2}

-- End of qosBandwidthProfile name mapping table


qosBandwidthProfileTable OBJECT-TYPE
	SYNTAX	SEQUENCE OF QosBandwidthProfileEntry
	ACCESS	not-accessible
	STATUS	mandatory
	DESCRIPTION
	"This object contains a table for creating and storing
	Bandwidth profiles. A Bandwidth profile contains upstream rate enforcement
	information for frames  to which this profile is applied.
			"
::= { qosProfiles 24 }
qosBandwidthProfileEntry OBJECT-TYPE
	SYNTAX 	QosBandwidthProfileEntry
	ACCESS	not-accessible
	STATUS	mandatory
	DESCRIPTION
		"Rows of this table contain QoS Bandwidth Profiles"
	INDEX {qosBandwidthProfileIndex }
::= {qosBandwidthProfileTable 1}

QosBandwidthProfileEntry ::=
     SEQUENCE { 
        qosBandwidthProfileIndex                AsamProfileIndex,
        qosBandwidthProfileName                 AsamProfileName,
        qosBandwidthProfileRowStatus            RowStatus	,
        qosBandwidthProfileRefCount             AsamProfileRefCount32,
        qosBandwidthProfileCIR                  INTEGER,
        qosBandwidthProfileAIR                  INTEGER,
        qosBandwidthProfileEIR                  INTEGER,
        qosBandwidthProfileDelayTolerance       INTEGER,
        qosBandwidthProfileABS                  INTEGER,
        qosBandwidthProfileEBS                  INTEGER,
        qosBandwidthProfileDBRu                 INTEGER
    }

qosBandwidthProfileIndex OBJECT-TYPE
	SYNTAX AsamProfileIndex
	ACCESS not-accessible
	STATUS mandatory
	DESCRIPTION
	 "This object is the index to the qosBandwidthProfileTable.
      ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileEntry 1}

qosBandwidthProfileName 	OBJECT-TYPE
	SYNTAX	AsamProfileName
	ACCESS read-write
	STATUS mandatory
	DESCRIPTION
	 "Octet string storing the operator-given name of the profile.
      ALCATEL NOTE:
                 ACCESS:     NA       USAGE:      NA
                 PERSIST:    YES       INSRVMOD:   NO
                 RANGE:      NA       DEFVALUE:   NA
                 UNITS:      NA       SPARSE:     NA
                 DESCR:      NA "
::= {qosBandwidthProfileEntry 2}

qosBandwidthProfileRowStatus OBJECT-TYPE
	SYNTAX	RowStatus
	ACCESS	read-write
	STATUS mandatory
	DESCRIPTION
"This object is used to create a new row or modify or
delete an existing row in this table. The usage is as per
standard semantics of 'RowStatus' defined in SNMPv2-TC.
      ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileEntry 3}

qosBandwidthProfileRefCount OBJECT-TYPE
	SYNTAX	AsamProfileRefCount32
	ACCESS read-only
	STATUS	mandatory
	DESCRIPTION
		" Indicates the number of entities using this profile. If the
reference count is greater than 0, then this profile is 'in use',
and may NOT be deleted. If the value is 0, then this profile is
'not in use', and can be deleted.
      ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileEntry 4}



qosBandwidthProfileCIR OBJECT-TYPE
	SYNTAX INTEGER(0..2147483647)
	ACCESS read-write
	STATUS mandatory
	DESCRIPTION
	 "This object stores the Committed Information Rate (CIR).
	Cannot be negative.  The range of CIR will be
   0..2400000 for GLT. The range of CIR will be 0..10000000 for FGXT-A
      ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileEntry 5}


qosBandwidthProfileAIR OBJECT-TYPE
	SYNTAX INTEGER(0..2147483647)
	ACCESS read-write
	STATUS mandatory
	DESCRIPTION
	 "This object stores the Assured Information Rate (AIR)
    Cannot be negative. The range of AIR will be 0..2400000 for GLT and
    0..10000000 for FGXT-A
      ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileEntry 6}

qosBandwidthProfileEIR OBJECT-TYPE
	SYNTAX INTEGER(0..2147483647)
	ACCESS read-write
	STATUS mandatory
	DESCRIPTION
	 "This object stores the Excess Information Rate (AIR)
	  Cannot be negative. The range of EIR will be 0..2400000 for GLT and
     0..10000000 for FGXT-A
      ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileEntry 7}

qosBandwidthProfileDelayTolerance OBJECT-TYPE
	SYNTAX INTEGER(1..240)
	ACCESS read-write
	STATUS mandatory
	DESCRIPTION
	 "This object stores the DelayTolerance
	of a shaper in units of 125 microseconds. Cannot be negative. This object is used only if type is singleTokenBucketGpon in the upstream direction.
      ALCATEL NOTE:
                 ACCESS:     NA       USAGE:      NA
                 PERSIST:    YES       INSRVMOD:   NO
                 RANGE:      NA       DEFVALUE:   NA
                 UNITS:      NA       SPARSE:     NA
                 DESCR:      NA "
	DEFVAL		{80}

::= { qosBandwidthProfileEntry 8}

qosBandwidthProfileABS OBJECT-TYPE
	SYNTAX INTEGER(1..256)
	ACCESS read-write
	STATUS mandatory
	DESCRIPTION
	 "This object stores the Assured Burst Size (ABS).
	Cannot be negative.  The range of ABS will be
   1-256 for EPON
      ALCATEL NOTE:
                 ACCESS:     NA       USAGE:      NA
                 PERSIST:    YES       INSRVMOD:   NO
                 RANGE:      NA       DEFVALUE:   NA
                 UNITS:      NA       SPARSE:     NA
                 DESCR:      NA "
     DEFVAL     {256}
::= { qosBandwidthProfileEntry 9}

qosBandwidthProfileEBS OBJECT-TYPE
	SYNTAX INTEGER(1..256)
	ACCESS read-write
	STATUS mandatory
	DESCRIPTION
	 "This object stores the Excess Burst Size (EBS).
	Cannot be negative.  The range of EBS will be
   1..256 for EPON
      ALCATEL NOTE:
                 ACCESS:     NA       USAGE:      NA
                 PERSIST:    YES       INSRVMOD:   NO
                 RANGE:      NA       DEFVALUE:   NA
                 UNITS:      NA       SPARSE:     NA
                 DESCR:      NA "
      DEFVAL     {256}
::= { qosBandwidthProfileEntry 10}

qosBandwidthProfileDBRu OBJECT-TYPE
    SYNTAX INTEGER
        {
            disabled(0),
            enabled (1),
            enabledIfSupported(2)
        }
    ACCESS read-write
    STATUS mandatory
    DESCRIPTION
    "This object stores the SR-DBA enabling. SR-DBA can be disabled (0), enabled (1),
     or conditionally enabled if supported (2).
     Only supported for NG-PON2.
     ALCATEL NOTE:
                 ACCESS:     NA       USAGE:      NA
                 PERSIST:    YES      INSRVMOD:   NO
                 RANGE:      NA       DEFVALUE:   2
                 UNITS:      NA       SPARSE:     NA
                 DESCR:      NA "
    DEFVAL      {enabledIfSupported}
::= { qosBandwidthProfileEntry 11}

-- end of qosBandwidthProfileTable

-- ============================================================================
--
-- Start of qosRateLimitProfileTable & qosRateLimitMappingTable
-- used for protocol rate limit
-- added by fengwei.fu@alcatel-sbell.com.cn for RCR ALU01749330 & ALU01157583
-- of prj 4.5
--
-- ============================================================================

-- ============================================================================
-- qosRateLimitProfileTable
-- ============================================================================

qosRateLimitProfileTable OBJECT-TYPE
        SYNTAX  SEQUENCE OF QosRateLimitProfileEntry
        ACCESS  not-accessible
        STATUS  mandatory
        DESCRIPTION
	"This object contains a table for creating and storing Protocol Rate
	Limitation profiles. A protocol rate limit profile contains the threshold
	values of all protocol types which EPON support. It can be used for rate
	limit in PON/LLID/VP level.
        Max 250 table items 
                        "
::= { qosProfiles 25 }

qosRateLimitProfileEntry OBJECT-TYPE
        SYNTAX  QosRateLimitProfileEntry
        ACCESS  not-accessible
        STATUS  mandatory
        DESCRIPTION
                "Rows of this table contain QoS Protocol Rate Limit Profiles"
        INDEX {qosRateLimitProfileIndex }
::= {qosRateLimitProfileTable 1}

QosRateLimitProfileEntry ::=
     SEQUENCE {
qosRateLimitProfileIndex           AsamProfileIndex,
                qosRateLimitProfileName            AsamProfileName,
                qosRateLimitProfileRowStatus       RowStatus       ,
                qosRateLimitProfileRefCount        AsamProfileRefCount32,
                qosRateLimitProfileTotalRate       INTEGER,
                qosRateLimitProfileTotalBurst       INTEGER,
                qosRateLimitProfileArpRate       INTEGER,
                qosRateLimitProfileArpBurst      INTEGER,
                qosRateLimitProfileDhcpRate       INTEGER,
                qosRateLimitProfileDhcpBurst      INTEGER,
                qosRateLimitProfileIgmpRate       INTEGER,
                qosRateLimitProfileIgmpBurst      INTEGER,
                qosRateLimitProfilePppoeRate       INTEGER,
                qosRateLimitProfilePppoeBurst      INTEGER,
                qosRateLimitProfileNdRate       INTEGER,
                qosRateLimitProfileNdBurst      INTEGER,
                qosRateLimitProfileIcmpv6Rate       INTEGER,
                qosRateLimitProfileIcmpv6Burst      INTEGER,
                qosRateLimitProfileMldRate       INTEGER,
                qosRateLimitProfileMldBurst      INTEGER,
                qosRateLimitProfileDhcpv6Rate       INTEGER,
                qosRateLimitProfileDhcpv6Burst      INTEGER,
                qosRateLimitProfileCfmRate       INTEGER,
                qosRateLimitProfileCfmBurst      INTEGER

                                }

qosRateLimitProfileIndex OBJECT-TYPE
        SYNTAX AsamProfileIndex
        ACCESS not-accessible
        STATUS mandatory
        DESCRIPTION
         "This object is the index to the qosRateLimitProfileTable.
          range is 1~250 
      ALCATEL NOTE:
                 ACCESS:     NA       USAGE:      NA
                 PERSIST:    YES       INSRVMOD:   NO
                 RANGE:      NA       DEFVALUE:   NA
                 UNITS:      NA       SPARSE:     NA
                 DESCR:      NA "
::= { qosRateLimitProfileEntry 1}

qosRateLimitProfileName    OBJECT-TYPE
        SYNTAX  AsamProfileName
        ACCESS read-write
        STATUS mandatory
        DESCRIPTION
         "Octet string storing the operator-given name of the profile.
      ALCATEL NOTE:
                 ACCESS:     NA       USAGE:      NA
                 PERSIST:    YES       INSRVMOD:   NO
                 RANGE:      NA       DEFVALUE:   NA
                 UNITS:      NA       SPARSE:     NA
                 DESCR:      NA "
::= {qosRateLimitProfileEntry 2}

qosRateLimitProfileRowStatus OBJECT-TYPE
        SYNTAX  RowStatus
        ACCESS  read-write
        STATUS mandatory
        DESCRIPTION
"This object is used to create a new row or modify or
delete an existing row in this table. The usage is as per
standard semantics of 'RowStatus' defined in SNMPv2-TC.
      ALCATEL NOTE:
                 ACCESS:     NA       USAGE:      NA
                 PERSIST:    YES       INSRVMOD:   NO
                 RANGE:      NA       DEFVALUE:   NA
                 UNITS:      NA       SPARSE:     NA
                 DESCR:      NA "
::= { qosRateLimitProfileEntry 3}

qosRateLimitProfileRefCount OBJECT-TYPE
        SYNTAX  AsamProfileRefCount32
        ACCESS read-only
        STATUS  mandatory
        DESCRIPTION
                " Indicates the number of entities using this profile. If the
reference count is greater than 0, then this profile is 'in use',
and may NOT be deleted. If the value is 0, then this profile is
'not in use', and can be deleted.
      ALCATEL NOTE:
                 ACCESS:     NA       USAGE:      NA
                 PERSIST:    YES       INSRVMOD:   NO
                 RANGE:      NA       DEFVALUE:   NA
                 UNITS:      NA       SPARSE:     NA
                 DESCR:      NA "
::= { qosRateLimitProfileEntry 4}

qosRateLimitProfileTotalRate OBJECT-TYPE
        SYNTAX INTEGER(0..2147483647)
        ACCESS read-write
        STATUS mandatory
        DESCRIPTION
         "This value means the threshold which is used to limit the summation of all
          protocols(ARP + DHCP + IGMP + PPPoE + DHCPv6....).
          The unit is pps.
          Default value(0) means NOT do rate limit.
      ALCATEL NOTE:
                 ACCESS:     NA       USAGE:      MAND
                 PERSIST:    YES      INSRVMOD:   NO
                 RANGE:      0..254   DEFVALUE:   0
                 UNITS:      PPS      SPARSE:     NA
                 DESCR:      NA "
      DEFVAL { 0 }
::= { qosRateLimitProfileEntry 5}

qosRateLimitProfileTotalBurst OBJECT-TYPE
        SYNTAX INTEGER(0..2147483647)
        ACCESS read-write
        STATUS mandatory
        DESCRIPTION
         "This object is used for burst value which is used to limit the summation
	  of all protocols(ARP + DHCP + IGMP + PPPoE + DHCPv6....)
          The unit is pps.
          This value shoul be more than or equals to qosRateLimitProfileTotalRate
      ALCATEL NOTE:
                 ACCESS:     NA       USAGE:      MAND
                 PERSIST:    YES      INSRVMOD:   NO
                 RANGE:      0..254   DEFVALUE:   0
                 UNITS:      PPS      SPARSE:     NA
                 DESCR:      NA "
::= { qosRateLimitProfileEntry 6}

qosRateLimitProfileArpRate OBJECT-TYPE
        SYNTAX INTEGER(0..2147483647)
        ACCESS read-write
        STATUS mandatory
        DESCRIPTION
         "This value means the threshold which is used to limit the rate of ARP 
      protocol packages sent to OBC..
          The unit is pps.
          Default value(0) means NOT do rate limit.
      ALCATEL NOTE:
                 ACCESS:     NA       USAGE:      OPT
                 PERSIST:    YES      INSRVMOD:   NO
                 RANGE:      0..254   DEFVALUE:   0
                 UNITS:      PPS      SPARSE:     NA
                 DESCR:      NA "
      DEFVAL { 0 }
::= { qosRateLimitProfileEntry 7}

qosRateLimitProfileArpBurst OBJECT-TYPE
        SYNTAX INTEGER(0..2147483647)
        ACCESS read-write
        STATUS mandatory
        DESCRIPTION
         "This object is used for burst value which is used to limit the ARP packages
	  rate to OBC.
          The unit is pps.
          This value should be more than or equals to qosRateLimitProfileArpRate.
      ALCATEL NOTE:
                 ACCESS:     NA       USAGE:      OPT
                 PERSIST:    YES      INSRVMOD:   NO
                 RANGE:      0..254   DEFVALUE:   0
                 UNITS:      PPS      SPARSE:     NA
                 DESCR:      NA "
::= { qosRateLimitProfileEntry 8}

qosRateLimitProfileDhcpRate OBJECT-TYPE
        SYNTAX INTEGER(0..2147483647)
        ACCESS read-write
        STATUS mandatory
        DESCRIPTION
         "This value means the threshold which is used to limit the rate of DHCP
          protocol packages sent to OBC..
          The unit is pps.
          Default value(0) means NOT do rate limit.
      ALCATEL NOTE:
                 ACCESS:     NA       USAGE:      OPT
                 PERSIST:    YES      INSRVMOD:   NO
                 RANGE:      0..254   DEFVALUE:   0
                 UNITS:      PPS      SPARSE:     NA
                 DESCR:      NA "
      DEFVAL { 0 }
::= { qosRateLimitProfileEntry 9}

qosRateLimitProfileDhcpBurst OBJECT-TYPE
        SYNTAX INTEGER(0..2147483647)
        ACCESS read-write
        STATUS mandatory
        DESCRIPTION
         "This object is used for burst value which is used to limit the DHCP packages
	  rate to OBC.
          The unit is pps.
          This value should be more than or equals to qosRateLimitProfileDhcpRate
      ALCATEL NOTE:
                 ACCESS:     NA       USAGE:      OPT
                 PERSIST:    YES      INSRVMOD:   NO
                 RANGE:      0..254   DEFVALUE:   0
                 UNITS:      PPS      SPARSE:     NA
                 DESCR:      NA "
::= { qosRateLimitProfileEntry 10}

qosRateLimitProfileIgmpRate OBJECT-TYPE
        SYNTAX INTEGER(0..2147483647)
        ACCESS read-write
        STATUS mandatory
        DESCRIPTION
         "This value means the threshold which is used to limit the rate of IGMP
          protocol packages sent to OBC..
          The unit is pps.
          Default value(0) means NOT do rate limit.
      ALCATEL NOTE:
                 ACCESS:     NA       USAGE:      OPT
                 PERSIST:    YES      INSRVMOD:   NO
                 RANGE:      0..254   DEFVALUE:   0
                 UNITS:      PPS      SPARSE:     NA
                 DESCR:      NA "
      DEFVAL { 0 }
::= { qosRateLimitProfileEntry 11}

qosRateLimitProfileIgmpBurst OBJECT-TYPE
        SYNTAX INTEGER(0..2147483647)
        ACCESS read-write
        STATUS mandatory
        DESCRIPTION
         "This object is used for burst value which is used to limit the IGMP packages
          rate to OBC.
          The unit is pps.
          This value should be more than or equals to qosRateLimitProfileIgmpRate
      ALCATEL NOTE:
                 ACCESS:     NA       USAGE:      OPT
                 PERSIST:    YES      INSRVMOD:   NO
                 RANGE:      0..254   DEFVALUE:   0
                 UNITS:      PPS       SPARSE:     NA
                 DESCR:      NA "
::= { qosRateLimitProfileEntry 12}

qosRateLimitProfilePppoeRate OBJECT-TYPE
        SYNTAX INTEGER(0..2147483647)
        ACCESS read-write
        STATUS mandatory
        DESCRIPTION
         "This value means the threshold which is used to limit the rate of PPPoE
          protocol packages sent to OBC..
          The unit is pps.
          Default value(0) means NOT do rate limit.
      ALCATEL NOTE:
                 ACCESS:     NA       USAGE:      OPT
                 PERSIST:    YES      INSRVMOD:   NO
                 RANGE:      0..254   DEFVALUE:   0
                 UNITS:      PPS      SPARSE:     NA
                 DESCR:      NA "
      DEFVAL { 0 }
::= { qosRateLimitProfileEntry 13}

qosRateLimitProfilePppoeBurst OBJECT-TYPE
        SYNTAX INTEGER(0..2147483647)
        ACCESS read-write
        STATUS mandatory
        DESCRIPTION
         "This object is used for burst value which is used to limit the PPPoE packages
          rate to OBC.
          The unit is pps.
          This value should be more than or equals to qosRateLimitProfilePppoeRate
      ALCATEL NOTE:
                 ACCESS:     NA       USAGE:      OPT
                 PERSIST:    YES      INSRVMOD:   NO
                 RANGE:      0..254   DEFVALUE:   0
                 UNITS:      PPS      SPARSE:     NA
                 DESCR:      NA "
::= { qosRateLimitProfileEntry 14}

qosRateLimitProfileNdRate OBJECT-TYPE
        SYNTAX INTEGER(0..2147483647)
        ACCESS read-write
        STATUS mandatory
        DESCRIPTION
         "This value means the threshold which is used to limit the rate of ND
          protocol packages sent to OBC..
          The unit is pps.
          Default value(0) means NOT do rate limit.
      ALCATEL NOTE:
                 ACCESS:     NA       USAGE:      OPT
                 PERSIST:    YES      INSRVMOD:   NO
                 RANGE:      0..254   DEFVALUE:   0
                 UNITS:      PPS      SPARSE:     NA
                 DESCR:      NA "
      DEFVAL { 0 }
::= { qosRateLimitProfileEntry 15}

qosRateLimitProfileNdBurst OBJECT-TYPE
        SYNTAX INTEGER(0..2147483647)
        ACCESS read-write
        STATUS mandatory
        DESCRIPTION
         "This object is used for burst value which is used to limit the ND packages
          rate to OBC.
          The unit is pps.
          This value should be more than or equals to qosRateLimitProfileNdRate
      ALCATEL NOTE:
                 ACCESS:     NA       USAGE:      OPT
                 PERSIST:    YES      INSRVMOD:   NO
                 RANGE:      0..254   DEFVALUE:   0
                 UNITS:      PPS      SPARSE:     NA
                 DESCR:      NA "
::= { qosRateLimitProfileEntry 16}

qosRateLimitProfileIcmpv6Rate OBJECT-TYPE
        SYNTAX INTEGER(0..2147483647)
        ACCESS read-write
        STATUS mandatory
        DESCRIPTION
         "This value means the threshold which is used to limit the rate of ICMPv6
          protocol packages sent to OBC..
          The unit is pps.
          Default value(0) means NOT do rate limit.
      ALCATEL NOTE:
                 ACCESS:     NA       USAGE:      OPT
                 PERSIST:    YES      INSRVMOD:   NO
                 RANGE:      0..254   DEFVALUE:   0
                 UNITS:      PPS      SPARSE:     NA
                 DESCR:      NA "
      DEFVAL { 0 }
::= { qosRateLimitProfileEntry 17}

qosRateLimitProfileIcmpv6Burst OBJECT-TYPE
        SYNTAX INTEGER(0..2147483647)
        ACCESS read-write
        STATUS mandatory
        DESCRIPTION
         "This object is used for burst value which is used to limit the ICMPv6 packages
          rate to OBC.
          The unit is pps.
          This value should be more than or equals to qosRateLimitProfileIcmpv6Rate
      ALCATEL NOTE:
                 ACCESS:     NA       USAGE:      OPT
                 PERSIST:    YES      INSRVMOD:   NO
                 RANGE:      0..254   DEFVALUE:   0
                 UNITS:      PPS      SPARSE:     NA
                 DESCR:      NA "
::= { qosRateLimitProfileEntry 18}

qosRateLimitProfileMldRate OBJECT-TYPE
        SYNTAX INTEGER(0..2147483647)
        ACCESS read-write
        STATUS mandatory
        DESCRIPTION
         "This value means the threshold which is used to limit the rate of MLD
          protocol packages sent to OBC..
          The unit is pps.
          Default value(0) means NOT do rate limit.
      ALCATEL NOTE:
                 ACCESS:     NA       USAGE:      OPT
                 PERSIST:    YES      INSRVMOD:   NO
                 RANGE:      0..254   DEFVALUE:   0
                 UNITS:      PPS      SPARSE:     NA
                 DESCR:      NA "
      DEFVAL { 0 }
::= { qosRateLimitProfileEntry 19}

qosRateLimitProfileMldBurst OBJECT-TYPE
        SYNTAX INTEGER(0..2147483647)
        ACCESS read-write
        STATUS mandatory
        DESCRIPTION
         "This object is used for burst value which is used to limit the MLD packages
          rate to OBC.
          The unit is pps.
          This value should be more than or equals to qosRateLimitProfileMldRate
      ALCATEL NOTE:
                 ACCESS:     NA       USAGE:      OPT
                 PERSIST:    YES      INSRVMOD:   NO
                 RANGE:      0..254   DEFVALUE:   0
                 UNITS:      PPS      SPARSE:     NA
                 DESCR:      NA "
::= { qosRateLimitProfileEntry 20}

qosRateLimitProfileDhcpv6Rate OBJECT-TYPE
        SYNTAX INTEGER(0..2147483647)
        ACCESS read-write
        STATUS mandatory
        DESCRIPTION
         "This value means the threshold which is used to limit the rate of DHCPv6 
          protocol packages sent to OBC..
          The unit is pps.
          Default value(0) means NOT do rate limit.
      ALCATEL NOTE:
                 ACCESS:     NA       USAGE:      OPT
                 PERSIST:    YES      INSRVMOD:   NO
                 RANGE:      0..254   DEFVALUE:   0
                 UNITS:      PPS      SPARSE:     NA
                 DESCR:      NA "
      DEFVAL { 0 }
::= { qosRateLimitProfileEntry 21}

qosRateLimitProfileDhcpv6Burst OBJECT-TYPE
        SYNTAX INTEGER(0..2147483647)
        ACCESS read-write
        STATUS mandatory
        DESCRIPTION
         "This object is used for burst value which is used to limit the DHCPv6 packages
          rate to OBC.
          The unit is pps.
          This value should be more than or equals to qosRateLimitProfileDhcpv6Rate
      ALCATEL NOTE:
                 ACCESS:     NA       USAGE:      OPT
                 PERSIST:    YES      INSRVMOD:   NO
                 RANGE:      0..254   DEFVALUE:   0
                 UNITS:      PPS      SPARSE:     NA
                 DESCR:      NA "
::= { qosRateLimitProfileEntry 22}


qosRateLimitProfileCfmRate OBJECT-TYPE
        SYNTAX INTEGER(0..2147483647)
        ACCESS read-write
        STATUS mandatory
        DESCRIPTION
         "This value means the threshold which is used to limit the rate of CFM
          protocol packages sent to OBC..
          The unit is pps.
          Default value(0) means NOT do rate limit.
      ALCATEL NOTE:
                 ACCESS:     NA       USAGE:      OPT
                 PERSIST:    YES      INSRVMOD:   NO
                 RANGE:      0..254   DEFVALUE:   0
                 UNITS:      PPS      SPARSE:     NA
                 DESCR:      NA "
      DEFVAL { 0 }
::= { qosRateLimitProfileEntry 23}

qosRateLimitProfileCfmBurst OBJECT-TYPE
        SYNTAX INTEGER(0..2147483647)
        ACCESS read-write
        STATUS mandatory
        DESCRIPTION
         "This object is used for burst value which is used to limit the CFM packages
          rate to OBC.
          The unit is pps.
          This value should be more than or equals to qosRateLimitProfileCfmRate
      ALCATEL NOTE:
                 ACCESS:     NA       USAGE:      OPT
                 PERSIST:    YES      INSRVMOD:   NO
                 RANGE:      0..254   DEFVALUE:   0
                 UNITS:      PPS      SPARSE:     NA
                 DESCR:      NA "
::= { qosRateLimitProfileEntry 24}

-- ============================================================================
-- end of qosRateLimitProfileTable
-- ============================================================================

-- ============================================================================
-- qosRateLimitProfile name mapping table
-- ============================================================================

qosRateLimitProfileMappingTable OBJECT-TYPE
        SYNTAX  SEQUENCE OF QosRateLimitProfileMappingEntry
        ACCESS  not-accessible
        STATUS  mandatory
        DESCRIPTION
        "This object contains a table for qosRateLimitProfile
name to index mapping"
::= { qosProfiles 26 }

qosRateLimitProfileMappingEntry OBJECT-TYPE
        SYNTAX  QosRateLimitProfileMappingEntry
        ACCESS  not-accessible
        STATUS mandatory
        DESCRIPTION
        " An entry (conceptual row) representing the qos
Protocol Rate Limit Profile Name to Index mapping. The system automatically creates an
entry in this Table for each corresponding entry (qosRateLimit profile)created in the qosRateLimitProfileTable.  Similarly, when an qosRateLimit profile is deleted, the corresponding entry in this table is also automatically deleted by the system."
        INDEX   {qosRateLimitProfileMappingName }
        ::= {qosRateLimitProfileMappingTable  1}

QosRateLimitProfileMappingEntry ::=
        SEQUENCE {
qosRateLimitProfileMappingName     AsamProfileName,
                qosRateLimitProfileMappingIndex      AsamProfileIndex
                        }

qosRateLimitProfileMappingName OBJECT-TYPE
        SYNTAX  AsamProfileName
        ACCESS  not-accessible
        STATUS  mandatory
        DESCRIPTION
                "A text string containing the name of this profile.
      ALCATEL NOTE:
                 ACCESS:     NA       USAGE:      NA
                 PERSIST:    NO       INSRVMOD:   NO
                 RANGE:      NA       DEFVALUE:   NA
                 UNITS:      NA       SPARSE:     NA
                 DESCR:      NA "
::= { qosRateLimitProfileMappingEntry 1}

qosRateLimitProfileMappingIndex OBJECT-TYPE
        SYNTAX  AsamProfileIndex
        ACCESS  read-only
        STATUS mandatory
        DESCRIPTION
                "This object is the Profile index.
     ALCATEL NOTE:
                 ACCESS:     NA       USAGE:      NA
                 PERSIST:    NO       INSRVMOD:   NO
                 RANGE:      NA       DEFVALUE:   NA
                 UNITS:      NA       SPARSE:     NA
                 DESCR:      NA "
::= { qosRateLimitProfileMappingEntry 2}

-- ============================================================================
--
-- End of qosRateLimitProfile name mapping table
--
-- ============================================================================

-- ============================================================================
--
-- Beginning of qosDscpToDot1PAlignProfileProfileTable
--
-- ============================================================================

qosDscpToDot1PAlignProfileTable OBJECT-TYPE
        SYNTAX	SEQUENCE OF QosDscpToDot1PAlignProfileEntry
	       ACCESS	not-accessible
	       STATUS	mandatory
	       DESCRIPTION
	             "This object contains a table for creating and storing
              	DscpToDot1PAlign profiles. A DscpToDot1PAlign profile contains
               a mapping between DSCP codepoints and associated PBit values. "
::= { qosProfiles 27 }

qosDscpToDot1PAlignProfileEntry OBJECT-TYPE
        SYNTAX 	QosDscpToDot1PAlignProfileEntry
        ACCESS	not-accessible
        STATUS	mandatory
        DESCRIPTION
		             "Rows of this table contain QoS DscpToDot1PAlign Profiles"
        INDEX {qosDscpToDot1PAlignProfileIndex }
::= {qosDscpToDot1PAlignProfileTable 1}

QosDscpToDot1PAlignProfileEntry ::=
        SEQUENCE { 
		                 qosDscpToDot1PAlignProfileIndex		    AsamProfileIndex,
		                 qosDscpToDot1PAlignProfileName	      AsamProfileName,
                   qosDscpToDot1PAlignProfileRowStatus  RowStatus,
                   qosDscpToDot1PAlignProfileRefCount	  AsamProfileRefCount32,
                   qosDscpToDot1PAlignProfileMapping	   OCTET STRING
                 }

qosDscpToDot1PAlignProfileIndex OBJECT-TYPE
        SYNTAX AsamProfileIndex
        ACCESS not-accessible
        STATUS mandatory
        DESCRIPTION
              "This object is the index to the qosDscpToDot1PAlignProfileTable.
        ALCATEL NOTE:
                ACCESS:     NA       USAGE:      NA
                PERSIST:    YES      INSRVMOD:   NO
                RANGE:      NA       DEFVALUE:   NA
                UNITS:      NA       SPARSE:     NA
                DESCR:      NA "
::= { qosDscpToDot1PAlignProfileEntry 1}

qosDscpToDot1PAlignProfileName 	OBJECT-TYPE
        SYNTAX	AsamProfileName
        ACCESS read-write
        STATUS mandatory
        DESCRIPTION
               "Octet string storing the operator-given name of the profile.
        ALCATEL NOTE:
                ACCESS:     NA       USAGE:      NA
                PERSIST:    YES      INSRVMOD:   NO
                RANGE:      NA       DEFVALUE:   NA
                UNITS:      NA       SPARSE:     NA
                DESCR:      NA "
::= {qosDscpToDot1PAlignProfileEntry 2}

qosDscpToDot1PAlignProfileRowStatus OBJECT-TYPE
        SYNTAX	RowStatus
        ACCESS	read-write
        STATUS mandatory
        DESCRIPTION
               "This object is used to create a new row or modify or
               delete an existing row in this table. The usage is as per
               standard semantics of 'RowStatus' defined in SNMPv2-TC.
        ALCATEL NOTE:
                 ACCESS:     NA       USAGE:      NA
                 PERSIST:    YES      INSRVMOD:   NO
                 RANGE:      NA       DEFVALUE:   NA
                 UNITS:      NA       SPARSE:     NA
                 DESCR:      NA "
::= { qosDscpToDot1PAlignProfileEntry 3}

qosDscpToDot1PAlignProfileRefCount OBJECT-TYPE
        SYNTAX	AsamProfileRefCount32
        ACCESS read-only
        STATUS	mandatory
        DESCRIPTION
               "Indicates the number of entities using this profile. If the
               reference count is greater than 0, then this profile is 'in use',
               and may NOT be deleted. If the value is 0, then this profile is
               'not in use', and can be deleted.
        ALCATEL NOTE:
                 ACCESS:     NA       USAGE:      NA
                 PERSIST:    YES      INSRVMOD:   NO
                 RANGE:      NA       DEFVALUE:   NA
                 UNITS:      NA       SPARSE:     NA
                 DESCR:      NA "
::= { qosDscpToDot1PAlignProfileEntry 4}

qosDscpToDot1PAlignProfileMapping OBJECT-TYPE
        SYNTAX OCTET STRING (SIZE(24))
        ACCESS read-write
        STATUS mandatory
        DESCRIPTION
               "This structure specifies mappings from DSCP value to Pbit value.
               The structure can be considered a bit string sequence of 64 '3-bit' groups.
               The 64 sequence entries represent the possible value of the 6-bit DSCP field.
               Each '3-bit' group specifies the Pbit value to which the associated DSCP 
               value should be mapped.

               The high-order 3 bits of the high-order byte represents the Pbit value
               associated with DSCP value 0.
               The low-order 3 bits of the low-order byte represents the Pbit value
               associated with DSCP value 63.
        ALCATEL NOTE:
                 ACCESS:     NA       USAGE:      NA
                 PERSIST:    YES      INSRVMOD:   NO
                 RANGE:      NA       DEFVALUE:   NA
                 UNITS:      NA       SPARSE:     NA
                 DESCR:      NA "
::= { qosDscpToDot1PAlignProfileEntry 5}

-- ============================================================================
--
-- End of qosDscpToDot1PAlignProfileProfileTable
--
-- ============================================================================

-- ============================================================================
--
-- Beginning of qosDscpToDot1PAlignProfile name mapping table
--
-- ============================================================================

qosDscpToDot1PAlignProfileMappingTable OBJECT-TYPE
        SYNTAX	SEQUENCE OF QosDscpToDot1PAlignProfileMappingEntry
        ACCESS	not-accessible
        STATUS	mandatory
        DESCRIPTION
               "This object contains a table for qosDscpToDot1PAlignProfile
               name to index mapping"
::= { qosProfiles 28 }

qosDscpToDot1PAlignProfileMappingEntry OBJECT-TYPE
        SYNTAX QosDscpToDot1PAlignProfileMappingEntry
        ACCESS	not-accessible
        STATUS mandatory
        DESCRIPTION
               "An entry (conceptual row) representing the qosDscpToDot1PAlign Profile Name to Index mapping. 
               The system automatically creates an entry in this Table for each corresponding entry created in the
               qosDscpToDot1PAlignProfileTable.  Similarly, when an qosDscpToDot1PAlign profile is deleted,
               the corresponding entry in this table is also automatically deleted by the system."
        INDEX	{qosDscpToDot1PAlignProfileMappingName }
::= {qosDscpToDot1PAlignProfileMappingTable  1}

QosDscpToDot1PAlignProfileMappingEntry ::=
        SEQUENCE {
                   qosDscpToDot1PAlignProfileMappingName    AsamProfileName,
                   qosDscpToDot1PAlignProfileMappingIndex   AsamProfileIndex
                 }

qosDscpToDot1PAlignProfileMappingName OBJECT-TYPE
        SYNTAX	AsamProfileName
        ACCESS	not-accessible
        STATUS mandatory
        DESCRIPTION
               "A text string containing the name of this profile.
        ALCATEL NOTE:
                 ACCESS:     NA       USAGE:      NA
                 PERSIST:    YES      INSRVMOD:   NO
                 RANGE:      NA       DEFVALUE:   NA
                 UNITS:      NA       SPARSE:     NA
                 DESCR:      NA "
::= { qosDscpToDot1PAlignProfileMappingEntry 1}

qosDscpToDot1PAlignProfileMappingIndex OBJECT-TYPE
        SYNTAX	AsamProfileIndex
        ACCESS	read-only
        STATUS mandatory
        DESCRIPTION
	              "This object is the Profile index. 
        ALCATEL NOTE:
                 ACCESS:     NA       USAGE:      NA
                 PERSIST:    YES      INSRVMOD:   NO
                 RANGE:      NA       DEFVALUE:   NA
                 UNITS:      NA       SPARSE:     NA
                 DESCR:      NA "
::= { qosDscpToDot1PAlignProfileMappingEntry 2}

-- ============================================================================
--
-- End of qosDscpToDot1PAlignProfile name mapping table
--
-- ============================================================================

-- qosCoSThresholdProfile                                                       
qosCoSThresholdProfileTable OBJECT-TYPE                                         
 	  SYNTAX	SEQUENCE OF QosCoSThresholdProfileEntry                                
 	  ACCESS	not-accessible                                                             
 	  STATUS	mandatory                                                                  
 	  DESCRIPTION                                                                        
 	      "This object contains a table for creating and storing                             
 	       cos threshold profiles. A cos threshold profile
 	       contains threshold information for tcs within
 	       the session to which this policer profile is attached."                                                                              
    ::= { qosProfiles 29 }                                                              

qosCoSThresholdProfileEntry OBJECT-TYPE
    SYNTAX 	QosCoSThresholdProfileEntry
    ACCESS	not-accessible
    STATUS	mandatory
    DESCRIPTION
		"Rows of this table contain QoS CoS Threshold Profiles"
    INDEX {qosCoSThresholdProfileIndex }
    ::= {qosCoSThresholdProfileTable 1}

QosCoSThresholdProfileEntry ::=
    SEQUENCE{ 
    qosCoSThresholdProfileIndex           AsamProfileIndex,
    qosCoSThresholdProfileName            AsamProfileName,
    qosCoSThresholdProfileRefCount        AsamProfileRefCount32,
    qosCoSThresholdProfileTc0Threshold    INTEGER,
    qosCoSThresholdProfileTc1Threshold    INTEGER,
    qosCoSThresholdProfileTc2Threshold    INTEGER,
    qosCoSThresholdProfileTc3Threshold    INTEGER,
    qosCoSThresholdProfileTc4Threshold    INTEGER,
    qosCoSThresholdProfileTc5Threshold    INTEGER,
    qosCoSThresholdProfileTc6Threshold    INTEGER,
    qosCoSThresholdProfileTc7Threshold    INTEGER,
    qosCoSThresholdProfileRowStatus       RowStatus
    }
				
qosCoSThresholdProfileIndex OBJECT-TYPE
    SYNTAX AsamProfileIndex
    ACCESS not-accessible
    STATUS mandatory
    DESCRIPTION
    "This object is the index to the qosCoSThresholdProfileTable."
::= { qosCoSThresholdProfileEntry 1}

qosCoSThresholdProfileName 	OBJECT-TYPE
    SYNTAX AsamProfileName
    ACCESS read-write
    STATUS mandatory
    DESCRIPTION
    "Octet string storing the operator-given name of the profile"
::= {qosCoSThresholdProfileEntry 2}

qosCoSThresholdProfileRefCount OBJECT-TYPE
    SYNTAX AsamProfileRefCount32
    ACCESS read-only
    STATUS mandatory
    DESCRIPTION
    "Indicates the number of entities using this profile. If the
    reference count is greater than 0, then this profile is 'in use',
    and may NOT be deleted. If the value is 0, then this profile is
    'not in use', and can be deleted."
::= { qosCoSThresholdProfileEntry 3}

qosCoSThresholdProfileTc0Threshold OBJECT-TYPE
    SYNTAX INTEGER(0..100)
    ACCESS read-write
    STATUS mandatory
    DESCRIPTION
    "This object stores the bucket drop percent for TC0. 
    Cannot be negative."
    DEFVAL { 0 }
::= { qosCoSThresholdProfileEntry 4}

qosCoSThresholdProfileTc1Threshold OBJECT-TYPE
    SYNTAX INTEGER(0..100)
    ACCESS read-write
    STATUS mandatory
    DESCRIPTION
    "This object stores the bucket drop percent for TC1. 
    Cannot be negative."
    DEFVAL { 0 }
::= { qosCoSThresholdProfileEntry 5}

qosCoSThresholdProfileTc2Threshold OBJECT-TYPE
    SYNTAX INTEGER(0..100)
    ACCESS read-write
    STATUS mandatory
    DESCRIPTION
    "This object stores the bucket drop percent for TC2. 
    Cannot be negative."
    DEFVAL { 0 }
::= { qosCoSThresholdProfileEntry 6}

qosCoSThresholdProfileTc3Threshold OBJECT-TYPE
    SYNTAX INTEGER(0..100)
    ACCESS read-write
    STATUS mandatory
    DESCRIPTION
    "This object stores the bucket drop percent for TC3. 
    Cannot be negative."
    DEFVAL { 0 }
::= { qosCoSThresholdProfileEntry 7}

qosCoSThresholdProfileTc4Threshold OBJECT-TYPE
    SYNTAX INTEGER(0..100)
    ACCESS read-write
    STATUS mandatory
    DESCRIPTION
    "This object stores the bucket drop percent for TC4. 
    Cannot be negative."
    DEFVAL { 0 }
::= { qosCoSThresholdProfileEntry 8}

qosCoSThresholdProfileTc5Threshold OBJECT-TYPE
    SYNTAX INTEGER(0..100)
    ACCESS read-write
    STATUS mandatory
    DESCRIPTION
    "This object stores the bucket drop percent for TC5. 
    Cannot be negative."
    DEFVAL { 0 }
::= { qosCoSThresholdProfileEntry 9}

qosCoSThresholdProfileTc6Threshold OBJECT-TYPE
    SYNTAX INTEGER(0..100)
    ACCESS read-write
    STATUS mandatory
    DESCRIPTION
    "This object stores the bucket drop percent for TC6. 
    Cannot be negative."
    DEFVAL { 0 }
::= { qosCoSThresholdProfileEntry 10}

qosCoSThresholdProfileTc7Threshold OBJECT-TYPE
    SYNTAX INTEGER(0..100)
    ACCESS read-write
    STATUS mandatory
    DESCRIPTION
    "This object stores the bucket drop percent for TC7. 
    Cannot be negative."
    DEFVAL { 0 }
::= { qosCoSThresholdProfileEntry 11}

qosCoSThresholdProfileRowStatus OBJECT-TYPE
    SYNTAX RowStatus
    ACCESS read-write
    STATUS mandatory
    DESCRIPTION
    "This object is used to create a new row or modify or
    delete an existing row in this table. The usage is as per
    standard semantics of 'RowStatus' defined in SNMPv2-TC, with
    following limitations:
    The entry associated with a Profile that is being used may
    not be deleted."
::= { qosCoSThresholdProfileEntry 12}


-- qosCoSThresholdProfile name mapping table

qosCoSThresholdProfileMappingTable OBJECT-TYPE
    SYNTAX	SEQUENCE OF QosCoSThresholdProfileMappingEntry
    ACCESS	not-accessible
    STATUS	mandatory
    DESCRIPTION
    "This object contains a table for qosCoSThresholdProfile
name to index mapping"
::= { qosProfiles 30 }

qosCoSThresholdProfileMappingEntry OBJECT-TYPE
    SYNTAX 	QosCoSThresholdProfileMappingEntry
    ACCESS	not-accessible
    STATUS mandatory
    DESCRIPTION
    "An entry (conceptual row) representing the qos
    policer threshold Profile Name to Index mapping. The system automatically 
    creates an entry in this Table for each corresponding entry 
    (qosCoSThreshold profile)created in the qosCoSThresholdProfileTable.
    Similarly, when an qosCoSThreshold profile is deleted, the corresponding
    entry in this table is also automatically deleted by the system."
    INDEX	{qosCoSThresholdProfileMappingName }
    ::= {qosCoSThresholdProfileMappingTable  1}

QosCoSThresholdProfileMappingEntry ::=
    SEQUENCE 
    { 
        qosCoSThresholdProfileMappingName     AsamProfileName,
        qosCoSThresholdProfileMappingIndex    AsamProfileIndex
    }

qosCoSThresholdProfileMappingName OBJECT-TYPE
    SYNTAX	AsamProfileName
    ACCESS	not-accessible
    STATUS  mandatory
    DESCRIPTION
    "A text string containing the name of this profile.
    ALCATEL NOTE:
    ACCESS:     NA       USAGE:      NA
    PERSIST:    YES       INSRVMOD:   NO
    RANGE:      NA       DEFVALUE:   NA
    UNITS:      NA       SPARSE:     NA
    DESCR:      NA "
::= { qosCoSThresholdProfileMappingEntry 1}

qosCoSThresholdProfileMappingIndex OBJECT-TYPE
    SYNTAX	AsamProfileIndex
    ACCESS	read-only
    STATUS mandatory
    DESCRIPTION
    "This object is the Profile index. 
    ALCATEL NOTE:
    ACCESS:     NA       USAGE:      NA
    PERSIST:    YES       INSRVMOD:   NO
    RANGE:      NA       DEFVALUE:   NA
    UNITS:      NA       SPARSE:     NA
    DESCR:      NA "
::= { qosCoSThresholdProfileMappingEntry 2}

-- End of qosCoSThresholdProfile name mapping table

-- qosPolicerPerTcProfile                                                       
qosPolicerPerTcProfileTable OBJECT-TYPE                                         
 	  SYNTAX	SEQUENCE OF QosPolicerPerTcProfileEntry                                
 	  ACCESS	not-accessible                                                             
 	  STATUS	mandatory                                                                  
 	  DESCRIPTION                                                                        
 	      "This object contains a table for creating and storing                             
 	       policerPerTc profiles. A policerPerTc profile contains policing
 	       information per TCs for frames within the session to which this
 	       policerPerTc profile is attached."                                                                              
    ::= { qosProfiles 31 }                                                              

qosPolicerPerTcProfileEntry OBJECT-TYPE
    SYNTAX 	QosPolicerPerTcProfileEntry
    ACCESS	not-accessible
    STATUS	mandatory
    DESCRIPTION
		"Rows of this table contain QoS policerPerTc Profiles"
    INDEX {qosPolicerPerTcProfileIndex }
    ::= {qosPolicerPerTcProfileTable 1}

QosPolicerPerTcProfileEntry ::=
    SEQUENCE{ 
    qosPolicerPerTcProfileIndex           AsamProfileIndex,
    qosPolicerPerTcProfileName            AsamProfileName,
    qosPolicerPerTcProfileRefCount        AsamProfileRefCount32,
    qosPolicerPerTcProfilePolicers         PolicerPerTcList ,
    qosPolicerPerTcProfileRowStatus       RowStatus
    }
				
qosPolicerPerTcProfileIndex OBJECT-TYPE
    SYNTAX AsamProfileIndex
    ACCESS not-accessible
    STATUS mandatory
    DESCRIPTION
    "This object is the index to the qosPolicerPerTcProfileTable."
::= { qosPolicerPerTcProfileEntry 1}

qosPolicerPerTcProfileName 	OBJECT-TYPE
    SYNTAX AsamProfileName
    ACCESS read-write
    STATUS mandatory
    DESCRIPTION
    "Octet string storing the operator-given name of the profile"
::= {qosPolicerPerTcProfileEntry 2}

qosPolicerPerTcProfileRefCount OBJECT-TYPE
    SYNTAX AsamProfileRefCount32
    ACCESS read-only
    STATUS mandatory
    DESCRIPTION
    "Indicates the number of entities using this profile. If the
    reference count is greater than 0, then this profile is 'in use',
    and may NOT be deleted. If the value is 0, then this profile is
    'not in use', and can be deleted."
::= { qosPolicerPerTcProfileEntry 3}

qosPolicerPerTcProfilePolicers OBJECT-TYPE
	SYNTAX PolicerPerTcList 
	ACCESS read-write
	STATUS mandatory
	DESCRIPTION
	 "The following mapping applies:
          The policerId corresponding to TC 0 is indicated in bytes 0-1, the polcerId corresponding 
          to TC 1 in indicated in bytes 2-3, etc... Graphical representation is given below :
          bytes14-15 bytes12-13 bytes10-11 bytes8-9 bytes6-7 bytes4-5 bytes2-3 bytes0-1 
           TC-7        TC-6       TC-5      TC-4      TC-3      TC-2      TC-1     TC-0
ALCATEL NOTE:
                 ACCESS:     RO       USAGE:      NA
                 PERSIST:    YES      INSRVMOD:   NO
                 RANGE:      NA       DEFVALUE:   NA
                 UNITS:      NA       SPARSE:     NA
                 DESCR:      NA."
::= { qosPolicerPerTcProfileEntry 4}

qosPolicerPerTcProfileRowStatus OBJECT-TYPE
    SYNTAX RowStatus
    ACCESS read-write
    STATUS mandatory
    DESCRIPTION
    "This object is used to create a new row or modify or
    delete an existing row in this table. The usage is as per
    standard semantics of 'RowStatus' defined in SNMPv2-TC, with
    following limitations:
    The entry associated with a Profile that is being used may
    not be deleted."
::= { qosPolicerPerTcProfileEntry 5}


-- qosPolicerPerTcProfile name mapping table

qosPolicerPerTcProfileMappingTable OBJECT-TYPE
    SYNTAX	SEQUENCE OF QosPolicerPerTcProfileMappingEntry
    ACCESS	not-accessible
    STATUS	mandatory
    DESCRIPTION
    "This object contains a table for qosPolicerPerTcProfile
name to index mapping"
::= { qosProfiles 32 }

qosPolicerPerTcProfileMappingEntry OBJECT-TYPE
    SYNTAX 	QosPolicerPerTcProfileMappingEntry
    ACCESS	not-accessible
    STATUS mandatory
    DESCRIPTION
    "An entry (conceptual row) representing the qos
    policerPerTc Profile Name to Index mapping. The system automatically 
    creates an entry in this Table for each corresponding entry 
    (qosPolicerPerTc profile)created in the qosPolicerPerTcProfileTable.
    Similarly, when an qosPolicerPerTc profile is deleted, the corresponding
    entry in this table is also automatically deleted by the system."
    INDEX	{qosPolicerPerTcProfileMappingName }
    ::= {qosPolicerPerTcProfileMappingTable  1}

QosPolicerPerTcProfileMappingEntry ::=
    SEQUENCE 
    { 
        qosPolicerPerTcProfileMappingName     AsamProfileName,
        qosPolicerPerTcProfileMappingIndex    AsamProfileIndex
    }

qosPolicerPerTcProfileMappingName OBJECT-TYPE
    SYNTAX	AsamProfileName
    ACCESS	not-accessible
    STATUS  mandatory
    DESCRIPTION
    "A text string containing the name of this profile.
    ALCATEL NOTE:
    ACCESS:     NA       USAGE:      NA
    PERSIST:    YES       INSRVMOD:   NO
    RANGE:      NA       DEFVALUE:   NA
    UNITS:      NA       SPARSE:     NA
    DESCR:      NA "
::= { qosPolicerPerTcProfileMappingEntry 1}

qosPolicerPerTcProfileMappingIndex OBJECT-TYPE
    SYNTAX	AsamProfileIndex
    ACCESS	read-only
    STATUS mandatory
    DESCRIPTION
    "This object is the Profile index. 
    ALCATEL NOTE:
    ACCESS:     NA       USAGE:      NA
    PERSIST:    YES       INSRVMOD:   NO
    RANGE:      NA       DEFVALUE:   NA
    UNITS:      NA       SPARSE:     NA
    DESCR:      NA "
::= { qosPolicerPerTcProfileMappingEntry 2}

-- End of qosPolicerPerTcProfile name mapping table

qosBandwidthProfileActualValuesTable OBJECT-TYPE
	SYNTAX	SEQUENCE OF QosBandwidthProfileActualValuesEntry
	ACCESS	not-accessible
	STATUS	mandatory
	DESCRIPTION
	"This object contains a table for retrieving
	bandwidth profiles adjusted DT, CIR, AIR, EIR values."
::= { qosProfiles 33 }

qosBandwidthProfileActualValuesEntry OBJECT-TYPE
	SYNTAX 	QosBandwidthProfileActualValuesEntry
	ACCESS	not-accessible
	STATUS	mandatory
	DESCRIPTION
		"Rows of this table contain QoS Bandwidth Profiles actual CIR, AIR, EIR and DT Values"
	INDEX {qosBandwidthProfileIndex, ponTechnologyType }
::= { qosBandwidthProfileActualValuesTable 1}

QosBandwidthProfileActualValuesEntry ::=
	SEQUENCE {
        ponTechnologyType INTEGER,
        qosBandwidthProfileActualCIR        INTEGER,
        qosBandwidthProfileActualAIR        INTEGER,
        qosBandwidthProfileActualEIR        INTEGER,
        qosBandwidthProfileActualDelayTolerance INTEGER
	         }
ponTechnologyType OBJECT-TYPE
	SYNTAX INTEGER {
	   gpon(1),
	   xgpon(2),
	   ngpon2(3)
	}
	ACCESS not-accessible
	STATUS mandatory
	DESCRIPTION
	 "This object is the pon technology. Based on the pon type to which profile is applied,
	  values are adjusted accordingly.
	 ALCATEL NOTE:
                 ACCESS:     NA       USAGE:      NA
                 PERSIST:    NO       INSRVMOD:   NA
                 RANGE:      1..3
                 DEFVALUE:   NA
                 UNITS:      NA       SPARSE:     NA
                 DESCR:      NA
                 As of ISAM5.3 release, this attribute is SUPPORTED."
::= { qosBandwidthProfileActualValuesEntry 1}

qosBandwidthProfileActualCIR OBJECT-TYPE
	SYNTAX INTEGER
	ACCESS read-only
	STATUS mandatory
	DESCRIPTION
	 "This object is actual Committed Information Rate (CIR) depending on ponType.
	 ALCATEL NOTE:
                 ACCESS:     NA       USAGE:      NA
                 PERSIST:    NO       INSRVMOD:   NA
                 RANGE:      0..10000000
                 DEFVALUE:   NA
                 UNITS:      kbps     SPARSE:     NA
                 DESCR:      NA
                 As of ISAM5.3 release, this attribute is SUPPORTED."
::= { qosBandwidthProfileActualValuesEntry 2}

qosBandwidthProfileActualAIR OBJECT-TYPE
	SYNTAX INTEGER
	ACCESS read-only
	STATUS mandatory
	DESCRIPTION
	 "This object is actual Assured Information Rate (AIR) depending on ponType.
	 ALCATEL NOTE:
                 ACCESS:     NA       USAGE:      NA
                 PERSIST:    NO       INSRVMOD:   NA
                 RANGE:      0..10000000
                 DEFVALUE:   NA
                 UNITS:      kbps     SPARSE:     NA
                 DESCR:      NA
                 As of ISAM5.3 release, this attribute is SUPPORTED."
::= { qosBandwidthProfileActualValuesEntry 3}

qosBandwidthProfileActualEIR OBJECT-TYPE
	SYNTAX INTEGER
	ACCESS read-only
	STATUS mandatory
	DESCRIPTION
	 "This object is actual Excess Information Rate (EIR) depending on ponType.
	 ALCATEL NOTE:
                 ACCESS:     NA       USAGE:      NA
                 PERSIST:    NO       INSRVMOD:   NA
                 RANGE:      0..10000000
                 DEFVALUE:   NA
                 UNITS:      kbps     SPARSE:     NA
                 DESCR:      NA
                 As of ISAM5.3 release, this attribute is SUPPORTED."
::= { qosBandwidthProfileActualValuesEntry 4}

qosBandwidthProfileActualDelayTolerance OBJECT-TYPE
	SYNTAX INTEGER
	ACCESS read-only
	STATUS mandatory
	DESCRIPTION
	 "This object is actual delay tolerance of a shaper in units of 125 microseconds.
	 ALCATEL NOTE:
                 ACCESS:     NA       USAGE:      NA
                 PERSIST:    NO       INSRVMOD:   NA
                 RANGE:      1..240
                 DEFVALUE:   NA
                 UNITS:      NA       SPARSE:     NA
                 DESCR:      NA
                 As of ISAM5.3 release, this attribute is SUPPORTED."
::= { qosBandwidthProfileActualValuesEntry 5}

-- end of qosBandwidthProfileActualValuesTable
--	Begin of qosAggrQueuesConfigProfile table 

qosAggrQueuesConfigProfileTable OBJECT-TYPE                                         
 	  SYNTAX	SEQUENCE OF QosAggrQueuesConfigProfileEntry
 	  ACCESS	not-accessible                                                             
 	  STATUS	mandatory                                                                  
 	  DESCRIPTION                                                                        
 	      "This object contains a table for creating and storing                             
 	       aggrQueuesConfig profiles. An aggrQueuesConfig profile contains the attributes of 8 queues."                                                                              
    ::= { qosProfiles 34 }                                                              

qosAggrQueuesConfigProfileEntry OBJECT-TYPE
    SYNTAX 	QosAggrQueuesConfigProfileEntry
    ACCESS	not-accessible
    STATUS	mandatory
    DESCRIPTION
		"Rows of this table contain QoS aggrQueuesConfig Profiles"
    INDEX {qosAggrQueuesConfigProfileIndex }
    ::= { qosAggrQueuesConfigProfileTable 1}

QosAggrQueuesConfigProfileEntry::=
    SEQUENCE{ 
    qosAggrQueuesConfigProfileIndex           AsamProfileIndex,
    qosAggrQueuesConfigProfileName            AsamProfileName,
    qosAggrQueuesConfigProfileRefCount        AsamProfileRefCount32,   
    qosAggrQueuesConfigProfileRowStatus       RowStatus,
    qosAggrQueuesConfigPriorities      INTEGER,  
    qosAggrQueuesConfigQ0Weight               INTEGER,
    qosAggrQueuesConfigQ1Weight               INTEGER,
    qosAggrQueuesConfigQ2Weight               INTEGER,
    qosAggrQueuesConfigQ3Weight               INTEGER,
    qosAggrQueuesConfigQ4Weight               INTEGER,
    qosAggrQueuesConfigQ5Weight               INTEGER,
    qosAggrQueuesConfigQ6Weight               INTEGER,
    qosAggrQueuesConfigQ7Weight               INTEGER,   
    qosAggrQueuesConfigQ0ShaperProfId      AsamProfilePointer,
    qosAggrQueuesConfigQ1ShaperProfId      AsamProfilePointer,
    qosAggrQueuesConfigQ2ShaperProfId      AsamProfilePointer,
    qosAggrQueuesConfigQ3ShaperProfId      AsamProfilePointer,
    qosAggrQueuesConfigQ4ShaperProfId      AsamProfilePointer,
    qosAggrQueuesConfigQ5ShaperProfId      AsamProfilePointer,
    qosAggrQueuesConfigQ6ShaperProfId      AsamProfilePointer,
    qosAggrQueuesConfigQ7ShaperProfId      AsamProfilePointer,
    qosAggrQueuesConfigQ0BacProfId            AsamProfilePointer,
    qosAggrQueuesConfigQ1BacProfId            AsamProfilePointer,
    qosAggrQueuesConfigQ2BacProfId            AsamProfilePointer,
    qosAggrQueuesConfigQ3BacProfId            AsamProfilePointer,
    qosAggrQueuesConfigQ4BacProfId            AsamProfilePointer,
    qosAggrQueuesConfigQ5BacProfId            AsamProfilePointer,
    qosAggrQueuesConfigQ6BacProfId            AsamProfilePointer,
    qosAggrQueuesConfigQ7BacProfId            AsamProfilePointer,
    qosAggrQueuesConfigQ0BandwidthProfId      AsamProfilePointer, 
    qosAggrQueuesConfigQ1BandwidthProfId      AsamProfilePointer, 
    qosAggrQueuesConfigQ2BandwidthProfId      AsamProfilePointer, 
    qosAggrQueuesConfigQ3BandwidthProfId      AsamProfilePointer, 
    qosAggrQueuesConfigQ4BandwidthProfId      AsamProfilePointer, 
    qosAggrQueuesConfigQ5BandwidthProfId      AsamProfilePointer, 
    qosAggrQueuesConfigQ6BandwidthProfId      AsamProfilePointer, 
    qosAggrQueuesConfigQ7BandwidthProfId      AsamProfilePointer, 
    qosAggrQueuesConfigBandwidthSharing       INTEGER
    }
				
qosAggrQueuesConfigProfileIndex OBJECT-TYPE
    SYNTAX AsamProfileIndex
    ACCESS not-accessible
    STATUS mandatory
    DESCRIPTION
"This object is the index to the qosAggrQueuesConfigProfileTable.
ALCATEL NOTE:
                 ACCESS:     RW       USAGE:      NA
                 PERSIST:    YES      INSRVMOD:   NO
                 RANGE:      NA       DEFVALUE:   NA
                 UNITS:      NA       SPARSE:     NA
             DESCR:      NA."
::= { qosAggrQueuesConfigProfileEntry 1}

qosAggrQueuesConfigProfileName 	OBJECT-TYPE
    SYNTAX AsamProfileName
    ACCESS read-write
    STATUS mandatory
    DESCRIPTION
"Octet string storing the operator-given name of the profile.
ALCATEL NOTE:
                 ACCESS:     RW       USAGE:      NA
                 PERSIST:    YES      INSRVMOD:   NO
                 RANGE:      NA       DEFVALUE:   NA
                 UNITS:      NA       SPARSE:     NA
             DESCR:      NA."
::= { qosAggrQueuesConfigProfileEntry 2}

qosAggrQueuesConfigProfileRefCount OBJECT-TYPE
    SYNTAX AsamProfileRefCount32
    ACCESS read-only
    STATUS mandatory
    DESCRIPTION
    "Indicates the number of entities using this profile. If the
    reference count is greater than 0, then this profile is 'in use',
    and may NOT be deleted. If the value is 0, then this profile is
'not in use', and can be deleted.
ALCATEL NOTE:
                 ACCESS:     RO       USAGE:      NA
                 PERSIST:    YES      INSRVMOD:   NO
                 RANGE:      NA       DEFVALUE:   NA
                 UNITS:      NA       SPARSE:     NA
             DESCR:      NA."
::= { qosAggrQueuesConfigProfileEntry 3}

qosAggrQueuesConfigProfileRowStatus OBJECT-TYPE
    SYNTAX RowStatus
    ACCESS read-write
    STATUS mandatory
    DESCRIPTION
    "This object is used to create a new row or modify or
    delete an existing row in this table. The usage is as per
    standard semantics of 'RowStatus' defined in SNMPv2-TC, with
    following limitations:
    The entry associated with a Profile that is being used may
not be deleted.
ALCATEL NOTE:
                 ACCESS:     RW       USAGE:      NA
                 PERSIST:    YES      INSRVMOD:   NO
                 RANGE:      NA       DEFVALUE:   NA
                 UNITS:      NA       SPARSE:     NA
                 DESCR:      NA."
::= { qosAggrQueuesConfigProfileEntry 4}

qosAggrQueuesConfigPriorities OBJECT-TYPE
        SYNTAX  INTEGER
        ACCESS  read-write
        STATUS mandatory
        DESCRIPTION
         "The configured priorities of 8 queues. The priorities and queues mapping see following:
          Bits28-31 bits24-27 bits20-23 bits16-19 bits12-15 bits8-11 bits4-7 bits0-3 
          queue-7   queue-6   queue-5    queue-4   queue-3   queue-2  queue-1 queue-0.
The valid priority range of each queue is from 1 to 8. 8 means highest priority and 1 means lowest priority. The default priority each queue is 1. So the default value is 0x11111111. 
ALCATEL NOTE:
                 ACCESS:     RW       USAGE:      NA
                 PERSIST:    YES      INSRVMOD:   NO
                 RANGE:      NA       DEFVALUE:   0x11111111
                 UNITS:      NA       SPARSE:     NA
                 DESCR:      NA."
::= { qosAggrQueuesConfigProfileEntry 5}

qosAggrQueuesConfigQ0Weight OBJECT-TYPE
        SYNTAX  INTEGER (0..127)
        ACCESS  read-write
        STATUS mandatory
        DESCRIPTION
         "The configured weights of queue 0. It is in the range 0..127. The dault weight of each queue is 1.
ALCATEL NOTE:
                 ACCESS:     RW       USAGE:      NA
                 PERSIST:    YES      INSRVMOD:   NO
                 RANGE:      NA       DEFVALUE:   1
                 UNITS:      NA       SPARSE:     NA
                 DESCR:      NA."
::= { qosAggrQueuesConfigProfileEntry 6}

qosAggrQueuesConfigQ1Weight OBJECT-TYPE
        SYNTAX  INTEGER ( 0..127)
        ACCESS  read-write
        STATUS mandatory
        DESCRIPTION
         "The configured weights of queue 1. It is in the range 0..127. The dault weight of each queue is 1.
ALCATEL NOTE:
                 ACCESS:     RW       USAGE:      NA
                 PERSIST:    YES      INSRVMOD:   NO
                 RANGE:      NA       DEFVALUE:   1
                 UNITS:      NA       SPARSE:     NA
                 DESCR:      NA."
::= { qosAggrQueuesConfigProfileEntry 7}

qosAggrQueuesConfigQ2Weight OBJECT-TYPE
        SYNTAX  INTEGER ( 0..127)
        ACCESS  read-write
        STATUS mandatory
        DESCRIPTION
         "The configured weights of queue 2. It is in the range 0..127. The dault weight of each queue is 1.
ALCATEL NOTE:
                 ACCESS:     RW       USAGE:      NA
                 PERSIST:    YES      INSRVMOD:   NO
                 RANGE:      NA       DEFVALUE:   1
                 UNITS:      NA       SPARSE:     NA
                 DESCR:      NA."
::= { qosAggrQueuesConfigProfileEntry 8}

qosAggrQueuesConfigQ3Weight OBJECT-TYPE
        SYNTAX  INTEGER ( 0..127)
        ACCESS  read-write
        STATUS mandatory
        DESCRIPTION
         "The configured weights of queue 3. It is in the range 0..127. The dault weight of each queue is 1.
ALCATEL NOTE:
                 ACCESS:     RW       USAGE:      NA
                 PERSIST:    YES      INSRVMOD:   NO
                 RANGE:      NA       DEFVALUE:   1
                 UNITS:      NA       SPARSE:     NA
                 DESCR:      NA."
::= { qosAggrQueuesConfigProfileEntry 9}

qosAggrQueuesConfigQ4Weight OBJECT-TYPE
        SYNTAX  INTEGER ( 0..127)
        ACCESS  read-write
        STATUS mandatory
        DESCRIPTION
         "The configured weights of queue 4. It is in the range 0..127. The dault weight of each queue is 1.
ALCATEL NOTE:
                 ACCESS:     RW       USAGE:      NA
                 PERSIST:    YES      INSRVMOD:   NO
                 RANGE:      NA       DEFVALUE:   1
                 UNITS:      NA       SPARSE:     NA
                 DESCR:      NA."
::= { qosAggrQueuesConfigProfileEntry 10}

qosAggrQueuesConfigQ5Weight OBJECT-TYPE
        SYNTAX  INTEGER ( 0..127)
        ACCESS  read-write
        STATUS mandatory
        DESCRIPTION
         "The configured weights of queue 5. It is in the range 0..127. The dault weight of each queue is 1.
ALCATEL NOTE:
                 ACCESS:     RW       USAGE:      NA
                 PERSIST:    YES      INSRVMOD:   NO
                 RANGE:      NA       DEFVALUE:   1
                 UNITS:      NA       SPARSE:     NA
                 DESCR:      NA."
::= { qosAggrQueuesConfigProfileEntry 11}

qosAggrQueuesConfigQ6Weight OBJECT-TYPE
        SYNTAX  INTEGER ( 0..127)
        ACCESS  read-write
        STATUS mandatory
        DESCRIPTION
         "The configured weights of queue 6. It is in the range 0..127. The dault weight of each queue is 1.
ALCATEL NOTE:
                 ACCESS:     RW       USAGE:      NA
                 PERSIST:    YES      INSRVMOD:   NO
                 RANGE:      NA       DEFVALUE:   1
                 UNITS:      NA       SPARSE:     NA
                 DESCR:      NA."
::= { qosAggrQueuesConfigProfileEntry 12}

qosAggrQueuesConfigQ7Weight OBJECT-TYPE
        SYNTAX  INTEGER ( 0..127)
        ACCESS  read-write
        STATUS mandatory
        DESCRIPTION
         "The configured weights of queue 7. It is in the range 0..127. The dault weight of each queue is 1.
ALCATEL NOTE:
                 ACCESS:     RW       USAGE:      NA
                 PERSIST:    YES      INSRVMOD:   NO
                 RANGE:      NA       DEFVALUE:   1
                 UNITS:      NA       SPARSE:     NA
                 DESCR:      NA."
::= { qosAggrQueuesConfigProfileEntry 13}

qosAggrQueuesConfigQ0ShaperProfId OBJECT-TYPE
        SYNTAX  AsamProfilePointer
        ACCESS  read-write
        STATUS mandatory
        DESCRIPTION
         "It is the shaper profile id assicated on the queue 0. The default value is 0.
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 14}

qosAggrQueuesConfigQ1ShaperProfId OBJECT-TYPE
        SYNTAX  AsamProfilePointer
        ACCESS  read-write
        STATUS mandatory
        DESCRIPTION
         "It is the shaper profile id assicated on the queue 1. The default value is 0.
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 15}

qosAggrQueuesConfigQ2ShaperProfId OBJECT-TYPE
        SYNTAX  AsamProfilePointer
        ACCESS  read-write
        STATUS mandatory
        DESCRIPTION
         "It is the shaper profile id assicated on the queue 2. The default value is 0.
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 16}

qosAggrQueuesConfigQ3ShaperProfId OBJECT-TYPE
        SYNTAX  AsamProfilePointer
        ACCESS  read-write
        STATUS mandatory
        DESCRIPTION
         "It is the shaper profile id assicated on the queue 3. The default value is 0.
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 17}

qosAggrQueuesConfigQ4ShaperProfId OBJECT-TYPE
        SYNTAX  AsamProfilePointer
        ACCESS  read-write
        STATUS mandatory
        DESCRIPTION
         "It is the shaper profile id assicated on the queue 4. The default value is 0.
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 18}

qosAggrQueuesConfigQ5ShaperProfId OBJECT-TYPE
        SYNTAX  AsamProfilePointer
        ACCESS  read-write
        STATUS mandatory
        DESCRIPTION
         "It is the shaper profile id assicated on the queue 5. The default value is 0.
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 19}

qosAggrQueuesConfigQ6ShaperProfId OBJECT-TYPE
        SYNTAX  AsamProfilePointer
        ACCESS  read-write
        STATUS mandatory
        DESCRIPTION
         "It is the shaper profile id assicated on the queue 6. The default value is 0.
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 20}

qosAggrQueuesConfigQ7ShaperProfId OBJECT-TYPE
        SYNTAX  AsamProfilePointer
        ACCESS  read-write
        STATUS mandatory
        DESCRIPTION
         "It is the shaper profile id assicated on the queue 7. The default value is 0.
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 21}

qosAggrQueuesConfigQ0BacProfId OBJECT-TYPE
        SYNTAX  AsamProfilePointer
        ACCESS  read-write
        STATUS mandatory
        DESCRIPTION
         "This is the BAC profile id associated with queue 0. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 22}

qosAggrQueuesConfigQ1BacProfId OBJECT-TYPE
        SYNTAX  AsamProfilePointer
        ACCESS  read-write
        STATUS mandatory
        DESCRIPTION
         "This is the BAC profile id associated with queue 1. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 23}

qosAggrQueuesConfigQ2BacProfId OBJECT-TYPE
        SYNTAX  AsamProfilePointer
        ACCESS  read-write
        STATUS mandatory
        DESCRIPTION
         "This is the BAC profile id associated with queue 2. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 24}

qosAggrQueuesConfigQ3BacProfId OBJECT-TYPE
        SYNTAX  AsamProfilePointer
        ACCESS  read-write
        STATUS mandatory
        DESCRIPTION
         "This is the BAC profile id associated with queue 3. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 25}

qosAggrQueuesConfigQ4BacProfId OBJECT-TYPE
        SYNTAX  AsamProfilePointer
        ACCESS  read-write
        STATUS mandatory
        DESCRIPTION
         "This is the BAC profile id associated with queue 4. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 26}

qosAggrQueuesConfigQ5BacProfId OBJECT-TYPE
        SYNTAX  AsamProfilePointer
        ACCESS  read-write
        STATUS mandatory
        DESCRIPTION
         "This is the BAC profile id associated with queue 5. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 27}

qosAggrQueuesConfigQ6BacProfId OBJECT-TYPE
        SYNTAX  AsamProfilePointer
        ACCESS  read-write
        STATUS mandatory
        DESCRIPTION
         "This is the BAC profile id associated with queue 6. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 28}

qosAggrQueuesConfigQ7BacProfId OBJECT-TYPE
        SYNTAX  AsamProfilePointer
        ACCESS  read-write
        STATUS mandatory
        DESCRIPTION
         "This is the BAC profile id associated with queue 7. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 29}

qosAggrQueuesConfigQ0BandwidthProfId OBJECT-TYPE
        SYNTAX  AsamProfilePointer
        ACCESS  read-write
        STATUS mandatory
        DESCRIPTION
         "This is the bandwidth profile id associated with queue 0. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 30}

qosAggrQueuesConfigQ1BandwidthProfId OBJECT-TYPE
        SYNTAX  AsamProfilePointer
        ACCESS  read-write
        STATUS mandatory
        DESCRIPTION
         "This is the bandwidth profile id associated with queue 1. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 31}

qosAggrQueuesConfigQ2BandwidthProfId OBJECT-TYPE
        SYNTAX  AsamProfilePointer
        ACCESS  read-write
        STATUS mandatory
        DESCRIPTION
         "This is the bandwidth profile id associated with queue 2. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 32}

qosAggrQueuesConfigQ3BandwidthProfId OBJECT-TYPE
        SYNTAX  AsamProfilePointer
        ACCESS  read-write
        STATUS mandatory
        DESCRIPTION
         "This is the bandwidth profile id associated with queue 3. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 33}

qosAggrQueuesConfigQ4BandwidthProfId OBJECT-TYPE
        SYNTAX  AsamProfilePointer
        ACCESS  read-write
        STATUS mandatory
        DESCRIPTION
         "This is the bandwidth profile id associated with queue 4. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 34}

qosAggrQueuesConfigQ5BandwidthProfId OBJECT-TYPE
        SYNTAX  AsamProfilePointer
        ACCESS  read-write
        STATUS mandatory
        DESCRIPTION
         "This is the bandwidth profile id associated with queue 5. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 35}

qosAggrQueuesConfigQ6BandwidthProfId OBJECT-TYPE
        SYNTAX  AsamProfilePointer
        ACCESS  read-write
        STATUS mandatory
        DESCRIPTION
         "This is the bandwidth profile id associated with queue 6. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 36}

qosAggrQueuesConfigQ7BandwidthProfId OBJECT-TYPE
        SYNTAX  AsamProfilePointer
        ACCESS  read-write
        STATUS mandatory
        DESCRIPTION
         "This is the bandwidth profile id associated with queue 7. The default value is 0
ALCATEL NOTE:
                 ACCESS:     RW       USAGE:      NA
                 PERSIST:    YES      INSRVMOD:   NO
                 RANGE:      NA       DEFVALUE:   0
                 UNITS:      NA       SPARSE:     NA
                 DESCR:      NA."
DEFVAL { 0 }
::= { qosAggrQueuesConfigProfileEntry 37}

qosAggrQueuesConfigBandwidthSharing OBJECT-TYPE
        SYNTAX  INTEGER
        ACCESS  read-write
        STATUS mandatory
        DESCRIPTION
         "The configured interface bandwidth sharing of 8 queues. The priorities and queues mapping see following:
          Bits28-31 bits24-27 bits20-23 bits16-19 bits12-15 bits8-11 bits4-7 bits0-3 
          queue-7   queue-6   queue-5    queue-4   queue-3   queue-2  queue-1 queue-0.
The valid sharing range of each queue is from 1 to 3. 1 means bandwidth sharing is disabled. 2 means the bandwidth sharing in one UNI. 3 means the bandwidth sharing across UNIs in one ONU. The default value of each queue is 1. So the default value is 0x11111111. 
ALCATEL NOTE:
                 ACCESS:     RW       USAGE:      NA
                 PERSIST:    YES      INSRVMOD:   NO
                 RANGE:      NA       DEFVALUE:   0x11111111
                 UNITS:      NA       SPARSE:     NA
                 DESCR:      NA."
::= { qosAggrQueuesConfigProfileEntry 38}

-- qosAggrQueuesConfigProfile name mapping table

qosAggrQueuesConfigProfileMappingTable OBJECT-TYPE
    SYNTAX	SEQUENCE OF QosAggrQueuesConfigProfileMappingEntry
    ACCESS	not-accessible
    STATUS	mandatory
    DESCRIPTION
    "This object contains a table for qosAggrQueuesConfigProfile name to index mapping"
::= { qosProfiles 35 }

qosAggrQueuesConfigProfileMappingEntry OBJECT-TYPE
    SYNTAX 	QosAggrQueuesConfigProfileMappingEntry
    ACCESS	not-accessible
    STATUS mandatory
    DESCRIPTION
    "An entry (conceptual row) representing the qos
    aggQueuesConfig Profile Name to Index mapping. The system automatically 
    creates an entry in this Table for each corresponding entry 
    (qosPolicerPerTc profile)created in the qosAggrQueuesConfigProfileTable.
    Similarly, when an qosAggrQueuesCofnig profile is deleted, the corresponding
    entry in this table is also automatically deleted by the system."
    INDEX	{qosAggrQueuesConfigProfileMappingName }
    ::= { qosAggrQueuesConfigProfileMappingTable 1}

QosAggrQueuesConfigProfileMappingEntry::=
    SEQUENCE 
    { 
        qosAggrQueuesConfigProfileMappingName    AsamProfileName,
        qosAggrQueuesConfigProfileMappingIndex   AsamProfileIndex
    }

qosAggrQueuesConfigProfileMappingName   OBJECT-TYPE
    SYNTAX	AsamProfileName
    ACCESS	not-accessible
    STATUS  mandatory
    DESCRIPTION
    "A text string containing the name of this profile.
    ALCATEL NOTE:
    ACCESS:     RO       USAGE:      NA
    PERSIST:    YES       INSRVMOD:   NO
    RANGE:      NA       DEFVALUE:   NA
    UNITS:      NA       SPARSE:     NA
    DESCR:      NA "
::= { qosAggrQueuesConfigProfileMappingEntry 1}

qosAggrQueuesConfigProfileMappingIndex   OBJECT-TYPE
    SYNTAX	AsamProfileIndex
    ACCESS	read-only
    STATUS mandatory
    DESCRIPTION
    "This object is the Profile index. 
    ALCATEL NOTE:
    ACCESS:     RO       USAGE:      NA
    PERSIST:    YES       INSRVMOD:   NO
    RANGE:      NA       DEFVALUE:   NA
    UNITS:      NA       SPARSE:     NA
    DESCR:      NA "
::= { qosAggrQueuesConfigProfileMappingEntry 2}

-- End of qosAggrQueuesConfigProfile name mapping table

-- ============================================================================
-- ==========================

-- TrafficClassMapping
qosLimDot1PtcMapping OBJECT IDENTIFIER ::= {qosMIB 4}
qosLimDot1PtcMappingTable OBJECT-TYPE
	SYNTAX	SEQUENCE OF QosLimDot1PTcMappingEntry
	ACCESS	not-accessible
	STATUS	mandatory
	DESCRIPTION
	"This object contains a table that defines the
	 mapping between the .1P field of the VLAN tag to
	a certain traffic class. The row index of the table is
 	the ingress .1P value (0..7) while the value is the
	 (the traffic class) (0..7)."
::= { qosLimDot1PtcMapping 1}
qosLimDot1PTcMappingEntry OBJECT-TYPE
	SYNTAX QosLimDot1PTcMappingEntry
	ACCESS not-accessible
	STATUS	mandatory
	DESCRIPTION
	"This table contains the 802.1P traffic class to queue mapping
	information. There are 8 rows, each containing one output
	traffic class number (0..7), one discard priority colour (0..1) 
	and one	policer colour (0..2) in the context of the outgoing 
	interface on LIMs"
	INDEX {qosLimDot1P }
	::= {qosLimDot1PtcMappingTable 1}
QosLimDot1PTcMappingEntry ::=
	SEQUENCE {	qosLimDot1P		 INTEGER,
			qosLimTc		 INTEGER,
			qosLimDPColour           QosColourType,
			qosLimPolicerColour      QosColourType
		  }
qosLimDot1P OBJECT-TYPE
	SYNTAX	INTEGER
	ACCESS	not-accessible
	STATUS mandatory
	DESCRIPTION
	 "This field is used to index the Dot1P traffic class
	mapping table. The lengths of the table is 8 (fixed)"
::= { qosLimDot1PTcMappingEntry 1 }

qosLimTc OBJECT-TYPE
	SYNTAX	INTEGER (0..7)
	ACCESS	read-write
	STATUS mandatory
	DESCRIPTION
	 "This object encodes the traffic class (0..7) into which
	frames coming in with the .1P value equal to the
	index of the row in this table will be cast.
	E.g., if row 6 contains value 3, that means that frames
	with .1P value equal to 6 will be cast in output traffic class 3
             "
::= { qosLimDot1PTcMappingEntry 2 }

qosLimDPColour OBJECT-TYPE
	SYNTAX	QosColourType
	ACCESS	read-write
	STATUS mandatory
	DESCRIPTION
	 "This object encodes the frame discard priority in queue. The colour corresponds to the colour defined in QueueProfileTable. ISAM supports green(0) and yellow(1) now. 
      ALCATEL NOTE:
                 ACCESS:     NA       USAGE:      NA
                 PERSIST:    YES       INSRVMOD:   NO
                 RANGE:      NA       DEFVALUE:   NA
                 UNITS:     green(0) , yellow(1)       SPARSE:     NA
                 DESCR:      NA "
	DEFVAL		{0}
::= { qosLimDot1PTcMappingEntry 3 }

qosLimPolicerColour OBJECT-TYPE
	SYNTAX	QosColourType
	ACCESS	read-write
	STATUS mandatory
	DESCRIPTION
	 "This object encodes the frame colour for TrTCM. The colour corresponds to the colour defined in PolicerProfileTable. ISAM supports green(0), yellow(1) and red(2) now. 
      ALCATEL NOTE:
                 ACCESS:     NA       USAGE:      NA
                 PERSIST:    YES       INSRVMOD:   NO
                 RANGE:      NA       DEFVALUE:   0
                 UNITS:     green(0) , yellow(1) ,red(2)  SPARSE:     NA
                 DESCR:      NA "
	DEFVAL		{0}
::= { qosLimDot1PTcMappingEntry 4 }

--
--
qosLimTcToQueueMappingTable OBJECT-TYPE
	SYNTAX	SEQUENCE OF QosLimTcToQueueMappingEntry
	ACCESS	not-accessible
	STATUS	mandatory
	DESCRIPTION
	"This object contains a table that defines the
	 mapping between the traffic class and the queue of a UNI. Three rows 
              in the table will be automatically created with default values and can only be edited but the operator. Row 1 is used for the case when the LIM has 4 queues per UNI and 4 TCs, Row 2 is used for the case when the LIM has 4 queues per UNI but 8 TCs, Row 3 is used for the case when the LIM has 8 queues per UNI but 8 TCs."
::= { qosLimDot1PtcMapping 2}
qosLimTcToQueueMappingEntry OBJECT-TYPE
	SYNTAX QosLimTcToQueueMappingEntry
	ACCESS not-accessible
	STATUS	mandatory
	DESCRIPTION
	"This table contains the 802.1P traffic class to queue mapping
	information. There are 8 rows, each containing one output
	buffer number (0..7) in the context of the outgoing interface
	"
	INDEX {qosLimTcToQueueMappingIndex}
	::= {qosLimTcToQueueMappingTable 1}
QosLimTcToQueueMappingEntry ::=
	SEQUENCE {	qosLimTcToQueueMappingIndex			INTEGER,			
			qosLimTcToQueueMappingQueue                           INTEGER,
			qosLimTcToQueueMappingName			AsamProfileName
				}
qosLimTcToQueueMappingIndex OBJECT-TYPE
	SYNTAX	INTEGER 
	ACCESS	not-accessible
	STATUS mandatory
	DESCRIPTION
	 "This field is used to identify the row of the table. Row 1 is used for the case when the LIM has 4 queues per UNI and 4 TCs, Row 2 is used for the case when the LIM has 4 queues per UNI but 8 TCs, Row 3 is used for the case when the LIM has 8 queues per UNI but 8 TCs."
::= { qosLimTcToQueueMappingEntry 1 }


qosLimTcToQueueMappingQueue OBJECT-TYPE
	SYNTAX	INTEGER 
	ACCESS	read-only
	STATUS mandatory
	DESCRIPTION
	 "The following mapping applies:
       The queue corresponding to TC 0 is indicated in bits 0-3, the queue corresponding to TC 1 in indicated in bit 4-7. The mapping uses 4 bits for implementation convenience. The MSB should be set to 0 if the queue is used (i.e valid queues are indicated with 0000 to 0111). If a particular TC is not used, then the corresponding bits have to be 1111. Graphical representation is given below :
      Bit31-28 bit27-24 bit23-20 bit19-16 bit15-bit12 bit11-8 bit7-4 bit3-0 
         TC7      TC6      TC5      TC4      TC3         TC2    TC1    TC0
             ALCATEL NOTE:
                 ACCESS:     RO       USAGE:      NA
                 PERSIST:    YES      INSRVMOD:   NO
                 RANGE:      NA       DEFVALUE:   NA
                 UNITS:      NA       SPARSE:     NA
                 		DESCR:      NA."
::= { qosLimTcToQueueMappingEntry 2 }

qosLimTcToQueueMappingName OBJECT-TYPE
	SYNTAX	AsamProfileName 
	ACCESS	not-accessible
	STATUS mandatory
	DESCRIPTION
	 "This field is used to identify the row of the table. Row 1 is used for the case when the LIM has 4 queues per UNI and 4 TCs and has the name 4queue4tc, Row 2 is used for the case when the LIM has 4 queues per UNI but 8 TCs and has the name 4queue8tc, Row 3 is used for the case when the LIM has 8 queues per UNI but 8 TCs and has the name 8queue8tc "
::= { qosLimTcToQueueMappingEntry 3 }


--
--
-- It stores the pbit to TC mappings
-- that can be used by a L2 Forwarder in the upstream and dowstream directions.
-- (same profile for both directions). Also stores the pbit to ingress color mappings
-- A row with index = 1 is created by default which  maps pbits 0..7 to TC 0..7 one 
-- to one (pbit 0 to TC 0, pbit 1 to TC 1 etc etc) and pBits 0..7 to green (color-unaware)
qosIngressQoSProfileTable OBJECT-TYPE
	SYNTAX	SEQUENCE OF QosIngressQoSProfileEntry
	ACCESS	not-accessible
	STATUS	mandatory
	DESCRIPTION
	" This table stores the pbit to TC mappings 
 that can be used by a VLAN PORT in the upstream and dowstream directions.
(same profile for both directions). Also stores the pbit to ingress color mappings.
A row with index = 1 is created by default which maps pbits 0..7 to TC 0..7 one to 
one (pbit 0 to TC 0, pbit 1 to TC 1 etc etc) and pBits 0..7 to green (color-unaware).
Rows with index = 2 to 32 can be created and deleted and modified by the operator."
::= { qosLimDot1PtcMapping 3}
qosIngressQoSProfileEntry OBJECT-TYPE
	SYNTAX QosIngressQoSProfileEntry
	ACCESS not-accessible
	STATUS	mandatory
	DESCRIPTION
	"This table contains the 802.1P pbits to traffic class mappings as well as 802.1P pBits to ingress color mappings"
	INDEX {qosIngressQoSProfileIndex }
	::= {qosIngressQoSProfileTable 1}
QosIngressQoSProfileEntry ::=
        SEQUENCE {qosIngressQoSProfileIndex           AsamProfileIndex,
                  qosIngressQoSProfileName            AsamProfileName,
                  qosIngressQoSProfileTc              INTEGER,
                  qosIngressQoSProfileRowStatus       RowStatus,
                  qosIngressQoSProfileRefCount        AsamProfileRefCount32,
                  qosIngressQoSProfileUseDEI          TruthValue,
                  qosIngressQoSProfileDot1PColorTable INTEGER,
                  qosIngressQoSProfilePolicingTc      INTEGER
				}
qosIngressQoSProfileIndex OBJECT-TYPE
	SYNTAX	AsamProfileIndex 
	ACCESS	not-accessible
	STATUS mandatory
	DESCRIPTION
	 "This field is used to identify the row of the table. Rows with  qosIngressQoSProfileIndex = 1 is automatically created by the system and cannot be edited. It  has one to one mapping of pbits (0..7) to TCs (0..7). Rows with qosIngressQoSProfileIndex = 2..32 can be created, deleted and modified by the operator."
::= { qosIngressQoSProfileEntry 1 }

qosIngressQoSProfileName OBJECT-TYPE
	SYNTAX	AsamProfileName
	ACCESS	read-write
	STATUS mandatory
	DESCRIPTION
	 "This field is used to identify the row of the table with a name"
::= { qosIngressQoSProfileEntry 2 }

qosIngressQoSProfileTc OBJECT-TYPE
	SYNTAX	INTEGER 
	ACCESS	read-write
	STATUS mandatory
	DESCRIPTION
	 "The following mapping applies:
          The TC corresponding to pbits 0 is indicated in bits 0-3, the TC corresponding 
          to pbit 1 in indicated in bit 4-7, !-The mapping uses 4 bits for implementation
	  convenience. The MSB should be set to 0 if the TC is used (i.e valid TCs are 
	  indicated with 0000 to 0111). If a particular TC is not used, then the corresponding 
	  bits have to be 1111. Graphical representation is given below :
      Bit31-28 bit27-24 bit23-20 bit19-16 bit15-bit12 bit11-8 bit7-4 bit3-0 
      pbit-7   pbit-6   pbit-5    pbit-4    pbit-3    pbit-2  pbit-1 pbit-0
             ALCATEL NOTE:
                 ACCESS:     RO       USAGE:      NA
                 PERSIST:    YES      INSRVMOD:   NO
                 RANGE:      NA       DEFVALUE:   NA
                 UNITS:      NA       SPARSE:     NA
                 DESCR:      NA."
::= { qosIngressQoSProfileEntry 3 }

qosIngressQoSProfileRowStatus OBJECT-TYPE
	SYNTAX	RowStatus
	ACCESS	read-write
	STATUS mandatory
	DESCRIPTION
	 "This object is the Row Status of the row in the table."
::= { qosIngressQoSProfileEntry 4 }

qosIngressQoSProfileRefCount OBJECT-TYPE
	SYNTAX	AsamProfileRefCount32 
	ACCESS	read-only
	STATUS mandatory
	DESCRIPTION
	 "This field is used to specify the reference count of how many times this profile has been applied. If 0 the profile is not in use and can be deleted."
::= { qosIngressQoSProfileEntry 5 }

qosIngressQoSProfileUseDEI OBJECT-TYPE
	SYNTAX	TruthValue
	ACCESS	read-write
	STATUS mandatory
	DESCRIPTION
	 "This object allows use of DEI bit to color ingress packets. If enabled, ingress packets 
          with DEI bit set will be colored as yellow. If policer action is set to remark and this 
          parameter is enabled then red/yellow packets will have their DEI bit set on egress.
      ALCATEL NOTE:
                 ACCESS:     NA       USAGE:      NA
                 PERSIST:    YES      INSRVMOD:   NO
                 RANGE:      yes,no   DEFVALUE:   no
                 UNITS:      NA       SPARSE:     NA
                 DESCR:      NA "
DEFVAL { false }
::= { qosIngressQoSProfileEntry 6 }

qosIngressQoSProfileDot1PColorTable OBJECT-TYPE
	SYNTAX	INTEGER 
	ACCESS	read-write
	STATUS mandatory
	DESCRIPTION
	 "The following mapping applies:
          The ingress color  corresponding to pbits 0 is indicated in bits 0-3, the ingress color
          corresponding to pbit 1 in indicated in bit 4-7, etc... Color can be green(0), yellow(1)
          or red (2) The mapping uses 4 bits for implementation convenience. The most significant 
          2 bits should be set to 0 if the dot1P value is used (i.e valid pBits are indicated with 
          0000 to 0010). If a particular pBit is not used, then the corresponding bits have to be 
          1111. Graphical representation is given below :
      Bit31-28 bit27-24 bit23-20 bit19-16 bit15-bit12 bit11-8 bit7-4 bit3-0 
      pbit-7   pbit-6   pbit-5    pbit-4    pbit-3    pbit-2  pbit-1    pbit-0
             ALCATEL NOTE:
                 ACCESS:     NA       USAGE:      NA
                 PERSIST:    YES      INSRVMOD:   NO
                 RANGE:      NA       DEFVALUE:   NA
                 UNITS:      NA       SPARSE:     NA
                 DESCR:      NA."
::= { qosIngressQoSProfileEntry 7 }

qosIngressQoSProfilePolicingTc OBJECT-TYPE
	SYNTAX	INTEGER 
	ACCESS	read-write
	STATUS mandatory
	DESCRIPTION
	 "The following mapping applies:
          The policing TC corresponding to pbits 0 is indicated in bits 0-3, the policing TC corresponding 
          to pbit 1 in indicated in bit 4-7, !-The mapping uses 4 bits for implementation
	  convenience. The MSB should be set to 0 if the policing TC is used (i.e valid TCs are 
	  indicated with 0000 to 0111). If a particular policing TC is not used, then the corresponding 
	  bits have to be 1111. Graphical representation is given below :
      Bit31-28 bit27-24 bit23-20 bit19-16 bit15-bit12 bit11-8 bit7-4 bit3-0 
      pbit-7   pbit-6   pbit-5    pbit-4    pbit-3    pbit-2  pbit-1 pbit-0
             ALCATEL NOTE:
                 ACCESS:     RO       USAGE:      NA
                 PERSIST:    YES      INSRVMOD:   NO
                 RANGE:      NA       DEFVALUE:   NA
                 UNITS:      NA       SPARSE:     NA
                 DESCR:      NA."
::= { qosIngressQoSProfileEntry 8 }


-- qosIngressQosProfile name mapping table.

qosIngressQosProfileMappingTable OBJECT-TYPE
	SYNTAX	SEQUENCE OF QosIngressQosProfileMappingEntry
	ACCESS	not-accessible
	STATUS	mandatory
	DESCRIPTION
	"This object contains a table for qosIngressQosProfile
name to index mapping"
::= { qosLimDot1PtcMapping 4 }

qosIngressQosProfileMappingEntry OBJECT-TYPE
	SYNTAX 	QosIngressQosProfileMappingEntry
	ACCESS	not-accessible
	STATUS mandatory
	DESCRIPTION
	" An entry (conceptual row) representing the qos
IngressQos Profile Name to Index mapping. The system automatically creates an
entry in this Table for each corresponding entry (qosIngressQos profile)created in the system.  Similarly, when an qosIngressQos profile is deleted, the corresponding entry in this table is also automatically deleted by the system."
	INDEX	{qosIngressQosProfileMappingName }
	::= {qosIngressQosProfileMappingTable  1}

QosIngressQosProfileMappingEntry ::=
	SEQUENCE { 
qosIngressQosProfileMappingName     AsamProfileName,
		qosIngressQosProfileMappingIndex      AsamProfileIndex
			}

qosIngressQosProfileMappingName OBJECT-TYPE
	SYNTAX	AsamProfileName
	ACCESS	not-accessible
	STATUS  mandatory
	DESCRIPTION
		"A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { qosIngressQosProfileMappingEntry 1}

qosIngressQosProfileMappingIndex OBJECT-TYPE
	SYNTAX	AsamProfileIndex
	ACCESS	read-only
	STATUS mandatory
	DESCRIPTION
		"This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { qosIngressQosProfileMappingEntry 2}

-- End of qosIngressQosProfile name mapping table




-- qosLimQueueConfigurations
qosLimQueueConfigurations OBJECT IDENTIFIER ::= {qosMIB 5}


qosLimQueueConfigTable OBJECT-TYPE
	SYNTAX	SEQUENCE OF QosLimQueueConfigEntry
	ACCESS	not-accessible
	STATUS	mandatory
	DESCRIPTION
	"This object contains a table which associates
	configurable queues on the LIM with queue profiles"
::= { qosLimQueueConfigurations 1 }
qosLimQueueConfigEntry OBJECT-TYPE
	SYNTAX 	QosLimQueueConfigEntry
	ACCESS 	not-accessible
	STATUS	mandatory
	DESCRIPTION
		"This table contains the LIM Queue configurations."
	INDEX {qosLimDslLinkIndex, qosLimDslQueueIndex}
::= {qosLimQueueConfigTable 1 }
QosLimQueueConfigEntry ::=
	SEQUENCE {	
                        qosLimDslLinkIndex	InterfaceIndex,
			qosLimDslQueueIndex	INTEGER,
			qosQueueProfileId	AsamProfilePointer,
			qosLimQueueShaperProfileId  AsamProfilePointer,
			qosLimQueueWeight  INTEGER,
			qosLimQueuePriority  INTEGER,
                        qosLimQueueOperationalWeight INTEGER
--			qosLimQueueShaperSharing TruthValue
				}

qosLimDslLinkIndex OBJECT-TYPE
	SYNTAX	InterfaceIndex
	ACCESS	not-accessible
	STATUS mandatory
	DESCRIPTION
	 "This field is used to index the physical interface
	 of a DSL link , p-t-p Ethernet I/F, the LSM GE uplink port, UNI or LLID."
::= { qosLimQueueConfigEntry 1 }

qosLimDslQueueIndex OBJECT-TYPE
	SYNTAX	INTEGER (0..7)
	ACCESS	not-accessible
	STATUS mandatory
	DESCRIPTION
	 "This object is used to index the queue within the
	 scope of one DSL link on the EBLT LIM, p-t-p Ethernet I/F or the LSM GE uplink port."
::= { qosLimQueueConfigEntry 2 }

qosQueueProfileId OBJECT-TYPE
	SYNTAX	AsamProfilePointer
	ACCESS	read-write
	STATUS mandatory
	DESCRIPTION
	 "This object contains a reference to an existing Queue
		 configuration profile. "
::= { qosLimQueueConfigEntry 3 }

qosLimQueueShaperProfileId OBJECT-TYPE
	SYNTAX	AsamProfilePointer
	ACCESS	read-write
	STATUS mandatory
	DESCRIPTION
	 "This object contains a reference to an existing shaper profile. 
      ALCATEL NOTE:
                 ACCESS:     NA       USAGE:      NA
                 PERSIST:    YES       INSRVMOD:   NO
                 RANGE:      NA       DEFVALUE:   NA
                 UNITS:      NA       SPARSE:     NA
                 DESCR:      This object is not supported on the LSM GE uplink port.  "
DEFVAL { 0 }
::= { qosLimQueueConfigEntry 4 }

qosLimQueueWeight OBJECT-TYPE
	SYNTAX	INTEGER
	ACCESS	read-write
	STATUS mandatory
	DESCRIPTION
	 "This object contains a weight of the queue in the range 0..127. 
          Weights are used when the same priority is assigned to multiple queues.
      ALCATEL NOTE:
                 ACCESS:     NA       USAGE:      NA
                 PERSIST:    YES       INSRVMOD:   NO
                 RANGE:      NA       DEFVALUE:   NA
                 UNITS:      NA       SPARSE:     NA
                 DESCR:      NA "
DEFVAL { 10 }
::= { qosLimQueueConfigEntry 5 }

qosLimQueuePriority OBJECT-TYPE
	SYNTAX	INTEGER
	ACCESS	read-write
	STATUS mandatory
	DESCRIPTION
	 "This object contains the priority of the queue in the range 1..8. 8 means highest priority and 1 means lowest priority.
      ALCATEL NOTE:
                 ACCESS:     NA       USAGE:      NA
                 PERSIST:    YES       INSRVMOD:   NO
                 RANGE:      NA       DEFVALUE:   NA
                 UNITS:      NA       SPARSE:     NA
                 DESCR:      NA "
DEFVAL { 1 }
::= { qosLimQueueConfigEntry 6}

qosLimQueueOperationalWeight OBJECT-TYPE
	SYNTAX	INTEGER
	ACCESS	read-only
	STATUS mandatory
	DESCRIPTION
	 "This object contains the operational weight of queue when autoSchedule enabled range 0..127. 
      ALCATEL NOTE:
                 ACCESS:     NA       USAGE:      NA
                 PERSIST:    YES      INSRVMOD:   NO
                 RANGE:      NA       DEFVALUE:   NA
                 UNITS:      NA       SPARSE:     NA
                 DESCR:      This object is not supported on the GE uplink 
                             port."
DEFVAL { 10 }
::= { qosLimQueueConfigEntry 7 }

--qosLimQueueShaperSharing OBJECT-TYPE
--	SYNTAX	TruthValue
--	ACCESS	read-write
--	STATUS mandatory
--	DESCRIPTION
--	 "This object specifies whether shaper sharing is enabled or disabled. Enabled if True.
--    ALCATEL NOTE:
--                 ACCESS:     NA       USAGE:      NA
--                 PERSIST:    YES       INSRVMOD:   NO
--                 RANGE:      NA       DEFVALUE:   NA
--                 UNITS:      NA       SPARSE:     NA
--                 DESCR:      NA "
--      DEFVAL { false }
--   ::= { qosLimQueueConfigEntry 8}


qosLimUpstreamQueueConfigTable OBJECT-TYPE
	SYNTAX	SEQUENCE OF QosLimUpstreamQueueConfigEntry
	ACCESS	not-accessible
	STATUS	mandatory
	DESCRIPTION
	"This object contains a table which associates
	configurable upstream queues on the LIM with queue profiles"
::= { qosLimQueueConfigurations 2 }
qosLimUpstreamQueueConfigEntry OBJECT-TYPE
	SYNTAX 	QosLimUpstreamQueueConfigEntry
	ACCESS 	not-accessible
	STATUS	mandatory
	DESCRIPTION
		"This table contains the upstream LIM Queue configurations."
	INDEX {qosLimUpstreamLinkIndex, qosLimUpstreamQueueIndex}
::= {qosLimUpstreamQueueConfigTable 1 }
QosLimUpstreamQueueConfigEntry ::=
	SEQUENCE {	qosLimUpstreamLinkIndex	InterfaceIndex,
			qosLimUpstreamQueueIndex	INTEGER,
			qosLimUpstreamQueueBandwidthProfileId  AsamProfilePointer,
			qosLimUpstreamQueueWeight  INTEGER,
			qosLimUpstreamQueuePriority  INTEGER,
			qosLimUpstreamQueueBandwidthSharing INTEGER,
			qosLimUpstreamQueueProfileId           AsamProfilePointer,
			qosLimUpstreamQueueBandwidthProfileExtId  AsamProfilePointer,		
			qosLimUpstreamQueueShaperProfileId  AsamProfilePointer
				}

qosLimUpstreamLinkIndex OBJECT-TYPE
	SYNTAX	InterfaceIndex
	ACCESS	not-accessible
	STATUS mandatory
	DESCRIPTION
	 "This field is used to index the physical interface
	 of a DSL link or ONT UNI or LLID or vlan port index."
::= { qosLimUpstreamQueueConfigEntry 1 }

qosLimUpstreamQueueIndex OBJECT-TYPE
	SYNTAX	INTEGER (0..7|255)
	ACCESS	not-accessible
	STATUS mandatory
	DESCRIPTION
	 "This object is used to index the queue within the
	 scope of one DSL link or ONT UNI.
The value 255 indicates the configuration is on the interface not on the queue."
::= { qosLimUpstreamQueueConfigEntry 2 }

qosLimUpstreamQueueBandwidthProfileId OBJECT-TYPE
	SYNTAX	AsamProfilePointer
	ACCESS	read-write
	STATUS mandatory
	DESCRIPTION
	 "This object contains a reference to an existing BW profile.
	 For EPON OLT in upstream,  this object used for DBA on 1G PON bandwidth. 
      ALCATEL NOTE:
                 ACCESS:     NA       USAGE:      NA
                 PERSIST:    YES       INSRVMOD:   NO
                 RANGE:      NA       DEFVALUE:   NA
                 UNITS:      NA       SPARSE:     NA
                 DESCR:      NA "
DEFVAL { 0 }
::= { qosLimUpstreamQueueConfigEntry 3 }

qosLimUpstreamQueueWeight OBJECT-TYPE
	SYNTAX	INTEGER
	ACCESS	read-write
	STATUS mandatory
	DESCRIPTION
	 "This object contains a weight of the queue in the range 0..127.  
          Weights are used when the same priority is assigned to multiple queues.
      ALCATEL NOTE:
                 ACCESS:     NA       USAGE:      NA
                 PERSIST:    YES       INSRVMOD:   NO
                 RANGE:      NA       DEFVALUE:   NA
                 UNITS:      NA       SPARSE:     NA
                 DESCR:      NA "
DEFVAL { 1 }
::= { qosLimUpstreamQueueConfigEntry 4 }

qosLimUpstreamQueuePriority OBJECT-TYPE
	SYNTAX	INTEGER
	ACCESS	read-write
	STATUS mandatory
	DESCRIPTION
	 "This object contains the priority of the queue in the range 1..8. 8 means highest priority and 1 means lowest priority.
      ALCATEL NOTE:
                 ACCESS:     NA       USAGE:      NA
                 PERSIST:    YES       INSRVMOD:   NO
                 RANGE:      NA       DEFVALUE:   NA
                 UNITS:      NA       SPARSE:     NA
                 DESCR:      NA "
DEFVAL { 1 }
::= { qosLimUpstreamQueueConfigEntry 5}

qosLimUpstreamQueueBandwidthSharing OBJECT-TYPE
	SYNTAX	INTEGER (1..4)
	ACCESS	read-write
	STATUS mandatory
	DESCRIPTION
	 "This object specifies whether shaper sharing is enabled or disabled. 1 = disabled, 2 = BW  or TCONT sharing enabled on a single UNI only, 3 = BW or TCONT sharing enabled on across UNIs of an ONT, 4 = BW or TCONT sharing enabled on a single VLAN port only.
      ALCATEL NOTE:
                 ACCESS:     NA       USAGE:      NA
                 PERSIST:    YES       INSRVMOD:   NO
                 RANGE:      1..4       DEFVALUE:  1
                 UNITS:      NA       SPARSE:     NA
                 DESCR:      NA "
DEFVAL { 1 }
::= { qosLimUpstreamQueueConfigEntry 6}

qosLimUpstreamQueueProfileId OBJECT-TYPE
	SYNTAX   AsamProfilePointer
	ACCESS   read-write
	STATUS   mandatory
	DESCRIPTION
	"This object contains a reference to an existing Queue
	     configuration profile.
        This object takes a default value 0 which means no queue profile is attached."
   DEFVAL {0}
::= {qosLimUpstreamQueueConfigEntry 7}

qosLimUpstreamQueueBandwidthProfileExtId OBJECT-TYPE
	SYNTAX	AsamProfilePointer
	ACCESS	read-write
	STATUS mandatory
	DESCRIPTION
	 "This object contains a reference to an existing BW profile.
	 For EPON OLT in upstream,  this object used for DBA  on 10G PON bandwidth. This object is not used on other types of boards. 
      ALCATEL NOTE:
                 ACCESS:     NA       USAGE:      NA
                 PERSIST:    YES       INSRVMOD:   NO
                 RANGE:      NA       DEFVALUE:   NA
                 UNITS:      NA       SPARSE:     NA
                 DESCR:      NA "
DEFVAL { 0 }
::= { qosLimUpstreamQueueConfigEntry 8 }

qosLimUpstreamQueueShaperProfileId OBJECT-TYPE
	SYNTAX	AsamProfilePointer
	ACCESS	read-write
	STATUS mandatory
	DESCRIPTION
	 "This object contains a reference to an existing shaper profile. 
      ALCATEL NOTE:
                 ACCESS:     NA       USAGE:      NA
                 PERSIST:    YES       INSRVMOD:   NO
                 RANGE:      NA       DEFVALUE:   NA
                 UNITS:      NA       SPARSE:     NA
                 DESCR:      NA "
DEFVAL { 0 }
::= { qosLimUpstreamQueueConfigEntry 9 }

qosRemoteQueueConfigTable OBJECT-TYPE
	SYNTAX	SEQUENCE OF QosRemoteQueueConfigEntry
	ACCESS	not-accessible
	STATUS	mandatory
	DESCRIPTION
	"This object contains a table used to configure the 
	physical downstream queues on the ONT's UNI"
::= { qosLimQueueConfigurations 3 }
qosRemoteQueueConfigEntry OBJECT-TYPE
	SYNTAX 	QosRemoteQueueConfigEntry
	ACCESS 	not-accessible
	STATUS	mandatory
	DESCRIPTION
		"This table contains the Remote DS Queue Configurations."
	INDEX {qosRemoteLinkIndex, qosRemoteQueueIndex}
::= {qosRemoteQueueConfigTable 1 }
QosRemoteQueueConfigEntry ::=
	SEQUENCE {	
                        qosRemoteLinkIndex      InterfaceIndex,
			qosRemoteQueueIndex     INTEGER,
			qosRemoteQueueWeight    INTEGER,
			qosRemoteQueuePriority  INTEGER
		}

qosRemoteLinkIndex OBJECT-TYPE
	SYNTAX	InterfaceIndex
	ACCESS	not-accessible
	STATUS mandatory
	DESCRIPTION
	 "This field is used to index the UNI interface.
	 It is the IfIndex of the UNI interface"
::= { qosRemoteQueueConfigEntry 1 }

qosRemoteQueueIndex OBJECT-TYPE
	SYNTAX	INTEGER (0..7)
	ACCESS	not-accessible
	STATUS mandatory
	DESCRIPTION
	 "This object is used to index the downstream queue on the 
	 UNI Interface"
::= { qosRemoteQueueConfigEntry 2 }

qosRemoteQueueWeight OBJECT-TYPE
	SYNTAX	INTEGER
	ACCESS	read-write
	STATUS mandatory
	DESCRIPTION
	 "This object contains a weight of the queue in the range 0..127. 
          Weights are used when the same priority is assigned to multiple queues.
      ALCATEL NOTE:
                 ACCESS:     NA       USAGE:      NA
                 PERSIST:    YES      INSRVMOD:   NO
                 RANGE:      0..127   DEFVALUE:   NA
                 UNITS:      NA       SPARSE:     NA
                 DESCR:      NA "
DEFVAL { 10 }
::= { qosRemoteQueueConfigEntry 3 }

qosRemoteQueuePriority OBJECT-TYPE
	SYNTAX	INTEGER
	ACCESS	read-write
	STATUS mandatory
	DESCRIPTION
	 "This object contains the priority of the queue in the range 1..8. 8 means highest priority and 1 means lowest priority.
      ALCATEL NOTE:
                 ACCESS:     NA       USAGE:      NA
                 PERSIST:    YES       INSRVMOD:   NO
                 RANGE:      1..8      DEFVALUE:   NA
                 UNITS:      NA       SPARSE:     NA
                 DESCR:      NA "
DEFVAL { 1 }
::= { qosRemoteQueueConfigEntry 4}

-- DSL Record
qosDslRecord OBJECT IDENTIFIER ::= {qosMIB 6}
--
--
--
--
-- qosDslRecordTable is used to attach 
--  a SchedulerNodeProfile to the ONT UNIs on GLT. The IfIndex of the ONT
-- UNI is used as index in that case. The number of upstream queues can also be
-- specified per UNI. The CAC profile can be attached to a ONT UNI.
-- qosDslRecordTable is used to attach a CAC profile and to read the 
-- currently available US and DS unicast BW on a PON interface by specifying the
-- IfIndex of the PON interface. The number of downstream queues per UNI is specified 
-- for the PON interface as a whole.
-- qosDslRecordTable is used to attach a Scheduler Node Profile to an ONT interface
-- by using the IfIndex of the ONT. Queue sharing across the UNIs of the ONT can also be enabled or
-- disabled. The other attributes will be ignored when used to store ONT information.

qosDslRecordTable OBJECT-TYPE
	SYNTAX	SEQUENCE OF QosDslRecordEntry
	ACCESS	not-accessible
	STATUS	mandatory
	DESCRIPTION
	"This object contains a table which is used to store
QoS settings that are applicable on a DSL link or ONT UNI or ONT or PON or LLID. 
			"
::= { qosDslRecord 1 }
qosDslRecordEntry OBJECT-TYPE
	SYNTAX	QosDslRecordEntry
	ACCESS	not-accessible
	STATUS	mandatory
	DESCRIPTION
		"This table contains the per-DSL link QoS settings"
	INDEX {qosDslRecordInterfaceIndex}
::= {qosDslRecordTable 1}
QosDslRecordEntry ::=
        SEQUENCE {      qosDslRecordInterfaceIndex          InterfaceIndex,
                        qosDslRecordSchedProfile            AsamProfilePointer,
                        qosDslRecordCacProfile              AsamProfilePointer,
                        qosDslRecordAvailableMcastBw        INTEGER,
                        qosDslRecordUsedMcastBw             INTEGER,
                        qosDslRecordDslFrBw                 INTEGER,
                        qosDslRecordSchedNodeProfile        AsamProfilePointer,
                        qosDslRecordDsNumQueue              INTEGER,
                        qosDslRecordOntUsNumQueue           INTEGER,
                        qosDslRecordAvailableUsUnicastBw    INTEGER,
                        qosDslRecordAvailableDsUnicastBw    INTEGER,
                        qosOntUpstreamQueueSharing          TruthValue,
--                      qosOntDownstreamQueueSharing        TruthValue,
                        qosOntUniQueueStatsEnable           TruthValue,
                        qosOntUniSchedulerNodeWeight        INTEGER,
                        qosPonAutoScheduleEnable            TruthValue,
                        qosOntUniSchedulerNodeEIR           INTEGER,                        
                        qosDslRecordDsNumRemoteQueue        INTEGER,
                        qosDslRecordVlanportQueues          TruthValue,
                        qosDslRecordDsFloodingShaperProfile AsamProfilePointer,
                        qosDslRecordCacProfileExt           AsamProfilePointer,
                        qosOntDsQueueSharing                DsQueueSharingType,
                        qosSchedulerMode                    SchedulerModeType,
                        qosOntUniGemSharingEnable           QosGemSharing,
                        qosIngressProfileId                 AsamProfilePointer,
                        qosPonSharedServiceMulticastSchedulerProfile  AsamProfilePointer,
                        qosPonSharedServiceBroadcastSchedulerProfile  AsamProfilePointer,
                        qosInterfaceBandwidthProfileId      AsamProfilePointer,
                        qosInterfaceBandwidthSharing        INTEGER,
                        qosInterfaceUsAggrQueuesConfigProfileId  AsamProfilePointer,
                        qosInterfaceDsAggrQueuesConfigProfileId    AsamProfilePointer,
                        qosDslRecordDsSchedulerTag      INTEGER
                 }

qosDslRecordInterfaceIndex OBJECT-TYPE
	SYNTAX	InterfaceIndex
	ACCESS	not-accessible
	STATUS mandatory
	DESCRIPTION
	 "This field is used to index the physical interface
	of a DSL link or in the ONT UNI, ONT or PON or LLID."
::= { qosDslRecordEntry 1 }

qosDslRecordSchedProfile OBJECT-TYPE
	SYNTAX	AsamProfilePointer
	ACCESS	read-write
	STATUS mandatory
	DESCRIPTION
	 "This object stores the scheduler profile ID attached to the
	DSL link indexed by qosDslRecordInterfaceIndex This profile is not curently supported, SchedulerNodeProfile is to be used instead."
::= { qosDslRecordEntry 2 }

qosDslRecordCacProfile OBJECT-TYPE
	SYNTAX	AsamProfilePointer
	ACCESS	read-write
	STATUS mandatory
	DESCRIPTION
	 "This object stores the CAC profile ID attached to the
	DSL link or ONT UNI or PON indexed by qosDslRecordInterfaceIndex.
	For EPON OLT in downstream, this object used for CAC on 1G PON bandwidth."
::= { qosDslRecordEntry 3 }

qosDslRecordAvailableMcastBw OBJECT-TYPE
	SYNTAX	INTEGER
	ACCESS	read-only
	STATUS mandatory
	DESCRIPTION
	"This object contains the maximum available bandwidth for
	 video multicast on an interface (Kilobits/sec). It is calculated
	 as: qosDslRecordDslFrBw - qosCacProfileResVoiceBw -
									
	qosCacProfileResDataBw
	where:
	'qosDslRecordDslFrBw' 	is the approximate net frame bandwidth
	calculated based on the minimum guaranteed raw bit rate or actual line 	rate read from interface management,
	'qosCacProfileResVoiceBw' 	is the reserved bandwidth for voice
	specified in the CAC profile attached to this DSL link, and
	'qosCacProfileResDataBw' is the reserved bandwidth for data
	specified in the same CAC profile mentioned earlier.
	For multicast admission control the minimum of this object and
	the qosCacProfileMaxMcastBw - read from the CAC profile
	attached to this DSL link - will be used."
::= { qosDslRecordEntry 4 }

qosDslRecordUsedMcastBw OBJECT-TYPE
	SYNTAX	INTEGER
	ACCESS	read-only
	STATUS mandatory
	DESCRIPTION
	 "This object contains the amount of bandwidth currently in use
	on an interface by known multicast streams (Kilobits/sec). "
::= { qosDslRecordEntry 5 }

qosDslRecordDslFrBw OBJECT-TYPE
	SYNTAX	INTEGER
	ACCESS	read-only
	STATUS mandatory
	DESCRIPTION
	 "This object contains the amount of frame net bandwidth
	available on a DSL link for transmitting Ethernet frames. It
	is calculated as the guaranteed raw sync rate of the DSL link,
	multiplied by a global ATM-overhead factor, (0.85 by default).
	You can change this value under the QoS Global Settings
	table."
::= { qosDslRecordEntry 6 }

qosDslRecordSchedNodeProfile OBJECT-TYPE
	SYNTAX	AsamProfilePointer
	ACCESS	read-write
	STATUS mandatory
	DESCRIPTION
	 "This object stores the scheduler Node profile ID attached to the
	DSL Line or ONT UNI or ONT indexed by InterfaceIndex of the DSL Line/UNI/ ONT"
::= { qosDslRecordEntry 7 }

qosDslRecordDsNumQueue OBJECT-TYPE
	SYNTAX	INTEGER
	ACCESS	read-write
	STATUS mandatory
	DESCRIPTION
	 "This object stores the number of downstream queues per UNI. This is settable for all 
          UNIs on a given PON by specifying the InterfaceIndex of the PON in this table. The 
          allowed values are 4 and 8. When there are services already configured on the ONT UNIs 
          of a PON, this value cannot be changed by the operator."
	DEFVAL		{4}

::= { qosDslRecordEntry 8 }


qosDslRecordOntUsNumQueue OBJECT-TYPE
	SYNTAX	INTEGER
	ACCESS	read-write
	STATUS mandatory
	DESCRIPTION
	 "This object stores the number of upstream queues per UNI on an ONT. This is configured 
          on an ONT basis with the IfIndex of the ONT as index. "
	DEFVAL		{8}

::= { qosDslRecordEntry 9 }



qosDslRecordAvailableUsUnicastBw OBJECT-TYPE
	SYNTAX	INTEGER
	ACCESS	read-only
	STATUS mandatory
	DESCRIPTION
	"This object contains the available upstream bandwidth for
	Unicast services on a PON interface on GLTs in kbps."
::= { qosDslRecordEntry 10}

qosDslRecordAvailableDsUnicastBw OBJECT-TYPE
	SYNTAX	INTEGER
	ACCESS	read-only
	STATUS mandatory
	DESCRIPTION
	"This object contains the available downstream bandwidth for
	Unicast services on a PON interface on GLTs in kbps"
::= { qosDslRecordEntry 11}

qosOntUpstreamQueueSharing OBJECT-TYPE
	SYNTAX	TruthValue
	ACCESS	read-write
	STATUS mandatory
	DESCRIPTION
	 "This object specifies whether upstream queue sharing is enabled or disabled per ONT. Enabled if True. 
          The value of this object cannot be changed after UNIs are created on the ONT.
      ALCATEL NOTE:
                 ACCESS:     NA       USAGE:      NA
                 PERSIST:    YES       INSRVMOD:   NO
                 RANGE:      yes,no       DEFVALUE:   no
                 UNITS:      NA       SPARSE:     NA
                 DESCR:      NA "
DEFVAL { false }
::= { qosDslRecordEntry 12}

--qosOntDownstreamQueueSharing OBJECT-TYPE
--	SYNTAX	TruthValue
--	ACCESS	read-write
--	STATUS mandatory
--	DESCRIPTION
--	 "This object specifies whether downstream queue sharing is enabled or disabled per ONT. Enabled if True. 
--          The value of this object cannot be changed after UNIs are created on the ONT.
--      ALCATEL NOTE:
--                 ACCESS:     NA       USAGE:      NA
--                 PERSIST:    YES       INSRVMOD:   NO
--                 RANGE:      yes,no       DEFVALUE:   no
--                 UNITS:      NA       SPARSE:     NA
--                 DESCR:      NA "
--DEFVAL { false }
--::= { qosDslRecordEntry 13}

qosOntUniQueueStatsEnable OBJECT-TYPE
	SYNTAX	TruthValue
	ACCESS	read-write
	STATUS mandatory
	DESCRIPTION
	 "This object enables queue stats collection for an ONT or UNI or PON interface. Can be enabled only on 32 UNIs(including PON interfaces) per GLT. For
     PON interface, it can only be enabled while the scheduler mode is set to service-flat, for other scheduler modes, it is disabled as default.

      ALCATEL NOTE:
                 ACCESS:     NA       USAGE:      NA
                 PERSIST:    YES       INSRVMOD:   NO
                 RANGE:      yes,no       DEFVALUE:   no
                 UNITS:      NA       SPARSE:     NA
                 DESCR:      NA "
DEFVAL { false }
::= { qosDslRecordEntry 14}

qosOntUniSchedulerNodeWeight OBJECT-TYPE
	SYNTAX	INTEGER
	ACCESS	read-only
	STATUS mandatory
	DESCRIPTION
	 "This object stores the derived weight of the scheduler for an ONT or UNI. It stores it as an 
          Integer with values between 0 and 127. "
	DEFVAL		{0}

::= { qosDslRecordEntry 15}

qosPonAutoScheduleEnable OBJECT-TYPE
	SYNTAX	TruthValue
	ACCESS	read-write
	STATUS mandatory
	DESCRIPTION
	 "This object enables derivation of weight in the queue object and of scheduler node derived weight in the UNI 
          and ONT objects based on CIR in the queue shaper profile.
      ALCATEL NOTE:
                 ACCESS:     NA       USAGE:      NA
                 PERSIST:    YES      INSRVMOD:   NO
                 RANGE:      yes,no   DEFVALUE:   no
                 UNITS:      NA       SPARSE:     NA
                 DESCR:      NA "
DEFVAL { false }
::= { qosDslRecordEntry 16}

qosOntUniSchedulerNodeEIR OBJECT-TYPE
	SYNTAX	INTEGER
	ACCESS	read-only
	STATUS mandatory
	DESCRIPTION
	 "This object stores the derived EIR of the scheduler for an ONT or UNI. Value is MAX(sum(queueLvl CIR) MaxQueueEIR). "
	DEFVAL		{0}

::= { qosDslRecordEntry 17}
		
qosDslRecordDsNumRemoteQueue OBJECT-TYPE
	SYNTAX	INTEGER
	ACCESS	read-write
	STATUS mandatory
	DESCRIPTION
	 "This object stores the number of physical downstream queues per UNI on the ONT. This is settable 
          for all UNIs on a given ONT by specifying the InterfaceIndex of the ONT in this table. The allowed 
          values are 0, 4 and  8. When there are services already configured on the UNIs of the ONT, this value 
          cannot be changed by the operator."
	DEFVAL		{0}

::= { qosDslRecordEntry 18 }

qosDslRecordVlanportQueues OBJECT-TYPE
	SYNTAX	TruthValue
	ACCESS	read-write
	STATUS mandatory
	DESCRIPTION
	 "This object indicates that queues are to be configured at VLAN port level.
      ALCATEL NOTE:
                 ACCESS:     NA       USAGE:      NA
                 PERSIST:    YES      INSRVMOD:   NO
                 RANGE:      yes,no   DEFVALUE:   no
                 UNITS:      NA       SPARSE:     NA
                 DESCR:      NA "
       DEFVAL { false }

::= { qosDslRecordEntry 19}

qosDslRecordDsFloodingShaperProfile OBJECT-TYPE
        SYNTAX  AsamProfilePointer
        ACCESS  read-write
        STATUS mandatory
        DESCRIPTION
         "This object stores the shaper profile ID attached to the
        PON indexed by qosDslRecordInterfaceIndex.
        This shaper is applied for downsteam flooding traffic including broadcast and unconfigured 
        multicast traffic. It is only relevant to Gpon Lt boards. "
::= { qosDslRecordEntry 20 }

qosDslRecordCacProfileExt OBJECT-TYPE
        SYNTAX  AsamProfilePointer
        ACCESS  read-write
        STATUS mandatory
        DESCRIPTION
         "This object is extended from qosDslRecordCacProfile.
         This object stores the CAC profile ID attached to the PON indexed by qosDslRecordInterfaceIndex.
         For EPON OLT in downstream,  this object used for CAC on 10G PON bandwidth.
         This object is not used on other types of boards."
::= { qosDslRecordEntry 21}

qosOntDsQueueSharing OBJECT-TYPE
      SYNTAX      DsQueueSharingType
      ACCESS      read-write
      STATUS mandatory
      DESCRIPTION
       "This object specifies whether dowstream queue sharing is enabled at ONT(1), UNI(2) or 
        vlanPort(3) level for this ONT. The value of this object cannot be changed adter UNI's are created on
       the ONT.

      ALCATEL NOTE:
                 ACCESS:     NA       USAGE:      NA
                 PERSIST:    YES      INSRVMOD:   NO
                 RANGE:      ONT,UNI,vlanPort DEFVALUE:   UNI
                 UNITS:      NA       SPARSE:     NA
                 DESCR:      NA "
DEFVAL { 2 }
::= { qosDslRecordEntry 22 }

qosSchedulerMode OBJECT-TYPE
      SYNTAX      SchedulerModeType
      ACCESS      read-write
      STATUS      mandatory
      DESCRIPTION
       "This object specifies which mode is selected for scheduler. There are 3 modes could be selected:
        -    Subscriber based hierarchy scheduling (1): subscriber-hierarchy, subscriber based scheduling via a TM tree of hierarchy subscriber levels to achieve subscriber fairness. 
        -    Service based hierarchy scheduling (2): service-hierarchy, service based scheduling cross all subscribers via a TM tree of hierarchy subscriber levels, which keeps the subscriber based scheduling for lowest service priority to achieve subscriber fairness.
        -    Service based flat scheduling (3): service-flat, service based scheduling cross all subscribers via a flat TM tree of aggregated service queues directly attached to the root, i.e. physical line (e.g. PON port). 
ALCATEL NOTE:
                 ACCESS:        NA       USAGE:      NA
                 PERSIST:       YES      INSRVMOD:   NO
                 RANGE:    subscriber-hierarchy, service-hierarchy, service-flat    
                 DEFVALUE:   subscriber-hierarchy
                 UNITS:          NA       SPARSE:     NA
                 DESCR:         NA "
DEFVAL { 1 }
::= { qosDslRecordEntry 23 }

qosOntUniGemSharingEnable OBJECT-TYPE
      SYNTAX      QosGemSharing
      ACCESS      read-write
      STATUS mandatory
      DESCRIPTION
       "This object specifies whether Gem Sharing is enabled or not. This obeject is used only in 
        case of UNI interface and all other interfaces do not use this object

      ALCATEL NOTE:
                 ACCESS:     NA       USAGE:      NA
                 PERSIST:    YES      INSRVMOD:   NO
                 RANGE:      1..3     DEFVALUE:   2
                 UNITS:      NA       SPARSE:     NA
                 DESCR:      NA "

DEFVAL { 2 }
::= { qosDslRecordEntry 24 }

qosIngressProfileId OBJECT-TYPE
	SYNTAX	AsamProfilePointer
	ACCESS	read-write
	STATUS mandatory
	DESCRIPTION
	 "This object contains a reference to an existing ingress profile. 
      ALCATEL NOTE:
                 ACCESS:     NA       USAGE:      NA
                 PERSIST:    YES       INSRVMOD:   NO
                 RANGE:      NA       DEFVALUE:   NA
                 UNITS:      NA       SPARSE:     NA
                 DESCR:      NA "
DEFVAL { 0 }
::= {qosDslRecordEntry 25 }

qosPonSharedServiceMulticastSchedulerProfile  OBJECT-TYPE
    SYNTAX   AsamProfilePointer
    ACCESS    read-write
    STATUS    mandatory
    DESCRIPTION
     "This object specifies the scheduling profile for PON shared multicast service in case of service-hierarchy scheduling  mode. 
      If no profile is associated, and service-hierarchy scheduling mode is specified, then  a system default multicast service scheduler node profile should be associated with the PON shared multicast service, in this default profile, the configuration should be: priority 6, weight 50, no shaper."
::= { qosDslRecordEntry 26 }

qosPonSharedServiceBroadcastSchedulerProfile OBJECT-TYPE
    SYNTAX   AsamProfilePointer
    ACCESS    read-write
    STATUS   mandatory
    DESCRIPTION
     " This object specifies the scheduling profile for PON shared broadcast service, i.e. flooding service, in case of service-hierarchy scheduling mode. 
       If no profile is associated, and service-based scheduling mode is specified, then  a system default multicast service scheduler node profile should be associated with the PON shared broadcast service, in this default profile, the configuration should be: priority 6, weight 50, no shaper."
::= { qosDslRecordEntry 27 }

qosInterfaceBandwidthProfileId OBJECT-TYPE
	SYNTAX	AsamProfilePointer
	ACCESS	read-write
	STATUS mandatory
	DESCRIPTION
	 "This object contains a reference to an existing BandWidth profile.	 
      ALCATEL NOTE:
                 ACCESS:     NA       USAGE:      NA
                 PERSIST:    YES      INSRVMOD:   NO
                 RANGE:      NA       DEFVALUE:   NA
                 UNITS:      NA       SPARSE:     NA
                 DESCR:      NA "
DEFVAL { 0 }
::= { qosDslRecordEntry 28 }


qosInterfaceBandwidthSharing OBJECT-TYPE
	SYNTAX	INTEGER (1..2)
	ACCESS	read-write
	STATUS mandatory
	DESCRIPTION
	 "This object specifies whether per interface bandwidth sharing is enabled or disabled. 1 = disabled, 2 = UNI level BW  or TCONT sharing across UNIs of an ONT.
      ALCATEL NOTE:
                 ACCESS:     NA       USAGE:      NA
                 PERSIST:    YES       INSRVMOD:   NO
                 RANGE:      1..2       DEFVALUE:  1
                 UNITS:      NA       SPARSE:     NA
                 DESCR:      NA "
DEFVAL { 1 }
::= { qosDslRecordEntry 29 }


qosInterfaceUsAggrQueuesConfigProfileId  OBJECT-TYPE
	SYNTAX	AsamProfilePointer 
	ACCESS	read-write
	STATUS mandatory
	DESCRIPTION
	 " This object specifies the aggrQueuesConfig profile applied on upstream queues of a UNI.
      ALCATEL NOTE:
                 ACCESS:     NA       USAGE:      NA
                 PERSIST:    YES      INSRVMOD:   NO
                 RANGE:               DEFVALUE:   0
                 UNITS:      NA       SPARSE:     NA
                 DESCR:      NA "
DEFVAL { 0 }
::= { qosDslRecordEntry 30 }  

qosInterfaceDsAggrQueuesConfigProfileId  OBJECT-TYPE
	SYNTAX	AsamProfilePointer 
	ACCESS	read-write
	STATUS mandatory
	DESCRIPTION
	 " This object specifies the aggrQueuesConfig profile applied on downstream queues of a UNI.
      ALCATEL NOTE:
                 ACCESS:     NA       USAGE:      NA
                 PERSIST:    YES      INSRVMOD:   NO
                 RANGE:               DEFVALUE:   0
                 UNITS:      NA       SPARSE:     NA
                 DESCR:      NA "
DEFVAL { 0 }
::= { qosDslRecordEntry 31 } 




qosDslRecordDsSchedulerTag OBJECT-TYPE
	SYNTAX SchedulerType
	ACCESS read-write
	STATUS mandatory
	DESCRIPTION
     		"This object used to identify downstream scheduler reference, 
			it shall be used for S+C forwarder only, the tag shall cover both Pbit and DEI,  
			 it shall be used for any scheduling mode, flat or subscriber based H-QoS or service based H-QoS,
			 and it shall be used for egress scheduling, including queue mapping and queue color mapping.
			1: c-vlan tag based
			2: s-vlan tag based
			3: egressOuterTag"
	DEFVAL { 3 }
::= {qosDslRecordEntry 32 }


-- qosStatisticsAndData
qosStatisticsAndData OBJECT IDENTIFIER ::= { qosMIB 7}
--
--
--
--
qosStatsP15mTable OBJECT-TYPE
	SYNTAX	SEQUENCE OF QosStatsP15mEntry
	ACCESS not-accessible
	STATUS	mandatory
	DESCRIPTION
	"This table contains the previous 15 minute QoS statistics on a
	per L3 LIM basis"
::= {qosStatisticsAndData 1 }

qosStatsP15mEntry OBJECT-TYPE
SYNTAX QosStatsP15mEntry
ACCESS not-accessible
STATUS mandatory
DESCRIPTION "An entry in the qosStatsP15mTable"
INDEX { eqptSlotId, qosStatsP15mIntervalNumber }
::= {qosStatsP15mTable 1 }

QosStatsP15mEntry ::= SEQUENCE
	{
		qosStatsP15mIntervalNumber	 		INTEGER,
		qosStatsP15mUpAggrBufOvflw 			Counter,
		qosStatsP15mUpObcAggrBufOvflw			Counter,
		qosStatsP15mDnObcAggrBufOvflw			Counter,
		qosStatsP15mDnUcAggrBufOvflw			Counter,
		qosStatsP15mDnMcAggrBufOvflw			Counter,
		qosStatsP15mObcInjectedBufOvflw			Counter,
		qosStatsP15mMeasuredTime			INTEGER,
		qosStatsP15mPartialAggrBufOvflw			Counter64bit,
		qosStatsP15mInvalidDataFlag			INTEGER

	}
qosStatsP15mIntervalNumber 	OBJECT-TYPE
	SYNTAX	INTEGER (1..32)
	ACCESS not-accessible
	STATUS mandatory
	DESCRIPTION
	"A number between 1 and 32, which identifies the interval for which the
set of statistics is available. The interval identified by 1 is the
most recently completed 15 minute interval, and the interval identified
by N is the interval immediately preceding the one identified by N-1."
::= {qosStatsP15mEntry 1 }
qosStatsP15mUpAggrBufOvflw 	OBJECT-TYPE
	SYNTAX	Counter
	ACCESS read-only
	STATUS mandatory
	DESCRIPTION
	 "This object is used to count the number of buffer overflows
	on an L3 LIM module in the upstream direction on a 15 minute
	interval basis. The upstream direction on the LIM is non-blocking,
	hence this value should always read zero under normal working
	conditions. The reassembly buffers are also included in this
	counter. [R4.2.03]On NELT-B, it indicates the packet drop ratio(unit:
 	10e-6) in the aggregated port."
::= {qosStatsP15mEntry 2 }

qosStatsP15mUpObcAggrBufOvflw 	OBJECT-TYPE
	SYNTAX	Counter
	ACCESS read-only
	STATUS mandatory
	DESCRIPTION
	 "This object is used to count the number of buffer overflows
	on an L3 LIM module for the OBC-directed traffic upstream
	on a 15 minute	 interval basis. In some special conditions
	such as system startup or re-start packet loss may occur here
	but under normal circumstances this counter should read zero.
	There are 4 queues towards the OBC (upstream). This counter
	counts the buffer overflows for all 4 queues together."
::= {qosStatsP15mEntry 3 }
qosStatsP15mDnObcAggrBufOvflw 	OBJECT-TYPE
	SYNTAX	Counter
	ACCESS read-only
	STATUS mandatory
	DESCRIPTION
	 "This object is used to count the number of buffer overflows
	on an L3 LIM module for the OBC-directed traffic downstream
	on a 15 minute	 interval basis.
	Under normal circumstances this counter should always read zero.
	There are 4 queues towards the OBC (downstream). This counter
	counts the buffer overflows for all 4 queues together."
::= {qosStatsP15mEntry 4 }
qosStatsP15mDnUcAggrBufOvflw 	OBJECT-TYPE
	SYNTAX	Counter
	ACCESS read-only
	STATUS mandatory
	DESCRIPTION
	 "Previous 15 minute downstream buffer pool overflow
	On an L3 LIM module the buffer space is divided into groups
	per usage: downstream pool, upstream pool, and
	OBC-injected traffic pool. This object stores a counter for the
	event of total buffer overflow of the downstream unicast pool.
	This even should not occur. Queue fill-up and tail drop is a
	normal condition for data traffic (individual queues) but not for
	voice and video on demand services (individual queues).
	If the total downstream pool is filled, that means
	that non-QoS aware packet loss will occur. This event can happen
	if the memory was statistically over-allocated or there is an
	internal system error, which should be reported.[R4.2.03]On NELT-B,
	it indicates the packet drop ratio(unit:10e-6) in CATAN uplink."
::= {qosStatsP15mEntry 5 }

qosStatsP15mDnMcAggrBufOvflw 	OBJECT-TYPE
	SYNTAX	Counter
	ACCESS read-only
	STATUS mandatory
	DESCRIPTION
	 "Previous 15 minute downstream multicast total buffer pool overflow
	On an L3 LIM module the buffer space is divided into groups
	per usage: downstream pool, upstream pool, multicast pool and
	OBC-injected traffic pool. This object stores a counter for the
	event of total buffer overflow of the downstream multicast pool.
	This even should be a rather rare event. On the long term,buffer
	overflow in the multicast pool may occur a few times a day less
	than a few tens under heavy multicast usage).This object is not implemented."
::= {qosStatsP15mEntry 6 }
qosStatsP15mObcInjectedBufOvflw OBJECT-TYPE
	SYNTAX	Counter
	ACCESS read-only
	STATUS mandatory
	DESCRIPTION
	 "Previous 15 minute for OBC-injected buffer overflow event on LIM
	This event happens if the processor cannot cope with the extensive
	load of the system and cannot reassemble a frame in due time.
	This event should not occur under normal working conditions.
	This counter is used for both upstream and downstream
	OBC-injected frames on an L3 LIM. This object is not implemented.
		"
::= {qosStatsP15mEntry 7 }
qosStatsP15mMeasuredTime 	OBJECT-TYPE
	SYNTAX	INTEGER
	ACCESS read-only
	STATUS mandatory
	DESCRIPTION
	 "The amount of time, measured in seconds, that statistics
	for this entry have been counted."
::= {qosStatsP15mEntry 8 }
qosStatsP15mPartialAggrBufOvflw 	OBJECT-TYPE 
	SYNTAX	Counter64bit
	ACCESS read-only
	STATUS mandatory
	DESCRIPTION
	    "Previous 15 minute dropped lower traffic class packets due to global buffer occupancy 
             threshold overflow. Currently the lower traffic class means BE+CL traffic. When global 
             available buffer used up, the dropped BE+CL packets will be counted in other aggregation 
             buffer overflow counters together with other traffic classes."
::= {qosStatsP15mEntry 9 }

qosStatsP15mInvalidDataFlag	OBJECT-TYPE 
	SYNTAX	INTEGER (0..1)
	ACCESS read-only
	STATUS mandatory
	DESCRIPTION
	    " This object indicates the validity of the corresponding counter statistics data.
It is set to 1 when the data is incomplete or invalid and set to 0 when the data is complete and valid. 
The data is incomplete or invalid mean:
- the measured time deviates by more than 10 seconds from the nominal interval duration (900 seconds for a 15 minutes interval), or 
- the data is incomplete in the accumulation period. "
::= {qosStatsP15mEntry 10 }



--
--
--
--
-- Current 15 minute counters
qosStatsC15mTable OBJECT-TYPE
	SYNTAX	SEQUENCE OF QosStatsC15mEntry
	ACCESS not-accessible
	STATUS	mandatory
	DESCRIPTION
	"This table contains the current 15 minute QoS statistics
	 on a per L3 LIM basis"
::= {qosStatisticsAndData 2 }
qosStatsC15mEntry OBJECT-TYPE
	SYNTAX QosStatsC15mEntry
	ACCESS not-accessible
	STATUS mandatory
	DESCRIPTION "An entry in the qosStatsC15mTable"
	INDEX { eqptSlotId }
::= {qosStatsC15mTable 1 }
QosStatsC15mEntry ::= SEQUENCE
	{
		qosStatsC15mUpAggrBufOvflw 			Counter,
		qosStatsC15mUpObcAggrBufOvflw			Counter,
		qosStatsC15mDnObcAggrBufOvflw			Counter,
		qosStatsC15mDnUcAggrBufOvflw			Counter,
		qosStatsC15mDnMcAggrBufOvflw			Counter,
		qosStatsC15mObcInjectedBufOvflw			Counter,
		qosStatsC15mElapseTime				INTEGER,
		qosStatsC15mMeasuredTime			INTEGER,
		qosStatsC15mPartialAggrBufOvflw			Counter64bit,
		qosStatsC15mInvalidDataFlag			INTEGER


	}
qosStatsC15mUpAggrBufOvflw 	OBJECT-TYPE
	SYNTAX	Counter
	ACCESS read-only
	STATUS mandatory
	DESCRIPTION
	 "This object is used to count the number of buffer overflows
	on an L3 LIM module in the upstream direction on a 15 minute
	interval basis in the current measurement epoch.
	The upstream direction on the LIM is non-blocking,
	hence this value should read always zero under normal working
 	conditions. The reassembly buffers are included in this
	counter. [R4.2.03]On NELT-B, it indicates the packet drop ratio(unit:
 	10e-6) in the aggregated port."
::= {qosStatsC15mEntry 1 }

qosStatsC15mUpObcAggrBufOvflw 	OBJECT-TYPE
	SYNTAX	Counter
	ACCESS read-only
	STATUS mandatory
	DESCRIPTION
	 "This object is used to count the number of buffer overflows
	on an L3 LIM module for the OBC-directed traffic upstream
	on a 15 minute	 interval basis in the current measurement epoch.
	In some special conditions
	such as system startup or re-start packet loss may occur here
	but under normal circumstances this counter should read zero.
	There are 4 queues towards the OBC (upstream). This counter
	counts the buffer overflows for all 4 queues together. "
::= {qosStatsC15mEntry 2 }

qosStatsC15mDnObcAggrBufOvflw 	OBJECT-TYPE
	SYNTAX	Counter
	ACCESS read-only
	STATUS mandatory
	DESCRIPTION
	 "This object is used to count the number of buffer overflows
	on an L3 LIM module for the OBC-directed traffic downstream
	on a 15 minute	 interval basis in the current measurement epoch.
	Under normal circumstances this counter should always readm zero.
	There are 4 queues towards the OBC (downstream). This counter
	counts the buffer overflows for all 4 queues together."
::= {qosStatsC15mEntry 3 }
qosStatsC15mDnUcAggrBufOvflw 	OBJECT-TYPE
	SYNTAX	Counter
	ACCESS read-only
	STATUS mandatory
	DESCRIPTION
	 "Current 15 minute downstream buffer pool overflow
	On an L3 LIM module the buffer space is divided into groups
	per usage: downstream pool, upstream pool, and
	OBC-injected traffic pool. This object stores a counter for the
	event of total buffer overflow of the downstream unicast pool.
	This even should not occur. Queue fill-up and tail drop is a
	normal condition for data traffic (individual queues) but not for
	voice and video on demand services (individual queues).
	If the total downstream pool is filled, that means
	that QoS un-aware packet loss will occur. This event can happen
	if the memory was statistically over-allocated via configuration
	or there is an	 internal system error, which should be reported.
	If the downstream buffer pool was statistically
	over-allocated, an warning message will be raised in
	the Error Management. [R4.2.03]On NELT-B, it indicates the packet
	drop ratio(unit:10e-6) in CATAN uplink"
::= {qosStatsC15mEntry 4 }
qosStatsC15mDnMcAggrBufOvflw 	OBJECT-TYPE
	SYNTAX	Counter
	ACCESS read-only
	STATUS mandatory
	DESCRIPTION
	 "Current 15 minute downstream multicast total buffer pool overflow
	On a LIM module the buffer space is divided into groups
	per usage: downstream pool, upstream pool, multicast pool and
	OBC-injected traffic pool. This object stores a counter for the
	event of total buffer overflow of the downstream multicast pool.
	This even should be a rather rare event. On the long term, buffer
	overflow in the multicast pool may occur a few times a day (less
	than a few tens under heavy multicast usage). This object is not implemented."
::= {qosStatsC15mEntry 5 }

qosStatsC15mObcInjectedBufOvflw OBJECT-TYPE
	SYNTAX	Counter
	ACCESS read-only
	STATUS mandatory
	DESCRIPTION
	 "Current 15 minute for OBC-injected buffer overflow event on LIM
	There is a reserved buffer pool for OBC-injected traffic which
	Under very heavy load conditions may eventually get full, and the
	LIM OBC will be unable to communicate with the external world for
	a very short time interval. If this counter reaches large numbers,
	(above ten) then there is an error condition and should be
	reported. This object is not implemented."
::= {qosStatsC15mEntry 6 }
qosStatsC15mElapseTime 	OBJECT-TYPE
	SYNTAX	INTEGER
	ACCESS read-only
	STATUS mandatory
	DESCRIPTION
	 "The elapsed time interval since the last measurement epoch
	started."
::= {qosStatsC15mEntry 7 }
qosStatsC15mMeasuredTime 	OBJECT-TYPE
	SYNTAX	INTEGER
	ACCESS read-only
	STATUS mandatory
	DESCRIPTION
	 "The amount of time, measured in seconds, that statistics
	for this entry have been counted."
::= {qosStatsC15mEntry 8 }
qosStatsC15mPartialAggrBufOvflw 	OBJECT-TYPE 
	SYNTAX	Counter64bit
	ACCESS read-only
	STATUS mandatory
	DESCRIPTION
	    "Current 15 minute dropped lower traffic class packets due to global buffer occupancy 
             threshold overflow. Currently the lower traffic class means BE+CL traffic. When global 
             available buffer used up, the dropped BE+CL packets will be counted in other aggregation 
             buffer overflow counters together with other traffic classes."
::= {qosStatsC15mEntry 9 }
qosStatsC15mInvalidDataFlag	OBJECT-TYPE 
	SYNTAX	INTEGER (0..1)
	ACCESS read-only
	STATUS mandatory
	DESCRIPTION
	    " This object indicates the validity of the corresponding counter statistics data.
It is set to 1 when the data is incomplete or invalid and set to 0 when the data is complete and valid. 
The data is incomplete or invalid mean:
- the measured time deviates by more than 10 seconds from the nominal interval duration (900 seconds for a 15 minutes interval), or 
- the data is incomplete in the accumulation period. "
::= {qosStatsC15mEntry 10 }

--
--
--
--
-- previous 1day counters
qosStatsP1dTable OBJECT-TYPE
	SYNTAX	SEQUENCE OF QosStatsP1dEntry
	ACCESS not-accessible
	STATUS	mandatory
	DESCRIPTION
	"This table contains the previous one day QoS statistics on a
	 per L3 LIM basis"
::= {qosStatisticsAndData 3 }
qosStatsP1dEntry OBJECT-TYPE
	SYNTAX	 QosStatsP1dEntry
	ACCESS	not-accessible
	STATUS 	mandatory
	DESCRIPTION
	"This table contains past one day QoS statistics"
	INDEX {eqptSlotId, qosStatsP1dIntervalNumber}
::=	{qosStatsP1dTable 1}
QosStatsP1dEntry ::= SEQUENCE
	{
		qosStatsP1dIntervalNumber			INTEGER,
		qosStatsP1dUpAggrBufOvflw 			Counter,
		qosStatsP1dUpObcAggrBufOvflw			Counter,
		qosStatsP1dDnObcAggrBufOvflw			Counter,
		qosStatsP1dDnUcAggrBufOvflw			Counter,
		qosStatsP1dDnMcAggrBufOvflw			Counter,
		qosStatsP1dObcInjectedBufOvflw			Counter,
		qosStatsP1dMeasuredTime				INTEGER,
		qosStatsP1dPartialAggrBufOvflw			Counter64bit,
		qosStatsP1dInvalidDataFlag				INTEGER
	}
qosStatsP1dIntervalNumber 	OBJECT-TYPE
	SYNTAX	INTEGER (1)
	ACCESS not-accessible
	STATUS mandatory
	DESCRIPTION
	"Presently always 1, because day statistics are only stored for
	 one day. This may change in the future."
::= {qosStatsP1dEntry 1}
qosStatsP1dUpAggrBufOvflw 	OBJECT-TYPE
	SYNTAX	Counter
	ACCESS read-only
	STATUS mandatory
	DESCRIPTION
	 "Previous One Day Upstream Aggregate Buffer Overflow
	This object is used to count the number of buffer overflows
	on an L3 LIM module in the upstream direction on a one day
	interval basis. The upstream direction on the LIM is non-blocking,
	hence this value should read always zero under normal working
	conditions. The reassembly buffers are also included in this
	counter. [R4.2.03]On NELT-B, it indicates the packet drop ratio(unit:
 	10e-6) in the aggregated port."
::= {qosStatsP1dEntry 2}

qosStatsP1dUpObcAggrBufOvflw 	OBJECT-TYPE
	SYNTAX	Counter
	ACCESS read-only
	STATUS mandatory
	DESCRIPTION
	 "Previous One Day Upstream OBC Aggregate Buffer Overflow
	This object is used to count the number of buffer overflows
 	on an L3 LIM module for the OBC-directed traffic upstream
	on a one day interval basis. In some special conditions
	such as system startup or re-start packet loss may occur here
	but under normal circumstances this counter should read zero.
	There are 4 queues towards the OBC (upstream). This counter
	counts the buffer overflows for all 4 queues together."
::= {qosStatsP1dEntry 3}

qosStatsP1dDnObcAggrBufOvflw 	OBJECT-TYPE
	SYNTAX	Counter
	ACCESS read-only
	STATUS mandatory
	DESCRIPTION
	 "Previous One Day Downstream OBC Aggregate Buffer Overflow
	This object is used to count the number of buffer overflows
	on a L3 LIM module for the OBC-directed traffic downstream
	on a one day interval basis.
	Under normal circumstances this counter should always read zero.
	There are 4 queues towards the OBC (downstream). This counter
	counts the buffer overflows for all 4 queues together."
::= {qosStatsP1dEntry 4}
qosStatsP1dDnUcAggrBufOvflw 	OBJECT-TYPE
	SYNTAX	Counter
	ACCESS read-only
	STATUS mandatory
	DESCRIPTION
	 "Previous One Day Downstream buffer pool overflow
	On an L3 LIM module the buffer space is divided into groups
	per usage: downstream pool, upstream pool, and
	OBC-injected traffic pool. This object stores a counter for the
	event of total buffer overflow of the downstream unicast pool.
	This even should not occur. Queue fill-up and tail drop is a
	normal condition for data traffic (individual queues) but not for
	voice and video on demand services (individual queues).
	If the total downstream pool is filled, that means
	that non-QoS aware packet loss will occur. This event can happen
	if the memory was statistically over-allocated or there is an
	internal system error, which should be reported.
	If the downstream buffer pool was statistically over-allocated,
	a warning message will be raised in the Error management after
	each queue configuration. [R4.2.03]On NELT-B, it indicates the 
	packet drop ratio(unit:10e-6) in CATAN uplink."
::= {qosStatsP1dEntry 5}
qosStatsP1dDnMcAggrBufOvflw 	OBJECT-TYPE
	SYNTAX	Counter
	ACCESS read-only
	STATUS mandatory
	DESCRIPTION
	 "Previous One Day Downstream Multicast total buffer pool overflow
	On an L3 LIM module the buffer space is divided into groups
	per usage: downstream pool, upstream pool, multicast pool and
	OBC-injected traffic pool. This object stores a counter for the
	event of total buffer overflow of the downstream multicast pool.
	This even should be a rather rare event. On the long term,buffer
	overflow in the multicast pool may occur a few times a day (less
	than a few tens under heavy multicast usage). This object is not implemented."
::= {qosStatsP1dEntry 6}
qosStatsP1dObcInjectedBufOvflw OBJECT-TYPE
	SYNTAX	Counter
	ACCESS read-only
	STATUS mandatory
	DESCRIPTION
	 "Previous One Day OBC-injected buffer-pool overflow
	In some heavy load conditions this event may occur as the
	OBC-injected frames fill up completely the buffer space mreserved
	for this purpose. In heavy load conditions, this even may occur
	with a low probability. If this counter reads in the order of
	hundreds or above, then there is clearly an error. This object is not implemented.
		"
::= {qosStatsP1dEntry 7}
qosStatsP1dMeasuredTime 	OBJECT-TYPE
	SYNTAX	INTEGER
	ACCESS read-only
	STATUS mandatory
	DESCRIPTION
	 "The actual time elapsed during which the measurement was made"
::= {qosStatsP1dEntry 8}

qosStatsP1dPartialAggrBufOvflw 	OBJECT-TYPE 
	SYNTAX	Counter64bit
	ACCESS read-only
	STATUS mandatory
	DESCRIPTION
	    "Previous One Day dropped lower traffic class packets due to global buffer occupancy 
             threshold overflow. Currently the lower traffic class means BE+CL traffic. When global 
             available buffer used up, the dropped BE+CL packets will be counted in other aggregation 
             buffer overflow counters together with other traffic classes."
::= {qosStatsP1dEntry 9}

qosStatsP1dInvalidDataFlag	OBJECT-TYPE 
	SYNTAX	INTEGER (0..1)
	ACCESS read-only
	STATUS mandatory
	DESCRIPTION
	    " This object indicates the validity of the corresponding counter statistics data.
It is set to 1 when the data is incomplete or invalid and set to 0 when the data is complete and valid. 
The data is incomplete or invalid mean:
- the measured time deviates by more than 10 seconds from the nominal interval duration (86400 seconds for a 24 hour interval), or 
- the data is incomplete in the accumulation period. "
::= {qosStatsP1dEntry 10 }


--
--
--
--
-- Current 1 day counters
qosStatsC1dTable OBJECT-TYPE
	SYNTAX	SEQUENCE OF QosStatsC1dEntry
	ACCESS not-accessible
	STATUS	mandatory
	DESCRIPTION
	"This table contains the current one day QoS statistics
	 on a per LIM basis"
::= {qosStatisticsAndData 4 }
qosStatsC1dEntry OBJECT-TYPE
	SYNTAX QosStatsC1dEntry
	ACCESS not-accessible
	STATUS mandatory
	DESCRIPTION "An entry in the qosStatsC1dTable"
	INDEX { eqptSlotId }
::= {qosStatsC1dTable 1 }


QosStatsC1dEntry ::= SEQUENCE
	{
		qosStatsC1dUpAggrBufOvflw 			Counter,
		qosStatsC1dUpObcAggrBufOvflw			Counter,
		qosStatsC1dDnObcAggrBufOvflw			Counter,
		qosStatsC1dDnUcAggrBufOvflw			Counter,
		qosStatsC1dDnMcAggrBufOvflw			Counter,
		qosStatsC1dObcInjectedBufOvflw			Counter,
		qosStatsC1dElapseTime				INTEGER,
		qosStatsC1dMeasuredTime				INTEGER,
		qosStatsC1dPartialAggrBufOvflw			Counter64bit,
		qosStatsC1dInvalidDataFlag				INTEGER
	}

qosStatsC1dUpAggrBufOvflw 	OBJECT-TYPE
	SYNTAX	Counter
	ACCESS read-only
	STATUS mandatory
	DESCRIPTION
	 "This object is used to count the number of buffer overflows
	on L3 LIM modules in the upstream direction on a one day
	interval basis in the current measurement epoch.
	The upstream direction on the LIM is non-blocking,
	hence this value should read always zero under normal working
	conditions. The reassembly buffers overflows are also
	included in this counter. [R4.2.03]On NELT-B, it indicates the 
	packet drop ratio(unit:10e-6) in the aggregated port."
::= {qosStatsC1dEntry 1 }

qosStatsC1dUpObcAggrBufOvflw 	OBJECT-TYPE
	SYNTAX	Counter
	ACCESS read-only
	STATUS mandatory
	DESCRIPTION
	 "This object is used to count the number of buffer overflows
	on L3 LIM modules for the OBC-directed traffic upstream
	on a one day interval basis in the current measurement epoch.
	In some special conditions
	such as system startup or re-start packet loss may occur here
	but under normal circumstances this counter should read zero.
	There are 4 queues towards the OBC (upstream). This counter
	counts the buffer overflows for all 4 queues together. "
::= {qosStatsC1dEntry 2 }
qosStatsC1dDnObcAggrBufOvflw 	OBJECT-TYPE
	SYNTAX	Counter
	ACCESS read-only
	STATUS mandatory
	DESCRIPTION
	 "This object is used to count the number of buffer overflows
	on an L3 LIM module for the OBC-directed traffic downstream
	on a one day interval basis in the current measurement epoch.
	Under normal circumstances this counter should always read zero.
	There are 4 queues towards the OBC (downstream). This counter
	counts the buffer overflows for all 4 queues together."
::= {qosStatsC1dEntry 3 }
qosStatsC1dDnUcAggrBufOvflw 	OBJECT-TYPE
	SYNTAX	Counter
	ACCESS read-only
	STATUS mandatory
	DESCRIPTION
	 "Current One Day Downstream buffer pool overflow.
	On an L3 LIM module the buffer space is divided into groups
	per usage: downstream pool, upstream pool, and
	OBC-injected traffic pool. This object stores a counter for the
	event of total buffer overflow of the downstream unicast pool.
	This even should not occur. Queue fill-up and tail drop is a
	normal condition for data traffic (individual queues) but not for
	voice and video on demand services (individual queues).
	If the total downstream pool is filled, that means
	that QoS un-aware packet loss will occur. This event can happen
	if the memory was statistically over-allocated or there is an
	internal system error, which should be reported.
	If the downstream buffer pool was statistically over-allocated,
	a warning message will be raised in the Error management after
	each queue configuration. [R4.2.03]On NELT-B, it indicates the 
	packet drop ratio(unit:10e-6) in CATAN uplink."
::= {qosStatsC1dEntry 4 }
qosStatsC1dDnMcAggrBufOvflw 	OBJECT-TYPE
	SYNTAX	Counter
	ACCESS read-only
	STATUS mandatory
	DESCRIPTION
	 "Current one day downstream multicast total buffer pool overflow
	On a LIM module the buffer space is divided into groups
	per usage: downstream pool, upstream pool, multicast pool and
	OBC-injected traffic pool. This object stores a counter for the
	event of total buffer overflow of the downstream multicast pool.
	This even should be a rather rare event. On the long term,buffer
	overflow in the multicast pool may occur a few times a day (less
	than a few tens under heavy multicast usage). This object is not implemented."
::= {qosStatsC1dEntry 5}

qosStatsC1dObcInjectedBufOvflw OBJECT-TYPE
	SYNTAX	Counter
	ACCESS read-only
	STATUS mandatory
	DESCRIPTION
	 "Current One Day OBC-injected buffer overflow event on EBLT LIMs.
	There is a reserved buffer pool for OBC-injected traffic which
	Under very heavy load conditions may eventually get full, and the
	LIM OBC will be unable to communicate with the external world for
	a very short time interval. If this counter reaches large numbers,
	(above ten) then there is an error condition and should be
	reported. This object is not implemented."
::= {qosStatsC1dEntry 6 }
qosStatsC1dElapseTime 	OBJECT-TYPE
	SYNTAX	INTEGER
	ACCESS read-only
	STATUS mandatory
	DESCRIPTION
	 "The elapsed time interval since the last measurement epoch
	started."
::= {qosStatsC1dEntry 7 }
qosStatsC1dMeasuredTime 	OBJECT-TYPE
	SYNTAX	INTEGER
	ACCESS read-only
	STATUS mandatory
	DESCRIPTION
	 "The measured time interval since the last measurement epoch
	started."
::= {qosStatsC1dEntry 8 }
qosStatsC1dPartialAggrBufOvflw OBJECT-TYPE 
	SYNTAX	Counter64bit
	ACCESS read-only
	STATUS mandatory
	DESCRIPTION
	    "Current One Day dropped lower traffic class packets due to global buffer occupancy threshold overflow. Currently the lower traffic class means BE+CL traffic. When global available buffer used up, the dropped BE+CL packets will be counted in other aggregation buffer overflow counters together with other traffic classes."
::= {qosStatsC1dEntry 9 }

qosStatsC1dInvalidDataFlag	OBJECT-TYPE 
	SYNTAX	INTEGER (0..1)
	ACCESS read-only
	STATUS mandatory
	DESCRIPTION
	    " This object indicates the validity of the corresponding counter statistics data.
It is set to 1 when the data is incomplete or invalid and set to 0 when the data is complete and valid. 
The data is incomplete or invalid mean:
- the measured time deviates by more than 10 seconds from the nominal interval duration (86400 seconds for a 24 hour interval), or 
- the data is incomplete in the accumulation period. "
::= {qosStatsC1dEntry 10 }

--
--
--
--
-- qosStatsTotalTable
qosStatsTotalTable OBJECT-TYPE
	SYNTAX	SEQUENCE OF QosStatsTotalEntry
	ACCESS not-accessible
	STATUS	mandatory
	DESCRIPTION
	"This table contains the current one day QoS statistics
	 per L3 LIM"
::= {qosStatisticsAndData 5 }
qosStatsTotalEntry OBJECT-TYPE
	SYNTAX QosStatsTotalEntry
	ACCESS not-accessible
	STATUS mandatory
	DESCRIPTION "An entry in the qosStatsTotalTable"
	INDEX { eqptSlotId }
::= {qosStatsTotalTable 1 }

QosStatsTotalEntry ::= SEQUENCE
	{
		qosStatsTotalUpAggrBufOvflw 			Counter,
		qosStatsTotalUpObcAggrBufOvflw			Counter,
		qosStatsTotalDnObcAggrBufOvflw			Counter,
		qosStatsTotalDnUcAggrBufOvflw			Counter,
		qosStatsTotalDnMcAggrBufOvflw			Counter,
		qosStatsTotalObcInjectedBufOvflw		Counter,
		qosStatsTotalElapseTime				INTEGER,
		qosStatsTotalMeasuredTime			INTEGER,
		qosStatsValid15mIntervals			INTEGER,
		qosStatsValid1dIntervals			INTEGER,
		qosTotalPolicersInUse				INTEGER,
		qosPolicersInUseVlan				INTEGER,
		qosPolicersInUseDot1X				INTEGER,
		qosPolicersInUsePPP				INTEGER,
        qosPolicersInUseIp			        INTEGER,
		qosPolicersInUseSubFlow				INTEGER,
		qosStatsTotalFanOutPassBytes			Counter64bit,
		qosStatsTotalFanOutPassFrames			Counter64bit,
		qosStatsTotalPartialAggrBufOvflw		Counter64bit
	}
qosStatsTotalUpAggrBufOvflw 	OBJECT-TYPE
	SYNTAX	Counter
	ACCESS read-only
	STATUS mandatory
	DESCRIPTION
	 "This object is used to count the number of buffer overflows
	per L3 LIM module in the upstream direction
	since the statistics were last reset.
	The upstream direction on the LIM is non-blocking,
	hence this value should read always zero under normal working
	conditions. The reassembly buffer overflows are also
	included in this counter. [R4.2.03]On NELT-B, it indicates the 
	packet drop ratio(unit:10e-6) in the aggregated port."
::= {qosStatsTotalEntry 1}

qosStatsTotalUpObcAggrBufOvflw 	OBJECT-TYPE
	SYNTAX	Counter
	ACCESS read-only
	STATUS mandatory
	DESCRIPTION
	 "This object is used to count the number of buffer overflows
	on a LIM module for the OBC-directed traffic upstream
	since the statistic was last reset.
	In some special conditions
	such as system startup or re-start packet loss may occur here
	but under normal circumstances this counter should read zero.
	There are 4 queues towards the OBC (upstream). This counter
	counts the buffer overflows for all 4 queues together."
::= {qosStatsTotalEntry 2}
qosStatsTotalDnObcAggrBufOvflw 	OBJECT-TYPE
	SYNTAX	Counter
	ACCESS read-only
	STATUS mandatory
	DESCRIPTION
	 "This object is used to count the number of buffer overflows
	on a LIM module for the OBC-directed traffic downstream
	since the statistic was last reset.
	Under normal circumstances this counter should always read zero.
	There are 4 queues towards the OBC (downstream). This counter
	counts the buffer overflows for all 4 queues together."
::= {qosStatsTotalEntry 3}
qosStatsTotalDnUcAggrBufOvflw 	OBJECT-TYPE
	SYNTAX	Counter
	ACCESS read-only
	STATUS mandatory
	DESCRIPTION
	 "Total Downstream buffer pool overflow.
	On an L3 LIM module the buffer space is divided into groups
	per usage: downstream pool, upstream pool, and
	OBC-injected traffic pool. This object stores a counter for the
	event of total buffer overflow of the downstream unicast pool.
	This even should not occur. Queue fill-up and tail drop is a
	normal condition for data traffic (individual queues) but not for
	voice and video on demand services (individual queues).
	If the total downstream pool is filled, that means
	that QoS un-aware packet loss will occur. This event can happen
	if the memory was statistically over-allocated or there is an
	internal system error, which should be reported.
	If the downstream buffer pool was statistically over-allocated,
	a warning message will be raised in the Error management after
	each queue configuration. [R4.2.03]On NELT-B, it indicates the 
	packet drop ratio(unit:10e-6) in CATAN uplink."
::= {qosStatsTotalEntry 4}
qosStatsTotalDnMcAggrBufOvflw 	OBJECT-TYPE
	SYNTAX	Counter
	ACCESS read-only
	STATUS mandatory
	DESCRIPTION
	 "Total Downstream Multicast Aggregate buffer pool overflow
	On L3 LIM modules the buffer space is divided into groups
	per usage: downstream pool, upstream pool, multicast pool and
	OBC-injected traffic pool. This object stores a counter for the
	event of total buffer overflow of the downstream multicast pool.
	This even should be a rather rare event. On the long term, buffer
	overflow in the multicast pool may occur a few times a day (less
	than a few tens under heavy multicast usage). This object is not implemented."
::= {qosStatsTotalEntry 5}
qosStatsTotalObcInjectedBufOvflw OBJECT-TYPE
	SYNTAX	Counter
	ACCESS read-only
	STATUS mandatory
	DESCRIPTION
	 "Total OBC-injected buffer overflow event on EBLT LIMs
	There is a reserved buffer pool for OBC-injected traffic which
	Under very heavy load conditions may eventually get full, and the
	LIM OBC will be unable to communicate with the external world for
	a very short time interval. This object is not implemented."
::= {qosStatsTotalEntry 6}
qosStatsTotalElapseTime 	OBJECT-TYPE
	SYNTAX	INTEGER
	ACCESS read-only
	STATUS mandatory
	DESCRIPTION
	 "The elapsed time interval since the last measurement epoch
	started."
::= {qosStatsTotalEntry 7}
qosStatsTotalMeasuredTime 	OBJECT-TYPE
	SYNTAX	INTEGER
	ACCESS read-only
	STATUS mandatory
	DESCRIPTION
	 "The measured time interval since the last measurement epoch
	started."
::= {qosStatsTotalEntry 8}
qosStatsValid15mIntervals OBJECT-TYPE
	SYNTAX INTEGER (0..96)
	ACCESS read-only
	STATUS mandatory
	DESCRIPTION
	"This object stores the number of statistics of 15 minutes
	collected so far. At most 96 such entries are stored."
::= { qosStatsTotalEntry 9}
qosStatsValid1dIntervals OBJECT-TYPE
	SYNTAX INTEGER (0..1)
	ACCESS read-only
	STATUS mandatory
	DESCRIPTION
	" This object stores the number of statistics of one day
	collected so far. At most one entry is stored from the past."
::= { qosStatsTotalEntry 10}
qosTotalPolicersInUse OBJECT-TYPE
	SYNTAX INTEGER
	ACCESS read-only
	STATUS mandatory
	DESCRIPTION
	 "This object shows the total number of policers in use per LIM.
The interface level policers are managed in hardware in pairs, so even if a
Session is using both up and downstream policers, it is counted as two policer.
But sub-flow is for single direction so a sub-flow policer is counted as one
actual policer.


		"
::= {qosStatsTotalEntry 11}
qosPolicersInUseVlan OBJECT-TYPE
	SYNTAX INTEGER
	ACCESS read-only
	STATUS mandatory
	DESCRIPTION
	 "This object shows the number of policers in use by static
	sessions (PVC, PVC.VLAN) per L3 LIM.
		"
::= {qosStatsTotalEntry 12}
qosPolicersInUseDot1X OBJECT-TYPE
	SYNTAX INTEGER
	ACCESS read-only
	STATUS mandatory
	DESCRIPTION
	 "This object shows the number of policers in use by Dot1X
	sessions per L3 LIM.
		"
::= {qosStatsTotalEntry 13}
qosPolicersInUsePPP OBJECT-TYPE
	SYNTAX INTEGER
	ACCESS read-only
	STATUS mandatory
	DESCRIPTION
	 "This object shows the number of policers in use by PPP
	sessions per L3 LIM."
::= {qosStatsTotalEntry 14}

qosPolicersInUseIp OBJECT-TYPE
	SYNTAX INTEGER
	ACCESS read-only
	STATUS mandatory
	DESCRIPTION
	"This object shows the number of policers in use by Ip
	sessions/interfaces per L3 LIM."
::= {qosStatsTotalEntry 15}

-- =======================================================================
qosPolicersInUseSubFlow OBJECT-TYPE
	SYNTAX INTEGER
	ACCESS read-only
	STATUS mandatory
	DESCRIPTION
	    "This object shows the number of policers in use by sub-flow
 per L3 LIM."
::= {qosStatsTotalEntry 16}

-- =======================================================================

qosStatsTotalFanOutPassBytes 	OBJECT-TYPE 
	SYNTAX	Counter64bit
	ACCESS read-only
	STATUS mandatory
	DESCRIPTION
"This object is used to count the number of LIM physical bus fan out passed bytes per LIM module at subscriber side since the statistics were last reset. Here the physical bus can refer to Utopia II, POS-II or even GE port of Ethernet LT. In fact it is the sum of passed bytes of all queues at subscriber side."
::= {qosStatsTotalEntry 17}

qosStatsTotalFanOutPassFrames 	OBJECT-TYPE 
	SYNTAX	Counter64bit
	ACCESS read-only
	STATUS mandatory
	DESCRIPTION
"This object is used to count the number of LIM physical bus fan out passed frames per LIM module at subscriber side since the statistics were last reset. Here the physical bus can refer to Utopia II, POS-II or even GE port of Ethernet LT. In fact it is the sum of passed frames of all queues at subscriber side."
::= {qosStatsTotalEntry 18}

qosStatsTotalPartialAggrBufOvflw 	OBJECT-TYPE 
	SYNTAX	Counter64bit
	ACCESS read-only
	STATUS mandatory
	DESCRIPTION
	    "This object is used to count the number of buffer overflows
		 on a LIM module for the dropped lower traffic class packets due to global buffer occupancy threshold overflow since the statistic was last reset. Currently the lower traffic class means BE+CL traffic. When global available buffer used up, the dropped BE+CL packets will be counted in other aggregation buffer overflow counters together with other traffic classes. "
::= {qosStatsTotalEntry 19}


--qosGlobalSettings
qosGlobalSettings OBJECT IDENTIFIER ::= { qosStatisticsAndData 6 }
qosGlobalCacSettings OBJECT IDENTIFIER ::= { qosGlobalSettings 1 }
qosAtmOverheadFactor OBJECT-TYPE
	SYNTAX INTEGER (1..100)
	ACCESS read-write
	STATUS mandatory
	DESCRIPTION
	 "QoS ATM Overhead Factor
	This object stores an appropriate value to estimate the bandwidth
	Overhead introduced by the ATM layer. It takes values between 1
	100, which is then normalized to (0.01, 1)
	Eth_BW = ATM_BW * qosAtmOverheadFactor/100
	The default value is 85 (leaving 15% overhead for ATM/AAL5/LLC 
	Encapsulation. As the precise overhead depends also on the Ethernet 
	frame size,
	this object can be used to tune the overhead factor is the
	factory default is considered too optimistic or too conservative."
::= {qosGlobalCacSettings 1 }

qosEthEfmOverheadFactor OBJECT-TYPE
	SYNTAX INTEGER (1..100)
	ACCESS read-write
	STATUS mandatory
	DESCRIPTION
	    "QoS Eth Efm Overhead Factor
		 This object stores an appropriate value to estimate the bandwidth
		 Overhead introduced by the Efm layer. It takes values between 1
		 100, which is then normalized to (0.01, 1)
				Eth_BW = EFM_BW * qosEthEfmOverheadFactor/100
		The default value is 97 (leaving 3% overhead for EFM
		Encapsulation. 
		As the precise overhead depends also on the Ethernet frame size,
		this object can be used to tune the overhead factor is the factory
		default is considered too optimistic or too conservative."
	DEFVAL		{97}
::= {qosGlobalCacSettings 2 }

qosCacModeSelection OBJECT-TYPE
	SYNTAX INTEGER (1..3)
	ACCESS read-write
	STATUS mandatory
	DESCRIPTION
	    "QoS CAC mode selection
This object stores an global CAC mode selection switch. It takes values between 1 to 3. 1 means no CAC in system. 2 means do CAC based on minimum synchronized rate. 3 means do CAC based on actual line rate."
	DEFVAL		{2}
::= {qosGlobalCacSettings 3}

-- ============================================================================
--
--
qosGlobalDslPolicerSettings OBJECT IDENTIFIER ::= { qosGlobalSettings 2 }
qosDslControlPktRate OBJECT-TYPE
	SYNTAX INTEGER (1..64)
	ACCESS read-write
	STATUS mandatory
	DESCRIPTION
	"This object can be used to police the user incoming packets on all
	pvc's ( for all protocols) of a dsl line. It takes values between
	1 and 64 pps."
       	DEFVAL {15} 
::= {qosGlobalDslPolicerSettings 1 }

qosDslControlPktBurst OBJECT-TYPE
	SYNTAX INTEGER (1..128)
	ACCESS read-write
	STATUS mandatory
	DESCRIPTION
	"This object can be used to police the user incoming packets on all
	pvc's ( for all protocols) of a dsl line. It takes values between
	1 and 128 packets."
       	DEFVAL {10}
::= {qosGlobalDslPolicerSettings 2 }

qosNniControlPktRate OBJECT-TYPE
	SYNTAX INTEGER (1..256)
	ACCESS read-write
	STATUS mandatory
	DESCRIPTION
	"This object can be used to police the user incoming packets on all
	NNI ports ( for all protocols) of Gpon. It takes values between
	1 and 256 pps."
       	DEFVAL {64} 
::= {qosGlobalDslPolicerSettings 3 }

qosNniControlPktBurst OBJECT-TYPE
	SYNTAX INTEGER (1..256)
	ACCESS read-write
	STATUS mandatory
	DESCRIPTION
	"This object can be used to police the user incoming packets on all
	NNI port's ( for all protocols) of Gpon. It takes values between
	1 and 256 packets."
       	DEFVAL {128}
::= {qosGlobalDslPolicerSettings 4 }

qosDslControlProtocolCtrl OBJECT-TYPE
	SYNTAX INTEGER {
		policearprip(1),
		nopolicearprip(2)
	}
	ACCESS read-write
	STATUS mandatory
	DESCRIPTION
        "This object indicates system level configuration for disabling the DSL
line level control packet policer for control protocol packets that remain in the 
data plane. Only ARP and RIP protocols are supported as part of this feature.
Note: This feature is only applicable to the user incoming control protocol packets
on all DSL lines, Ethernet UNI and not applicable for Ethernet NNI and HC UNI variant."
        DEFVAL {policearprip}
::= {qosGlobalDslPolicerSettings 5 }

-- ============================================================================
--
qosLineControlPktRateLimitTable OBJECT-TYPE
	SYNTAX  SEQUENCE OF QosLineControlPktRateLimitEntry
	ACCESS	not-accessible
	STATUS	mandatory
	DESCRIPTION
		"This object contains a table for creating and storing police rate and burst per protocl."
::= { qosGlobalSettings 3}

qosLineControlPktRateLimitEntry OBJECT-TYPE
	SYNTAX QosLineControlPktRateLimitEntry
	ACCESS not-accessible
	STATUS	mandatory
	DESCRIPTION
		"This table contains as rows qosLineControlPktRateLimitTable"
	INDEX {qosLineControlPktRateLimitId }
::= {qosLineControlPktRateLimitTable  1}


QosLineControlPktRateLimitEntry ::=
	SEQUENCE {	
		qosLineControlPktRateLimitId       INTEGER,	
		qosLineControlPktRateLimitRowStatus RowStatus,
		qosLineControlPktRateLimitRate     INTEGER,
		qosLineControlPktRateLimitBurst    INTEGER
	}

qosLineControlPktRateLimitId OBJECT-TYPE 
	SYNTAX INTEGER	{
		arp (1),
		igmp (2),
		dhcpv4 (3),
		dhcpv6 (4),
		icmpv6 (5),
		cfm (6),
		pppox (7)
	}
	ACCESS	not-accessible
	STATUS mandatory
	DESCRIPTION
		"This field is the protocol identification which is used to index the qosLineControlPktRateLimitTable."
::= {  qosLineControlPktRateLimitEntry 1 }

qosLineControlPktRateLimitRowStatus OBJECT-TYPE
	SYNTAX	RowStatus
	ACCESS	read-write
	STATUS  mandatory
	DESCRIPTION
		"This object is used to create a new row or modify or
		delete an existing row in this table. The usage is as per
		standard semantics of 'RowStatus' defined in SNMPv2-TC."
::= { qosLineControlPktRateLimitEntry 2}

qosLineControlPktRateLimitRate OBJECT-TYPE 	
	SYNTAX	INTEGER(1 .. 64)	
	ACCESS	read-write	
	STATUS mandatory	
	DESCRIPTION	    
		"This object can be used to police the user incoming packets of protocol 
                 specified by qosLineControlPktRateLimitId on all pvc's of a dsl line. 
                 It takes values between 1 and 64 pps. "
	DEFVAL {15} 
::= {  qosLineControlPktRateLimitEntry 3 }

qosLineControlPktRateLimitBurst OBJECT-TYPE
	SYNTAX 	INTEGER(1..128)	
	ACCESS	read-write	
	STATUS mandatory	
	DESCRIPTION	    
		"This object can be used to police the user incoming packets of protocol 
                 specified by qosLineControlPktRateLimitId on all pvc's of a dsl line. 
                 It takes values between 1 and 128 packets."
	DEFVAL {10}
::= {  qosLineControlPktRateLimitEntry 4 }

-- ===========================================================================

qosGlobalPbitSettings OBJECT IDENTIFIER ::= { qosGlobalSettings 4 }

qosPbitBasedSchedulingForSCVlanCCUpStr OBJECT-TYPE
	SYNTAX INTEGER {
        sVLANpbitbased  (1),
	   cVLANpbitbased  (2)     
        }
	ACCESS read-write
	STATUS mandatory
	DESCRIPTION
     		" This object indicates p-bit rules for S+C Vlan Cross Connect
		in the upstream direction. 
		sVLANpbitbased (1) : (legacy behaviour) 
		After ISAM determines the p-bit to be used on egress,
		based on configuration on bridge port or VLAN port level.
		Apply this calculated p-bit to the S-VLAN and C-VLAN, 
		both are modified and identical. Schedule the packet
		in line with the S-VLAN p-bit 
		cVLANpbitbased (2) : 
		After ISAM determines the p-bit to be used on egress,
		based on configuration on bridge port or VLAN port level
		Case of tagged user frames: apply this calculated p-bit to the
		S-VLAN part only (do not modify the C-VLAN). 
		Case of untagged user frames: apply this calculated p-bit to
		the S-VLAN and C-VLAN, both are identical. In any case, schedule
		the packet in line with the S-VLAN p-bit

        ALCATEL NOTE:
                 ACCESS:     NA       USAGE:      NA
                 PERSIST:    YES       INSRVMOD:   NO
                 RANGE:      NA      DEFVALUE:   1
                 UNITS:      NA       SPARSE:     NA
                                     DESCR:      NA"
::= {qosGlobalPbitSettings 1 }

qosPbitBasedSchedulingForSCVlanCCDwnStr OBJECT-TYPE
	SYNTAX INTEGER {
           sVLANpbitbased  (1),
	   cVLANpbitbased  (2)     
        }
	ACCESS read-write
	STATUS mandatory
	DESCRIPTION
		" This object indicates p-bit rules for S+C Vlan Cross Connect
		in the downstream direction. 
		sVLANpbitbased (1) : (legacy behaviour) 
		use the p-bit of the network S-VLAN as reference for dual tagged
		ingress traffic. Make use of the current algorithm to determine
		the p-bit of the egress packet.Apply this calculated p-bit to the
		user C-VLAN only (if present when frame is passed to user).
		Traffic class mapping and scheduling is based on the final
		calculated user C-VLAN p-bit.
		cVLANpbitbased (2) : 
		use the p-bit of the network C-VLAN as reference for dual tagged
		ingress traffic.Make use of the current algorithm to determine
		the p-bit of the egress packet.Apply this calculated p-bit to the
		user C-VLAN only (if present when frame is passed to user).
		Traffic class mapping and scheduling is based on the final
		calculated user C-VLAN p-bit.
 
        ALCATEL NOTE:
                 ACCESS:     NA       USAGE:      NA
                 PERSIST:    YES       INSRVMOD:   NO
                 RANGE:      NA      DEFVALUE:   1
                 UNITS:      NA       SPARSE:     NA
                                     DESCR:      NA"
::= {qosGlobalPbitSettings 2 }

qosPbitBasedSchedulingForSCiBridgeUpStr OBJECT-TYPE
	SYNTAX INTEGER {
           sVLANpbitbased  (1),
	   cVLANpbitbased  (2)     
        }
	ACCESS read-write
	STATUS mandatory
	DESCRIPTION
     		"This object indicates p-bit rules for S+C iBridge
		in the upstream direction. 
		sVLANpbitbased (1) : (legacy behaviour) 
		After ISAM determines the p-bit to be used on egress,
		based on configuration on bridge port or VLAN port level.
		Apply this calculated p-bit to the S-VLAN and C-VLAN,
		both are modified and identical. Schedule the packet
		in line with the S-VLAN p-bit 
		cVLANpbitbased (2) : 
		After ISAM determines the p-bit to be used on egress,
		based on configuration on bridge port or VLAN port level
		Case of tagged user frames: apply this calculated p-bit to the
		S-VLAN part only (do not modify the C-VLAN). 
		Case of untagged user frames: apply this calculated p-bit to
		the S-VLAN and C-VLAN, both are identical. In any case, schedule
		the packet in line with the S-VLAN p-bit
 
        ALCATEL NOTE:
                 ACCESS:     NA       USAGE:      NA
                 PERSIST:    YES       INSRVMOD:   NO
                 RANGE:      NA      DEFVALUE:   1
                 UNITS:      NA       SPARSE:     NA
                                     DESCR:      NA"
::= {qosGlobalPbitSettings 3 }

qosPbitBasedSchedulingForSCiBridgeDwnStr OBJECT-TYPE
	SYNTAX INTEGER {
           sVLANpbitbased  (1),
	   cVLANpbitbased  (2)     
        }
	ACCESS read-write
	STATUS mandatory
	DESCRIPTION
		"This object indicates p-bit rules for S+C Vlan iBridge
		in the downstream direction. 
		sVLANpbitbased (1) : 
		use the p-bit of the network S-VLAN as reference for dual tagged
		ingress traffic. Make use of the current algorithm to determine
		the p-bit of the egress packet.Apply this calculated p-bit to the
		user C-VLAN only (if present when frame is passed to user).
		Traffic class mapping and scheduling is based on the final
		calculated user C-VLAN p-bit.
		cVLANpbitbased (2) : (legacy behaviour)
		use the p-bit of the network C-VLAN as reference for dual tagged
		ingress traffic.Make use of the current algorithm to determine
		the p-bit of the egress packet.Apply this calculated p-bit to the
		user C-VLAN only (if present when frame is passed to user).
		Traffic class mapping and scheduling is based on the final
		calculated user C-VLAN p-bit.

        ALCATEL NOTE:
                 ACCESS:     NA       USAGE:      NA
                 PERSIST:    YES       INSRVMOD:   NO
                 RANGE:      NA      DEFVALUE:   2
                 UNITS:      NA       SPARSE:     NA
                                     DESCR:      NA"
::= {qosGlobalPbitSettings 4 }

qosUpstrProtocolDslCtrl OBJECT-TYPE      
               SYNTAX INTEGER {
                 disable  (1),
                 enable (2)     
        }
        ACCESS read-write
	STATUS mandatory
	DESCRIPTION
		"This object indicates p-bit marking for the control packets (ARP,DHCPv4/v6, PPPoE, ND,MLD)
		snooped to the OBC in the upstream direction . 
		disable (1) : (legacy behaviour)
		Retains the existing behaviour for the pbit marking of the 
		control packet snooped to OBC. i.e Control packets does not undergo 
		Qos Treatment. The resultant P-bit which is sent to the Network in 
		the control packet varies from protocol to protocol .
		enable (2) : 
		Control Packet to undergo Qos Treatment, control packet will undergo Qos Treatment
		involving only decision point which comes from either port default/vlan default, 
		QoS session profile marker, P-bit contract table or default p-bits. Decision based on
		tagging of  DSCP bits , the ACL/CCL stage and the DSCP to p-bit alignment  wont be 
		applied for control packets.

	ALCATEL NOTE:
	ACCESS:     NA       USAGE:      NA
	PERSIST:    YES       INSRVMOD:   YES
	RANGE:      NA      DEFVALUE:   1
	UNITS:      NA       SPARSE:     NA
	DESCR: This attribute is supported only on CATAN, IXP based DSL LTs and TI SEM (7367 SX) Platform only.
	It is not supported for HC-UNI, NNI port of NELT-B."
::= {qosGlobalPbitSettings 5 }
qosGlobalSwitchSettings OBJECT IDENTIFIER ::= {qosGlobalSettings 5 }
qosGlobalSwitchA OBJECT-TYPE
    SYNTAX INTEGER
    ACCESS read-write	
    STATUS mandatory	
    DESCRIPTION	    
        "This object is a bitmap to indicate the switch of some global functions,
        currently:
        bit 0 - useDEI, if the bit is set, enable DEI aware.
        bit 1 - setDEI, if the bit is set, enable DEI remark.
        ALCATEL NOTE:
         ACCESS:     NA       USAGE:      NA
         PERSIST:    YES      INSRVMOD:   NO
         RANGE:      0..3     DEFVALUE:   0
         UNITS:      NA       SPARSE:     NA
         DESCR:      NA"
::= {qosGlobalSwitchSettings 1 }


-- ===========================================================================

--qosLimQueueStatsP15mTable

qosLimQueueStatsP15mTable OBJECT-TYPE
	SYNTAX	SEQUENCE OF QosLimQueueStatsP15mEntry
	ACCESS  not-accessible
	STATUS	mandatory
	DESCRIPTION
	"This table contains the previous 15 minute QoS statistics on a 
	per EBLT LIM basis"
::= {qosStatisticsAndData 7 }

qosLimQueueStatsP15mEntry OBJECT-TYPE
    SYNTAX      QosLimQueueStatsP15mEntry
    ACCESS      not-accessible
    STATUS      mandatory
    DESCRIPTION "An entry in the qosLimQueueStatsP15mTable"
    INDEX      {qosLimQueueStatsP15mLineLinkIndex, qosLimQueueStatsP15mLineQueueIndex, qosLimQueueStatsP15mIntervalNumber }
    ::=  {qosLimQueueStatsP15mTable 1 }


QosLimQueueStatsP15mEntry ::= SEQUENCE
   {
      qosLimQueueStatsP15mLineLinkIndex               InterfaceIndex,
      qosLimQueueStatsP15mLineQueueIndex           INTEGER,
      qosLimQueueStatsP15mIntervalNumber           INTEGER,
      qosLimQueueStatsP15mLineQueueLoad               INTEGER,
      qosLimQueueStatsP15mPassBytes                Counter64bit,
      qosLimQueueStatsP15mPassFrames               Counter64bit,
      qosLimQueueStatsP15mDiscBytes                Counter64bit,
      qosLimQueueStatsP15mDiscFrames               Counter64bit,
      qosLimQueueStatsP15mMeasuredTime             INTEGER,
      qosLimQueueStatsP15mQueuePeakUsage           INTEGER,
      qosLimQueueStatsP15mInvalidDataFlag          INTEGER
   }


qosLimQueueStatsP15mLineLinkIndex 	OBJECT-TYPE 
	SYNTAX	InterfaceIndex
	ACCESS read-only
	STATUS mandatory
	DESCRIPTION
	    " This object is used to index the physical line such as DSL line on the LIM."
::= {qosLimQueueStatsP15mEntry 1 }


qosLimQueueStatsP15mLineQueueIndex 	OBJECT-TYPE 
	SYNTAX	INTEGER (0 .. 8)
	ACCESS read-only
	STATUS mandatory
	DESCRIPTION
	    " This object is used to index the queue within the 
		 scope of one physical link on the LIM. Index 8 means total physical line. Queue index 0 to 3 correspond to current queue 0 to queue 3. Currently queue index 4 to 7 are always null as only four queue per line supported."
::= {qosLimQueueStatsP15mEntry 2 }

qosLimQueueStatsP15mIntervalNumber 	OBJECT-TYPE 
	SYNTAX	INTEGER (1)
	ACCESS not-accessible
	STATUS mandatory
	DESCRIPTION
	"A number, which identifies the interval for which the 
    set of statistics is available. The interval identified by 1 is the 
    most recently completed 15 minute interval, and the interval identified 
    by N is the interval immediately preceding the one identified by N-1. currently only 1 interval supported."
::= {qosLimQueueStatsP15mEntry 3 }

qosLimQueueStatsP15mLineQueueLoad 	OBJECT-TYPE 
	SYNTAX	INTEGER
	ACCESS read-only
	STATUS mandatory
	DESCRIPTION
	    "This object is used to show the queue load percentage. It means the average load percentage in this 15 minutes. If queue index is 8, the load is for physical line. Its range is from 0 to 100. System should check its value in the range of 0 to 100. If calculation result is above 100, system should round it to 100."
::= {qosLimQueueStatsP15mEntry 4 }

qosLimQueueStatsP15mPassBytes 	OBJECT-TYPE 
	SYNTAX	Counter64bit
	ACCESS read-only
	STATUS mandatory
	DESCRIPTION
	    "Previous 15 minute passed bytes in this queue. If queue index is 8, it means the sum of each queue of this physical line."
::= {qosLimQueueStatsP15mEntry 5 }

qosLimQueueStatsP15mPassFrames 	OBJECT-TYPE 
	SYNTAX	Counter64bit
	ACCESS read-only
	STATUS mandatory
	DESCRIPTION
	    " Previous 15 minute passed frames in this queue. If queue index is 8, it means the sum of each queue of this physical line."
::= {qosLimQueueStatsP15mEntry 6 }

qosLimQueueStatsP15mDiscBytes OBJECT-TYPE 
	SYNTAX	Counter64bit
	ACCESS read-only
	STATUS mandatory
	DESCRIPTION
	    " Previous 15 minutes discarded bytes in this queue. If queue index is 8, it means the sum of each queue of this physical line."
::= {qosLimQueueStatsP15mEntry 7  }

qosLimQueueStatsP15mDiscFrames OBJECT-TYPE 
	SYNTAX	Counter64bit
	ACCESS read-only
	STATUS mandatory
	DESCRIPTION
	    " Previous 15 minutes discarded frames in this queue. If queue index is 8, it means the sum of each queue of this physical line."
::= {qosLimQueueStatsP15mEntry 8  }
 

qosLimQueueStatsP15mMeasuredTime 	OBJECT-TYPE 
	SYNTAX	INTEGER
	ACCESS read-only
	STATUS mandatory
	DESCRIPTION
	    "The amount of time, measured in seconds, that statistics 
		 for this entry have been counted."
::= {qosLimQueueStatsP15mEntry 9  }

qosLimQueueStatsP15mQueuePeakUsage	OBJECT-TYPE 
	SYNTAX	INTEGER
	ACCESS read-only
	STATUS mandatory
	DESCRIPTION
	    "This object is used to show the queue peak usage in percentage. It means the Highest of (Queuesize-AverageFreeQueueSpace)queue peak usage percentage in this 15 minutes duration. Its range is from 0 to 100. System should check its value in the range of 0 to 100.
Note: For line level it always display as default ‘0’."
::= {qosLimQueueStatsP15mEntry 10 }


qosLimQueueStatsP15mInvalidDataFlag	OBJECT-TYPE 
	SYNTAX	INTEGER (0..1)
	ACCESS read-only
	STATUS mandatory
	DESCRIPTION
	    " This object indicates the validity of the corresponding counter statistics data.
It is set to 1 when the data is incomplete or invalid and set to 0 when the data is complete and valid. 
The data is incomplete or invalid mean:
- the measured time deviates by more than 10 seconds from the nominal interval duration (900 seconds for a 15 minutes interval), or 
- the data is incomplete in the accumulation period."
::= { qosLimQueueStatsP15mEntry 11 }

--qosLimQueueStatsC15mTable

qosLimQueueStatsC15mTable OBJECT-TYPE
	SYNTAX	SEQUENCE OF QosLimQueueStatsC15mEntry
	ACCESS not-accessible
	STATUS	mandatory
	DESCRIPTION
	"This table contains the current 15 minute QoS statistics on a 
	per EBLT LIM basis"
::= {qosStatisticsAndData 8 }

qosLimQueueStatsC15mEntry OBJECT-TYPE
    SYNTAX      QosLimQueueStatsC15mEntry
    ACCESS      not-accessible
    STATUS      mandatory
    DESCRIPTION "An entry in the qosLimQueueStatsC15mTable"
    INDEX      { qosLimQueueStatsC15mLineLinkIndex, qosLimQueueStatsC15mLineQueueIndex}
    ::=  {qosLimQueueStatsC15mTable 1 }


QosLimQueueStatsC15mEntry ::= SEQUENCE
	{
		qosLimQueueStatsC15mLineLinkIndex		 			InterfaceIndex,
		qosLimQueueStatsC15mLineQueueIndex				INTEGER,
		qosLimQueueStatsC15mLineQueueLoad					INTEGER,
		qosLimQueueStatsC15mPassBytes						Counter64bit,
		qosLimQueueStatsC15mPassFrames					Counter64bit,
		qosLimQueueStatsC15mDiscBytes						Counter64bit,
		qosLimQueueStatsC15mDiscFrames					Counter64bit,
		qosLimQueueStatsC15mElapseTime					INTEGER,
		qosLimQueueStatsC15mMeasuredTime					INTEGER,
		qosLimQueueStatsC15mQueuePeakUsage           		INTEGER,
		qosLimQueueStatsC15mInvalidDataFlag          		INTEGER
	}

qosLimQueueStatsC15mLineLinkIndex 	OBJECT-TYPE 
	SYNTAX	InterfaceIndex
	ACCESS read-only
	STATUS mandatory
	DESCRIPTION
	    " This object is used to index the physical line such as DSL line on the LIM."
::= {qosLimQueueStatsC15mEntry 1 }


qosLimQueueStatsC15mLineQueueIndex 	OBJECT-TYPE 
	SYNTAX	INTEGER (0 .. 8)
	ACCESS read-only
	STATUS mandatory
	DESCRIPTION
	    " This object is used to index the queue within the 
		 scope of one physical link on the LIM. Index 8 means total physical line. Queue index 0 to 3 correspond to current queue 0 to queue 3. Currently queue index 4 to 7 are always null as only four queue per line supported."
::= {qosLimQueueStatsC15mEntry 2 }


qosLimQueueStatsC15mLineQueueLoad 	OBJECT-TYPE 
	SYNTAX	INTEGER
	ACCESS read-only
	STATUS mandatory
	DESCRIPTION
	    "This object is used to show the queue load percentage. It means the average load percentage in  measured time of this 15 minutes. If queue index is 8, the load is for physical line. Its range is from 0 to around 100. System should check its value in the range of 0 to 100. If calculation result is above 100, system should round it to 100."
::= {qosLimQueueStatsC15mEntry 3 }

qosLimQueueStatsC15mPassBytes 	OBJECT-TYPE 
	SYNTAX	Counter64bit
	ACCESS read-only
	STATUS mandatory
	DESCRIPTION
	    "Current 15 minute passed bytes in this queue. If queue index is 8, it means the sum of each queue of this physical line."
::= {qosLimQueueStatsC15mEntry 4 }

qosLimQueueStatsC15mPassFrames 	OBJECT-TYPE 
	SYNTAX	Counter64bit
	ACCESS read-only
	STATUS mandatory
	DESCRIPTION
	    " Current 15 minute passed frames in this queue. If queue index is 8, it means the sum of each queue of this physical line."
::= {qosLimQueueStatsC15mEntry 5 }

qosLimQueueStatsC15mDiscBytes OBJECT-TYPE 
	SYNTAX	Counter64bit
	ACCESS read-only
	STATUS mandatory
	DESCRIPTION
	    " Current 15 minutes discarded bytes in this queue. If queue index is 8, it means the sum of each queue of this physical line."
::= {qosLimQueueStatsC15mEntry 6  }

qosLimQueueStatsC15mDiscFrames OBJECT-TYPE 
	SYNTAX	Counter64bit
	ACCESS read-only
	STATUS mandatory
	DESCRIPTION
	    " Current 15 minutes discarded frames in this queue. If queue index is 8, it means the sum of each queue of this physical line."
::= {qosLimQueueStatsC15mEntry 7  }

qosLimQueueStatsC15mElapseTime 	OBJECT-TYPE 
	SYNTAX	INTEGER
	ACCESS read-only
	STATUS mandatory
	DESCRIPTION
	    "The elapsed time interval since the last measurement epoch started."
::= {qosLimQueueStatsC15mEntry 8  }


qosLimQueueStatsC15mMeasuredTime 	OBJECT-TYPE 
	SYNTAX	INTEGER
	ACCESS read-only
	STATUS mandatory
	DESCRIPTION
	    "The amount of time, measured in seconds, that statistics 
		 for this entry have been counted."
::= {qosLimQueueStatsC15mEntry 9  }

qosLimQueueStatsC15mQueuePeakUsage	OBJECT-TYPE 
	SYNTAX	INTEGER
	ACCESS read-only
	STATUS mandatory
	DESCRIPTION
	    "This object is used to show the queue peak usage in percentage. It means the Highest of (Queuesize-AverageFreeQueueSpace)queue peak usage percentage in this 15 minutes duration. Its range is from 0 to 100. System should check its value in the range of 0 to 100.
Note: For line level it always display as default ‘0’."
::= {qosLimQueueStatsC15mEntry 10 }

qosLimQueueStatsC15mInvalidDataFlag	OBJECT-TYPE 
	SYNTAX	INTEGER (0..1)
	ACCESS read-only
	STATUS mandatory
	DESCRIPTION
	    " This object indicates the validity of the corresponding counter statistics data.
It is set to 1 when the data is incomplete or invalid and set to 0 when the data is complete and valid. 
The data is incomplete or invalid mean:
- the measured time deviates by more than 10 seconds from the nominal interval duration (900 seconds for a 15 minutes interval), or 
- the data is incomplete in the accumulation period."
::= { qosLimQueueStatsC15mEntry 11 }


-- qosFanOutLoadStatsP15mTable
qosFanOutLoadStatsP15mTable OBJECT-TYPE
	SYNTAX	SEQUENCE OF QosFanOutLoadStatsP15mEntry
	ACCESS not-accessible
	STATUS	mandatory
	DESCRIPTION
	"This table contains the previous 15 minute QoS statistics on a 
	per EBLT LIM basis"
::= {qosStatisticsAndData 9 }

qosFanOutLoadStatsP15mEntry OBJECT-TYPE
    SYNTAX      QosFanOutLoadStatsP15mEntry
    ACCESS      not-accessible
    STATUS      mandatory
    DESCRIPTION "An entry in the qosFanOutLoadStatsP15mTable"
    INDEX      { eqptSlotId, qosFanOutLoadStatsP15mTrafficClass, qosFanOutLoadStatsP15mIntervalNumber }
    ::=  {qosFanOutLoadStatsP15mTable 1 }


QosFanOutLoadStatsP15mEntry ::= SEQUENCE
	{
		qosFanOutLoadStatsP15mTrafficClass	 			INTEGER,
		qosFanOutLoadStatsP15mIntervalNumber	 			INTEGER,
		qosFanOutLoadStatsP15mLoad						INTEGER,
		qosFanOutLoadStatsP15mPassBytes					Counter64bit,
		qosFanOutLoadStatsP15mPassFrames					Counter64bit,
		qosFanOutLoadStatsP15mMeasuredTime				INTEGER,
		qosFanOutLoadStatsP15mInvalidDataFlag				INTEGER
	}


qosFanOutLoadStatsP15mTrafficClass 	OBJECT-TYPE 
	SYNTAX	INTEGER (0 .. 8)
	ACCESS read-only
	STATUS mandatory
	DESCRIPTION
	    " This object is used to index the traffic class on the LIM. Index 8 means total traffic. Index 0 to 7 refer to the traffic class with different priority, the same sequence with queue index definition."
::= {qosFanOutLoadStatsP15mEntry 1 }

qosFanOutLoadStatsP15mIntervalNumber 	OBJECT-TYPE 
	SYNTAX	INTEGER (1..96)
	ACCESS not-accessible
	STATUS mandatory
	DESCRIPTION
	"A number between 1 and 96, which identifies the interval for which the set of statistics is available. The interval identified by 1 is the most recently completed 15 minute interval, and the interval identified by N is the interval immediately preceding the one identified by N-1."
::= {qosFanOutLoadStatsP15mEntry 2 }


qosFanOutLoadStatsP15mLoad 	OBJECT-TYPE 
	SYNTAX	INTEGER
	ACCESS read-only
	STATUS mandatory
	DESCRIPTION
	    "This object is used to show the traffic class load percentage. It calculates total throughput of internal bus of LIM by the passed bits in this 15 minutes, compared with internal bus capability of LIM. It means the average load percentage in this 15 minutes. If traffic class index is 8, the load is for total traffic of LIM. System should check its value in the range of 0 to 100. If calculation result is above 100, system should round it to 100."
::= {qosFanOutLoadStatsP15mEntry 3 }


qosFanOutLoadStatsP15mPassBytes 	OBJECT-TYPE 
	SYNTAX	Counter64bit
	ACCESS read-only
	STATUS mandatory
	DESCRIPTION
	    "Previous 15 minute passed bytes in this traffic class. If traffic class is 8, it means the sum of each traffic class of this LIM."
::= {qosFanOutLoadStatsP15mEntry 4 }

qosFanOutLoadStatsP15mPassFrames 	OBJECT-TYPE 
	SYNTAX	Counter64bit
	ACCESS read-only
	STATUS mandatory
	DESCRIPTION
	    " Previous 15 minute passed frames in this traffic class. If traffic class is 8, it means the sum of each traffic class of this LIM."
::= {qosFanOutLoadStatsP15mEntry 5 }


qosFanOutLoadStatsP15mMeasuredTime 	OBJECT-TYPE 
	SYNTAX	INTEGER
	ACCESS read-only
	STATUS mandatory
	DESCRIPTION
	    "The amount of time, measured in seconds, that statistics 
		 for this entry have been counted."
::= {qosFanOutLoadStatsP15mEntry 6  }

qosFanOutLoadStatsP15mInvalidDataFlag	OBJECT-TYPE 
	SYNTAX	INTEGER (0..1)
	ACCESS read-only
	STATUS mandatory
	DESCRIPTION
	    " This object indicates the validity of the corresponding counter statistics data.
It is set to 1 when the data is incomplete or invalid and set to 0 when the data is complete and valid. 
The data is incomplete or invalid mean:
- the measured time deviates by more than 10 seconds from the nominal interval duration (900 seconds for a 15 minutes interval), or 
- the data is incomplete in the accumulation period."
::= { qosFanOutLoadStatsP15mEntry 7 }

-- qosFanOutLoadStatsC15mTable
qosFanOutLoadStatsC15mTable OBJECT-TYPE
	SYNTAX	SEQUENCE OF QosFanOutLoadStatsC15mEntry
	ACCESS not-accessible
	STATUS	mandatory
	DESCRIPTION
	"This table contains the current 15 minute QoS statistics on a 
	per EBLT LIM basis"
::= {qosStatisticsAndData 10 }

qosFanOutLoadStatsC15mEntry OBJECT-TYPE
    SYNTAX      QosFanOutLoadStatsC15mEntry
    ACCESS      not-accessible
    STATUS      mandatory
    DESCRIPTION "An entry in the qosFanOutLoadStatsC15mTable"
    INDEX      { eqptSlotId, qosFanOutLoadStatsC15mTrafficClass}
    ::=  {qosFanOutLoadStatsC15mTable 1 }


QosFanOutLoadStatsC15mEntry ::= SEQUENCE
	{
		qosFanOutLoadStatsC15mTrafficClass	 			INTEGER,
		qosFanOutLoadStatsC15mLoad						INTEGER,
		qosFanOutLoadStatsC15mPassBytes					Counter64bit,
		qosFanOutLoadStatsC15mPassFrames					Counter64bit,
		qosFanOutLoadStatsC15mElapseTime					INTEGER,
		qosFanOutLoadStatsC15mMeasuredTime				INTEGER,
		qosFanOutLoadStatsC15mInvalidDataFlag				INTEGER
	}



qosFanOutLoadStatsC15mTrafficClass 	OBJECT-TYPE 
	SYNTAX	INTEGER (0 .. 8)
	ACCESS read-only
	STATUS mandatory
	DESCRIPTION
	    " This object is used to index the traffic class on the LIM. Index 8 means total traffic. Index 0 to 7 refer to the traffic class with different priority, the same sequence with queue index definition."
::= {qosFanOutLoadStatsC15mEntry 1 }

qosFanOutLoadStatsC15mLoad 	OBJECT-TYPE 
	SYNTAX	INTEGER
	ACCESS read-only
	STATUS mandatory
	DESCRIPTION
	    "This object is used to show the traffic class load percentage. It calculates total throughput of internal bus of LIM by the passed bits in this 15 minutes, compared with internal bus capability of LIM. It means the average load percentage in the measured time. If traffic class index is 8, the load is for total traffic of LIM. System should check its value in the range of 0 to 100. If calculation result is above 100, system should round it to 100."
::= {qosFanOutLoadStatsC15mEntry 2 }


qosFanOutLoadStatsC15mPassBytes 	OBJECT-TYPE 
	SYNTAX	Counter64bit
	ACCESS read-only
	STATUS mandatory
	DESCRIPTION
	    "Current 15 minute passed bytes in this traffic class. If traffic class is 8, it means the sum of each traffic class of this LIM."
::= {qosFanOutLoadStatsC15mEntry 3 }

qosFanOutLoadStatsC15mPassFrames 	OBJECT-TYPE 
	SYNTAX	Counter64bit
	ACCESS read-only
	STATUS mandatory
	DESCRIPTION
	    " Current 15 minute passed frames in this traffic class. If traffic class is 8, it means the sum of each traffic class of this LIM."
::= {qosFanOutLoadStatsC15mEntry 4 }

qosFanOutLoadStatsC15mElapseTime 	OBJECT-TYPE 
	SYNTAX	INTEGER
	ACCESS read-only
	STATUS mandatory
	DESCRIPTION
	    "The elapsed time interval since the last measurement epoch started."
::= {qosFanOutLoadStatsC15mEntry 5  }


qosFanOutLoadStatsC15mMeasuredTime 	OBJECT-TYPE 
	SYNTAX	INTEGER
	ACCESS read-only
	STATUS mandatory
	DESCRIPTION
	    "The amount of time, measured in seconds, that statistics 
		 for this entry have been counted."
::= {qosFanOutLoadStatsC15mEntry 6  }

qosFanOutLoadStatsC15mInvalidDataFlag	OBJECT-TYPE 
	SYNTAX	INTEGER (0..1)
	ACCESS read-only
	STATUS mandatory
	DESCRIPTION
	    " This object indicates the validity of the corresponding counter statistics data.
It is set to 1 when the data is incomplete or invalid and set to 0 when the data is complete and valid. 
The data is incomplete or invalid mean:
- the measured time deviates by more than 10 seconds from the nominal interval duration (900 seconds for a 15 minutes interval), or 
- the data is incomplete in the accumulation period."
::= { qosFanOutLoadStatsC15mEntry 7 }

-- qosFanOutLoadStatsP1dTable
qosFanOutLoadStatsP1dTable OBJECT-TYPE
	SYNTAX	SEQUENCE OF QosFanOutLoadStatsP1dEntry
	ACCESS not-accessible
	STATUS	mandatory
	DESCRIPTION
	"This table contains the previous 1 day QoS statistics on a 
	per EBLT LIM basis"
::= {qosStatisticsAndData 11 }

qosFanOutLoadStatsP1dEntry OBJECT-TYPE
    SYNTAX      QosFanOutLoadStatsP1dEntry
    ACCESS      not-accessible
    STATUS      mandatory
    DESCRIPTION "An entry in the qosFanOutLoadStatsP1dTable"
    INDEX      { eqptSlotId, qosFanOutLoadStatsP1dIntervalNumber }
    ::=  {qosFanOutLoadStatsP1dTable 1 }


QosFanOutLoadStatsP1dEntry ::= SEQUENCE
	{
		qosFanOutLoadStatsP1dIntervalNumber	 			INTEGER,
		qosFanOutLoadStatsP1dPassBytes					Counter64bit,
		qosFanOutLoadStatsP1dPassFrames					Counter64bit,
		qosFanOutLoadStatsP1dMeasuredTime					INTEGER,
		qosFanOutLoadStatsP1dInvalidDataFlag				INTEGER
	}

qosFanOutLoadStatsP1dIntervalNumber 	OBJECT-TYPE 
	SYNTAX	INTEGER (1)
	ACCESS not-accessible
	STATUS mandatory
	DESCRIPTION
	"A number, which identifies the interval for which the set of statistics is available. The interval identified by 1 is the most recently completed 1 day interval, and the interval identified by N is the interval immediately preceding the one identified by N-1. Currently we support only 1 entry."
::= {qosFanOutLoadStatsP1dEntry 1 }

qosFanOutLoadStatsP1dPassBytes 	OBJECT-TYPE 
	SYNTAX	Counter64bit
	ACCESS read-only
	STATUS mandatory
	DESCRIPTION
	    "Previous 1 day passed bytes in this traffic class. "
::= {qosFanOutLoadStatsP1dEntry 2 }

qosFanOutLoadStatsP1dPassFrames 	OBJECT-TYPE 
	SYNTAX	Counter64bit
	ACCESS read-only
	STATUS mandatory
	DESCRIPTION
	    " Previous 1 day passed frames in this traffic class. "
::= {qosFanOutLoadStatsP1dEntry 3 }


qosFanOutLoadStatsP1dMeasuredTime 	OBJECT-TYPE 
	SYNTAX	INTEGER
	ACCESS read-only
	STATUS mandatory
	DESCRIPTION
	    "The amount of time, measured in seconds, that statistics 
		 for this entry have been counted."
::= {qosFanOutLoadStatsP1dEntry 4  }

qosFanOutLoadStatsP1dInvalidDataFlag	OBJECT-TYPE 
	SYNTAX	INTEGER (0..1)
	ACCESS read-only
	STATUS mandatory
	DESCRIPTION
	    " This object indicates the validity of the corresponding counter statistics data.
It is set to 1 when the data is incomplete or invalid and set to 0 when the data is complete and valid. 
The data is incomplete or invalid mean:
- the measured time deviates by more than 10 seconds from the nominal interval duration (86400 seconds for a 24 hour interval), or 
- the data is incomplete in the accumulation period."
::= { qosFanOutLoadStatsP1dEntry 5 }

-- qosFanOutLoadStatsC1dTable
qosFanOutLoadStatsC1dTable OBJECT-TYPE
	SYNTAX	SEQUENCE OF QosFanOutLoadStatsC1dEntry
	ACCESS not-accessible
	STATUS	mandatory
	DESCRIPTION
	"This table contains the current 1 day QoS statistics on a 
	per EBLT LIM basis"
::= {qosStatisticsAndData 12 }

qosFanOutLoadStatsC1dEntry OBJECT-TYPE
    SYNTAX      QosFanOutLoadStatsC1dEntry
    ACCESS      not-accessible
    STATUS      mandatory
    DESCRIPTION "An entry in the qosFanOutLoadStatsC1dTable"
    INDEX      { eqptSlotId }
    ::=  {qosFanOutLoadStatsC1dTable 1 }


QosFanOutLoadStatsC1dEntry ::= SEQUENCE
	{
		qosFanOutLoadStatsC1dPassBytes					Counter64bit,
		qosFanOutLoadStatsC1dPassFrames					Counter64bit,
		qosFanOutLoadStatsC1dElapseTime					INTEGER,
		qosFanOutLoadStatsC1dMeasuredTime					INTEGER,
		qosFanOutLoadStatsC1dInvalidDataFlag				INTEGER
	}

qosFanOutLoadStatsC1dPassBytes 	OBJECT-TYPE 
	SYNTAX	Counter64bit
	ACCESS read-only
	STATUS mandatory
	DESCRIPTION
	    "Current 1 day passed bytes in this traffic class. "
::= {qosFanOutLoadStatsC1dEntry 1 }

qosFanOutLoadStatsC1dPassFrames 	OBJECT-TYPE 
	SYNTAX	Counter64bit
	ACCESS read-only
	STATUS mandatory
	DESCRIPTION
	    " Current 1 day passed frames in this traffic class. "
::= {qosFanOutLoadStatsC1dEntry 2 }


qosFanOutLoadStatsC1dElapseTime 	OBJECT-TYPE 
	SYNTAX	INTEGER
	ACCESS read-only
	STATUS mandatory
	DESCRIPTION
	    "The elapsed time interval since the last measurement epoch started."
::= {qosFanOutLoadStatsC1dEntry 3  }


qosFanOutLoadStatsC1dMeasuredTime 	OBJECT-TYPE 
	SYNTAX	INTEGER
	ACCESS read-only
	STATUS mandatory
	DESCRIPTION
	    "The amount of time, measured in seconds, that statistics 
		 for this entry have been counted."
::= {qosFanOutLoadStatsC1dEntry 5  }

qosFanOutLoadStatsC1dInvalidDataFlag	OBJECT-TYPE 
	SYNTAX	INTEGER (0..1)
	ACCESS read-only
	STATUS mandatory
	DESCRIPTION
	    " This object indicates the validity of the corresponding counter statistics data.
It is set to 1 when the data is incomplete or invalid and set to 0 when the data is complete and valid. 
The data is incomplete or invalid mean:
- the measured time deviates by more than 10 seconds from the nominal interval duration (86400 seconds for a 24 hour interval), or 
- the data is incomplete in the accumulation period."
::= { qosFanOutLoadStatsC1dEntry 6 }

-- qosStatsSettingTable
qosStatsSettingTable OBJECT-TYPE
	SYNTAX	SEQUENCE OF QosStatsSettingEntry
	ACCESS not-accessible
	STATUS	mandatory
	DESCRIPTION
	"This table contains the configurable parameters of QoS queue statistics function."
::= {qosStatisticsAndData 13 }

qosStatsSettingEntry OBJECT-TYPE
    SYNTAX      QosStatsSettingEntry
    ACCESS      not-accessible
    STATUS      mandatory
    DESCRIPTION "An entry in the qosStatsSettingTable"
    INDEX      { eqptSlotId }
    ::=  {qosStatsSettingTable 1 }


QosStatsSettingEntry ::= SEQUENCE
	{
		qosLimBufferOccupancyThreshold		 				INTEGER,
		qosStatsSettingQueueStatsEnable						INTEGER,
		qosStatsSettingFanOutLoadTcaEnable					INTEGER,
		qosStatsSettingFanOutLoadTcaThreshold				INTEGER,
		qosStatsSettingAggrBufOvflwTcaEnable					INTEGER,
		qosStatsSettingUpAggrBufOvflwTcaThreshold			INTEGER,
		qosStatsSettingUpObcAggrBufOvflwTcaThreshold			INTEGER,
		qosStatsSettingDnObcAggrBufOvflwTcaThreshold			INTEGER,
		qosStatsSettingDnUcAggrBufOvflwTcaThreshold			INTEGER,
		qosStatsSettingPartialAggrBufOvflwTcaThreshold		Counter64bit
	}

qosLimBufferOccupancyThreshold 	OBJECT-TYPE 
	SYNTAX	INTEGER ( 0 .. 100 )
	ACCESS read-write
	STATUS mandatory
	DESCRIPTION
	"The threshold is defined as percentage. Means the ratio of occupied data buffer entries to the LIM global data buffer size. The incoming packets to BE and CL queues will be dropped when this threshold arrives while the incoming packets to voice and video queues can be queued. Default 0 means system don't judge the threshold cross over. the range of this object is from 0 to 100. System shold convert the percentage to the number of occupied data buffer entries according to system global data buffer size. "
		DEFVAL { 0 }
::= {qosStatsSettingEntry 1 }


qosStatsSettingQueueStatsEnable 	OBJECT-TYPE 
	SYNTAX	INTEGER 
			{
				enabled (1),
				disabled (2)
			}
	ACCESS read-write
	STATUS mandatory
	DESCRIPTION
	"setting the object to enable or disable queue statistics of the LIM. It only means the increment of HW queues counters is enabled or disabled. The upper layer interfaces of queue statistics are still open to operator. For example, operator still can access the P15m queue drop counter of a specific queue even if this object is disabled.  "
		DEFVAL { disabled }
::= {qosStatsSettingEntry 2 }


qosStatsSettingFanOutLoadTcaEnable 	OBJECT-TYPE 
	SYNTAX	INTEGER 
			{
				enabled (1),
				disabled (2)
			}
	ACCESS read-write
	STATUS mandatory
	DESCRIPTION
	"setting the object to enable or disable the threshold crossover alarm of fan-out load of the LIM. Only if this object is enabled, system will send TCA when fan-out load is supper than nonzero fan-out load threshold."
		DEFVAL { disabled }
::= {qosStatsSettingEntry 3 }

qosStatsSettingFanOutLoadTcaThreshold 	OBJECT-TYPE 
	SYNTAX	INTEGER ( 0 .. 100 )
	ACCESS read-write
	STATUS mandatory
	DESCRIPTION
	"The threshold of LT fan out load, defined as percentage, means the ratio of  the 15 minutes PM counter of LIM fan out passed bytes to the LIM internal net bus capability. Fan out load means the LIM internal bus fan out throughput in downstream direction. The calculation is the sum of all PM counters of queue passed bytes of the LIM, divided by LIM net bus capability and time interval. Default 0 means system don't judge the threshold cross over. The value range of this object is 0 to 100."
		DEFVAL { 0 }
::= {qosStatsSettingEntry 4 }


qosStatsSettingAggrBufOvflwTcaEnable 	OBJECT-TYPE 
	SYNTAX	INTEGER 
			{
				enabled (1),
				disabled (2)
			}
	ACCESS read-write
	STATUS mandatory
	DESCRIPTION
	"setting the object to enable or disable the threshold crossover alarm of aggregation buffer overflow in the LIM. Only if this object is enabled, system will send TCA when each type of aggregation buffer overflow is supper than their nonzero threshold."
		DEFVAL { disabled }
::= {qosStatsSettingEntry 5 }


qosStatsSettingUpAggrBufOvflwTcaThreshold 	OBJECT-TYPE 
	SYNTAX	INTEGER 
	ACCESS read-write
	STATUS mandatory
	DESCRIPTION
	"The threshold of upstream aggregation buffer overflow TCA. The unit is frame. This referred PM counter UpAggrBufOvflw is incremented when any of the 4 upstream aggregate buffers overflow, or when there is no free packet handler for a reassembly area. Also incremented when the free list is up for upstream packets (if possible) on an LIM module on a 15 minute interval basis. Default 0 means system don't judge the threshold cross over."
		DEFVAL { 0 }
::= {qosStatsSettingEntry 6 }


qosStatsSettingUpObcAggrBufOvflwTcaThreshold 	OBJECT-TYPE 
	SYNTAX	INTEGER 
	ACCESS read-write
	STATUS mandatory
	DESCRIPTION
	" The threshold of OBC-directed upstream aggregation buffer overflow TCA. The unit is frame. This referred PM counter UpObcAggrBufOvflw is incremented when any of the OBC directed queues for upstream packets overflow on an LIM module on a 15 minute interval basis. These are packet counters; byte counters not needed. Default 0 means system don't judge the threshold cross over."
		DEFVAL { 0 }
::= {qosStatsSettingEntry 7 }


qosStatsSettingDnObcAggrBufOvflwTcaThreshold 	OBJECT-TYPE 
	SYNTAX	INTEGER 
	ACCESS read-write
	STATUS mandatory
	DESCRIPTION
	" The threshold of downstream OBC-directed aggregation buffer overflow TCA. The unit is frame. This referred PM counter DnObcAggrBufOvflw is incremented when any of the OBC directed queues for downstream packets overflow on an LIM module on a 15 minute interval basis. These are packet counters; byte counters not needed. Default 0 means system don't judge the threshold cross over."
		DEFVAL { 0 }
::= {qosStatsSettingEntry 8 }


qosStatsSettingDnUcAggrBufOvflwTcaThreshold 	OBJECT-TYPE 
	SYNTAX	INTEGER 
	ACCESS read-write
	STATUS mandatory
	DESCRIPTION
	"The threshold of downstream data aggregation buffer overflow TCA. The unit is frame. This referred PM counter  DnUcAggrBufOvflw is incremented when the total free list is up for a downstream packets on an LIM module on a 15 minute interval basis. Default 0 means system don't judge the threshold cross over."
		DEFVAL { 0 }
::= {qosStatsSettingEntry 9 }

qosStatsSettingPartialAggrBufOvflwTcaThreshold 	OBJECT-TYPE 
	SYNTAX	Counter64bit 
	ACCESS read-write
	STATUS mandatory
	DESCRIPTION
	"The threshold of dropped lower class packets of global buffer occupancy threshold overflow TCA. The unit is frame. This referred PM counter  PartialAggrBufOvflw is incremented when the used buffer number is above global buffer occupancy threshold and the packet is belongs to lower classes traffic on an LIM module on a 15 minute interval basis. Default 0 means system don't judge the threshold cross over. Currently lower traffic class means BE+CL  traffic."
::= {qosStatsSettingEntry 10 }


-- qosQueueStatsTcaTable
qosQueueStatsTcaTable OBJECT-TYPE
	SYNTAX	SEQUENCE OF QosQueueStatsTcaEntry
	ACCESS not-accessible
	STATUS	mandatory
	DESCRIPTION
	"This table contains per queue the configurable TCA parameters of QoS queue statistics function."
::= {qosStatisticsAndData 14 }

qosQueueStatsTcaEntry OBJECT-TYPE
    SYNTAX      QosQueueStatsTcaEntry
    ACCESS      not-accessible
    STATUS      mandatory
    DESCRIPTION "An entry in the qosQueueStatsTcaTable"
    INDEX      { qosQueueStatsTcaLineLinkIndex, qosQueueStatsTcaLineQueueIndex }
    ::=  {qosQueueStatsTcaTable 1 }


QosQueueStatsTcaEntry ::= SEQUENCE
	{
		qosQueueStatsTcaLineLinkIndex			 				InterfaceIndex,
		qosQueueStatsTcaLineQueueIndex						INTEGER,
		qosQueueStatsTcaEnable									INTEGER,
		qosQueueStatsQueueLoadTcaThreshold					INTEGER,
		qosQueueStatsDiscFramesTcaThreshold					INTEGER,
		qosQueueStatsQueuePeakUsageThreshold					INTEGER
	}

qosQueueStatsTcaLineLinkIndex 	OBJECT-TYPE 
	SYNTAX	InterfaceIndex 
	ACCESS not-accessible
	STATUS mandatory
	DESCRIPTION
	" This object is used to index the physical lines of this LIM. "
::= {qosQueueStatsTcaEntry 1 }


qosQueueStatsTcaLineQueueIndex 	OBJECT-TYPE 
	SYNTAX	INTEGER ( 0..7 )
	ACCESS not-accessible
	STATUS mandatory
	DESCRIPTION
	" This object is used to index the queue within the scope of one physical link on the LIM. Currently Index 0 to 3 correspond to physical queue 0 to 3, and index 4 to 7 is meaningless since only four queues per line supported"
::= {qosQueueStatsTcaEntry 2 }


qosQueueStatsTcaEnable 	OBJECT-TYPE 
	SYNTAX	INTEGER 
			{
				enabled (1),
				disabled (2)
			}
	ACCESS read-write
	STATUS mandatory
	DESCRIPTION
	"setting the object to enable or disable each queue statistic TCA of this queue. It contains the TCA of passed/discarded bytes/frames of this queue. Only if this object is enabled, system will send related TCA when some of queue counter of this queue are supper than their nonzero threshold."
		DEFVAL { disabled }
::= {qosQueueStatsTcaEntry 3 }


qosQueueStatsQueueLoadTcaThreshold 	OBJECT-TYPE 
	SYNTAX	INTEGER ( 0 .. 100 )
	ACCESS read-write
	STATUS mandatory
	DESCRIPTION
	" The threshold of queue traffic load, defined as percentage. Means the ratio of the statistical traffic rate of this queue to the actual line rate. The referred PM counter is LimQueueStatsPassBytes. Default 0 means system don't judge the threshold cross over. The value range of this object is from 0 to 100. "
		DEFVAL { 0 }
::= {qosQueueStatsTcaEntry 4 }


qosQueueStatsDiscFramesTcaThreshold 	OBJECT-TYPE 
	SYNTAX	INTEGER 
	ACCESS read-write
	STATUS mandatory
	DESCRIPTION
	" The threshold of discarded frames of this queue. The referred PM counter is LimQueueStatsDiscFrames. Default 0 means system don't judge the threshold cross over. "
		DEFVAL { 0 }
::= {qosQueueStatsTcaEntry 5 }

qosQueueStatsQueuePeakUsageThreshold 	OBJECT-TYPE 
	SYNTAX	INTEGER ( 0 .. 100 )
	ACCESS read-write
	STATUS mandatory
	DESCRIPTION
	" The threshold of queue peak usage, defined as percentage. Queue peak usage means the Highest(Queue Size – AverageFreeQeueSize)in a given duration. Default 0 means system don't judge the threshold cross over. The value range of this object is from 0 to 100. "
		DEFVAL { 0 }
::= {qosQueueStatsTcaEntry 6 }


-- qosLimQueueStatsPerfInfoTable

qosLimQueueStatsPerfInfoTable OBJECT-TYPE
	SYNTAX	SEQUENCE OF QosLimQueueStatsPerfInfoEntry
	ACCESS not-accessible
	STATUS	mandatory
	DESCRIPTION
	"Table of number of previous statistics intervals for the traffic on a LIM queue or line."
::= {qosStatisticsAndData 15 }

qosLimQueueStatsPerfInfoEntry OBJECT-TYPE
    SYNTAX      QosLimQueueStatsPerfInfoEntry
    ACCESS      not-accessible
    STATUS      mandatory
    DESCRIPTION "An entry in the qosLimQueueStatsPerfInfoTable"
    INDEX      { qosLimQueueStatsPerfInfoLineLinkIndex, qosLimQueueStatsPerfInfoLineQueueIndex }
    ::=  {qosLimQueueStatsPerfInfoTable 1 }


QosLimQueueStatsPerfInfoEntry ::= SEQUENCE
	{
		qosLimQueueStatsPerfInfoLineLinkIndex				InterfaceIndex,
		qosLimQueueStatsPerfInfoLineQueueIndex				INTEGER,
		qosLimQueueStatsPerfInfo15MValidIntervals				INTEGER
	}

qosLimQueueStatsPerfInfoLineLinkIndex 	OBJECT-TYPE 
	SYNTAX	InterfaceIndex 
	ACCESS not-accessible
	STATUS mandatory
	DESCRIPTION
	" This object is used to index the physical lines of this LIM. "
::= {qosLimQueueStatsPerfInfoEntry 1 }


qosLimQueueStatsPerfInfoLineQueueIndex 	OBJECT-TYPE 
	SYNTAX	INTEGER ( 0..8 )
	ACCESS not-accessible
	STATUS mandatory
	DESCRIPTION
	" This object is used to index the queue within the scope of one physical link on the LIM. Index 8 means total line. Currently Index 0 to 3 correspond to physical queue 0 to 3, and index 4 to 7 is meaningless since only four queues per line supported"
::= {qosLimQueueStatsPerfInfoEntry 2 }


qosLimQueueStatsPerfInfo15MValidIntervals 	OBJECT-TYPE 
	SYNTAX	INTEGER (0..1)
	ACCESS read-only
	STATUS mandatory
	DESCRIPTION
	" Number of previous 15 minutes intervals."
::= {qosLimQueueStatsPerfInfoEntry 3 }


-- qosFanOutLoadStats15MPerfInfoTable
qosFanOutLoadStats15MPerfInfoTable OBJECT-TYPE
	SYNTAX	SEQUENCE OF QosFanOutLoadStats15MPerfInfoEntry
	ACCESS not-accessible
	STATUS	mandatory
	DESCRIPTION
	"Table of number of previous statistics intervals for the fan out traffic on a LIM."
::= {qosStatisticsAndData 16 }

qosFanOutLoadStats15MPerfInfoEntry OBJECT-TYPE
    SYNTAX      QosFanOutLoadStats15MPerfInfoEntry
    ACCESS      not-accessible
    STATUS      mandatory
    DESCRIPTION "An entry in the qosFanOutLoadStats15MPerfInfoTable"
    INDEX      { eqptSlotId, qosFanOutLoadStats15MPerfInfoTrafficClass } 
    ::=  {qosFanOutLoadStats15MPerfInfoTable 1 }


QosFanOutLoadStats15MPerfInfoEntry ::= SEQUENCE
	{
		qosFanOutLoadStats15MPerfInfoTrafficClass				INTEGER,
		qosFanOutLoadStats15MPerfInfo15MValidIntervals		INTEGER
	}


qosFanOutLoadStats15MPerfInfoTrafficClass 	OBJECT-TYPE 
	SYNTAX	INTEGER ( 0..8 )
	ACCESS not-accessible
	STATUS mandatory
	DESCRIPTION
	" This object is used to index the traffic class on the LIM. Index 8 means total traffic. Index 0 to 7 refer to the traffic class with different priority, the same sequence with queue index definition."
::= {qosFanOutLoadStats15MPerfInfoEntry 1 }


qosFanOutLoadStats15MPerfInfo15MValidIntervals 	OBJECT-TYPE 
	SYNTAX	INTEGER (0..96)
	ACCESS read-only
	STATUS mandatory
	DESCRIPTION
	" Number of previous 15 minutes intervals."
::= {qosFanOutLoadStats15MPerfInfoEntry 2 }


-- qosFanOutLoadStats1DPerfInfoTable
qosFanOutLoadStats1DPerfInfoTable OBJECT-TYPE
	SYNTAX	SEQUENCE OF QosFanOutLoadStats1DPerfInfoEntry
	ACCESS not-accessible
	STATUS	mandatory
	DESCRIPTION
	"Table of number of previous statistics intervals for the fan out traffic on a LIM."
::= {qosStatisticsAndData 17 }

qosFanOutLoadStats1DPerfInfoEntry OBJECT-TYPE
    SYNTAX      QosFanOutLoadStats1DPerfInfoEntry
    ACCESS      not-accessible
    STATUS      mandatory
    DESCRIPTION "An entry in the qosFanOutLoadStats1DPerfInfoTable"
    INDEX      { eqptSlotId } 
    ::=  {qosFanOutLoadStats1DPerfInfoTable 1 }


QosFanOutLoadStats1DPerfInfoEntry ::= SEQUENCE
	{
		qosFanOutLoadStats1DPerfInfo1DValidIntervals		INTEGER
	}


qosFanOutLoadStats1DPerfInfo1DValidIntervals 	OBJECT-TYPE 
	SYNTAX	INTEGER (0..1)
	ACCESS read-only
	STATUS mandatory
	DESCRIPTION
	" Number of previous 15 minutes intervals."
::= {qosFanOutLoadStats1DPerfInfoEntry 1 }



qosLimObcBackplaneQueueStatsC15mTable OBJECT-TYPE
	SYNTAX	SEQUENCE OF QosLimObcBackplaneQueueStatsC15mEntry
	ACCESS not-accessible
	STATUS	mandatory
	DESCRIPTION
	"This table contains the current QoS statistics on a 
	per GLT LIM basis of packets discarded towards OBC and backplane"
::= {qosStatisticsAndData 18 }

qosLimObcBackplaneQueueStatsC15mEntry OBJECT-TYPE
    SYNTAX      QosLimObcBackplaneQueueStatsC15mEntry
    ACCESS      not-accessible
    STATUS      mandatory
    DESCRIPTION "An entry in the qosLimObcBackplaneQueueStatsC15mTable"
    INDEX      { eqptSlotId }
    ::=  {qosLimObcBackplaneQueueStatsC15mTable 1 }


QosLimObcBackplaneQueueStatsC15mEntry ::= SEQUENCE
	{
		qosLimObcBackplaneQueueStatsC15mObcLowDiscPkts	 Counter,
		qosLimObcBackplaneQueueStatsC15mObcLowDiscBytes	 Counter,
		qosLimObcBackplaneQueueStatsC15mObcHighDiscPkts	 Counter,
		qosLimObcBackplaneQueueStatsC15mObcHighDiscBytes Counter,
		qosLimObcBackplaneQueueStatsC15mBplLowDiscPkts   Counter,
		qosLimObcBackplaneQueueStatsC15mBplLowDiscBytes  Counter,
		qosLimObcBackplaneQueueStatsC15mBplHighDiscPkts	 Counter,
		qosLimObcBackplaneQueueStatsC15mBplHighDiscBytes Counter,
                qosLimObcBackplaneQueueStatsC15mBplDownDiscPkts  Counter
	}


qosLimObcBackplaneQueueStatsC15mObcLowDiscPkts OBJECT-TYPE 
	SYNTAX	Counter
	ACCESS read-only
	STATUS mandatory
	DESCRIPTION
	    " Current discarded packet count towards OBC due to low water mark crossing."
::= { qosLimObcBackplaneQueueStatsC15mEntry 1  }

qosLimObcBackplaneQueueStatsC15mObcLowDiscBytes OBJECT-TYPE 
	SYNTAX	Counter
	ACCESS read-only
	STATUS mandatory
	DESCRIPTION
	    " Current discarded byte count towards OBC due to low water mark crossing."
::= { qosLimObcBackplaneQueueStatsC15mEntry 2  }

qosLimObcBackplaneQueueStatsC15mObcHighDiscPkts OBJECT-TYPE 
	SYNTAX	Counter
	ACCESS read-only
	STATUS mandatory
	DESCRIPTION
	    " Current discarded packet count towards OBC due to high water mark crossing."
::= { qosLimObcBackplaneQueueStatsC15mEntry 3  }

qosLimObcBackplaneQueueStatsC15mObcHighDiscBytes OBJECT-TYPE 
	SYNTAX	Counter
	ACCESS read-only
	STATUS mandatory
	DESCRIPTION
	    " Current discarded byte count towards OBC due to high water mark crossing."
::= { qosLimObcBackplaneQueueStatsC15mEntry 4  }


qosLimObcBackplaneQueueStatsC15mBplLowDiscPkts OBJECT-TYPE 
	SYNTAX	Counter
	ACCESS read-only
	STATUS mandatory
	DESCRIPTION
	    " Current discarded packet count towards backplane due to low water mark crossing.
	    [R4.2.03]On NELT-B, it indicates the packet drop ratio(unit:10e-6) in BCM uplink."
::= { qosLimObcBackplaneQueueStatsC15mEntry 5  }

qosLimObcBackplaneQueueStatsC15mBplLowDiscBytes OBJECT-TYPE 
	SYNTAX	Counter
	ACCESS read-only
	STATUS mandatory
	DESCRIPTION
	    " Current discarded bytes count towards backplane due to low water mark crossing.
	    [R4.2.03]On NELT-B, it indicates the bytes drop ratio(unit:10e-6) in BCM uplink."
::= { qosLimObcBackplaneQueueStatsC15mEntry 6  }


qosLimObcBackplaneQueueStatsC15mBplHighDiscPkts OBJECT-TYPE 
	SYNTAX	Counter
	ACCESS read-only
	STATUS mandatory
	DESCRIPTION
	    " Current discarded packet count towards backplane due to high water mark crossing."
::= { qosLimObcBackplaneQueueStatsC15mEntry 7  }

qosLimObcBackplaneQueueStatsC15mBplHighDiscBytes OBJECT-TYPE 
	SYNTAX	Counter
	ACCESS read-only
	STATUS mandatory
	DESCRIPTION
	    " Current discarded bytes count towards backplane due to high water mark crossing."
::= { qosLimObcBackplaneQueueStatsC15mEntry 8  }

qosLimObcBackplaneQueueStatsC15mBplDownDiscPkts OBJECT-TYPE 
	SYNTAX	Counter
	ACCESS read-only
	STATUS mandatory
	DESCRIPTION
	    " Current discarded bytes count from backplane due to water mark crossing."
::= { qosLimObcBackplaneQueueStatsC15mEntry 9  }

qosLimObcBackplaneQueueStatsP15mTable OBJECT-TYPE
	SYNTAX	SEQUENCE OF QosLimObcBackplaneQueueStatsP15mEntry
	ACCESS not-accessible
	STATUS	mandatory
	DESCRIPTION
	"This table contains the prev 15 min QoS statistics on a 
	per GLT LIM basis of packets discarded towards OBC and backplane. Only one 15 min interval is supported."
::= {qosStatisticsAndData 19 }

qosLimObcBackplaneQueueStatsP15mEntry OBJECT-TYPE
    SYNTAX      QosLimObcBackplaneQueueStatsP15mEntry
    ACCESS      not-accessible
    STATUS      mandatory
    DESCRIPTION "An entry in the qosLimObcBackplaneQueueStatsP15mTable"
    INDEX      { eqptSlotId, qosLimObcBackplaneQueueStatsP15mCounterIndex}
    ::=  {qosLimObcBackplaneQueueStatsP15mTable 1 }


QosLimObcBackplaneQueueStatsP15mEntry ::= SEQUENCE
	{
		qosLimObcBackplaneQueueStatsP15mCounterIndex     INTEGER,
		qosLimObcBackplaneQueueStatsP15mObcLowDiscPkts   Counter,
		qosLimObcBackplaneQueueStatsP15mObcLowDiscBytes	 Counter,
		qosLimObcBackplaneQueueStatsP15mObcHighDiscPkts	 Counter,
		qosLimObcBackplaneQueueStatsP15mObcHighDiscBytes Counter,
		qosLimObcBackplaneQueueStatsP15mBplLowDiscPkts	 Counter,
		qosLimObcBackplaneQueueStatsP15mBplLowDiscBytes	 Counter,
		qosLimObcBackplaneQueueStatsP15mBplHighDiscPkts	 Counter,
		qosLimObcBackplaneQueueStatsP15mBplHighDiscBytes Counter,
                qosLimObcBackplaneQueueStatsP15mBplDownDiscPkts  Counter
	}


qosLimObcBackplaneQueueStatsP15mCounterIndex OBJECT-TYPE 
	SYNTAX	INTEGER (1)
	ACCESS not-accessible
	STATUS mandatory
	DESCRIPTION
	    " Number of previous interval. Currently only value of 1 is supported."
::= { qosLimObcBackplaneQueueStatsP15mEntry 1  }

qosLimObcBackplaneQueueStatsP15mObcLowDiscPkts OBJECT-TYPE 
	SYNTAX	Counter
	ACCESS read-only
	STATUS mandatory
	DESCRIPTION
	    " Current discarded packet count towards OBC due to low water mark crossing."
::= { qosLimObcBackplaneQueueStatsP15mEntry 2  }

qosLimObcBackplaneQueueStatsP15mObcLowDiscBytes OBJECT-TYPE 
	SYNTAX	Counter
	ACCESS read-only
	STATUS mandatory
	DESCRIPTION
	    " Current discarded bytes count towards OBC due to low water mark crossing."
::= { qosLimObcBackplaneQueueStatsP15mEntry 3 }


qosLimObcBackplaneQueueStatsP15mObcHighDiscPkts OBJECT-TYPE 
	SYNTAX	Counter
	ACCESS read-only
	STATUS mandatory
	DESCRIPTION
	    " Current discarded packet count towards OBC due to high water mark crossing."
::= { qosLimObcBackplaneQueueStatsP15mEntry 4 }

qosLimObcBackplaneQueueStatsP15mObcHighDiscBytes OBJECT-TYPE 
	SYNTAX	Counter
	ACCESS read-only
	STATUS mandatory
	DESCRIPTION
	    " Current discarded byte count towards OBC due to high water mark crossing."
::= { qosLimObcBackplaneQueueStatsP15mEntry 5 }



qosLimObcBackplaneQueueStatsP15mBplLowDiscPkts OBJECT-TYPE 
	SYNTAX	Counter
	ACCESS read-only
	STATUS mandatory
	DESCRIPTION
	    " Current discarded packet count towards backplane due to low water mark crossing.
	    [R4.2.03]On NELT-B, it indicates the packet drop ratio(unit:10e-6) in BCM uplink."
::= { qosLimObcBackplaneQueueStatsP15mEntry 6 }

qosLimObcBackplaneQueueStatsP15mBplLowDiscBytes OBJECT-TYPE 
	SYNTAX	Counter
	ACCESS read-only
	STATUS mandatory
	DESCRIPTION
	    " Current discarded bytes count towards backplane due to low water mark crossing.
	    [R4.2.03]On NELT-B, it indicates the bytes drop ratio(unit:10e-6) in BCM uplink."
::= { qosLimObcBackplaneQueueStatsP15mEntry 7 }


qosLimObcBackplaneQueueStatsP15mBplHighDiscPkts OBJECT-TYPE 
	SYNTAX	Counter
	ACCESS read-only
	STATUS mandatory
	DESCRIPTION
	    " Current discarded packet count towards backplane due to high water mark crossing."
::= { qosLimObcBackplaneQueueStatsP15mEntry 8 }


qosLimObcBackplaneQueueStatsP15mBplHighDiscBytes OBJECT-TYPE 
	SYNTAX	Counter
	ACCESS read-only
	STATUS mandatory
	DESCRIPTION
	    " Current discarded bytes count towards backplane due to high water mark crossing."
::= { qosLimObcBackplaneQueueStatsP15mEntry 9 }

qosLimObcBackplaneQueueStatsP15mBplDownDiscPkts OBJECT-TYPE 
	SYNTAX	Counter
	ACCESS read-only
	STATUS mandatory
	DESCRIPTION
	    " Current discarded packet count from backplane due to water mark crossing."
::= { qosLimObcBackplaneQueueStatsP15mEntry 10 }


-- **************************************
-- qosResourceUsageTable .47.7.20
-- **************************************
qosResourceUsageTable OBJECT-TYPE
	SYNTAX	SEQUENCE OF QosResourceUsageEntry
	ACCESS not-accessible
	STATUS	mandatory
	DESCRIPTION
	"This table contains QOS resource usage information.
Currently, this table contains only information applicable for line cards of type NELT-B."
::= {qosStatisticsAndData 20 }


--qosLimColorBasedQueueStatsP15mTable

qosLimColorBasedQueueStatsP15mTable OBJECT-TYPE
	SYNTAX	SEQUENCE OF QosLimColorBasedQueueStatsP15mEntry
	ACCESS  not-accessible
	STATUS	mandatory
	DESCRIPTION
	"This table contains the previous 15 minute color based queue statistics on a 
	per EBLT LIM basis"
::= {qosStatisticsAndData 21 }

qosLimColorBasedQueueStatsP15mEntry OBJECT-TYPE
    SYNTAX      QosLimColorBasedQueueStatsP15mEntry
    ACCESS      not-accessible
    STATUS      mandatory
    DESCRIPTION "An entry in the qosLimColorBasedQueueStatsP15mTable"
    INDEX      {qosLimColorBasedQueueStatsP15mLineLinkIndex, qosLimColorBasedQueueStatsP15mLineQueueIndex, qosLimColorBasedQueueStatsP15mIntervalNumber }
    ::=  {qosLimColorBasedQueueStatsP15mTable 1 }


QosLimColorBasedQueueStatsP15mEntry ::= SEQUENCE
   {
      qosLimColorBasedQueueStatsP15mLineLinkIndex               InterfaceIndex,
      qosLimColorBasedQueueStatsP15mLineQueueIndex              INTEGER,
      qosLimColorBasedQueueStatsP15mIntervalNumber              INTEGER,
      qosLimColorBasedQueueStatsP15mRedPassBytes                Counter64bit,
      qosLimColorBasedQueueStatsP15mRedPassFrames               Counter64bit,
      qosLimColorBasedQueueStatsP15mRedDiscBytes                Counter64bit,
      qosLimColorBasedQueueStatsP15mRedDiscFrames               Counter64bit,
      qosLimColorBasedQueueStatsP15mYellowPassBytes              Counter64bit,
      qosLimColorBasedQueueStatsP15mYellowPassFrames             Counter64bit,
      qosLimColorBasedQueueStatsP15mYellowDiscBytes              Counter64bit,
      qosLimColorBasedQueueStatsP15mYellowDiscFrames             Counter64bit,
      qosLimColorBasedQueueStatsP15mGreenPassBytes              Counter64bit,
      qosLimColorBasedQueueStatsP15mGreenPassFrames             Counter64bit,
      qosLimColorBasedQueueStatsP15mGreenDiscBytes              Counter64bit,
      qosLimColorBasedQueueStatsP15mGreenDiscFrames             Counter64bit,
      qosLimColorBasedQueueStatsP15mMeasuredTime                INTEGER
   }


qosLimColorBasedQueueStatsP15mLineLinkIndex 	OBJECT-TYPE 
	SYNTAX	InterfaceIndex
	ACCESS read-only
	STATUS mandatory
	DESCRIPTION
	    " This object is used to index the physical line such as DSL line on the LIM."
::= {qosLimColorBasedQueueStatsP15mEntry 1 }


qosLimColorBasedQueueStatsP15mLineQueueIndex 	OBJECT-TYPE 
	SYNTAX	INTEGER (0 .. 8)
	ACCESS read-only
	STATUS mandatory
	DESCRIPTION
	    " This object is used to index the queue within the 
		 scope of one physical link on the LIM. Index 8 means total physical line."
::= {qosLimColorBasedQueueStatsP15mEntry 2 }

qosLimColorBasedQueueStatsP15mIntervalNumber 	OBJECT-TYPE 
	SYNTAX	INTEGER (1)
	ACCESS not-accessible
	STATUS mandatory
	DESCRIPTION
	"A number, which identifies the interval for which the 
    set of statistics is available. The interval identified by 1 is the 
    most recently completed 15 minute interval, and the interval identified 
    by N is the interval immediately preceding the one identified by N-1. currently only 1 interval supported."
::= {qosLimColorBasedQueueStatsP15mEntry 3 }


qosLimColorBasedQueueStatsP15mRedPassBytes 	OBJECT-TYPE 
	SYNTAX	Counter64bit
	ACCESS read-only
	STATUS mandatory
	DESCRIPTION
	    "Previous 15 minute passed bytes with color RED in this queue. If queue index is 8, it means the sum of each queue of this physical line."
::= {qosLimColorBasedQueueStatsP15mEntry 4 }

qosLimColorBasedQueueStatsP15mRedPassFrames 	OBJECT-TYPE 
	SYNTAX	Counter64bit
	ACCESS read-only
	STATUS mandatory
	DESCRIPTION
	    " Previous 15 minute passed frames with color RED in this queue. If queue index is 8, it means the sum of each queue of this physical line."
::= {qosLimColorBasedQueueStatsP15mEntry 5 }

qosLimColorBasedQueueStatsP15mRedDiscBytes OBJECT-TYPE 
	SYNTAX	Counter64bit
	ACCESS read-only
	STATUS mandatory
	DESCRIPTION
	    " Previous 15 minutes discarded bytes with color RED in this queue. If queue index is 8, it means the sum of each queue of this physical line."
::= {qosLimColorBasedQueueStatsP15mEntry 6  }

qosLimColorBasedQueueStatsP15mRedDiscFrames OBJECT-TYPE 
	SYNTAX	Counter64bit
	ACCESS read-only
	STATUS mandatory
	DESCRIPTION
	    " Previous 15 minutes discarded frames with color RED in this queue. If queue index is 8, it means the sum of each queue of this physical line."
::= {qosLimColorBasedQueueStatsP15mEntry 7  }
 

qosLimColorBasedQueueStatsP15mYellowPassBytes 	OBJECT-TYPE 
	SYNTAX	Counter64bit
	ACCESS read-only
	STATUS mandatory
	DESCRIPTION
	    "Previous 15 minute passed bytes with color YELLOW in this queue. If queue index is 8, it means the sum of each queue of this physical line."
::= {qosLimColorBasedQueueStatsP15mEntry 8 }

qosLimColorBasedQueueStatsP15mYellowPassFrames 	OBJECT-TYPE 
	SYNTAX	Counter64bit
	ACCESS read-only
	STATUS mandatory
	DESCRIPTION
	    " Previous 15 minute passed frames with color YELLOW in this queue. If queue index is 8, it means the sum of each queue of this physical line."
::= {qosLimColorBasedQueueStatsP15mEntry 9 }

qosLimColorBasedQueueStatsP15mYellowDiscBytes OBJECT-TYPE 
	SYNTAX	Counter64bit
	ACCESS read-only
	STATUS mandatory
	DESCRIPTION
	    " Previous 15 minutes discarded bytes with color YELLOW in this queue. If queue index is 8, it means the sum of each queue of this physical line."
::= {qosLimColorBasedQueueStatsP15mEntry 10  }

qosLimColorBasedQueueStatsP15mYellowDiscFrames OBJECT-TYPE 
	SYNTAX	Counter64bit
	ACCESS read-only
	STATUS mandatory
	DESCRIPTION
	    " Previous 15 minutes discarded frames with color YELLOW in this queue. If queue index is 8, it means the sum of each queue of this physical line."
::= {qosLimColorBasedQueueStatsP15mEntry 11  }
 
qosLimColorBasedQueueStatsP15mGreenPassBytes 	OBJECT-TYPE 
	SYNTAX	Counter64bit
	ACCESS read-only
	STATUS mandatory
	DESCRIPTION
	    "Previous 15 minute passed bytes with color GREEN in this queue. If queue index is 8, it means the sum of each queue of this physical line."
::= {qosLimColorBasedQueueStatsP15mEntry 12 }

qosLimColorBasedQueueStatsP15mGreenPassFrames 	OBJECT-TYPE 
	SYNTAX	Counter64bit
	ACCESS read-only
	STATUS mandatory
	DESCRIPTION
	    " Previous 15 minute passed frames with color GREEN in this queue. If queue index is 8, it means the sum of each queue of this physical line."
::= {qosLimColorBasedQueueStatsP15mEntry 13 }

qosLimColorBasedQueueStatsP15mGreenDiscBytes OBJECT-TYPE 
	SYNTAX	Counter64bit
	ACCESS read-only
	STATUS mandatory
	DESCRIPTION
	    " Previous 15 minutes discarded bytes with color GREEN in this queue. If queue index is 8, it means the sum of each queue of this physical line."
::= {qosLimColorBasedQueueStatsP15mEntry 14  }

qosLimColorBasedQueueStatsP15mGreenDiscFrames OBJECT-TYPE 
	SYNTAX	Counter64bit
	ACCESS read-only
	STATUS mandatory
	DESCRIPTION
	    " Previous 15 minutes discarded frames with color GREEN in this queue. If queue index is 8, it means the sum of each queue of this physical line."
::= {qosLimColorBasedQueueStatsP15mEntry 15  }
 
qosLimColorBasedQueueStatsP15mMeasuredTime 	OBJECT-TYPE 
	SYNTAX	INTEGER
	ACCESS read-only
	STATUS mandatory
	DESCRIPTION
	    "The amount of time, measured in seconds, that statistics 
		 for this entry have been counted."
::= {qosLimColorBasedQueueStatsP15mEntry 16  }


--qosLimColorBasedQueueStatsC15mTable

qosLimColorBasedQueueStatsC15mTable OBJECT-TYPE
	SYNTAX	SEQUENCE OF QosLimColorBasedQueueStatsC15mEntry
	ACCESS  not-accessible
	STATUS	mandatory
	DESCRIPTION
	"This table contains the current 15 minute color based queue statistics on a 
	per EBLT LIM basis"
::= {qosStatisticsAndData 22 }

qosLimColorBasedQueueStatsC15mEntry OBJECT-TYPE
    SYNTAX      QosLimColorBasedQueueStatsC15mEntry
    ACCESS      not-accessible
    STATUS      mandatory
    DESCRIPTION "An entry in the qosLimColorBasedQueueStatsC15mTable"
    INDEX      {qosLimColorBasedQueueStatsC15mLineLinkIndex, qosLimColorBasedQueueStatsC15mLineQueueIndex }
    ::=  {qosLimColorBasedQueueStatsC15mTable 1 }


QosLimColorBasedQueueStatsC15mEntry ::= SEQUENCE
   {
      qosLimColorBasedQueueStatsC15mLineLinkIndex               InterfaceIndex,
      qosLimColorBasedQueueStatsC15mLineQueueIndex              INTEGER,
      qosLimColorBasedQueueStatsC15mRedPassBytes                Counter64bit,
      qosLimColorBasedQueueStatsC15mRedPassFrames               Counter64bit,
      qosLimColorBasedQueueStatsC15mRedDiscBytes                Counter64bit,
      qosLimColorBasedQueueStatsC15mRedDiscFrames               Counter64bit,
      qosLimColorBasedQueueStatsC15mYellowPassBytes              Counter64bit,
      qosLimColorBasedQueueStatsC15mYellowPassFrames             Counter64bit,
      qosLimColorBasedQueueStatsC15mYellowDiscBytes              Counter64bit,
      qosLimColorBasedQueueStatsC15mYellowDiscFrames             Counter64bit,
      qosLimColorBasedQueueStatsC15mGreenPassBytes              Counter64bit,
      qosLimColorBasedQueueStatsC15mGreenPassFrames             Counter64bit,
      qosLimColorBasedQueueStatsC15mGreenDiscBytes              Counter64bit,
      qosLimColorBasedQueueStatsC15mGreenDiscFrames             Counter64bit,
      qosLimColorBasedQueueStatsC15mMeasuredTime                INTEGER
   }


qosLimColorBasedQueueStatsC15mLineLinkIndex 	OBJECT-TYPE 
	SYNTAX	InterfaceIndex
	ACCESS read-only
	STATUS mandatory
	DESCRIPTION
	    " This object is used to index the physical line such as DSL line on the LIM."
::= {qosLimColorBasedQueueStatsC15mEntry 1 }


qosLimColorBasedQueueStatsC15mLineQueueIndex 	OBJECT-TYPE 
	SYNTAX	INTEGER (0 .. 8)
	ACCESS read-only
	STATUS mandatory
	DESCRIPTION
	    " This object is used to index the queue within the 
		 scope of one physical link on the LIM. Index 8 means total physical line."
::= {qosLimColorBasedQueueStatsC15mEntry 2 }

qosLimColorBasedQueueStatsC15mRedPassBytes 	OBJECT-TYPE 
	SYNTAX	Counter64bit
	ACCESS read-only
	STATUS mandatory
	DESCRIPTION
	    " Current 15 minute passed bytes with color RED in this queue. If queue index is 8, it means the sum of each queue of this physical line."
::= {qosLimColorBasedQueueStatsC15mEntry 3 }

qosLimColorBasedQueueStatsC15mRedPassFrames 	OBJECT-TYPE 
	SYNTAX	Counter64bit
	ACCESS read-only
	STATUS mandatory
	DESCRIPTION
	    " Current 15 minute passed frames with color RED in this queue. If queue index is 8, it means the sum of each queue of this physical line."
::= {qosLimColorBasedQueueStatsC15mEntry 4 }

qosLimColorBasedQueueStatsC15mRedDiscBytes OBJECT-TYPE 
	SYNTAX	Counter64bit
	ACCESS read-only
	STATUS mandatory
	DESCRIPTION
	    " Current 15 minutes discarded bytes with color RED in this queue. If queue index is 8, it means the sum of each queue of this physical line."
::= {qosLimColorBasedQueueStatsC15mEntry 5  }

qosLimColorBasedQueueStatsC15mRedDiscFrames OBJECT-TYPE 
	SYNTAX	Counter64bit
	ACCESS read-only
	STATUS mandatory
	DESCRIPTION
	    " Current 15 minutes discarded frames with color RED in this queue. If queue index is 8, it means the sum of each queue of this physical line."
::= {qosLimColorBasedQueueStatsC15mEntry 6  }
 

qosLimColorBasedQueueStatsC15mYellowPassBytes 	OBJECT-TYPE 
	SYNTAX	Counter64bit
	ACCESS read-only
	STATUS mandatory
	DESCRIPTION
	    "Current 15 minute passed bytes with color YELLOW in this queue. If queue index is 8, it means the sum of each queue of this physical line."
::= {qosLimColorBasedQueueStatsC15mEntry 7 }

qosLimColorBasedQueueStatsC15mYellowPassFrames 	OBJECT-TYPE 
	SYNTAX	Counter64bit
	ACCESS read-only
	STATUS mandatory
	DESCRIPTION
	    " Current 15 minute passed frames with color YELLOW in this queue. If queue index is 8, it means the sum of each queue of this physical line."
::= {qosLimColorBasedQueueStatsC15mEntry 8 }

qosLimColorBasedQueueStatsC15mYellowDiscBytes OBJECT-TYPE 
	SYNTAX	Counter64bit
	ACCESS read-only
	STATUS mandatory
	DESCRIPTION
	    " Current 15 minutes discarded bytes with color YELLOW in this queue. If queue index is 8, it means the sum of each queue of this physical line."
::= {qosLimColorBasedQueueStatsC15mEntry 9  }

qosLimColorBasedQueueStatsC15mYellowDiscFrames OBJECT-TYPE 
	SYNTAX	Counter64bit
	ACCESS read-only
	STATUS mandatory
	DESCRIPTION
	    " Current 15 minutes discarded frames with color YELLOW in this queue. If queue index is 8, it means the sum of each queue of this physical line."
::= {qosLimColorBasedQueueStatsC15mEntry 10  }
 
qosLimColorBasedQueueStatsC15mGreenPassBytes 	OBJECT-TYPE 
	SYNTAX	Counter64bit
	ACCESS read-only
	STATUS mandatory
	DESCRIPTION
	    "Current 15 minute passed bytes with color GREEN in this queue. If queue index is 8, it means the sum of each queue of this physical line."
::= {qosLimColorBasedQueueStatsC15mEntry 11 }

qosLimColorBasedQueueStatsC15mGreenPassFrames 	OBJECT-TYPE 
	SYNTAX	Counter64bit
	ACCESS read-only
	STATUS mandatory
	DESCRIPTION
	    " Current 15 minute passed frames with color GREEN in this queue. If queue index is 8, it means the sum of each queue of this physical line."
::= {qosLimColorBasedQueueStatsC15mEntry 12 }

qosLimColorBasedQueueStatsC15mGreenDiscBytes OBJECT-TYPE 
	SYNTAX	Counter64bit
	ACCESS read-only
	STATUS mandatory
	DESCRIPTION
	    " Current 15 minutes discarded bytes with color GREEN in this queue. If queue index is 8, it means the sum of each queue of this physical line."
::= {qosLimColorBasedQueueStatsC15mEntry 13  }

qosLimColorBasedQueueStatsC15mGreenDiscFrames OBJECT-TYPE 
	SYNTAX	Counter64bit
	ACCESS read-only
	STATUS mandatory
	DESCRIPTION
	    " Current 15 minutes discarded frames with color GREEN in this queue. If queue index is 8, it means the sum of each queue of this physical line."
::= {qosLimColorBasedQueueStatsC15mEntry 14  }
 
qosLimColorBasedQueueStatsC15mMeasuredTime 	OBJECT-TYPE 
	SYNTAX	INTEGER
	ACCESS read-only
	STATUS mandatory
	DESCRIPTION
	    "The amount of time, measured in seconds, that statistics 
		 for this entry have been counted."
::= {qosLimColorBasedQueueStatsC15mEntry 15  }


     
qosVlanPortColorTroubleshootTable    OBJECT-TYPE
      SYNTAX   SEQUENCE OF QosVlanPortColorTroubleshootEntry
      ACCESS   not-accessible
      STATUS   mandatory
      DESCRIPTION
         " QoS color troubleshoot counters for a vlan port.
             ALCATEL NOTE:
                 TABLESIZE:  DEP [16 per LT card]
                 DESCR:      NA"
      ::= { qosStatisticsAndData 23  }

   qosVlanPortColorTroubleshootEntry OBJECT-TYPE
      SYNTAX   QosVlanPortColorTroubleshootEntry
      ACCESS   not-accessible
      STATUS   mandatory
      DESCRIPTION
         "Table entry for QoS color troubleshoot counters for vlan port."
      INDEX   { ifIndex  }
      ::= { qosVlanPortColorTroubleshootTable    1 }

    QosVlanPortColorTroubleshootEntry ::=
      SEQUENCE {
            qosVlanportUpGreenBeforePolicer
               Counter64bit,
            qosVlanportUpYellowBeforePolicer
               Counter64bit,
            qosVlanportUpRedBeforePolicer
               Counter64bit,
            qosVlanportUpG2GAfterPolicer
               Counter64bit,
            qosVlanportUpG2YAfterPolicer
               Counter64bit,
            qosVlanportUpG2RAfterPolicer
               Counter64bit,
            qosVlanportUpY2YAfterPolicer
               Counter64bit,
            qosVlanportUpY2RAfterPolicer
               Counter64bit,
            qosVlanportUpR2RAfterPolicer
               Counter64bit,
            qosVlanportDnGreenBeforePolicer
               Counter64bit,
            qosVlanportDnYellowBeforePolicer
               Counter64bit,
            qosVlanportDnRedBeforePolicer
               Counter64bit,
            qosVlanportDnG2GAfterPolicer
               Counter64bit,
            qosVlanportDnG2YAfterPolicer
               Counter64bit,
            qosVlanportDnG2RAfterPolicer
               Counter64bit,
            qosVlanportDnY2YAfterPolicer
               Counter64bit,
            qosVlanportDnY2RAfterPolicer
               Counter64bit,
            qosVlanportDnR2RAfterPolicer
               Counter64bit
                }


    qosVlanportUpGreenBeforePolicer OBJECT-TYPE
      SYNTAX   Counter64bit
      ACCESS     read-only
      STATUS   mandatory
      DESCRIPTION
         "64-bit counter of the green packets send to policer in up direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 1 }
      
    qosVlanportUpYellowBeforePolicer OBJECT-TYPE
      SYNTAX   Counter64bit
      ACCESS     read-only
      STATUS   mandatory
      DESCRIPTION
         "64-bit counter of the yellow packets send to policer in up direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 2 }
      
      qosVlanportUpRedBeforePolicer OBJECT-TYPE
      SYNTAX   Counter64bit
      ACCESS     read-only
      STATUS   mandatory
      DESCRIPTION
         "64-bit counter of the red packets send to policer in up direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 3 }
      
      qosVlanportUpG2GAfterPolicer OBJECT-TYPE
      SYNTAX   Counter64bit
      ACCESS     read-only
      STATUS   mandatory
      DESCRIPTION
         "64-bit counter of the green packets which from green packets after policer in up direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 4 }
      
      qosVlanportUpG2YAfterPolicer OBJECT-TYPE
      SYNTAX   Counter64bit
      ACCESS     read-only
      STATUS   mandatory
      DESCRIPTION
         "64-bit counter of the yellow packets which translate from green packets after policer in up direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 5 }
      
       qosVlanportUpG2RAfterPolicer OBJECT-TYPE
      SYNTAX   Counter64bit
      ACCESS     read-only
      STATUS   mandatory
      DESCRIPTION
         "64-bit counter of the red packets which translate from green packets after policer in up direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 6 }
      
       qosVlanportUpY2YAfterPolicer OBJECT-TYPE
      SYNTAX   Counter64bit
      ACCESS     read-only
      STATUS   mandatory
      DESCRIPTION
         "64-bit counter of the yellow packets which from yellow packets after policer in up direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 7 }
      
      qosVlanportUpY2RAfterPolicer OBJECT-TYPE
      SYNTAX   Counter64bit
      ACCESS     read-only
      STATUS   mandatory
      DESCRIPTION
         "64-bit counter of the red packets which translate from yellow packets after policer in up direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 8 }
      
      qosVlanportUpR2RAfterPolicer OBJECT-TYPE
      SYNTAX   Counter64bit
      ACCESS     read-only
      STATUS   mandatory
      DESCRIPTION
         "64-bit counter of the red packets which from red packets after policer in up direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 9 }
      
      qosVlanportDnGreenBeforePolicer OBJECT-TYPE
      SYNTAX   Counter64bit
      ACCESS     read-only
      STATUS   mandatory
      DESCRIPTION
         "64-bit counter of the green packets send to policer in down direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 10 }
      
      qosVlanportDnYellowBeforePolicer OBJECT-TYPE
      SYNTAX   Counter64bit
      ACCESS     read-only
      STATUS   mandatory
      DESCRIPTION
         "64-bit counter of the yellow packets send to policer in down direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 11 }
      
        qosVlanportDnRedBeforePolicer OBJECT-TYPE
      SYNTAX   Counter64bit
      ACCESS     read-only
      STATUS   mandatory
      DESCRIPTION
         "64-bit counter of the red packets send to policer in down direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 12 }
      
       qosVlanportDnG2GAfterPolicer OBJECT-TYPE
      SYNTAX   Counter64bit
      ACCESS     read-only
      STATUS   mandatory
      DESCRIPTION
         "64-bit counter of the green packets which from green packets after policer in down direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 13 }
      
    qosVlanportDnG2YAfterPolicer OBJECT-TYPE
      SYNTAX   Counter64bit
      ACCESS     read-only
      STATUS   mandatory
      DESCRIPTION
         "64-bit counter of the yellow packets which translate from green packets after policer in down direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 14 }
      
      qosVlanportDnG2RAfterPolicer OBJECT-TYPE
      SYNTAX   Counter64bit
      ACCESS     read-only
      STATUS   mandatory
      DESCRIPTION
         "64-bit counter of the red packets which translate from green packets after policer in down direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 15 }
      
      qosVlanportDnY2YAfterPolicer OBJECT-TYPE
      SYNTAX   Counter64bit
      ACCESS     read-only
      STATUS   mandatory
      DESCRIPTION
         "64-bit counter of the yellow packets which from yellow packets after policer in down direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 16 }
      
      qosVlanportDnY2RAfterPolicer OBJECT-TYPE
      SYNTAX   Counter64bit
      ACCESS     read-only
      STATUS   mandatory
      DESCRIPTION
         "64-bit counter of the red packets which translate from yellow packets after policer in down direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 17 }
      
       qosVlanportDnR2RAfterPolicer OBJECT-TYPE
      SYNTAX   Counter64bit
      ACCESS     read-only
      STATUS   mandatory
      DESCRIPTION
         "64-bit counter of the red packets which from red packets after policer in down direction.
             ALCATEL NOTE:
                 ACCESS:     NA       USAGE:      NA
                 PERSIST:    NO       INSRVMOD:   NO
                 RANGE:      NA       DEFVALUE:   NA
                 UNITS:      frames   SPARSE:     NA
                 DESCR:      NA"
      ::= { qosVlanPortColorTroubleshootEntry 18 }
     
qosResourceUsageEntry OBJECT-TYPE
    SYNTAX      QosResourceUsageEntry
    ACCESS      not-accessible
    STATUS      mandatory
    DESCRIPTION "An entry in the qosResourceUsageTable"
    INDEX      { eqptSlotId }
    ::=  {qosResourceUsageTable 1 }


QosResourceUsageEntry ::= SEQUENCE
	{
		qosResourceUsageAvailableSharedHwResource			Uint32,
		qosResourceUsageUsedSharedHwResourcesPart1			Uint32,
		qosResourceUsageUsedSharedHwResourcesPart2			Uint32,
		qosResourceUsageExcessIpAntispoofingPart1			Uint32,
		qosResourceUsageExcessIpAntispoofingPart2			Uint32
	}


qosResourceUsageAvailableSharedHwResource OBJECT-TYPE 
	SYNTAX	Uint32 
	ACCESS read-only
	STATUS mandatory
	DESCRIPTION
	    " The  available NELT-B HW resources per port-group ( port-group 1 = interfaces 1 until 18, port-group 2 = interfaces 19 until 36 ), i.e. used + unused qos ingress hardware filter, shared by next QOS items :
-	The supported QOS Policies of a sessionprofile attached to a bridge/vlan port.
-	The supported Policers (SAP level) of a sessionprofile attached to a bridge/vlan port.
-	DSCP enforcement (SAP level) of a sessionprofile attached to a bridge/vlan port.

ALCATEL NOTE:
                 ACCESS:     NA       USAGE:      NA
                 PERSIST:    NO       INSRVMOD:   NO
                 RANGE:      NA       DEFVALUE:   0
                 UNITS:      NA       SPARSE:     NA
                 DESCR:  
Object only applicable for NELT-B Line cards.    
"
::= { qosResourceUsageEntry 1 }


qosResourceUsageUsedSharedHwResourcesPart1 OBJECT-TYPE 
	SYNTAX	Uint32 
	ACCESS read-only
	STATUS mandatory
	DESCRIPTION
	    " Number of used shared NELT-B HW resources, i.e. qos ingress hardware filter, for QOS items in use for interfaces 1 until 18.
QOS items:
-	The supported QOS Policies of a sessionprofile attached to a bridge/vlan port.
-	The supported Policers (SAP level) of a sessionprofile attached to a bridge/vlan port.
-	DSCP enforcement (SAP level) of a sessionprofile attached to a bridge/vlan port.

ALCATEL NOTE:
                 ACCESS:     NA       USAGE:      NA
                 PERSIST:    NO       INSRVMOD:   NO
                 RANGE:      NA       DEFVALUE:   0
                 UNITS:      NA       SPARSE:     NA
                 DESCR: 
Object only applicable for NELT-B Line cards.
"
::= { qosResourceUsageEntry 2 }



qosResourceUsageUsedSharedHwResourcesPart2 OBJECT-TYPE 
	SYNTAX	Uint32 
	ACCESS read-only
	STATUS mandatory
	DESCRIPTION
	    " Number of used shared NELT-B HW resources, i.e. qos ingress hardware filter, for QOS items in use for interfaces 19 until 36.
QOS items:
-	The supported QOS Policies of a sessionprofile attached to a bridge/vlan port.
-	The supported Policers (SAP level) of a sessionprofile attached to a bridge/vlan port.
-	DSCP enforcement (SAP level) of a sessionprofile attached to a bridge/vlan port.

ALCATEL NOTE:
                 ACCESS:     NA       USAGE:      NA
                 PERSIST:    NO       INSRVMOD:   NO
                 RANGE:      NA       DEFVALUE:   0
                 UNITS:      NA       SPARSE:     NA
                 DESCR:  
Object only applicable for NELT-B Line cards.
"
::= { qosResourceUsageEntry 3 }



qosResourceUsageExcessIpAntispoofingPart1 OBJECT-TYPE 
	SYNTAX	Uint32 
	ACCESS read-only
	STATUS mandatory
	DESCRIPTION
	    " Number of shared NELT-B HW resources, i.e. qos ingress hardware filter, (reported by object qosResourceUsageUsedSharedHwResourcesPart1)  which must be released for interfaces 1 unitil 18 to be able to apply IpAntispoofing on ports of type Hicap-UNI. 

ALCATEL NOTE:
                 ACCESS:     NA       USAGE:      NA
                 PERSIST:    NO       INSRVMOD:   NO
                 RANGE:      NA       DEFVALUE:   0
                 UNITS:      NA       SPARSE:     NA
                 DESCR: 
Object only applicable for NELT-B Line cards.
"
::= { qosResourceUsageEntry 4 }


qosResourceUsageExcessIpAntispoofingPart2 OBJECT-TYPE 
	SYNTAX	Uint32 
	ACCESS read-only
	STATUS mandatory
	DESCRIPTION
	    " Number of shared NELT-B HW resources, i.e. qos ingress hardware filter, (reported by object qosResourceUsageUsedSharedHwResourcesPart2)  which must be released for interfaces 19 unitil 36 to be able to apply IpAntispoofing on ports of type Hicap-UNI. 


ALCATEL NOTE:
                 ACCESS:     NA       USAGE:      NA
                 PERSIST:    NO       INSRVMOD:   NO
                 RANGE:      NA       DEFVALUE:   0
                 UNITS:      NA       SPARSE:     NA
                 DESCR: 
Object only applicable for NELT-B Line cards.
"
::= { qosResourceUsageEntry 5 }





-- DSCPDot1PAlignment
qosDscpDot1PAlignment OBJECT IDENTIFIER ::= {qosMIB 8}

qosDscpToDot1PAlignmentTable OBJECT-TYPE
        SYNTAX  SEQUENCE OF QosDscpToDot1PAlignmentEntry
        ACCESS	not-accessible
	STATUS	mandatory
	DESCRIPTION
	"This object contains a table that defines the mapping from DSCP
         value to the .1P field of the VLAN tag. The row index of the table
         is the ingress DSCP value (0..63) while the value is the .1P(0..7)."
::= { qosDscpDot1PAlignment 1}

qosDscpToDot1PAlignmentEntry OBJECT-TYPE
	SYNTAX QosDscpToDot1PAlignmentEntry
	ACCESS not-accessible
	STATUS	mandatory
	DESCRIPTION
	"This table contains the DSCP value to 802.1P traffic class mapping
         information. There are 64 rows, each containing one .1P value (0..7)"
	INDEX {qosDscpToDot1PAlignmentDscp }
	::= {qosDscpToDot1PAlignmentTable  1}


QosDscpToDot1PAlignmentEntry ::=
	SEQUENCE {	qosDscpToDot1PAlignmentDscp      INTEGER,	
			qosDscpToDot1PAlignmentDot1P     INTEGER
		 }

qosDscpToDot1PAlignmentDscp OBJECT-TYPE
	SYNTAX	INTEGER(0 .. 63)
	ACCESS	not-accessible
	STATUS mandatory
	DESCRIPTION
	    "This field is used to index the DSCP to Dot1P alignment table.
             The lengths of the table is 64 (fixed)"
::= {  qosDscpToDot1PAlignmentEntry 1 }


qosDscpToDot1PAlignmentDot1P OBJECT-TYPE
	SYNTAX	INTEGER(0 .. 7)
	ACCESS	read-write
	STATUS mandatory
	DESCRIPTION
	"This object encodes the Dot1P (0..7) into which
	frames coming in with the DSCP value equal to the
	index of the row in this table.
	E.g., if row 63 contains value 7, that means that frames
	with DSCP value equal to 63 will be encoded to .1P value 7"
::= {  qosDscpToDot1PAlignmentEntry 2 }


--
--

qosDscpToDot1PAlignmentL3Traffic OBJECT-TYPE
	SYNTAX INTEGER	{
				true (1),
				false (2)
			}
	ACCESS read-write
	STATUS mandatory
	DESCRIPTION
        "setting this object to true will do the DSCP to P-bits
         alignment for all the L3 forwarding traffic"
        DEFVAL {false}
::= {	qosDscpDot1PAlignment 2}






    qosPccRules OBJECT IDENTIFIER ::= { qosMIB 9 }

    --**************************************************************
    -- PCC RULES
    --**************************************************************

    pccRuleTable OBJECT-TYPE
        SYNTAX          SEQUENCE OF PccRuleEntry
        ACCESS          not-accessible
        STATUS          mandatory
        DESCRIPTION
             "The table is partitioned per userLineId and sub-partitioned
              per userFwdPortId. 
              Each table row is indexed by pccRuleIndex.
              Each such table row contains the parameters of a PCC Rule obtained
              via e.g. the DIAMETER Gxr Interface.
        ALCATEL NOTE:
             TABLESIZE: depends on the number of User Lines,
                  multiplied by the average number of PCC Rules per User Line.
                  The latter is about 0.15 PCC Rules, derived from:
                  average 1.5 set-top box per household, and
                  average 10% of the streaming traffic is unicast video (VoD).
             "
        ::= { qosPccRules 1 }

    pccRuleEntry OBJECT-TYPE
        SYNTAX          PccRuleEntry
        ACCESS          not-accessible
        STATUS          mandatory
        DESCRIPTION
             "Rows are created automatically when a PCC rule is accepted and
              installed by the DSLAM after being downloaded by a Policy and
              Charging Rule Function (PCRF server).
             "
        INDEX { userLineId, userFwdPortId, pccRuleIndex }
        ::= { pccRuleTable 1 }

    PccRuleEntry ::= SEQUENCE {
        userLineId           InterfaceIndex,
        userFwdPortId        InterfaceIndex,
        pccRuleIndex                INTEGER,
        pccRuleName            OCTET STRING,
        pccRuleMaxDownRate          INTEGER,
        pccRulePreEmptPriority       Uint32,
        pccRulePreEmpVulnerability  INTEGER
        }

    userLineId OBJECT-TYPE
        SYNTAX          InterfaceIndex
        ACCESS          read-only
        STATUS          mandatory
        DESCRIPTION
             "The userLineId identifies a ADSL-port index, a VDSL-port index, 
              or a native Ethernet-port index.
              In case the PCC Rule is installed via the DIAMETER Gxr Interface, the
              userLine Id must match with a rcSessionUserLineId in the DIAMETER
              MIB.
        ALCATEL NOTE:
             ACCESS:    NA
             USAGE:     NA
             PERSIST:   NA
             INSRVMOD:  NA
             RANGE:     NA
             DEFVALUE:  NA
             UNITS:     NA
             SPARSE:    NO
             "
        ::= { pccRuleEntry 1 }

    userFwdPortId OBJECT-TYPE
        SYNTAX          InterfaceIndex
        ACCESS          read-only
        STATUS          mandatory
        DESCRIPTION
             "The userFwdPortId identify a VLAN port or a PPPoE client port, so
              in general the access port to the forwarding service.
              The value is the ifIndex that matches with the circuit id in the
              Gxr's Bearer-Identifier AVP.
        ALCATEL NOTE:
             ACCESS:    NA
             USAGE:     NA
             PERSIST:   NA
             INSRVMOD:  NA
             RANGE:     NA
             DEFVALUE:  NA
             UNITS:     NA
             SPARSE:    NO
             "
        ::= { pccRuleEntry 2 }

    pccRuleIndex OBJECT-TYPE
        SYNTAX          INTEGER
        ACCESS          read-only
        STATUS          mandatory
        DESCRIPTION
             "An index to distinguish between different PCC rules.
        ALCATEL NOTE:
             ACCESS:    NA
             USAGE:     NA
             PERSIST:   NA
             INSRVMOD:  NA
             RANGE:     NA
             DEFVALUE:  NA
             UNITS:     NA
             SPARSE:    NO
             "
        ::= { pccRuleEntry 3 }

    pccRuleName OBJECT-TYPE
        SYNTAX          OCTET STRING (SIZE(0..32))
        ACCESS          read-only
        STATUS          mandatory
        DESCRIPTION
             "The name of the PCC rule.  
              The name is unique with an RC session, i.e. per User Line.
        ALCATEL NOTE:
             ACCESS:    NA
             USAGE:     NA
             PERSIST:   NA
             INSRVMOD:  NA
             RANGE:     NA
             DEFVALUE:  NA
             UNITS:     NA
             SPARSE:    NO
             "
        ::= { pccRuleEntry 4 }

    pccRuleMaxDownRate OBJECT-TYPE
        SYNTAX          INTEGER
        ACCESS          read-only
        STATUS          mandatory
        DESCRIPTION
             "The pccRuleMaxDownRate defines the maximum bit rate to be reserved
              for the downlink direction. 
        ALCATEL NOTE:
             ACCESS:    NA
             USAGE:     NA
             PERSIST:   NA
             INSRVMOD:  NA
             RANGE:     NA
             DEFVALUE:  NA
             UNITS:     Kilobits/sec
             SPARSE:    NO
             "
        ::= { pccRuleEntry 5 }

    pccRulePreEmptPriority OBJECT-TYPE
        SYNTAX          Uint32
        ACCESS          read-only
        STATUS          mandatory
        DESCRIPTION
             "The value of pccRulePreEmptPriority is used to decide which PCC rules
              to terminate in the event of a bandwidth drop of the User Line, 
              whilst the line remains operational.
              The highest level of priority is specified by the value 1.
        ALCATEL NOTE:
             ACCESS:    NA
             USAGE:     NA
             PERSIST:   NA
             INSRVMOD:  NA
             RANGE:     1..15
             DEFVALUE:  NA
             UNITS:     NA
             SPARSE:    NO
             "
        ::= { pccRuleEntry 6 }

    pccRulePreEmpVulnerability OBJECT-TYPE
        SYNTAX          INTEGER {
                                enabled(1),
                                disabled(2)
                                }
        ACCESS          read-only
        STATUS          mandatory
        DESCRIPTION
             "When pccRulePreEmpVulnerability is enabled, it is allowed to
              consider this rule for termination in the event of a bandwidth drop
              of the User Line, whilst the line remains operational.
        ALCATEL NOTE:
             ACCESS:    NA
             USAGE:     NA
             PERSIST:   NA
             INSRVMOD:  NA
             RANGE:     NA
             DEFVALUE:  NA
             UNITS:     NA
             SPARSE:    NO
             "
        ::= { pccRuleEntry 7 }

    pccRuleEthIpFactor OBJECT-TYPE
        SYNTAX          Uint32
        ACCESS          read-write
        STATUS          mandatory
        DESCRIPTION
             "The rates in PCC rules are IP-rates, while ISAM RAC calculations
              are done with Eth-rates.
              The value pccRuleEthIpFactor gives in percentages the conversion
              factor IP-to-Ethernet. So the frame net bandwidth available on a
              DSL link for transmitting Ethernet frames equals the IP-rate
              multiplied by pccRuleEthIpFactor/100. 
              Ethernet overhead is about 20 bytes per IP packet. Then for 
              a stream of 1Kbyte IP packets, the Ehernet overhead is 2 percent,
              and so the pccRuleEthIpFactor is 102 percent.
              This is taken as default value.
        ALCATEL NOTE:
             ACCESS:    NA
             USAGE:     NA
             PERSIST:   YES
             INSRVMOD:  YES
             RANGE:     NA
             DEFVALUE:  102
             UNITS:     percentage
             SPARSE:    NO
             "
        ::= { qosPccRules 2 }


		
		
-- Pon Record
qosPonRecord OBJECT IDENTIFIER ::= {qosMIB 10}
--
--
--
--
-- qosPonRecordTable is used to read the 
-- currently available US and DS unicast BW on a PON interface by specifying the
-- IfIndex of the PON interface or a chanelpair. 

qosPonRecordTable OBJECT-TYPE
        SYNTAX  SEQUENCE OF QosPonRecordEntry
        ACCESS  not-accessible
        STATUS  mandatory
        DESCRIPTION
        "This object contains a table which is used to store
QoS settings that are applicable on GPON or NGPON2. 
                        "
::= { qosPonRecord 1 }
qosPonRecordEntry OBJECT-TYPE
        SYNTAX  QosPonRecordEntry
        ACCESS  not-accessible
        STATUS  mandatory
        DESCRIPTION
        "This table contains the per-PON link QoS settings"
        INDEX {qosPonRecordInterfaceIndex}
::= {qosPonRecordTable 1}
QosPonRecordEntry ::=
        SEQUENCE {      qosPonRecordInterfaceIndex           InterfaceIndex,
                        qosCurrentTcontsPerFrame             INTEGER,
                        qosFreeTcontsPerFrame                INTEGER 
                 }

qosPonRecordInterfaceIndex OBJECT-TYPE
        SYNTAX  InterfaceIndex
        ACCESS  not-accessible
        STATUS mandatory
        DESCRIPTION
         "This field is used to index the physical interface
        of a Pon or a channel-pair.
		
	    For GPON & NGPON2 - SUPPORTED as of ISAM5.5
        For DSL – NOT SUPPORTED"
::= { qosPonRecordEntry 1 }

qosCurrentTcontsPerFrame OBJECT-TYPE
        SYNTAX  INTEGER
        ACCESS  read-only
        STATUS  mandatory
        DESCRIPTION
         " This attribute represents current tconts number per frame
           with 0.01 granularity.
      ALCATEL NOTE:
                 ACCESS:     NA       USAGE:      NA
                 PERSIST:    NO       INSRVMOD:   NO
                 RANGE:      NA       DEFVALUE:   NA
                 UNITS:      NA       SPARSE:     NA
                 DESCR:      NA 

        For GPON & NGPON2 - SUPPORTED as of ISAM5.5
        For DSL – NOT SUPPORTED"
::= { qosPonRecordEntry 2 } 

qosFreeTcontsPerFrame OBJECT-TYPE
        SYNTAX  INTEGER
        ACCESS  read-only
        STATUS  mandatory
        DESCRIPTION
         " This attribute represents free tconts number per frame
           with 0.01 granularity.
      ALCATEL NOTE:
                 ACCESS:     NA       USAGE:      NA
                 PERSIST:    NO       INSRVMOD:   NO
                 RANGE:      NA       DEFVALUE:   NA
                 UNITS:      NA       SPARSE:     NA
                 DESCR:      NA 

        For GPON & NGPON2 - SUPPORTED as of ISAM5.5
        For DSL – NOT SUPPORTED"
::= { qosPonRecordEntry 3 } 

availableBandwidthChangeLogLastIndex OBJECT-TYPE
        SYNTAX Gauge 
        ACCESS  read-only
        STATUS  mandatory
        DESCRIPTION
         " This object specifies the index of the entry last added to
          the availableBandwidthChangeLogTable.
           This object is incremented each time for bandwidth of PON or 
		  Channel Pair changes and an entry is added in that log table
      ALCATEL NOTE:
                 ACCESS:     NA       USAGE:      NA
                 PERSIST:    NO       INSRVMOD:   NA
                 RANGE:      NA       DEFVALUE:   0
                 UNITS:      NA       SPARSE:     NA
                 DESCR:      NA 
        For GPON & NGPON2 - SUPPORTED as of ISAM5.5
        For DSL - NOT SUPPORTED"
::= { qosPonRecord 2 }

availableBandwidthChangeLogTable OBJECT-TYPE
        SYNTAX  SEQUENCE OF AvailableBandwidthChangeLogEntry
        ACCESS  not-accessible
        STATUS  mandatory
        DESCRIPTION
        "This table is used to log the events each time the bandwidth of the PON/Channel-pair 
	  changes,the log table is a wrap-around table. When table reached its maximum number 
	  of entries the oldest entries are overwritten.
                        "
::= { qosPonRecord 3 }
availableBandwidthChangeLogEntry OBJECT-TYPE
        SYNTAX  AvailableBandwidthChangeLogEntry
        ACCESS  not-accessible
        STATUS  mandatory
        DESCRIPTION
        "This entry logs the event that available BandWidth on a PON interface or a 
	  chanelpair has changed.With the ifIndex of a PON interface or a chanelpair the
	  Manager can retrieve the details from the qosPonRecordTable."
        INDEX {availableBandwidthChangeLogIndex}
::= {availableBandwidthChangeLogTable 1}
AvailableBandwidthChangeLogEntry ::=
        SEQUENCE {      availableBandwidthChangeLogIndex               Gauge,
                        availableBandwidthChangeInterfaceIndex         InterfaceIndex,
                        availableBandwidthChangeLogTime                NetworkTimeInSeconds 
                 }

availableBandwidthChangeLogIndex OBJECT-TYPE
        SYNTAX  Gauge
        ACCESS  not-accessible
        STATUS mandatory
        DESCRIPTION
         "This object is used as index into this table.

        ALCATEL NOTE:
       	ACCESS:		NA            
		USAGE:		NA
       	PERSIST:     NO            
		INSRVMOD:    NA
       	RANGE:       NA         
		DEFVALUE:    NA
        UNITS:       NA            
		SPARSE:      NA
		DESCR		NA  
		For GPON & NGPON2 - SUPPORTED as of ISAM5.5
        For DSL  NOT SUPPORTED"
::= { availableBandwidthChangeLogEntry 1 }

availableBandwidthChangeInterfaceIndex OBJECT-TYPE
        SYNTAX  InterfaceIndex
        ACCESS  read-only
        STATUS  mandatory
        DESCRIPTION
         "Indicates the interfaceIndex of the bandwidth of PON/Channel-pair changes.

       	ALCATEL NOTE:
       	ACCESS:		NA            
		USAGE:		NA
        PERSIST:     NO            
		INSRVMOD:    NA
       	RANGE:       interfaceIndex         
		DEFVALUE:    0
       	UNITS:       NA            
		SPARSE:      NA
		DESCR		NA  
		For GPON & NGPON2 - SUPPORTED as of ISAM5.5
        For DSL  NOT SUPPORTED"
::= { availableBandwidthChangeLogEntry 2 } 

availableBandwidthChangeLogTime OBJECT-TYPE
        SYNTAX  NetworkTimeInSeconds
        ACCESS  read-only
        STATUS  mandatory
        DESCRIPTION
         " Indicates the moment in time that bandwidth of PON/Channel-Pair changes.

        ALCATEL NOTE:
       	ACCESS:		NA            
		USAGE:		NA
       	PERSIST:     NO            
		INSRVMOD:    NA
       	RANGE:       seconds         
		DEFVALUE:    NA
        UNITS:       NA            
		SPARSE:      NA
		DESCR		NA  
		For GPON & NGPON2 - SUPPORTED as of ISAM5.5
        For DSL  NOT SUPPORTED"
::= { availableBandwidthChangeLogEntry 3 } 
		
		
END
