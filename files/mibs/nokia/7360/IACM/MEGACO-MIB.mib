-- IVPS_MGCH_MIB

-- ============================================================================
--  This specification is published by Alcatel under Non-Disclosure
--  Agreement(s) (NDA) with specific parties and has to be considered as
--  Confidential Information as defined in such NDA.
--  Alcatel reserves the right to revise this document for any reason,
--  including but not limited to conformity with standards promulgated by
--  various agencies, utilisation of advances in the state of the technical
--  areas, or the reflection of changes in the design of any equipment,
--  techniques, or procedures described or referred to herein.
--  The product specifications and other technical or performance information
--  contained herein are subject to change without notice.
--  Updates of this document will be issued under the above NDA's.
--  Alcatel makes no representation or warranty, expressed or implied, with
--  respect to the sufficiency, accuracy, or utility of any information or
--  opinion contained herein. Alcatel expressly advises that any use of for 
--  any purpose or reliance upon this technical reference is at the risk of
--  the user and that Alcatel will not be liable for any damage or injury
--  incurred by any person arising out of the sufficiency, accuracy, or
--  utility of any information or opinion contained herein.
--  This document is not to be construed as a suggestion to any manufacturer
--  to modify or change any of its products, nor does this document represent
--  any commitment by Alcatel to sell or purchase any product.
--  Nothing contained herein will be construed as conferring by implication,
--  estoppel, or otherwise any license or right under any patent, whether or
--  not the use of any information herein necessarily employs an invention of
--  any existing or later issued patent.
--  Alcatel reserves the right not to offer any or all of these products and
--  to withdraw any or all of them at any future time.
--  Copyright (C) 2006, Alcatel. All Rights Reserved.
-- ===============================================================================
 
 
--  MODULE-IDENTITY
--  LAST-UPDATED "200707130000Z"
--  ORGANIZATION "Alcatel"
--  CONTACT-INFO "Email: tao.b.liu@alcatel-sbell.com.cn"
--  DESCRIPTION  "IVPS MGCH MIB"
--
--  REVISION     "200707130000Z "
--  DESCRIPTION
--    "Version: 3FE25609AAAA_FDT659.V3.5.0.0.1
--     Editor:  Liu Tao
--     Changes:
--     * ANTms55444 : 
--       - From abaa to aaaa :
--    "
--
--  REVISION     "200707160000Z "
--  DESCRIPTION
--    "Version:
--     Editor:  Xie Tong
--     Changes:
--     * ANTms55444:
--       - Remove OAM mib objects :
--    "
--  REVISION     "200710310000Z "
--  DESCRIPTION
--    "Version:
--     Editor:  Luo Min
--     Changes:
--     * ANTms64265:
--       - add DSCP/Pbit for QOS feature :
--    "
--  REVISION     "200803181530Z"
--  DESCRIPTION
--    "Version: base on 3FE25609AAAA_GIS036.V3.6.1.0.0
--     Editor:  Yang Yuhua
--     Changes:
--     * ANTms67364:
--       - Add two new scarlars medGwyEventRequestID,medGwyEventList in the medGwyMegacoExtTable
--    "

--  REVISION     "200806170000Z "
--  DESCRIPTION
--    "Version:
--     Editor:  He Chunye
--     Changes:
--     * ANTms64393:
--       - obsolete accessBoardType in accessBoardTable
--	 - add accessBoardPlannedType and accessBoardActualType in accessBoardTable
--     * ANTms60111:
--       - update description of ltLineTest
--    "
--
--  REVISION     "200811150000Z"
--  DESCRIPTION
--    "Version:base on 3FE25609AAAA_FDT747.V4.0.0.0.2
--     Editor:  Li Hamei
--     Changes:
--     * ANTms24357:
--       - Update max line impedance value from 9 to 15
--    "
--
--  REVISION     "200902250000Z"
--  DESCRIPTION
--    "Version:base on 3FE25609AAAA_V4.0.0.0.0
--     Editor:  Li Hamei
--     Changes:
--     * ANTms44381 and ANTmt43930:
--       - Update description for medGwyPassiveHeartbeatInterval, medGwyActiveHeartbeatInterval, accessBoardId,
--       - accessEquipmentAsamId, mediaGatewayName,signallingGatewayInterfaceUserLabel
--    "
--
--  REVISION     "200903060000Z"
--  DESCRIPTION
--    "Version:base on 3FE25609AAAA_V4.0.0.0.0
--     Editor:  He Chunye
--     Changes:
--     * NTms60111:
--       - Add thresholdMin and thresholdMax in LtTestParamEntry
--    "
--
--  REVISION     "200905180000Z"
--  DESCRIPTION
--    "Version:base on 3FE25609AAAA_V4.0.0.0.2
--     Editor:  Li Haimei
--     Changes:
--     * ANTmt58459:
--       - Update description of accessTerminationId
--    "
--
--  REVISION     "200911230000Z"
--  DESCRIPTION
--    "Version:base on 3FE25609AAAA_V4.2.0.0.0
--     Editor:  Wu Xiuwen
--     Changes:
--     * ANTmt60010:
--       - Fdt993: Config external CDE parameter
--    "
--
--  REVISION     "201003250000Z"
--  DESCRIPTION
--    "Version:base on 3FE25609AAAA_V4.1.0.0.3
--     Editor:  He Chunye
--     Changes:
--     * 
--	    - Update Alcatel note of ltTestTypeString object from mandatory to optional for FR ALU00217749 
--	    - Update ltTestParamTable from write-only to read-write for FR ALU00217751.
--	    - Update description of ltTrapLineId  for FR ALU00217753 
--	    - Update ltTrapSessionId and ltTrapCmd for FR ALU00217753.
--    "
--
--  REVISION     "201006170000Z"
--  DESCRIPTION
--    "Version:base on 3FE25609AAAA_V4.2.0.1.1
--     Changes:
--     *
--          - Update description of ltTrapStatus and ltTrapLineHookStatus objects for ALU00431646.
--          - Update description of ltTimeOutPeriod object for ALU00441777.
--    "
--  REVISION     "201006250000Z"
--  DESCRIPTION
--    "Version:base on 3FE25609AAAA_V4.1.0.2.1
--     Editor:  He Chunye
--     Changes:
--     *
--          - Add one new object ltSessionInputErrCode in ltSessionTable, see ALU00428300
--    "
--    "
--
--  REVISION     "201008250000Z"
--  DESCRIPTION
--    "Version:base on 3FE25609AAAA_V4.2.0.3.1
--     Editor:  He Chunye
--     Changes:
--     *
--          - Add one new object ltSessionInactiveTimer in ltSessionTable, see ALU00736428
--    "
--
--  REVISION     "201101140000Z"
--  DESCRIPTION
--    "Version:base on 3FE25609AAAA_V4.3.0.2.0
--     Editor:  Zhao Xiaohui
--     Changes:
--     *
--          - Add new object CallStatus, OpStatDownReason, TestStatus, ChannelStatus in
--          - AccTerminationTable, see ALU00122454
--    "
--
--  REVISION     "201102100000Z"
--  DESCRIPTION
--    "Version:base on 3FE25609AAAA_V4.3.0.2.0
--     Editor:  GE Weimin
--     Changes:
--     *
--          - Modify the description of accTerminationImpedance according to 
--          - review comments. please refer comment #678679
--    "
--
--  REVISION     "201209050000Z"
--  DESCRIPTION
--   "Version: base on 3FE25629AAAA_V4.4.0.0.0
--    Editor:    Dixon Wang
--    Changes: 
--    RCR ALU00782371:
--      - Add object accTerminationIsdnCodec into the accessTerminationTable according to RCR ALU00782371. 
--   "
--
--  REVISION     "201210170000Z"
--  DESCRIPTION
--   "Version: base on 3FE25609AAAA_V4.4.0.3.2
--    Editor:    Dixon Wang
--    Changes: 
--    FR ALU01831301:
--      - Update the impedance description of MIB object accTerminationImpedance. 
--   "
--
--  REVISION     "201401280000z"
--  DESCRIPTION 
--   "Version: base on 76b87b8f687a
--    Editor:  Dennis Shao
--    Changes:
--    RCR ALU01944197:
--     - Update for  MIB readiness for R5.1.x features.
--     - For ALU01930754 (ISAMv H.248 : The mib configurable Timer-T must range from 0 to 99) 
--      - Update range for object medGwyDialingStartTimer. 
--   "
--
--  REVISION     "201401270000z"
--  DESCRIPTION 
--   "Version: base on 76b87b8f687a
--    Editor:    Hanks Li
--    Changes:
--    RCR ALU01944197:
--     - Update for  MIB readiness for R5.1.x features.
--     - For ALU01939867 ISAM-V H.248 :Define New MGC Type  comverse.
--      - Update range and value for object medGwyCtrlrCallServerType. 
--   "
--
--  REVISION     "201403040000Z"
--  DESCRIPTION
--    "Version: base on 1331ffc3edbb
--    Editor:   Catherine Zhang
--    Changes:
--          - Add new object medGwyCtrlrESAMgcIPAddress, medGwyCtrlrESAMgcUDPPort,
--          - mediaGatewayESAMgcService and mediaGatewayTriggerESAMgc, see ALU01914616.
--    "
--
--  REVISION     "201403050000z"
--  DESCRIPTION 
--   "Version: base on 28f8157c5b9e 
--    Editor:    Hanks Li
--    Changes:
--    FR ALU01957288:
--     - Update description of accTerminationImpedance.
--    FR ALU01957784:
--     - Update description of accTerminationTCAEnable. 
--   "
--
--  REVISION     "201403110000z"
--  DESCRIPTION 
--   "Version: base on 948973851bac 
--    Editor:    Hanks Li
--    Changes:
--    RCR ALU01944197:
--     - MIB readiness for R5.1.x features.
--    RCR ALU01943990:
--     - 7367-SX: POTS: Support H248 and ANSI GR303 
--   "
--
--  REVISION     "201403230000z"
--  DESCRIPTION 
--   "Version: base on c1f6906efdc5 
--    Editor:    Hanks Li
--    Changes:
--    RCR ALU01944197:
--     - MIB readiness for R5.1.x features.
--    RCR ALU01943990:
--     - 7367-SX: POTS: Support H248 and ANSI GR303, Update some mib description and default value to distinguish different products,as MDU 7367 will use the same mib with ISAMV. 
--     - Update value and range of accTerminationImpedance. 
--   "
--
--  REVISION     "201406030000z"
--  DESCRIPTION 
--   "Version: base on 3dfb2d96251b
--    Editor:   Dennis Shao 
--    Changes:
--    RCR ALU01944197:
--     - MIB readiness for R5.1.x features.
--     - Use Support/Applicable to instead of "just for isamv" and "mandatory for isamv".
--     
--   "
--
-- REVISION     "201408270000Z"
-- DESCRIPTION
--   "Version: base on R52 changeset: 89a63e42ccd2
--   Editor: Anny Zhong
--   Changes:
--   *
--         - Add two parameters to MIB type LTTestType:eZenerResistance/eZenerVoltage
--         - Add two bits in description of ltTestTypeExtend: bit20/bit19.
--         - Change all 10-6V to 10E-6V; Change all 10-6A to 10E-6A
--         - for RCR ALU01774601  Increase line test parameters for NBLT ROH test
--
--         - Update interrupted declaration of eVoiceDiagnosisH248Caller and eVoiceDiagnosisH248Callee 
--         - for RCR ALU01927330 in R5.2.x MIB Readiness RCR ALU01977195
--   "
--
-- REVISION     "201409190000Z"
-- DESCRIPTION
--   "Version: base on R52 changeset: 4ee91d676bae2d00fcfa816c0ec97295434dd790
--   Editor: Bill Feng
--   Changes:
--   *
--         - Add two parameters to MIB type LTTestType:eVoiceDiagnosisH248Caller/eVoiceDiagnosisH248Callee.
--         - Add two bits in description of ltTestTypeLow: bit8/bit7.
--         - Extend one parameter to LtLineIdExtReportEntry  to report received DTMF.
--   "
--
-- REVISION     "201409260000Z"
-- DESCRIPTION
--   "Version: base on R52 changeset: 3db02f126fe3da953f2affb98842ab2630fda840
--   Editor: Bill Feng
--   Changes:
--   *
--         - Add two objects to medGwyMegacoExtTable:mediaGatewayIPConfigMode/mediaGatewayIPDhcpv4Option60.
--         - Add two objects to ivpsBasicParamsTable: ivpsBasicParamVoiceIPConfigMode/ivpsBasicParamVoiceIPDhcpv4Option60  
--   "
--
-- REVISION     "201411130000Z"
-- DESCRIPTION
--   "Version: base on R52 changeset: d099378eaafa5cae4109a5e5d0c4b52b107f845f
--   Editor: Anny Zhong
--   Changes:
--   *
--         - Rename ltExtRpsVal in LtLineIdExtReportEntry as ltExtRpDtmfValue.
--   "
--
-- REVISION     "201411170000Z"
-- DESCRIPTION
--   "Version: base on R52 changeset: 4b47ca14d234cdcbcca10131b2150da13ca3b8e1
--   Editor: Loren Zhang
--   Changes:
--   *
--         - Update default value as null for ivpsBasicParamVoiceIPDhcpv4Option60/medGwyIPDhcpv4Option60.
--   "
--
-- REVISION     "201503110000z"
-- DESCRIPTION
--   "Version: base on 
--   Editor: Bonnie Huang
--   Changes:
--   *
--         - Update description of accessTerminationTable and add new item accTermVoiceServAtMgc in MIB.
--   "
--    "
--
--  REVISION     "201504240000Z"
--  DESCRIPTION
--    "Version:base on 
--     Editor:  Jason Chen
--     Changes:
--     *
--          - Update the description of accTermVoiceServAtMgc according to 
--          - demo review comments. 
--    "
--
--  REVISION     "201507070000Z"
--  DESCRIPTION
--    "Version:base on 
--     Editor:  Jason Chen
--     Changes:
--     *
--         - Delete parameter LTTestType:eReservedForFuture and add parameter LTTestType:eForceRingSubscriber.
--         - Update the description of ltTestTypeHigh: delete Reserved_For_Future and add Force_Ring_Subscriber. 
--         - Update the description of ltTestTypeLow: add new parameter ForceRing in eLineTestAttribute and  
--         - replace parameter eReservedForFuture by eForceRingSubscriber.
--         - Update the description of ltTestTypeExtend: add new parameter ForceRing in eLineTestAttribute.
--    "
--    "
--
--  REVISION     "201512280000Z"
--  DESCRIPTION
--    "Version:base on 
--     Editor:  Loren Zhang
--     Changes:
--     *
--          - Update the description of accTermVoiceServAtMgc according to FR ALU02160609.
--    "     
--  REVISION     "201601080000Z"
--  DESCRIPTION
--    "Version:base on 
--     Editor:  Sundarsa
--     Changes:
--     *
--         - Included new object ltSessionForcedTest in ltSessionTable.
--    "
--  REVISION     "201604110000Z"
--  DESCRIPTION
--    "Version:base on 
--     Editor:  kirubass
--     Changes:
--     *
--         - Modify the Mib parameter name resetUnfinished as resetUnavailable in ltHwControlTable. 
--    "

--  REVISION     "201602010000Z"
--  DESCRIPTION
--    "Version:base on 
--     Editor: Squall Zhou 
--     Changes:
--     *
--         - 1. Modify the description of "ltTestTypeExtend"
--         - 2. Define enum LTPraLoopbackTestResult
--         - 3. Add a new value "eISDNPraLoopBack" for "ltTestType" in "ltTestParamTable"
--         - 4. Add attribute class "ISDN_PRA_loopback_test" for ltTestTypeLow.
--    "

--  REVISION     "201606280000Z"
--  DESCRIPTION
--    "Version:base on 
--     Editor: Rain Ding 
--     Changes:
--     *
--         - 1. Update DESCRIPTION of accTerminationImpedance for ALU02222057 
--         - 2. Update DESCRIPTION of capaLineImpedanceBitmap for ALU02222057 
--         - 3. Update range of mediaGatewayVLAN for ALU02231452 
--    "

--  REVISION     "201610250000Z"
--  DESCRIPTION
--    "Version:base on
--     Editor: Rain Ding
--     Changes:
--     *
--      - update mib for RCR ALU02209084 ISAMV H248 NPOTS support share lines
--         - 1. modify object "accTerminationCallStatus" in table accessTerminationTable
--         - 2. create a new table named "accessSharedLineTerminationTable"
--    "

--  REVISION     "201610280000Z"
--  DESCRIPTION
--    "Version:base on
--     Editor:Dennis Shao
--     Changes:
--     *
--        - Add a new table accessTerminationLITable for RCR ALU02259582"



--  REVISION     "201611010000Z"
--  DESCRIPTION
--    "Version:base on 
--     Editor: Arthur Liu 
--     Changes:
--     *
--         - 1. Modify the description of "ltTestTypeExtend" for ALU02222349
--         - 2. Define enum LTPraRemoteLBTestResult, LTPraPayloadLBTestResult, LTPraLocalLBTestResult, LTPraCableLBTestResult   
--         - 3. Add new values eISDNPraRemoteLoopBack, eISDNPraPayloadLoopBack, eISDNPraLocalLoopBack, eISDNPraCableLoopBack for "ltTestType"
--    "


--  REVISION     "201611240000Z"
--  DESCRIPTION
--    "Version:base on 
--     Editor: Arthur Liu 
--     Changes:
--     *
--         - 1. Update value for LTPraRemoteLBTestResult and LTPraPayloadLBTestResult 
--         - 2. Update description of LTPraCableLBTestResult
--         - 3. Update description of ltTimeOutPeriod adding time limit of ISDN PRA loopback 
--    "

--  REVISION     "201612080000Z"
--  DESCRIPTION
--    "Version: base on
--     Editor: Rain Ding
--     Changes:
--     *
--         update following description for RCR ALU02209084:
--         -1. Update the description of internallyBlocked
--         -2. Update the description of internallyBlocked
--         -3. Add "alcatel-lucent note" for each object
--         -4. Explain what the value '0' and the range [1..32767] means
--         -5. Replace 'major' by 'prime" and 'affiliated' by 'secondary"
--         -6. Update the description of accessSharedLineTerminationTable
--    "

--  REVISION     "201612150000Z"
--  DESCRIPTION
--    "Version: base on
--     Editor: Rain Ding
--     Changes:
--     *
--         -Update the description of medGwyPstnTermFormatStr for RCR ALU02209084
--    "

--  REVISION     "201612150000Z"
--  DESCRIPTION
--    "Version:base on 
--     Editor: Arthur Liu 
--     Changes:
--     *
--         - 1. Add value testErrLoopbackHWsetFailed and testErrPatternCheckFailed for LTErrCode
--    "


--  REVISION     "201612300000Z"
--  DESCRIPTION
--    "Version:base on 
--     Editor: Arthur Liu 
--     Changes:
--     *
--         - 1. Update value 2 to hwSetFailed for LTPraLocalLBTestResult 
--         - 2. Add new value hwSetFailed(2) for LTPraCableLBTestResult
--    "

--  REVISION     "201702240000Z"
--  DESCRIPTION
--    "Version:base on
--     Editor:Dennis Shao
--     Changes:
--     *
--         - 1. Update object accTerminationLISrcUdpPort range from (49152..65535) to (49153..65535)
--    "

--  REVISION     "201703140000Z"
--  DESCRIPTION
--    "Version:base on
--     Editor:Jun AG Wang
--     Changes:
--     *
--         - 1. change internallyBlocked to shareCutoff
--    "

--  REVISION     "201703170000Z"
--  DESCRIPTION
--    "Version:base on
--     Editor:Jun AG Wang
--     Changes:
--     *
--         - 1. change shareCutoff to sharedCutoff
--    "

--  REVISION     "201704250000Z"
--  DESCRIPTION
--    "Version:base on
--     Editor:Jun AG Wang
--     Changes:
--     *
--         - 1. change accTerminationtId range from [0|1..32676] or [0|1..8175] to [0..32767] or [0..8175]
--         - 2. change accSharedLineTerminationtId range from [0|1..32676] to [0..32767] 
--    "
--  REVISION     "201705080000Z"
--  DESCRIPTION
--    "Version:base on
--     Editor:Jun AG Wang
--     Changes:
--     *
--         - 1. change description of accSharedLineTerminationtId, accSharedLineTerminationAdminStatus, accTerminationLI.
--    "

-- *********************************************************************
-- MEGACO-MIB
-- Media Gateway Control MIB
-- *********************************************************************
-- ===============================================================================

MEGACO-MIB DEFINITIONS ::= BEGIN

   IMPORTS
      OBJECT-TYPE
      FROM RFC-1212

      ifIndex,
      InterfaceIndex
                FROM ITF-MIB


      IpAddress, Counter, Gauge
      FROM RFC1155-SMI

      DisplayString, RowStatus, TestAndIncr, TruthValue
      FROM SNMPv2-TC

      asam, alcatel
      FROM SYSTEM-MIB;

   -- *****************************************************************
   -- OID for the MIB
   -- *****************************************************************
   megacoMib OBJECT IDENTIFIER ::= {asam 55}

   -- *****************************************************************
   -- Object Groups
   -- *****************************************************************
   mediaGatewayConfig OBJECT IDENTIFIER      ::= {megacoMib 1}
   accessEquipmentConfig OBJECT IDENTIFIER   ::= {megacoMib 2}
   accessTerminationConfig OBJECT IDENTIFIER ::= {megacoMib 3}
   ivpsConfig OBJECT IDENTIFIER              ::= {megacoMib 4}
   signallingGatewayInterfaceConfig OBJECT IDENTIFIER      ::= {megacoMib 5}   
   ltLineTest OBJECT IDENTIFIER              ::= {megacoMib 6}
   -- *****************************************************************
   -- Textual conventions for the Media Gateway MIB
   -- *****************************************************************
   -- MediaGatewayId ::= TEXTUAL-CONVENTION
   -- DISPLAY-HINT "d"
   -- DESCRIPTION "Internal media gateway Id that can be used to identify
   -- any media gateway uniquely within this IVPS."
   -- SYNTAX INTEGER (1..2147483647)
   MediaGatewayId ::= INTEGER (1..2147483647)

   -- AccessEquipmentId ::= TEXTUAL-CONVENTION
   -- DISPLAY-HINT "d"
   -- DESCRIPTION "Internal ISAM-V Id that can be used to identify
   -- any access NE uniquely within this IVPS."
   -- SYNTAX INTEGER (1..2147483647)
   AccessEquipmentId ::= INTEGER (1..255)
   
   -- AccessBoardId ::= TEXTUAL-CONVENTION
   -- DISPLAY-HINT "d"
   -- DESCRIPTION "Slot identifier composed of the rack number (4 bits),
   -- subrack number (4 bits) and slot number (8 bits)."
   -- SYNTAX INTEGER (1..65535)
   AccessBoardId ::= INTEGER (1..65535)
   
   -- TerminationUserPortId ::= TEXTUAL-CONVENTION
   -- DISPLAY-HINT "d"
   -- DESCRIPTION "User Port identifier composed of the rack number
   -- (4 bits), subrack number (4 bits), slot number
   -- (8 bits) and port number (16 bits)."
   -- SYNTAX INTEGER (1..2147483647)
   TerminationUserPortId ::= INTEGER (1..2147483647)
   
   -- AccessTerminationId ::= TEXTUAL-CONVENTION
   -- DISPLAY-HINT "d"
   -- DESCRIPTION "Possible termination Id that can be used to identify
   -- any access termination uniquely."
   -- SYNTAX INTEGER (1..2147483647)
   AccessTerminationId ::= INTEGER (0..2147483647)

   -- SignallingGatewayInterfaceId ::= TEXTUAL-CONVENTION
   -- DISPLAY-HINT "d"
   -- DESCRIPTION "Internal signalling gateway Id that can be used to identify
   -- any signalling gateway uniquely within this MGI."
   -- SYNTAX INTEGER (1..2147483647)
   SignallingGatewayInterfaceId ::= INTEGER (1..2147483647)   
   
   MedGwyEventListType ::= OCTET STRING (SIZE (8))
   
   -- *****************************************************************
   -- mediaGatewayTable
   -- *****************************************************************
   mediaGatewayTable OBJECT-TYPE
      SYNTAX SEQUENCE OF MediaGatewayEntry
      ACCESS not-accessible
      STATUS mandatory
      DESCRIPTION "List of gateways configured for this IVPS."
   ::= {mediaGatewayConfig 1}

   -- *****************************************************************
   -- mediaGatewayEntry
   -- *****************************************************************
   mediaGatewayEntry OBJECT-TYPE
      SYNTAX MediaGatewayEntry
      ACCESS not-accessible
      STATUS mandatory
      DESCRIPTION "Entry holding configuration information for a gateway."
      INDEX {mediaGatewayId}
   ::= {mediaGatewayTable 1}
   
   MediaGatewayEntry ::= SEQUENCE
   {
      mediaGatewayId MediaGatewayId, -- na
      mediaGatewayRowStatus RowStatus, -- rw
      mediaGatewayName DisplayString, -- rw
      mediaGatewayOperStatus INTEGER, -- ro
      mediaGatewayAdminStatus INTEGER, -- rw
      mediaGatewayIPAddress IpAddress, -- rw
      mediaGatewayUDPPort INTEGER, -- rw
      mediaGatewaySubnetMask IpAddress, -- rw
      mediaGatewayNextHop IpAddress, -- rw
      mediaGatewayVLAN INTEGER, -- rw
      medGwyCtrlrCallServerId INTEGER, -- rw
      medGwyCtrlrPrimaryIPAddress IpAddress, -- rw
      medGwyCtrlrPrimaryUDPPort INTEGER, -- rw
      medGwyCtrlrSecondaryIPAddress IpAddress, -- rw
      medGwyCtrlrSecondaryUDPPort INTEGER, -- rw
      medGwyCtrlrActiveAddress INTEGER, -- ro
      mediaGatewaySGI INTEGER, -- ro      
      medGwyCtrlrCallServerType INTEGER, --rw
      mediaGatewayLockType INTEGER, --wo
      mediaGatewayLockDelay INTEGER, --wo
      mediaGatewaySignDscp INTEGER, -- rw
      mediaGatewaySignDot1P INTEGER, -- rw
      mediaGatewayVoiceDscp INTEGER, -- rw
      mediaGatewayVoiceDot1P INTEGER, -- rw
      mediaGatewayMidType INTEGER, -- rw
      mediaGatewayDomainName DisplayString, -- rw
      mediaGatewaySVCReasonFormat INTEGER, -- rw
      mediaGatewayProfileName DisplayString, -- rw
      medGwyCtrlrTertiaryIPAddress IpAddress, -- rw
      medGwyCtrlrTertiaryUDPPort INTEGER, -- rw      
      medGwyCtrlrQuaternaryIPAddress IpAddress, -- rw
      medGwyCtrlrQuaternaryUDPPort INTEGER, -- rw
      medGwyCtrlrESAMgcIPAddress IpAddress, -- ro
      medGwyCtrlrESAMgcUDPPort INTEGER, -- ro
      mediaGatewayESAMgcService INTEGER, -- rw
      mediaGatewayTriggerESAMgc INTEGER, -- wo
      medGwyIPConfigMode INTEGER -- rw	  
   }
   
   mediaGatewayId OBJECT-TYPE
      SYNTAX MediaGatewayId
      ACCESS not-accessible
      STATUS mandatory
      DESCRIPTION "The unique media gateway Id which identifies this
                   media gateway."
   ::= {mediaGatewayEntry 1}
   
   mediaGatewayRowStatus OBJECT-TYPE
      SYNTAX RowStatus
      ACCESS read-write
      STATUS mandatory
      DESCRIPTION "Allows to control the creation and deletion
                   of rows in this table."
   ::= {mediaGatewayEntry 2}

   mediaGatewayName OBJECT-TYPE
      SYNTAX DisplayString
      ACCESS read-write
      STATUS mandatory
      DESCRIPTION "Name for this media gateway.The max number of the string is 64. This parameter will be used for MG mid when mediaGatewayMidType select device-name. Only '*','/','_','$','@','ALPHA','DIGIT', '-', '.' are valid for device-name. 
                      ALCATEL NOTE:
                      SUPPORT:        YES
                      PERSIST:        YES
                      INSRVMOD:       NA
                      RANGE:  NA
                      DEFVALUE:  'AG'
                      UNITS:  NA"
      DEFVAL {"AG"}
   ::= {mediaGatewayEntry 3}
   
   mediaGatewayOperStatus OBJECT-TYPE
      SYNTAX INTEGER
      {
         up (1), -- ready to communicate with MGC
         down (2), -- the mgi can not communicate with MGC
         shuttingdown (3) --the shuttingdown state
      }
      ACCESS read-only
      STATUS mandatory
      DESCRIPTION "The current operational state of the gateway."
   ::= {mediaGatewayEntry 4}
   
   mediaGatewayAdminStatus OBJECT-TYPE
      SYNTAX INTEGER
      {
         locked (1),
         unlocked (2)
      }
      ACCESS read-write
      STATUS mandatory
      DESCRIPTION "The current administrative state of the gateway."
      DEFVAL {locked}
   ::= {mediaGatewayEntry 5}
   
   mediaGatewayIPAddress OBJECT-TYPE
      SYNTAX IpAddress
      ACCESS read-write
      STATUS mandatory
      DESCRIPTION "IP address for this media gateway.If the medGwyIPConfigMode is DHCP, it is optional; If the medGwyIPConfigMode is MANUAL, it is mandatory."
      DEFVAL {'00000000'H} 
   ::= {mediaGatewayEntry 6}
   
   mediaGatewayUDPPort OBJECT-TYPE
      SYNTAX INTEGER (1025..65534)
      ACCESS read-write
      STATUS mandatory
      DESCRIPTION "UDP port for this media gateway."
      DEFVAL {2944}
   ::= {mediaGatewayEntry 7}
   
   mediaGatewaySubnetMask OBJECT-TYPE
      SYNTAX IpAddress
      ACCESS read-write
      STATUS mandatory
      DESCRIPTION "Subnet mask for this media gateway.If the medGwyIPConfigMode is DHCP, it is optional; If the medGwyIPConfigMode is MANUAL, it is mandatory."
      DEFVAL {'00000000'H}
   ::= {mediaGatewayEntry 8}
   
   mediaGatewayNextHop OBJECT-TYPE
      SYNTAX IpAddress
      ACCESS read-write
      STATUS mandatory
      DESCRIPTION "IP address for the next routing hop in this media gateway.If the medGwyIPConfigMode is DHCP, it is optional; If the medGwyIPConfigMode is MANUAL, it is mandatory."
      DEFVAL {'00000000'H}
   ::= {mediaGatewayEntry 9}
   
   mediaGatewayVLAN OBJECT-TYPE
      SYNTAX INTEGER (1..4093)
      ACCESS read-write
      STATUS mandatory
      DESCRIPTION "VLAN for this media gateway."
   ::= {mediaGatewayEntry 10}
   
   medGwyCtrlrCallServerId OBJECT-TYPE
      SYNTAX INTEGER (0..2147483647)
      ACCESS read-write
      STATUS mandatory
      DESCRIPTION "Identifier of the peer call server."
      DEFVAL {0}
   ::= {mediaGatewayEntry 11}
   
   medGwyCtrlrPrimaryIPAddress OBJECT-TYPE
      SYNTAX IpAddress
      ACCESS read-write
      STATUS mandatory
      DESCRIPTION "Primary IP address of the media gateway controller."
   ::= {mediaGatewayEntry 12}
   
   medGwyCtrlrPrimaryUDPPort OBJECT-TYPE
      SYNTAX INTEGER (1..65534)
      ACCESS read-write
      STATUS mandatory
      DESCRIPTION "Primary UDP port of the media gateway controller."
      DEFVAL {2944}
   ::= {mediaGatewayEntry 13}
   
   medGwyCtrlrSecondaryIPAddress OBJECT-TYPE
      SYNTAX IpAddress
      ACCESS read-write
      STATUS mandatory
      DESCRIPTION "Secondary IP address of the media gateway controller."
      DEFVAL {'00000000'H}
   ::= {mediaGatewayEntry 14}
   
   medGwyCtrlrSecondaryUDPPort OBJECT-TYPE
      SYNTAX INTEGER (1..65534)
      ACCESS read-write
      STATUS mandatory
      DESCRIPTION "Secondary UDP port of the media gateway controller."
      DEFVAL {2944}
   ::= {mediaGatewayEntry 15}
   
   medGwyCtrlrActiveAddress OBJECT-TYPE
      SYNTAX INTEGER
      {
         primary (1),
         secondary (2),
         none(3),
         other(4),
         tertiary(5),
         quaternary(6),
         emergencystandalone(7)
      }
      ACCESS read-only
      STATUS mandatory
      DESCRIPTION "Indicates which is the curretly active address
                   for the associated media gateway controller."
      DEFVAL {primary}
   ::= {mediaGatewayEntry 16}

   mediaGatewaySGI OBJECT-TYPE
      SYNTAX INTEGER (0..2147483647)
      ACCESS read-only
      STATUS mandatory
      DESCRIPTION "The ISDN unique signalling gateway Id which identifies this
                   media gateway, 0 indicates there is no sgi is configured"
   ::= {mediaGatewayEntry 17}
   
   medGwyCtrlrCallServerType OBJECT-TYPE
      SYNTAX INTEGER {
                       general(1),
                       lucent-fs5000 (2),
                       alcatel-a5020 (3),
                       alcatel-e10 (4),
                       zte-zxss(5), 
                       hw-soft3000(6),
                       siemens(7),
                       nortel(8),
                       ericsson(9),
                       meta-softswitch(10),
		       italtel(11),
                       comverse(12),
                       g6-gr303(13),
		       other-vendor3(14),
		       other-vendor4(15),
                       other-vendor16(16),
		       other-vendor17(17) 
		     }
      ACCESS read-write
      STATUS mandatory
        DESCRIPTION " The vendor type  of MGC server. It is accessed by CLI/T&D command and NOT displayed on GUI.  
                    ALCATEL NOTE:
                      SUPPORT:        YES
                      PERSIST:        YES
                      INSRVMOD:       NO
                      RANGE:  1 | 2 | 3 |4 |5 |6 |7 |8 |9 |10 |11 |12 |13 |14 |15 |16 |17
                      DEFVALUE:       general(1)
                      UNITS:  NA                              
                   "
      DEFVAL { general }
    ::= { mediaGatewayEntry 18 }

   mediaGatewayLockType	OBJECT-TYPE
	SYNTAX	INTEGER
	{
	  force(1),  -- the forced lock type
	  graceful(2)  --the graceful lock type
	}
	ACCESS	write-only
	STATUS	mandatory
	DESCRIPTION	"The Type of the lock command.
	Should be set ONLY if the AdminStatus is locked.	
	ALCATEL NOTE 
	ACCESS: WO
	USAGE: MAN 
	PERSIST: NO 
	INSRVMOD: NO 
	RANGE: force or graceful 
	DEFVALUE: NO 
	UNITS: NA 
	SPARSE: NO 
	DESCR: NA "
	DEFVAL {force}
    ::= {mediaGatewayEntry 19}

   mediaGatewayLockDelay	OBJECT-TYPE
	SYNTAX	INTEGER (0..3600000)
	ACCESS	write-only
	STATUS	mandatory
	DESCRIPTION	"The Timer of the lock command , the unit is milliseconds.
		ALCATEL NOTE 
		ACCESS: WO 
		USAGE: MAN 
		PERSIST: NO 
		INSRVMOD: NO 
		RANGE: From 0 to 3600000 
		DEFVALUE: 0 
		UNITS: MILLISECOND 
		SPARSE: NO 
		DESCR: NA "
	DEFVAL {0}
    ::= {mediaGatewayEntry 20}

   mediaGatewaySignDscp OBJECT-TYPE
      SYNTAX INTEGER (0..63)
      ACCESS read-write
      STATUS mandatory
      DESCRIPTION "Signaling DSCP for this media gateway."
      DEFVAL {0}
   ::= {mediaGatewayEntry 21}

   mediaGatewaySignDot1P OBJECT-TYPE
      SYNTAX INTEGER (0..7)
      ACCESS read-write
      STATUS mandatory
      DESCRIPTION "Signaling P-bit for this media gateway."
      DEFVAL {0}	
   ::= {mediaGatewayEntry 22}

   mediaGatewayVoiceDscp OBJECT-TYPE
      SYNTAX INTEGER (0..63)
      ACCESS read-write
      STATUS mandatory
      DESCRIPTION "Voice DSCP for this media gateway."
      DEFVAL {0}
   ::= {mediaGatewayEntry 23}

   mediaGatewayVoiceDot1P OBJECT-TYPE
      SYNTAX INTEGER (0..7)
      ACCESS read-write
      STATUS mandatory
      DESCRIPTION "Voice P-bit for this media gateway."
      DEFVAL {0}
   ::= {mediaGatewayEntry 24}

   mediaGatewayMidType OBJECT-TYPE
      SYNTAX INTEGER {
                       ipv4 (1),
                       ipv4-port (2),
                       domain-name (3),
                       domain-name-port (4),
                       device-name (5)
                     }
      ACCESS read-write
      STATUS mandatory
      DESCRIPTION " The mid type  of MG. If ipv4 is selected, the mediaGatewayIPAddress will be used for the MG mid; If ipv4-port is selected, the mediaGatewayIPAddress+mediaGatewayUDPPort will be used for the MG mid; If domain-name is selected, the mediaGatewayDomainName will be used to support MG mid; If domain-name-port is selected, the mediaGatewayDomainName+mediaGatewayUDPPort will be used to support MG mid; if device-name is selected, the mediaGatewayName will be used for MG mid.
                    ALCATEL NOTE:
                      SUPPORT:        YES
                      PERSIST:        YES
                      INSRVMOD:       NO
                      RANGE:  1 | 2 | 3 | 4 |5
                      DEFVALUE:       ipv4-port(2)
                      UNITS:  NA
                   "
      DEFVAL { ipv4-port }
    ::= { mediaGatewayEntry 25 }
    
   mediaGatewayDomainName OBJECT-TYPE
      SYNTAX DisplayString
      ACCESS read-write
      STATUS mandatory
      DESCRIPTION "Domain Name of this media gateway. Only 'ALPHA','DIGIT', '-', '.', '@' are valid for domainName. The max number of the string is 255. If address-type select domain-name, this parameter will be used for MG mid. 
                      ALCATEL NOTE:
                      SUPPORT:        YES
                      PERSIST:        YES
                      INSRVMOD:       NO
                      RANGE:  SIZE(1..255) 
                      DEFVALUE: 'isamv.alcatel-lucent.com' 
                      UNITS:  NA"
      DEFVAL {"isamv.alcatel-lucent.com"}
   ::= {mediaGatewayEntry 26}

   mediaGatewaySVCReasonFormat OBJECT-TYPE
      SYNTAX INTEGER {
      with-quotation (1),
      without-quotation (2)
      }
      ACCESS read-write
      STATUS mandatory
      DESCRIPTION " The format of reason, which used in H248 service change.
                     ALCATEL NOTE:
                     SUPPORT: YES
                     PERSIST: YES
                     INSRVMOD: NO
                     RANGE: 1 | 2
                     DEFVALUE: with-quotation (1)
                     UNITS: NA"
      DEFVAL { with-quotation }
   ::= { mediaGatewayEntry 27 }
    
   mediaGatewayProfileName OBJECT-TYPE
      SYNTAX DisplayString
      ACCESS read-write
      STATUS mandatory
      DESCRIPTION "Profile Name of this media gateway. Which used in H248 message service change. The max number of the string is 64.
                     ALCATEL NOTE:
                     SUPPORT: YES
                     PERSIST: YES
                     INSRVMOD: NO
                     RANGE: SIZE(1..64)
                     DEFVALUE: 'AGW'
                     UNITS: NA"
      DEFVAL {"AGW"}
   ::= { mediaGatewayEntry 28 }   

      medGwyCtrlrTertiaryIPAddress OBJECT-TYPE
      SYNTAX IpAddress
      ACCESS read-write
      STATUS mandatory
      DESCRIPTION " Tertiary IP address of the media gateway controller."
      DEFVAL {'00000000'H}
   ::= {mediaGatewayEntry 29}
   
   medGwyCtrlrTertiaryUDPPort OBJECT-TYPE
      SYNTAX INTEGER (1..65534)
      ACCESS read-write
      STATUS mandatory
      DESCRIPTION "Tertiary UDP port of the media gateway controller."
      DEFVAL {2944}
   ::= {mediaGatewayEntry 30}

   medGwyCtrlrQuaternaryIPAddress OBJECT-TYPE
      SYNTAX IpAddress
      ACCESS read-write
      STATUS mandatory
      DESCRIPTION " IP Address of the quaternary media gateway controller."
      DEFVAL {'00000000'H}
   ::= {mediaGatewayEntry 31}
   
   medGwyCtrlrQuaternaryUDPPort OBJECT-TYPE
      SYNTAX INTEGER (1..65534)
      ACCESS read-write
      STATUS mandatory
      DESCRIPTION "UDP port of the quaternary media gateway controller."
      DEFVAL {2944}
   ::= {mediaGatewayEntry 32}
 
   medGwyCtrlrESAMgcIPAddress OBJECT-TYPE
      SYNTAX IpAddress
      ACCESS read-only
      STATUS mandatory
      DESCRIPTION "IP address of the local ESA media gateway controller.
                   In case the ESA MGC service is enabled, the ESA MGC will own the same IP@ as the IP@
                   configured for the Media Gateway (mediaGatewayIPAddress).
                   Thus when the ESA MGC service is enabled, this object will show the same IP@ as the
                   IP@ configured for the media gateway.
				   In case the ESA MGC service is disabled, this object will show the IP@ = 0.0.0.0.
                       - 7302/7330 ISAM-V : Supported 
 	               - 7363 ISAM MX : Not Applicable 
	               - 7367 ISAM SX-12VP : Not Applicable
                   ALCATEL-LUCENT NOTE:
                   ACCESS:   READ-ONLY
                   USAGE:    NA
                   PERSIST:  NO
    		       INSRVMOD: NA
                   RANGE:    NA
                   DEFVALUE: NA
                   UNITS:    NA
                   SPARSE:   NO "
   ::= {mediaGatewayEntry 33}

   medGwyCtrlrESAMgcUDPPort OBJECT-TYPE
      SYNTAX INTEGER (0..65535)
      ACCESS read-only
      STATUS mandatory
      DESCRIPTION "UDP port of the local ESA media gateway controller.
                   The ESA MGC UDP port MUST be different from the UDP Port configured for the Media Gateway
                   (mediaGatewayUDPPort). In case the ESA MGC service is enabled, the ESA MGC will own the UDP
                   port 65534. Thus when the ESA MGC service is enabled, this object will show the UDP port = 65534.
                   In case the ESA MGC service is disabled, this object will show the UDP port = 0
                       - 7302/7330 ISAM-V : Supported
                       - 7363 ISAM MX : Not Applicable
                       - 7367 ISAM SX-12VP : Not Applicable
                   ALCATEL-LUCENT NOTE:
                   ACCESS:   READ-ONLY
                   USAGE:    NA
                   PERSIST:  NA
                   INSRVMOD: NA
                   RANGE:    NA
                   DEFVALUE: NA
                   UNITS:    NA
                   SPARSE:   NO "
   ::= {mediaGatewayEntry 34}

   mediaGatewayESAMgcService OBJECT-TYPE
      SYNTAX INTEGER
      {
         enable(1),
         disable(2)
      }
      ACCESS read-write
      STATUS mandatory
      DESCRIPTION "Allows to enable/disable the local ESA mgc feature for this MG.
                       - 7302/7330 ISAM-V : Supported
                       - 7363 ISAM MX : Not Applicable
                       - 7367 ISAM SX-12VP : Not Applicable
                   . "
      DEFVAL {disable}
   ::= {mediaGatewayEntry 35}

   mediaGatewayTriggerESAMgc OBJECT-TYPE
      SYNTAX INTEGER
      {
         failover(1),
         failback(2)
      }
      ACCESS write-only
      STATUS mandatory
      DESCRIPTION "Allows to manually failover to local ESA mgc or failback to external normal mgc for this MG.
                   Only allowed when mediaGatewayESAMgcService is enabled.
                       - 7302/7330 ISAM-V : Supported
                       - 7363 ISAM MX : Not Applicable
                       - 7367 ISAM SX-12VP : Not Applicable
                   . "
   ::= {mediaGatewayEntry 36}
   
   medGwyIPConfigMode OBJECT-TYPE
        SYNTAX  INTEGER
        {
         dhcp(1),
         manual(2)        
        } 
      ACCESS read-write        
      STATUS mandatory        
      DESCRIPTION " The configure mode of the IP addresses.         
      ALCATEL NOTE        
      ACCESS: RW         
      USAGE: MAN        
      PERSIST: YES        
      INSRVMOD: NO        
      RANGE: 1 | 2        
      DEFVALUE: manual(2)        
      UNITS: NA        
      SPARSE: NO        
      DESCR: NA "   
      ::= {mediaGatewayEntry  37}


   -- *****************************************************************
   -- mediaGatewayNextId
   -- *****************************************************************
   mediaGatewayNextId OBJECT-TYPE
      SYNTAX TestAndIncr
      ACCESS read-only
      STATUS mandatory
      DESCRIPTION "Next free identifier for a new mediaGatewayEntry."
   ::= {mediaGatewayConfig 2}

   medGwyMegacoExtTable OBJECT-TYPE 
	SYNTAX SEQUENCE OF MedGwyMegacoExtEntry 
	ACCESS not-accessible 
	STATUS mandatory 
	DESCRIPTION "The megaco service extension of mediaGatewayTable.
		ALCATEL NOTE 
		ACCESS: NA 
		USAGE: MAN 
		PERSIST: YES 
		INSRVMOD: NO 
		RANGE: NA 
		DEFVALUE: NA 
		UNITS: NA 
		SPARSE: NO 
		DESCR: NA ." 
    ::= {mediaGatewayConfig 3} 

   medGwyMegacoExtEntry OBJECT-TYPE 
	SYNTAX MedGwyMegacoExtEntry 
	ACCESS not-accessible 
	STATUS mandatory 
	DESCRIPTION "An entry containing megaco service configuration information of a media gateway interface. 
		ALCATEL NOTE 
		ACCESS: NA 
		USAGE: MAN 
		PERSIST: YES 
		INSRVMOD: NO 
		RANGE: NA 
		DEFVALUE: NA 
		UNITS: NA 
		SPARSE: NO 
		DESCR: NA " 
	INDEX {mediaGatewayId} 
    ::= {medGwyMegacoExtTable 1} 

   MedGwyMegacoExtEntry ::= SEQUENCE 
   { 
	medGwyTermFormatType INTEGER, --rw 
	medGwyPstnTermFormatStr DisplayString, --rw 
	medGwyIsdnTermFormatStr DisplayString, --rw 
	medGwyIsdnSuffix1Str DisplayString,   --rw
	medGwyIsdnSuffix2Str DisplayString,   --rw
	medGwyTMAX INTEGER, --rw 
	medGwyMaxNetworkDelay INTEGER, --rw 
	medGwyMaxTransRetransmission INTEGER, --rw 
	medGwyReduceBatteryDelay INTEGER, --rw 
	medGwyReleaseDelay INTEGER, --rw 
	medGwyGracefulWaitingReleaseDelay INTEGER,  --rw
	medGwyActiveHeartbeatMode INTEGER, --rw 
	medGwyActiveHeartbeatInterval INTEGER, --rw 
	medGwyPassiveHeartbeatMode INTEGER, --rw 
	medGwyPassiveHeartbeatInterval INTEGER, --rw 
	medGwyRetransmissionMode INTEGER, --rw
	medGwyRetransmissionInterval INTEGER, --rw
	medGwyMaxWaitingDelay    INTEGER,  --rw
	medGwyProvisionalResponse  INTEGER, --rw 
	medGwyEventRequestID INTEGER, --rw
	medGwyEventList MedGwyEventListType, --rw 
	medGwyRfc2833PayloadType  INTEGER, --rw
	medGwyRfc2833Processing INTEGER, --rw 
	medGwyDialingStartTimer  INTEGER, --rw
	medGwyDialingLongTimer INTEGER, --rw 
	medGwyDialingShortTimer  INTEGER, --rw
	medGwyMinDataJitterBuffer INTEGER, --rw 
	medGwyInitDataJitterBuffer  INTEGER, --rw
	medGwyMaxDataJitterBuffer INTEGER, --rw 
	medGwyEphemeralTermPrefix  DisplayString, --rw
	medGwyEphemeralTermMin Gauge, --rw 
	medGwyEphemeralTermMax Gauge, --rw 
	medGwyReleaseType  INTEGER,  --rw
	medGwyIPDhcpv4Option60 DisplayString -- rw

   } 

   medGwyTermFormatType OBJECT-TYPE 
	SYNTAX INTEGER 
	{ 
	  hierarchy (1), --the hierarchy format type 
	  flat (2) --the flat format type 
	} 
	ACCESS read-write 
	STATUS mandatory 
	DESCRIPTION "The termination ID format type of the MGI.
		ALCATEL NOTE 
	ACCESS: RW 
	USAGE: MAN 
	PERSIST: YES 
	INSRVMOD: NO 
	RANGE: NA 
	DEFVALUE: flat(2)
	UNITS: NA 
	SPARSE: NO 
	DESCR: NA " 
   ::= {medGwyMegacoExtEntry 1} 

   medGwyPstnTermFormatStr OBJECT-TYPE 
	SYNTAX DisplayString 
	ACCESS read-write 
	STATUS mandatory 
	DESCRIPTION "The termination ID format pattern of PSTN user, 
        In case the termination ID type is hierarchical, the termination ID shall be configured based on the following format:
        [prefix][['Dslam_Id'][delim]][['rack'][format][delim]]'shelf'[format][delim]'slot'[format][delim] 'port'[format]
		where:
        [] = optional.
        [prefix]: The prefix is a string constructed by characters, numbers and some special characters. The character can be uppercase as well as lower case and the special character should be valid MEGACO character which  include '_', '/', '.', '*', '@', '$' and '-'. The maximum length is 10.
        The maximum length of the full hierarchical termination ID string equals 72 bytes.
        Key-words: Dslam_Id (optional), rack (optional), shelf (mandatory), slot (mandatory), port (mandatory).
        The sequence of the key-words as shown in the typical format string must be respected.
        A key-word can only occur once in the hierarchical termination ID character string.
        '/'defined as the default delimiter
        Delimiter can be any valid character, special character or string not overlapping with any of the key-words.
        The delimiter is copied to the generated termination ID.
        [format]: Each key-word can be followed by a number of numeric digits with the maximum number of digits = 5. Leading zeros are to be included where needed.
        At least one of the delimiter and the format must be presenting after each key-word(exclude 'Dslam_Id').
        The number of digits and the value of the digits configured in the format string define the minimum number of digits to be generated (might require leading zeros).
        No digits being present in the configured syntax means that no format needs to be applied.
        The real value of the hierarchical termination id will autonomously be generated by the system based on the configured hierarchical termination id format string.
        SHARED Lines : For the prime termination the key-word 'port' is substituted by the real port id, while for the secondary termination (connected to that same port), the key-word 'port' is substituted by a virtual port id.
        For the 72 lines LT board the virtual port id ranges from 73 up to 144, while for the 48 lines LT board the virtual port id ranges from 49 up to 96.
        For the 72 lines LT board, if the real port id of a termination is X then the virtual port id of the secondary termination connected to that same real port id X equals X+72.
        Similar for the 48 lines LT board, if the real port id of a termination is X then the virtual port id of the secondary termination connected to that same real port id X equals X+48.

     Some examples:
        AL/Dslam_Id/rack/shelf/slot/port (FOR nod01/1/1/1/1) - AL/nod01/1/1/1/1
        AL/Dslam_Id/shelf/slot/port (FOR nod01/1/1/1/1) - AL/nod01/1/1/1
        AL/rack/shelf/slot/port (FOR nod01/1/1/1/1) - AL/1/1/1/1
        AL/rack0/shelf0/slot0/port00 (FOR nod01/1/1/1/1) - AL/1/1/1/01
        ALDslam_Idrack0shelf0slot0port00 (FOR nod01/1/1/1/1) - ALnod0111101
        ALDslam_Idrack0shelf0slot0port0 (FOR nod01/1/1/1/12) - ALnod0111112

        If the termid-type is flat,It should be a string constructed according to the following rule: 
        [prefix]['<tid'[formater]'>']: 
        prefix is a string construct by any character that is valid for MEGACO termination id. 
        formater is a format string to indicate how ISAMV should format the id right before it. 
        It must be constructed by zero or at most five digits. The number of digits indicat the minimum width of the id in the termination id,If contains no digit, it indicat that no format need to be applied. 
        For example: 
        format string port position termination id 
        (termination-id) 
        AL/0 AL/0 
        AL0 AL0 
        AL<tid000> 0 AL000 
        AL<tid000> 888 AL888

		ALCATEL NOTE 
		ACCESS: RW 
		USAGE: MAN 
		PERSIST: YES 
		INSRVMOD: NO 
		RANGE: NA 
		DEFVALUE: 'AL' 
		UNITS: NA 
		SPARSE: NO 
		DESCR: NA " 
   ::= {medGwyMegacoExtEntry 2} 

   medGwyIsdnTermFormatStr OBJECT-TYPE 
	SYNTAX DisplayString 
	ACCESS read-write 
	STATUS mandatory 
	DESCRIPTION "The termination ID format pattern of ISDN user, 
        In case the termination ID type is hierarchical, the termination ID shall be configured based on the following format:
        [prefix][['Dslam_Id'][delim]][['rack'][format][delim]]'shelf'[format][delim]'slot'[format][delim] 'port' [format] [delim]]'channel'
		where:
        [] = optional.
        [prefix]: The prefix is a string constructed by characters, numbers and some special characters. The character can be uppercase as well as lower case and the special character should be valid MEGACO character which  include '_', '/', '.', '*', '@', '$' and '-'. The maximum length is 10.
        The maximum length of the full hierarchical termination ID string equals 72 bytes.
        Key-words: Dslam_Id (optional), rack (optional), shelf (mandatory), slot (mandatory), port (mandatory),channel(mandatory).
        The sequence of the key-words as shown in the typical format string must be respected.
        A key-word can only occur once in the hierarchical termination ID character string.
        '/'defined as the default delimiter
        Delimiter can be any valid character, special character or string not overlapping with any of the key-words.
        The delimiter is copied to the generated termination ID.
        [format]: Each key-word can be followed by a number of numeric digits with the maximum number of digits = 5. Leading zeros are to be included where needed.
        At least one of the delimiter and the format must be presenting after each key-word(exclude 'Dslam_Id').
        The number of digits and the value of the digits configured in the format string define the minimum number of digits to be generated (might require leading zeros).
        No digits being present in the configured syntax means that no format needs to be applied. 
        The real value of the hierarchical termination id will autonomously be generated by the system based on the configured hierarchical termination id format string.
        Some examples:
        BA/Dslam_Id/rack/shelf/slot/port/channel (FOR nod01/1/1/1/1) - BA/nod01/1/1/1/1
        BA/Dslam_Id/shelf/slot/port/channel (FOR nod01/1/1/1/1) - BA/nod01/1/1/1
        BA/rack/shelf/slot/port/channel (FOR nod01/1/1/1/1) - BA/1/1/1/1/B1
        BA/rack0/shelf0/slot0/port00/channel (FOR nod01/1/1/1/1) - BA/1/1/1/01
        BADslam_Idrack0shelf0slot0port00/channel (FOR nod01/1/1/1/1) - BAnod0111101
        BADslam_Idrack0shelf0slot0port0/channel (FOR nod01/1/1/1/12) - BAnod0111112

        If the termid-type is flat,It should be a string constructed according to the following rule: 
        [prefix]['<tid'[formater]'>']: 
        prefix is a string construct by any character that is valid for MEGACO termination id. 
        formater is a format string to indicate how ISAMV should format the id right before it. 
        It must be constructed by zero or at most five digits. The number of digits indicat the minimum width of the id in the termination id,If contains no digit, it indicat that no format need to be applied. ISDN termination id should not be zero because zero is reserved for special use of IID. 
		for example: 
        format string port position termination id 
        (termination-id) 
        BA/1 BA/1 
        BA1  BA1
        BA<tid000> 0 BA001
        BA<tid000> 888 BA888

		ALCATEL NOTE 
		ACCESS: NA 
		USAGE: MAN 
		PERSIST: YES 
		INSRVMOD: NO 
		RANGE: NA 
		DEFVALUE: Get from CDE File or DataBase
		UNITS: NA 
		SPARSE: NO 
		DESCR: NA " 
   ::= {medGwyMegacoExtEntry 3} 

   medGwyIsdnSuffix1Str	OBJECT-TYPE
	SYNTAX	DisplayString
	ACCESS	read-write
	STATUS	mandatory
	DESCRIPTION "The suffix1 of the ISDN User Termination Format,
		It represents the channel of the ISDN User. 
		The max length of the ISDN Suffix1 is about 8.
		ALCATEL NOTE 
		ACCESS: RW 
		USAGE: MAN 
		PERSIST: YES 
		INSRVMOD: NO 
		RANGE: NA 
		DEFVALUE: Get from CDE File 
		UNITS: NA 
		SPARSE: NO 
		DESCR: NA ."
   ::= {medGwyMegacoExtEntry 4}

   medGwyIsdnSuffix2Str	OBJECT-TYPE
	SYNTAX	DisplayString
	ACCESS	read-write
	STATUS	mandatory
	DESCRIPTION "The suffix2 of the ISDN User Termination Format,
	It represents the channel of the ISDN User.
	The max length of the ISDN Suffix2 is about 8.	
	ALCATEL NOTE 
	ACCESS: RW 
	USAGE: MAN 
	PERSIST: YES 
	INSRVMOD: NO 
	RANGE: NA 
	DEFVALUE: Get from CDE File 
	UNITS: NA 
	SPARSE: NO 
	DESCR: NA  "
   ::= {medGwyMegacoExtEntry 5}

   medGwyTMAX OBJECT-TYPE 
	SYNTAX INTEGER (1000..30000)
	ACCESS read-write 
	STATUS mandatory 
	DESCRIPTION "The max time of MGC handling the transaction. The unit is millisecond.
	ALCATEL NOTE 
	ACCESS: RW 
	USAGE: MAN 
	PERSIST: YES 
	INSRVMOD: NO 
	RANGE: From 1000 to 30000
	DEFVALUE: 16000 
	UNITS: MILLISECOND 
	SPARSE: NO 
	DESCR: NA " 
	DEFVAL {16000} 
   ::= {medGwyMegacoExtEntry 6} 

   medGwyMaxNetworkDelay OBJECT-TYPE 
	SYNTAX INTEGER (100..1000)
	ACCESS read-write 
	STATUS mandatory 
	DESCRIPTION "The max network delay time. The unit is millisecond.
		ALCATEL NOTE 
		ACCESS: RW 
		USAGE: MAN 
		PERSIST: YES 
		INSRVMOD: NO 
		RANGE: From 100 to 1000 
		DEFVALUE: 500 
		UNITS: MILLISECOND 
		SPARSE: NO 
		DESCR: NA " 
	DEFVAL {500} 
   ::= {medGwyMegacoExtEntry 7} 

   medGwyMaxTransRetransmission OBJECT-TYPE 
	SYNTAX INTEGER (7..11)
	ACCESS read-write 
	STATUS mandatory 
	DESCRIPTION "The max retransimit times of the transaction. The unit is times.
		ALCATEL NOTE 
		ACCESS: RW 
		USAGE: MAN 
		PERSIST: YES 
		INSRVMOD: NO 
		RANGE: From 7 To 11 
		DEFVALUE: 7 
		UNITS: TIMES 
		SPARSE: NO 
		DESCR: NA " 
	DEFVAL {7} 
   ::= {medGwyMegacoExtEntry 8} 

   medGwyReduceBatteryDelay OBJECT-TYPE 
	SYNTAX INTEGER (0..120000)
	ACCESS read-write 
	STATUS mandatory 
	DESCRIPTION "The delay before MGI coming into reduced battery state. The unit is millisecond.
		ALCATEL NOTE 
		ACCESS: RW 
		USAGE: MAN 
		PERSIST: YES 
		INSRVMOD: YES 
		RANGE: From 0 To 120000 
		DEFVALUE: 70000 
		UNITS: MILLISECOND 
		SPARSE: NO 
		DESCR: NA ." 
	DEFVAL {70000} 
   ::= {medGwyMegacoExtEntry 9} 

   medGwyReleaseDelay OBJECT-TYPE 
	SYNTAX INTEGER (0..900000)
	ACCESS read-write 
	STATUS mandatory 
	DESCRIPTION "The delay before MGI releasing all sessions 
		after the connection with MGC lost temporally. The unit is millisecond. 
		ALCATEL NOTE 
		ACCESS: RW 
		USAGE: MAN 
		PERSIST: YES 
		INSRVMOD: YES 
		RANGE: From 0 To 900000 
		DEFVALUE: 600000 
		UNITS: MILLISECOND 
		SPARSE: NO 
		DESCR: NA " 
	DEFVAL {600000} 
::= {medGwyMegacoExtEntry 10} 
 

   medGwyGracefulWaitingReleaseDelay  OBJECT-TYPE
	SYNTAX	INTEGER (0..3600000)
	ACCESS read-write
	STATUS	mandatory
	DESCRIPTION  "The delay after the graceful lock delay timer expired.
		The unit is millisecond. 
		ALCATEL NOTE 
		ACCESS: RW 
		USAGE: MAN 
		PERSIST: YES 
		INSRVMOD: YES 
		RANGE: From 0 To 3600000 
		DEFVALUE: 0 
		UNITS: MILLISECOND 
		SPARSE: NO 
		DESCR: NA "
	DEFVAL	{0}
   ::= {medGwyMegacoExtEntry 11}

   medGwyActiveHeartbeatMode OBJECT-TYPE 
	SYNTAX INTEGER 
	{ 
	  fix (1), 
	  dynamic (2) 
	} 
	ACCESS read-write 
	STATUS mandatory 
	DESCRIPTION "The active heartbeat mode of the MGI.
		ALCATEL NOTE 
		ACCESS: RW 
		USAGE: MAN 
		PERSIST: YES 
		INSRVMOD: YES 
		RANGE: NA 
		DEFVALUE: fix 
		UNITS: NA 
		SPARSE: NO 
		DESCR: NA " 
	DEFVAL {fix} 
   ::= {medGwyMegacoExtEntry 12} 

   medGwyActiveHeartbeatInterval OBJECT-TYPE 
	SYNTAX INTEGER (0..65535)
	ACCESS read-write 
	STATUS mandatory 
	DESCRIPTION "The active heartbeat interval of the MGI, 
		this object is only valid when the medGwActiveHeartbeatMode = fix(1).
		The unit is 10 millisecond.
		ALCATEL NOTE 
		ACCESS: RW 
		USAGE: MAN 
		PERSIST: YES 
		INSRVMOD: YES 
		RANGE: From 0 To 65535 
		DEFVALUE: 0 
		UNITS: 10 MILLISECOND 
		SPARSE: NO 
		DESCR: NA " 
	DEFVAL {0} 
   ::= {medGwyMegacoExtEntry 13} 

   medGwyPassiveHeartbeatMode OBJECT-TYPE 
	SYNTAX INTEGER 
	{ 
	  fix (1), 
	  dynamic (2) 
	} 
	ACCESS read-write 
	STATUS mandatory 
	DESCRIPTION "The passive heartbeat mode of the MGI.
		ALCATEL NOTE 
		ACCESS: RW 
		USAGE: MAN 
		PERSIST: YES 
		INSRVMOD: YES 
		RANGE: NA 
		DEFVALUE: dynamic 
		UNITS: NA 
		SPARSE: NO 
		DESCR: NA " 
	DEFVAL {dynamic} 
   ::= {medGwyMegacoExtEntry 14} 

   medGwyPassiveHeartbeatInterval OBJECT-TYPE 
	SYNTAX INTEGER (0..65535)
	ACCESS read-write 
	STATUS mandatory 
	DESCRIPTION "The passive heartbeat interval of the MGI, 
		this object is only valid when the medGwPassiveHeartbeatMode = fix(1).
		The unit is 10 millisecond. 
		ALCATEL NOTE 
		ACCESS: RW 
		USAGE: MAN 
		PERSIST: YES 
		INSRVMOD: YES 
		RANGE: From 0 To 65535 
		DEFVALUE: 0 
		UNITS: 10 MILLISECOND 
		SPARSE: NO 
		DESCR: NA " 
	DEFVAL {0} 
   ::= {medGwyMegacoExtEntry 15}

   medGwyRetransmissionMode	OBJECT-TYPE
   	SYNTAX	INTEGER
   	{
	  fix (1), 
	  dynamic (2) 
   	}
	ACCESS read-write 
	STATUS mandatory 
	DESCRIPTION "The Retransmission mode of the MGI.
		ALCATEL NOTE 
		ACCESS: RW 
		USAGE: MAN 
		PERSIST: YES 
		INSRVMOD: NO 
		RANGE: NA 
		DEFVALUE: fix 
		UNITS: NA 
		SPARSE: NO 
		DESCR: NA " 
	DEFVAL {fix} 
   ::= {medGwyMegacoExtEntry 16}

   medGwyRetransmissionInterval OBJECT-TYPE 
	SYNTAX INTEGER (100..4000)
	ACCESS read-write 
	STATUS mandatory 
	DESCRIPTION "The Retransmission interval of the MGI, 
		this object is only valid when the medGwyRetransmissionMode = fix(1).
		The unit is millisecond. 
		ALCATEL NOTE 
		ACCESS: RW 
		USAGE: MAN 
		PERSIST: YES 
		INSRVMOD: NO 
		RANGE: From 100 To 4000 
		DEFVALUE: 4000 
		UNITS: MILLISECOND 
		SPARSE: NO 
		DESCR: NA " 
	DEFVAL {4000} 
   ::= {medGwyMegacoExtEntry 17}
   
   medGwyMaxWaitingDelay OBJECT-TYPE 
	SYNTAX INTEGER (0..120)
	ACCESS read-write 
	STATUS mandatory 
	DESCRIPTION "The maximum time that Media Gateway has to wait after a
	             restart before contacting to the Call Server, 
		     The unit is second. 
		ALCATEL NOTE 
		ACCESS: RW 
		USAGE: MAN 
		PERSIST: YES 
		INSRVMOD: NO 
		RANGE: From 0 To 120 
		DEFVALUE: 5 
		UNITS: SECOND 
		SPARSE: NO 
		DESCR: NA " 
	DEFVAL {5} 
   ::= {medGwyMegacoExtEntry 18}
   
   medGwyProvisionalResponse OBJECT-TYPE 
	SYNTAX INTEGER (0..10000)
	ACCESS read-write 
	STATUS mandatory 
	DESCRIPTION "The time need to send a transaction pending since the
        	reception of the transcation.
		The unit is millisecond. 
		ALCATEL NOTE 
		ACCESS: RW 
		USAGE: MAN 
		PERSIST: YES 
		INSRVMOD: NO 
		RANGE: From 0 To 10000 
		DEFVALUE: 1000 
		UNITS: MILLISECOND 
		SPARSE: NO 
		DESCR: NA " 
	DEFVAL {1000} 
   ::= {medGwyMegacoExtEntry 19}
   
   medGwyEventRequestID   OBJECT-TYPE 
	SYNTAX INTEGER (0..65535)
	ACCESS read-write 
	STATUS mandatory 
	DESCRIPTION "The event request identification, it is configured to cater for different MGCs, such as the case that an event is not requested from MGC.
		when this parameter is set, MG will send the event with the configured event request ID. 
		ALCATEL NOTE 
		ACCESS: RW 
		USAGE: MAN 
		PERSIST: YES 
		INSRVMOD: YES
		RANGE: From 0 To 65535 
		DEFVALUE: 0
		UNITS: NA
		SPARSE: NO 
		DESCR: NA "
	DEFVAL {0} 
   ::= {medGwyMegacoExtEntry 20}
	
   medGwyEventList   OBJECT-TYPE 
	SYNTAX MedGwyEventListType
	ACCESS read-write 
	STATUS mandatory 
	DESCRIPTION "This is a bitmap. Each bit represents an event which is supported by MG.
			If a bit is set, the corresponding event is supported. More than one mode can be set simultaneously.
			The respective event types correspond to the following integer values in the bitmap, 
			other bit positions are reserved for future use:
			
			Octet 1 :
				1: indicate stimal/stedsig event
				2: indicate al/of event
				4: indicate al/on event
				8: indicate al/of {strict=state} event
				16: indicate al/on {strict=state} event
				32: indicate ocp/mg_overload event
				64: reserved for future
				128: reserved for future
    Octet 2-7:  Reserved for future use
	 
		ALCATEL NOTE 
		ACCESS: RW
		USAGE: MAN 
		PERSIST: YES 
		INSRVMOD: YES
		RANGE: NA 
		DEFVALUE: NA
		UNITS: NA 
		SPARSE: NO 
		DESCR: NA "
	DEFVAL {'0000000000000000'H } 
   ::= {medGwyMegacoExtEntry 21} 
   
      medGwyRfc2833PayloadType   OBJECT-TYPE 
	SYNTAX INTEGER (96..127)
	ACCESS read-write 
	STATUS mandatory 
	DESCRIPTION " Payload type of RFC2833
	 
		ALCATEL NOTE 
		ACCESS: RW
		USAGE: MAN 
		PERSIST: YES 
		INSRVMOD: YES
		RANGE: From 96 To 127
		DEFVALUE: 96
		UNITS: NA 
		SPARSE: NO 
		DESCR: NA "

	DEFVAL {96} 
   ::= {medGwyMegacoExtEntry 22} 

   medGwyRfc2833Processing   OBJECT-TYPE 
	SYNTAX INTEGER
   	{
	  audio (1), 
	  rfc2833 (2), 
	  both (3) 
   	}
	ACCESS read-write 
	STATUS mandatory 
	DESCRIPTION " Processing procedure for the DTMF event tones
	 
		ALCATEL NOTE 
		ACCESS: RW
		USAGE: MAN 
		PERSIST: YES 
		INSRVMOD: YES
		RANGE: NA
		DEFVALUE: audio
		UNITS: NA 
		SPARSE: NO 
		DESCR: NA "

	DEFVAL { audio } 
   ::= {medGwyMegacoExtEntry 23} 

   medGwyDialingStartTimer   OBJECT-TYPE 
	SYNTAX INTEGER (0..99)
	ACCESS read-write 
	STATUS mandatory 
	DESCRIPTION " The start timer of dialing
				Default maximum waiting time for dialing the first digit.
				The unit is second.
				Value T=0 means the start-dial-timer is to be disabled. In this case the MG shall wait indefinitely for digits if the start timer is not overrided by MGC's command. 
	 
		ALCATEL NOTE 
		ACCESS: RW
		USAGE: MAN 
		PERSIST: YES 
		INSRVMOD: NO
		RANGE: From 0 To 99
		DEFVALUE: 10
		UNITS: SECOND 
		SPARSE: NO 
		DESCR: NA "

	DEFVAL {10} 
   ::= {medGwyMegacoExtEntry 24} 

   medGwyDialingLongTimer   OBJECT-TYPE 
	SYNTAX INTEGER (1..60)
	ACCESS read-write 
	STATUS mandatory 
	DESCRIPTION " The long timer of dialing.
				Default maximum waiting time for dialing when no matching found in the digitmap.
				The unit is second.
	 
		ALCATEL NOTE 
		ACCESS: RW
		USAGE: MAN 
		PERSIST: YES 
		INSRVMOD: NO
		RANGE: From 1 To 60
		DEFVALUE: 20
		UNITS: SECOND 
		SPARSE: NO 
		DESCR: NA "

	DEFVAL {20} 
   ::= {medGwyMegacoExtEntry 25} 

   medGwyDialingShortTimer   OBJECT-TYPE 
	SYNTAX INTEGER (1..60)
	ACCESS read-write 
	STATUS mandatory 
	DESCRIPTION " The short timer of dialing
				Default maximum waiting time for dialing when matching found in the digitmap.
				The unit is second.
	 
		ALCATEL NOTE 
		ACCESS: RW
		USAGE: MAN 
		PERSIST: YES 
		INSRVMOD: NO
		RANGE: From 1 To 60
		DEFVALUE: 5
		UNITS: SECOND 
		SPARSE: NO 
		DESCR: NA "

	DEFVAL {5} 
   ::= {medGwyMegacoExtEntry 26} 

   medGwyMinDataJitterBuffer   OBJECT-TYPE 
	SYNTAX INTEGER (0..200)
	ACCESS read-write 
	STATUS mandatory 
	DESCRIPTION " Minimum jitter buffer for data calls working in RTP mode.
				The unit is millisecond.
	 
		ALCATEL NOTE 
		ACCESS: RW
		USAGE: MAN 
		PERSIST: YES 
		INSRVMOD: YES
		RANGE: From 0 To 200
		DEFVALUE: 50
		UNITS: MILLISECOND 
		SPARSE: NO 
		DESCR: NA "

	DEFVAL {50} 
   ::= {medGwyMegacoExtEntry 27} 

   medGwyInitDataJitterBuffer   OBJECT-TYPE 
	SYNTAX INTEGER (0..200)
	ACCESS read-write 
	STATUS mandatory 
	DESCRIPTION " Initial jitter buffer for data calls working in RTP mode.
				The unit is millisecond.
	 
		ALCATEL NOTE 
		ACCESS: RW
		USAGE: MAN 
		PERSIST: YES 
		INSRVMOD: YES
		RANGE: From 0 To 200
		DEFVALUE: 50
		UNITS: MILLISECOND 
		SPARSE: NO 
		DESCR: NA "

	DEFVAL {50} 
   ::= {medGwyMegacoExtEntry 28} 

   medGwyMaxDataJitterBuffer   OBJECT-TYPE 
	SYNTAX INTEGER (0..200)
	ACCESS read-write 
	STATUS mandatory 
	DESCRIPTION " Maximum jitter buffer for data calls working in RTP mode.
				The unit is millisecond.
	 
		ALCATEL NOTE 
		ACCESS: RW
		USAGE: MAN 
		PERSIST: YES 
		INSRVMOD: YES
		RANGE: From 0 To 200
		DEFVALUE: 50
		UNITS: MILLISECOND 
		SPARSE: NO 
		DESCR: NA "

	DEFVAL {50} 
   ::= {medGwyMegacoExtEntry 29} 


   medGwyEphemeralTermPrefix   OBJECT-TYPE 
	SYNTAX DisplayString
	ACCESS read-write 
	STATUS mandatory 
	DESCRIPTION " Define the prefix to compose the ephemeral termination id.
                   The max number of the string is 10.
                   This parameter can not be same with medGwyPstnTermFormatStr and medGwyIsdnTermFormatStr.
	 
		ALCATEL NOTE 
		ACCESS: RW
		USAGE: MAN 
		PERSIST: YES 
		INSRVMOD: NO
		RANGE: From 0 To 10
		DEFVALUE: NA
		UNITS: NA 
		SPARSE: NO 
		DESCR: NA "

	DEFVAL {"E"} 
   ::= {medGwyMegacoExtEntry 30} 

   medGwyEphemeralTermMin   OBJECT-TYPE 
	SYNTAX Gauge
	ACCESS read-write 
	STATUS mandatory 
	DESCRIPTION " Minimum value of ephemeral termination for PSTN and ISDN-BA.
	 
		ALCATEL NOTE 
		ACCESS: RW
		USAGE: MAN 
		PERSIST: YES 
		INSRVMOD: NO
		RANGE: From 0 To 4294967295
		DEFVALUE: 65536
		UNITS: NA 
		SPARSE: NO 
		DESCR: NA "

	DEFVAL {65536} 
   ::= {medGwyMegacoExtEntry 31} 

   medGwyEphemeralTermMax   OBJECT-TYPE 
	SYNTAX Gauge
	ACCESS read-write 
	STATUS mandatory 
	DESCRIPTION " Maximum value of ephemeral termination for PSTN and ISDN-BA.
	 
		ALCATEL NOTE 
		ACCESS: RW
		USAGE: MAN 
		PERSIST: YES 
		INSRVMOD: NO
		RANGE: From 0 To 4294967295
		DEFVALUE: 72366
		UNITS: NA 
		SPARSE: NO 
		DESCR: NA "

	DEFVAL {72366} 
   ::= {medGwyMegacoExtEntry 32}

   medGwyReleaseType		OBJECT-TYPE
	SYNTAX	INTEGER
	{
	  normal(1),  -- release active call immediately or after delay time
	  never(2)      --preserve active call
	}
	ACCESS	read-write
	STATUS	mandatory
	DESCRIPTION	"The Type of release the active call.
	When the value is never it means it will preserve active call , when the value is normal,
            it means the active call will be released immediately or after delay time according to the define of medGwyReleaseDelay.
	ALCATEL NOTE 
	ACCESS: WO
	USAGE: MAN 
	PERSIST: YES 
	INSRVMOD: NO 
	RANGE: normal or never
	DEFVALUE: normal 
	UNITS: NA 
	SPARSE: NO 
	DESCR: NA "
	DEFVAL {normal}
    ::= {medGwyMegacoExtEntry  33}

    medGwyIPDhcpv4Option60 OBJECT-TYPE
      SYNTAX DisplayString 
      ACCESS read-write
      STATUS mandatory
      DESCRIPTION "DHCP option 60 for the DHCP client.The max length of the string is 64. 
      If this parameter equal to null string, DHCP client should send DHCP message without option 60.
      ALCATEL NOTE 
      ACCESS: RW
      USAGE: MAN 
      PERSIST: YES
      INSRVMOD: NO
      RANGE: NA 
      DEFVALUE: null 
      UNITS: NA 
      SPARSE: NO 
      DESCR: NA " 
      ::= {medGwyMegacoExtEntry  34}

   
   -- *****************************************************************
   -- accessEquipmentTable
   -- *****************************************************************
   accessEquipmentTable OBJECT-TYPE
      SYNTAX SEQUENCE OF AccessEquipmentEntry
      ACCESS not-accessible
      STATUS mandatory
      DESCRIPTION "List of ISAM-V NEs having an access board associated to this NVPS. 
	               - 7302/7330 ISAM-V  : Supported 
	               - 7363 ISAM MX      : Not Applicable 
	               - 7367 ISAM SX-12VP : Not Applicable
	  ."
   ::= {accessEquipmentConfig 1}
   
   -- *****************************************************************
   -- accessEquipmentEntry
   -- *****************************************************************
   accessEquipmentEntry OBJECT-TYPE
      SYNTAX AccessEquipmentEntry
      ACCESS not-accessible
      STATUS mandatory
      DESCRIPTION "Entry holding configuration information for an ISAM-V NE."
      INDEX {accessEquipmentId}
   ::= {accessEquipmentTable 1}
   
   AccessEquipmentEntry ::= SEQUENCE
   {
      accessEquipmentId AccessEquipmentId, -- na
      accessEquipmentRowStatus RowStatus, -- rw
      accessEquipmentAsamId DisplayString, -- rw
      accessEquipmentVoiceIPAddress IpAddress, -- rw
      accessEquipmentVoiceNextHop IpAddress -- rw
   }
   
   accessEquipmentId OBJECT-TYPE
      SYNTAX AccessEquipmentId
      ACCESS not-accessible
      STATUS mandatory
      DESCRIPTION "Unique internal identifier for this ISAM-V NE."
   ::= {accessEquipmentEntry 1}
   
   accessEquipmentRowStatus OBJECT-TYPE
      SYNTAX RowStatus
      ACCESS read-write
      STATUS mandatory
      DESCRIPTION "Allows to control the creation and deletion
                   of rows in this table."
   ::= {accessEquipmentEntry 2}
   
   accessEquipmentAsamId OBJECT-TYPE
      SYNTAX DisplayString
      ACCESS read-write
      STATUS mandatory
      DESCRIPTION "Identifier of an ISAM-V NE. The max number of the string is 64. 
                   The string accept all printable characters. 
                   It is mandatory parameter of Equipment table entry. 
                      ALCATEL NOTE:
                      SUPPORT:        YES
                      PERSIST:        YES
                      INSRVMOD:       NA
                      RANGE:  NA
                      DEFVALUE:  NA
                      UNITS:  NA"
      DEFVAL {""}
   ::= {accessEquipmentEntry 3}
   
   accessEquipmentVoiceIPAddress OBJECT-TYPE
      SYNTAX IpAddress
      ACCESS read-write
      STATUS mandatory
      DESCRIPTION "IP address of the voice services for this ISAM-V NE."
   ::= {accessEquipmentEntry 4}
   
   accessEquipmentVoiceNextHop OBJECT-TYPE
      SYNTAX IpAddress
      ACCESS read-write
      STATUS mandatory
      DESCRIPTION "IP address of the next hop for this ISAM-V NE, in case
      accessEquipmentVoiceIPAddress is not in the same subnet as XLES subnet"
      DEFVAL {'00000000'H}
   ::= {accessEquipmentEntry 5}

  
   -- *****************************************************************
   -- accessEquipmentNextId
   -- *****************************************************************
   accessEquipmentNextId OBJECT-TYPE
      SYNTAX TestAndIncr
      ACCESS read-only
      STATUS mandatory
      DESCRIPTION "Next free identifier for a new accessEquipmentEntry. 
	               - 7302/7330 ISAM-V  : Supported 
				   - 7363 ISAM MX      : Not Applicable 
				   - 7367 ISAM SX-12VP : Not Applicable
	  ."
   ::= {accessEquipmentConfig 2}
   
   -- *****************************************************************
   -- accessBoardTable
   -- *****************************************************************
   accessBoardTable OBJECT-TYPE
      SYNTAX SEQUENCE OF AccessBoardEntry
      ACCESS not-accessible
      STATUS mandatory
      DESCRIPTION "List of POLT boards associated to this IVPS.
	               - 7302/7330 ISAM-V  : Supported 
				   - 7363 ISAM MX      : Not Applicable 
				   - 7367 ISAM SX-12VP : Not Applicable
	  ."
   ::= {accessEquipmentConfig 3}
   
   -- *****************************************************************
   -- accessBoardEntry
   -- *****************************************************************
   accessBoardEntry OBJECT-TYPE
      SYNTAX AccessBoardEntry
      ACCESS not-accessible
      STATUS mandatory
      DESCRIPTION "Entry holding configuration information for an
                   associated POLT board."
      INDEX {accessBoardHldrEquipmentId, accessBoardId}
   ::= {accessBoardTable 1}
   
   AccessBoardEntry ::= SEQUENCE
   {
      accessBoardHldrEquipmentId AccessEquipmentId, -- na
      accessBoardId AccessBoardId, -- na
      accessBoardRowStatus RowStatus, -- rw
      accessBoardCommStatus INTEGER, -- ro
      accessBoardLanxport   INTEGER,   --rw
      accessBoardPlannedType  DisplayString,  --rw
      accessBoardActualType  DisplayString  --ro
   }
   
   accessBoardHldrEquipmentId OBJECT-TYPE
      SYNTAX AccessEquipmentId
      ACCESS not-accessible
      STATUS mandatory
      DESCRIPTION "Internal identifier of the ISAM-V NE holding this POLT board."
   ::= {accessBoardEntry 1}
   
   accessBoardId OBJECT-TYPE
      SYNTAX AccessBoardId
      ACCESS not-accessible
      STATUS mandatory
      DESCRIPTION "Slot identifier composed of the rack number (4 bits),
                   subrack number (4 bits) and slot number (8 bits).the slotId(low byte) start from 1, and the 
                   slotId 1 corresponds to LT1."
   ::= {accessBoardEntry 2}
   
   accessBoardRowStatus OBJECT-TYPE
      SYNTAX RowStatus
      ACCESS read-write
      STATUS mandatory
      DESCRIPTION "Allows to control the creation and deletion
                   of rows in this table."
   ::= {accessBoardEntry 3}
   
   accessBoardCommStatus OBJECT-TYPE
      SYNTAX INTEGER
      {
         up (1),
         down (2),
         unknown (3)
      }
      ACCESS read-only
      STATUS mandatory
      DESCRIPTION "Represents the state of the communications with the POLT."
   ::= {accessBoardEntry 4}

-- accessBoardType OBJECT-TYPE
-- 	SYNTAX INTEGER
-- 	{
-- 		pstn(1),
-- 		isdn(2)
-- 	}
-- 	ACCESS read-write
-- 	STATUS mandatory
-- 	DESCRIPTION "The type of the user board."
--	DEFVAL {pstn}
-- ::= {accessBoardEntry 5}

   accessBoardLanxport	OBJECT-TYPE
	SYNTAX	INTEGER (1..32)
	ACCESS   read-write
	STATUS	mandatory
	DESCRIPTION  "The logical slot of the board.
		This value is used to calculate the UDP port.
		Notes: If the board is in the main rack not the extension rack, 
		The LANXPORT must be the same as SLOT number, if not, the LT board will not be up state.
		ALCATEL NOTE 
		ACCESS: RW 
		USAGE: MAN 
		PERSIST: YES 
		INSRVMOD: NO 
		RANGE: From 1 to 32 
		DEFVALUE: NA 
		UNITS: NA 
		SPARSE: NO 
		DESCR: NA  "
   ::=  {accessBoardEntry  6}
  
    accessBoardPlannedType OBJECT-TYPE
   	SYNTAX DisplayString
   	ACCESS read-write
   	STATUS mandatory
        DESCRIPTION  "
                A string representing the board (POLT-A,NPOT-A,BALT-B,NBAT-A,NBLT-B,...) that is
                planned in the slot. If the board is planned, the string consists of a mnemonic that
                identifies the board type.
                Following mnemonics are valid:
                <BOARD_MNEMONIC> A board of a specific type. Refer to the ETSI and
                                US Configurations documents for the list of boards 
                                that are supported in a given release.
                                ODM board types are planned with the board mnemonic, 
                                they are treated as unmanaged boards.
                NOT_PLANNED   No board is planned in the slot.
		ALCATEL NOTE 
		ACCESS: RW 
		USAGE: MAN 
		PERSIST: YES 
		INSRVMOD: NO 
		RANGE: NA 
		DEFVALUE: NA 
		UNITS: NA 
		SPARSE: NO 
		DESCR: NA  "
   ::= {accessBoardEntry 7}

   accessBoardActualType        OBJECT-TYPE
        SYNTAX  DisplayString
        ACCESS   read-only
        STATUS  mandatory
        DESCRIPTION  "
                A string representing the board (POLT-A,NPOT-A,BALT-B,NBAT-A,NBLT-B,...) that is 
                actually present in the slot.
                Following values are possible:
                <BOARD_MNEMONIC> Indicates the detected board-type. Uses same mnemonics as
                                described in object assessBoardPlannedType.
                UNKNOWN         The type of the detected board is unknown
                                and the planned board type is not UNMANAGED.
		ALCATEL NOTE 
		ACCESS: RO 
		USAGE: MAN 
		PERSIST: NO 
		INSRVMOD: NO 
		RANGE: NA 
		DEFVALUE: UNKNOWN 
		UNITS: NA 
		SPARSE: NO 
		DESCR: NA  "
	DEFVAL {"UNKNOWN"}
   ::=  {accessBoardEntry  8}

   -- *****************************************************************
   -- accessTerminationTable
   -- *****************************************************************
   accessTerminationTable OBJECT-TYPE
      SYNTAX SEQUENCE OF AccessTerminationEntry
      ACCESS not-accessible
      STATUS mandatory
      DESCRIPTION 
            "The accessTerminationTable contains the list of configured user ports.
            An entry MUST be configured for a user port when the voice service is subscribed for this user  port 
            i.e. the voice service is enabled at the MGC for this user port.
            An entry MAY be configured for a user port  without voice service subscription 
            i.e. the voice service for this port is disabled at the MGC. 
            For this latter configuration option, the HW and Media Gateway behaviour shall depend on 
            the setting of the administrative state for this port as described for the accTermVoiceServAtMgc object."

   ::= {accessTerminationConfig 1}
   
   -- *****************************************************************
   -- accessTerminationEntry
   -- *****************************************************************
   accessTerminationEntry OBJECT-TYPE
      SYNTAX AccessTerminationEntry
      ACCESS not-accessible
      STATUS mandatory
      DESCRIPTION "Entry holding configuration information for a configured user port."
      INDEX {accTerminationHldrEquipmentId, accTerminationUserPortId}
   ::= {accessTerminationTable 1}
   
   AccessTerminationEntry ::= SEQUENCE
   {
      accTerminationHldrEquipmentId AccessEquipmentId, -- na
      accTerminationUserPortId TerminationUserPortId, -- na
      accTerminationRowStatus RowStatus, -- rw
      accTerminationtId AccessTerminationId, -- rw
      accTerminationAssocMedGwyId MediaGatewayId, -- rw
      accTerminationOperStatus INTEGER, -- ro
      accTerminationAdminStatus INTEGER, -- rw
      accTerminationLineCharact INTEGER, -- rw
      accTerminationUserPortType INTEGER, -- rw
      accTerminationPacketSwitchType INTEGER, -- rw
      accTerminationL1ActivateType  INTEGER, --rw  
      accTerminationImpedance       INTEGER, --rw          
--      accTerminationGain       INTEGER, 
      accTerminationIdStr  DisplayString, -- ro
      accTerminationLockType		INTEGER, --wo
      accTerminationLockDelay	INTEGER, --wo
      accTerminationVoiceDscp INTEGER, -- rw
      accTerminationVoiceDot1P INTEGER, -- rw
      accTerminationETSIClipDataMode INTEGER, -- rw
      accTerminationMeteringPulseType INTEGER, -- rw
      accTerminationDirectoryNumber DisplayString, --rw
      accTerminationCallStatus  INTEGER, -- ro
      accTerminationOpStatDownReason  INTEGER, -- ro
      accTerminationTestStatus  INTEGER, -- ro
      accTerminationChannelStatus  INTEGER, -- ro
      accTerminationRxGain      INTEGER, --rw                
      accTerminationTxGain      INTEGER, --rw 
      accTerminationPowerSource1Status         INTEGER, --ro	 
      accTerminationPowerSource2Status         INTEGER, --ro
      accTerminationIsdnCodec     INTEGER,  --rw
      accTermVoiceServAtMgc       INTEGER  --rw
   }
   
   accTerminationHldrEquipmentId OBJECT-TYPE
      SYNTAX AccessEquipmentId
      ACCESS not-accessible
      STATUS mandatory
      DESCRIPTION "Internal identifier of the ISAM-V NE holding
                   the board owner of this user port.
                   - 7302/7330 ISAM-V  : Supported 
                   - 7363 ISAM MX      : Supported (Only can be 1)
                   - 7367 ISAM SX-12VP : Supported(Only can be 1)
. "
   ::= {accessTerminationEntry 1}
   
   accTerminationUserPortId OBJECT-TYPE
      SYNTAX TerminationUserPortId
      ACCESS not-accessible
      STATUS mandatory
      DESCRIPTION "User Port identifier composed of the rack number (4 bits),
                   subrack number (4 bits), slot number (8 bits) and
                   port number (16 bits)."
   ::= {accessTerminationEntry 2}
   
   accTerminationRowStatus OBJECT-TYPE
      SYNTAX RowStatus
      ACCESS read-write
      STATUS mandatory
      DESCRIPTION "Allows to control the creation and deletion
                   of rows in this table."
   ::= {accessTerminationEntry 3}
   
   accTerminationtId OBJECT-TYPE
      SYNTAX AccessTerminationId
      ACCESS read-write
      STATUS mandatory
      DESCRIPTION "Unique identifier of this termination,for pstn termination,its range
                   is [0..32767],for isdn termination, its range is  [0..8175].
                   if operator does not specify the value, the system will automatically assign a free termination ID in the range [0..32767] or [0..8175]."
   ::= {accessTerminationEntry 4}
   
   accTerminationAssocMedGwyId OBJECT-TYPE
      SYNTAX MediaGatewayId
      ACCESS read-write
      STATUS mandatory
      DESCRIPTION "Identifier of the associated media gateway."
   ::= {accessTerminationEntry 5}
   
   accTerminationOperStatus OBJECT-TYPE
      SYNTAX INTEGER
      {
         up (1),
         down (2),
         shuttingdown (3)
      }
      ACCESS read-only
      STATUS mandatory
      DESCRIPTION "The current operational state of this user port.
      		ALCATEL NOTE 
		ACCESS: RO 
		USAGE: MAN 
		PERSIST: NO 
		INSRVMOD: NO 
		RANGE: NA 
		DEFVALUE: NA 
		UNITS: NA 
		SPARSE: NO 
		DESCR: NA ."
   ::= {accessTerminationEntry 6}
   
   accTerminationAdminStatus OBJECT-TYPE
      SYNTAX INTEGER
      {
         locked (1),
         unlocked (2)
      }
      ACCESS read-write
      STATUS mandatory
      DESCRIPTION "The current administrative state of this user port."
      DEFVAL {locked}
   ::= {accessTerminationEntry 7}
   
   accTerminationLineCharact OBJECT-TYPE
      SYNTAX INTEGER
      ACCESS read-write
      STATUS mandatory
      DESCRIPTION "Line characteristics of the termination. Possible values
                   are 25 meaning 25 mA feeding and
                   40 meaning 40 mA feeding."
      DEFVAL {25}
   ::= {accessTerminationEntry 8}

   accTerminationUserPortType OBJECT-TYPE
   	SYNTAX INTEGER
   	{
   		pstn(1),
   		isdn(2)
   	}
   	ACCESS read-write
   	STATUS mandatory
   	DESCRIPTION "The type of the user port. "
        DEFVAL {pstn}
   ::= {accessTerminationEntry 9}

   accTerminationPacketSwitchType OBJECT-TYPE
   	SYNTAX INTEGER
   	{
   		enable(1),
   		disable(2)
   	}
   	ACCESS read-write
   	STATUS mandatory
   	DESCRIPTION "The type of the packet switch type for ISDN. "
	DEFVAL {disable}
   ::= {accessTerminationEntry 10}

   accTerminationL1ActivateType OBJECT-TYPE
   	SYNTAX INTEGER
   	{
   		permanent(1),
   		percall(2)
   	}
   	ACCESS read-write
   	STATUS mandatory
   	DESCRIPTION "The type of the Layer1 activate type for ISDN. "
 	DEFVAL {permanent}
   ::= {accessTerminationEntry 11}

  accTerminationImpedance OBJECT-TYPE
      SYNTAX INTEGER
      ACCESS read-write
      STATUS mandatory
      DESCRIPTION "Impedance index (1-32), 1 means default value,
                   only impedance values with a resistance value equal the 
                   pre-configured value in the CDE file can be chosen.
                   1: default value. (If set to default value but get the corresponding actual value defined in CDE profile)
                   2: 200 Ohm+(680 Ohm//100nF)
                   3: 220 Ohm+(820Ohm//120nF)
                   4: 220 Ohm+(820 Ohm//120nF) miniSplitter
                   5: 270 Ohm+(750 Ohm//150nF)
                   6: 300 Ohm+(1000 Ohm//220nF)
                   7: 370 Ohm+(620 Ohm//310nF)
                   8: 600 Ohm
                   9: 900 Ohm
                   10: 370 Ohm+(620 Ohm//310nF) + Splitter
                   11: 600 Ohm+ Splitter
                   12: 370NVLSASplitter
                   13: 370SkinnySplitter
                   14: 270DuratelSplitter
                   15: 2703MSplitter 
                   16: 100Ohm+(1650Ohm//5nF) 
                   17: 150Ohm+(510Ohm//47nF) 
                   18: 220Ohm+Splitter 
                   19: schmReserved19
                   20: schmReserved20
                   21: schmReserved21
                   22-32: schmReserved
                   
		   ALCATEL NOTE: 
                     PERSIST: NO 
                     INSRVMOD: NO 
                     RANGE: NA 
                     DEFVALUE: 1 
                     UNITS: NA"
      DEFVAL {1}
   ::= {accessTerminationEntry 12}


--   accTerminationGain OBJECT-TYPE
--   	SYNTAX INTEGER(-8..8)
--   	ACCESS read-write
--   	STATUS mandatory
--   	DESCRIPTION "Line Gain. "
--   	DEFVAL {0}
--   ::= {accessTerminationEntry 13}

   accTerminationIdStr	OBJECT-TYPE
   	SYNTAX	DisplayString
   	ACCESS	read-only
   	STATUS	mandatory
   	DESCRIPTION	"The String of the access Termination Id. 
		In this string, it use the digit to replace the medGwyPstnTermFormatStr or
		medGwyIsdnTermFormatStr. The max length is also 72.
		The string is something like the 'AL/Dslam_Id/rack/shelf/slot/port' for PSTN User. 
		And 'BA/Dslam_Id/rack/shelf/slot/port' for ISDN User. It does not contain channel.
		because ISDN User both contain two channels.
		ALCATEL NOTE 
		ACCESS: RO 
		USAGE: MAN 
		PERSIST: NO 
		INSRVMOD: NO 
		RANGE: NA 
		DEFVALUE: NA 
		UNITS: NA 
		SPARSE: NO 
		DESCR: NA ."
   ::= {accessTerminationEntry 14}

   accTerminationLockType	OBJECT-TYPE
   	SYNTAX	INTEGER
   	{
   		force (1),
   		graceful (2)
   	}
   	ACCESS	write-only
   	STATUS	mandatory
   	DESCRIPTION	"The termination lock type.
	Should be set ONLY if the AdminStatus is locked.   	
		ALCATEL NOTE 
		ACCESS: WO 
		USAGE: MAN 
		PERSIST: NO 
		INSRVMOD: NO 
		RANGE: NA 
		DEFVALUE: force 
		UNITS: NA 
		SPARSE: NO 
		DESCR: NA "
   	DEFVAL	{force}
   ::= {accessTerminationEntry 15}  

   accTerminationLockDelay	OBJECT-TYPE
   	SYNTAX	INTEGER (0..3600000)
   	ACCESS	write-only
   	STATUS	mandatory
   	DESCRIPTION	"The delay timer before lock the access termination, 
		The object is only valid when accTerminationLockType  is equal to graceful(2). . 
		The range of this object is equal and large than zero. 
		ALCATEL NOTE 
		ACCESS: WO 
		USAGE: MAN 
		PERSIST: NO 
		INSRVMOD: NO 
		RANGE: From 0 to 3600000 
		DEFVALUE: 0 
		UNITS: MILLISECOND 
		SPARSE: NO 
		DESCR: NA "
   	DEFVAL	{0}
   ::= {accessTerminationEntry 16}

   accTerminationVoiceDscp OBJECT-TYPE
   	SYNTAX INTEGER(-1..63)
   	ACCESS read-write
   	STATUS mandatory
   	DESCRIPTION "Voice DSCP. "
   	DEFVAL {-1}
   ::= {accessTerminationEntry 17}

   accTerminationVoiceDot1P OBJECT-TYPE
   	SYNTAX INTEGER(-1..7)
   	ACCESS read-write
   	STATUS mandatory
   	DESCRIPTION "Voice P-bit. "
   	DEFVAL {-1}
   ::= {accessTerminationEntry 18}

   accTerminationETSIClipDataMode OBJECT-TYPE
	SYNTAX INTEGER
		{
		cdevalue(1),
		fsk(2),
		dtmf(3)
		}
	ACCESS read-write
	STATUS mandatory
	DESCRIPTION
		" The ETSI clip data transmission protocol of the access termination. 
		  The clip data mode can only be configured in PSTN line cards. 
			cdevalue(1)	- CDE configuration will be applied for ETSI CLIP.
			fsk(2)	- fsk will be applied for ETSI CLIP.
			dtmf(3) - dtmf will be applied for ETSI CLIP.
			
		ALCATEL-LUCENT NOTE:
			ACCESS:     read-write
	        USAGE:      OPT
			PERSIST:  	Yes
			INSRVMOD: 	YES
			RANGE:	    1 | 2 | 3
			DEFVALUE: 	1
			UNITS:	    NA	
	        SPARSE:     NO
		"
	DEFVAL {cdevalue} 
	::= { accessTerminationEntry 19 }

	accTerminationMeteringPulseType OBJECT-TYPE
	
		SYNTAX INTEGER
		{
		pulse(1),
		linePolarityReverse(2)
		}
	ACCESS read-write
	STATUS mandatory
	DESCRIPTION
		" The metering pulse type of the access termination. 
		  The metering pulse type only be configured in PSTN line cards. 
			pulse(1) - 12/16KHZ sine waveform pulse will be
			applied for metering pulse.
			linePolarityReverse(2)	- line polarity reverse pulse
			will be applied for metering pulse.
			
		ALCATEL-LUCENT NOTE:
			ACCESS:     read-write
	        USAGE:      OPT
			PERSIST:  	Yes
			INSRVMOD: 	YES
			RANGE:	    1 | 2
			DEFVALUE: 	1
			UNITS:	    NA	
	        SPARSE:     NO
		"
	DEFVAL {pulse} 
	::= { accessTerminationEntry 20 }
	
	accTerminationDirectoryNumber OBJECT-TYPE
	
		SYNTAX DisplayString

	ACCESS read-write
	STATUS mandatory
	DESCRIPTION
		" The Termination Directory Number associated with the POTS/ISDN BA line. 
		  This field will be provisioned via the 5529 APC as part of the subscriber
		  provisioning process. 
		  The new data field can enter any ASCII-String(not only digit)with a maximum
		  length of 16 characters.
			
		ALCATEL-LUCENT NOTE:
			ACCESS:     read-write
	        USAGE:      OPT
			PERSIST:  	Yes
			INSRVMOD: 	NO
			RANGE:	    SIZE(0..16)
			DEFVALUE:
			UNITS:	    NA	
	        SPARSE:     NO
		"
	DEFVAL {""} 
	::= { accessTerminationEntry 21 }

    accTerminationCallStatus OBJECT-TYPE
	SYNTAX INTEGER
		{
                none(0),
		onhook(1),
		offhook(2),
		dialling(3),
		calling(4),
		idleoffhook(6),
		busyTone(7),
		howlerTone(8),
		ringing(9),
		releasing(10),
		ringback(11),
		callerConnected(12),
		calleeConnected(13),
        sharedCutoff(14)
		}
	ACCESS read-only
	STATUS mandatory
	DESCRIPTION
		" The status of call at this termination. The meaning of the status is list as
		following:
           none(0): there is no meaning when oper status is down and admin-status is down
		       onhook(1): hook on without any call
		       offhook(2): hookoff but user no dialling
		       dialling(3): dial digit
		       calling(4):setting up connection with remote (notify msg)
		       idleoffhook(6): parking
		       busyTone(7): this status unused after R41
		       howlerTone(8): this status unused after R41
		       ringing(9): ringing
		       releasing(10): call has been terminated. but suscriber does not hook on. Some
		       tone maybe play in this state. The line is in releasing state
		       ringback(11): ringback tone to caller
		       callerConnected(12): call has been setup (connected as caller)
		       calleeConnected(13): call has been setup (connected as callee)
               sharedCutoff(14):The one termination configured at a shared line is cut off by the system
                                     when the other termination configured at that same share line is found to be in one of
                                     the following states : offhook, dialling, ringing, releasing, ringback, callerConnected,
                                     calleeConnected.
                                 The one termination that is in sharedCutoff state will hear silence upon going off-hook
                                     (no dial-tone is put at the line); Also incoming call attempts are rejected for the one
                                     termination in internal blocked state.

		ALCATEL-LUCENT NOTE:
			ACCESS:     NA
	    USAGE:      NA
			PERSIST:    NO
			INSRVMOD:   NA
			RANGE:	    0..14
			DEFVALUE    NA
			UNITS:	    NA	
	    SPARSE:     NO
		"
	::= { accessTerminationEntry 22 }

    accTerminationOpStatDownReason OBJECT-TYPE
	SYNTAX INTEGER
		{
    none(0),
		registering(1),
		registrationFailure(2),
		physicalFailure(3)
		}
	ACCESS read-only
	STATUS mandatory
	DESCRIPTION
		" The oper status down reason of this access termination.
           none(0) - there is no meaning when term is up
		       registering(1) - The termination is registering.
		       registrationFailure(2) - The termination registration is failed.
		       physicalFailure(3) - The termination is out of service.
	
		ALCATEL-LUCENT NOTE:
			ACCESS:     NA
	                USAGE:      NA
			PERSIST:    NO
			INSRVMOD:   NA
			RANGE:	    0 | 1 | 2 | 3
			DEFVALUE    NA
			UNITS:	    NA	
	                SPARSE:     NO
		"
	::= { accessTerminationEntry 23 }

    accTerminationTestStatus OBJECT-TYPE
	SYNTAX INTEGER
		{
		noTesting(1),
		mtaTesting(2),
		intgLineTesting(3)
		}
	ACCESS read-only
	STATUS mandatory
	DESCRIPTION
		" The test status of this access termination.
		       noTesting(1) - The termination is not under testing.
		       mtaTesting(2) - The termination is under MTA testing.
		       intgLineTesting(3) - The termination is under integrated line testing.
	
		ALCATEL-LUCENT NOTE:
			ACCESS:     NA
	                USAGE:      NA
			PERSIST:    NO
			INSRVMOD:   NA
			RANGE:	    1 | 2 | 3
			DEFVALUE    NA
			UNITS:	    NA	
	                SPARSE:     NO
		"
	::= { accessTerminationEntry 24 }
  
    accTerminationChannelStatus OBJECT-TYPE
	SYNTAX INTEGER
		{
                none(0),
		idle(1),
		b1-busy(2),
		b2-busy(3),
		both-channels-busy(4)
		}
	ACCESS read-only
	STATUS mandatory
	DESCRIPTION
		" The test status of this access termination.
                none(0) - There is no meaning. Initial value.
		idle(1) - both channels are idle.
		b1-busy(2) - B1 channel is busy. B2 is idle.
		b2-busy(3) - B2 channel is busy. B1 is idle.
		both-channels-busy(4) - both channels are busy.
	
		ALCATEL-LUCENT NOTE:
			ACCESS:     NA
	                USAGE:      NA
			PERSIST:    NO
			INSRVMOD:   NA
			RANGE:	    0 | 1 | 2 | 3 | 4
			DEFVALUE    NA
			UNITS:	    NA	
	                SPARSE:     NO
		"
	::= { accessTerminationEntry 25 }

   accTerminationRxGain OBJECT-TYPE
   	SYNTAX INTEGER(-14..6)
   	ACCESS read-write
   	STATUS mandatory
   	DESCRIPTION "Line Receive Gain. 
   	  ALCATEL NOTE 
			ACCESS: RW 
			USAGE: MAN 
			PERSIST: YES 
			INSRVMOD: YES 
			RANGE: From -14 to 6 
			DEFVALUE: 0 
			UNITS: dB 
			SPARSE: NO 
			DESCR: NA "
   	DEFVAL {0}
   ::= {accessTerminationEntry 26}

   accTerminationTxGain OBJECT-TYPE
   	SYNTAX INTEGER(-14..6)
   	ACCESS read-write
   	STATUS mandatory
   	DESCRIPTION "Line Transmission Gain. 
   		ALCATEL NOTE 
			ACCESS: RW 
			USAGE: MAN 
			PERSIST: YES 
			INSRVMOD: YES 
			RANGE: From -14 to 6 
			DEFVALUE: 0 
			UNITS: dB 
			SPARSE: NO 
			DESCR: NA "
   	DEFVAL {0}
   ::= {accessTerminationEntry 27}

   accTerminationPowerSource1Status OBJECT-TYPE
   	SYNTAX INTEGER
   	{
                none(0),
   		normal(1),
   		abnormal(2)
   	}
   	ACCESS read-only
   	STATUS mandatory
   	DESCRIPTION "The ISDN status of the power source 1. "
        DEFVAL {normal}
   ::= {accessTerminationEntry 28}

    accTerminationPowerSource2Status OBJECT-TYPE
   	SYNTAX INTEGER
   	{
                none(0),
   		normal(1),
   		abnormal(2)
   	}
   	ACCESS read-only
   	STATUS mandatory
   	DESCRIPTION "The ISDN status of the power source 2. "
        DEFVAL {normal}
   ::= {accessTerminationEntry 29}

    accTerminationIsdnCodec OBJECT-TYPE
    SYNTAX INTEGER
    {
        alaw(0),
        ulaw(1)
    }
    ACCESS read-write
    STATUS mandatory
    DESCRIPTION "the codec type of isdn "
        DEFVAL {alaw}
    ::= {accessTerminationEntry 30}

    accTermVoiceServAtMgc   OBJECT-TYPE
    SYNTAX  INTEGER
    {
        enabled (1),
        disabled (2)
    }
    ACCESS  read-write    
    STATUS  mandatory
    DESCRIPTION 
        "This MIB object indicates whether the voice service is enabled/disabled  at the MGC for this termination.
        Enabled (1)  : The termination is known to the MGC. The termination can be registered to the MGC.
        Disabled (2) : The termination is NOT known to the MGC. The termination CANNOT be registered to the MGC.
        When a termination entry has this object set to 'disabled (2)' while the accTerminationAdminStatus = locked, 
        the line is not feeded; Should the line go off-hook, no tone is generated.
        When a termination entry has this object set to 'disabled(2)' while the accTerminationAdminStatus = unlocked, the line is feeded;
        Should the line go off-hook, a special busy tone with  tone name = nnatone (number_not_assigned tone ) and with tone ID = 237, is played.
        - 7302 ISAM-V: PSTN, isr5301 Supported
                         ISDN, Not Applicable
        - 7363 ISAM MX: Not Applicable 
        - 7367 ISAM SX-12VP: Not Applicable
 
        ALCATEL-LUCENT NOTE:
            ACCESS:                   READ-WRITE
            USAGE:                    OPTIONAL
            PERSIST:                  YES
            INSRVMOD:                 YES
            RANGE:                    1 | 2 
            DEFVALUE:                 enabled (1) (for backward compatibility reason)
            UNITS:                    NA  
            SPARSE:                   NO"
            DEFVAL  {enabled}
   ::= {accessTerminationEntry 31}
 
   -- *****************************************************************
   -- terminationTable
   -- *****************************************************************
  -- terminationTable OBJECT-TYPE
  --    SYNTAX SEQUENCE OF TerminationEntry
  --    ACCESS not-accessible
  --    STATUS mandatory
  --    DESCRIPTION "Virtual list of configured user ports indexed by
  --                 the associated media gateway."
  -- ::= {accessTerminationConfig 2}
   
   -- *****************************************************************
   -- terminationEntry
   -- *****************************************************************
  -- terminationEntry OBJECT-TYPE
  --   SYNTAX TerminationEntry
  --    ACCESS not-accessible
  --    STATUS mandatory
  --    DESCRIPTION "Virtual entry holding configuration information for a
  --                 configured user port."
  --    INDEX {terminationAssocMedGwyId, terminationId}
  -- ::= {terminationTable 1}
   
  -- TerminationEntry ::= SEQUENCE
  -- {
  --    terminationAssocMedGwyId MediaGatewayId, -* na
  --    terminationId AccessTerminationId, -* na
  --    terminationUserPortId TerminationUserPortId, -* ro
  --    terminationHldrEquipmentId AccessEquipmentId -* ro
  -- }
   
  --  terminationAssocMedGwyId OBJECT-TYPE
  --    SYNTAX MediaGatewayId
  --    ACCESS not-accessible
  --    STATUS mandatory
  --    DESCRIPTION "Identifier of the associated media gateway."
  -- ::= {terminationEntry 1}
     
  -- terminationId OBJECT-TYPE
  --    SYNTAX AccessTerminationId
  --    ACCESS not-accessible
  --    STATUS mandatory
  --   DESCRIPTION "Unique identifier of this termination."
  -- ::= {terminationEntry 2}
   
  -- terminationUserPortId OBJECT-TYPE
  --    SYNTAX TerminationUserPortId
  --    ACCESS read-only
  --    STATUS mandatory
  --    DESCRIPTION "User port identifier composed of the rack number (4 bits),
  --                 subrack number (4 bits), slot number (8 bits) and
  --                 port number (16 bits)."
  -- ::= {terminationEntry 3}
   
 --  terminationHldrEquipmentId OBJECT-TYPE
 --     SYNTAX AccessEquipmentId
 --     ACCESS read-only
 --     STATUS mandatory
 --     DESCRIPTION "Internal identifier of the ISAM-V NE holding
 --                  the board owner of this user port."
 --  ::= {terminationEntry 4}
   

 -- *****************************************************************
 -- terminationExtTable
 -- *****************************************************************
   terminationExtTable OBJECT-TYPE
      SYNTAX SEQUENCE OF TerminationExtEntry
      ACCESS not-accessible
      STATUS mandatory
      DESCRIPTION "Virtual list of configured user ports indexed by
                   the associated media gateway, extended for isdn port."
   ::= {accessTerminationConfig 3}
   
   -- *****************************************************************
   -- terminationEntry
   -- *****************************************************************
   terminationExtEntry OBJECT-TYPE
      SYNTAX TerminationExtEntry
      ACCESS not-accessible
      STATUS mandatory
      DESCRIPTION "Virtual entry holding configuration information for a
                   configured user port."
      INDEX {terminationExtAssocMedGwyId, terminationExtUserPortType, terminationExtId}
   ::= {terminationExtTable 1}
   
   TerminationExtEntry ::= SEQUENCE
   {
      terminationExtAssocMedGwyId MediaGatewayId, -- na
      terminationExtUserPortType INTEGER, -- na
      terminationExtId AccessTerminationId, -- na
      terminationExtHldrEquipmentId AccessEquipmentId, -- ro
      terminationExtUserPortId TerminationUserPortId -- ro
   }
   
   terminationExtAssocMedGwyId OBJECT-TYPE
      SYNTAX MediaGatewayId
      ACCESS not-accessible
      STATUS mandatory
      DESCRIPTION "Identifier of the associated media gateway."
   ::= {terminationExtEntry 1}
     
   terminationExtUserPortType OBJECT-TYPE
   	SYNTAX INTEGER
   	{
   		pstn(1),
   		isdn(2)
   	}
   	ACCESS not-accessible
   	STATUS mandatory
   	DESCRIPTION "The type of the user port." 
   ::= { terminationExtEntry 2}

   terminationExtId OBJECT-TYPE
      SYNTAX AccessTerminationId
      ACCESS not-accessible
      STATUS mandatory
      DESCRIPTION "Unique identifier of this termination."
   ::= {terminationExtEntry 3}
  
   terminationExtHldrEquipmentId OBJECT-TYPE
      SYNTAX AccessEquipmentId
      ACCESS read-only
      STATUS mandatory
      DESCRIPTION "Internal identifier of the ISAM-V NE holding
                   the board owner of this user port. 
				   - 7302/7330 ISAM-V  : Supported 
				   - 7363 ISAM MX      : Not Applicable 
				   - 7367 ISAM SX-12VP : Not Applicable
				   ."
   ::= {terminationExtEntry 4}

   terminationExtUserPortId OBJECT-TYPE
      SYNTAX TerminationUserPortId
      ACCESS read-only
      STATUS mandatory
      DESCRIPTION "User port identifier composed of the rack number (4 bits),
                   subrack number (4 bits), slot number (8 bits) and
                   port number (16 bits)."
   ::= {terminationExtEntry 5}
  
   --******************************************************************
   -- accessTerminationTCATable
   --******************************************************************
   accessTerminationTCATable OBJECT-TYPE
      SYNTAX SEQUENCE OF AccessTerminationTCAEntry
      ACCESS not-accessible
      STATUS mandatory
      DESCRIPTION "This table allows to enable/disable the RTP QoS Metrics Alarm reporting as well as the configuration of the upper threshold for each of these RTP QoS Metrics. All RTP QoS Metric thresholds are checked upon call completion and checked against the statistics collected in the scope of RTCP.  Alarm reporting is done on a per call basis. In case a RTP QoS Metric would be exceeded, the appropriate RTP QoS Metrics Threshold Crossing Alarm will raised at call completion. A RTP QoS Metrics Threshold Crossing Alarm can only be reported once during a call. A RTP QoS Metrics Threshold Crossing Alarm been raised at call  completion is autonomously reset by the system immediately after this RTP QoS Metrics Threshold Crossing Alarm was raised."
   ::= {accessTerminationConfig 5}

   -- *****************************************************************
   -- accessTerminationTCAEntry
   -- *****************************************************************
   accessTerminationTCAEntry OBJECT-TYPE
      SYNTAX AccessTerminationTCAEntry
      ACCESS not-accessible
      STATUS mandatory
      DESCRIPTION "Entry holding TCA configuration information for a configured user port. An accessTerminationTCATable Entry is autonomously created by system, when the operator creates an accessTerminationTable entry. Vice versa, when a accessTerminationTable is deleted by the perator, the corresponding entry in the accessTerminationTCATable becomes autonomously deleted by the system. 
[TABLESIZE] : DEP [Num AccessTerminationTable entries]. Maximum number of entries is 5000."
      INDEX {accTerminationHldrEquipmentId, accTerminationUserPortId}
   ::= {accessTerminationTCATable 1}

   AccessTerminationTCAEntry ::= SEQUENCE
   {
    accTerminationTCAEnable INTEGER,
    accTerminationRtpPacketLossTCAThreshold INTEGER,
    accTerminationRtpJitterTCAThreshold INTEGER,
    accTerminationRtpDelayTCAThreshold INTEGER 
   }

   accTerminationTCAEnable OBJECT-TYPE
      SYNTAX INTEGER
      { 
       enabled(1),
       disabled(2)
	  }
      ACCESS read-write
      STATUS mandatory
      DESCRIPTION " Allows to enable/disable the Threshold Crossing Alarm feature for this termination.
                ALCATEL NOTE
                ACCESS: RW
                USAGE: NA
                PERSIST: YES
                INSRVMOD: YES
                RANGE: 1|2
                DEFVALUE: disabled(2)
                UNITS: NA
                SPARSE: NO
                DESCR: NA ."
	  DEFVAL { disabled }
   ::= {accessTerminationTCAEntry 1}

   accTerminationRtpPacketLossTCAThreshold OBJECT-TYPE
      SYNTAX INTEGER (0..100)
      ACCESS read-write
      STATUS mandatory
      DESCRIPTION " The RTP packet loss TCA threshold of this megaco termination. 
	                When the total RTP packet loss has exceeded the configured threshold, then raise the TCA alarm of this port at call completion. 
                    Configuring a value 0 means that the threshold is ignored even if the overall enable/disable TCA feature object is set to enabled.
                ALCATEL NOTE
                ACCESS: RW
                USAGE: NA
                PERSIST: YES
                INSRVMOD: YES
                RANGE: (0..100)
                DEFVALUE: 1
                UNITS: Percentage
                SPARSE: NO
                DESCR: NA ."
      DEFVAL { 1 }
   ::= {accessTerminationTCAEntry 2}

   accTerminationRtpJitterTCAThreshold OBJECT-TYPE
      SYNTAX INTEGER 
      ACCESS read-write
      STATUS mandatory
      DESCRIPTION " The RTP jitter TCA threshold of this megaco termination. 
	                When the RTP interarrival jitter has exceeded the configured threshold, then raise the TCA alarm for this port at call completion.
                    The unit is millisecond. Configuring a value 0 means that the threshold is ignored even if the overall enable/disable TCA feature object is set to enabled.
                ALCATEL NOTE
                ACCESS: RW
                USAGE: NA
                PERSIST: YES
                INSRVMOD: YES
                RANGE: NA
                DEFVALUE: 60
                UNITS: milli-seconds
                SPARSE: NO
                DESCR: NA ."
      DEFVAL { 60 }
   ::= {accessTerminationTCAEntry 3}   

      accTerminationRtpDelayTCAThreshold OBJECT-TYPE
      SYNTAX INTEGER
      ACCESS read-write
      STATUS mandatory
      DESCRIPTION " The RTP delay TCA threshold of this megaco termination. 
	                When the RTP round trip delay has exceeded the configured threshold, then raise the TCA alarm for this port at call completion. 
			        The unit is millisecond. Configuring a value 0 means that the threshold is ignored even if the overall enable/disable TCA feature object is set to enabled.
                ALCATEL NOTE
                ACCESS: RW
                USAGE: NA
                PERSIST: YES
                INSRVMOD: YES
                RANGE: NA
                DEFVALUE: 400
                UNITS: milli-seconds
                SPARSE: NO
                DESCR: NA ."
      DEFVAL { 400 }
   ::= {accessTerminationTCAEntry 4}   

   --******************************************************************
   -- accessTerminationLITable
   --******************************************************************
   accessTerminationLITable OBJECT-TYPE
      SYNTAX SEQUENCE OF AccessTerminationLIEntry
      ACCESS not-accessible
      STATUS mandatory
      DESCRIPTION "This table allows to enable the voice lawful intercept.
                   Before enable the LI, src-port,dest-port,dest-ip is mandatory.
                   Source IP is same as RTP IP. The max number of entries can be configured  is 50"
   ::= {accessTerminationConfig 7}

   -- *****************************************************************
   -- accessTerminationLIEntry
   -- *****************************************************************

   accessTerminationLIEntry OBJECT-TYPE
      SYNTAX AccessTerminationLIEntry
      ACCESS not-accessible
      STATUS mandatory
      DESCRIPTION "Entry holding voice lawful intercept configuration information for a configured user port"
      INDEX {accTerminationHldrEquipmentId, accTerminationUserPortId}
   ::= {accessTerminationLITable 1}

   AccessTerminationLIEntry ::= SEQUENCE
   {
    accTerminationLIRowStatus RowStatus,  --rw
    accTerminationLI INTEGER,  --rw
    accTerminationLISrcUdpPort INTEGER,  --rw
    accTerminationLIDestIPAddr IpAddress,  --rw
    accTerminationLIDestUdpPort INTEGER  --rw
   }

   accTerminationLIRowStatus OBJECT-TYPE
      SYNTAX RowStatus
      ACCESS read-write
      STATUS mandatory
      DESCRIPTION "Allows to control the creation and deletion of rows in this table."
   ::= {accessTerminationLIEntry 1}

   accTerminationLI OBJECT-TYPE
      SYNTAX INTEGER
      {
          enable(1),
          disable(2)
      }
      ACCESS read-write
      STATUS mandatory
      DESCRIPTION "Allows to enable/disable the Lawful Intercept.
          - 7302/7330 ISAM-V : Supported(IP address reduction mode)
          - 7363 ISAM MX : Not Applicable
          - 7367 ISAM SX-12VP : Not Applicable
            ALCATEL NOTE
            ACCESS: RW
            USAGE: OPT
            PERSIST: YES
            INSRVMOD: NO
            RANGE: 1|2
            DEFVALUE: disabled(2)
            UNITS: NA
            SPARSE: NO
            DESCR: NA."
      DEFVAL {disable}
   ::= {accessTerminationLIEntry 2}

   accTerminationLISrcUdpPort OBJECT-TYPE
      SYNTAX INTEGER (49153..65535)
      ACCESS read-write
      STATUS mandatory
      DESCRIPTION "The source UDP port for Lawful Intercept. Source IP address is same as Voice IP.
              - 7302/7330 ISAM-V  : Supported(IP address reduction mode)
              - 7363 ISAM MX      : Not Applicable
              - 7367 ISAM SX-12VP : Not Applicable
                ALCATEL NOTE
                ACCESS: RW
                USAGE: MAN
                PERSIST: YES
                INSRVMOD: NO
                RANGE: (49153..65535)
                DEFVALUE: 65535
                UNITS: NA
                SPARSE: NO
                DESCR: NA."
   ::= {accessTerminationLIEntry 3}

   accTerminationLIDestIPAddr OBJECT-TYPE
      SYNTAX IpAddress
      ACCESS read-write
      STATUS mandatory
      DESCRIPTION " The destination IP address for Lawful Intercept.
           - 7302/7330 ISAM-V  : Supported(IP address reduction mode)
           - 7363 ISAM MX      : Not Applicable
           - 7367 ISAM SX-12VP : Not Applicable
                ALCATEL NOTE
                ACCESS: RW
                USAGE: MAN
                PERSIST: YES
                INSRVMOD: NO
                RANGE: NA
                DEFVALUE: 0.0.0.0
                UNITS: NA
                SPARSE: NO
                DESCR: NA."
   ::= {accessTerminationLIEntry 4}

   accTerminationLIDestUdpPort OBJECT-TYPE
      SYNTAX INTEGER (0..65535)
      ACCESS read-write
      STATUS mandatory
      DESCRIPTION "The destination UDP port for Lawful Intercept.
              - 7302/7330 ISAM-V  : Supported(IP address reduction mode)
              - 7363 ISAM MX      : Not Applicable
              - 7367 ISAM SX-12VP : Not Applicable
                ALCATEL NOTE
                ACCESS: RW
                USAGE: MAN
                PERSIST: YES
                INSRVMOD: NO
                RANGE: (0..65535)
                DEFVALUE: 65535
                UNITS: NA
                SPARSE: NO
                DESCR: NA."
   ::= {accessTerminationLIEntry 5}


   -- *****************************************************************
   -- ivpsParams
   -- *****************************************************************
   ivpsParams OBJECT IDENTIFIER ::= {ivpsConfig 1}
   
   --ivpsOAMIPAddress OBJECT-TYPE
      --SYNTAX IpAddress
      --ACCESS read-only
      --STATUS mandatory
      --DESCRIPTION "OAM IP address of this IVPS."
   --::= {ivpsParams 1}
   
   --ivpsOAMUDPPort OBJECT-TYPE
      --SYNTAX INTEGER (0..65535)
      --ACCESS read-only
      --STATUS mandatory
      --DESCRIPTION "OAM UDP port of this IVPS."
   --::= {ivpsParams 2}
   
   --ivpsOAMSubnetMask OBJECT-TYPE
      --SYNTAX IpAddress
      --ACCESS read-only
      --STATUS mandatory
      --DESCRIPTION "OAM subnet mask of this IVPS."
   --::= {ivpsParams 3}
   
   --ivpsOAMNextHop OBJECT-TYPE
      --SYNTAX IpAddress
      --ACCESS read-only
      --STATUS mandatory
      --DESCRIPTION "OAM IP address for the next routing hop in this IVPS."
   --::= {ivpsParams 4}
   
   --ivpsOAMVLAN OBJECT-TYPE
      --SYNTAX INTEGER (2..4093)
      --ACCESS read-write
      --STATUS mandatory
      --DESCRIPTION "OAM VLAN of this IVPS."
      --DEFVAL {4093}
   --::= {ivpsParams 5}
   
   --ivpsXLESIPAddress OBJECT-TYPE
      --SYNTAX IpAddress
      --ACCESS read-write
      --STATUS mandatory
      --DESCRIPTION "Signalling IP address of this IVPS."
   --::= {ivpsParams 6}
   
   --ivpsXLESUDPPort OBJECT-TYPE
      --SYNTAX INTEGER (0..65535)
      --ACCESS read-only
      --STATUS mandatory
      --DESCRIPTION "Signalling UDP port of this IVPS."
   --::= {ivpsParams 7}
   
   --ivpsXLESSubnetMask OBJECT-TYPE
      --SYNTAX IpAddress
      --ACCESS read-write
      --STATUS mandatory
      --DESCRIPTION "Signalling subnet mask of this IVPS."
   --::= {ivpsParams 8}
   
   --ivpsXLESNextHop OBJECT-TYPE
      --SYNTAX IpAddress
      --ACCESS read-write
      --STATUS mandatory
      --DESCRIPTION "Signalling IP address for the next routing hop in this IVPS."
   --::= {ivpsParams 9}

   --ivpsXLESVLAN OBJECT-TYPE
      --SYNTAX INTEGER (0..4093)
      --ACCESS read-write
      --STATUS mandatory
      --DESCRIPTION "Voice and signalling VLAN of this IVPS. 0 for clean"
   --::= {ivpsParams 10}

   --ivpsPrivateIPAddress	OBJECT-TYPE
   	--SYNTAX	IpAddress
   	--ACCESS	read-write
   	--STATUS	mandatory
   	--DESCRIPTION	"The private Ip Address of IVPS. 
		--The ivpsPrivateIPAddress is used for the voice communication.
		--ALCATEL NOTE 
		--ACCESS: RW 
		--USAGE: MAN 
		--PERSIST: YES 
		--INSRVMOD: NO 
		--RANGE: NA 
		--DEFVALUE: 0.0.0.0 
		--UNITS: NA 
		--SPARSE: NO 
		--DESCR: NA "
	  --DEFVAL {'00000000'H}
   --::= {ivpsParams 11}

   --ivpsPrivateSubnetMask	OBJECT-TYPE
   	--SYNTAX	IpAddress
   	--ACCESS	read-write
   	--STATUS	mandatory
   	--DESCRIPTION	"The private Subnet Mask of IVPS.
		--The ivpsPrivateSubnetMask is used to distinguish the privateSubnet.
		--ALCATEL NOTE 
		--ACCESS: RW 
		--USAGE: MAN 
		--PERSIST: YES 
		--INSRVMOD: NO 
		--RANGE: NA 
		--DEFVALUE: 0.0.0.0 
		--UNITS: NA 
		--SPARSE: NO 
		--DESCR: NA "
	--DEFVAL {'00000000'H}
   --::= {ivpsParams 12}

   --ivpsPrivateVLAN OBJECT-TYPE
      --SYNTAX INTEGER (0..4093)
      --ACCESS read-write
      --STATUS mandatory
      --DESCRIPTION "private VLAN of this IVPS. 0 means use the same as XLES Vlan.
      --Also this Vlan need configured in the LANX, only configure at the LT port.
      --		ALCATEL NOTE 
		--ACCESS: RW 
		--USAGE: MAN 
		--PERSIST: YES 
		--INSRVMOD: NO 
		--RANGE: NA 
		--DEFVALUE: NA
		--UNITS: NA 
		--SPARSE: NO 
		--DESCR: NA "
   --::= {ivpsParams 13}

   ivpsBasicParamsTable OBJECT-TYPE
    SYNTAX SEQUENCE OF IvpsBasicParamsEntry
    ACCESS not-accessible
    STATUS mandatory
    DESCRIPTION "The IVPS basic config params table , including all XLES params and Private params." 
   ::= {ivpsParams 14}
   
   ivpsBasicParamsEntry OBJECT-TYPE
      SYNTAX IvpsBasicParamsEntry
      ACCESS not-accessible
      STATUS mandatory
      DESCRIPTION "The IVPS basic config params entry." 
      INDEX { ivpsBasicParamIndex }
   ::= {ivpsBasicParamsTable 1}
    
   IvpsBasicParamsEntry ::= SEQUENCE
   {
      ivpsBasicParamIndex               INTEGER,
      ivpsBasicParamXLESIPAddress       IpAddress,    
      ivpsBasicParamXLESUDPPort         INTEGER (0..65535),  
      ivpsBasicParamXLESSubnetMask      IpAddress, 
      ivpsBasicParamXLESNextHop         IpAddress,   
      ivpsBasicParamXLESVLAN            INTEGER (0..4093), 
      ivpsBasicParamPrivateIPAddress    IpAddress,
      ivpsBasicParamPrivateSubnetMask   IpAddress,
      ivpsBasicParamPrivateVLAN         INTEGER (0..4093),
      ivpsBasicParamVoiceIPConfigMode    INTEGER,
      ivpsBasicParamVoiceIPDhcpv4Option60    DisplayString
   }   
   
   ivpsBasicParamIndex OBJECT-TYPE
    SYNTAX INTEGER
    ACCESS not-accessible
    STATUS mandatory
    DESCRIPTION "Index of the table. always equals to 1." 
   ::= {ivpsBasicParamsEntry 1}   

   ivpsBasicParamXLESIPAddress OBJECT-TYPE
      SYNTAX IpAddress
      ACCESS read-write
      STATUS mandatory
      DESCRIPTION " Voice and XLES signalling IP address of this IVPS.
	                The object must be configured on 7302/7330 ISAM-V , but optional for 7363 ISAM MX/7367 ISAM SX-12VP.
	                - 7302/7330 ISAM-V  : Supported(Mandatory)
	                - 7363 ISAM MX      : Supported
					- 7367 ISAM SX-12VP : Supported
	  ."
      DEFVAL {'00000000'H}
   ::= {ivpsBasicParamsEntry 2}
   
   ivpsBasicParamXLESUDPPort OBJECT-TYPE
      SYNTAX INTEGER (0..65535)
      ACCESS read-only
      STATUS mandatory
      DESCRIPTION "Signalling UDP port of this IVPS.
	               - 7302/7330 ISAM-V  : Supported 
				   - 7363 ISAM MX      : Not Applicable 
				   - 7367 ISAM SX-12VP : Not Applicable
	  ."
   ::= {ivpsBasicParamsEntry 3}
   
   ivpsBasicParamXLESSubnetMask OBJECT-TYPE
      SYNTAX IpAddress
      ACCESS read-write
      STATUS mandatory
      DESCRIPTION "Subnet mask of the ivpsBasicParamXLESIPAddress.
	                The object must be configured on 7302/7330 ISAM-V , but optional for 7363 ISAM MX/7367 ISAM SX-12VP.
	                - 7302/7330 ISAM-V  : Supported(Mandatory)
	                - 7363 ISAM MX      : Supported
					- 7367 ISAM SX-12VP : Supported
	  ."
      DEFVAL {'00000000'H}
   ::= {ivpsBasicParamsEntry 4}
   
   ivpsBasicParamXLESNextHop OBJECT-TYPE
      SYNTAX IpAddress
      ACCESS read-write
      STATUS mandatory
      DESCRIPTION "The IP address for the next routing hop of the ivpsBasicParamXLESIPAddress.
	                The object must be configured on 7302/7330 ISAM-V , but optional for 7363 ISAM MX/7367 ISAM SX-12VP.
	                - 7302/7330 ISAM-V  : Supported(Mandatory)
	                - 7363 ISAM MX      : Supported
					- 7367 ISAM SX-12VP : Supported
	  ."
      DEFVAL {'00000000'H}
   ::= {ivpsBasicParamsEntry 5}

   ivpsBasicParamXLESVLAN OBJECT-TYPE
      SYNTAX INTEGER (0..4093)
      ACCESS read-write
      STATUS mandatory
      DESCRIPTION "Voice and XLES VLAN of this IVPS. 0 for clean.
	                The object must be configured on 7302/7330 ISAM-V , but optional for 7363 ISAM MX/7367 ISAM SX-12VP.
	                - 7302/7330 ISAM-V  : Supported(Mandatory)
	                - 7363 ISAM MX      : Supported
					- 7367 ISAM SX-12VP : Supported
	  ."
   ::= {ivpsBasicParamsEntry 6}

   ivpsBasicParamPrivateIPAddress	OBJECT-TYPE
   	SYNTAX	IpAddress
   	ACCESS	read-write
   	STATUS	mandatory
   	DESCRIPTION	"The private Ip Address of IVPS. 
		The ivpsPrivateIPAddress is used for the voice communication.
		- 7302/7330 ISAM-V  : Supported 
		- 7363 ISAM MX      : Not Applicable 
		- 7367 ISAM SX-12VP : Not Applicable

		ALCATEL NOTE 
		ACCESS: RW 
		USAGE: MAN 
		PERSIST: YES 
		INSRVMOD: NO 
		RANGE: NA 
		DEFVALUE: 0.0.0.0 
		UNITS: NA 
		SPARSE: NO 
		DESCR: NA "
	DEFVAL {'00000000'H}
   ::= {ivpsBasicParamsEntry 7}

   ivpsBasicParamPrivateSubnetMask	OBJECT-TYPE
   	SYNTAX	IpAddress
   	ACCESS	read-write
   	STATUS	mandatory
   	DESCRIPTION	"The private Subnet Mask of IVPS.
		The ivpsPrivateSubnetMask is used to distinguish the privateSubnet.
		- 7302/7330 ISAM-V  : Supported 
		- 7363 ISAM MX      : Not Applicable 
		- 7367 ISAM SX-12VP : Not Applicable

		ALCATEL NOTE 
		ACCESS: RW 
		USAGE: MAN 
		PERSIST: YES 
		INSRVMOD: NO 
		RANGE: NA 
		DEFVALUE: 0.0.0.0 
		UNITS: NA 
		SPARSE: NO 
		DESCR: NA "
	DEFVAL {'00000000'H}
   ::= {ivpsBasicParamsEntry 8}

   ivpsBasicParamPrivateVLAN OBJECT-TYPE
      SYNTAX INTEGER (0..4093)
      ACCESS read-write
      STATUS mandatory
      DESCRIPTION "private VLAN of this IVPS. 0 means use the same as XLES Vlan.
      Also this Vlan need configured in the LANX, only configure at the LT port. 
	  - 7302/7330 ISAM-V  : Supported 
	  - 7363 ISAM MX      : Not Applicable 
	  - 7367 ISAM SX-12VP : Not Applicable

      		ALCATEL NOTE 
		ACCESS: RW 
		USAGE: MAN 
		PERSIST: YES 
		INSRVMOD: NO 
		RANGE: NA 
		DEFVALUE: NA
		UNITS: NA 
		SPARSE: NO 
		DESCR: NA "
   ::= {ivpsBasicParamsEntry 9}

   ivpsBasicParamVoiceIPConfigMode OBJECT-TYPE      
      SYNTAX INTEGER           
      {
           dhcp(1),            
          manual(2)
      }      
      ACCESS read-write      
      STATUS mandatory      
      DESCRIPTION " The configure mode of the IP addresses     
        - 7302/7330 ISAM-V  : Supported 
        - 7363 ISAM MX      : Supported 
        - 7367 ISAM SX-12VP : Not Applicable 

        ALCATEL NOTE  
        ACCESS: RW    
        USAGE: MAN    
         PERSIST: YES  
         INSRVMOD: NO  
        RANGE: 1 | 2  
        DEFVALUE: manual(2)  
        UNITS: NA     
        SPARSE: NO    
        DESCR: NA "   
      ::= {ivpsBasicParamsEntry 10}

    ivpsBasicParamVoiceIPDhcpv4Option60 OBJECT-TYPE      
      SYNTAX DisplayString      
       ACCESS read-write      
       STATUS mandatory      
       DESCRIPTION "DHCP option 60 for the DHCP client.The max length of the string is 64. 
       If this parameter equal to null string, DHCP client should send DHCP message without option 60.
          - 7302/7330 ISAM-V  : Supported 
          - 7363 ISAM MX      : Supported 
          - 7367 ISAM SX-12VP : Not Applicable 

	   ALCATEL NOTE   
	   ACCESS: RW     
       USAGE: MAN     
       PERSIST: YES   
       INSRVMOD: NO   
       RANGE: NA      
       DEFVALUE: null   
       UNITS: NA      
       SPARSE: NO     
       DESCR: NA "   
    ::= { ivpsBasicParamsEntry 11}
   
	
	
	
   -- *****************************************************************
   -- IVPS BITMAPS
   -- *****************************************************************
   ivpsSpontaneousChanges OBJECT IDENTIFIER ::= {ivpsConfig 4}

   -- *****************************************************************
   -- IVPS Number Of Spontaneous Changes
   -- *****************************************************************
   ivpsNumberOfSpontaneousChanges OBJECT-TYPE
      SYNTAX Counter
      ACCESS read-only
      STATUS mandatory
      DESCRIPTION
         "This is a counter indicating the number of spontaneous
          changes occured in the IVPS since the system started up.
          Its value is reported via the changeOccured TRAP when a
          change in any object is detected by the IVPS.
          These changes might be got from a Manager by getting
          the value of the ivpsMediaGatewayStatusBitmap and all
          the rows in the ivpsAccTermStatusTable"

      ::= { ivpsSpontaneousChanges 1 }
   
   -- *****************************************************************
   -- IVPS Media Gateway Status Bitmap
   -- *****************************************************************
   ivpsMediaGatewayStatusBitmap OBJECT-TYPE
      SYNTAX OCTET STRING
      ACCESS read-only
      STATUS mandatory
      DESCRIPTION
         "This bitmap represents the current values of the 
          mediaGatewayOperStatus and medGwyCtrlrActiveAddress
          atributes of all the currently created Media Gateways.
          
          It contains n bytes: one for each Media Gateway.
          n = Maximum number of Media Gateways (1 in R1)

          Layout:
             MG-1-Status   MG-2-Status      MG-N-Status
            ============= =============    =============
               Byte 1        Byte 2     ...    Byte n

          MG-i-Status Layout:
            - Bit 0 (LSB): mediaGatewayOperStatus for i-th
              Media Gateway.
              Syntax: 1 = Up, 0 = Down
            - Bits 1,2,3: medGwyCtrlrActiveAddress for i-th
              Media Gateway.(LSB, bit 2 is big)
              Syntax: three bits integer: 1 = primary, 2 = secondary, 3 = none, 4 = other, 5 = tertiary, 6 = quaternary, 7 = emergencystandalone
                      note: value bit3 bit2 bit1
                                1       0    0    1
                                2       0    1    0
                                3       0    1    1
                                4       0    0    0
                                5       1    0    1
                                6       1    1    0
                                7       1    1    1

            - Bit 3 : reserved
            	
            	note: in the following, the 'SGI' refer to the signaling gateway
            	      belong to i-th media gateway.
            	
            - Bit 4 : whether SGI is configurated.
              Syntax: 1 = configurated, 0 = not configurated                      
            - Bit 5 : signallingGatewayOperStatus for SGI
              Syntax: 1 = Up, 0 = Down
            - Bits 8,9,10(BYTE2): signallingGatewayInterfaceAssocASP for SGI
              Syntax: two bits integer: (LSB, bit 10 is big)
                      0 = None,      1 = primary,
                      2 = secondary, 3 = both,  4 = tertiary, 5 = quaternary 
                      note: value bit10  bit9 bit8
                                0       0      0    0
                                1       0      0    1
                                2       0      1    0
                                3       0      1    1
            					4       1      0    0
                                5       1      0    1"

      ::= { ivpsSpontaneousChanges 2 }
      
   -- *****************************************************************
   -- IVPS Access Equipment Bitmap
   -- *****************************************************************
   ivpsAccEquipmentBitmap OBJECT-TYPE
      SYNTAX Counter
      ACCESS read-only
      STATUS mandatory
      DESCRIPTION
         "This bitmap represents the currently declared Access Equipments
          in this IVPS.
		  - 7302/7330 ISAM-V  : Supported 
		  - 7363 ISAM MX      : Not Applicable 
		  - 7367 ISAM SX-12VP : Not Applicable
          
          It contains 256 bits (in 32 bytes): one for each Access Equipment. 
          A bit set to one indicates that the corresponding Access Equipment
          is declared in the IVPS. A bit set to zero indicates that such Access
          Equipment is not declared.
          
          To find the accessEquipmentId identifying the corresponding Access Equipment,
          the following formula might be applied:
          
                 accessEquipmentId = ((BN - 1) * 8) + bn
                 BN = Byte Number (1..32)
                 bn = bit number (1..8 (msb))"
            
      ::= { ivpsSpontaneousChanges 3 }
   
   -- *****************************************************************
   -- IVPS Termination Status Table
   -- *****************************************************************
   ivpsAccTermStatusTable OBJECT-TYPE
      SYNTAX SEQUENCE OF IvpsAccTermStatusEntry
      ACCESS not-accessible
      STATUS mandatory
      DESCRIPTION
         "This table contains one entry for each created
          Access Equipment. Each entry is indexed by the
          Access Equipment Id. and holds a Bitmap with
          the current Operational Status of all the
          Access Terminations that are configured under
          this Access Equipment."
   ::= { ivpsSpontaneousChanges 4 }
   
   ivpsAccTermStatusEntry OBJECT-TYPE
      SYNTAX IvpsAccTermStatusEntry
      ACCESS not-accessible
      STATUS mandatory
      DESCRIPTION
         "This entry holds a Bitmap with the current
          Operational Status of all the Access Terminations
          that are configured under the Access Equipment
          identified by the ivpsHldrAccEquipmentId index."
      INDEX { ivpsHldrAccEquipmentId }
   ::= { ivpsAccTermStatusTable 1 }
   
   IvpsAccTermStatusEntry ::= SEQUENCE
   {
      ivpsHldrAccEquipmentId AccessEquipmentId, -- na
      ivpsHldrAccEqptNbrOfChanges Counter,
      ivpsAccTermStatusBitmap OCTET STRING -- ro
   }
   
   ivpsHldrAccEquipmentId OBJECT-TYPE
      SYNTAX AccessEquipmentId
      ACCESS not-accessible
      STATUS mandatory
      DESCRIPTION
         "Internal identifier of the Access Equipment holding
          the Access Terminations whose status is represented
          in this bitmap."
   ::= { ivpsAccTermStatusEntry 1 }
   
   ivpsHldrAccEqptNbrOfChanges OBJECT-TYPE
      SYNTAX Counter
      ACCESS read-only
      STATUS mandatory
      DESCRIPTION
         "This is a counter indicating the number of spontaneous 
         changes occured in the Access Equipment identified by 
         the ivpsHldrAccEqptId index since the system started up."
      ::= { ivpsAccTermStatusEntry 2 }
   
   ivpsAccTermStatusBitmap OBJECT-TYPE
      SYNTAX OCTET STRING
      ACCESS read-only
      STATUS mandatory
      DESCRIPTION
         "This Bitmap represents the current value of the
          accTerminationOperStatus attribute for all the Access
          Terminations that are created under the Access Boards
          that are in turn created under the Access Equipment
          identified by the ivpsHldrAccEquipmentId index.
                   
          It is a variable length Bitmap that contains n*11 bytes:
          each set of 11 bytes represents the information related
          to one created Access Board.
          n = Number of Access Boards created under this
              Access Equipment (maximum = The max number of 
              one node can support, now define it as 24).

          Each set of 11 bytes has the following layout:
          
         RackNumber  ShelfNumber     SlotNumber    72-Bits-UsePortStatusBitmap
            ============= ==============================
           4bits MSB      4bits LSB           Byte 2           Byte 3...Byte 11
                       Byte  1
          
	   *RackNumber: integer value holding the number of rack
	                 where the Access Board is inserted(1..16)
	                 
	   *ShelfNumber: integer value holding the number of shelf
	   		   where the Access Board is inserted(1..16)
	   		   
          * SlotNumber: integer value holding the number of slot
                        where the Access Board is inserted (1..16)
          
          * 72-Bits-UsePortStatusBitmap Layout:
            - Bit 0 (LSB): accTerminationOperStatus for the
                           Access Termination associated to
                           the first User Port in this Access
                           Board.

            - Bit 1:        accTerminationOperStatus for the
                            Access Termination associated to
                            the second User Port in this Access
                            Board.
          
            - Bit 71 (MSB): accTerminationOperStatus for the
                            Access Termination associated to
                            the 72-th User Port in this Access
                            Board.
          "
   ::= { ivpsAccTermStatusEntry 3 }   
   
   ivpsTraps OBJECT IDENTIFIER ::= {ivpsConfig 2}

   ivpsStatusChangeSource OBJECT-TYPE
      SYNTAX OBJECT IDENTIFIER
      ACCESS not-accessible
      STATUS mandatory
      DESCRIPTION "OID of the changing object.
	  - 7302/7330 ISAM-V  : Supported 
	  - 7363 ISAM MX      : Not Applicable 
	  - 7367 ISAM SX-12VP : Not Applicable
	  ."
   ::= {ivpsTraps 1}
   
   ivpsStatusChangeValue OBJECT-TYPE
      SYNTAX INTEGER (0..65535)
      ACCESS not-accessible
      STATUS mandatory
      DESCRIPTION "New value of the changing object.
	  - 7302/7330 ISAM-V  : Supported 
	  - 7363 ISAM MX      : Not Applicable 
	  - 7367 ISAM SX-12VP : Not Applicable
	  ."
   ::= {ivpsTraps 2}

---****************************************************************
--- ivpsCapacity
---****************************************************************

    ivpsCapacity OBJECT IDENTIFIER::={ivpsConfig 5}

    capaLineImpedanceBitmap OBJECT-TYPE
      SYNTAX OCTET STRING(SIZE(0..31))
      ACCESS read-only
      STATUS mandatory
      DESCRIPTION "This bitmap represents the current supported line impedance scheme
                  index, each bit stands for a line impedance type, those values are configured in CDE file.
              Bit 0:reserved
              Bit 1:default value. (default value of CDE profile)
              Bit 2:200 Ohm+(680 Ohm//100nF)
	      Bit 3:220 Ohm+(820 Ohm//120nF)
	      Bit 4:220 Ohm+(820 Ohm//120nF) miniSplitter
	      Bit 5:270 Ohm+(750 Ohm//150nF)
	      Bit 6:300 Ohm+(1000 Ohm//220nF)
	      Bit 7:370 Ohm+(620 Ohm//310nF)
	      Bit 8:600 Ohm
	      Bit 9:900 Ohm
	      Bit 10:370 Ohm+(620 Ohm//310nF) + Splitter
	      Bit 11:600 Ohm+ Splitter
              Bit 12:370NVLSASplitter
              Bit 13:370SkinnySplitter
              Bit 14:270DuratelSplitter
              Bit 15:2703MSplitter
              Bit 16:100Ohm+(1650Ohm//5nF)
              Bit 17:150Ohm+(510Ohm//47nF)
              Bit 18:220Ohm+Splitter
              Bit 19:schmReserved19
              Bit 20:schmReserved20
              Bit 21:schmReserved21
              Bit 22-31:reserved
              Syntax:1--support, 0==unsupport."
   ::={ivpsCapacity 1}

---****************************************************************
--- ivpsCapacity end
---****************************************************************

---****************************************************************
--- ivpsDBParams
---****************************************************************

    ivpsDBParams OBJECT IDENTIFIER::={ivpsConfig 6}

    ivpsSaveConfiguration OBJECT-TYPE
   	SYNTAX	INTEGER
   	{
   		save(1)
   	}
      ACCESS write-only
      STATUS mandatory
      DESCRIPTION "When this object is set to 'save', all unsaved configuration
            of XVPS will be saved to NT.
			- 7302/7330 ISAM-V  : Supported 
			- 7363 ISAM MX      : Not Applicable 
			- 7367 ISAM SX-12VP : Not Applicable
			."
   ::={ivpsDBParams 1}

    ivpsSaveConfigProgress OBJECT-TYPE
   	SYNTAX	INTEGER
   	{
   		ongoing(1),
   		finishedAndSuccessful(2),
   		finishedButFailed(3)
   	}
      ACCESS read-only
      STATUS mandatory
      DESCRIPTION "This object is used to sepcify the current status of saving configuration
           progress. The value can be one of the following three:ongoing(1),finishedAndSuccessful(2),
           finishedButFailed(3). 
		   - 7302/7330 ISAM-V  : Supported 
		   - 7363 ISAM MX      : Not Applicable 
		   - 7367 ISAM SX-12VP : Not Applicable
		   ."
   ::={ivpsDBParams 2}

---****************************************************************
--- ivpsDBParams   End
---****************************************************************

---****************************************************************
--- LINE TEST
---****************************************************************
-- *********************************************************************
-- In ISAM-V4.1, session management among H248-LT line test, SIP-LT line test, xDSL-LT line test(BBLT MELT) is different.
-- H248-LT line test:  
--    	1) only one session is supported for H248-LT line test from IVPS card.  
--	2) no session timer implementation for H248-LT  line test.
-- SIP-LT line test:
--  	1) Multiple sessions(max 8 sessions) supported for SIP-LT line test from NT card.
-- 	Multiple sessions line testing are applicable in different SIP-LTs: 
--         At the same time, one SIP-LT only can have one session.
--         When a session is on testing and another session comes, if they have ports in same SIP-LT, 
--         LTSS SWBB returns error to prompt another session has been testing on the same SIP-LT.
-- 	2) Provide session timer implementation, If one session created and no operation in session states of revcmd or revinfo 
--  within 30 minutes, the session will be destroyed by the LTSS SWBB automatically. In other session states, the session will 
--  not be destroyed by the LTSS SWBB automatically.
--	thus operator who really wants to do test could get the session.
--  xDSL-LT line test(BBLT MELT)
--	1) Multiple sessions(max 8 sessions) supported for BBLT MELT from NT card.
-- 	Multiple sessions line testing are applicable in different BBLTs: 
--         At the same time, one BBLT only can have one session.
--         When a session is on testing and another session comes, if they have ports in same BBLT, 
--         LTSS SWBB returns error to prompt another session has been testing on the same BBLT.
-- 	2) Provide session timer implementation, If one session created and no operation in session states of revcmd or revinfo 
--  within 30 minutes, the session will be destroyed by the LTSS SWBB automatically. In other session states, 
--  the session will not be destroyed by the LTSS SWBB automatically.
--	thus operator who really wants to do test could get the session.
--  3) Do not care the line port state. That��s to say, whether the port state is lock or unlock, we can do the xDSL line testing(BBLT MELT).

--*********************************************************************
-- Usage
--=================================================================
-- Begin:
--  sessionIdAvailable = get (ltSessionIdAvaiable)
--  if ( 0 == sessionIdAvailable ) // no available session.
--  {  // get ltMaxNumOfSession
--     getTable(ltSessionTable) // get all sessions in the table.
--      choice a session to cancel, according to ltSessionOwnerId
--     set(ltSessionCmd<in SessionTable> = destroy<Destroy the row>)
--        goto Begin
--  }
--  
--  set(ltSessionCmd<in SessionTable> = create<Create a row> with sessionIdAvailable as index)
--  set(   ltTimeOutPeriod 
--	       ltLineNum      
--         ltTestTypeHigh 
--         ltTestTypeLow  
--         ltTestParamNum 
--         ltTestMode
--         ltSessionOwnerId  <in SessionTable> ) 
--  for (n=0; n < lineNumToTest; n++)
--     set( ltLineIdStatus <in ltLineIdTable> = in_test ) //create n rows for n lines test
--  set(   testType 
--         value1   
--	       value2   
--	       value3   
--	       value4   
--	       value5  
--	       thresholdMin  // set test result threshold min to device
--	       thresholdMax // set test result threshold max to device <in ltTestParamTable> ) //set test param
--  set(ltSessionCmd<in SessionTable> = start_test<Change row status> with sessionIdAvailable as index)
-- 
--  WaitFlag = TRUE;
--  while( WaitFlag )
--  {
--    state = get( ltSessionState );
--    
--    switch(state){
--       case idle:
--       case rev_cmd:
--       case sta_error:
--          WaitFlag = FALSE;  
--					processErrorState();
--					break;
--       case run_cmd:
--       case rev_info:
--          sleep(xx);
--          break;
--       case test_over:
--          WaitFlag = FALSE
--          processGetTestResult()
--          break;
--       case testhold:
--          processGetTestedResult() //for continuous: only to get the results of tested rounds of all multi rounds.
--                                   //for interactive tests, only receive sub test's result.
--     }
--  }
--  set(ltSessionCmd<in SessionTable> = destroy<destroy row> with sessionIdAvailable as index)
--End:
--
--processErrorState
--{
--   // restart test or send error message to user.
--}
--processGetTestResutl()
--{
--    get( ltLineIdStatus, 
--         ltRpCommonStat,
--         ltRpValNum <in ltLineIdTable>)
--    if (ltLineIdStatus == test_over ) {
--        get ( ltStat,ltRpVal> int ltLineIdExtReportTable )// using sessionId,LineId,testType as index.
--    }
--}
--
--Interrupt process
--Now, we have only sevel test items which can be interrupted by network manager. 
--1.noise level 
-- eNormal_Noise_Level_Testing(39) 
--2.AC current 
-- eNormal_AC_CurrentTest_Testing_ab(32), 
-- eNormal_AC_CurrentTest_Testing_ag(33), 
-- eNormal_AC_CurrentTest_Testing_bg(34), 
--3.DC current 
-- eNormal_DC_CurrentTest_Testing_ab(35), 
-- eNormal_DC_CurrentTest_Testing_ag(36), 
-- eNormal_DC_CurrentTest_Testing_bg(37), 
--4.howler tone 
-- eNormal_Contition_Howler_Testing(41) 

--In phase2, these test items could be interrupted by network manager.
--1.Block/Continuous Read test(in fact, Block/Continuous is the test mode but not the test item.)
--2.Cable Pair Identification test
--3.Talking with Subscriber test
--4.Ring Subscriber with Auto Ring
--5.Line Reverse
--6.DP/DTMF Signal


--scenario: 
--// start a test... 
--// start interupt. 
--// change session state machine. 
--set ltSessionTable.ltSessionCmd = send_info 
--// set the interupt lineIdStatus. 
--for () // set every line need to be interupt 
-- set ltLineIdTable.ltLineIdStatus = in_test 
--
--// change session state machine. 
--set ltSessionTable.ltSessionCmd = start_info 
--
--
--=========================================================
--  Data Define
--  LTU8::= INTEGER(0..255) 
--  LTU16::= INTEGER(0..65535)  
--  LTU32::= Gauge
--  LTS32::= INTEGER   
     
  LTSessionCmd::= INTEGER
  {
    create(1),      	--create a test session, ready for test data transfering
    starttest(2),    	--transfer data done, start a test
    sendinfo(3),  	    --start to transfer info data for an underway testing, to cancel 1 or some lines' test task
    startinfo(4),      	--transfer info data done, start info operation
    destroy(5),         --destroy a test session
    receiveSubTest(6),  --start to transfer the sub test's data
    startSubTest(7),    --transfer sub test's data done, start the sub test
    repeat(8),          --repeat the last test, just for continuous mode test.
    endtest(9)          --end current test session.
  }           
                      
  LTSessionState::= INTEGER
  {
	  idle(1),               --indicate the session is not initialized, you can create it.
	  revcmd(2),         --indicate the session is recieving TEST cmd.
	  runcmd(3),         --indicate the session is running TEST cmd.
	  revinfo(4),          --indicate the session is recieving INFO cmd.
	  testover(5),        --indicate the session test is finished, you can get test result.
	  stateerror(6),      --something is wrong. 
	  testhold(7)         --indicate the session is held for sub test of talking test or 1 round is finished in continuous test. 
  }
  --NOTICE::OPERATOR COULD SEND DESTROY COMMAND @ TESTOVER STATUS, WHILE @ TESTHOLD STATUS, OPERATOR NEED ONLY GET TEST RESULTS!
                      
  LTLineIdStatus::= INTEGER
  {
  	intest(1),         -- put the line in the test. this is for write to put the lineId to test.
  	testover(2),       -- this line is tested, and the result is ready for polling.  this is read-only
  	rstpartlyready(3), -- it's defined for DP/DTMF test test, in this state, results partly are ready for tested rounds, network manager shall get these results but need re-read from first result(ltExtRpRstIndex=1) every time.
  	testrejected(4)    -- line test not supported for shared line, line test rejected.
  }

   LTLineIdHookChangeStatus::= INTEGER
  {
  	fromOffhooktoOnhook(1),   -- the tested line has hook state change, it from off hook to on hook
  	fromOnhooktoOffhook(2)    -- the tested line has hook state change, it from on hook to off hook
  }

  LTTestMode::= INTEGER
  {
    single(1),       -- default value, means the test needn't repeat in program, it will end after one time.
    block(2),        -- 20 rounds test will be done automatically by NBLT after test start, all results would be report together.
    continuous(3),   -- operator's program will send repeat command to NBLT to start a new round after receive last round's result.
    interactive(4),  -- the interactive test.
    cablepair(5)     -- the cable pair test.
  }
  -- !!! about test mode, please notice ::
  -- the block test would do 20 rounds automatically after recieve test start command, 
  -- and 20 rounds' results would be reported one time after 20 rounds done.
  -- while continuous test would do 1 round after start command, and would be re-started 
  -- by the repeat command sent out by Operator after get last round's result.
  -- !!!please be noticed, the repeat command is sent out automatically by operator's program(network manager..), 
  -- the test would be repeat and repeat untill the operator cancel or end the test. 
  -- Continuous does not has the limition of 20 rounds.
  -- Moreover:
  -- Block/Continuous test only support these test types:
  --   Foreign Voltage (AC/DC)
  --   Capacitance
  --   Insulation Resistance
  -- And only 1 of these test types could be set in 1 test requirement, that means u could not combine AC current of TR with
  -- any other test type, no matter it's AC current RG or Capacity of TR.

  -- for block test, the 20 rounds result are all available but for continuous, the next result would overwritten the last one.
  --    Finally, xDSL line test  only support the following values of test mode for NALT-M/NVLT-M lines:
  --    single(1),
  --    cablepair(5)
                        

LTSessionInputErrCode::= INTEGER
{
	noErr(0),				 -- 0  no error.
	ltTestParamNumInconsistent(1),           -- 1  the actual input param number in ltTestParamTable is not equal to ltTestParamNum.
 	ltTestParamNumOutOfRange(2),             -- 2  the input param number is out of range, from 0 to 4 is allowed.  
	testTypeNeedNoParam(3),                  -- 3  the input test param is meaningless, because those test types not need any test param.
        testParamForNonTestingType(4),           -- 4  the input test param for those test types which are not in current test session.
	missingltTestParamConfiguration(5),  	 -- 5  missing test param configuration for those test types which must have test param.
	missingltTimeOutPeriod(6),               -- 6  missing ltTimeOutPeriod value.
  	ltTimeOutPeriodNotEnough(7),	         -- 7  the input ltTimeOutPeriod is not enough for test.
	ltLineNumInconsistent(8),          	 -- 8  the actual input line number in ltLineIdTable is not equal to ltLineNum.
	ltLineNumOutOfRange(9),		         -- 9  the input line number is out of range, from 1 to 72 is allowed.
	invalidLineId(10),              	 -- 10 the input lineId is invalid.
        duplicatedLineId(11),                    -- 11 the same lineId configed twice
    	missingltTestType(12),                   -- 12 missing ltTestTypeHigh and ltTestTypeLow.
	invalidTestType(13),		         -- 13 the input ltTestTypeHigh and ltTestTypeLow is incorrect.
	thresholdNumOutOfRange(14),	         -- 14 input too many threshold, the number of threshold from 0 to 39 is allowed.
	testTypeNeedNoThreshold(15),             -- 15 the input threshold is meaningless, because those test types do not need any threshold.
	thresholdForNonTestingType(16),    	 -- 16 the input threshold for those test types which are not in current test session.
	testTypeMismatchTestMode(17),            -- 17 the input test type does not match with the test mode.
	ltlineNumMismatchTestModeOrTestType(18), -- 18 the input line number is not match test mode and test type. All talking test, cable pair test, block test and continuous test only support one line for certain test.
	wrongLineStatusForSubTest(19),       	 -- 19 the line status for subtest is not in holding or the line which has no father test first.
	oneTestItemForBlockOrContinousTest(20),  -- 20 block test and continous test must be only one test type
        lineIdInNonTestingStatus(21),               -- 21 the input lineId is not in testing status.
        testModeNotSupportRepeatTest(22),           -- 22 repeate test can only be done in continous test mode
        sessionStateIncorrect(23),                  -- 23 the command not allowed in current session state
	systemInternalError(24), 		    -- 24 internal system error
        sessionInactiveTimerOutOfRange(25),         -- 25 ltSessionInactiveTimer value out of range 
        ltTimeOutPeriodTooLong(26)                  -- 26 the input ltTimeOutPeriod is too long
}
                      
  LTCommonErrCode::= INTEGER
  {
    testUnFinished(0),                  -- 0   used as the original linetest status or not started because of missing subsequent command input.  
    testFinished(1),                    -- 1   used as the total logic result outcome.
    testStopedbyTimeOut(2),             -- 2   if the resetall cmd is arrived, the later coming test request is wrong.
    testCanceledbyOperator(3),          -- 3   as an error flag to construct the result package.
    testBreakedbyUser(5),               -- 5  stop while testing by user,eg: user on-hook before howler tone is sent out.
    testPPFailed(6),                    -- 6 PP Failed. Hardware failed. If LTCommonErrCode equals to testPPFailed(6), then the detail error code in each  test result unit structure will be explained to LTErrCode.
    testLineBusyInTestNow(8),           -- 8   The line is busy in used(such as call or other service)
    testLongTimeNoNextOperator(9),      -- 9 In continuous/talking test, long time no further operator(600s)
    testLineStatusError(11),            -- 11  LT Timer operator failed
    testOutofMemory(12),                -- 12  Fail to apply result buffer in LT board.
    testTimerOperateFail(13),           -- 13  Operation fail of timer.
    testTypeEmpty(14),                  -- 14  No test type in test request.
    testTypeLogicError(15),             -- 15  measurementNotSupported                    
    testTypeUnknown(16),                -- 16  the test command is illegal.   
    testParaLineIDError(17),            -- 17  the LineId in test command is not valid.              
    testParaOperateError(18),           -- 18  illegal operation
    testParaSerialNumError(19),         -- 19  error session ID
    testCurrentLineInTesting(21),       -- 21  the line is in another line test
    testOtherFail(22),                  -- 22  some other fail.
    testEndedbyOperator(23),            -- 23  the test was over because of end operation of operator
    testOnHookbyOperator(24),           -- 24  the test was over because operator on hook.
    testParaValueError(26),             -- 26  for DTMF TEST, Test Para Less than 1    
    testLineLluRelayConfigError(27),    -- 27  line LLURelay configuration not ok for MELT
    testSharedLineInServiceError(35),   -- 35  Shared Line does not support Line Test
    
    sessionTimeout(105),                -- 105 Test Session time out.
    invalidPortID(106),                 -- 106 LineId is not valid. 
    pOLTMessageMissing(107),            -- 107 LT msg is not recieved.
    redundancyPorts(110),               -- 110 Redundancy Port IDs for the testtype only support 1 port                   every test.
    wrongEndTestSequenceNumber(112),    -- 112 End command used wrong session ID.
    portDisable(114),                   -- 114 LT board is not available.
    pOLTFail(117),                      -- 117 LT board failed.
    portUnknownState(118),              -- 118 this line is in an unknown state.
    outOfMem(119),                      -- 119 xVPS or NT run out of memory.
    newTimerErr(120),                   -- 120 create timer failed.
    startTimerErr(121),                 -- 121 start timer failed.
    sendMsgErr(122),                    -- 122 send msg failed.
    getPortIpudpErr(123),               -- 123 get line ip/udp failed.
    portEnableLock(124),                -- 124 line enable but locked.
    portDisableUnlock(125),             -- 125 line disable and unlocked.
    portDisableLock(126),               -- 126 line disable and locked.
    abortTimerErr(127),                 -- 127 abort timer failed.
    emptyTestType(128),                 -- 128 the test type bitmap is empty
    testTypeMismatchWithMode(129),      -- 129 Test Type Mismatch With Test sMode
    portDisableNetUnlock(130),          -- 130 AdminState:Unlock, OperState:Disable from MGC
    portDisableVaUnlockGroundKey(131),        -- 131 AdminState:Unlock, OperState:Disable from AG(Ground Key) 
    portDisableVaUnlockOverCurrent(132),      -- 132 AdminState:Unlock, OperState:Disable from AG(Over Current)
    portDisableVaUnlockOverTemperature(133),  -- 133 AdminState:Unlock, OperState:Disable from AG(Over Temperature)
    portDisableNetLock(134),                  -- 134 AdminState:Lock, OperState:Disable from MGC
    portDisableVaLockGroundKey(135),          -- 135 AdminState:Lock, OperState:Disable from AG(Ground Key)
    portDisableVaLockOverCurrent(136),        -- 136 AdminState:Lock, OperState:Disable from AG(Over Current)
    portDisableVaLockOverTemperature(137),    -- 137 AdminState:Lock, OperState:Disable from AG(Over Temperature)
    portNotSupportLineTest(138),              -- 138 Line Test is not supported for the port.
    portUndergoinginMTATest(139),             -- the port is undergoing in MTA test now.
    testCurrentLTboardInTesting(140),         -- the board which has this session's test port is undergoing in another line test now.
    testFinishedAndPassed(141),               -- GR909 group test passed
    testFinishedAndFailed(142)                -- GR909 group test failed
  }

  LTErrCode::= INTEGER    -- If LTCommonErrCode equals to testPPFailed(6), then the detail error code in each  test result unit structure will be explained to this enum.
  {
    pPSuccess(1),
    pPErrNomMeasurementFailed(2),
    pPErrNomHookDetected(3),
    pPErrNomAlreadyRunning(4),
    pPErrNomNotImplemented(5),       
    pPErrNetOffhookDETECTED(6),
    pPErrNetInvalidOPMODE(7),
    pPErrNetOther(8),
    pPErrNetVinUnsupp(9),
    pPErrNetSlicUnsupp(10),
    testBeyondCDEThreshold(11),               
    testTimeout(12),
    testInterrupted(13),             -- test course was interrupted.
    testErrOther(14),
    testErrofVinetic(15),            -- error coursed by Vinetic chip
    testErrLineIsOnHook(16),         -- test ended by on hook event.
    testErrLineIsOffHook(17),        -- test ended by off hook event.
    testBeyondConfigedThreshold(18),  -- test result beyond the threshold that operator configed
    pPErrVinDegradedAccuracy(19),     -- the accuracy of the results are degraded because of low leakage resistance
                                      -- For impendence test, the resistance part is too low of an impedance compared with the capacitance part. 
                                      -- Repeat the test with a higher frequency to improve the accuracy.
		pPErrVinThermalFaultDetected(20),			-- a thermal fault was detected during the test, the results of the test are indeterminate
																					-- For impendence test, a very large capacitor is present. 
		pPErrVinExcessiveAcInduction(21),			-- excessive AC induction was detected during the test, the results of the test are indeterminate
																					-- For impendence test, the test cannot be executed due to an external AC fault.	
		pPErrVinCmSaturationDetected(22),			-- common mode saturation was detected during the test, the results of capacitance measurements could not be calculated.	
																					-- For impendence test, can repeat the test with a reduced common mode voltage value.	
		pPErrVinDiffSaturationDetected(23),		-- differential saturation was detected during the test, the results of capacitance measurements could not be calculated
																					-- For impendence test, can repeat the test with a reduced differential voltage value.
		pPErrVinExcessiveForeignVoltage(24),	-- a large foreign voltage prevented the respective tests from being executed
		pPErrVinCapacitorOutOfRange(25),			-- capacitor were too large to be measured		
		pPErrVinExcessiveLowResistance(26),	  -- the 3-element capacitance test has not been executed due to the presence of a very low fault resistance
		pPErrVinReceiverOffHook(27),					-- the 4-Element Resistance test has measured a low metallic resistance and the ROH test recognized it as a receiver off-hook, as opposed to a metallic fault.
		pPErrVinTestNotPassed(28),						-- test failed because the measured voltage never settled to within tolerancelimits. 
		pPErrVinGndReported(29),		          -- a single resistance to ground
		pPErrVinResistanceOutOfRange(30),	    -- Resistance were too large to be measured
		testErrLineStatusNotSupported(31),	  -- the related test item can not be executed in current line status.
		testItemNotApplicable(32),		        -- the related test item was not applicable
		passed(33),                           -- GR909 sub test passed
		failed(34),                            -- GR909 sub test failed
		voiceDialnosisDiallingRelease(35),
        voiceDialnosisAfterDialRelease(36),
        voiceDialnosisNoIncomingCall(37),
        voiceDialnosisOffHookRelease(38),
        voiceDialnosisNoAnswer(39),
        voiceDialnosisDTMFCheckFail(40),
        voiceDiagnosisNoDialTone(41),
    testErrLoopbackHWsetFailed(42),       -- ISDN PRA loopback setting failed
    testErrPatternCheckFailed(43)         -- ISDN PRA loopback pattern check failed 
  } 


  LTTestType::= INTEGER
  {
    eFEACofUserLineTestingTR(1),              --  1 Feeded AC RMS voltage of user line (Tip-Ring) */    
    eFEACofUserLineTestingTG(2),              --  2 Feeded AC RMS voltage of user line (Tip-Ground) */  
    eFEACofUserLineTestingRG(3),              --  3 Feeded AC RMS voltage of user line (Ring-Ground) */ 
    eFOACofUserLineTestingTR(4),              --  4 Foreign AC RMS voltage of user line (Tip-Ring) */
    eFOACofUserLineTestingTG(5),              --  5 Foreign AC RMS voltage of user line (Tip-Ground) */
    eFOACofUserLineTestingRG(6),              --  6 Foreign AC RMS voltage of user line (Ring-Ground) */
    eFEDCofUserLineTestingTR(7),              --  7 Feeded DC voltage of user line (Tip-Ring) */
    eFEDCofUserLineTestingTG(8),              --  8 Feeded DC voltage of user line (Tip-Ground) */
    eFEDCofUserLineTestingRG(9),              --  9 Feeded DC voltage of user line (Ring-Ground) */
    eFODCofUserLineTestingTR(10),             -- 10 Foreign DC voltage of user line (Tip-Ring)  */
    eFODCofUserLineTestingTG(11),             -- 11 Foreign DC voltage of user line (Tip-Ground)  */
    eFODCofUserLineTestingRG(12),             -- 12 Foreign DC voltage of user line (Ring-Ground)  */
    eFeedingCurrentTesting(13),               -- 13 Feeding current (Tip-Ring)                    */
    eFEDCofUserLineTestingRT(14),             -- 14 Feeded DC voltage of user line (Ring-Tip) */
    eInsulatingRofUserLineTestingTR(15),      -- 15 Insulating resistance of user line (Tip-Ring)*/
    eInsulatingRofUserLineTestingRT(16),      -- 16 Insulating resistance of user line (Ring-Tip)*/
    eInsulatingRofUserLineTestingTG(17),      -- 17 Insulating resistance of user line (Tip-Ground)*/
    eInsulatingRofUserLineTestingRG(18),      -- 18 Insulating resistance of user line (Ring-Ground)*/
    eInsulatingRBatofUserLineTestingT(19),   -- 19 Insulating battery resistance of user line (Tip-Bat)   */
    eInsulatingRBatofUserLineTestingR(20),   -- 20 Insulating battery resistance of user line (Ring-Bat)   */
    eCofUserLineTestingTR(21),                -- 21 Capacitance of user line (Tip-Ring)           */
    eCofUserLineTestingRT(22),                -- 22 Capacitance of user line (Ring-Tip)           */
    eCofUserLineTestingTG(23),                -- 23 Capacitance of user line (Tip-Ground)           */
    eCofUserLineTestingRG(24),                -- 24 Capacitance of user line (Ring-Ground)           */
    eImpedanceofUserCircuitTestingTR(25),     -- 25 Impedance of user circuit (Tip-Ring)      */
    eImpedanceofUserCircuitTestingRT(26),     -- 26 Impedance of user circuit (Ring-Tip)  */
    eImpedanceofUserCircuitTestingTG(27),     -- 27 Impedance of user circuit (Tip-Ground)          */
    eImpedanceofUserCircuitTestingRG(28),     -- 28 Impedance of user circuit (Ring-Ground)          */
    eLowCapcitancePhoneDetect(29),            -- 29 Low Capacitance phone detect, changed from dayong.wang*/
    eForceRingSubscriber(30),                 -- 30 Force Ring Subscriber test               */
    eDTDelayofUserCircuitTesting(31),         -- 31 Dial Tone Delay of user circuit only in Idle*/
    eTerminationTesting(32),                  -- 32 Termination  ( M Socket detection )            */
    eNormalACCurrentTestTestingTR(33),        -- 33 AC Current Test Normal Test (Tip-Ring)           */
    eNormalACCurrentTestTestingTG(34),        -- 34 AC Current Test Normal Test (Tip-Ground)           */
    eNormalACCurrentTestTestingRG(35),        -- 35 AC Current Test Normal Test (Ring-Ground)          */
    eNormalDCCurrentTestTestingTR(36),        -- 36 DC Current Test Normal Test (Tip-Ring)           */
    eNormalDCCurrentTestTestingTG(37),        -- 37 DC Current Test Normal Test (Tip-Ground)           */
    eNormalDCCurrentTestTestingRG(38),        -- 38 DC Current Test Normal Test (Ring-Ground)           */
    eNormalNoiseLevelTesting(40),             -- 40 Noise Level Normal Test                          */
    eNormalContitionHowlerTesting(42),        -- 42 Howler Test Under Normal Test Condition only in Parking */
    eStatusMonitoredTesting(44),              -- 44 Status Monitored Test*/
    eCablePairIdentification(45),             -- 45 Cable Pair Identification Test
    eTalkingtest(46),                         -- 46 Talking test (father test item)
    eLinereverse(47),                         -- 47 Line Reverse test, subtest of talking test
    ePrivateMeterPulses(48),                  -- 48 Private Meter Pulses test, subtest of talking test
    eRingSubscriber(49),                      -- 49 Ring Subscriber with Auto Ring test, subtest of talking test
    eDPDTMFSignal(50),                        -- 50 DP/DTMF Signal test, subtest of talking test
    eRofUserLoopTesting(51),                  -- 51 Resistance of user loop (Tip-Ring), subtest of talking test */
    eCapacitanceOfSignature(52),              -- 52 Capacitance of ETSI signature or electronic ringer */ 
    eResistanceOfRinger(53),                  --53 Resistance of ETSI signature of electronic ringe  */
    eISDNLoopBack(54),			                  --54 ISDN Loop Back test  */
    eLongitudinalCurrentTesting(55),          --55  Measurement of the difference between the currents on the a-lead and the b-lead (longitudinal current) */
    eVoiceDiagnosisH248Caller(56),            -- 56 H248 Voice Diagnosis Caller */
    eVoiceDiagnosisH248Callee(57),            -- 57 H248 Voice Diagnosis Callee	 */
    eConductanceOfUserLineTestingTR(58),      -- 58 Conductance of user line (Tip-Ring) */
    eConductanceOfUserLineTestingTG(59),      -- 59 Conductance of user line (Tip-Ground) */
    eConductanceOfUserLineTestingRG(60),      -- 60 Conductance of user line (Ring-Ground)  */
    eSusceptanceOfUserLineTestingTR(61),      -- 61 Susceptance of user line (Tip-Ring) */
    eSusceptanceOfUserLineTestingTG(62),      -- 62 Susceptance of user line (Tip-Ground) */
    eSusceptanceOfUserLineTestingRG(63),      -- 63 Susceptance of user line (Ring-Ground) */
    eHazardousVoltageTesting(64),             -- 64 Voltage detected hazardous to person */
    eGalvanicSignatureTesting(65),            -- 65 Galvanic signature detected   */
    eCapacitiveEndDeviceTesting(66),          -- 66 End device capacitance > 50 nF detected  */
    ePPAVariantTesting(67),                   -- 67 PPA variant testing  */
    eTerminationRohTesting(68),               -- 68 Receiver off-hook detected testing  */
    eTerminationElecRingerTesting(69),        -- 69 Electronic ringer detected testing */
    eGR909RingerTesting(70),                  -- 70 GR909 Ringer Equivalency Number testing	 */
    eGR909DrawAndBreakDialToneDelay(71),      -- 71 GR909 Draw and Break Dial Tone Delay testing  */
    eGR909RohTesting(72),                     -- 72 GR909 Receiver Off-Hook testing */
    eGR909HazardousPotential(73),             -- 73 GR909 Hazardous Potential testing */
    eGR909ForeignElectromotive(74),           -- 74 GR909 Foreign ElectroMotive Force testing */
    eGR909ResistiveFaults (75),               -- 75 GR909 Resistive Faults testing */
    eZenerResistance(76),                     -- 76 electronic Zener Resistance testing */
    eZenerVoltage(77),                        -- 77 electronic Zener Voltage testing */
    eISDNPraRemoteLoopBack(78),               -- 78 ISDN PRA Remote Loop Back test */
    eISDNPraPayloadLoopBack(79),              -- 79 ISDN PRA Payload Loop Back test */
    eISDNPraLocalLoopBack(80),                -- 80 ISDN PRA Local Loop Back test */
    eISDNPraCableLoopBack(81)                 -- 81 ISDN PRA Cable Loop Back test */
  }
  
  -- This is used in ltRpVal in ltLineIdExtReportTable. for HowlerTone test
  LTHowlerToneTestResult::= INTEGER
  {
    playSuccessfulAndOnHookNormal(1),
    playSuccessfulAndTestTerminated(2),
    playSuccessfulButOnHookTimeout(3), 
    playFailed(4)
  } 
  -- This is used in ltRpVal in ltLineIdExtReportTable. for StatusMonitor test 
  LTStatusMonitoredTestResult::= INTEGER
  {
    eStatusMonitoredBlock(2),  
    eStatusMonitoredIdle(3), 
    eStatusMonitoredBusy(4), 
    eStatusMonitoredParking(5),
    eStatusMonitoredShort(6) 
  }

  -- This is used in ltRpVal in ltLineIdExtReportTable. for Cable pair identify test
  LTTraceToneTestResult::= INTEGER
  {
    playTraceToneOKTestTerminated(1),
    playTraceToneOKTimeout(2),
    playTraceToneFailed(3),
    stopTraceToneFailed(4)
  }

  LTMeterTestResult::= INTEGER
  {
    meterSuccess(1),
    meterFailed (2)
  }

  -- This is used in ltRpVal in ltLineIdExtReportTable. for line reverse test
  LTLineReverseTestResult::= INTEGER
  {
    lineReverseOKTestTerminated(1),
    lineReverseOKTimeout(2),
    lineReverseFailed(3)
  }

  -- This is used in ltRpVal in ltLineIdExtReportTable. for RingSubscriber test
  LTRingSubscriberTestResult::= INTEGER
  {
    ringSuccessfulAndTestTerminated(1),
    ringSuccessfulAndStopedByOffHook(2),
    ringSuccessfulAndTimeout(3), 
    ringFailed(4),
    ringFailedBecausePortisOffHook(5),
    ringStopFailed(6)
  } 

  -- This is used in ltRpVal in ltLineIdExtReportTable. for DP/DTMF Signal test
  LTDPDTMFSignalTestResult::= INTEGER
  {
    numberDP1(1),
    numberDP2(2),
    numberDP3(3),
    numberDP4(4),
    numberDP5(5),
    numberDP6(6),
    numberDP7(7),
    numberDP8(8),
    numberDP9(9),
    numberDP0(10),
    starDP(11),      --*
    poundDP(12),     --#
    numberDTMF1(65537),      
    numberDTMF2(65538),      
    numberDTMF3(65539),      
    numberDTMF4(65540),      
    numberDTMF5(65541),      
    numberDTMF6(65542),      
    numberDTMF7(65543),      
    numberDTMF8(65544),      
    numberDTMF9(65545),      
    numberDTMF0(65546),      
    starDTMF(65547),      --*
    poundDTMF(65548)      --#
  } 

 -- This is used in ltRpVal in ltLineIdExtReportTable. for loopback test
LTLoopbackTestResult::= INTEGER
{
    testSuccess(1),
    l1LoopFailOnNT(2),
    l1PatternFailOnNT(3),
    l1LoopFailOnLT(4),
    l1PatternFailOnLT(5),
    l1LoopFailOnNTandLT(6),
    l1LoopFailonNTPatternFailOnLT(7),
    l1PatternFailOnNTLoopFailOnLT(8),
    l1PatternFailOnNTandLT(9)
}

-- This is used for hazardous voltage testing.    
LTHazardousVoltageResult::= INTEGER
{
    noHazardousVoltage(1),
    hazardousVoltage(2)
}

-- This is used for PPA variant testing.    
LTPPAResult::= INTEGER
{
    ppa(1),
    ppaInvers(2),
    ppaNotDetected(3),
    ppaAnalysisNotAvailable(4)
}

-- This is used for Force Ring Subscriber testing
LTForceRingResult::= INTEGER
{
    noResult(0),
    terminatedByOperator(1),
    breakByUserHookChange(2),
    forceRingTimeOut(3)
}

-- This is used for ltBusyStatus in ltBusyPortTable.   
LtBusyStatus::= INTEGER
{
    toBeTested(1),       -- Te line is in the test queue and will be tested.        
    inMeasurement(2),    -- The line is currently in measurement.
    inSearchTone(3),     -- The line is currently in search tone.
    testFinished(4)      -- Test on this line is finished.
}

-- This is used for ltGroupTestOption to specify group/collective test types.
LTGroupTestOpt::= INTEGER
{
    none(1),                  -- Normal group test
    extended(2),              -- Group test with extended report values
    pots-collective(3),       -- Collective test for POTS
    melt-collective(4)        -- Collective test for MELT
}  

-- This is used in ltRpVal in ltLineIdExtReportTable for isdn pra remote loopback test.
LTPraRemoteLBTestResult::= INTEGER
{
   testEnvSetUpSuccess(1),              -- remote loopback setting is successful
   testEnvSetUpFailed(2),               -- remote loopback setting is failed
   testSessionTerminatedByOperator(3),  -- remote loopback session terminated by operator
   testSessionTimeout(4)                -- remote loopback session timed out
}

-- This is used in ltRpVal in ltLineIdExtReportTable for isdn pra payload loopback test.
LTPraPayloadLBTestResult::= INTEGER
{
   testEnvSetUpSuccess(1),              -- payload loopback setting is successful 
   testEnvSetUpFailed(2),               -- payload loopback setting is failed
   testSessionTerminatedByOperator(3),  -- payload loopback session terminated by operator
   testSessionTimeout(4)                -- payload loopback session timed out
}

-- This is used in ltRpVal in ltLineIdExtReportTable for isdn pra local loopback test.
LTPraLocalLBTestResult::= INTEGER
{
    successful(1),            -- test is successful including local loopback setting and pattern check
    hwSetFailed(2),           -- local loopback or MSP setting failed and pattern check not implemented
    patternMismatch(3)        -- local loopback setting is successful but pattern check failed
}

-- This is used in ltRpVal in ltLineIdExtReportTable for isdn pra cable loopback test.
LTPraCableLBTestResult::= INTEGER
{
    successful(1),            -- test is successful including cable loopback setting and pattern check
    hwSetFailed(2),           -- cable loopback or MSP setting failed and pattern check not implemented
    patternMismatch(3)        -- cable loopback setting is successful but pattern check failed
}


-- Next available sessionId
ltSessionIdAvaiable OBJECT-TYPE
      SYNTAX INTEGER(0..255)
      ACCESS read-only
      STATUS mandatory
      DESCRIPTION "the byte indicate the next available sessionId. 
      Actually, its range is  [1,ltMaxNumberOfSession]. 
      As ltMaxNumberOfSession is set 16 in ALCATEL-LUCENT, so its range is [1,16]      
       0: No available sessionId. 
       1-ltMaxNumberOfSession: the available sessionId.
       
	ALCATEL-LUCENT NOTE:
		ACCESS:     RO
		USAGE:       MAND
		PERSIST:   	NO
		INSRVMOD: 	NA
		RANGE:	(1..16)
		DEFVALUE:  NA
		UNITS:	NA
		SPARSE: NO"
   ::= {ltLineTest 1}

ltMaxNumberOfSession OBJECT-TYPE
      SYNTAX INTEGER(0..255)
      ACCESS read-only
      STATUS mandatory
      DESCRIPTION "the byte indicate the max number of sessions. 
       If this number is (n), then the ltSessionId of ltSessionTable is in [1, n]. 
	ALCATEL-LUCENT NOTE:
		ACCESS:     RO
		USAGE:       MAND
		PERSIST:   	NO
		INSRVMOD: 	NA
		RANGE:	(0..255)
		DEFVALUE:  NA
		UNITS:	NA
		SPARSE: NO"
   ::= {ltLineTest 2}
      
--Session Table   
ltSessionTable OBJECT-TYPE
    SYNTAX SEQUENCE OF LtSessionEntry
    ACCESS not-accessible
    STATUS mandatory
    DESCRIPTION "Test Session Table. For network manager to create session, destroy session. 
      ALCATEL-LCENT NOTE: 
		TABLESIZE: 16
		DESCR:NA."   
 ::= {ltLineTest 3}

ltSessionEntry OBJECT-TYPE
    SYNTAX LtSessionEntry
    ACCESS not-accessible
    STATUS mandatory
    DESCRIPTION "Test Session Table Entry." 
    INDEX { ltSessionId }
   ::= {ltSessionTable 1}
   
LtSessionEntry::= SEQUENCE
{
   ltSessionId      INTEGER,
   ltSessionCmd     LTSessionCmd,   
   ltSessionStatus  LTSessionState,
   ltSessionOwnerId Gauge,
   ltTimeOutPeriod  Gauge, 
   ltLineNum        INTEGER, 
   ltTestTypeHigh   Gauge, 
   ltTestTypeLow    Gauge,  
   ltTestParamNum   INTEGER,
   ltTestMode       LTTestMode,
   ltTestTypeString OCTET STRING (SIZE (1..255)),   
   ltSessionInputErrCode  LTSessionInputErrCode,
   ltSessionInactiveTimer INTEGER,
   ltSessionBusyOverwrite  TruthValue,
   ltTestTypeExtend Gauge,
   ltGroupTestOption LTGroupTestOpt,
   ltSessionForcedTest TruthValue
}

ltSessionId OBJECT-TYPE
    SYNTAX INTEGER(1..255)
    ACCESS not-accessible
    STATUS mandatory
    DESCRIPTION "Index of the table. 
    Actually, its range is  [1,ltMaxNumberOfSession]. 
    As ltMaxNumberOfSession is set 16 in ALCATEL-LUCENT, so its range is [1,16]  
 	ALCATEL-LUCENT NOTE:
		ACCESS:     NA
		USAGE:       NA
		PERSIST:   	NO
		INSRVMOD: 	NA
		RANGE:	(1..16)
		DEFVALUE:  NA
		UNITS:	NA
		SPARSE: NO"
  ::= {ltSessionEntry 1}
   
ltSessionCmd   OBJECT-TYPE
   SYNTAX     LTSessionCmd
   ACCESS     read-write
   STATUS     mandatory
   DESCRIPTION "This MIB object is used to control the actions on the Test session 
    create create a test session, ready for test data transfering 
    starttest transfer data done, start a test 
    sendinfo start to transfer info data for an underway testing, to cancel 1 or some lines' test task 
    startinfo transfer info data done, start info operation 
    destroy destroy a test session 
    receiveSubTest start to transfer the sub test's data 
    startSubTest transfer sub test's data done, start the sub test 
    repeat repeat the last test, just for continuous mode test. 
    endtest end current test session. 
    if the MELT session is not created/initialized, this object can have a value of 0.
	ALCATEL-LUCENT NOTE:
		ACCESS:     RW
		USAGE:       MAND
		PERSIST:   	NO
		INSRVMOD: 	NA
		RANGE:	NA
		DEFVALUE:  NA
		UNITS:	NA
		SPARSE: NO"
	::= {ltSessionEntry 2}  

ltSessionStatus   OBJECT-TYPE
     SYNTAX     LTSessionState
     ACCESS     read-only
     STATUS     mandatory
     DESCRIPTION "This MIB object is used to show the session status
	    idle				indicate the session is not initialized, you can create it.
	    revcmd			indicate the session is recieving TEST cmd.
	    runcmd			indicate the session is running TEST cmd.
	    revinfo			indicate the session is recieving INFO cmd.
	    testover		indicate the session test is finished, you can get test result.
	    stateerror	something is wrong. 
	    testhold		indicate the session is held for sub test of talking test or 1 round is finished in continuous test. 
	ALCATEL-LUCENT NOTE:
		ACCESS:     RO
		USAGE:       MAND
		PERSIST:   	NO
		INSRVMOD: 	NA
		RANGE:	NA
		DEFVALUE:  NA
		UNITS:	NA
		SPARSE: NO"
  ::= { ltSessionEntry 3}  

ltSessionOwnerId   OBJECT-TYPE
     SYNTAX     Gauge
     ACCESS     read-write
     STATUS     mandatory
     DESCRIPTION "OwnerId of the session. This is appointed by network manager itself.
	ALCATEL-LUCENT NOTE:
		ACCESS:     RW
		USAGE:       MAND
		PERSIST:   	NO
		INSRVMOD: 	NA
		RANGE:	NA
		DEFVALUE:  NA
		UNITS:	NA
		SPARSE: NO"
  ::= { ltSessionEntry 4}  
	  
ltTimeOutPeriod   OBJECT-TYPE
   SYNTAX     Gauge
   ACCESS     read-write
   STATUS     mandatory
   DESCRIPTION "A parameter used to set the whole test timer including all test items of all lines for the session. Unit(s)
ltTimeOutPeriod should be larger than or equal to the sum of all lines' limited time plus line test management time (TIME_LENGTH_BUFFER_BASED_LT_NEED<2s>).
Each line's limited time is the sum of all the test items' limited time in this line.

Line Test management time per session.
TIME_LENGTH_BUFFER_BASED_LT_NEED                    2s

Below is the limitd time of each test item of each line for NBLT MELT 
TIME_LENGTH_LIMITE_GROUP                            15s+5s(5s is the delay time of discharge)
TIME_LENGTH_LIMITE_FE_AC_OF_USERLINE                3s
TIME_LENGTH_LIMITE_FO_AC_OF_USERLINE                10s
TIME_LENGTH_LIMITE_FE_DC_OF_USERLINE                3s
TIME_LENGTH_LIMITE_FO_DC_OF_USERLINE                10s+5s(5s is the delay time of discharge)
TIME_LENGTH_LIMITE_FEEDING_CURRENT                  3s
TIME_LENGTH_LIMITE_R_OF_USERLOOP                    6s
TIME_LENGTH_LIMITE_INSULATING_R_OF_USERLINE         6s
TIME_LENGTH_LIMITE_C_OF_USERLINE                    15s
TIME_LENGTH_LIMITE_IMPEDANCE_OF_USERCIRCUIT         5s
TIME_LENGTH_LIMITE_LOW_CAP_DETECT                   20s
TIME_LENGTH_LIMITE_FORCE_RING_SUBSCRIBE             120s
TIME_LENGTH_LIMITE_DT_DELAY_OF_USERCIRCUIT          8s
TIME_LENGTH_LIMITE_M_SOCKET                         6s 
TIME_LENGTH_LIMITE_NORMAL_AC_CURRENTTEST            66s
TIME_LENGTH_LIMITE_NORMAL_DC_CURRENTTEST            66s
TIME_LENGTH_LIMITE_NORMAL_NOISE_LeveL               66s
TIME_LENGTH_LIMITE_NORMAL_CONDITION_Howler          120s
TIME_LENGTH_LIMITE_STATUS_MONITORED                 3s
TIME_LENGTH_LIMITE_CABLE_PAIR_IDENTITY              65s
TIME_LENGTH_LIMITE_TALKING                          3s 
TIME_LENGTH_LIMITE_TALKING_HOLDING                  600s 
TIME_LENGTH_LIMITE_TALKING_TEST_LINE_REVERSE        5s
TIME_LENGTH_LIMITE_TALKING_TEST_METER_PULSE         6s
TIME_LENGTH_LIMITE_TALKING_TEST_RING                60s
TIME_LENGTH_LIMITE_TALKING_TEST_DTMF                60s
TIME_LENGTH_LIMITE_ISDN_LOOPBACK                    20s
TIME_LENGTH_LIMITE_LONGITUDINAL_CURRENT             3s
TIME_LENGTH_LIMITE_INCLUDE_ELECTRONIC_RINGER        10s
TIME_LENGTH_LIMITE_TERM_CAPACITIVE                  15s
TIME_LENGTH_LIMITE_PPA_VARIANT                      15s
TIME_LENGTH_LIMITE_ROH_ZENER                        8s
TIME_LENGTH_LIMITE_DT_DELAY_OF_USERCIRCUIT          8s
TIME_LENGTH_LIMITE_GR909_RINGER_ROH_HP_FEMF_RF      20s
TIME_LENGTH_LIMITE_GR909_DIALTONE_DELAY             8s
TIME_LENGTH_LIMITE_ISDNPRA_REMOTE_LOOPBACK          2s
TIME_LENGTH_LIMITE_ISDNPRA_PAYLOAD_LOOPBACK         2s
TIME_LENGTH_LIMITE_ISDNPRA_LOCAL_LOOPBACK           4s
TIME_LENGTH_LIMITE_ISDNPRA_CABLE_LOOPBACK           2s
Below is the limitd time of each test item of each line for xDSL line test(BBLT MELT)
TIME_LENGTH_LIMITE_GROUP_MELT                       18s
TIME_LENGTH_LIMITE_INCLUDE_ETSI_SIGNATURE_MELT      18
TIME_LENGTH_LIMITE_FO_AC_OF_USERLINE_MELT           5s
TIME_LENGTH_LIMITE_FO_DC_OF_USERLINE_MELT           5s
TIME_LENGTH_LIMITE_INSULATING_R_OF_USERLINE_MELT    18s
TIME_LENGTH_LIMITE_C_OF_USERLINE_MELT               18s
TIME_LENGTH_LIMITE_CABLE_PAIR_IDENTITY              65s
TIME_LENGTH_LIMITE_ILTF_ANALYSIS_DATA_MELT          20s
	ALCATEL-LUCENT NOTE:
		ACCESS:     RW
		USAGE:       MAND
		PERSIST:   	NO
		INSRVMOD: 	NA
		RANGE:	NA
		DEFVALUE:  NA
		UNITS:	NA
		SPARSE: NO"
  ::= {ltSessionEntry 5}  

ltLineNum   OBJECT-TYPE
   SYNTAX     INTEGER(1..255)
   ACCESS     read-write
   STATUS     mandatory
   DESCRIPTION "A parameter for the session. Indicate how many LINEs in the session for test, 
     it's to say there are ltLineNum rows in ltLineIdTable for this session. range: [1,72]
     if the MELT session is not created/initialized, this object can have a value of 0.
	ALCATEL-LUCENT NOTE:
		ACCESS:     RW
		USAGE:       MAND
		PERSIST:   	NO
		INSRVMOD: 	NA
		RANGE:	(1..72)
		DEFVALUE:  NA
		UNITS:	NA
		SPARSE: NO"
  ::= {ltSessionEntry 6}  
	  
ltTestTypeHigh   OBJECT-TYPE
   SYNTAX     Gauge
   ACCESS     read-write
   STATUS     mandatory
   DESCRIPTION "A parameter for the session. Indicate line test items. 
				With ltTestTypeLow and ltTestTypeExtend they are a 96bit bitmap for test items.
    --bit31, FE_AC_of_UserLine_Testing(tr),              unit : uV (10E-6V) 
    --bit30, FE_AC_of_UserLine_Testing(tg),              unit : uV (10E-6V) 
    --bit29, FE_AC_of_UserLine_Testing(rg),              unit : uV (10E-6V) 
    --bit28, FO_AC_of_UserLine_Testing(tr),              unit : uV (10E-6V) 
    --bit27, FO_AC_of_UserLine_Testing(tg),              unit : uV (10E-6V) 
    --bit26, FO_AC_of_UserLine_Testing(rg),              unit : uV (10E-6V) 
    --bit25, FE_DC_of_UserLine_Testing(tr),              unit : uV (10E-6V) 
    --bit24, FE_DC_of_UserLine_Testing(tg),              unit : uV (10E-6V)
    --bit23, FE_DC_of_UserLine_Testing(rg),              unit : uV (10E-6V)
    --bit22, FO_DC_of_UserLine_Testing(tr),              unit : uV (10E-6V) 
    --bit21, FO_DC_of_UserLine_Testing(tg),              unit : uV (10E-6V) 
    --bit20, FO_DC_of_UserLine_Testing(rg),              unit : uV (10E-6V) 
    --bit19, Feeding_Current_Testing,                    unit : uA (10E-6A)                
    --bit18, FE_DC_of_UserLine_Testing(rt),              unit : uV (10E-6V)                     
    --bit17, Insulating_R_of_UserLine_Testing(tr),       unit : ohm
    --bit16, Insulating_R_of_UserLine_Testing(rt),       unit :ohm
    --bit15, Insulating_R_of_UserLine_Testing(tg),       unit : ohm
    --bit14, Insulating_R_of_UserLine_Testing(rg),       unit : ohm
    --bit13, Insulating_R_Bat_of_UserLine_Testin(gt),   unit : ohm
    --bit12, Insulating_R_Bat_of_UserLine_Testin(gr),   unit : ohm
    --bit11, C_of_UserLine_Testing(tr),                  unit : pF
    --bit10, C_of_UserLine_Testing(rt),                  unit : pF
    --bit09, C_of_UserLine_Testing(tg),                  unit : pF
    --bit08, C_of_UserLine_Testing(rg),                  unit : pF
    --bit07, Impedance_of_UserCircuit_Testing(tr),       unit : ohm
    --bit06, Impedance_of_UserCircuit_Testing(rt),       unit : ohm
    --bit05, Impedance_of_UserCircuit_Testing(tg),       unit : ohm
    --bit04, Impedance_of_UserCircuit_Testing(rg),       unit : ohm
    --bit03, Low_Capcitance_PhoneDetect,                 TRUE(1) or FLASE(0)
    --bit02, Force_Ring_Subscriber,                      enum LTForceRingResult
    --bit01, DT_Delay_of_UserCircuit_Testing,        unit : ms                          
    --bit00, Termination_Testing(M Socket),          TRUE(1) or FLASE(0)      
	ALCATEL-LUCENT NOTE:
		ACCESS:     RW
		USAGE:       MAND
		PERSIST:   	NO
		INSRVMOD: 	NA
		RANGE:	NA
		DEFVALUE:  NA
		UNITS:	NA
		SPARSE: NO"
 ::= {ltSessionEntry 7}  
 
ltTestTypeLow   OBJECT-TYPE
   SYNTAX     Gauge
   ACCESS     read-write
   STATUS     mandatory
   DESCRIPTION "A parameter for the session. Indicate line test items. 
				With ltTestTypeHigh and ltTestTypeExtend they are a 96bit bitmap for test items.
    --bit31, Normal_AC_CurrentTest_Testing(tr),          unit : uV (10E-6V) 
    --bit30, Normal_AC_CurrentTest_Testing(tg),          unit : uV (10E-6V) 
    --bit29, Normal_AC_CurrentTest_Testing(rg),          unit : uV (10E-6V) 
    --bit28, Normal_DC_CurrentTest_Testing(tr),          unit : uV (10E-6V) 
    --bit27, Normal_DC_CurrentTest_Testing(tg),          unit : uV (10E-6V) 
    --bit26, Normal_DC_CurrentTest_Testing(rg),          unit : uV (10E-6V) 
    --bit24, Normal_Noise_Level_Testing,                 unit : 0.001dbm                   
    --bit22, Normal_Contition_Howler_Testing,              enum LTHowlerToneTestResult 
    --bit20, Status_Monitored_Testing,                     enum LTStatusMonitoredTestResult
    --bit19, Cable Pair Identification Test,               enum LTTraceToneTestResult
    --bit18, Talking test (father test item),              enum LTMeterTestResult
    --bit17, Line Reverse test,   subtest of talking test, enum LTLineReverseTestResult
    --bit16, Private Meter Pulses test,   subtest of talking test, logic result
    --bit15, Ring Subscriber with Auto Ring test, subtest of talking test, enum LTRingSubscriberTestResult
    --bit14, DP/DTMF Signal test, subtest of talking test, enum LTDPDTMFSignalTestResult
    --bit13, R_of_UserLoop_Testing,                       unit : ohm    
    --bit12, Capacitance of Signature,                   unit:pF
    --bit11, Resistance of Ringer,                       unit:ohm
    --bit10,ISDN Loop Back,			         enum LTLoopbackTestResult
    --bit9, Longitudinal Current Testing,  unit : uA (10E-6A)
    --bit8, H248 Voice Diagnosis Caller, 				
	--bit7, H248 Voice Diagnosis Callee,			
	--bit6, Conductance_of_User_Line_Testing(tr),       unit : uS/10
	--bit5, Conductance_of_User_Line_Testing(tg),       unit : uS/10
	--bit4, Conductance_of_User_Line_Testing(rg),       unit : uS/10
	--bit3, Susceptance_of_User_Line_Testing(tr),       unit : uS/10
	--bit2, Susceptance_of_User_Line_Testing(tr),       unit : uS/10
	--bit1, Susceptance_of_User_Line_Testing(tr),       unit : uS/10
    --bit0, Hazardous Voltage Testing,                  enum LTHazardousVoltageResult  
    bitmap construct rules:
		we sort all tests into 5 different class by their attribute, and only tests of the same attribute could exist in one session. 
		1) all attribute was defined here: 
		 enum eLineTestAttribute{
  		      Electric,                     // 0    electric parameter test(R,vol,C,current)
        	      DialTone,                     // 1    especially for dail tone test,
                      AC_DC_CURRENT,              // 2 especially for AC/DC current test, for it need 2 commands: START or END.
        	      NOISE_LEVEL,                  // 3    only for noise level
        	      HowlerTone,                   // 4    only for howler tone test.
        	      StatusMonitored,              // 5    only for statusMonitored test.
      		      TalkingTest,                  // 6    2006.11.25, added for line testing phase 2
       		      TalkingSubTestDtmf,           // 7   2006.11.25, added for line testing phase 2
        	      TalkingSubTestOther,          // 8    2006.11.25, added for line testing phase 2
        	      CablePairIdentity,            // 9    2006.12.3, added for line testing phase 2
        	      Electric_OnlyIdle,            // 10  ANTmt52585, Msocket can only be done in IDLE, yuandax, 2009-04-13
        	      ISDN_loopback_test,           // 11  ISDN loopback test
        	      VoiceDiagnosisH248Caller,     // 12
        	      VoiceDiagnosisH248Callee,     // 13
        	      Butt_LineTestAttribute,       // 14
        	      ForceRing,                    //15
                  ISDN_PRA_loopback_test        //16  ISDN PRA loopback test
		};
		2) the relationship between every test and these attribute was described like this table: 
		eFE_AC_of_UserLine_Testing_tr , Electric
		eFE_AC_of_UserLine_Testing_tg , Electric
		eFE_AC_of_UserLine_Testing_rg , Electric
		eFO_AC_of_UserLine_Testing_tr , Electric 
		eFO_AC_of_UserLine_Testing_tg , Electric 
		eFO_AC_of_UserLine_Testing_rg , Electric 
		eFE_DC_of_UserLine_Testing_tr , Electric 
		eFE_DC_of_UserLine_Testing_tg , Electric 
		eFE_DC_of_UserLine_Testing_rg , Electric 
		eFO_DC_of_UserLine_Testing_tr , Electric 
		eFO_DC_of_UserLine_Testing_tg , Electric 
		eFO_DC_of_UserLine_Testing_rg , Electric 
		eFeeding_Current_Testing ,      Electric 
		eR_of_UserLoop_Testing ,        Electric 
		eInsulating_R_of_UserLine_Testing_tr , Electric 
		eInsulating_R_of_UserLine_Testing_rt , Electric 
		eInsulating_R_of_UserLine_Testing_tg , Electric 
		eInsulating_R_of_UserLine_Testing_rg , Electric 
		eInsulating_R_Bat_of_UserLine_Testing_t, Electric 
		eInsulating_R_Bat_of_UserLine_Testing_r, Electric 
		eC_of_UserLine_Testing_tr , Electric 
		eC_of_UserLine_Testing_rt , Electric 
		eC_of_UserLine_Testing_tg , Electric 
		eC_of_UserLine_Testing_rg , Electric 
		eImpedance_of_UserCircuit_Testing_tr , Electric 
		eImpedance_of_UserCircuit_Testing_rt , Electric 
		eImpedance_of_UserCircuit_Testing_tg , Electric 
		eImpedance_of_UserCircuit_Testing_rg , Electric 
		eLowCapcitancePhoneDetect,             Electric 
		eForceRingSubscriber,                  ForceRing 
		eDT_Delay_of_UserCircuit_Testing , DialTone 
		eTermination_Testing , Electric 
		eNormal_AC_CurrentTest_Testing_tr , AC_DC_CURRENT 
		eNormal_AC_CurrentTest_Testing_tg , AC_DC_CURRENT 
		eNormal_AC_CurrentTest_Testing_rg , AC_DC_CURRENT 
		eNormal_DC_CurrentTest_Testing_tr , AC_DC_CURRENT 
		eNormal_DC_CurrentTest_Testing_tg , AC_DC_CURRENT 
		eNormal_DC_CurrentTest_Testing_rg , AC_DC_CURRENT 
		eNormal_Noise_Level_Testing , NOISE_LEVEL 
		eNormal_Contition_Howler_Testing , HowlerTone 
		eStatus_Monitored_Testing , StatusMonitored 
		eBulk_Testing ,  Electric 
		eGroup_Testing , Electric
		eCablePairIdentification, CabIdentify
		eTalkingtest,             Talking
		eLine reverse,            Talking
		ePrivateMeterPulses,      Talking
		eRingSubscriber,          Talking
		eDP_DTMFSignal,           Talking		  
		eFE_DC_of_UserLine_Testing_rt , Electric
		eCapacitance_Of_Signature,   Electric
		eResistance_Of_Ringer,      Electric
		eISDNLoopBack, ISDN_loopback_test
		H248_Caller Voice Diagnosis Testing,      TBD
		H248_Callee Voice Diagnosis Testing,      TBD
		eConductance_Of_User_Line_Testing_tr,     Electric
		eConductance_Of_User_Line_Testing_tg,     Electric
		eSusceptance_Of_User_Line_Testing_rg,     Electric
		eSusceptance_Of_User_Line_Testing_tr,     Electric
		eSusceptance_Of_User_Line_Testing_tg,     Electric
		eSusceptance_Of_User_Line_Testing_rg,     Electric
		Hazardous Valtage testing,                Electric

	ALCATEL-LUCENT NOTE:
		ACCESS:     RW
		USAGE:       MAND
		PERSIST:   	NO
		INSRVMOD: 	NA
		RANGE:	NA
		DEFVALUE:  NA
		UNITS:	NA
		SPARSE: NO"
	::= {ltSessionEntry 8}	

ltTestParamNum   OBJECT-TYPE
   SYNTAX     INTEGER(0..255)
   ACCESS     read-write
   STATUS     mandatory
   DESCRIPTION "A parameter for the session. Indicate how many PARAM lines in the session for test,  it's to say there are ltTestParamNum rows in ltTestParamTable for this session.
	ALCATEL-LUCENT NOTE:
		ACCESS:     RW
		USAGE:       MAND
		PERSIST:   	NO
		INSRVMOD: 	NA
		RANGE:	(0..64)
		DEFVALUE:  NA
		UNITS:	NA
		SPARSE: NO"
  ::= {ltSessionEntry 9}

ltTestMode   OBJECT-TYPE
   SYNTAX     LTTestMode
   ACCESS     read-write
   STATUS     mandatory
   DESCRIPTION "the test mode means whether test should be repeat and which way it repeats.
    single				default value, means the test needn't repeat in program, it will end after one time.
    block					20 rounds test will be done automatically by NBLT after test start, all results would be report together.
    continuous		operator's program will send repeat command to NBLT to start a new round after receive last round's result.
    interactive		the interactive test.
    cablepair			the cable pair test.
	ALCATEL-LUCENT NOTE:
		ACCESS:     RW
		USAGE:       MAND
		PERSIST:   	NO
		INSRVMOD: 	NA
		RANGE:	NA
		DEFVALUE:  NA
		UNITS:	NA
		SPARSE: NO"
  ::= {ltSessionEntry 10}  
	
ltTestTypeString OBJECT-TYPE
   SYNTAX     OCTET STRING (SIZE (1..255))
   ACCESS     read-write
   STATUS     optional
   DESCRIPTION "ready to transfer test type info from ltTestTypeHigh/ltTestTypeLow.	in R3.3v, we defined the this object to replace ltTestTypeHigh/ltTestTypeLow to record the information of which test types operator want to test. Because the ltTestTypeString can including more bits. But 5530 does not want make MIB objects discard, so this object defined but not in use.
    this object will always show zero-length(empty) octet-string, set requests will be accepted but they won't have any effect on the object.
	ALCATEL-LUCENT NOTE:
		ACCESS:     RW
		USAGE:       OPT
		PERSIST:   	NO
		INSRVMOD: 	NA
		RANGE:	NA
		DEFVALUE:  NA
		UNITS:	NA
		SPARSE: NO"
  ::= {ltSessionEntry 11}  


ltSessionInputErrCode OBJECT-TYPE
   SYNTAX     LTSessionInputErrCode
   ACCESS     read-only
   STATUS     mandatory
   DESCRIPTION " when start test fails with genErr, this object indicates the detailed reason of the failure. This object is not suitable for H248 linetest, should be ignored..
 	noErr(0),				 -- 0  no error.
	ltTestParamNumInconsistent(1),           -- 1  the actual input param number in ltTestParamTable is not equal to ltTestParamNum.
 	ltTestParamNumOutOfRange(2),             -- 2  the input param number is out of range, from 0 to 4 is allowed.  
	testTypeNeedNoParam(3),                  -- 3  the input test param is meaningless, because those test types not need any test param.
        testParamForNonTestingType(4),           -- 4  the input test param for those test types which are not in current test session.
	missingltTestParamConfiguration(5),  	 -- 5  missing test param configuration for those test types which must have test param.
	missingltTimeOutPeriod(6),               -- 6  missing ltTimeOutPeriod value.
  	ltTimeOutPeriodNotEnough(7),	         -- 7  the input ltTimeOutPeriod is not enough for test.
	ltLineNumInconsistent(8),          	 -- 8  the actual input line number in ltLineIdTable is not equal to ltLineNum.
	ltLineNumOutOfRange(9),		         -- 9  the input line number is out of range, from 1 to 72 is allowed.
	invalidLineId(10),              	 -- 10 the input lineId is invalid.
        duplicatedLineId(11),                    -- 11 the same lineId configed twice
    	missingltTestType(12),                   -- 12 missing ltTestTypeHigh and ltTestTypeLow.
	invalidTestType(13),		         -- 13 the input ltTestTypeHigh and ltTestTypeLow is incorrect.
	thresholdNumOutOfRange(14),	         -- 14 input too many threshold, the number of threshold from 0 to 39 is allowed.
	testTypeNeedNoThreshold(15),             -- 15 the input threshold is meaningless, because those test types do not need any threshold.
	thresholdForNonTestingType(16),    	 -- 16 the input threshold for those test types which are not in current test session.
	testTypeMismatchTestMode(17),            -- 17 the input test type does not match with the test mode.
	ltlineNumMismatchTestModeOrTestType(18), -- 18 the input line number is not match test mode and test type. All talking test, cable pair test, block test and continuous test only support one line for certain test.
	wrongLineStatusForSubTest(19),       	 -- 19 the line status for subtest is not in holding or the line which has no father test first.
	oneTestItemForBlockOrContinousTest(20),  -- 20 block test and continous test must be only one test type
        lineIdInNonTestingStatus(21),               -- 21 the input lineId is not in testing status.
        testModeNotSupportRepeatTest(22),           -- 22 repeate test can only be done in continous test mode
        sessionStateIncorrect(23),                  -- 23 the command not allowed in current session state
	systemInternalError(24), 		    -- 24 internal system error.
        sessionInactiveTimerOutOfRange(25)          -- 25 ltSessionInactiveTimer value out of range
	
	ALCATEL-LUCENT NOTE:
		ACCESS:     RO
		USAGE:       MAN
		PERSIST:   	NO
		INSRVMOD: 	NA
		RANGE:	NA
		DEFVALUE:  NA
		UNITS:	NA
		SPARSE: NO"
  ::= {ltSessionEntry 12}  

ltSessionInactiveTimer OBJECT-TYPE
   SYNTAX     INTEGER(0..65535) 
   ACCESS     read-write
   STATUS     mandatory
   DESCRIPTION "The parameter used to set the timer to destroy the session when it is inactive.
The value can be 0 or from 120 to 65535. value 0 means never destroy the session automatically. and if configured not-zero, the value should be from 120 to 65535 seconds.
The timer can be configured only in session REV_CMD state, in other states, the configuration will NOT allowed.
This active timer is effective in all session states(REV_CMD, REV_INFO, TEST_HOLD and TEST_OVER) except for test running(RUN_CMD).
If there is no GET or SET operations during this period means the session is inactive, then the session will be destroyed automatically when timeout.
Any snmp GET or SET operation will make the timer restart.
If no value is set for this parameter, default value 0 will be used that means never destroy the session automatically in any session states.
For MEGACO Line Test, this object should be ignored.

    ALCATEL-LUCENT NOTE:
                ACCESS:     RW
                USAGE:      OPT 
                PERSIST:        NO
                INSRVMOD:       NA
                RANGE:  (0..65535)
                DEFVALUE: 0
                UNITS:  seconds
                SPARSE: NO"
  ::= {ltSessionEntry 13}

ltSessionBusyOverwrite   OBJECT-TYPE
    SYNTAX    TruthValue
    ACCESS     read-write
    STATUS     mandatory
    DESCRIPTION " This object specifies whether to forcefully drop existent
        calls before execution of the line test of the session if any of the
        line tests can't be executed during the call.
        The value true(1) means if any of the requested line tests can't be
        executed during the call and there are existent calls on some lines
        of the session, then all the calls of those lines will be dropped
        before executing the line tests of those lines. Else if all the 
        requested line tests can be executed during the call, then the calls
        of those lines won't dropped before executing the line tests.
        The value false(2) means if any of the requested line tests can't be
        executed during the call and there are existent calls on some lines
        of the session, then only the line tests on those lines will be 
        rejected, and the line tests on the other lines which have no calls
        can still be executed.
        For MEGACO LineTest, this object shall be ignored.
        
        ALCATEL-LUCENT NOTE:
        ACCESS:     RW
        USAGE:       OPT
        PERSIST:   	NO
        INSRVMOD: 	NA
        RANGE:	See above
        DEFVALUE:  false(2)
        UNITS:	NA
        SPARSE: NO"
::= {ltSessionEntry 14}  

ltTestTypeExtend   OBJECT-TYPE
   SYNTAX     Gauge   
   ACCESS     read-write
   STATUS     mandatory
   DESCRIPTION "A parameter for the session. Indicate line test items.  
                With ltTestTypeLow and ltTestTypeHigh they are a 96bit bitmap for test items.
            --bit31, Galvanic  Signature Testing,                 TRUE(1) or FLASE(0)
            --bit30, End Device Capacitance Testing,              TRUE(1) or FLASE(0)
            --bit29, PPA Variant Testing,                         enum LTPPAVariantResult
            --bit28, Termination Roh Testing,                     TRUE(1) or FLASE(0)
            --bit27, Termination Ringer Testing,                  TRUE(1) or FLASE(0)
            --bit26, GR909 Ringer,                                PASSED (1) / FAILED (0)
            --bit25, GR909 Draw/Break Dial Tone Delay,	          PASSED (1) / FAILED (0)
            --bit24, GR909 Receiver Off Hook,                     PASSED (1) / FAILED (0)
            --bit23, GR909 Hazardous Potential,                   PASSED (1) / FAILED (0)
            --bit22, GR909 Foreign Electromotive Force,           PASSED (1) / FAILED (0)
            --bit21, GR909 Resistive faults,                      PASSED (1) / FAILED (0)
            --bit20, Zener Resistance,                            unit : ohm
            --bit19, Zener Voltage,                               unit : uV (10E-6V)
            --bit18, Isdn Pra Remote loopback,                    enum LTPraRemoteLBTestResult
            --bit17, Isdn Pra Payload loopback,                   enum LTPraPayloadLBTestResult
            --bit16, Isdn Pra Local loopback,                     enum LTPraLocalLBTestResult
            --bit15, Isdn Pra Cable loopback,                     enum LTPraCableLBTestResult
            --bit14-bit0: reserved
	 bitmap construct rules:
		we sort all tests into the following different class by their attribute, and only tests of the same attribute could exist in one session. 
		1) all attribute was defined here: 
            enum eLineTestAttribute{
                Electric,                     // 0    electric parameter test(R,vol,C,current)
                DialTone,                     // 1    especially for dail tone test,
                AC_DC_CURRENT,                // 2 especially for AC/DC current test, for it need 2 commands: START or END.
                NOISE_LEVEL,                  // 3    only for noise level
                HowlerTone,                   // 4    only for howler tone test.
                StatusMonitored,              // 5    only for statusMonitored test.
                TalkingTest,                  // 6    2006.11.25, added for line testing phase 2
                TalkingSubTestDtmf,           // 7   2006.11.25, added for line testing phase 2
                TalkingSubTestOther,          // 8    2006.11.25, added for line testing phase 2
                CablePairIdentity,            // 9    2006.12.3, added for line testing phase 2
                Electric_OnlyIdle,            // 10  ANTmt52585, Msocket can only be done in IDLE, yuandax, 2009-04-13
                ISDN_loopback_test,           // 11  ISDN loopback test
                VoiceDiagnosisH248Caller,     // 12
                VoiceDiagnosisH248Callee,     // 13
                Butt_LineTestAttribute,       // 14
                ForceRing,                    //15
                ISDN_PRA_loopback_test          //16  ISDN PRA loopback test
            };
            2) the relationship between every test and these attribute was described like this table: 
                Galvanic Signature Testing,         Electric      
                End Device Capacitance Testing,      Electric      
                PPA Variant Testing,                 Electric      
                Termination Roh Testing,             Electric   
                Termination Ringer Testing,          Electric      
                Zener resistance,                    Electric
                Zener voltage,                       Electric
                Isdn Pra Remote loopback,            ISDN_PRA_loopback_test
                Isdn Pra Payload loopback,           ISDN_PRA_loopback_test
                Isdn Pra Local loopback,             ISDN_PRA_loopback_test
                Isdn Pra Cable loopback,             ISDN_PRA_loopback_test
            ALCATEL-LUCENT NOTE:
            ACCESS:     RW
            USAGE:       MAND    
            PERSIST:        NO      
            INSRVMOD:       NA
            RANGE:  NA
            DEFVALUE:  NA
            UNITS:  NA
            SPARSE: NO"   
::= {ltSessionEntry  15}

ltGroupTestOption   OBJECT-TYPE
     SYNTAX     LTGroupTestOpt
     ACCESS     read-write
     STATUS     mandatory
     DESCRIPTION "This MIB object is used to specify different group/collective test types defined in LTGroupTestOpt.
        ALCATEL-LUCENT NOTE:
                ACCESS:     RO
                USAGE:       MAND
                PERSIST:        NO
                INSRVMOD:       NA
                RANGE:  1|2|3|4
                DEFVALUE:  1   --none
                UNITS:  NA
                SPARSE: NO"
  ::= { ltSessionEntry 16}

ltSessionForcedTest   OBJECT-TYPE
    SYNTAX    TruthValue
    ACCESS     read-write
    STATUS     mandatory
    DESCRIPTION " This object specifies whether to forcefully show the melt
        measurement result on execution of the line test even if SLIC HW has a 
	failure. The value true(1) means force the MELT measurement for requested line tests. 
        The value false(2) means force measurement is not required.
        This object is only applicable for MELT test

        ALCATEL-LUCENT NOTE:
        ACCESS:     RW
        USAGE:      OPT
        PERSIST:    NO
        INSRVMOD:   NA
        RANGE:	    See above
        DEFVALUE:  false(2)
        UNITS:	   NA
        SPARSE:    NO"
::= {ltSessionEntry 17}

-- LineId Table
ltLineIdTable OBJECT-TYPE
      SYNTAX SEQUENCE OF LtLineIdEntry
      ACCESS not-accessible
      STATUS mandatory
      DESCRIPTION "LineId Table.
      ALCATEL-LUCENT NOTE: 
		TABLESIZE: 72
		DESCR:NA."   
   ::= {ltLineTest 4}
   
ltLineIdEntry OBJECT-TYPE
      SYNTAX LtLineIdEntry
      ACCESS not-accessible
      STATUS mandatory
      DESCRIPTION "LineId Table Entry." 
      INDEX { ltAssoSessionId, ltLineId }
   ::= {ltLineIdTable 1}
   
LtLineIdEntry::= SEQUENCE
{
      ltAssoSessionId         INTEGER,    
      ltLineId                Gauge,  
      ltLineIdStatus          LTLineIdStatus, 
      ltRpCommonStat          LTCommonErrCode,   
      ltRpValNum              Gauge, 
      ltLineHookChangeStatus  LTLineIdHookChangeStatus,
      ltRpCommonStatText      DisplayString,
      ltSearchToneRemainingTime  INTEGER,
      ltTestCompleteTimeStamp Gauge

}

ltAssoSessionId OBJECT-TYPE
      SYNTAX INTEGER(1..255)
      ACCESS not-accessible
      STATUS mandatory
      DESCRIPTION "Index of the table. This sessionId associated with ltSessionId in ltSessionTable. 
      Actually, its range is  [1,ltMaxNumberOfSession]. 
      As ltMaxNumberOfSession is set 16 in ALCATEL-LUCENT, so its range is [1,16] 
	ALCATEL-LUCENT NOTE:
		ACCESS:     NA
		USAGE:       MAND
		PERSIST:   	NO
		INSRVMOD: 	NA
		RANGE:	[1..16]
		DEFVALUE:  NA
		UNITS:	NA
		SPARSE: NO"
   ::= { ltLineIdEntry 1}
   
ltLineId   OBJECT-TYPE
     SYNTAX     Gauge
     ACCESS     not-accessible
     STATUS     mandatory
     DESCRIPTION "This is the Index of LineId Table, It's the identifier of Line, such as 0x01110706
         +==============+ 
         |    nodeId    |   8 bits. this is the same to EQPTID 
         +==============+ 
         | Rack |SubRack|   8 bits. 
         +==============+ 
         |     slot     | 
         +==============+ 
         |    lineId    | 
         +==============+ 
   Rack,SubRack and lineId are 1-based. For example: for the port numbers: range from 0x01~0x30. 
       For slot: LT1: 03  LT2: 04 
   Example: 0x 01110510   
            0x 01   11                  05   10 
            (node1) (rack 1,subrack1) (LT3) (port 16)
            
   the mapping between ltLineId(logicIndex) and ifIndex:   
       Change from line test ID to ifindex:
 		       line test line ID format : 0xAABBCCDD
 		       ifindex format:          : 0xBBCC00DD-1
       Change form ifindex to line test ID:
           ifindex format:          : 0xXXYY00ZZ
           line test line ID format : 0x01XXYYZZ+1

	ALCATEL-LUCENT NOTE:
		ACCESS:     NA
		USAGE:       MAND
		PERSIST:   	NO
		INSRVMOD: 	NA
		RANGE:	NA
		DEFVALUE:  NA
		UNITS:	NA
		SPARSE: NO"
    ::= {ltLineIdEntry 2}   
    
ltLineIdStatus     OBJECT-TYPE
     SYNTAX     LTLineIdStatus
     ACCESS     read-write
     STATUS     mandatory
     DESCRIPTION "This is the line status. Include (NOT_IN_TEST, SET_TEST, RESULT_READY)
                  for write   1: create a row for test
                  for read    0: not created
                              2: this line test is over and result is ready  
	ALCATEL-LUCENT NOTE:
		ACCESS:     RW
		USAGE:       MAND
		PERSIST:   	NO
		INSRVMOD: 	NA
		RANGE:	0 | 1 | 2
		DEFVALUE:  NA
		UNITS:	NA
		SPARSE: NO"
 ::= {ltLineIdEntry 3}   
 
ltRpCommonStat   OBJECT-TYPE
 SYNTAX     LTCommonErrCode
     ACCESS     read-only
     STATUS     mandatory
     DESCRIPTION "Result status means the test result status. Filled by LT and interpret by network manager 
	ALCATEL-LUCENT NOTE:
		ACCESS:     RO
		USAGE:       MAND
		PERSIST:   	NO
		INSRVMOD: 	NA
		RANGE:	NA
		DEFVALUE:  NA
		UNITS:	NA
		SPARSE: NO"
  ::= {ltLineIdEntry 4} 
  
ltRpValNum   OBJECT-TYPE
     SYNTAX     Gauge
     ACCESS     read-only
     STATUS     mandatory
     DESCRIPTION "Available results numbers. Indicate the network manager to retrieve the test result. 
      That's to say there are ltRpValNum rows results in ltLineIdExtReportTable associated with the lineId.
	ALCATEL-LUCENT NOTE:
		ACCESS:     RO
		USAGE:       MAND
		PERSIST:   	NO
		INSRVMOD: 	NA
		RANGE:	NA
		DEFVALUE:  NA
		UNITS:	NA
		SPARSE: NO"
  ::= {ltLineIdEntry 5}  
  
  ltLineHookChangeStatus   OBJECT-TYPE
	     SYNTAX     LTLineIdHookChangeStatus
	     ACCESS     read-only
	     STATUS     mandatory
	     DESCRIPTION "Line hook state change.
	                  1: off hook to on hook,
	                  2: on hook to off hook,
	                  others: undefined.
	ALCATEL-LUCENT NOTE:
		ACCESS:     RO
		USAGE:       MAND
		PERSIST:   	NO
		INSRVMOD: 	NA
		RANGE:	1 | 2
		DEFVALUE:  NA
		UNITS:	NA
		SPARSE: NO"
	  ::= {ltLineIdEntry 6}

ltRpCommonStatText   OBJECT-TYPE    
 SYNTAX     DisplayString
     ACCESS     read-only
     STATUS     mandatory
     DESCRIPTION "The Description of the exception texts according to the errors reported per line. The max length for the string is 256.
	-- testUnFinished(0): Line test not finished or not started because of missing subsequent command input.  
	-- testFinished(1): Line test finished
	-- testStopedbyTimeOut(2): Line test stopped due to line test period timeout (ltTimeOutPeriod)
	-- testCanceledbyOperator(3): Line test canceled by operator
	-- testBreakedbyUser(5): Line test interrupted by subscriber
	-- testPPFailed(6): Passive Test Terminator test failed due to hardware failure 
	-- testLineBusyInTestNow(8): The line is busy; it may be in use by another line test or is involved in a call
	-- testLongTimeNoNextOperator(9): Line test stopped because no subsequent operator command received in time
	-- testLineStatusError(11): Line status does not allow line test
	-- testOutofMemory(12): Line test failed; result buffer could not be allocated due to lack of memory
	-- testTimerOperateFail(13): Timer could not be started
	-- testTypeEmpty(14): No line test type configured in line test session request
	-- testTypeLogicError(15): Line test type configured in line test session request not supported 
	-- testTypeUnknown(16): Line test type configured in line test session request is unknown  
	-- testParaLineIDError(17): The configured line id is invalid 
	-- testParaOperateError(18): The configured line test command is invalid 
	-- testParaSerialNumError(19): The configured session id is invalid 
	-- testCurrentLineInTesting(21): The line is currently in <searchtone/measurement> by session <sessionid>
	-- testOtherFail(22): Other line test failure 
	-- testEndedbyOperator(23): Line test stopped by the operator
	-- testOnHookbyOperator(24): On-hook event caused by operator during talking test 
	-- testParaValueError(26): Insufficient amount of test parameters configured for DTMF test 
	-- sessionTimeout(105): Session Time-out
	-- invalidPortID(106): Invalid line Id configured 
	-- pOLTMessageMissing(107): Internal Line test communication error
	-- redundancyPorts(110): The configuration of multiple line IDs in this test session is not allowed 
	-- wrongEndTestSequenceNumber(112): Wrong session id configured in line test session abort command 
	-- portDisable(114): Admin state of Subscriber line is disabled 
	-- pOLTFail(117): LT board has failed 
	-- portUnknownState(118): The subscriber line is in an unknown admin state 
	-- outOfMem(119): The NVPS board or the NT board has ran out of memory
	-- newTimerErr(120): Internal error : No new timer could be created 
	-- startTimerErr(121): Internal error : Timer could not be started 
	-- sendMsgErr(122): Internal error: Internal message transmission error 
	-- getPortIpudpErr(123): Internal error: Subscriber line IP@/UDP port could not be retrieved 
	-- portEnableLock(124): H248 only: subscriber line enabled and locked 
	-- portDisableUnlock(125): Subscriber line disabled and unlocked 
	-- portDisableLock(126): Subscriber line disabled and locked 
	-- abortTimerErr(127): Internal error: Abort of a timer failed 
	-- emptyTestType(128): None of a high-type test type or a low-type test type or type-extend test type has been configured
	-- testTypeMismatchWithMode(129): Mismatch between configured test type and configured test mode 
	-- portDisableNetUnlock(130): H248 only: Subscriber line admin unlocked but operationally disabled by MGC 
	-- portDisableVaUnlockGroundKey(131): Subscriber line admin unlocked but operationally disabled by ground-key alarm 
	-- portDisableVaUnlockOverCurrent(132): Subscriber line admin unlocked but operationally disabled by over current alarm 
	-- portDisableVaUnlockOverTemperature(133): Subscriber line admin unlocked but operationally disabled by over temperature alarm 
	-- portDisableNetLock(134): H248 only: subscriber line locked and operationally disabled by MGC 
	-- portDisableVaLockGroundKey(135): Subscriber line admin locked and operationally disabled by ground-key alarm 
	-- portDisableVaLockOverCurrent(136): Subscriber line admin locked and operationally disabled by over current alarm 
	-- portDisableVaLockOverTemperature(137): Subscriber line admin locked and operationally disabled by over temperature alarm 
	-- portNotSupportLineTest(138): Line Test is not supported for this subscriber line 
	-- portUndergoinginMTATest(139): The subscriber line is actually involved in MTA test 
	-- testCurrentLTboardInTesting(140): Line test could not be started; concurrency problem with busy ltsession <sessionid>, ltsession busy reason: <in_searchtone/in_measurement>

   ALCATEL-LUCENT NOTE:
       ACCESS:     RO
       USAGE:       MAND
       PERSIST:    NO
       INSRVMOD:   NA
       RANGE:  NA
       DEFVALUE:  NA
       UNITS:  NA
       SPARSE: NO"
  ::= {ltLineIdEntry 7}

ltSearchToneRemainingTime     OBJECT-TYPE    
     SYNTAX     INTEGER(0 .. 4294967295)
     ACCESS     read-only
     STATUS     mandatory
     DESCRIPTION "This object specifies the remaining time of search tone in seconds. A 0 value means that search tone is ended(timout or stopped by operator). The range of search tone duration (65~5400 sec) is configured in ltTimeOutPeriod.
   ALCATEL-LUCENT NOTE:
       ACCESS:     RO
       USAGE:       MAND
       PERSIST:    NO
       INSRVMOD:   NA
       RANGE:  NA
       DEFVALUE:  NA
       UNITS:  NA
       SPARSE: NO"
  ::= {ltLineIdEntry 8}

ltTestCompleteTimeStamp     OBJECT-TYPE    
     SYNTAX     Gauge
     ACCESS     read-only
     STATUS     mandatory
     DESCRIPTION "This object is implemented for line test measurements and will not take effect for search tone. It specifies the time stamp of the end of the testing (test reported returned/ test timeout/ test ended by operator).  
   ALCATEL-LUCENT NOTE:
       ACCESS:     RO
       USAGE:       MAND
       PERSIST:    NO
       INSRVMOD:   NA
       RANGE:  NA
       DEFVALUE:  NA
       UNITS:  NA
       SPARSE: NO"
  ::= {ltLineIdEntry 9}   
 	   	 
-- LineId Table End

	
-- TestParam Table Begin
ltTestParamTable OBJECT-TYPE
	      SYNTAX SEQUENCE OF LtTestParamEntry
	      ACCESS not-accessible
	      STATUS mandatory
	      DESCRIPTION "This Table is used for network manager to set some parameters used in the test.  you can refer to the table in MIB usage for more detailed
     	 ALCATEL-LUCENT NOTE: 
		TABLESIZE: 1024(because ltMaxNumberOfSession is 16 and the max test item num of a session is 64, so the table size is 64*ltMaxNumberOfSession=1024)
		DESCR:NA."               
	   ::= {ltLineTest 6}	      
-- for sip line test feature, we add 2 new objects (thresholdMin/thresholdMax) in this table to meet the new requirement 
-- that operator can set line test item��s threshold values instead of threshold values defined in CDE file. 
-- The 2 new objects are applied in xDSL line test feature in the same way.
-- This change will only supported in SIP line test and xDSL line test, as for MEGACO version, no change will included.
-- As for the detail, thresholdMin will be used to transfer the minimum threshold value, and thresholdMax for maximum threshold value. Eg:
-- 1 -  minimum : 1000, maximum 3000,  then thresholdMin = 1000, thresholdMax=3000.
-- 2 -  minimum : -3000, maximum -1000,  thresholdMin= -3000,thresholdMax=-1000.
-- For the value, because that value 0 might be a valid value of threshold, 
-- so we will differ the value is by initialized from set by operator, If really from operator, value 0 will be sent to LT board.

ltTestParamEntry OBJECT-TYPE
	      SYNTAX LtTestParamEntry
	      ACCESS not-accessible
	      STATUS mandatory
	      DESCRIPTION "Test Param Table Entry.
	      you can refer to the able in MIB usage for more detailed" 
	      INDEX { ltTestParamAssoSessionId, ltTestType }
	   ::= {ltTestParamTable 1}
	   
LtTestParamEntry::= SEQUENCE
{
   ltTestParamAssoSessionId INTEGER,
	 ltTestType             LTTestType, 
	 ltValue1               INTEGER, 
	 ltValue2               INTEGER, 
	 ltValue3               INTEGER, 
	 ltValue4               INTEGER, 
	 ltValue5               INTEGER,
	 thresholdMin           INTEGER,
	 thresholdMax           INTEGER,
   thresholdMin2          INTEGER,
   thresholdMax2          INTEGER,
   ltStrValue1            OCTET STRING,
   ltStrValue2            OCTET STRING
} 
	
ltTestParamAssoSessionId OBJECT-TYPE
      SYNTAX INTEGER(1..255)
      ACCESS not-accessible
      STATUS mandatory
      DESCRIPTION "Index of the table. This value associated with ltSessionId in ltSessionTable. 
      It's range is [1..ltMaxNumberOfSession]. Since ltMaxNumberOfSession is 16, so its range is [1..16].
	ALCATEL-LUCENT NOTE:
		ACCESS:     NA
		USAGE:       MAND
		PERSIST:   	NO
		INSRVMOD: 	NA
		RANGE:	[1..16]
		DEFVALUE:  NA
		UNITS:	NA
		SPARSE: NO"
   ::= { ltTestParamEntry 1}

ltTestType OBJECT-TYPE
      SYNTAX     LTTestType
	ACCESS     not-accessible
	STATUS     mandatory
	DESCRIPTION "Index of the table. The test item associated with the test parameter row
	ALCATEL-LUCENT NOTE:
		ACCESS:     NA
		USAGE:       MAND
		PERSIST:   	NO
		INSRVMOD: 	NA
		RANGE:	NA
		DEFVALUE:  NA
		UNITS:	NA
		SPARSE: NO"
	  ::= {ltTestParamEntry 2} 

ltValue1   OBJECT-TYPE
	     SYNTAX     INTEGER
	     ACCESS     read-write
	     STATUS     mandatory
	     DESCRIPTION "Test parameter value1
	ALCATEL-LUCENT NOTE:
		ACCESS:     RW
		USAGE:       MAND
		PERSIST:   	NO
		INSRVMOD: 	NA
		RANGE:	NA
		DEFVALUE:  NA
		UNITS:	NA
		SPARSE: NO"
	  ::= {ltTestParamEntry 3}  	  
	  
ltValue2   OBJECT-TYPE
SYNTAX     INTEGER
	     ACCESS     read-write
	     STATUS     mandatory
	     DESCRIPTION "Test parameter value2
	ALCATEL-LUCENT NOTE:
		ACCESS:     RW
		USAGE:       MAND
		PERSIST:   	NO
		INSRVMOD: 	NA
		RANGE:	NA
		DEFVALUE:  NA
		UNITS:	NA
		SPARSE: NO"
	  ::= {ltTestParamEntry 4} 

ltValue3   OBJECT-TYPE
	     SYNTAX     INTEGER
	     ACCESS     read-write
	     STATUS     mandatory
	     DESCRIPTION "Test parameter value3
	ALCATEL-LUCENT NOTE:
		ACCESS:     RW
		USAGE:       MAND
		PERSIST:   	NO
		INSRVMOD: 	NA
		RANGE:	NA
		DEFVALUE:  NA
		UNITS:	NA
		SPARSE: NO"
	  ::= {ltTestParamEntry 5} 

ltValue4   OBJECT-TYPE
	     SYNTAX     INTEGER
	     ACCESS     read-write
	     STATUS     mandatory
	     DESCRIPTION "Test parameter value4
	ALCATEL-LUCENT NOTE:
		ACCESS:     RW
		USAGE:       MAND
		PERSIST:   	NO
		INSRVMOD: 	NA
		RANGE:	NA
		DEFVALUE:  NA
		UNITS:	NA
		SPARSE: NO"
	  ::= {ltTestParamEntry 6} 
	  
ltValue5   OBJECT-TYPE
	     SYNTAX     INTEGER
	     ACCESS     read-write
	     STATUS     mandatory
	     DESCRIPTION "Test parameter value5
	ALCATEL-LUCENT NOTE:
		ACCESS:     RW
		USAGE:       MAND
		PERSIST:   	NO
		INSRVMOD: 	NA
		RANGE:	NA
		DEFVALUE:  NA
		UNITS:	NA
		SPARSE: NO"
	  ::= {ltTestParamEntry 7}  
	  
thresholdMin   OBJECT-TYPE
	     SYNTAX     INTEGER
	     ACCESS     read-write
	     STATUS     mandatory
	     DESCRIPTION "threshold min of this test type.
	ALCATEL-LUCENT NOTE:
		ACCESS:     RW
		USAGE:       MAND
		PERSIST:   	NO
		INSRVMOD: 	NA
		RANGE:	NA
		DEFVALUE:  NA
		UNITS:	NA
		SPARSE: NO"
	  ::= {ltTestParamEntry 8}  
	  
thresholdMax   OBJECT-TYPE
	     SYNTAX     INTEGER
	     ACCESS     read-write
	     STATUS     mandatory
	     DESCRIPTION "threshold max of this test type
	ALCATEL-LUCENT NOTE:
		ACCESS:     RW
		USAGE:       MAND
		PERSIST:   	NO
		INSRVMOD: 	NA
		RANGE:	NA
		DEFVALUE:  NA
		UNITS:	NA
		SPARSE: NO"
	  ::= {ltTestParamEntry 9}  
	  
thresholdMin2   OBJECT-TYPE
	     SYNTAX     INTEGER
	     ACCESS     read-write
	     STATUS     mandatory
	     DESCRIPTION "threshold min of this test type.
	ALCATEL-LUCENT NOTE:
		ACCESS:     RW
		USAGE:       MAND
		PERSIST:   	NO
		INSRVMOD: 	NA
		RANGE:	NA
		DEFVALUE:  NA
		UNITS:	NA
		SPARSE: NO" 
	  ::= {ltTestParamEntry 10}  
	  
thresholdMax2   OBJECT-TYPE
	     SYNTAX     INTEGER
	     ACCESS     read-write
	     STATUS     mandatory
	     DESCRIPTION "threshold max of this test type
	ALCATEL-LUCENT NOTE:
		ACCESS:     RW
		USAGE:       MAND
		PERSIST:   	NO
		INSRVMOD: 	NA
		RANGE:	NA
		DEFVALUE:  NA
		UNITS:	NA
		SPARSE: NO"
	  ::= {ltTestParamEntry 11}  

	  ltStrValue1   OBJECT-TYPE
     SYNTAX     OCTET STRING
     ACCESS     read-write
     STATUS     mandatory
     DESCRIPTION "Test parameter of string value1
       ALCATEL-LUCENT NOTE:
               ACCESS:    WO
               USAGE:     MAND
               PERSIST:   NO
               INSRVMOD: NA
               RANGE:  NA
               DEFVALUE:  NA
               UNITS:  NA
               SPARSE: NO"
  ::= {ltTestParamEntry 12}

ltStrValue2   OBJECT-TYPE
            SYNTAX     OCTET STRING
            ACCESS     read-write
            STATUS     mandatory
            DESCRIPTION "Test parameter of string value2
       ALCATEL-LUCENT NOTE:
               ACCESS:    WO
               USAGE:     MAND
               PERSIST:   NO
               INSRVMOD: NA
               RANGE:  NA
               DEFVALUE:  NA
               UNITS:  NA
               SPARSE: NO"
         ::= {ltTestParamEntry 13}
	  
--TestParam Table End
	
ltReport OBJECT IDENTIFIER ::= {ltLineTest 7}

ltTrapSessionId   OBJECT-TYPE
	     SYNTAX     INTEGER
	     ACCESS     read-only
	     STATUS     mandatory
	     DESCRIPTION "Trap sessionId associated with ltSessionId in ltSessionTable. 
	ALCATEL-LUCENT NOTE:
		ACCESS:     NA
		USAGE:       MAND
		PERSIST:   	NO
		INSRVMOD: 	NA
		RANGE:	NA
		DEFVALUE:  NA
		UNITS:	NA
		SPARSE: NO"
	  ::= {ltReport 1}  	
	    
ltTrapCmd   OBJECT-TYPE
	     SYNTAX     INTEGER 
	     ACCESS     read-only
	     STATUS     mandatory
	     DESCRIPTION "Trap cmd indicate with event happened in ivps. 
                     1: test over,
                     2: sub talking test or 1 round of continuous test finished, result is ready and session is in hold. 
                     3: line hook state change,
                     others: undefined.
	ALCATEL-LUCENT NOTE:
		ACCESS:     NA
		USAGE:       MAND
		PERSIST:   	NO
		INSRVMOD: 	NA
		RANGE:	1 | 2 | 3
		DEFVALUE:  NA
		UNITS:	NA
		SPARSE: NO"
	  ::= {ltReport 2}  	
	  
ltTrapLineId   OBJECT-TYPE
	     SYNTAX     Gauge
	     ACCESS     read-only
	     STATUS     mandatory
	     DESCRIPTION "concerned Line in the event(Cmd). If only one line in test concerned with the Cmd, this value is set to the actual lineId, else the value is set to 0xFFFF.
	ALCATEL-LUCENT NOTE:
		ACCESS:     NA
		USAGE:       MAND
		PERSIST:   	NO
		INSRVMOD: 	NA
		RANGE:	NA
		DEFVALUE:  NA
		UNITS:	NA
		SPARSE: NO"
	  ::= {ltReport 3}  	
	  
ltTrapStatus   OBJECT-TYPE
	     SYNTAX     Gauge
	     ACCESS     read-only
	     STATUS     mandatory
	     DESCRIPTION "reserved object, not defined in this version.
        ALCATEL-LUCENT NOTE:
		ACCESS:     NA
		USAGE:       MAND
		PERSIST:   	NO
		INSRVMOD: 	NA
		RANGE:	NA
		DEFVALUE:  NA
		UNITS:	NA
		SPARSE: NO"
	  ::= {ltReport 4} 

ltTrapLineHookStatus   OBJECT-TYPE
	     SYNTAX     Gauge
	     ACCESS     read-only
	     STATUS     mandatory
	     DESCRIPTION "Line hook state, this object is only relevant for NBLT;
                          for BBLT it should be ignored.
	                  0: not-applicable 
	                  1: on hook
	                  2: off hook,
	                  others: undefined.
	ALCATEL-LUCENT NOTE:
		ACCESS:     NA
		USAGE:       MAND
		PERSIST:   	NO
		INSRVMOD: 	NA
		RANGE:	1 | 2
		DEFVALUE:  NA
		UNITS:	NA
		SPARSE: NO"
	  ::= {ltReport 5} 

-- LineId Report Table with Multi Results
ltLineIdExtReportTable OBJECT-TYPE
      SYNTAX SEQUENCE OF LtLineIdExtReportEntry 
      ACCESS not-accessible
      STATUS mandatory
      DESCRIPTION "LineIdReport Multi Results Table.
     	 ALCATEL-LUCENT NOTE: 
		TABLESIZE: 28800
		DESCR:NA."               
   ::= {ltLineTest 8}   
   
ltLineIdExtReportEntry  OBJECT-TYPE
      SYNTAX LtLineIdExtReportEntry 
      ACCESS not-accessible
      STATUS mandatory
      DESCRIPTION "LineIdReport Multi Results Table Entry."
      INDEX { ltExtRpAssoSessionId , ltExtRpAssoLineId, ltExtRpTestType, ltExtRpRstIndex }
   ::= {ltLineIdExtReportTable 1}
   

LtLineIdExtReportEntry::= SEQUENCE
{
   ltExtRpAssoSessionId INTEGER,    
   ltExtRpAssoLineId    Gauge,  
   ltExtRpTestType      LTTestType, 
   ltExtRpRstIndex      INTEGER,
   ltExtRpStat          LTErrCode,   
   ltExtRpVal           INTEGER,
   ltExtRpVal2          INTEGER,
   ltExtRpVal3          INTEGER,
   ltExtRpVal4          INTEGER,
   ltExtRpVal5          INTEGER,
   ltExtRpVal6          INTEGER,
   ltExtRpVal7          INTEGER,
   ltExtRpVal8          INTEGER,
   ltExtRpVal9          INTEGER,
   ltExtRpVal10         INTEGER,
   ltExtRpVal11         INTEGER,
   ltExtRpVal12         INTEGER,
   ltExtRpVal13         INTEGER,
   ltExtRpVal14         INTEGER,
   ltExtRpVal15         INTEGER,
   ltExtRpVal16         INTEGER,
   ltExtRpValidity      INTEGER,
   ltExtRpDtmfValue     OCTET STRING
}

ltExtRpAssoSessionId  OBJECT-TYPE
      SYNTAX INTEGER(1..255)
      ACCESS not-accessible
      STATUS mandatory
      DESCRIPTION "Index of the table. This sessionId associates with ltAssoSessionId in ltLineIdTable.
      Actually, its range is  [1,ltMaxNumberOfSession]. 
      As ltMaxNumberOfSession is set 16 in ALCATEL-LUCENT, so its range is [1,16] 
	ALCATEL-LUCENT NOTE:
		ACCESS:     NA
		USAGE:       MAND
		PERSIST:   	NO
		INSRVMOD: 	NA
		RANGE:	[1..16]
		DEFVALUE:  NA
		UNITS:	NA
		SPARSE: NO"
   ::= { ltLineIdExtReportEntry 1}
   
ltExtRpAssoLineId   OBJECT-TYPE
     SYNTAX     Gauge
     ACCESS     not-accessible
     STATUS     mandatory
     DESCRIPTION "This is the Index of LineIdReport Table, 
     It assocuates with ltAssoLineId in ltLineIdTable
	ALCATEL-LUCENT NOTE:
		ACCESS:     NA
		USAGE:       MAND
		PERSIST:   	NO
		INSRVMOD: 	NA
		RANGE:	NA
		DEFVALUE:  NA
		UNITS:	NA
		SPARSE: NO"
    ::= {ltLineIdExtReportEntry 2}   
    
ltExtRpTestType     OBJECT-TYPE
     SYNTAX     LTTestType
     ACCESS     not-accessible
     STATUS     mandatory
     DESCRIPTION " This value associated with ltTestType in LtTestParamEntry.     
	ALCATEL-LUCENT NOTE:
		ACCESS:     NA
		USAGE:       MAND
		PERSIST:   	NO
		INSRVMOD: 	NA
		RANGE:	NA
		DEFVALUE:  NA
		UNITS:	NA
		SPARSE: NO"
 ::= {ltLineIdExtReportEntry 3}   
 
ltExtRpRstIndex   OBJECT-TYPE
     SYNTAX     INTEGER(0..255)
     ACCESS     not-accessible
     STATUS     mandatory
     DESCRIPTION "This is the Index of Multi Results, Current from 1 to 20
	ALCATEL-LUCENT NOTE:
		ACCESS:     NA
		USAGE:       MAND
		PERSIST:   	NO
		INSRVMOD: 	NA
		RANGE:	[1..20]
		DEFVALUE:  NA
		UNITS:	NA
		SPARSE: NO"
    ::= {ltLineIdExtReportEntry 4}   
  
ltExtRpStat   OBJECT-TYPE
     SYNTAX     LTErrCode
     ACCESS     read-only
     STATUS     mandatory
     DESCRIPTION "Result status means the test result status. Filled by LT and interpret by network manager
	ALCATEL-LUCENT NOTE:
		ACCESS:     RO
		USAGE:       MAND
		PERSIST:   	NO
		INSRVMOD: 	NA
		RANGE:	NA
		DEFVALUE:  NA
		UNITS:	NA
		SPARSE: NO"
  ::= {ltLineIdExtReportEntry 5}
  
ltExtRpVal   OBJECT-TYPE
     SYNTAX     INTEGER
     ACCESS     read-only
     STATUS     mandatory
     DESCRIPTION "value report from LT.
    line test result value 1 of the specified line and test type
	ALCATEL-LUCENT NOTE:
		ACCESS:     RO
		USAGE:       MAND
		PERSIST:   	NO
		INSRVMOD: 	NA
		RANGE:	NA
		DEFVALUE:  NA
		UNITS:	NA
		SPARSE: NO"
  ::= {ltLineIdExtReportEntry 6}  
ltExtRpVal2   OBJECT-TYPE
     SYNTAX     INTEGER
     ACCESS     read-only
     STATUS     mandatory
     DESCRIPTION "value report from LT.
     line test result value 2 of the specified line and test type
	ALCATEL-LUCENT NOTE:
		ACCESS:     RO
		USAGE:       MAND
		PERSIST:   	NO
		INSRVMOD: 	NA
		RANGE:	NA
		DEFVALUE:  NA
		UNITS:	NA
		SPARSE: NO"
  ::= {ltLineIdExtReportEntry 7} 

ltExtRpVal3   OBJECT-TYPE
     SYNTAX     INTEGER
     ACCESS     read-only
     STATUS     mandatory
     DESCRIPTION "value report from LT.
        line test result value 3 of the specified line and test type
	ALCATEL-LUCENT NOTE:
		ACCESS:     RO
		USAGE:       MAND
		PERSIST:   	NO
		INSRVMOD: 	NA
		RANGE:	NA
		DEFVALUE:  NA
		UNITS:	NA
		SPARSE: NO"
  ::= {ltLineIdExtReportEntry 8}

ltExtRpVal4   OBJECT-TYPE
     SYNTAX     INTEGER
     ACCESS     read-only
     STATUS     mandatory
     DESCRIPTION "value report from LT.
        line test result value 4 of the specified line and test type
	ALCATEL-LUCENT NOTE:
		ACCESS:     RO
		USAGE:       MAND
		PERSIST:   	NO
		INSRVMOD: 	NA
		RANGE:	NA
		DEFVALUE:  NA
		UNITS:	NA
		SPARSE: NO"
  ::= {ltLineIdExtReportEntry 9}

ltExtRpVal5   OBJECT-TYPE
     SYNTAX     INTEGER
     ACCESS     read-only
     STATUS     mandatory
     DESCRIPTION "value report from LT.
        line test result value 5 of the specified line and test type , reserved for future use
	ALCATEL-LUCENT NOTE:
		ACCESS:     RO
		USAGE:       MAND
		PERSIST:   	NO
		INSRVMOD: 	NA
		RANGE:	NA
		DEFVALUE:  NA
		UNITS:	NA
		SPARSE: NO"
  ::= {ltLineIdExtReportEntry 10} 

ltExtRpVal6   OBJECT-TYPE
     SYNTAX     INTEGER
     ACCESS     read-only
     STATUS     mandatory
     DESCRIPTION "value report from LT.
        line test result value 6 of the specified line and test type , reserved for future use
        ALCATEL-LUCENT NOTE:
                ACCESS:     RO
                USAGE:       MAND
                PERSIST:        NO
                INSRVMOD:       NA
                RANGE:  NA
                DEFVALUE:  NA
                UNITS:  NA
                SPARSE: NO"
  ::= {ltLineIdExtReportEntry 11}

ltExtRpVal7   OBJECT-TYPE
     SYNTAX     INTEGER
     ACCESS     read-only
     STATUS     mandatory
     DESCRIPTION "value report from LT.
        line test result value 7 of the specified line and test type , reserved for future use
        ALCATEL-LUCENT NOTE:
                ACCESS:     RO
                USAGE:       MAND
                PERSIST:        NO
                INSRVMOD:       NA
                RANGE:  NA
                DEFVALUE:  NA
                UNITS:  NA
                SPARSE: NO"
  ::= {ltLineIdExtReportEntry 12} 

ltExtRpVal8   OBJECT-TYPE
     SYNTAX     INTEGER
     ACCESS     read-only
     STATUS     mandatory
     DESCRIPTION "value report from LT.
        line test result value 8 of the specified line and test type , reserved for future use
        ALCATEL-LUCENT NOTE:
                ACCESS:     RO
                USAGE:       MAND
                PERSIST:        NO
                INSRVMOD:       NA
                RANGE:  NA
                DEFVALUE:  NA
                UNITS:  NA
                SPARSE: NO"
  ::= {ltLineIdExtReportEntry 13}

ltExtRpVal9   OBJECT-TYPE
     SYNTAX     INTEGER
     ACCESS     read-only
     STATUS     mandatory
     DESCRIPTION "value report from LT.
        line test result value 9 of the specified line and test type , reserved for future use
        ALCATEL-LUCENT NOTE:
                ACCESS:     RO
                USAGE:       MAND
                PERSIST:        NO
                INSRVMOD:       NA
                RANGE:  NA
                DEFVALUE:  NA
                UNITS:  NA
                SPARSE: NO"
  ::= {ltLineIdExtReportEntry 14}

ltExtRpVal10   OBJECT-TYPE
     SYNTAX     INTEGER
     ACCESS     read-only
     STATUS     mandatory
     DESCRIPTION "value report from LT.
        line test result value 10 of the specified line and test type , reserved for future use
        ALCATEL-LUCENT NOTE:
                ACCESS:     RO
                USAGE:       MAND
                PERSIST:        NO
                INSRVMOD:       NA
                RANGE:  NA
                DEFVALUE:  NA
                UNITS:  NA
                SPARSE: NO"
  ::= {ltLineIdExtReportEntry 15}

ltExtRpVal11   OBJECT-TYPE
     SYNTAX     INTEGER
     ACCESS     read-only
     STATUS     mandatory
     DESCRIPTION "value report from LT.
        line test result value 11 of the specified line and test type , reserved for future use
        ALCATEL-LUCENT NOTE:
                ACCESS:     RO
                USAGE:       MAND
                PERSIST:        NO
                INSRVMOD:       NA
                RANGE:  NA
                DEFVALUE:  NA
                UNITS:  NA
                SPARSE: NO"
  ::= {ltLineIdExtReportEntry 16}

ltExtRpVal12   OBJECT-TYPE
     SYNTAX     INTEGER
     ACCESS     read-only
     STATUS     mandatory
     DESCRIPTION "value report from LT.
        line test result value 12 of the specified line and test type , reserved for future use
        ALCATEL-LUCENT NOTE:
                ACCESS:     RO
                USAGE:       MAND
                PERSIST:        NO
                INSRVMOD:       NA
                RANGE:  NA
                DEFVALUE:  NA
                UNITS:  NA
                SPARSE: NO"
  ::= {ltLineIdExtReportEntry 17}

ltExtRpVal13   OBJECT-TYPE
     SYNTAX     INTEGER
     ACCESS     read-only
     STATUS     mandatory
     DESCRIPTION "value report from LT.
        line test result value 13 of the specified line and test type , reserved for future use
        ALCATEL-LUCENT NOTE:
                ACCESS:     RO
                USAGE:       MAND
                PERSIST:        NO
                INSRVMOD:       NA
                RANGE:  NA
                DEFVALUE:  NA
                UNITS:  NA
                SPARSE: NO"
  ::= {ltLineIdExtReportEntry 18}

ltExtRpVal14   OBJECT-TYPE
     SYNTAX     INTEGER
     ACCESS     read-only
     STATUS     mandatory
     DESCRIPTION "value report from LT.
        line test result value 14 of the specified line and test type , reserved for future use
        ALCATEL-LUCENT NOTE:
                ACCESS:     RO
                USAGE:       MAND
                PERSIST:        NO
                INSRVMOD:       NA
                RANGE:  NA
                DEFVALUE:  NA
                UNITS:  NA
                SPARSE: NO"
  ::= {ltLineIdExtReportEntry 19}

ltExtRpVal15   OBJECT-TYPE
     SYNTAX     INTEGER
     ACCESS     read-only
     STATUS     mandatory
     DESCRIPTION "value report from LT.
        line test result value 15 of the specified line and test type , reserved for future use
        ALCATEL-LUCENT NOTE:
                ACCESS:     RO
                USAGE:       MAND
                PERSIST:        NO
                INSRVMOD:       NA
                RANGE:  NA
                DEFVALUE:  NA
                UNITS:  NA
                SPARSE: NO"
  ::= {ltLineIdExtReportEntry 20}

ltExtRpVal16   OBJECT-TYPE
     SYNTAX     INTEGER
     ACCESS     read-only
     STATUS     mandatory
     DESCRIPTION "value report from LT.
        line test result value 16 of the specified line and test type , reserved for future use
        ALCATEL-LUCENT NOTE:
                ACCESS:     RO
                USAGE:       MAND
                PERSIST:        NO
                INSRVMOD:       NA
                RANGE:  NA
                DEFVALUE:  NA
                UNITS:  NA
                SPARSE: NO"
  ::= {ltLineIdExtReportEntry 21}

ltExtRpValidity   OBJECT-TYPE
     SYNTAX     INTEGER (0..65535) 
     ACCESS     read-only
     STATUS     mandatory
     DESCRIPTION "This is a bitmap for the validity identification of the report values. 
0 = the measurement was not taken or the result is not reliable. 
1 = the measurement was taken and the result is reliable.
It will be stored as a decimal number such as 40960. It should be converted to binary: 1010 0000 0000 0000. The mapping rule for the bitmap is:
High bit=============>Low bit
ltExtRpVal1=======> ltExtRpVal16
			ltExtRpVal1   ltExtRpVal2   ltExtRpVal3   ltExtRpVal4   ltExtRpVal5   ltExtRpVal6   ...
Validity:       1             0             1              0            0             0         ...
        ALCATEL-LUCENT NOTE:
                ACCESS:     RO
                USAGE:       MAND
                PERSIST:        NO
                INSRVMOD:       NA
                RANGE:  NA  
                DEFVALUE:  NA
                UNITS:  NA      
                SPARSE: NO"     
  ::= {ltLineIdExtReportEntry 22}

  ltExtRpDtmfValue   OBJECT-TYPE
       SYNTAX     OCTET STRING
       ACCESS     read-only
       STATUS     mandatory
       DESCRIPTION "string value of report form voice LT. It displays the received DTMF number and this object is only applicable to the eVoiceDiagnosisH248Caller and eVoiceDiagnosisH248Callee NBLT types.
      ALCATEL-LUCENT NOTE:
           ACCESS:    WO
           USAGE:     MAND
           PERSIST:   NO
           INSRVMOD: NA
           RANGE:  NA
           DEFVALUE:  NA
           UNITS:  NA
           SPARSE: NO"
  ::= {ltLineIdExtReportEntry 23} 
 
-- LineId Report Table with Multi Results End

--BusyPort Table   

ltBusyPortTable OBJECT-TYPE
      SYNTAX SEQUENCE OF LtBusyPortEntry
      ACCESS not-accessible
      STATUS mandatory
      DESCRIPTION "ltBusyPortTable. It is used to retrieve the busy ports in current sessions.
      ALCATEL-LUCENT NOTE: 
      TABLESIZE: 1152(because ltMaxNumberOfSession is 16 and the max test item num of a session is 72, so the table size is 72*ltMaxNumberOfSession=1152) 
      DESCR: NA."   
   ::= {ltLineTest 9}
   
ltBusyPortEntry OBJECT-TYPE
      SYNTAX LtBusyPortEntry
      ACCESS not-accessible
      STATUS mandatory
      DESCRIPTION  "ltBusyPortEntry Table Entry."
      INDEX { ltBusyPortSessionId, ltBusyPortLineId }
   ::= {ltBusyPortTable 1}
   
LtBusyPortEntry::= SEQUENCE
{
	ltBusyPortSessionId     INTEGER,
	ltBusyPortLineId        Gauge,  
	ltBusyStatus            LtBusyStatus 
}

ltBusyPortSessionId OBJECT-TYPE
      SYNTAX INTEGER(1..255)
      ACCESS not-accessible
      STATUS mandatory
      DESCRIPTION "Index of ltBusyPortTable. SessionId associated with ltSessionId in ltSessionTable, its range is  [1,ltMaxNumberOfSession], 
	  As ltMaxNumberOfSession is set 16 in ALCATEL-LUCENT, so its range is [1,..16].
        ALCATEL-LUCENT NOTE:
                ACCESS:     NA
                USAGE:       NA
                PERSIST:        NO
                INSRVMOD:       NA
                RANGE:  [1..16]
                DEFVALUE:  NA
                UNITS:  NA
                SPARSE: NO"
   ::= {ltBusyPortEntry 1}

ltBusyPortLineId   OBJECT-TYPE
     SYNTAX     Gauge
     ACCESS     not-accessible
     STATUS     mandatory
     DESCRIPTION "It's the identifier of busy Line, such as 0x01110706
         +==============+ 
         |    nodeId    |   8 bits. this is the same to EQPTID 
         +==============+ 
         | Rack |SubRack|   8 bits. 
         +==============+ 
         |     slot     | 
         +==============+ 
         |    lineId    | 
         +==============+ 
   Rack,SubRack and lineId are 1-based. For example: for the port numbers: range from 0x01~0x30. 
       For slot: LT1: 01  LT2: 02 
   Example: 0x 01110510   
            0x 01   11                  05   10 
            (node1) (rack 1,subrack1) (LT5) (port 16)
            
   the mapping between ltLineId(logicIndex) and ifIndex:   
       Change from line test ID to ifindex:
              line test line ID format : 0xAABBCCDD
              ifindex format:          : 0xBBCC00DD-1
       Change form ifindex to line test ID:
           ifindex format:          : 0xXXYY00ZZ
           line test line ID format : 0x01XXYYZZ+1

   ALCATEL-LUCENT NOTE:
       ACCESS:     NA
       USAGE:       MAND
       PERSIST:    NO
       INSRVMOD:   NA
       RANGE:  NA
       DEFVALUE:  NA
       UNITS:  NA
       SPARSE: NO"
    ::= {ltBusyPortEntry 2}   

ltBusyStatus OBJECT-TYPE
      SYNTAX LtBusyStatus 
      ACCESS read-only
      STATUS mandatory
      DESCRIPTION "All the lines indexed by the ltBusyPortSessionId and ltBusyPortLineId can be retrieved. Current status (one choice from LtBusyStatus) will be returned. The status returned in ltBusyStatus object may be different in retrievals according to the actual status of such line. 
   ALCATEL-LUCENT NOTE:
       ACCESS:     NA
       USAGE:       MAND
       PERSIST:    NO
       INSRVMOD:   NA
       RANGE: 1|2|3|4  
       DEFVALUE:  1   --toBeTested 
       UNITS:  NA
       SPARSE: NO"
   ::= {ltBusyPortEntry 3}

-- BusyPort Table End

-- Vendor Info Table begin

ltVendorInfoTable OBJECT-TYPE
      SYNTAX SEQUENCE OF LtVendorInfoEntry
      ACCESS not-accessible
      STATUS mandatory
      DESCRIPTION "ltVendorInfoTable.
      ALCATEL-LUCENT NOTE: 
      TABLESIZE: 256 
      DESCR:NA."   
   ::= {ltLineTest 10}
   
ltVendorInfoEntry OBJECT-TYPE
      SYNTAX LtVendorInfoEntry
      ACCESS not-accessible
      STATUS mandatory
      DESCRIPTION "ltVendorInfoTable Table Entry."
      INDEX {ltBoardPosition}
   ::= {ltVendorInfoTable 1}
   
LtVendorInfoEntry::= SEQUENCE
{
      ltBoardPosition        INTEGER,
      ltVendorId             DisplayString,    
      ltHwVersion            DisplayString,   
      ltFwVersion           DisplayString
}

ltBoardPosition OBJECT-TYPE
      SYNTAX INTEGER (0 .. 4294967295)
      ACCESS not-accessible
      STATUS mandatory
      DESCRIPTION "It's the index of the ltVendorInfoTable. It specifies the board position such as 0x00110700
          +==============+
          |    nodeId    |   8 bits. this is the same to EQPTID, default as 00 for SIP/DSL linetest.
          +==============+
          | Rack |SubRack|   8 bits.
          +==============+
          |     slot     |
          +==============+
          |      0       |
          +==============+
    Rack,SubRack and slot are 1-based.
        For slot: LT1: 01  LT2: 02
    Example: 0x 00110700
             0x 00   11                  07   00
                     (rack 1,subrack1)  (LT7)
   ALCATEL-LUCENT NOTE:
       ACCESS:     NA
       USAGE:       MAND
       PERSIST:    NO
       INSRVMOD:   NA
       RANGE:   NA 
       DEFVALUE:  NA
       UNITS:  NA
       SPARSE: NO"
   ::= {ltVendorInfoEntry 1}

ltVendorId OBJECT-TYPE
      SYNTAX DisplayString
      ACCESS read-only
      STATUS mandatory
      DESCRIPTION "manufacturer of the measurement chipset, vendor name in string. Max length is 32.  
   ALCATEL-LUCENT NOTE:
       ACCESS:     NA
       USAGE:       MAND
       PERSIST:    NO
       INSRVMOD:   NA
       RANGE:   NA 
       DEFVALUE:  NA
       UNITS:  NA
       SPARSE: NO"
   ::= {ltVendorInfoEntry 2}


ltHwVersion OBJECT-TYPE
      SYNTAX DisplayString
      ACCESS read-only
      STATUS mandatory
      DESCRIPTION "LineTest chipset hardware version in string. The max length is 32. 
   ALCATEL-LUCENT NOTE:
       ACCESS:     NA
       USAGE:       MAND
       PERSIST:    NO
       INSRVMOD:   NA
       RANGE:   NA 
       DEFVALUE:  NA
       UNITS:  NA
       SPARSE: NO"
   ::= {ltVendorInfoEntry 3}

ltFwVersion OBJECT-TYPE
      SYNTAX DisplayString
      ACCESS read-only
      STATUS mandatory
      DESCRIPTION "LineTest chipset firmware version in string. The max length is 32. 
   ALCATEL-LUCENT NOTE:
       ACCESS:     NA
       USAGE:       MAND
       PERSIST:    NO
       INSRVMOD:   NA
       RANGE:   NA 
       DEFVALUE:  NA
       UNITS:  NA
       SPARSE: NO"
   ::= {ltVendorInfoEntry 4}

-- Vendor Info table end


-- ltHwStatusTable begin

ltHwStatusTable OBJECT-TYPE
      SYNTAX SEQUENCE OF LtHwStatusEntry
      ACCESS not-accessible
      STATUS mandatory
      DESCRIPTION "ltHwStatusTable.
      ALCATEL-LUCENT NOTE: 
      TABLESIZE: Maximal number of LT slots in the system
      DESCR:NA."   
   ::= {ltLineTest 12}
    
ltHwStatusEntry OBJECT-TYPE
      SYNTAX  LtHwStatusEntry
      ACCESS not-accessible
      STATUS mandatory
      DESCRIPTION "ltHwStatusTable Table Entry."
      INDEX {ltMeltBoardPosition} 
   ::= {ltHwStatusTable 1}
   
LtHwStatusEntry::= SEQUENCE
{
      ltMeltBoardPosition             INTEGER,
      ltMeltOperationalStatusGlobal   INTEGER,
      ltMeltOperationalStatusSlic1    INTEGER,
      ltMeltOperationalStatusSlic2    INTEGER,
      ltMeltOperationalStatusSlic3    INTEGER,
      ltMeltOperationalStatusSlic4    INTEGER,
      ltMeltOperationalStatusSlic5    INTEGER
}


ltMeltBoardPosition OBJECT-TYPE
      SYNTAX INTEGER (0 .. 4294967295)
      ACCESS not-accessible
      STATUS mandatory
      DESCRIPTION "It's the index of the ltHwStatusTable. It specifies the board position such as 0x00110700
          +==============+
          |    nodeId    |   8 bits. this is the same to EQPTID, default as 00 for SIP/DSL linetest.
          +==============+
          | Rack |SubRack|   8 bits.
          +==============+
          |     slot     |
          +==============+
          |      0       |
          +==============+
    Rack,SubRack and slot are 1-based.
        For slot: LT1: 01  LT2: 02
    Example: 0x 00110700
             0x 00   11                  07   00
                     (rack 1,subrack1)  (LT7)
   ALCATEL-LUCENT NOTE:
       ACCESS:     NA
       USAGE:       MAND
       PERSIST:    NO
       INSRVMOD:   NA
       RANGE:   NA 
       DEFVALUE:  NA
       UNITS:  NA
       SPARSE: NO"
   ::= {ltHwStatusEntry 1}

ltMeltOperationalStatusGlobal OBJECT-TYPE
     SYNTAX     INTEGER
      {
         operational (1),    
         notOperational (2)
      }
     ACCESS     read-only
     STATUS     mandatory
     DESCRIPTION "MELT global status: operational or not.
        ALCATEL-LUCENT NOTE:
                ACCESS:     RO
                USAGE:       MAND
                PERSIST:        NO
                INSRVMOD:       NA
                RANGE:  NA
                DEFVALUE:  NA
                UNITS:  NA
                SPARSE: NO"
  ::= {ltHwStatusEntry 2}

ltMeltOperationalStatusSlic1 OBJECT-TYPE
     SYNTAX     INTEGER
      {
         operational (1),    
         notOperational (2),
         notPresent (3)
      }
     ACCESS     read-only
     STATUS     mandatory
     DESCRIPTION "MELT SLIC 1 status: operational, not operational, not present
        ALCATEL-LUCENT NOTE:
                ACCESS:     RO
                USAGE:       MAND
                PERSIST:        NO
                INSRVMOD:       NA
                RANGE:  NA
                DEFVALUE:  NA
                UNITS:  NA
                SPARSE: NO"
  ::= {ltHwStatusEntry 3}


ltMeltOperationalStatusSlic2 OBJECT-TYPE
     SYNTAX     INTEGER
     {
         operational (1),    
         notOperational (2),
         notPresent (3)
      }
     ACCESS     read-only
     STATUS     mandatory
     DESCRIPTION "MELT SLIC 2 status: operational, not operational, not present
        ALCATEL-LUCENT NOTE:
                ACCESS:     RO
                USAGE:       MAND
                PERSIST:        NO
                INSRVMOD:       NA
                RANGE:  NA
                DEFVALUE:  NA
                UNITS:  NA
                SPARSE: NO"
  ::= {ltHwStatusEntry 4}

ltMeltOperationalStatusSlic3 OBJECT-TYPE
     SYNTAX     INTEGER
      {
         operational (1),
         notOperational (2),
         notPresent (3)
      }
     ACCESS     read-only
     STATUS     mandatory
     DESCRIPTION "MELT SLIC 3 status: operational, not operational, not present
        ALCATEL-LUCENT NOTE:
                ACCESS:     RO
                USAGE:       MAND
                PERSIST:        NO
                INSRVMOD:       NA
                RANGE:  NA
                DEFVALUE:  NA
                UNITS:  NA
                SPARSE: NO"
  ::= {ltHwStatusEntry 5}

ltMeltOperationalStatusSlic4 OBJECT-TYPE
     SYNTAX     INTEGER
      {
         operational (1),
         notOperational (2),
         notPresent (3)
      } 
     ACCESS     read-only
     STATUS     mandatory
     DESCRIPTION "MELT SLIC 4 status: operational, not operational, not present
        ALCATEL-LUCENT NOTE:
                ACCESS:     RO
                USAGE:       MAND
                PERSIST:        NO
                INSRVMOD:       NA
                RANGE:  NA
                DEFVALUE:  NA
                UNITS:  NA
                SPARSE: NO"
  ::= {ltHwStatusEntry 6}


ltMeltOperationalStatusSlic5 OBJECT-TYPE
     SYNTAX     INTEGER
      {
         operational (1),    
         notOperational (2),
         notPresent (3)
      }
     ACCESS     read-only
     STATUS     mandatory
     DESCRIPTION "MELT SLIC 5 status: operational, not operational, not present
        ALCATEL-LUCENT NOTE:
                ACCESS:     RO
                USAGE:       MAND
                PERSIST:        NO
                INSRVMOD:       NA
                RANGE:  NA
                DEFVALUE:  NA
                UNITS:  NA
                SPARSE: NO"
  ::= {ltHwStatusEntry 7}

-- ltHwStatusTable end

-- ltHwLineStatusTable begin

ltHwLineStatusTable OBJECT-TYPE
      SYNTAX SEQUENCE OF LtHwLineStatusEntry
      ACCESS not-accessible
      STATUS mandatory
      DESCRIPTION "ltHwLineStatusTable.
      ALCATEL-LUCENT NOTE: 
      TABLESIZE: DEP[Number of XDSL lines].
      DESCR:NA."   
   ::= {ltLineTest 13}
    
ltHwLineStatusEntry OBJECT-TYPE
      SYNTAX  LtHwLineStatusEntry
      ACCESS not-accessible
      STATUS mandatory
      DESCRIPTION "ltHwLineStatusTable Table Entry."
      INDEX {ifIndex} 
   ::= {ltHwLineStatusTable 1}
   
LtHwLineStatusEntry::= SEQUENCE
{
      ltMeltHwLineOperationalStatus     INTEGER
}

ltMeltHwLineOperationalStatus  OBJECT-TYPE
     SYNTAX     INTEGER
      {
         operational (1),    
         notOperational (2)
      }
     ACCESS     read-only
     STATUS     mandatory
     DESCRIPTION "MELT Hw status per line: operational or not.
        ALCATEL-LUCENT NOTE:
                ACCESS:     RO
                USAGE:      MAND
                PERSIST:    NO
                INSRVMOD:   NA
                RANGE:      NA
                DEFVALUE:   NA
                UNITS:      NA
                SPARSE:     NO"
  ::= {ltHwLineStatusEntry 1}

-- ltHwLineStatusTable end

-- ltHwControlTable begin

ltHwControlTable OBJECT-TYPE
      SYNTAX SEQUENCE OF LtHwControlEntry
      ACCESS not-accessible
      STATUS mandatory
      DESCRIPTION "ltHwControlTable.
      ALCATEL-LUCENT NOTE: 
      TABLESIZE: Maximal number of LT slots in the system
      DESCR:NA."   
   ::= {ltLineTest 14}
    
ltHwControlEntry OBJECT-TYPE
      SYNTAX  LtHwControlEntry
      ACCESS not-accessible
      STATUS mandatory
      DESCRIPTION "ltHwControlTable Table Entry."
      INDEX { ltMeltHwCtrlBoardPosition } 
   ::= {ltHwControlTable 1}
   
LtHwControlEntry::= SEQUENCE
{
      ltMeltHwCtrlBoardPosition       INTEGER,
      ltMeltReset                     INTEGER,
      ltMeltSelfTest                  INTEGER
}


ltMeltHwCtrlBoardPosition OBJECT-TYPE
      SYNTAX INTEGER (0 .. 4294967295)
      ACCESS not-accessible
      STATUS mandatory
      DESCRIPTION "It's the index of the ltHwControlTable. It specifies the board position such as 0x00110700
          +==============+
          |    nodeId    |   8 bits. this is the same to EQPTID, default as 00 for SIP/DSL linetest.
          +==============+
          | Rack |SubRack|   8 bits.
          +==============+
          |     slot     |
          +==============+
          |      0       |
          +==============+
    Rack,SubRack and slot are 1-based.
        For slot: LT1: 01  LT2: 02
    Example: 0x 00110700
             0x 00   11                  07   00
                     (rack 1,subrack1)  (LT7)
   ALCATEL-LUCENT NOTE:
       ACCESS:     NA
       USAGE:       MAND
       PERSIST:    NO
       INSRVMOD:   NA
       RANGE:   NA 
       DEFVALUE:  NA
       UNITS:  NA
       SPARSE: NO"
   ::= {ltHwControlEntry 1}

ltMeltReset OBJECT-TYPE
     SYNTAX     INTEGER
      {
         idle(1),
         resetStart(2),
         resetOngoing(3),
         resetFinished(4),
         resetUnavailable(5)
      }
     ACCESS     read-write
     STATUS     mandatory
     DESCRIPTION "Trigger the Reset operation on the MELT board and view the status of reset operation.This operation can be supported only for LT cards has Vinetic chipset. Check the ltVendorInfoTable for the chipset information.
                  idle            -> Initial state
                  resetStart      -> Trigger the MELT reset operation.
                  resetOngoing    -> Reset is in progress
                  resetFinished   -> Reset operation completed
                  resetUnavailable -> Unable to perform Reset operation due to some reason. For e.g. resource unavailability, operation not supported on the card.
                  Note:ResetStart can be triggered at any state of operation except on resetOngoing state.
        ALCATEL-LUCENT NOTE:
                ACCESS:     RW
                USAGE:       MAND
                PERSIST:        NO
                INSRVMOD:       NA
                RANGE:  NA
                DEFVALUE:  NA
                UNITS:  NA
                SPARSE: NO"
  ::= {ltHwControlEntry 2}

ltMeltSelfTest OBJECT-TYPE
     SYNTAX     INTEGER
      {
         idle(1),
         testStart(2),
         testOngoing(3),
         testfinishedAndPassed(4),
         testfinishedAndFailed(5),
         testUnfinished(6)
      }
     ACCESS     read-write
     STATUS     mandatory
     DESCRIPTION "Trigger the Self test operation on the MELT board and view the status of self test operation.
                  idle                  -> Initial state
                  testStart             -> Trigger the Self test.
                  testOngoing           -> Test is in progress
                  testfinishedAndPassed -> Test is completed
                  testfinishedAndFailed -> Test has completed with failure result
                  testUnfinished       -> Unable to perform operation due to some reason. For e.g. resource unavailability
Note: testStart can be triggered at any state of operation except on testOngoing state. 
        ALCATEL-LUCENT NOTE:
                ACCESS:     RW
                USAGE:       MAND
                PERSIST:        NO
                INSRVMOD:       NA
                RANGE:  NA
                DEFVALUE:  NA
                UNITS:  NA
                SPARSE: NO"
  ::= {ltHwControlEntry 3}

-- ltHwControlTable end

-- *****************************************************************
-- Line Test Define End.
-- *****************************************************************

   
   -- *****************************************************************
   -- signallingGatewayInterfaceTable
   -- *****************************************************************
   signallingGatewayInterfaceTable OBJECT-TYPE
      SYNTAX SEQUENCE OF SignallingGatewayInterfaceEntry
      ACCESS not-accessible
      STATUS mandatory
      DESCRIPTION "List of signalling gateways configured for this MGI for ISDN."
   ::= {signallingGatewayInterfaceConfig 1}

   -- *****************************************************************
   -- signallingGatewayInterfaceEntry
   -- *****************************************************************
   signallingGatewayInterfaceEntry OBJECT-TYPE
      SYNTAX SignallingGatewayInterfaceEntry
      ACCESS not-accessible
      STATUS mandatory
      DESCRIPTION "Entry holding configuration information for a gateway."
      INDEX {signallingGatewayInterfaceId}
   ::= {signallingGatewayInterfaceTable 1}

   SignallingGatewayInterfaceEntry ::= SEQUENCE
   {
      signallingGatewayInterfaceId SignallingGatewayInterfaceId, -- na
      signallingGatewayInterfaceRowStatus RowStatus, -- rw
      signallingGatewayInterfacePrimaryASPIPAddress IpAddress, --rw
      signallingGatewayInterfacePrimarySCTPPort INTEGER, --rw
      signallingGatewayInterfaceSecondaryASPIPAddress IpAddress, --rw
      signallingGatewayInterfaceSecondarySCTPPort INTEGER, --rw
      signallingGatewayInterfaceTertiaryASPIPAddress IpAddress, --rw
      signallingGatewayInterfaceTertiarySCTPPort INTEGER, --rw
      signallingGatewayInterfaceQuaternaryASPIPAddress IpAddress, --rw
      signallingGatewayInterfaceQuaternarySCTPPort INTEGER, --rw
      signallingGatewayInterfaceAssocASP INTEGER, -- ro
      signallingGatewayInterfaceIPAddress IpAddress, -- rw
      signallingGatewayInterfaceSCTPPort INTEGER, --ro
      signallingGatewayInterfaceUserLabel DisplayString, -- rw
      signallingGatewayInterfaceMGI MediaGatewayId, -- rw
      signallingGatewayInterfaceAdminStatus INTEGER, -- rw
      signallingGatewayInterfaceOperStatus INTEGER -- rw 
   }

   signallingGatewayInterfaceId OBJECT-TYPE
      SYNTAX SignallingGatewayInterfaceId
      ACCESS not-accessible
      STATUS mandatory
      DESCRIPTION "The unique signaling gateway Interface Id which identifies this
                   signaling gateway. Notice: this ID should be same to the ID of MGI it belongs to."
   ::= {signallingGatewayInterfaceEntry 1}

   signallingGatewayInterfaceRowStatus OBJECT-TYPE
      SYNTAX RowStatus
      ACCESS read-write
      STATUS mandatory
      DESCRIPTION "Allows to control the creation and deletion
                   of rows in this table."
   ::= {signallingGatewayInterfaceEntry 2}

   signallingGatewayInterfacePrimaryASPIPAddress OBJECT-TYPE
   	SYNTAX IpAddress
   	ACCESS read-write
      STATUS mandatory   	
   	DESCRIPTION "The IP Address of the Primary ASP."
   ::= {signallingGatewayInterfaceEntry 3}

   signallingGatewayInterfacePrimarySCTPPort OBJECT-TYPE
   	SYNTAX INTEGER(1..65534)
   	ACCESS read-write
      STATUS mandatory   	   	
   	DESCRIPTION "The SCTP Port of the Primary ASP"
   ::= {signallingGatewayInterfaceEntry 4}

   signallingGatewayInterfaceSecondaryASPIPAddress OBJECT-TYPE
   	SYNTAX IpAddress
   	ACCESS read-write
      STATUS mandatory   	   	
   	DESCRIPTION "The IP Address of the Secondary ASP "
   ::= {signallingGatewayInterfaceEntry 5}

   signallingGatewayInterfaceSecondarySCTPPort OBJECT-TYPE
   	SYNTAX INTEGER(1..65534)
   	ACCESS read-write
      STATUS mandatory   	   	
   	DESCRIPTION "The SCTP Port of the Secondary ASP"
        DEFVAL {9900}
   ::= {signallingGatewayInterfaceEntry 6}

   signallingGatewayInterfaceAssocASP OBJECT-TYPE
   	SYNTAX INTEGER
   	{ none  (0),
	    primary (1),
	    secondary (2),
	    both (3),
	    tertiary(4),
        quaternary(5)
  	}
   	ACCESS read-only
      STATUS mandatory   	   	
   	DESCRIPTION "The Associated ASP "
   ::= {signallingGatewayInterfaceEntry 7}

   signallingGatewayInterfaceIPAddress OBJECT-TYPE
   	SYNTAX IpAddress
   	ACCESS read-write
      STATUS mandatory   	   	
   	DESCRIPTION "The IP Address of the signalling gateway interface."
   ::= {signallingGatewayInterfaceEntry 8}

   signallingGatewayInterfaceSCTPPort OBJECT-TYPE
   	SYNTAX INTEGER(0..65535)
   	ACCESS read-only
      STATUS mandatory   	   	
   	DESCRIPTION "The SCTP Port of the signalling gateway interface."
   ::= {signallingGatewayInterfaceEntry 9}

   signallingGatewayInterfaceUserLabel OBJECT-TYPE
   	SYNTAX DisplayString
   	ACCESS read-write
      STATUS mandatory   	   	
   	DESCRIPTION "The User Label of the signalling gateway interface.
   	             The max number of the string is 64.
   	             The string accept all printable characters.
   	             It is mandatory parameters of signalling Gateway interface.
			           ALCATEL NOTE:
                 SUPPORT:        YES
                 PERSIST:        YES
                 INSRVMOD:       NA
                 RANGE:  NA
                 DEFVALUE: NA
                 UNITS:  NA"
   ::= {signallingGatewayInterfaceEntry 10}

   signallingGatewayInterfaceMGI OBJECT-TYPE
   	SYNTAX MediaGatewayId
   	ACCESS read-write
      STATUS mandatory   	   	
   	DESCRIPTION "The media gateway inteface ID associated with the 
   				signalling gateway interface."
   ::= {signallingGatewayInterfaceEntry 11}

   signallingGatewayInterfaceAdminStatus OBJECT-TYPE
      SYNTAX INTEGER
      {
         locked (1),
         unlocked (2)
      }
      ACCESS read-write
      STATUS mandatory
      DESCRIPTION "The current administrative state of the gateway."
      DEFVAL {locked}
   ::= {signallingGatewayInterfaceEntry 12}

   signallingGatewayInterfaceOperStatus OBJECT-TYPE
      SYNTAX INTEGER
      {
         up (1), 
         down (2)
      }
      ACCESS read-only
      STATUS mandatory
      DESCRIPTION "The current operational state of the gateway."
   ::= {signallingGatewayInterfaceEntry 13}
      
 signallingGatewayInterfaceTertiaryASPIPAddress OBJECT-TYPE
   	SYNTAX IpAddress
   	ACCESS read-write
      STATUS mandatory   	   	
   	DESCRIPTION "The IP Address of the Tertiary ASP "
   ::= {signallingGatewayInterfaceEntry 14}

   signallingGatewayInterfaceTertiarySCTPPort OBJECT-TYPE
   	SYNTAX INTEGER(1..65534)
   	ACCESS read-write
      STATUS mandatory   	   	
   	DESCRIPTION "The SCTP Port of the Tertiary ASP"
        DEFVAL {9900}
   ::= {signallingGatewayInterfaceEntry 15}

   signallingGatewayInterfaceQuaternaryASPIPAddress OBJECT-TYPE
    SYNTAX IpAddress
    ACCESS read-write
      STATUS mandatory          
    DESCRIPTION "The IP Address of the Quaternary ASP "
   ::= {signallingGatewayInterfaceEntry 16}

   signallingGatewayInterfaceQuaternarySCTPPort OBJECT-TYPE
    SYNTAX INTEGER(1..65534)
    ACCESS read-write
      STATUS mandatory          
    DESCRIPTION "The SCTP Port of the Quaternary ASP"
        DEFVAL {9900}
   ::= {signallingGatewayInterfaceEntry 17}

   -- *****************************************************************
   -- mediaGatewayNextId
   -- *****************************************************************
   signallingGatewayInterfaceNextId OBJECT-TYPE
      SYNTAX TestAndIncr
      ACCESS read-only
      STATUS mandatory
      DESCRIPTION "Next free identifier for a new signallingGatewayInterfaceEntry for ISDN."
   ::= {signallingGatewayInterfaceConfig 2}

-- *****************************************************************
-- accessSharedLineTerminationTable
-- *****************************************************************
   accessSharedLineTerminationTable OBJECT-TYPE
      SYNTAX SEQUENCE OF AccessSharedLineTerminationEntry
      ACCESS not-accessible
      STATUS mandatory
      DESCRIPTION
         "The accessSharedLineTerminationTable contains the list of configured secondary terminations.
          An entry MUST be configured for the secondary termination when the voice service is subscribed for the secondary termination i.e. the voice service is enabled at the MGC for the secondary termination.
          An entry MAY be configured for the secondary termination without voice service subscription i.e. the voice service for this port is disabled at the MGC.
          For this latter configuration option, the HW and Media Gateway behavior shall depend on the setting of the administrative state for this port as described for the accSharedLineTermVoiceServAtMgc object.
          The secondary termination entry ONLY can be configured after paired prime termination entry been created.
          This table is only applicable to 7302/7330 ISAM-V PSTN.
          A prime termination entry ONLY can be deleted after paired secondary termination entry been deleted.
          Parameters that are shared by prime and secondary termination are only defined at the prime termination entry,
          including following parameters:
             accTerminationAssocMedGwyId,
             accTerminationLineCharact,
             accTerminationImpedance,
             accTerminationRxGain,
             accTerminationTxGain.
         If a COMMON object is defined with INSRVMOD=no, the admin state of both must be locked before the value can be modified.
         If a COMMON object is defined with INSRVMOD=yes, the value can be modified directly no matter what admin status is.
          ALCATEL-LUCENT NOTE:
          TABLESIZE:  2500"
   ::= {accessTerminationConfig 6}

-- *****************************************************************
-- accessSharedLineTerminationEntry
-- *****************************************************************
   accessSharedLineTerminationEntry OBJECT-TYPE
      SYNTAX AccessSharedLineTerminationEntry
      ACCESS not-accessible
      STATUS mandatory
      DESCRIPTION "Entry holding configuration information for a configured secondary termination"
      INDEX {accSharedLineTerminationHldrEquipmentId, accSharedLineTerminationUserPortId}
   ::= {accessSharedLineTerminationTable 1}

   AccessSharedLineTerminationEntry ::= SEQUENCE
   {
      accSharedLineTerminationHldrEquipmentId     AccessEquipmentId,        -- na
      accSharedLineTerminationUserPortId          TerminationUserPortId,    -- na
      accSharedLineTerminationRowStatus           RowStatus,                -- rw
      accSharedLineTerminationtId                 AccessTerminationId,      -- rw
      accSharedLineTerminationOperStatus          INTEGER,                  -- ro
      accSharedLineTerminationAdminStatus         INTEGER,                  -- rw
      accSharedLineTerminationIdStr               DisplayString,            -- ro
      accSharedLineTerminationLockType            INTEGER,                  -- wo
      accSharedLineTerminationLockDelay           INTEGER,                  -- wo
      accSharedLineTerminationDirectoryNumber     DisplayString,            -- rw
      accSharedLineTerminationCallStatus          INTEGER,                  -- ro
      accSharedLineTerminationOpStatDownReason    INTEGER,                  -- ro
      accSharedLineTermVoiceServAtMgc             INTEGER                   -- rw
 }
accSharedLineTerminationHldrEquipmentId OBJECT-TYPE
      SYNTAX AccessEquipmentId
      ACCESS not-accessible
      STATUS mandatory
      DESCRIPTION "Internal identifier of the ISAM-V NE holding
                   the board owner of this user port.
      ALCATEL-LUCENT NOTE:
           ACCESS:   READ-WRITE
           USAGE:    MAND
           PERSIST:  YES
           INSRVMOD: NA
           RANGE:    NA
           DEFVALUE: NA
           UNITS:    NA
           SPARSE:   NO
           "
   ::= {accessSharedLineTerminationEntry 1}

accSharedLineTerminationUserPortId OBJECT-TYPE
      SYNTAX TerminationUserPortId
      ACCESS not-accessible
      STATUS mandatory
      DESCRIPTION "User Port identifier composed of the rack number (4 bits),
                   subrack number (4 bits), slot number (8 bits) and
                   port number (16 bits).
       ALCATEL-LUCENT NOTE:
            ACCESS:   READ-WRITE
            USAGE:    MAND
            PERSIST:  YES
            INSRVMOD: NA
            RANGE:    NA
            DEFVALUE: NA
            UNITS:    NA
            SPARSE:   NO
            "
   ::= {accessSharedLineTerminationEntry 2}

accSharedLineTerminationRowStatus OBJECT-TYPE
      SYNTAX RowStatus
      ACCESS read-write
      STATUS mandatory
      DESCRIPTION "Allows to control the creation and deletion of rows in this table.
        ALCATEL-LUCENT NOTE:
             ACCESS:   READ-WRITE
             USAGE:    MAND
             PERSIST:  NO
             INSRVMOD: YES
             RANGE:    1 | 4 | 6 -- active (1), createAndGo (4), destroy (6)
             DEFVALUE: NA
             UNITS:    NA
             SPARSE:   NO
             "
   ::= {accessSharedLineTerminationEntry 3}

accSharedLineTerminationtId OBJECT-TYPE
      SYNTAX AccessTerminationId
      ACCESS read-write
      STATUS mandatory
      DESCRIPTION "Unique identifier of the secondary termination, its range is [0..32767]
      if operator does not specify the value, the system will automatically assign a free termination ID in the range [0..32767].
        ALCATEL-LUCENT NOTE:
             ACCESS:    READ-WRITE
             USAGE:     OPT
             PERSIST:   NO
             INSRVMOD:  NO
             RANGE:     NA
             DEFVALUE:  NA
             UNITS:     NA
             SPARSE:    NO
             DESCR:     NA
             "
   ::= {accessSharedLineTerminationEntry 4}

accSharedLineTerminationOperStatus OBJECT-TYPE
      SYNTAX INTEGER
      {
         up (1),
         down (2),
         shuttingdown (3)
      }
      ACCESS read-only
      STATUS mandatory
      DESCRIPTION "The current operational state of the secondary termination.
        ALCATEL-LUCENT NOTE:
           ACCESS:    RO
           USAGE:     MAND
           PERSIST:   NO
           INSRVMOD:  NO
           RANGE:     NA
           DEFVALUE:  NA
           UNITS:     NA
           SPARSE:    NO
           DESCR:     NA
           "
      ::= {accessSharedLineTerminationEntry 5}

accSharedLineTerminationAdminStatus OBJECT-TYPE
      SYNTAX INTEGER
      {
         locked (1),
         unlocked (2)
      }
      ACCESS read-write
      STATUS mandatory
      DESCRIPTION "The current administrative state of the secondary termination.
         ALCATEL-LUCENT NOTE:
              ACCESS:    READ-WRITE
              USAGE:     OPT
              PERSIST:   YES
              INSRVMOD:  YES
              RANGE:     1 | 2
              DEFVALUE:  1
              UNITS:     NA
              SPARSE:    NO
              DESCR:     NA
      "
      DEFVAL {locked}
   ::= {accessSharedLineTerminationEntry 6}

accSharedLineTerminationIdStr OBJECT-TYPE
    SYNTAX  DisplayString
    ACCESS  read-only
    STATUS  mandatory
    DESCRIPTION "The String of the secondary Termination Id.
        In this string, it use the digit to replace the medGwyPstnTermFormatStr or
        medGwyIsdnTermFormatStr. The max length is also 72.
        The string is something like the 'AL/Dslam_Id/rack/shelf/slot/port'.
        ALCATEL-LUCENT NOTE:
             ACCESS:    RO
             USAGE:     MAND
             PERSIST:   NO
             INSRVMOD:  NO
             RANGE:     NA
             DEFVALUE:  NA
             UNITS:     NA
             SPARSE:    NO
             DESCR:     NA ."
   ::= {accessSharedLineTerminationEntry 7}

accSharedLineTerminationLockType OBJECT-TYPE
    SYNTAX  INTEGER
    {
        force (1),
        graceful (2)
    }
    ACCESS  write-only
    STATUS  mandatory
    DESCRIPTION "The lock type of the secondary termination.
    Should be set ONLY if the AdminStatus is locked.
    ALCATEL-LUCENT NOTE:
        ACCESS:    WO
        USAGE:     MAND
        PERSIST:   NO
        INSRVMOD:  NO
        RANGE:     NA
        DEFVALUE:  force
        UNITS:     NA
        SPARSE:    NO
        DESCR:     NA "
        DEFVAL  {force}
   ::= {accessSharedLineTerminationEntry 8}

accSharedLineTerminationLockDelay  OBJECT-TYPE
    SYNTAX  INTEGER (0..3600000)
    ACCESS  write-only
    STATUS  mandatory
    DESCRIPTION "The delay timer before lock the secondary termination,
        The object is only valid when accSharedLineTerminationLockType is equal to graceful (2).
        The range of this object is equal and large than zero.
    ALCATEL-LUCENT NOTE:
        ACCESS:     WO
        USAGE:      MAND
        PERSIST:    NO
        INSRVMOD:   NO
        RANGE:      0..3600000
        DEFVALUE:   0
        UNITS:      MILLISECOND
        SPARSE:     NO
        DESCR:      NA "
        DEFVAL  {0}
   ::= {accessSharedLineTerminationEntry 9}

accSharedLineTerminationDirectoryNumber OBJECT-TYPE
    SYNTAX DisplayString
    ACCESS read-write
    STATUS mandatory
    DESCRIPTION
        "The secondary termination Directory Number associated with the POTS line.
         This field will be provisioned via the 5529 APC as part of the subscriber provisioning process.
         The new data field can enter any ASCII-String (not only digit) with a maximum length of 16 characters.
        ALCATEL-LUCENT NOTE:
            ACCESS:     read-write
            USAGE:      OPT
            PERSIST:    Yes
            INSRVMOD:   NO
            RANGE:      SIZE(0..16)
            DEFVALUE:
            UNITS:      NA
            SPARSE:     NO
        "
    DEFVAL {""}
::= { accessSharedLineTerminationEntry 10 }

accSharedLineTerminationCallStatus OBJECT-TYPE
    SYNTAX INTEGER
        {
        none(0),
        onhook(1),
        offhook(2),
        dialling(3),
        calling(4),
        idleoffhook(6),
        busyTone(7),
        howlerTone(8),
        ringing(9),
        releasing(10),
        ringback(11),
        callerConnected(12),
        calleeConnected(13),
        sharedCutoff(14)
        }
    ACCESS read-only
    STATUS mandatory
    DESCRIPTION
        "The status of call at the secondary termination. The meaning of the status is list as following:
        none(0): there is no meaning when oper status is down and admin-status is down
        onhook(1): hook on without any call
        offhook(2): hookoff but user no dialling
        dialling(3): dial digit
        calling(4):setting up connection with remote (notify msg)
        idleoffhook(6): parking
        busyTone(7): this status unused after R41
        howlerTone(8): this status unused after R41
        ringing(9): ringing
        releasing(10): call has been terminated. but subscriber does not hook on. Some tone maybe play in this state. The line is in releasing state
        ringback(11): ringback tone to caller
        callerConnected(12): call has been setup (connected as caller)
        calleeConnected(13): call has been setup (connected as callee)
        sharedCutoff(14):The one termination configured at a shared line is cut off by the system
                                     when the other termination configured at that same share line is found to be in one of
                                     the following states : offhook, dialling, ringing, releasing, ringback, callerConnected,
                                     calleeConnected.
                                 The one termination that is in sharedCutoff state will hear silence upon going off-hook
                                     (no dial-tone is put at the line); Also incoming call attempts are rejected for the one
                                     termination in internal blocked state.

        ALCATEL-LUCENT NOTE:
            ACCESS:     NA
            USAGE:      NA
            PERSIST:    NO
            INSRVMOD:   NA
            RANGE:      0..14
            DEFVALUE    NA
            UNITS:      NA
            SPARSE:     NO
        "
    ::= { accessSharedLineTerminationEntry 11 }

accSharedLineTerminationOpStatDownReason OBJECT-TYPE
    SYNTAX INTEGER
        {
        none(0),
        registering(1),
        registrationFailure(2),
        physicalFailure(3)
        }
    ACCESS read-only
    STATUS mandatory
    DESCRIPTION
        "The operation status down reason of the secondary termination.
               none(0) - there is no meaning when term is up
               registering(1) - The secondary termination is registering.
               registrationFailure(2) - The secondary termination registration has failed.
               physicalFailure(3) - The secondary termination is out of service.

        ALCATEL-LUCENT NOTE:
            ACCESS:     NA
            USAGE:      NA
            PERSIST:    NO
            INSRVMOD:   NA
            RANGE:      0 | 1 | 2 | 3
            DEFVALUE    NA
            UNITS:      NA
            SPARSE:     NO
        "
    ::= { accessSharedLineTerminationEntry 12 }

accSharedLineTermVoiceServAtMgc   OBJECT-TYPE
    SYNTAX  INTEGER
    {
        enabled (1),
        disabled (2)
    }
    ACCESS  read-write
    STATUS  mandatory
    DESCRIPTION
        "This MIB object indicates whether the voice service is enabled/disabled at the MGC for the secondary termination.
        Enabled (1) : The secondary termination is known to the MGC. The secondary termination can be registered to the MGC.
        Disabled (2) : The secondary termination is NOT known to the MGC. The secondary termination CANNOT be registered to the MGC.
        When the secondary termination entry has this object set to 'disabled (2)' while the accSharedLineTerminationAdminStatus = locked, the secondary termination is not feeded; Should the secondary termination go off-hook, no tone is generated.
        When the secondary termination entry has this object set to 'disabled(2)' while the accSharedLineTerminationAdminStatus = unlocked, the secondary termination is feeded; Should the secondary termination go off-hook, a special busy tone with tone name = nnatone (number_not_assigned tone ) and with tone ID = 237, is played.
ALCATEL-LUCENT NOTE:
            ACCESS:    READ-WRITE
            USAGE:     OPT
            PERSIST:   YES
            INSRVMOD:  YES
            RANGE:     1 | 2
            DEFVALUE:  enabled (1) (for backward compatibility reason)
            UNITS:     NA
            SPARSE:    NO"
            DEFVAL  {enabled}
   ::= {accessSharedLineTerminationEntry 13}

END
