-- =============================================================================
--  This specification is published by Alcatel under Non-Disclosure
--  Agreement(s) (NDA) with specific parties and has to be considered as
--  Confidential Information as defined in such NDA.
--  Alcatel reserves the right to revise this document for any reason,
--  including but not limited to conformity with standards promulgated by
--  various agencies, utilisation of advances in the state of the technical
--  areas, or the reflection of changes in the design of any equipment,
--  techniques, or procedures described or referred to herein.
--  The product specifications and other technical or performance information
--  contained herein are subject to change without notice.
--  Updates of this document will be issued under the above NDA's.
--  Alcatel makes no representation or warranty, expressed or implied, with
--  respect to the sufficiency, accuracy, or utility of any information or
--  opinion contained herein. Alcatel expressly advises that any use of for 
--  any purpose or reliance upon this technical reference is at the risk of
--  the user and that Alcatel shall not be liable for any damage or injury
--  incurred by any person arising out of the sufficiency, accuracy, or
--  utility of any information or opinion contained herein.
--  This document is not to be construed as a suggestion to any manufacturer
--  to modify or change any of its products, nor does this document represent
--  any commitment by Alcatel to sell or purchase any product.
--  Nothing contained herein shall be construed as conferring by implication,
--  estoppel, or otherwise any license or right under any patent, whether or
--  not the use of any information herein necessarily employs an invention of
--  any existing or later issued patent.
--  Alcatel reserves the right not to offer any or all of these products and
--  to withdraw any or all of them at any future time.
--  Copyright (C) 2003, Alcatel. All Rights Reserved.
-- =============================================================================
--
--  MODULE-IDENTITY
--  LAST-UPDATED Oct 25, 2012
--  ORGANIZATION "Alcatel"
--  CONTACT-INFO
--
--          Email:  asam.mibsupport@alcatel.be
--
--  DESCRIPTION "This vendor specific MIB is defined to manage 
--               the PON and ONT aspects of the Alcatel FTTU platform. " 
--  
--  REVISION 
--  DESCRIPTION
--        "Version: 3FE-51251-AYAD-PBZZA
--         Editor: jinke.qi@alcatel-sbell.com.cn 
--	           susan.liu@alcatel-sbell.com.cn
--         Changes:  See below "
--  
--
-- =============================================================================
-- 
--  EPON MIB HISTORY
--  Li Lin C 28/12/2012
--  RCR ALU01780616 DPoE Multiple LLID 
--  Add MIB objects for EponOntEntry
--    Add eponOntLlidPattern
--  Remove MIB objects from EponOntEntry
--    Remove eponOntAssignableLinkNum
--  Add MIB objects for eponLogicalLinkEntry
--    Add eponLogicalLinkGroupId
--    Add eponLogicalLinkAssignedSerialNum

--  Yang Fan J 25/10/2012
--  RCR ALU01798442 DPoE Link OAM
--  Change Default value of OID eponOntFilterDot1p

--  Shi Jing C 12/09/2012
--  RCR ALU01810173 Configurable TPID on EPON ONU
--  Add MIB objects for EponOntEntry
--    Add eponOntConfigStpid
--    Add eponOntConfigCtpid

--.Agan  09/10/2012
--  For ISAM 4.5
--  RCR ALU01798442 - DPoE Link OAM
--      Added eponLanEtherPortStatTable for DPOE UNI statistics
--      Added DPOE codepoint to eponOntSwVerCtrlUpgradeMode attribute in eponOntSwVerCtlTable
--
-- Shivaaram - 10/5/2011
-- For ISAM4.3
-- RCR ALU00720037 - Embedded OTDR on EPON LT
--	  Added eponPonOltsideOpInfoSpecialFeatures in eponPonOltsideOpInfoTable (ALU00720037):
--
--
-- He yang - 12/20/2008
-- For FGU4.6.50:
--
-- He yang - 10/13/2009
-- For FGU4.X.X:
--  change: add one value for eponOntIgmpHandlingMode
--
-- Liu Sai - 7/10/2010
-- For ISAM4.2.20
-- Qi Jinke - 8/31/2010
-- For ISAM4.2.30
-- Guan Yue - 4/26/2011
-- For ISAM4.3.02

EPON-MIB DEFINITIONS ::= BEGIN

IMPORTS
  
        OBJECT-TYPE          FROM RFC-1212
         
        asam 		        FROM SYSTEM-MIB
        RowStatus            FROM SNMPv2-TC
        ifIndex              FROM ITF-MIB         
         
        AsamProfileIndex     FROM ASAM-TC-MIB
        AsamProfilePointer   FROM ASAM-TC-MIB
        AsamProfileName      FROM ASAM-TC-MIB
        AsamProfileRefCount  FROM ASAM-TC-MIB
        NetworkTimeInSeconds FROM ASAM-TC-MIB
        MacAddress	     FROM SNMPv2-TC 
        DisplayString        FROM RFC1213-MIB
        IpAddress            FROM RFC1155-SMI;

IfIndex ::= INTEGER (1..2147483647)

-- Administrative State 1 = unlock, 2 = lock

PonAdminState ::= INTEGER {enabled(1),disabled(2)}

Boolean ::= INTEGER (0..1)
EponTcClassfierFields ::= INTEGER (0..255)
--			{
--				destination mac (0),
--				source mac (1),
--				vlan priority (2),
--				vlan id (3),
--				ethernet type (4),
--				destination ip (5),
--				source ip (6),
--				ip version (7),
--				ip dscp (8),
--				ip precedence (9),
--				source l4 port (10),
--				destination l4 port (11),
--				IP protocol (12),
--				ipv6 traffic class (13),
--				ipv6 flow label (14),
--				ipv6 next header (15),
--				destination ipv6 address(16),
--				source ipv6 address(17),
--				destination ipv6 prefix(18),
--				source ipv6 prefix (19),
--        not defined(255)
--			}

EponTcClassfierOperators  ::= INTEGER (0..255)
--			{
--				nevermatch (0),
--				equal (1),
--				not equal (2),
--				less than or equal (3),
--				greater than or equal (4),
--				field exist (5),
--				field not exist (6),
--				always match (7),
--        not defined(255) 
--			}	

-- Operational State 1 = enabled, 2 = disabled

PonOperState ::= INTEGER {up(1),down(2)}

EponSystemPriority  ::= INTEGER
{ 
      bestEffort (0), 
      background (1), 
      spare (2), 
      excellentEffort (3), 
      controlledLoad (4), 
      videoLessThan100msLatencyAndJitter (5), 
      videoLessThan10msLatencyAndJitter (6), 
      networkControl (7) 
} 

EponOntPriority ::= INTEGER   
{ 
      bestEffort (0), 
      background (1), 
      spare (2), 
      excellentEffort (3), 
      controlledLoad (4), 
      videoLessThan100msLatencyAndJitter (5), 
      videoLessThan10msLatencyAndJitter (6), 
      networkControl (7),
      notset(255) 
} 


-- Next Profile Index (As Defined in ASAM-TC-MIB)
-- **********************************************
-- A Next Profile Index is used by the Agent to inform the Manager
-- of the next available Profile Index that may be used for creating
-- a new Profile.  This index must not be in use by an existing entry
-- in the table.  A value of 0 indicates no more profiles may be
-- defined in the associated table.

AsamNextProfileIndex ::= INTEGER(0..65535)

-- Max Profile Index(As Defined in ASAM-TC-MIB)
-- ********************************************
-- The Max Profile Index is used by the manager to know the maximum number
-- of profiles that can be created.

AsamMaxProfileIndex ::= INTEGER(0..65535)
apon OBJECT IDENTIFIER ::= { asam 35 }
epon OBJECT IDENTIFIER ::= { apon 50 }

eponPonGroup  OBJECT IDENTIFIER ::= { epon 1 }

eponOntGroup  OBJECT IDENTIFIER ::= { epon 2 }  

eponLinkGroup  OBJECT IDENTIFIER ::= { epon 3 }

eponLanGroup  OBJECT IDENTIFIER ::= { epon 4 }

eponServicesGroup  OBJECT IDENTIFIER ::= { epon 5 }

eponProfilesGroup  OBJECT IDENTIFIER ::= { epon 6 } 

eponStatisticsGroup  OBJECT IDENTIFIER ::= { epon 7 }   
  
eponSystemGroup  OBJECT IDENTIFIER ::= { epon 9 } 

eponPotsGroup  OBJECT IDENTIFIER ::= { epon 10 }

eponOntSwGroup  OBJECT IDENTIFIER ::= { epon 11 }
-- *********************************************

-- EPON PON CONFIGURATION TABLE
--
-- This table contains configuration information specific to
-- an OLT's control of a specific PON port. Upon creation of
-- an OLT line card, the agent automatically creates 8 rows 
-- in this table (one for each PON port).

-- *********************************************

eponPonConfigTable  OBJECT-TYPE
	SYNTAX SEQUENCE OF EponPonConfigEntry
	ACCESS	not-accessible
	STATUS	mandatory  
	DESCRIPTION 
	 "  this table indicates pon interface.
	 ALCATEL NOTE:
             SUPPORT: YES   TABLESIZE: DEP"
	::= { eponPonGroup 1 }

eponPonConfigEntry  OBJECT-TYPE
	SYNTAX 	EponPonConfigEntry
	ACCESS	not-accessible
	STATUS	mandatory       
	DESCRIPTION
         "An entry in the eponPonConfigTable. 
          Row creation : Pon entry is created by the system when EPON board planed. 
          for ELT8-A, 8 Pon entry are auto-created when board planning.
          Row deletion : Pon entry is deleted by the system when EPON board planed. 
          for ELT8-A, 8 Pon entry are auto-deleted when board planning.
          ALCATEL NOTE:
             SUPPORT: YES"
	INDEX	{ eponPonConfigIfIndex }
	::= { eponPonConfigTable 1 }

EponPonConfigEntry ::= SEQUENCE {
    eponPonConfigIfIndex	            IfIndex,
    eponPonConfigPollingDiscoveryPeriod	    INTEGER,
    eponPonConfigDBAPollingInterval0        INTEGER,  
    eponPonConfigDBAPollingInterval1        INTEGER,
    eponPonConfigDBAPollingInterval2        INTEGER,
    eponPonConfigDBAPollingInterval3        INTEGER,
    eponPonConfigDBAPollingInterval4        INTEGER,
    eponPonConfigDBAPollingInterval5        INTEGER,
    eponPonConfigDBAPollingInterval6        INTEGER,
    eponPonConfigDBAPollingInterval7        INTEGER,  
    eponPonAuthMode                         INTEGER,
    eponPonPmCollectInd	                    INTEGER,
    eponPonConfigFecDownstreamInd           INTEGER,
    eponPonConfigRssiInd                    INTEGER,
    eponRSSIProfileId                       INTEGER,
    eponPonSFPType                          INTEGER,
    eponOpticalModuleType                   INTEGER,
    eponPonPortMode                         INTEGER,
    eponPonGetNextFree                      INTEGER,
    eponPonMaxOntNum                        INTEGER,
    eponPonFreeOntNum                       INTEGER,   
    eponPonConfigRogueTestCmd               INTEGER,
    eponPonIdlePwrTCAEnable                 INTEGER,
    eponPonIdlePwrTCAThreshold              INTEGER,
    eponPonIdlePwrCurrent                   INTEGER,
    eponPonRateLimitProfileId               INTEGER,
    eponPonDisablePortAsPkgOverload         Boolean
           }

eponPonConfigIfIndex  OBJECT-TYPE
	SYNTAX 	IfIndex
	ACCESS	read-only
	STATUS	mandatory
	DESCRIPTION 
		"Each row is indexed by the ifIndex of the
		 PON (which is statically assigned based
		 on slot/port on the OLT line card) 
                 ALCATEL NOTE:
                 ACCESS:     NA       USAGE:      NA
                 PERSIST:    YES      INSRVMOD:   NO
                 RANGE:      NA       DEFVALUE:   NA
                 UNITS:      NA       SPARSE:     NA
                "
::= { eponPonConfigEntry 1 }

eponPonConfigPollingDiscoveryPeriod  OBJECT-TYPE
	SYNTAX 	INTEGER (10..65540)	
	ACCESS	read-write
	STATUS	mandatory
	DESCRIPTION 
		"this object indicates the discovery windown for onu register.
         ALCATEL NOTE:
                 ACCESS:     NA       USAGE:      OPT
                 PERSIST:    YES      INSRVMOD:   YES
                 RANGE:      10..65540 DEFVALUE:   1000
                 UNITS:      Ms      SPARSE:     NA
		 "
::= { eponPonConfigEntry 2 }




eponPonConfigDBAPollingInterval0 OBJECT-TYPE
	SYNTAX	INTEGER
	ACCESS  read-write
	STATUS	mandatory
	DESCRIPTION
		" there are 8 DBA polling interval per pon interface. 
		Each polling interval time determines the DBA interval
		time. this object indicates the interval time for level-0.
		 Note that each LLID are configured one polling interval level via eponLogicalLinkDBAPollingLevel .
		 ALCATEL NOTE:
                 ACCESS:     NA       USAGE:      OPT
                 PERSIST:    YES      INSRVMOD:   YES
                 RANGE:      0..65535       DEFVALUE:   15
                 UNITS: 65.5us        SPARSE:     NA"
::= { eponPonConfigEntry  4} 

eponPonConfigDBAPollingInterval1 OBJECT-TYPE
	SYNTAX	INTEGER
	ACCESS  read-write
	STATUS	mandatory
	DESCRIPTION
		" there are 8 DBA polling interval per pon interface. 
		Each polling interval time determines the DBA interval
		time. this object indicates the interval time for level-1.
		 Note that each LLID are configued one polling interval level via eponLogicalLinkDBAPollingLevel .
		 ALCATEL NOTE:
                 ACCESS:     NA       USAGE:      OPT
                 PERSIST:    YES      INSRVMOD:   YES
                 RANGE:      0 .. 65535       DEFVALUE:   30
                 UNITS: 65.5us        SPARSE:     NA"
::= { eponPonConfigEntry  5}

eponPonConfigDBAPollingInterval2 OBJECT-TYPE
	SYNTAX	INTEGER
	ACCESS  read-write
	STATUS	mandatory
	DESCRIPTION
			" there are 8 DBA polling interval per pon interface. 
		Each polling interval time determines the DBA interval
		time. this object indicates the interval time for level-2.
		 Note that each LLID are configued one polling interval level via eponLogicalLinkDBAPollingLevel .
		 ALCATEL NOTE:
                 ACCESS:     NA       USAGE:      OPT
                 PERSIST:    YES      INSRVMOD:   YES
                 RANGE:      0 .. 65535       DEFVALUE:   60
                 UNITS: 65.5us        SPARSE:     NA"
::= { eponPonConfigEntry  6} 

eponPonConfigDBAPollingInterval3 OBJECT-TYPE
	SYNTAX	INTEGER
	ACCESS  read-write
	STATUS	mandatory
	DESCRIPTION
			" there are 8 DBA polling interval per pon interface. 
		Each polling interval time determines the DBA interval
		time. this object indicates the interval time for level-3.
		 Note that each LLID are configued one polling interval level via eponLogicalLinkDBAPollingLevel .
		 ALCATEL NOTE:
                 ACCESS:     NA       USAGE:      OPT
                 PERSIST:    YES      INSRVMOD:   YES
                 RANGE:      0 .. 65535       DEFVALUE:   60
                 UNITS: 65.5us        SPARSE:     NA"
::= { eponPonConfigEntry  7}   

eponPonConfigDBAPollingInterval4 OBJECT-TYPE
	SYNTAX	INTEGER
	ACCESS  read-write
	STATUS	mandatory
	DESCRIPTION
			" there are 8 DBA polling interval per pon interface. 
		 Each polling interval time determines the DBA interval
		 time. this object indicates the interval time for level-4.
		 Note that each LLID are configued one polling interval level via eponLogicalLinkDBAPollingLevel .
		 ALCATEL NOTE:
                 ACCESS:     NA       USAGE:      OPT
                 PERSIST:    YES      INSRVMOD:   YES
                 RANGE:      0 .. 65535  DEFVALUE:   60
                 UNITS: 65.5us        SPARSE:     NA"
::= { eponPonConfigEntry  8}

eponPonConfigDBAPollingInterval5 OBJECT-TYPE
	SYNTAX	INTEGER
	ACCESS  read-write
	STATUS	mandatory
	DESCRIPTION
		" there are 8 DBA polling interval per pon interface. 
		Each polling interval time determines the DBA interval
		time. this object indicates the interval time for level-5.
		 Note that each LLID are configued one polling interval level via eponLogicalLinkDBAPollingLevel .
		 ALCATEL NOTE:
                 ACCESS:     NA       USAGE:      OPT
                 PERSIST:    YES      INSRVMOD:   YES
                 RANGE:      0 .. 65535       DEFVALUE:   60
                 UNITS: 65.5us        SPARSE:     NA"

::= { eponPonConfigEntry  9}

eponPonConfigDBAPollingInterval6 OBJECT-TYPE
	SYNTAX	INTEGER
	ACCESS  read-write
	STATUS	mandatory
	DESCRIPTION
		" there are 8 DBA polling interval per pon interface. 
		Each polling interval time determines the DBA interval
		time. this object indicates the interval time for level-6.
		 Note that each LLID are configued one polling interval level via eponLogicalLinkDBAPollingLevel .
		 ALCATEL NOTE:
                 ACCESS:     NA       USAGE:      OPT
                 PERSIST:    YES      INSRVMOD:   YES
                 RANGE:      0 .. 65535       DEFVALUE:   60
                 UNITS: 65.5us        SPARSE:     NA"
::= { eponPonConfigEntry  10}

eponPonConfigDBAPollingInterval7 OBJECT-TYPE
	SYNTAX	INTEGER
	ACCESS  read-write
	STATUS	mandatory
	DESCRIPTION
			" there are 8 DBA polling interval per pon interface. 
		Each polling interval time determines the DBA interval
		time. this object indicates the interval time for level-7.
		 Note that each LLID are configued one polling interval level via eponLogicalLinkDBAPollingLevel .
		 ALCATEL NOTE:
                 ACCESS:     NA       USAGE:      OPT
                 PERSIST:    YES      INSRVMOD:   YES
                 RANGE:      0 .. 65535       DEFVALUE:   60
                 UNITS: 65.5us        SPARSE:     NA"
::= { eponPonConfigEntry  11}  

  eponPonAuthMode  OBJECT-TYPE
	SYNTAX 	INTEGER 
	ACCESS	read-write
	STATUS	mandatory
	DESCRIPTION 
		"ONT Authtication mode option for this pon interface level.   supported values are  
		 mixed(1)
		 MAC (2),
		 Logical(3)
         ALCATEL NOTE:
		 ACCESS: NA        usage: OPT
		 persistent: YES   INSRVMOD:YES
         RANGE:1..3     DEFVALUE: 1 
         UNITS: NA         SPARSE: NA  "
::= { eponPonConfigEntry  12}

eponPonPmCollectInd  OBJECT-TYPE
	SYNTAX 	INTEGER
	ACCESS	read-write
	STATUS	mandatory
	DESCRIPTION 
		" This indicates whether Performance Monitors
		   should be collected for PON.
	
		  1 = PM collection enabled
		  2 = PM collection disabled

		 Default = 2 = disabled.
  "
	::= { eponPonConfigEntry 13 }

eponPonConfigFecDownstreamInd  OBJECT-TYPE
	SYNTAX 	INTEGER {
		enable(1),
		disable(2)
	}
	ACCESS	read-write
	STATUS	mandatory
	DESCRIPTION 
		" Used to Enable/Disable use of FEC in Downstream direction
		   for all OLT transmissions on this PON..

		 Default = 2 = Disable "
	::= { eponPonConfigEntry 14 }
	
eponPonConfigRssiInd  OBJECT-TYPE
	SYNTAX 	INTEGER {
		enable(1),
		disable(2)
	}
	ACCESS	read-write
	STATUS	mandatory
	DESCRIPTION 
		" Used to Enable/Disable RSSI function on this PON..
		 Default = 2 = Disable "
	::= { eponPonConfigEntry 15 }
	
eponRSSIProfileId OBJECT-TYPE
	SYNTAX 	INTEGER 
	ACCESS	read-write
	STATUS	mandatory
	DESCRIPTION 
		"Indicate the RSSI TCA profile, refer to SfpRSSIProfileTable.
		default:0 means associate with nothing profile. 
		  The alarm high threshold for Rx power: refer to the object eponPonRxPowerAlmHigh in eponPonTcaTable.
		  The alarm low threshold for Rx power: refer to the object eponPonRxPowerAlmLow in eponPonTcaTable.
		
ALCATEL NOTE:
		 ACCESS: NA        usage: OPT
		 persistent: YES   INSRVMOD:YES
     RANGE:0           DEFVALUE: 0 
     UNITS: NA         SPARSE: NA  "
::= { eponPonConfigEntry 30}


     
eponPonSFPType OBJECT-TYPE
        SYNTAX  INTEGER 
        ACCESS  read-only
        STATUS  mandatory
        DESCRIPTION
                "show the actual optics module type which is indicated as PX20/PX20+ and APN.
ALCATEL NOTE:
                 ACCESS: NA        usage: NA
                 persistent: NO   INSRVMOD:NA
                 RANGE:           1-1000BASE-PX20+
                                  2-1000BASE-PX20
                                  3-10/1GBASE-PRX(T1)
                                  4-10GBASE-PR-D3(T2)
                                  5-10&1/1GBASE-PRX(T3)
                                  6-10&1/10GBASE-PR(T4)
                                  255-unknown
                 DEFVALUE: NA
                 UNITS: NA         SPARSE: NA  "

::= { eponPonConfigEntry 31}

eponOpticalModuleType OBJECT-TYPE
        SYNTAX  INTEGER
        ACCESS  read-write
        STATUS  mandatory
        DESCRIPTION
                "used to plan the optics module type plugging in the pon port which is indicated as PX20/PX20+ and APN.
ALCATEL NOTE:
                 ACCESS: NA        usage: OPT
                 persistent: YES   INSRVMOD:YES                                             
                 RANGE:           0-AUTO
                                  1-1000BASE-PX20+
                                  2-1000BASE-PX20
                                  3-10/1GBASE-PRX(T1)
                                  4-10GBASE-PR-D3(T2)
                                  5-10&1/1GBASE-PRX(T3)
                                  6-10&1/10GBASE-PR(T4)

                 DEFVALUE: AUTO
                 UNITS: NA         SPARSE: NA  "                                               
                                    
::= { eponPonConfigEntry 32}

eponPonPortMode OBJECT-TYPE                           
        SYNTAX  INTEGER
        ACCESS  read-write
        STATUS  mandatory
        DESCRIPTION                         
                "A bitmap, used to plan the pon port mode which is used to limit the registered ONT to this pon port.
                 bit0: 1G;
                 bit1: 10G Asymmetric;
                 bit2: 10G Symmetric.

                 before change it, should check if eponOntBandWidthType is matching or not and the pon port's status is down.
                 Default value: 7

ALCATEL NOTE:
                 ACCESS: NA        usage: OPT
                 persistent: YES   INSRVMOD:YES
                 RANGE:1~7
                 DEFVALUE: 7 
                 UNITS: NA         SPARSE: NA  "

::= { eponPonConfigEntry 33} 

eponPonGetNextFree OBJECT-TYPE
       SYNTAX INTEGER
       ACCESS  read-only
       STATUS  mandatory
       DESCRIPTION
       "pon get next free onu Id
        ALCATEL NOTE:
                 ACCESS:     NA        USAGE:      NA
                 PERSIST:    NO        INSRVMOD:   YES
                 RANGE:      NO        DEFVALUE:   NA
                 UNITS:      NA        SPARSE:     NA"
               
::= { eponPonConfigEntry 34}

eponPonMaxOntNum OBJECT-TYPE
       SYNTAX INTEGER
       ACCESS read-only
       STATUS mandatory
       DESCRIPTION
       "Max Ont number in a pon
       ALCATEL NOTE:
                 ACCESS:     NA        USAGE:      NA
                 PERSIST:    NO        INSRVMOD:   YES
                 RANGE:      NO        DEFVALUE:   NA
                 UNITS:      NA        SPARSE:     NA"      
	      
::= { eponPonConfigEntry 35}

eponPonFreeOntNum OBJECT-TYPE
       SYNTAX INTEGER
       ACCESS read-only
       STATUS mandatory
       DESCRIPTION
          "How many free onuId left
	  ALCATEL NOTE:
                 ACCESS:     NA        USAGE:      NA
                 PERSIST:    NO        INSRVMOD:   YES
                 RANGE:      NO        DEFVALUE:   NA
                 UNITS:      NA        SPARSE:     NA"
::= { eponPonConfigEntry 36}

eponPonConfigRogueTestCmd OBJECT-TYPE
	SYNTAX 	INTEGER 
	ACCESS	read-write
	STATUS	mandatory
	DESCRIPTION 
		"This attribute allows the manager to manually enable or disable
		PON rogue test diagnostic.
		Attribute values are as follows:
                0 - No Rogue Test has been done since system reset
		1 - Stop PON Rogue test
		2 - Initiate 'ON-OFF TEST' PON Rogue Test
		3 - Initiate 'PATTERN TEST' PON Rogue Test
                4 - Last time Rogue Test is ongoing
                5 - Last time Rogue Test finished
                6 - Last time Rogue Test Canceled
		Default = 0"
::= { eponPonConfigEntry 37}

eponPonIdlePwrTCAEnable OBJECT-TYPE
	SYNTAX 	INTEGER 
	ACCESS	read-write
	STATUS	mandatory
	DESCRIPTION 
		"This attribute allows the manager to enable or disable PON 
		   idle power monitor.
		   Attribute values are as follows:
		   1 - Enable
		   2 - Disable
		 Default = 2"
::= { eponPonConfigEntry 38}

eponPonIdlePwrTCAThreshold OBJECT-TYPE
	SYNTAX 	INTEGER 
	ACCESS	read-write
	STATUS	mandatory
	DESCRIPTION 
		"This attribute allows the manager to configure PON 
		idle power threshold. If the idle power larger than 
		threshold, system will report alarm. In rogue onu 
		detect, it only diagnose the idle power larger than 
		threshold.
    ALCATEL NOTE:
    ACCESS:     NA       USAGE:    NA
    PERSIST:    NO       INSRVMOD: NA
    RANGE:      0..65535  DEFVALUE: 10
    UNITS:      0.1uW     SPARSE:     NA
    DESCR:      NA "
::= { eponPonConfigEntry 39}

eponPonIdlePwrCurrent OBJECT-TYPE
	SYNTAX 	INTEGER 
	ACCESS	read-only
	STATUS	mandatory
	DESCRIPTION 
		"This attribute get current PON idle power value.
		ALCATEL NOTE:
    ACCESS:     NA       USAGE:    NA
    PERSIST:    NO       INSRVMOD: NA
    RANGE:      0..65535  DEFVALUE: NA
    UNITS:      0.1uW     SPARSE:     NA
    DESCR:      NA "
::= { eponPonConfigEntry 40}

eponPonRateLimitProfileId OBJECT-TYPE
        SYNTAX  INTEGER
        ACCESS  read-write
        STATUS  mandatory
        DESCRIPTION
          "Indicate the Protocol Rate Limit profile, refer to qosRateLimitProfileTable.
           0 means not associate any profile.
           default value is 0.
           This attribut is reserved for the future usage. It does not work in project 4.5.01
           ALCATEL NOTE:
                 ACCESS: YES       usage: OPT
                 persistent: YES   INSRVMOD:YES
                 RANGE:0..250      DEFVALUE: 0
                 UNITS: NA         SPARSE: NA  "
           DEFVAL { 0 }
::= { eponPonConfigEntry 41}

eponPonDisablePortAsPkgOverload  OBJECT-TYPE
        SYNTAX  Boolean
        ACCESS  read-write
        STATUS  mandatory
        DESCRIPTION
          "Indicates whether disable PON port when receive protocol packages number exceed the thershold value.
                 0 means no action when overload .
                 1 measn close PON port when overload.
           Defaultly, NOT to close PON port when protocol packages overload.
           This attribut is reserved for the future usage. It does not work in project 4.5.01
           ALCATEL NOTE:
                 ACCESS: YES       usage: OPT
                 persistent: YES   INSRVMOD:NA
                 RANGE:0..1        DEFVALUE: 0
                 UNITS: NA         SPARSE: NA "
           DEFVAL { 0 }
::= { eponPonConfigEntry 42 }
     
-- *********************************************
-- EPON PON DISCOVERED ONT TABLE
--	
-- For a specific PON, this table contains the 
-- MAC address of ONTs that have been auto-discovered but have
 --not yet been manually provisioned (i.e. ENTERED)
-- by the operator. In TL1, these are referred to as 
-- NEWEONT alarms. The operator does not directly
-- create or delete rows in this table.  The OLT
-- agent automatically manages the creation and
-- deletion of rows. Rows are automatically created
-- when an ONT is auto-discovered on a specific PON.
-- Rows are not automatically deleted just because a
-- NEWEONT alarm is cleared (the reason being that the
-- AWS still needs to reference the associated row to
-- determine the MAC address for the cleared NEWEONT alarm).
-- So, NEWEONT alarms are normally
-- cleared when an operator (or the system) creates an ONT on a
-- PON (with MAC address) that has a match in this
-- table )  This table is used to store ONT information that
-- is required to be displayed with the NEWEONT alarm
-- (i.e. ONT's MAC address). The table indexes (i.e. 
-- eponPonDiscovOntIfIndex and eponPonDiscovOntNum)
-- match up with the Index1 and Index 2 fields 
-- actually contained in the Alarm MIB (for a
-- NEWEONT alarm).
-- *********************************************

eponPonDiscovOntTable  OBJECT-TYPE
	SYNTAX SEQUENCE OF EponPonDiscovOntEntry
	ACCESS	not-accessible
	STATUS	mandatory  
	DESCRIPTION 
	"  this table indicates the discoveried ONT.
	 ALCATEL NOTE:
             SUPPORT: YES   TABLESIZE: DEP"
	::= { eponPonGroup 2 }

eponPonDiscovOntEntry  OBJECT-TYPE
	SYNTAX 	EponPonDiscovOntEntry
	ACCESS	not-accessible
	STATUS	mandatory  
	DESCRIPTION 
	"An entry in theeponPonDiscovOntTable . 
     Row creation :Rows are automatically created when an ONT is auto-discovered on a specific PON
     Row deletion : Rows are not automatically deleted just because a NEWEONT alarm is cleared
     ALCATEL NOTE:
        SUPPORT: YES"
	INDEX	{ eponPonConfigIfIndex,
		      eponPonDiscovOntNum }
	::= { eponPonDiscovOntTable 1 }

EponPonDiscovOntEntry ::= SEQUENCE {
	eponPonDiscovOntNum			             INTEGER,
	eponPonDiscovOntMacAddr		           MacAddress ,
    eponPonDiscovOntLogicalAuthID                DisplayString (SIZE(0..24)),
    eponPonDiscovOntAuthfailType INTEGER        

}


eponPonDiscovOntNum  OBJECT-TYPE
	SYNTAX 	INTEGER (1..128)
	ACCESS	read-only
	STATUS	mandatory
	DESCRIPTION 
	" it identified a specified ONT number. 
	ALCATEL NOTE:
	ACCESS:     NA       USAGE:      NA
    PERSIST:    NO     INSRVMOD:   NO
    RANGE:      1..128    DEFVALUE:   NA
    UNITS:      NA       SPARSE:     NA  "
	::= { eponPonDiscovOntEntry 1 }


eponPonDiscovOntMacAddr  OBJECT-TYPE
	SYNTAX 	MacAddress
	ACCESS	read-only
	STATUS	mandatory
	DESCRIPTION 
		"The  MAC address of the ONT that has been auto-discovered
		 on the specific PON. 
		 	ALCATEL NOTE:
	ACCESS:     NA       USAGE:      NA
    PERSIST:   NO        INSRVMOD:   NO
    RANGE:      NA       DEFVALUE:   NA
    UNITS:      NA       SPARSE:     NA  "

	::= { eponPonDiscovOntEntry 2 }  

eponPonDiscovOntLogicalAuthID OBJECT-TYPE
        SYNTAX  DisplayString (SIZE(0..24))
        ACCESS  read-only
        STATUS  mandatory
        DESCRIPTION
            " The Logical ID of the ONT that has been auto_discovered on the specific PON.

            ALCATEL NOTE:
                 ACCESS: NA        usage:NA
                 persistent: NO    INSRVMOD: NO
                 RANGE:NA          DEFVALUE: NA
                 UNITS: NA         SPARSE: NA "
        
        ::= { eponPonDiscovOntEntry 3 }

eponPonDiscovOntAuthfailType OBJECT-TYPE
        SYNTAX  INTEGER (0..3)
        ACCESS  read-only
        STATUS  mandatory
        DESCRIPTION
            " The Authentication failure type of the ONT that has been auto_discovered on the specific PON.
              0x00:  no failure
              0x01:  LOID not exist
              0x02:  Password error
              0x03:  LOID conflict      

            ALCATEL NOTE:
                 ACCESS: NA        usage:NA
                 persistent: NO   INSRVMOD: NO
         RANGE: 0~3        DEFVALUE: 0
         UNITS: NA         SPARSE: NA "
	
	::= { eponPonDiscovOntEntry 4 }

-- *********************************************
-- eponPonOltsideOpInfoTable==	
-- this table is used to get the temperature,Voltage,Bias,RX power and TX power at OLT pon
-- side.	
	eponPonOltsideOpInfoTable  OBJECT-TYPE
	SYNTAX SEQUENCE OF EponPonOltsideOpInfoEntry
	ACCESS	not-accessible
	STATUS	mandatory  
	DESCRIPTION 
	 "  this table indicates optical module parameter in pon interface.
	 ALCATEL NOTE:
             SUPPORT: YES   TABLESIZE: DEP"
	::= { eponPonGroup 3 }

eponPonOltsideOpInfoEntry  OBJECT-TYPE
	SYNTAX 	EponPonOltsideOpInfoEntry
	ACCESS	not-accessible
	STATUS	mandatory       
	DESCRIPTION
         "An entry in the eponPonConfigTable. 
          Row creation : Pon entry is auto-created by the system when EPON board planed. 
          for ELT8-A, 8 Pon entry are auto-created when board planning.
          Row deletion : Pon entry is auto-deleted by the system when EPON board planed. 
          for ELT8-A, 8 Pon entry are auto-deleted when board planning.
          ALCATEL NOTE:
             SUPPORT: YES"
	INDEX	{eponPonConfigIfIndex }
	::= { eponPonOltsideOpInfoTable 1 }

EponPonOltsideOpInfoEntry ::= SEQUENCE {
    eponPonOltsideOpInfoTemperature                      INTEGER,
    eponPonOltsideOpInfoVoltage                          INTEGER,
    eponPonOltsideOpInfoTxBias                           INTEGER,
    eponPonOltsideOpInfoTxPower                          INTEGER,
    eponPonOltsideOpInfoSpecialFeatures                  INTEGER,
    eponPon10GOltsideOpInfoTxBias                        INTEGER,
    eponPon10GOltsideOpInfoTxPower                       INTEGER
       }

  eponPonOltsideOpInfoTemperature  OBJECT-TYPE
	SYNTAX 	INTEGER 
	ACCESS	read-only
	STATUS	mandatory
	DESCRIPTION 
	"this object indicates curent temperature for OLT pon interface. FFFF means unknown
		ALCATEL NOTE:
                 ACCESS:     NA       USAGE:    NA
                 PERSIST:    NO      INSRVMOD: NA
                 RANGE:     -32768..32768      DEFVALUE:  NA
                 UNITS:    1/256 Celsius      SPARSE:     NA
                  "
::= { eponPonOltsideOpInfoEntry 1 }

eponPonOltsideOpInfoVoltage  OBJECT-TYPE
	SYNTAX 	INTEGER 
	ACCESS	read-only
	STATUS	mandatory
	DESCRIPTION 
	"this object indicates curent voltage for OLT pon interface. FFFF means unknown

		ALCATEL NOTE:
                 ACCESS:     NA       USAGE:    NA
                 PERSIST:    NO      INSRVMOD: NA
                 RANGE:     0..65500  DEFVALUE:  NA
                 UNITS:     100u Volt      SPARSE:     NA
                  "
::= { eponPonOltsideOpInfoEntry 2}
	
eponPonOltsideOpInfoTxBias  OBJECT-TYPE
	SYNTAX 	INTEGER 
	ACCESS	read-only
	STATUS	mandatory
	DESCRIPTION 
		"this object indicates curent Tx bias for OLT pon interface. FFFF means unknown

		ALCATEL NOTE:
                 ACCESS:     NA       USAGE:    NA
                 PERSIST:    NO      INSRVMOD: NA
                 RANGE:     0..65500      DEFVALUE:  NA
                 UNITS:     2uA      SPARSE:     NA
                  "
::= { eponPonOltsideOpInfoEntry  3}	 

eponPonOltsideOpInfoTxPower  OBJECT-TYPE
	SYNTAX 	INTEGER 
	ACCESS	read-only
	STATUS	mandatory
	DESCRIPTION 
	"this object indicates curent TX power for OLT pon interface.  FFFF means unknown

		ALCATEL NOTE:
                 ACCESS:     NA       USAGE:    NA
                 PERSIST:    NO      INSRVMOD: NA
                 RANGE:     0..65535      DEFVALUE:  NA
                 UNITS:     0.1 uW      SPARSE:     NA
                  "
::= { eponPonOltsideOpInfoEntry 4 }

eponPonOltsideOpInfoSpecialFeatures  OBJECT-TYPE
	SYNTAX 	INTEGER (0..255)
	ACCESS	read-only
	STATUS	mandatory
	DESCRIPTION 
		"SpecialFeatures byte at address 116(decimal) of A0 EEPROM of the
                 SFP module.
                 Following values are meaningfull :
                   20H : Default
                   21H : Supports 2500BASE-X 
                   22H : 10/100BASE FX/LX with PHY/SGMII
                   23H : 10/100/1000BASE-T Electrical with PHY/SGMII and without LOS
                   24H : 10/100/1000BASE-T with PHY/SGMII and with LOS
                   25H : Ethernet to E1/T1 
                   26H : GPON OLT
                   27H : GPON OTDR capable 
                   2AH : EPON OLT
                   2BH : EPON OTDR capable 
                   2CH : 10G EPON ONU SFP+

	  This attribute was first added in ISAM4.3   "
	::= { eponPonOltsideOpInfoEntry 5 }

eponPon10GOltsideOpInfoTxBias  OBJECT-TYPE
        SYNTAX  INTEGER           
        ACCESS  read-only
        STATUS  mandatory
        DESCRIPTION
                "this object indicates curent Tx bias for OLT 10G pon interface. FFFF means unknown
       
                ALCATEL NOTE:
                 ACCESS:     NA       USAGE:    NA
                 PERSIST:    NO      INSRVMOD: NA
                 RANGE:     0..65500      DEFVALUE:  NA
                 UNITS:     2uA      SPARSE:     NA
                  "
::= { eponPonOltsideOpInfoEntry  6}

eponPon10GOltsideOpInfoTxPower  OBJECT-TYPE
        SYNTAX  INTEGER
        ACCESS  read-only
        STATUS  mandatory
        DESCRIPTION
        "this object indicates curent TX power for OLT 10G pon interface.  FFFF means unknown
       
                ALCATEL NOTE:
                 ACCESS:     NA       USAGE:    NA
                 PERSIST:    NO      INSRVMOD: NA
                 RANGE:     0..65535      DEFVALUE:  NA
                 UNITS:     0.1 uW      SPARSE:     NA
                  "
::= { eponPonOltsideOpInfoEntry 7}

-- *********************************************
-- eponPonOltsideOntOpInfoTable==	
-- this table is used to get the temperature,Voltage,Bias,RX power and TX power at OLT pon
-- side.	
	eponPonOltsideOntOpInfoTable  OBJECT-TYPE
	SYNTAX SEQUENCE OF EponPonOltsideOntOpInfoEntry
	ACCESS	not-accessible
	STATUS	mandatory  
	DESCRIPTION 
	 "  this table indicates optical module parameter in pon interface.
	 ALCATEL NOTE:
             SUPPORT: YES   TABLESIZE: DEP"
	::= { eponPonGroup 4 }

eponPonOltsideOntOpInfoEntry  OBJECT-TYPE
	SYNTAX 	EponPonOltsideOntOpInfoEntry
	ACCESS	not-accessible
	STATUS	mandatory       
	DESCRIPTION
         "An entry in the eponPonOltsideOntOpInfoTable. 
          ALCATEL NOTE:
             SUPPORT: YES"
	INDEX	{eponOntIndex }
	::= { eponPonOltsideOntOpInfoTable 1 }

EponPonOltsideOntOpInfoEntry ::= SEQUENCE {
    eponPonOltsideOntOpInfoRxPower                          INTEGER 
       }

eponPonOltsideOntOpInfoRxPower  OBJECT-TYPE
	SYNTAX 	INTEGER 
	ACCESS	read-only
	STATUS	mandatory
	DESCRIPTION 
	"this object indicates certain ONT curent RX power for OLT pon interface. FFFF means unknown

		ALCATEL NOTE:
                 ACCESS:     NA       USAGE:    NA
                 PERSIST:    NO      INSRVMOD: NA
                 RANGE:     0..65535      DEFVALUE:  NA
                 UNITS:     0.1uW     SPARSE:     NA
                  "
::= { eponPonOltsideOntOpInfoEntry  1 }


-- *********************************************
-- eponPonTcaTable==	
-- this table is used to .	
	eponPonTcaTable  OBJECT-TYPE
	SYNTAX SEQUENCE OF EponPonTcaEntry
	ACCESS	not-accessible
	STATUS	mandatory  
	DESCRIPTION 
	 "  this table indicates OLT side TCA threshold
	 ALCATEL NOTE:
             SUPPORT: YES   TABLESIZE: DEP"
	::= { eponPonGroup 5 }

eponPonTcaEntry  OBJECT-TYPE
	SYNTAX 	EponPonTcaEntry
	ACCESS	not-accessible
	STATUS	mandatory       
	DESCRIPTION
         "An entry in the eponPonTcaTable .
          ALCATEL NOTE:
             SUPPORT: YES"
	INDEX	{eponPonConfigIfIndex }
	::= { eponPonTcaTable 1 }

EponPonTcaEntry ::= SEQUENCE {
    eponPonRxPowerAlmLow        INTEGER,
    eponPonRxPowerAlmHigh       INTEGER
       }

eponPonRxPowerAlmLow  OBJECT-TYPE
	SYNTAX 	INTEGER 
	ACCESS	read-write
	STATUS	mandatory
	DESCRIPTION 
	"this object indicates alarm low threshold for Rx power. If Rx power is less than 
         this vlaue, then alarm named Rx power too low at OLT side generated.

		ALCATEL NOTE:
                 ACCESS:     NA       USAGE:    NA
                 PERSIST:    NO      INSRVMOD: YES
                RANGE: 0..65535      DEFVALUE:  0 
                 UNITS:   0.1uW      SPARSE:     NA
                  "
::= { eponPonTcaEntry  1 }

eponPonRxPowerAlmHigh  OBJECT-TYPE
	SYNTAX 	INTEGER 
	ACCESS	read-write
	STATUS	mandatory
	DESCRIPTION 
	"this object indicates alarm high threshold for Rx power. If Rx power is more than 
         this vlaue, then alarm named Rx power too high at OLT side generated.

		ALCATEL NOTE:
                 ACCESS:     NA       USAGE:    NA
                 PERSIST:    NO      INSRVMOD: YES
                RANGE:      0..65535     DEFVALUE: 5012 
                 UNITS:     0.1uW     SPARSE:     NA
                  "
::= { eponPonTcaEntry  2 }

-- *********************************************
--  EPON PON ROGUE TEST RESULT TABLE
--	
-- For a specific PON, this table contains the 
-- rogue ont Test result information. It include rogue 
-- onu,unknow onu which is the OLT cannot get onu tx  
-- power controlcapibility and unsupport onu which is 
-- cannot support disable onu tx power control.
-- *********************************************

eponPonRogueTestResultTable  OBJECT-TYPE
	SYNTAX SEQUENCE OF EponPonRogueTestResultEntry
        ACCESS  not-accessible
        STATUS  mandatory
        DESCRIPTION
        "This table indicates rogue ONT test result.
        This table include rogue onu,unknow onu and unsupport
        onu. unknow onu is the OLT cannot get onu tx power control 
        capibility, cannot judge if the onu is rogue onu.
        unsupport onu is the onu cannot support disable onu tx 
        power control,not support on/off test. This table will be 
        generated when rogue onu detection finish. If  manager 
        start rogue onu detection, this table will be cleaned.
        The index are eponPonConfigIfIndex and eponPonRogueTestResultOntNum,
        eponPonConfigIfIndex is the index of eponPonConfigTable."
        ::= { eponPonGroup 6 }
        
eponPonRogueTestResultEntry OBJECT-TYPE
        SYNTAX   EponPonRogueTestResultEntry
        ACCESS  not-accessible
        STATUS  mandatory
        INDEX   {  eponPonConfigIfIndex,
		      eponPonRogueTestResultOntNum  }
        ::= { eponPonRogueTestResultTable 1 }

EponPonRogueTestResultEntry ::=  SEQUENCE { 
    eponPonRogueTestResultOntNum                  INTEGER,
    eponPonRogueTestResultOntMAC                  MacAddress,
    eponPonRogueTestResultOntIfindex              IfIndex,
    eponPonRogueTestResultOntStatus               INTEGER,
    eponPonRogueTestResultRogueAlmStatus          INTEGER
}
                       
eponPonRogueTestResultOntNum  OBJECT-TYPE
	SYNTAX 	INTEGER
	ACCESS	read-only
	STATUS	mandatory
	DESCRIPTION 
	"This attribute indicates the ONT number of rogue test result sequence
	 on the specific PON 
	ALCATEL NOTE:
	ACCESS:     NA       USAGE:      NA
	PERSIST:    NO       INSRVMOD:   NO
	RANGE:      NA       DEFVALUE:   NA
	UNITS:      NA       SPARSE:     NA  "
	::= { eponPonRogueTestResultEntry 1 }


eponPonRogueTestResultOntMAC  OBJECT-TYPE
	SYNTAX 	MacAddress
	ACCESS	read-only
	STATUS	mandatory
	DESCRIPTION 
        "This attribute indicates the MAC address of the rogue test result ont
        on the specific PON. if no MAC could be get, NULL will be shown.
	ALCATEL NOTE:
	ACCESS:     NA       USAGE:      NA
	PERSIST:    NO       INSRVMOD:   NO
	RANGE:      NA       DEFVALUE:   NA
	UNITS:      NA       SPARSE:     NA  "
	::= { eponPonRogueTestResultEntry 2 }  

eponPonRogueTestResultOntIfindex  OBJECT-TYPE
	SYNTAX 	IfIndex
	ACCESS	read-only
	STATUS	mandatory
	DESCRIPTION 
	"This attribute indicates the ONT ifindex of the rogue test
	on the specific PON.For unplanned ONT which has no ont ifindex,
	NULL will be shown, and using 0 to represent its value.
	ALCATEL NOTE:
	ACCESS:     NA                    USAGE:      NA
	PERSIST:    NO                    INSRVMOD:   NO
	RANGE:      0,1..2147483647       DEFVALUE:   NA
	UNITS:      NA                    SPARSE:     NA "
::= { eponPonRogueTestResultEntry 3 }

eponPonRogueTestResultOntStatus          OBJECT-TYPE
	SYNTAX 	INTEGER 
	ACCESS	read-only
	STATUS	mandatory
	DESCRIPTION 
	"This attribute indicates the ont status in rogue onu test result.
	unknow(1) - the OLT cannot get onu tx power control capibility, cannot judge if the onu is rogue onu.
	not-support(2) - the onu cannot support disable onu tx power control,not-support on/off test.
	rogueOnu(3)   - the onu is rogue onu.		
        noTest(4).- the onu is not tested, which has never online and no mac availabe for test
	ALCATEL NOTE:
	ACCESS:     NA      USAGE: NA
	PERSIST:    NO      INSRVMOD:   NO
	RANGE:      1..4    DEFVALUE:   NA
	UNITS:      NA      SPARSE:     NA
	DESCR:      NA"
::= { eponPonRogueTestResultEntry 4}

eponPonRogueTestResultRogueAlmStatus OBJECT-TYPE
	SYNTAX 	INTEGER 
	ACCESS	read-write
	STATUS	mandatory
	DESCRIPTION 
        "This attribute indicates rogue onu alarm status of onts in this table.
	This attribute allow user to clear rogue onu alarm by clear(3).only 
	clear(3) can be set, and the eponPonRogueTestResultRogueAlmStatus must
	be active(2).
	no-roguealarm(1) - the onu never report rogue alarm.
	active(2) - the onu has rogue alarm.
	clear (3) - the onu had rogue alarm,but the alarm be cleared.
	ALCATEL NOTE:
	ACCESS:     NA      USAGE: NA
	PERSIST:    NO      INSRVMOD:   NO
	RANGE:      1..3    DEFVALUE:   NA
	UNITS:      NA      SPARSE:     NA
	DESCR:      NA"
::= { eponPonRogueTestResultEntry 5}

-- *********************************************
-- *********************************************
--
-- EPON ONT TABLE
--
-- This is a new table for EPON. Rows are created as 
-- a result of operator provisioning action

-- *********************************************

eponOntTable  OBJECT-TYPE
	SYNTAX SEQUENCE OF EponOntEntry
	ACCESS	not-accessible
	STATUS	mandatory  
	DESCRIPTION 
	 "  this table indicates ONT.
	 ALCATEL NOTE:
             SUPPORT: YES   TABLESIZE: DEP"
	::= { eponOntGroup 1 }

eponOntEntry  OBJECT-TYPE
	SYNTAX 	EponOntEntry
	ACCESS	not-accessible
	STATUS	mandatory    
	DESCRIPTION
         "An entry in the eponOntTable.
          Row creation : one entry is created when operator configure ONT.
          Row deletion : one entry is deleted when operator set eponOntRowStatus as destroy.
          ALCATEL NOTE:
             SUPPORT: YES"
	INDEX	{ eponOntIndex }
	::= { eponOntTable 1 }

EponOntEntry ::= SEQUENCE {
	eponOntIndex				           IfIndex,
	eponOntRowStatus			           RowStatus,
	eponOntMacAddress		                   MacAddress, 
        eponOntLogicalAuthID			           DisplayString (SIZE(0..24)),
	eponOntLogicalAuthPassword		           DisplayString (SIZE(0..12)),

	eponOntVendorId			               OCTET STRING (SIZE(4)),
	eponOntModel                                   OCTET STRING (SIZE(4)),                     
	eponOntHardwareVersion			       OCTET STRING (SIZE(0..8)),
	eponOntChipVendorID                            OCTET STRING (SIZE(2)),     
	eponOntChipModule                              OCTET STRING (SIZE(2)), 
	eponOntChipVersion                             OCTET STRING (SIZE(3)),
        eponOntBatteryBackup		              Boolean, 
    
         
        eponOntSwActiveVersion		            OCTET STRING (SIZE(0..16)),
	eponOntSwPassiveVersion		            OCTET STRING (SIZE(0..16)), 
	eponOntFirmwareVersion                  OCTET STRING, 
	eponOntSwPlannedVersion		            OCTET STRING (SIZE(0..16)),
        eponOntSwDownloadVersion		        OCTET STRING (SIZE(0..16)),        
         
        eponOntRebootCmd			            INTEGER,
        eponOntAdminState			            PonAdminState,
        eponOntOperState                        PonOperState,

        eponOntFECCapability                    INTEGER,   
        eponOntFECMode                          INTEGER, 
    
        eponOntIgmpHandlingMode                 INTEGER,
        eponOntFastLeaveCapability              INTEGER,
        eponOntFastLeave                        INTEGER,
 	          
        eponOntRTT                              INTEGER, 

        eponOntMacAgeTime                       INTEGER,
    
        eponOntMaxSupportedLinksNum             INTEGER,
        eponOntAssignableUpstreamQueueNum       INTEGER,
	eponOntAssignableDownstreamQueueNum     INTEGER,
	eponOntLinkUpstreamMaxQueueNum          INTEGER,
	eponOntPortDownstreamMaxQueueNum        INTEGER,
        
        eponOntFEPortNum                        INTEGER,
        eponOntFEPortBitmap                     OCTET STRING,
        eponOntGEPortNum                        INTEGER,
        eponOntGEPortBitmap                     OCTET STRING,
        eponOntPotsPortNum                      INTEGER,
        eponOntE1PortNum                        INTEGER,
        eponOntAdsl2PlusPortNum                 INTEGER,
        eponOntVdslPortNum                      INTEGER,
    
        eponOntPhysicalLineIDAdmin               INTEGER,
        eponOntActualMacAddress                  MacAddress,
        eponOntAlarmAdmin                        PonAdminState,  
        eponOntSwActCommit                       INTEGER, 
        eponOntSwUpgradeMode                     INTEGER,
        eponOntPlannedVariant                    DisplayString,
        eponOntConfigMode                        INTEGER,
        eponOntTransmitID                        INTEGER,       
        eponOntTransmitIDadmin                   INTEGER,    
        eponOntConfigCounter                     INTEGER,
        eponOntType                              INTEGER,    
        eponOntProtectionType                    INTEGER,
        eponOntPonPortNum                        INTEGER,
        eponOntSlotNum                           INTEGER,
        eponOntWLANPortNum                       INTEGER,
        eponOntUSBPortNum                        INTEGER,
        eponOntRFPortNum                         INTEGER,
        eponOntIPV6Sense                         INTEGER,
        eponOntSFPPowerSupplyControlCapability   INTEGER,
        eponOntDiscovTime		         NetworkTimeInSeconds,
        eponOntAuthTime			         NetworkTimeInSeconds,
        eponOntONUIDMethod                       INTEGER,
        eponOntConfigcmd                         INTEGER,
        eponOntBandWidthType                     INTEGER,
        eponOntAlrmCtrlProfId                    INTEGER,
        eponOntConfigStpid                       INTEGER,
        eponOntConfigCtpid                        INTEGER,
        eponOntLlidPattern                        INTEGER,
        eponOntSNBundleControl                   INTEGER,
        eponOntSNBundleStatus                    INTEGER
}

eponOntIndex  OBJECT-TYPE
	SYNTAX 	IfIndex
	ACCESS	read-only
	STATUS	mandatory
	DESCRIPTION 
		"Each row is indexed by the ifIndex of the ONT.
		ALCATEL NOTE:
                 ACCESS:     NA       USAGE:      NA
                 PERSIST:    YES      INSRVMOD:   NO
                 RANGE:      NA       DEFVALUE:   NA
                 UNITS:      NA       SPARSE:     NA"
::= { eponOntEntry 1 }


eponOntRowStatus  OBJECT-TYPE
	SYNTAX 	RowStatus
	ACCESS	read-write
	STATUS	mandatory
	DESCRIPTION 
		"This object indicates the status of this entry.
		 ALCATEL NOTE:
		 ACCESS: NA        usage: MAND
         persistent: YES   INSRVMOD:YES
         RANGE:1,4,6       DEFVALUE: NA  
         UNITS: NA         SPARSE: NA  "
::= { eponOntEntry 2 }


eponOntMacAddress OBJECT-TYPE
	SYNTAX	MacAddress
	ACCESS	read-write
	STATUS  mandatory
	DESCRIPTION
	    "This object stores the base MAC address of ONT. It is a 6 octet string
as defined in Bridge-MIB. At least one of eponOntMacAddress and eponOntLogicalAuthID must be configured
when planning ONT.
 ALCATEL NOTE:
		 ACCESS: NA        usage: NA
         persistent: YES   INSRVMOD:NO      
         RANGE:NA        DEFVALUE: NA
         UNITS: NA         SPARSE: NA  "

::= {eponOntEntry 3}  
   
eponOntLogicalAuthID OBJECT-TYPE
	SYNTAX	DisplayString (SIZE(0..24))
	ACCESS	read-write
	STATUS  mandatory
	DESCRIPTION
	    "
	    This object stores the logical ID of ONT. At least one of eponOntMacAddress and eponOntLogicalAuthID must be configured
when planning ONT.

	    ALCATEL NOTE:
		 ACCESS: NA        usage:NA
		 persistent: YES   INSRVMOD:YES
         RANGE:NA        DEFVALUE: NA
         UNITS: NA         SPARSE: NA "
::= {eponOntEntry 4}

eponOntLogicalAuthPassword OBJECT-TYPE
	SYNTAX	DisplayString (SIZE(0..12))
	ACCESS	read-write
	STATUS  mandatory
	DESCRIPTION
	    "
        This object stores the password of ONT
	    ALCATEL NOTE:
		 ACCESS: NA        usage: NA
		 persistent: YES   INSRVMOD:YES
         RANGE:NA        DEFVALUE: NA
         UNITS: NA         SPARSE: NA "
::= {eponOntEntry 5} 

 
eponOntVendorId  OBJECT-TYPE
	SYNTAX 	OCTET STRING (SIZE(4))
	ACCESS	read-only
	STATUS	mandatory
	DESCRIPTION 
		"Used to represent vendor ID of ONT.  
		Vendor ID is a string of characters, which is used to identify the 
		specified ONU vendor, whose code follows ANSI T1.220 standard and 
		ASCII/ANSI character code. 
		(The code set for the Vendor_ID is specified in ANSI T1 .220. 
		The 4 characters are mapped in the 4-byte field by taking each ASCII/ANSI character code and concatenating them.)

		ALCATEL NOTE:
		 ACCESS: NA        usage: NA
		 persistent: NO   INSRVMOD:NA
         RANGE:NA        DEFVALUE: NA
         UNITS: NA         SPARSE: NA "
	::= { eponOntEntry 6 }
	
eponOntModel  OBJECT-TYPE
	SYNTAX 	OCTET STRING (SIZE(4))
	ACCESS	read-only
	STATUS	mandatory
	DESCRIPTION 
		"This object reprents the ONT type whose codes are defined by Vendor.
		ALCATEL NOTE:
		 ACCESS: NA        usage: NA
		 persistent: NO   INSRVMOD:NA
         RANGE:NA        DEFVALUE: NA
         UNITS: NA         SPARSE: NA "

::= { eponOntEntry 7 }

eponOntHardwareVersion  OBJECT-TYPE
	SYNTAX 	OCTET STRING (SIZE(0..8))
	ACCESS	read-only
	STATUS	mandatory
	DESCRIPTION 
		"This object indicates  hardware version of the ONT.
		 it should be ASCII code. If the version number length is less than 8 bytes, 
		 it should be put into the lowest bytes according to the lowest byte alignment.   
		ALCATEL NOTE:
		 ACCESS: NA        usage: NA
		 persistent: NO   INSRVMOD:NA
         RANGE:NA        DEFVALUE: NA
         UNITS: NA         SPARSE: NA "

::= { eponOntEntry 8 }


eponOntChipVendorID  OBJECT-TYPE
	SYNTAX 	OCTET STRING (SIZE(2))
	ACCESS	read-only
	STATUS	mandatory
	DESCRIPTION 
		"
		Vendor ID of chip is a string of characters, and its code follows JEDEC ID.
        ALCATEL NOTE:
		 ACCESS: NA        usage: NA
		 persistent: NO   INSRVMOD:NA
         RANGE:NA        DEFVALUE: NA
         UNITS: NA         SPARSE: NA "

::= { eponOntEntry  9 }	
	
eponOntChipModule  OBJECT-TYPE
	SYNTAX 	OCTET STRING (SIZE(2))
	ACCESS	read-only
	STATUS	mandatory
	DESCRIPTION 
		"Indicates chip module of ONT. 
		Chip part number, and its code is defined by chipset vendor.
		ALCATEL NOTE:
		 ACCESS: NA        usage: NA
		 persistent: NO   INSRVMOD:NA
         RANGE:NA        DEFVALUE: NA
         UNITS: NA         SPARSE: NA "

::= { eponOntEntry  10 }	 

eponOntChipVersion  OBJECT-TYPE
	SYNTAX 	OCTET STRING (SIZE(3))
	ACCESS	read-only
	STATUS	mandatory
	DESCRIPTION 
		"Indicates chip version of ONT. 
		If there is not version number, it can be Chip Design Date, whose format is YY/MM/DD
		ALCATEL NOTE:
		 ACCESS: NA        usage: NA
		 persistent: NO   INSRVMOD:NA
         RANGE:NA        DEFVALUE: NA
         UNITS: NA         SPARSE: NA "

::= { eponOntEntry  11 }


eponOntBatteryBackup  OBJECT-TYPE
	SYNTAX 	Boolean
	ACCESS	read-only
	STATUS	mandatory
	DESCRIPTION 
		"Indicates whether the ONT is equipped with battery backup.
		 0 means no backup battery .
		 1 measn it has backup battery.
		 ALCATEL NOTE:
		 ACCESS: NA        usage: NA
		 persistent: NO   INSRVMOD:NA
         RANGE:NA        DEFVALUE: NA
         UNITS: NA         SPARSE: NA "

::= { eponOntEntry 12 }


eponOntSwActiveVersion  OBJECT-TYPE
	SYNTAX 	OCTET STRING (SIZE(0..16))
	ACCESS	read-only
	STATUS	mandatory
	DESCRIPTION 
		"The active software version in the ONT.  
		it should be ASCII code. If the version number length is less than 16 bytes,
		 it should be put in the lowest bytes according to LSB alignment.

         ALCATEL NOTE:
		 ACCESS: NA        usage: NA
		 persistent: NO   INSRVMOD:NA
         RANGE:NA        DEFVALUE: NA
         UNITS: NA         SPARSE: NA "

	::= { eponOntEntry 13 }


eponOntSwPassiveVersion  OBJECT-TYPE
	SYNTAX 	OCTET STRING (SIZE(0..16))
	ACCESS	read-only
	STATUS	mandatory
	DESCRIPTION 
		"The passive software version in the ONT.
		 Cannot be created by operator - read from ONT.
		Note: Not Supported in R4230 release. 
		  ALCATEL NOTE:
		 ACCESS: NA        usage: NA
		 persistent: NO   INSRVMOD:NA
         RANGE:NA        DEFVALUE: NA
         UNITS: NA         SPARSE: NA "
::= { eponOntEntry 14 }   
	
eponOntFirmwareVersion  OBJECT-TYPE
	SYNTAX 	OCTET STRING 
	ACCESS	read-only
	STATUS	mandatory
	DESCRIPTION 
		"Firmware version of the ONT. it is hex number.
		ALCATEL NOTE:
		 ACCESS: NA        usage: NA
		 persistent: NO   INSRVMOD:NA
         RANGE:NA        DEFVALUE: NA
         UNITS: NA         SPARSE: NA "

::= { eponOntEntry  15 }


eponOntSwPlannedVersion  OBJECT-TYPE
	SYNTAX 	OCTET STRING (SIZE(0..16))
	ACCESS	read-write
	STATUS	mandatory
	DESCRIPTION 
		" The special string value UNPLANNED means that any download and activation processing 
		  associated with this attribute is inhibited.
		  Modification is permitted even after ONT activation.
		  Default = string value UNPLANNED  .
		   it should be ASCII code. If the version number length is less than 16 bytes,
		   it should be put in the lowest bytes according to LSB alignment.
		  ALCATEL NOTE:
		 ACCESS: NA        usage: OPT
		 persistent: YES   INSRVMOD:YES
		 RANGE:NA        DEFVALUE: UNPLANNED
         UNITS: NA         SPARSE: NA "

	::= { eponOntEntry 16}

eponOntSwDownloadVersion  OBJECT-TYPE
	SYNTAX 	OCTET STRING (SIZE(0..16))
	ACCESS	write-only
	STATUS	mandatory
	DESCRIPTION 
		" 	  This attribute is used to download an ONT Sw version  

		  
		  ALCATEL NOTE:
		 ACCESS: NA        usage: NA
		 persistent: YES  INSRVMOD:NA
         RANGE:NA        DEFVALUE: NA
         UNITS: NA         SPARSE: NA "
	::= { eponOntEntry 17 }
 
 
 eponOntRebootCmd  OBJECT-TYPE
	SYNTAX 	INTEGER {
		  restart(1)
		  
	}
	ACCESS	read-write
	STATUS	mandatory
	DESCRIPTION 
		"Manager sets this attribute to reboot ONU .
		 ALCATEL NOTE:
		 ACCESS: NA        usage: OPT
		 persistent: YES  INSRVMOD:YES
		 RANGE:1         DEFVALUE:NA
         UNITS: NA         SPARSE: NA "

::= { eponOntEntry 18}

eponOntAdminState  OBJECT-TYPE
	SYNTAX 	PonAdminState
	ACCESS	read-write
	STATUS	mandatory
	DESCRIPTION 
		"The Admin State of the ONT. 
		 enable(1)
		 disable(2)

		ALCATEL NOTE:
		 ACCESS: NA        usage: OPT
		 persistent: YES   INSRVMOD:YES
		 RANGE:1..2       DEFVALUE:1
         UNITS: NA         SPARSE: NA 

Note: NOT SUPPORTED in R4230 release, replaced by entry in ifMIB"
	::= { eponOntEntry 19 }

eponOntOperState  OBJECT-TYPE
	SYNTAX 	PonOperState
	ACCESS	read-only
	STATUS	mandatory
	DESCRIPTION 
		"Indicates operational state of the ONT.  
		up(1)
		down(2)
        ALCATEL NOTE:
                 ACCESS:     NA       USAGE: NA
                 PERSIST:    NO      INSRVMOD:   NO
                 RANGE:      1, 2    DEFVALUE:   NA
                 UNITS:      NA       SPARSE:     NA
                 DESCR:      NA
       Note: NOT SUPPORTED in R4230 release, replaced by entry in ifMIB"
::= { eponOntEntry  20}

                  
eponOntFECCapability  OBJECT-TYPE 
	SYNTAX 	INTEGER
	ACCESS	read-only
	STATUS	mandatory
	DESCRIPTION 
		"Indicates FEC ability of the ONT.  
		 unknown(0)
		 supported(1) 
		 not-supported(2)
		 ALCATEL NOTE:
                 ACCESS:     NA      USAGE: NA
                 PERSIST:    NO      INSRVMOD:   NO
                 RANGE:      0..2    DEFVALUE:   0
                 UNITS:      NA       SPARSE:     NA
                 DESCR:      NA"
::= { eponOntEntry  21}   

eponOntFECMode   OBJECT-TYPE
	SYNTAX 	INTEGER
	ACCESS	read-write
	STATUS	mandatory
	DESCRIPTION 
		"this object is valid only in case Indicates eponOntFECCapability equal to supported.
		 this object enable or disabale FEC mode of the ONT. 
		 enable(1)
		 disable(2)
		ALCATEL NOTE:
                 ACCESS:     NA      USAGE: OPT
                 PERSIST:   YES     INSRVMOD:  YES
                 RANGE:      1..2    DEFVALUE:   2
                 UNITS:      NA       SPARSE:     NA
                 DESCR:      NA"

::= { eponOntEntry  22 }

       
eponOntIgmpHandlingMode OBJECT-TYPE
	SYNTAX	INTEGER
	ACCESS  read-write
	STATUS	mandatory
	DESCRIPTION
		" This object is used to determine the IGMP handling mode on a paticular UNI.
		
		Attribute values are as follows:
		
		  0 - IGMP snooping mode
		  1 - controllable IGMP mode 
2-  flooding mode
          
		  ALCATEL NOTE:
                 ACCESS:     NA      USAGE: OPT
                 PERSIST:    YES     INSRVMOD:  YES
                 RANGE:      0..2    DEFVALUE:   1                
                 UNITS:      NA       SPARSE:     NA"
 ::= { eponOntEntry 23} 
 
eponOntFastLeaveCapability OBJECT-TYPE
	SYNTAX 	INTEGER
	ACCESS	read-only
	STATUS	mandatory
	DESCRIPTION 
		"Indicates ONT fast leave ability.  It's a bitmap.
                 bit1: IGMP snooping non-fast-leave
                 bit2: IGMP snooping fast-leave
                 bit3: CTC  non-fast-leave
                 bit4: CTC  fast-leave
        
            
  ALCATEL NOTE:
                 ACCESS:     NA      USAGE: NA
                 PERSIST:    YES     INSRVMOD:  YES
                 RANGE:     1..15    DEFVALUE:   NA
                 UNITS:      NA       SPARSE:     NA"

::= { eponOntEntry 24 }

                   
eponOntFastLeave OBJECT-TYPE
	SYNTAX 	INTEGER
    ACCESS	read-write
	STATUS	mandatory
	DESCRIPTION 
		"Indicates enable or disable ONT fast leave function . 
		  disable(1)
		  enable(2)
		  ALCATEL NOTE:
                 ACCESS:     NA      USAGE: OPT
                 PERSIST:    YES     INSRVMOD:  YES
                 RANGE:     1..2    DEFVALUE:   1
                 UNITS:      NA       SPARSE:     NA"

::= { eponOntEntry 25 }

     
 eponOntRTT  OBJECT-TYPE
	SYNTAX 	INTEGER
	ACCESS	read-only
	STATUS	mandatory
	DESCRIPTION 
		" Indicates the range value per ONT. 
 ALCATEL NOTE:
                 ACCESS:     NA       USAGE:     NA
                 PERSIST:    NO      INSRVMOD:   NO
                 RANGE:     0..27111  DEFVALUE:  NA
                 UNITS:      16ns TQ       SPARSE:     NA
                 DESCR:      NA"
::= { eponOntEntry  26 }  
	
eponOntMacAgeTime  OBJECT-TYPE
	SYNTAX 	INTEGER(0..287)
	ACCESS	read-write
	STATUS	mandatory
	DESCRIPTION 
		" Indicates MAC aging time per ONT .
 ALCATEL NOTE:
                 ACCESS:     NA       USAGE:      OPT
                 PERSIST:    YES      INSRVMOD:   YES
                 RANGE:      0..287   DEFVALUE: 287 
                 UNITS:      s     SPARSE:     NA
                 DESCR:      NA"
::= { eponOntEntry  27 }  	
	  
	  
	
	
eponOntMaxSupportedLinksNum  OBJECT-TYPE 
	SYNTAX INTEGER
	ACCESS read-only
	STATUS mandatory
	DESCRIPTION
	    	"This object indicates the max supported link number for ONT.  
	    	ALCATEL NOTE:
                 ACCESS:     NA       USAGE:      NA
                 PERSIST:    NO       INSRVMOD:   NA
                 RANGE:      NA       DEFVALUE: NA           
                 UNITS:      NA      SPARSE:     NA
                 DESCR:      NA"
::= { eponOntEntry 29 }	

eponOntAssignableUpstreamQueueNum   OBJECT-TYPE 
	SYNTAX INTEGER
	ACCESS read-only
	STATUS mandatory
	DESCRIPTION
	    	"This object stores the number of assigned upstream queues from ONT.
	    	ALCATEL NOTE:
                 ACCESS:     NA       USAGE:      NA
                 PERSIST:    NO       INSRVMOD:   NA
                 RANGE:      NA       DEFVALUE: NA           
                 UNITS:      NA      SPARSE:     NA
                 DESCR:      NA"

::= { eponOntEntry  31}  

eponOntAssignableDownstreamQueueNum   OBJECT-TYPE 
	SYNTAX INTEGER
	ACCESS read-only
	STATUS mandatory
	DESCRIPTION
	    	"This object stores the number of assigned downstream queues from ONT. 
	    	ALCATEL NOTE:
                 ACCESS:     NA       USAGE:      NA
                 PERSIST:    NO       INSRVMOD:   NA
                 RANGE:      NA       DEFVALUE: NA           
                 UNITS:      NA      SPARSE:     NA
                 DESCR:      NA"

::= {eponOntEntry 32}  	
	
eponOntLinkUpstreamMaxQueueNum  OBJECT-TYPE 
	SYNTAX INTEGER
	ACCESS read-only
	STATUS mandatory
	DESCRIPTION
	    	"This object stores the max queues per link in upstream direction from ONT.
	    	ALCATEL NOTE:
                 ACCESS:     NA       USAGE:      NA
                 PERSIST:    NO       INSRVMOD:   NA
                 RANGE:      NA       DEFVALUE: NA           
                 UNITS:      NA      SPARSE:     NA
                 DESCR:      NA"

::= { eponOntEntry 33} 

eponOntPortDownstreamMaxQueueNum  OBJECT-TYPE 
	SYNTAX INTEGER
	ACCESS read-only
	STATUS mandatory
	DESCRIPTION
	    	"This object stores the max queues per port in downstream direction from ONT. 
	    	ALCATEL NOTE:
                 ACCESS:     NA       USAGE:      NA
                 PERSIST:    NO       INSRVMOD:   NA
                 RANGE:      NA       DEFVALUE: NA           
                 UNITS:      NA      SPARSE:     NA
                 DESCR:      NA"

::= { eponOntEntry 34}
 
	
eponOntFEPortNum  OBJECT-TYPE
	SYNTAX 	INTEGER
	ACCESS	read-only
	STATUS	mandatory
	DESCRIPTION 
		"Indicates the number of FE ports per ONT. 
 ALCATEL NOTE:
                 ACCESS:     NA       USAGE:    NA
                 PERSIST:    NO      INSRVMOD:   NO
                 RANGE:      NA      DEFVALUE:  NA
                 UNITS:      NA       SPARSE:     NA
                 DESCR:      NA"
::= { eponOntEntry  35 }         
	
	
eponOntFEPortBitmap   OBJECT-TYPE
	SYNTAX 	OCTET STRING (SIZE(8))
	ACCESS	read-only
	STATUS	mandatory
	DESCRIPTION 
		"Indicates the bitmap of FE ports per ONT.                       
	   Indicates the bitmap of FE ports per ONT.   bitx=1 means port x is FE port.
	   bitx=0  means x is not FE port.
 ALCATEL NOTE:
                 ACCESS:     NA       USAGE:     NA
                 PERSIST:    NO      INSRVMOD:   NA
                 RANGE:      NA      DEFVALUE:  NA
                 UNITS:      NA       SPARSE:     NA
                 DESCR:      NA
"
::= { eponOntEntry  36 } 	
	
eponOntGEPortNum  OBJECT-TYPE
	SYNTAX 	INTEGER
	ACCESS	read-only
	STATUS	mandatory
	DESCRIPTION 
		" Indicates the number of GE ports per ONT 
 ALCATEL NOTE:
                 ACCESS:     NA       USAGE:      NA
                 PERSIST:    NO      INSRVMOD:   NA
                 RANGE:      NA    DEFVALUE:  NA
                 UNITS:      NA       SPARSE:     NA
                 DESCR:      NA
"
::= { eponOntEntry  37 } 
	
	
eponOntGEPortBitmap  OBJECT-TYPE
	SYNTAX 	OCTET STRING (SIZE(8))
	ACCESS	read-only
	STATUS	mandatory
	DESCRIPTION 
		" Indicates the bitmap of GE ports per ONT.   bitx=1 means port x is GE port.bitx=0  means
		x is not GE port.
 ALCATEL NOTE:
                 ACCESS:     NA       USAGE:     NA
                 PERSIST:    NO      INSRVMOD:   NA
                 RANGE:      NA      DEFVALUE:  NA
                 UNITS:      NA       SPARSE:     NA
                 DESCR:      NA
"
::= { eponOntEntry  38 }


eponOntPotsPortNum  OBJECT-TYPE
	SYNTAX 	INTEGER
	ACCESS	read-only
	STATUS	mandatory
	DESCRIPTION 
		"Indicates the number of POTS ports per ONT. 
 ALCATEL NOTE:
                 ACCESS:     NA       USAGE:     NA
                 PERSIST:    NO      INSRVMOD:   NA
                 RANGE:      NA    DEFVALUE:  NA
                 UNITS:      NA       SPARSE:     NA
                 DESCR:      NA"
	::= { eponOntEntry  39 }

eponOntE1PortNum  OBJECT-TYPE
	SYNTAX 	INTEGER
	ACCESS	read-only
	STATUS	mandatory
	DESCRIPTION 
		" Indicates the number of E1 ports per ONT 
 ALCATEL NOTE:
                 ACCESS:     NA       USAGE:     NA
                 PERSIST:    NO      INSRVMOD:   NA
                 RANGE:      NA    DEFVALUE:  NA
                 UNITS:      NA       SPARSE:     NA
                 DESCR:      NA"
::= { eponOntEntry  40 }
 
 
 eponOntAdsl2PlusPortNum  OBJECT-TYPE
	SYNTAX 	INTEGER
	ACCESS	read-only
	STATUS	mandatory
	DESCRIPTION 
		" Indicates the number of adsl2pluse ports per ONT. 
 ALCATEL NOTE:
                 ACCESS:     NA       USAGE:      NA
                 PERSIST:    NO      INSRVMOD:  NA
                 RANGE:      NA    DEFVALUE:  NA
                 UNITS:      NA       SPARSE:     NA
                 DESCR:      NA"
::= { eponOntEntry  41 }


eponOntVdslPortNum  OBJECT-TYPE
	SYNTAX 	INTEGER
	ACCESS	read-only
	STATUS	mandatory
	DESCRIPTION 
		" Indicates the number of vdsl ports per ONT 
 ALCATEL NOTE:
                 ACCESS:     NA      USAGE:     NA
                 PERSIST:    NO      INSRVMOD:   NA
                 RANGE:      NA      DEFVALUE:  NA
                 UNITS:      NA       SPARSE:     NA
                 DESCR:      NA "
::= { eponOntEntry  42 }

  
eponOntPhysicalLineIDAdmin  OBJECT-TYPE
	SYNTAX	INTEGER 
	ACCESS  read-write
	STATUS	mandatory
	DESCRIPTION
		" This object identify whether ONT should add option for DHCP/PPP partially.
		 enable(1)
		 disable(2)
		ALCATEL NOTE:
                 ACCESS:     NA       USAGE:    OPT
                 PERSIST:    YES      INSRVMOD:   NA
                 RANGE:      NA       DEFVALUE:  2
                 UNITS:      NA       SPARSE:     NA
                 DESCR:      NA "
::= { eponOntEntry  43}

eponOntActualMacAddress OBJECT-TYPE
	SYNTAX	MacAddress
	ACCESS	read-only
	STATUS  mandatory
	DESCRIPTION
	    "This object stores the actual MAC address of ONT. It is a 6 octet string
as defined in Bridge-MIB. The MAC address is get when ONT online.
 ALCATEL NOTE:
		 ACCESS:     NA   usage:       NA
         persistent: NO   INSRVMOD:    NA
         RANGE:      NA   DEFVALUE:    NA
         UNITS:      NA   SPARSE:      NA
         DESCR:      NA "

::= {eponOntEntry 44}  


eponOntAlarmAdmin  OBJECT-TYPE
	SYNTAX   PonAdminState
	ACCESS	read-write
	STATUS	mandatory
	DESCRIPTION 
		"Enable/disable EONT ONT alarms, Disable means TK chipset will not report any ONT alarms  
		ENABLE(1)
		DISABLE(2)
        ALCATEL NOTE:
                 ACCESS:     NA       USAGE: NA
                 PERSIST:    NO       INSRVMOD:   NO
                 RANGE:      1, 2     DEFVALUE:   2
                 UNITS:      NA       SPARSE:     NA
                 DESCR:      NA
                 Note: NOT SUPPORTED in R4230 release "
::= { eponOntEntry  45}

eponOntSwActCommit  OBJECT-TYPE
	SYNTAX 	INTEGER
	ACCESS	write-only
	STATUS	mandatory
	DESCRIPTION 
		" 
		  This attribute is used to active or commint an ONT Sw version    
		  
		   Active (1)
		   Commit(2)
		  
		 ALCATEL NOTE:
		 ACCESS: NA        usage: NA
		 persistent: NA  INSRVMOD:NA
         RANGE:NA        DEFVALUE: NA
         UNITS: NA         SPARSE: NA "
	::= { eponOntEntry 46 }  
	
 eponOntSwUpgradeMode  OBJECT-TYPE
	SYNTAX 	INTEGER
	ACCESS	read-write
	STATUS	mandatory
	DESCRIPTION 
		" 
		  This attribute is used to specify ONT Software upgarde Mode    
                   NONE (0)
		   CTC (1)
		   TK  (2)
                   DPoE (3)
		  
		 ALCATEL NOTE:
		 ACCESS: NA        usage: NA
		 persistent: NA    INSRVMOD:NA
         RANGE:0..3        DEFVALUE: 1
         UNITS: NA         SPARSE: NA "
	::= { eponOntEntry 47 }  

eponOntPlannedVariant   OBJECT-TYPE
        SYNTAX  DisplayString
        ACCESS  read-write
        STATUS  mandatory
        DESCRIPTION
                " This attribute is operator specified free-form displayable text field.
                  This attribute has same connotation as eponOntSwVerCtlPlannedVariant attribute in
                  eponOntSwVerCtlTable (where it represents a key in that table along with
                  eponOntSwVerCtlHwVersion attribute).

                  See descriptions in eponOntSwPlannedVersion and eponOntSwDownloadVersion
                  attributes regarding how this attribute plays a role when either of those attributes
                  are set to special value AUTO.

                  Modification is permitted.

                  Maximum of 16 displayable characters.

                  Default = null string.  "
        ::= { eponOntEntry 48 }

eponOntConfigMode  OBJECT-TYPE
      SYNTAX  INTEGER {
              disable(1),
              enable-ALU-mode(2),
              enable-CU-mode(3)              
      }
      ACCESS  read-write
      STATUS  mandatory
      DESCRIPTION 
              " Used to Enable/Disable ONT configuration save function.
                  Default = 1 = Disable.
        ALCATEL NOTE:
                ACCESS: NA       usage: OPT
                persistent: YES  INSRVMOD:YES 
                RANGE:1..3       DEFVALUE: 1  
                UNITS: NA        SPARSE: NA "
::= { eponOntEntry 49 }


eponOntTransmitID  OBJECT-TYPE
      SYNTAX  INTEGER {
              activeSFP(0),
              standbySFP(1),
              activeandstandbySFP(2)
      }
      ACCESS  read-write
      STATUS  mandatory
      DESCRIPTION
              "This attribute indicate the ONU optical Tx power supply control ID"
::= { eponOntEntry 50 }

eponOntTransmitIDadmin  OBJECT-TYPE
      SYNTAX  INTEGER(0..65535)
      ACCESS  read-write
      STATUS  mandatory
      DESCRIPTION
              "This attribute manage the ONU optical Tx power supply control ID shutdown time.
               0 means reenable TX power
               1..65534 means time for shutdown transmitID
               65535 means shutdown permanently
               ALCATEL NOTE:
               ACCESS:     NA       USAGE:    NA
               PERSIST:    NO       INSRVMOD: NA
               RANGE:      0..65535 DEFVALUE: NA
               UNITS:      Second   SPARSE:     NA
               DESCR:      NA "
::= { eponOntEntry 51 }

eponOntConfigCounter  OBJECT-TYPE
      SYNTAX  INTEGER
      ACCESS  read-only
      STATUS  mandatory
      DESCRIPTION
              "This attribute record the counter that OAM message from OLT to ONU."
::= { eponOntEntry 52 } 

eponOntType  OBJECT-TYPE
      SYNTAX  INTEGER
      ACCESS  read-only
      STATUS  mandatory
      DESCRIPTION 
              " This attribute indicate ont type.
                  SFU(0),
                  HGU(1),
                  SBU(2),
                  box_model_MDU(3),
                  mini_modular_MDU(4)- support Etherent interface type ,
                  box_modular_MDU(5) - support xDSL interface type ,
                  frame_modular_MDU(6) - support xDSL interface type,
                  modular_MDU(7) - support xDSL and Etherent board mixture,
                  MTU(8)  

        ALCATEL NOTE:
                ACCESS: NA       usage: NA
                persistent: NO  INSRVMOD:NO 
                RANGE: NA        DEFVALUE: NA
                UNITS: NA        SPARSE: NA "
::= { eponOntEntry 54 }

eponOntProtectionType  OBJECT-TYPE
      SYNTAX  INTEGER
      ACCESS  read-only
      STATUS  mandatory
      DESCRIPTION 
              " This attribute indicate which protection type the ont supported.
                  not support(0),
                  support typeC(1),
                  support typeD(2)
      
        ALCATEL NOTE:
                ACCESS: NA       usage: NA
                persistent: NO  INSRVMOD:NO 
                RANGE: NA        DEFVALUE: NA
                UNITS: NA        SPARSE: NA "
::= { eponOntEntry 55 }

eponOntPonPortNum  OBJECT-TYPE
      SYNTAX  INTEGER
      ACCESS  read-only
      STATUS  mandatory
      DESCRIPTION 
              " This attribute indicate the number of ont pon port.
        ALCATEL NOTE:
                ACCESS: NA       usage: NA
                persistent: NO  INSRVMOD:NO 
                RANGE: NA        DEFVALUE: NA
                UNITS: NA        SPARSE: NA "
::= { eponOntEntry 56 }

eponOntSlotNum  OBJECT-TYPE
      SYNTAX  INTEGER
      ACCESS  read-only
      STATUS  mandatory
      DESCRIPTION 
              " This attribute indicate the number of plugable MDU slot. This object is meaningless for SFU/HGU/SBU/box model MDU and the value is 0 for
                SFU/HGU/SBU/box model MDU.
        ALCATEL NOTE:
                ACCESS: NA       usage: NA
                persistent: NO  INSRVMOD:NO 
                RANGE: NA        DEFVALUE: NA
                UNITS: NA        SPARSE: NA "
::= { eponOntEntry 57 }

eponOntWLANPortNum  OBJECT-TYPE
      SYNTAX  INTEGER
      ACCESS  read-only
      STATUS  mandatory
      DESCRIPTION 
              " This attribute indicate WLAN port number that the ONT could support.
        ALCATEL NOTE:
                ACCESS: NA       usage: NA
                persistent: NO  INSRVMOD:NO 
                RANGE: NA        DEFVALUE: NA
                UNITS: NA        SPARSE: NA "
::= { eponOntEntry 58 }

eponOntUSBPortNum  OBJECT-TYPE
      SYNTAX  INTEGER
      ACCESS  read-only
      STATUS  mandatory
      DESCRIPTION 
              " This attribute indicate USB port number that the ONT could support.
        ALCATEL NOTE:
                ACCESS: NA       usage: NA
                persistent: NO  INSRVMOD:NO 
                RANGE: NA        DEFVALUE: NA
                UNITS: NA        SPARSE: NA "
::= { eponOntEntry 59 }

eponOntRFPortNum  OBJECT-TYPE
      SYNTAX  INTEGER
      ACCESS  read-only
      STATUS  mandatory
      DESCRIPTION 
              " This attribute indicate RF port number that the ONT could support.
        ALCATEL NOTE:
                ACCESS: NA       usage: NA
                persistent: NO  INSRVMOD:NO 
                RANGE: NA        DEFVALUE: NA
                UNITS: NA        SPARSE: NA "
::= { eponOntEntry 60 }

eponOntIPV6Sense  OBJECT-TYPE
      SYNTAX  INTEGER
      ACCESS  read-only
      STATUS  mandatory
      DESCRIPTION 
              " This attribute indicate the ONT could support IPV6 senseing or not.
                 nosupport(0),
                 support(1)
        ALCATEL NOTE:
                ACCESS: NA       usage: NA
                persistent: NO  INSRVMOD:NO 
                RANGE: NA        DEFVALUE: NA
                UNITS: NA        SPARSE: NA "
::= { eponOntEntry 61 }

eponOntSFPPowerSupplyControlCapability  OBJECT-TYPE
      SYNTAX  INTEGER
      ACCESS  read-only
      STATUS  mandatory
      DESCRIPTION 
              " This attribute indicate ONT could support SFP power control or not
                   0: not support power supply control
                   1: only support TX power control
                   2:Support both Tx and Rx power supply control
        ALCATEL NOTE:
                ACCESS: NA       usage: NA
                persistent: NO  INSRVMOD:NO 
                RANGE: NA        DEFVALUE: NA
                UNITS: NA        SPARSE: NA "
::= { eponOntEntry 62 }

eponOntDiscovTime OBJECT-TYPE
        SYNTAX   NetworkTimeInSeconds
        ACCESS   read-only
        STATUS   mandatory
        DESCRIPTION
            "This object indicate ONT discovery time, not support in R4230
 ALCATEL NOTE:
                 ACCESS:     NA   usage:       NA
         persistent: NO   INSRVMOD:    NA
         RANGE:      NA   DEFVALUE:    NA
         UNITS:      NA   SPARSE:      NA
         DESCR:      NA "

::= {eponOntEntry 63}

eponOntAuthTime OBJECT-TYPE
        SYNTAX  NetworkTimeInSeconds
        ACCESS  read-only
        STATUS  mandatory
        DESCRIPTION
            "This object indicate the time when ONT pass authentication, not support in R4230
 ALCATEL NOTE:
                 ACCESS:     NA   usage:       NA
         persistent: NO   INSRVMOD:    NA
         RANGE:      NA   DEFVALUE:    NA
         UNITS:      NA   SPARSE:      NA
         DESCR:      NA "

::= {eponOntEntry 64}

eponOntONUIDMethod  OBJECT-TYPE
      SYNTAX  INTEGER{
           sys(0),
           mac(1),
           loid(2)
           }
      ACCESS  read-write
      STATUS  mandatory
      DESCRIPTION
              "This indicates which value should be filled in ONUID for DHCP/PPP option.
               if value is SYS, the ontID method should be configured based on eponAccessLoopONUIDMethod .

                 Default = 0 = SYS.
                 1 = MAC,
                 2 = LOID.

                ALCATEL NOTE:
                 ACCESS: NA        usage:OPT
                 persistent: YES    INSRVMOD:YES
                 RANGE:0..2        DEFVALUE: 0
                 UNITS: NA         SPARSE: NA"
::= { eponOntEntry 65 }

eponOntConfigcmd  OBJECT-TYPE
      SYNTAX  INTEGER 
      ACCESS  read-write
      STATUS  mandatory
      DESCRIPTION 
              " Used to indicate action for configuration.This object, when read, always returns a value of
               No-Action(0). The Action range is 1-3.
               No-Action(0),
               Save-OAM(1),
               clear-OAM(2),
               restore-factory(3),

        ALCATEL NOTE:
                ACCESS: NA       usage: NA
                persistent: NO  INSRVMOD:YES 
                RANGE:0..3       DEFVALUE: 0  
                UNITS: NA        SPARSE: NA "
::= { eponOntEntry 66 }

eponOntBandWidthType  OBJECT-TYPE
      SYNTAX  INTEGER
      ACCESS  read-write
      STATUS  mandatory
      DESCRIPTION
              " Used to plan the Ont type should register.
                0: auto;
                1: 10G Symmetric;
                2: 10G Asymmetric;
                3: 1G.

                before change it, should check if it is matching with eponPonOpticalModuleType or not and the ont's status is down.
        ALCATEL NOTE:
                ACCESS: NA       usage: OPT
                persistent: YES  INSRVMOD:NO
                RANGE:1..3       DEFVALUE: auto
                UNITS: NA        SPARSE: NA "
::= { eponOntEntry 72 }

eponOntAlrmCtrlProfId  OBJECT-TYPE
SYNTAX  INTEGER
        ACCESS  read-write
        STATUS  mandatory
        DESCRIPTION
        "this object indicates the onu using which alarm control profile

                ALCATEL NOTE:
                 ACCESS:     NA       USAGE:    NA
                 PERSIST:    YES      INSRVMOD: NA
                 RANGE:      NA       DEFVALUE: 1 
                 UNITS:      NA      SPARSE:     NA
                  "

::= { eponOntEntry 73 }

eponOntConfigStpid  OBJECT-TYPE
	SYNTAX 	INTEGER(0..5)
	ACCESS	read-write
	STATUS	mandatory
	DESCRIPTION 
              " This attribute indicates an alternate S-VLAN TPID that is used to identify a S-VLAN tag in a frame, including the following values:
                  Default = 0 = 0x88a8,
                  1 = 0x8100,
                  2 = 0x9100,
                  3 = 0x9200,
                  4 = Reserve1,
                  5 = Reserve2.
 ALCATEL NOTE:
                 ACCESS:     NA       USAGE:      OPT
                 PERSIST:    YES      INSRVMOD:   YES
                 RANGE:      0..5     DEFVALUE:   0
                 UNITS:      NA       SPARSE:     NA
                 DESCR:      NA"

::= { eponOntEntry  74 }  
eponOntConfigCtpid  OBJECT-TYPE
	SYNTAX 	INTEGER(0..5)
	ACCESS	read-write
	STATUS	mandatory
	DESCRIPTION 
              " This attribute indicates an alternate C-VLAN TPID that is used to identify a C-VLAN tag in a frame, including the following values:
                  Default = 0 = 0x8100,
                  1 = 0x88a8,
                  2 = 0x9100,
                  3 = 0x9200,
                  4 = Reserve1,
                  5 = Reserve2.
ALCATEL NOTE:
                 ACCESS:     NA       USAGE:      OPT
                 PERSIST:    YES      INSRVMOD:   YES
                 RANGE:      0..5     DEFVALUE:   0
                 UNITS:      NA       SPARSE:     NA
                 DESCR:      NA"
::= { eponOntEntry  75 }

eponOntLlidPattern OBJECT-TYPE
	SYNTAX 	INTEGER
	ACCESS	read-write
	STATUS	mandatory
	DESCRIPTION 
              " This attribute indicates the LLID pattern of onu, 1*1, 1*4, 1* 8 for SFP and 2*1, 2*4 for salira ONU, including the following values:
                  0 =1*1, upstream: fixed 4 queue per LLID on ONT, downstream: select 4 or 8 queue per LLID on OLT, 4 is default
                  1 =1*4, upstream: fixed 1 queue per LLID on ONT, downstream: fixed 1 queue per LLID on OLT
                  2 =1*8, upstream: fixed 1 queue per LLID on ONT, downstream: fixed 1 queue per LLID on OLT
                  3 =2*1, upstream: fixed 4 queue per LLID on ONT, downstream: select 4 or 8 queue per LLID on OLT, 4 is default,LLID 1 belong to LLID group 1, LLID 2 belong to LLID group 2
                  4 =2*4, upstream: fixed 1 queue per LLID on ONT, downstream: fixed 1 queue per LLID on OLT
                LLID 1/2/3/4 belong to LLID group 1, LLID 5/6/7/8 belong to LLID group 2

ALCATEL NOTE:
                 ACCESS:     NA       USAGE:      OPT
                 PERSIST:    YES      INSRVMOD:   NO
                 RANGE:      0..4     DEFVALUE:   0
                 UNITS:      NA       SPARSE:     NA
                 DESCR:      NA"
::= { eponOntEntry  76 } 

eponOntSNBundleControl  OBJECT-TYPE
	SYNTAX 	INTEGER
	ACCESS	read-write
	STATUS	mandatory
	DESCRIPTION 
              "This attribute indicates whether the ONT should bundle MAC with LOID, 
                RCR: ALU01405714 OLT supports LOID bond with MAC.
Including the following values:
                  Default = 0 = Unbundle,
                  1 = Bundle, The operator manually bundle MAC with LOID.
                  2 = Auto-Bundle, Auto bundle the MAC with LOID after the first authentication of this ONU              
                       after a period of time.
ALCATEL NOTE:
                 ACCESS:     NA       USAGE:     OPT
                 PERSIST:    YES      INSRVMOD:   YES
                 RANGE:      0..2     DEFVALUE:   0
                 UNITS:      NA       SPARSE:     NA
                 DESCR:      NA"
::= { eponOntEntry  77 }

eponOntSNBundleStatus  OBJECT-TYPE
	SYNTAX 	INTEGER
	ACCESS	read-only
	STATUS	mandatory
	DESCRIPTION 
              "This attribute indicates whether the MAC of ONT is bundled with LOID, 
                RCR: ALU01405714 OLT supports LOID bond with MAC.
Including the following values:
                  Default = 0 = Unbundled,
                  1 = Bundled,
ALCATEL NOTE:
                 ACCESS:     NA       USAGE:     NA
                 PERSIST:    YES      INSRVMOD:   NA
                 RANGE:     0..1     DEFVALUE:   0
                 UNITS:      NA       SPARSE:     NA
                 DESCR:      NA"
::= { eponOntEntry  78}


-- *********************************************
-- *********************************************
--
-- EPON ONT TCA TABLE
--
-- This is an extention table of EPON ONT Table

-- *********************************************

eponOntTcaTable  OBJECT-TYPE
	SYNTAX SEQUENCE OF EponOntTcaEntry
	ACCESS	not-accessible
	STATUS	mandatory  
	DESCRIPTION 
	 "  this table indicates threshold for temperature,Voltage, Bias, rx-power and Tx-power per ONT.
	 ALCATEL NOTE:
             SUPPORT: YES   TABLESIZE: DEP"
	::= { eponOntGroup 2 }

eponOntTcaEntry  OBJECT-TYPE
	SYNTAX 	EponOntTcaEntry
	ACCESS	not-accessible
	STATUS	mandatory   
	DESCRIPTION
         "An entry in the eponOntTcaTable. 
          Row creation : an entry is auto-created by the system when ONU created in eponOntTable . 
          Row deletion : an entry is auto-deleted by the system when ONU deleted in eponOntTable .        
          ALCATEL NOTE:
             SUPPORT: YES"
	INDEX	{ eponOntIndex }
	::= { eponOntTcaTable 1 }

EponOntTcaEntry ::= SEQUENCE {
	eponOntTcaTemperatureAlmLow            INTEGER,
	eponOntTcaTemperatureAlmHigh           INTEGER, 
	eponOntTcaTemperatureWarnLow           INTEGER,
	eponOntTcaTemperatureWarnHigh          INTEGER, 
	eponOntTcaVoltageAlmLow                INTEGER,
	eponOntTcaVoltageAlmHigh               INTEGER,
	eponOntTcaVoltageWarnLow               INTEGER,
	eponOntTcaVoltageWarnHigh              INTEGER,
        eponOntTcaTxBiasAlmLow                 INTEGER,
	eponOntTcaTxBiasAlmHigh                INTEGER,
	eponOntTcaTxBiasWarnLow                INTEGER,
	eponOntTcaTxBiasWarnHigh               INTEGER, 
	eponOntTcaTxPowerAlmLow                INTEGER,
	eponOntTcaTxPowerAlmHigh               INTEGER,
	eponOntTcaTxPowerWarnLow               INTEGER,
	eponOntTcaTxPowerWarnHigh              INTEGER,
        eponOntTcaRxPowerAlmLow                INTEGER,
	eponOntTcaRxPowerAlmHigh               INTEGER,
	eponOntTcaRxPowerWarnLow               INTEGER,
	eponOntTcaRxPowerWarnHigh              INTEGER   
}


eponOntTcaTemperatureAlmLow  OBJECT-TYPE
	SYNTAX 	INTEGER 
	ACCESS	read-write
	STATUS	mandatory
	DESCRIPTION 
		"this object indicates alarm low threshold for temperature.
		ALCATEL NOTE:
                 ACCESS:     NA       USAGE:    OPT
                 PERSIST:    YES      INSRVMOD:   YES
                 RANGE:     -32768..32768      DEFVALUE:  0
                 UNITS:     1/256 Celsius       SPARSE:     NA
                 DESCR:      NA "

::= { eponOntTcaEntry 1 }

eponOntTcaTemperatureAlmHigh  OBJECT-TYPE
	SYNTAX 	INTEGER 
	ACCESS	read-write
	STATUS	mandatory
	DESCRIPTION 
	"this object indicates alarm hign threshold for temperature.
		ALCATEL NOTE:
                 ACCESS:     NA       USAGE:    OPT
                 PERSIST:    NO      INSRVMOD:   YES
                 RANGE:    -32768..32768      DEFVALUE:  17920
                 UNITS:     1/256 Celsius       SPARSE:     NA
                 DESCR:      NA "
::= { eponOntTcaEntry 2 }

eponOntTcaTemperatureWarnLow  OBJECT-TYPE
	SYNTAX 	INTEGER 
	ACCESS	read-write
	STATUS	mandatory
	DESCRIPTION 
		"this object indicates warn low threshold for temperature.
		ALCATEL NOTE:
                 ACCESS:     NA       USAGE:    OPT
                 PERSIST:    NO      INSRVMOD:   YES
                 RANGE:     -32768..32768      DEFVALUE: 0
                 UNITS:     1/256 Celsius       SPARSE:     NA
                 DESCR:      NA "
::= { eponOntTcaEntry 3 }

eponOntTcaTemperatureWarnHigh  OBJECT-TYPE
	SYNTAX 	INTEGER 
	ACCESS	read-write
	STATUS	mandatory
	DESCRIPTION 
		"this object indicates warn hign threshold for temperature.
		ALCATEL NOTE:
                 ACCESS:     NA       USAGE:    OPT
                 PERSIST:    NO      INSRVMOD:   YES
                 RANGE:    -32768..32768      DEFVALUE: 17920
                 UNITS:     1/256 Celsius        SPARSE:     NA
                 DESCR:      NA "
::= { eponOntTcaEntry 4 }
	
eponOntTcaVoltageAlmLow  OBJECT-TYPE
	SYNTAX 	INTEGER 
	ACCESS	read-write
	STATUS	mandatory
	DESCRIPTION 
	"this object indicates alarm low threshold for Voltage.
		ALCATEL NOTE:
                 ACCESS:     NA       USAGE:    OPT
                 PERSIST:    NO      INSRVMOD:   YES
                 RANGE:    0..65500   DEFVALUE:  31350
                 UNITS:      100 uVolt       SPARSE:     NA
                 DESCR:      NA "
::= { eponOntTcaEntry 5 }

eponOntTcaVoltageAlmHigh  OBJECT-TYPE
	SYNTAX 	INTEGER 
	ACCESS	read-write
	STATUS	mandatory
	DESCRIPTION 
	"this object indicates alarm hign threshold for Voltage.
		ALCATEL NOTE:
                 ACCESS:     NA       USAGE:    OPT
                 PERSIST:    NO      INSRVMOD:   YES
                 RANGE:    0..65500   DEFVALUE:  34650
                 UNITS:      100 uVolt       SPARSE:     NA
                 DESCR:      NA "
::= { eponOntTcaEntry 6 }

eponOntTcaVoltageWarnLow  OBJECT-TYPE
	SYNTAX 	INTEGER 
	ACCESS	read-write
	STATUS	mandatory
	DESCRIPTION 
		"this object indicates warn low threshold for Voltage.
		ALCATEL NOTE:
                 ACCESS:     NA       USAGE:    OPT
                 PERSIST:    NO      INSRVMOD:   YES
                 RANGE:    0..65500   DEFVALUE:  31350
                 UNITS:      100 uVolt      SPARSE:     NA
                 DESCR:      NA "
::= { eponOntTcaEntry 7 }

eponOntTcaVoltageWarnHigh  OBJECT-TYPE
	SYNTAX 	INTEGER 
	ACCESS	read-write
	STATUS	mandatory
	DESCRIPTION 
		"this object indicates warn hign threshold for Voltage.
	ALCATEL NOTE:
                 ACCESS:     NA       USAGE:    OPT
                 PERSIST:    NO      INSRVMOD:   YES
                 RANGE:    0..65500   DEFVALUE:  34650
                 UNITS:     100 uVolt       SPARSE:     NA
                 DESCR:      NA "
::= { eponOntTcaEntry 8 } 

eponOntTcaTxBiasAlmLow  OBJECT-TYPE
	SYNTAX 	INTEGER 
	ACCESS	read-write
	STATUS	mandatory
	DESCRIPTION 
	"this object indicates alarm low threshold for bias.
		ALCATEL NOTE:
                 ACCESS:     NA       USAGE:    OPT
                 PERSIST:    NO      INSRVMOD:   YES
                 RANGE:     0..65500      DEFVALUE:  2500
                 UNITS:      2 uA       SPARSE:     NA
                 DESCR:      NA "
::= { eponOntTcaEntry 9 }

eponOntTcaTxBiasAlmHigh  OBJECT-TYPE
	SYNTAX 	INTEGER 
	ACCESS	read-write
	STATUS	mandatory
	DESCRIPTION 
		"this object indicates alarm hign threshold for bias.
	ALCATEL NOTE:
                 ACCESS:     NA       USAGE:    OPT
                 PERSIST:    NO      INSRVMOD:   YES
                 RANGE:     0..65500         DEFVALUE:  55000
                 UNITS:      2 uA        SPARSE:     NA
                 DESCR:      NA "
::= { eponOntTcaEntry 10 }

eponOntTcaTxBiasWarnLow  OBJECT-TYPE
	SYNTAX 	INTEGER 
	ACCESS	read-write
	STATUS	mandatory
	DESCRIPTION 
		"this object indicates warn low threshold for bias.
		ALCATEL NOTE:
                 ACCESS:     NA       USAGE:    OPT
                 PERSIST:    NO      INSRVMOD:   YES
                 RANGE:     0..65500         DEFVALUE:  2500
                 UNITS:      2 uA        SPARSE:     NA
                 DESCR:      NA "
::= { eponOntTcaEntry 11 }

eponOntTcaTxBiasWarnHigh  OBJECT-TYPE
	SYNTAX 	INTEGER 
	ACCESS	read-write
	STATUS	mandatory
	DESCRIPTION 
	"this object indicates warn hign threshold for bias.
		ALCATEL NOTE:
                 ACCESS:     NA       USAGE:    OPT
                 PERSIST:    NO      INSRVMOD:   YES
                 RANGE:     0..65500    DEFVALUE:  55000
                 UNITS:     2 uA       SPARSE:     NA
                 DESCR:      NA "
::= { eponOntTcaEntry 12 }
 
eponOntTcaTxPowerAlmLow  OBJECT-TYPE
	SYNTAX 	INTEGER 
	ACCESS	read-write
	STATUS	mandatory
	DESCRIPTION 
	"this object indicates alarm low threshold for Tx power.
		ALCATEL NOTE:
                 ACCESS:     NA       USAGE:    OPT
                 PERSIST:    NO      INSRVMOD:   YES
                 RANGE:    0..65535   DEFVALUE:  7943
                 UNITS:     0.1uW      SPARSE:     NA
                 DESCR:      NA "
::= { eponOntTcaEntry 13 }

eponOntTcaTxPowerAlmHigh  OBJECT-TYPE
	SYNTAX 	INTEGER 
	ACCESS	read-write
	STATUS	mandatory
	DESCRIPTION 
		"this object indicates alarm hign threshold for Tx power.
			ALCATEL NOTE:
                 ACCESS:     NA       USAGE:    OPT
                 PERSIST:    NO      INSRVMOD:   YES
                 RANGE:    0..65535   DEFVALUE:  25110
                 UNITS:       0.1uW         SPARSE:     NA
                 DESCR:      NA "
::= { eponOntTcaEntry 14 }

eponOntTcaTxPowerWarnHigh  OBJECT-TYPE
	SYNTAX 	INTEGER 
	ACCESS	read-write
	STATUS	mandatory
	DESCRIPTION 
	"this object indicates warn hign threshold for Tx power.
		ALCATEL NOTE:
                 ACCESS:     NA       USAGE:    OPT
                 PERSIST:    NO      INSRVMOD:   YES
                 RANGE:    0..65535    DEFVALUE: 25110
                 UNITS:      0.1uW       SPARSE:     NA
                 DESCR:      NA "

::= { eponOntTcaEntry 15 }  

eponOntTcaTxPowerWarnLow  OBJECT-TYPE
	SYNTAX 	INTEGER 
	ACCESS	read-write
	STATUS	mandatory
	DESCRIPTION 
		"this object indicates warn low threshold for Tx power.
		ALCATEL NOTE:
                 ACCESS:     NA       USAGE:    OPT
                 PERSIST:    NO      INSRVMOD:   YES
                 RANGE:    0..65535   DEFVALUE:  7943
                 UNITS:      0.1uW       SPARSE:     NA
                 DESCR:      NA "
::= { eponOntTcaEntry 16 }  

eponOntTcaRxPowerAlmLow  OBJECT-TYPE
	SYNTAX 	INTEGER 
	ACCESS	read-write
	STATUS	mandatory
	DESCRIPTION 
		"this object indicates alarm low threshold for Rx power.
			ALCATEL NOTE:
                 ACCESS:     NA       USAGE:    OPT
                 PERSIST:    NO      INSRVMOD:   YES
                 RANGE:    0..65535    DEFVALUE:  40
                 UNITS:      0.1uW        SPARSE:     NA
                 DESCR:      NA "

::= { eponOntTcaEntry 17 }

eponOntTcaRxPowerAlmHigh  OBJECT-TYPE
	SYNTAX 	INTEGER 
	ACCESS	read-write
	STATUS	mandatory
	DESCRIPTION 
		"this object indicates alarm hign threshold for Rx power.
			ALCATEL NOTE:
                 ACCESS:     NA       USAGE:    OPT
                 PERSIST:    NO      INSRVMOD:   YES
                 RANGE:    0..65535    DEFVALUE:  5012
                 UNITS:     0.1uW        SPARSE:     NA
                 DESCR:      NA "
::= { eponOntTcaEntry 18 }

eponOntTcaRxPowerWarnHigh  OBJECT-TYPE
	SYNTAX 	INTEGER 
	ACCESS	read-write
	STATUS	mandatory
	DESCRIPTION 
		"this object indicates warn hign threshold for Rx power.
			ALCATEL NOTE:
                 ACCESS:     NA       USAGE:    OPT
                 PERSIST:    NO      INSRVMOD:   YES
                 RANGE:    0..65535   DEFVALUE:  5012
                 UNITS:      0.1uW        SPARSE:     NA
                 DESCR:      NA "
::= { eponOntTcaEntry 19 }  

eponOntTcaRxPowerWarnLow  OBJECT-TYPE
	SYNTAX 	INTEGER 
	ACCESS	read-write
	STATUS	mandatory
	DESCRIPTION 
		"this object indicates warn low threshold for Rx power.
			ALCATEL NOTE:
                 ACCESS:     NA       USAGE:    OPT
                 PERSIST:    NO      INSRVMOD:   YES
                 RANGE:    0..65535    DEFVALUE:  40
                 UNITS:      0.1uW         SPARSE:     NA
                 DESCR:      NA "

::= { eponOntTcaEntry 20 }  

-- eponOntOltsideOpInfoTable 
-- this table  is used to indicatge the optical module parameter at ONT side.
--
  
    eponOntOltsideOpInfoTable  OBJECT-TYPE
	SYNTAX SEQUENCE OF EponOntOltsideOpInfoEntry
	ACCESS	not-accessible
	STATUS	mandatory  
	DESCRIPTION 
	 "  this table indicates optical module parameter such as  temperature,Voltage, Bias, rx-power and Tx-power per ONT.
	 ALCATEL NOTE:
             SUPPORT: YES   TABLESIZE: DEP"
	::= { eponOntGroup 3 }

eponOntOltsideOpInfoEntry  OBJECT-TYPE
	SYNTAX 	EponOntOltsideOpInfoEntry
	ACCESS	not-accessible
	STATUS	mandatory   
	DESCRIPTION
         "An entry in the eponOntTcaTable. 
          Row creation : an entry is auto-created by the system when ONU created in eponOntTable . 
          Row deletion : an entry is auto-deleted by the system when ONU deleted in eponOntTable .        
          ALCATEL NOTE:
             SUPPORT: YES"
	INDEX	{ eponOntIndex }
	::= { eponOntOltsideOpInfoTable 1 }

EponOntOltsideOpInfoEntry ::= SEQUENCE {		
	eponOntOltsideOpInfoTemperature		               INTEGER,
	eponOntOltsideOpInfoVoltage                         INTEGER,                    
	eponOntOltsideOpInfoTxBias			               INTEGER,
	eponOntOltsideOpInfoTxPower                         INTEGER,     
	eponOntOltsideOpInfoRxPower                         INTEGER     
}

eponOntOltsideOpInfoTemperature  OBJECT-TYPE
	SYNTAX 	INTEGER 
	ACCESS	read-only
	STATUS	mandatory
	DESCRIPTION 
	"this object indicates curent temperature for ONT. FFFF means unkown.
		ALCATEL NOTE:
                 ACCESS:     NA       USAGE:    NA
                 PERSIST:    NO      INSRVMOD: NA
                 RANGE:     -32768..32768       DEFVALUE:  NA
                 UNITS:     1/256 Celsius       SPARSE:     NA
                  "
::= { eponOntOltsideOpInfoEntry  1 }

eponOntOltsideOpInfoVoltage  OBJECT-TYPE
	SYNTAX 	INTEGER 
	ACCESS	read-only
	STATUS	mandatory
	DESCRIPTION 
	"this object indicates curent voltage for ONT.   FFFF means unkown.

		ALCATEL NOTE:
                 ACCESS:     NA       USAGE:    NA
                 PERSIST:    NO      INSRVMOD: NA
                 RANGE:     0..65500       DEFVALUE:  NA
                 UNITS:      100 uV       SPARSE:     NA
                  "
::= { eponOntOltsideOpInfoEntry  2 }
	
eponOntOltsideOpInfoTxBias  OBJECT-TYPE
	SYNTAX 	INTEGER 
	ACCESS	read-only
	STATUS	mandatory
	DESCRIPTION 
		"this object indicates curent Tx bias for ONT.  FFFF means unkown.

		ALCATEL NOTE:
                 ACCESS:     NA       USAGE:    NA
                 PERSIST:    NO      INSRVMOD: NA
                 RANGE:     0..65500       DEFVALUE:  NA
                 UNITS:      2 uA       SPARSE:     NA
                  "
::= { eponOntOltsideOpInfoEntry  3 }	 

eponOntOltsideOpInfoTxPower  OBJECT-TYPE
	SYNTAX 	INTEGER 
	ACCESS	read-only
	STATUS	mandatory
	DESCRIPTION 
	"this object indicates curent TX power for ONT. FFFF means unkown.

		ALCATEL NOTE:
                 ACCESS:     NA       USAGE:    NA
                 PERSIST:    NO      INSRVMOD: NA
                 RANGE:     0..65535       DEFVALUE:  NA
                 UNITS:      0.1uW       SPARSE:     NA
                  "
::= { eponOntOltsideOpInfoEntry  4 }
	
eponOntOltsideOpInfoRxPower  OBJECT-TYPE
	SYNTAX 	INTEGER 
	ACCESS	read-only
	STATUS	mandatory
	DESCRIPTION 
	"this object indicates curent Rx power for ONT.  FFFF means unkown.

		ALCATEL NOTE:
                 ACCESS:     NA       USAGE:    NA
                 PERSIST:    NO      INSRVMOD: NA
                 RANGE:     0..65535       DEFVALUE:  NA
                 UNITS:      0.1uW       SPARSE:     NA
                  "
::= { eponOntOltsideOpInfoEntry  5 }	 

-- *********************************************
-- *********************************************
-- EPON ONT voice info table
--
-- *********************************************
  
eponOntVoiceOpInfoTable  OBJECT-TYPE
	SYNTAX SEQUENCE OF EponOntVoiceOpInfoEntry
	ACCESS	not-accessible
	STATUS	mandatory  
	DESCRIPTION 
	 "  this table indicates voice operation info 
	 ALCATEL NOTE:
             SUPPORT: YES   TABLESIZE: DEP"
	::= { eponOntGroup  4}

eponOntVoiceOpInfoEntry  OBJECT-TYPE
	SYNTAX 	EponOntVoiceOpInfoEntry
	ACCESS	not-accessible
	STATUS	mandatory   
	DESCRIPTION
         "       
          ALCATEL NOTE:
             SUPPORT: YES"
	INDEX	{ eponOntIndex }
	::= { eponOntVoiceOpInfoTable 1 }

EponOntVoiceOpInfoEntry ::= SEQUENCE {		
	eponOntVoiceOpInfoMacaddr		            MacAddress,
	eponOntVoiceOpInfoProtocol                          INTEGER,                    
	eponOntVoiceOpIadSwVersion			    OCTET STRING (SIZE(0..32)),
	eponOntVoiceOpSwTime                                OCTET STRING (SIZE(0..32)),
	eponOntVoiceOpUserCount                             INTEGER     

}

eponOntVoiceOpInfoMacaddr  OBJECT-TYPE
	SYNTAX 	MacAddress 
	ACCESS	read-only
	STATUS	mandatory
	DESCRIPTION 
		"this object indicates the mac addr of IAD.

		ALCATEL NOTE:
                 ACCESS:     NA       USAGE:    NA
                 PERSIST:    NO      INSRVMOD: NA
                 RANGE:      NA       DEFVALUE:  NA
                 UNITS:      NA       SPARSE:     NA
                  "
::= { eponOntVoiceOpInfoEntry  1 }	 

eponOntVoiceOpInfoProtocol  OBJECT-TYPE
	SYNTAX 	INTEGER 
	ACCESS	read-only
	STATUS	mandatory
	DESCRIPTION 
	"this object indicates the supported voice protocol, SIP or H248
	 0 = H.248
	 1 = SIP
         254 = NOTSUPPORT
         255 = UNKNOW

		ALCATEL NOTE:
                 ACCESS:     NA       USAGE:    NA
                 PERSIST:    NO      INSRVMOD: NA
                 RANGE:     0,1,254,255      DEFVALUE:  NA
                 UNITS:      NA      SPARSE:     NA
                  "
::= { eponOntVoiceOpInfoEntry  2 }
	
eponOntVoiceOpIadSwVersion  OBJECT-TYPE
	SYNTAX 	OCTET STRING (SIZE(0..32)) 
	ACCESS	read-only
	STATUS	mandatory
	DESCRIPTION 
	"this object indicates IAD Sw version.

		ALCATEL NOTE:
                 ACCESS:     NA       USAGE:    NA
                 PERSIST:    NO      INSRVMOD: NA
                 RANGE:      NA       DEFVALUE:  NA
                 UNITS:      NA      SPARSE:     NA
                  "
::= { eponOntVoiceOpInfoEntry  3 }

eponOntVoiceOpSwTime  OBJECT-TYPE
	SYNTAX 	OCTET STRING (SIZE(0..32)) 
	ACCESS	read-only
	STATUS	mandatory
	DESCRIPTION 
	"this object indicates IAD Sw version time.

		ALCATEL NOTE:
                 ACCESS:     NA       USAGE:    NA
                 PERSIST:    NO      INSRVMOD: NA
                 RANGE:      NA       DEFVALUE:  NA
                 UNITS:      NA      SPARSE:     NA
                  "
::= { eponOntVoiceOpInfoEntry  4 }

eponOntVoiceOpUserCount  OBJECT-TYPE
	SYNTAX 	INTEGER 
	ACCESS	read-only
	STATUS	mandatory
	DESCRIPTION 
	"this object indicates the number of POTS interface in the IAD.

		ALCATEL NOTE:
                 ACCESS:     NA       USAGE:    NA
                 PERSIST:    NO      INSRVMOD: NA
                 RANGE:      NA       DEFVALUE:  NA
                 UNITS:      NA      SPARSE:     NA
                  "
::= { eponOntVoiceOpInfoEntry  5 }

-- *********************************************
-- *********************************************
--
-- EPON ONT MANAGEMENT TABLE
--
-- This is also an extention table of EPON ONT Table

-- *********************************************

eponOntMngTable  OBJECT-TYPE
	SYNTAX SEQUENCE OF EponOntMngEntry
	ACCESS	not-accessible
	STATUS	mandatory  
	DESCRIPTION 
	 " This table indicates SNMP managment para per ONT.
	 ALCATEL NOTE:
             SUPPORT: YES   TABLESIZE: DEP"
	::= { eponOntGroup 5 }

eponOntMngEntry  OBJECT-TYPE
	SYNTAX 	EponOntMngEntry
	ACCESS	not-accessible
	STATUS	mandatory   
	DESCRIPTION
         "An entry in the eponOntMngTable. 
          Row creation : an entry is auto-created by the system when ONU created in eponOntTable . 
          Row deletion : an entry is auto-deleted by the system when ONU deleted in eponOntTable .        
          ALCATEL NOTE:
             SUPPORT: YES"
	INDEX	{ eponOntIndex }
	::= { eponOntMngTable 1 }

EponOntMngEntry ::= SEQUENCE {
	eponOntMngIpAddr                       IpAddress,
	eponOntMngIpMask                       IpAddress, 
	eponOntMngDefGw                        IpAddress,
	eponOntMngCvlan                        INTEGER,
	eponOntMngSvlan                        INTEGER,
	eponOntMngDot1p                        EponSystemPriority, 
	eponOntMngSnmpVer                      INTEGER,
	eponOntMngTrapHostIpAddr               IpAddress,
	eponOntMngTrapPort                     INTEGER,
	eponOntMngSnmpPort                     INTEGER,
    eponOntMngSecurityName                 OCTET STRING,
	eponOntMngCommRead                     OCTET STRING,
	eponOntMngCommWrite                    OCTET STRING
}

eponOntMngIpAddr  OBJECT-TYPE
	SYNTAX 	IpAddress 
	ACCESS	read-write
	STATUS	mandatory
	DESCRIPTION 
		"this object indicates management IP Addr.
		ALCATEL NOTE:
                 ACCESS:    NA       USAGE:    OPT
                 PERSIST:   YES      INSRVMOD:   YES
                 RANGE:     NA       DEFVALUE:  NA
                 UNITS:     NA       SPARSE:     NA
                 DESCR:     NA "

::= { eponOntMngEntry 1 }

eponOntMngIpMask  OBJECT-TYPE
	SYNTAX 	IpAddress 
	ACCESS	read-write
	STATUS	mandatory
	DESCRIPTION 
		"this object indicates management IP subnet.
		ALCATEL NOTE:
                 ACCESS:    NA       USAGE:    OPT
                 PERSIST:   YES      INSRVMOD:   YES
                 RANGE:     NA       DEFVALUE:  NA
                 UNITS:     NA       SPARSE:     NA
                 DESCR:     NA "

::= { eponOntMngEntry 2 }

eponOntMngDefGw  OBJECT-TYPE
	SYNTAX 	IpAddress 
	ACCESS	read-write
	STATUS	mandatory
	DESCRIPTION 
		"this object indicates management default gateway.
		ALCATEL NOTE:
                 ACCESS:    NA       USAGE:    OPT
                 PERSIST:   YES      INSRVMOD:   YES
                 RANGE:     NA       DEFVALUE:  NA
                 UNITS:     NA       SPARSE:     NA
                 DESCR:     NA "

::= { eponOntMngEntry 3 }

eponOntMngCvlan  OBJECT-TYPE
	SYNTAX 	INTEGER 
	ACCESS	read-write
	STATUS	mandatory
	DESCRIPTION 
		"this object indicates data management CVLAN ID for a specified ONT.
		ALCATEL NOTE:
                 ACCESS:     NA       USAGE:    OPT
                 PERSIST:    NO       INSRVMOD:   YES
                 RANGE:      0..4093  DEFVALUE: 0 
                 UNITS:      NA       SPARSE:     NA
                 DESCR:      NA "
::= { eponOntMngEntry 4 }

eponOntMngSvlan  OBJECT-TYPE
	SYNTAX 	INTEGER 
	ACCESS	read-write
	STATUS	mandatory
	DESCRIPTION 
		"this object indicates data management SVLAN ID for a specified ONT .
		ALCATEL NOTE:
                 ACCESS:     NA       USAGE:    OPT
                 PERSIST:    NO       INSRVMOD:   YES
                 RANGE:      0,2..4093  DEFVALUE: NA
                 UNITS:      NA       SPARSE:     NA
                 DESCR:      NA "
::= { eponOntMngEntry 5 }

eponOntMngDot1p  OBJECT-TYPE
	SYNTAX 	EponSystemPriority 
	ACCESS	read-write
	STATUS	mandatory
	DESCRIPTION 
		"this object indicates data management priority for a specified ONT.
		ALCATEL NOTE:
                 ACCESS:     NA        USAGE:      OPT
                 PERSIST:    NO        INSRVMOD:   YES
                 RANGE:      0..7      DEFVALUE:   5
                 UNITS:      NA        SPARSE:     NA
                 DESCR:      NA "
::= { eponOntMngEntry 6 }

eponOntMngSnmpVer  OBJECT-TYPE
	SYNTAX 	INTEGER 
	ACCESS	read-write
	STATUS	mandatory
	DESCRIPTION 
		"this object indicates ONT SNMP version.
		ALCATEL NOTE:
                 ACCESS:     NA        USAGE:      OPT
                 PERSIST:    NO        INSRVMOD:   YES
                 RANGE:      1..3      DEFVALUE:   2
                 UNITS:      NA        SPARSE:     NA
                 DESCR:      NA "
::= { eponOntMngEntry 7 }

eponOntMngTrapHostIpAddr  OBJECT-TYPE
	SYNTAX 	IpAddress 
	ACCESS	read-write
	STATUS	mandatory
	DESCRIPTION 
		"this object indicates management trap host IP Addr.
		ALCATEL NOTE:
                 ACCESS:    NA       USAGE:    OPT
                 PERSIST:   YES      INSRVMOD:   YES
                 RANGE:     NA       DEFVALUE:  NA
                 UNITS:     NA       SPARSE:     NA
                 DESCR:     NA "

::= { eponOntMngEntry 8 }

eponOntMngTrapPort  OBJECT-TYPE
	SYNTAX 	INTEGER 
	ACCESS	read-write
	STATUS	mandatory
	DESCRIPTION 
		"this object indicates trap port.
		ALCATEL NOTE:
                 ACCESS:     NA        USAGE:      OPT
                 PERSIST:    NO        INSRVMOD:   YES
                 RANGE:      NA        DEFVALUE:   NA
                 UNITS:      NA        SPARSE:     NA
                 DESCR:      NA "
::= { eponOntMngEntry 9 }

eponOntMngSnmpPort  OBJECT-TYPE
	SYNTAX 	INTEGER 
	ACCESS	read-write
	STATUS	mandatory
	DESCRIPTION 
		"this object indicates Snmp port.
		ALCATEL NOTE:
                 ACCESS:     NA        USAGE:      OPT
                 PERSIST:    NO        INSRVMOD:   YES
                 RANGE:      NA        DEFVALUE:   NA
                 UNITS:      NA        SPARSE:     NA
                 DESCR:      NA "
::= { eponOntMngEntry 10 }

eponOntMngSecurityName  OBJECT-TYPE
	SYNTAX 	OCTET STRING 
	ACCESS	read-write
	STATUS	mandatory
	DESCRIPTION 
		"this object indicates Security name.
		ALCATEL NOTE:
                 ACCESS:     NA        USAGE:      OPT
                 PERSIST:    NO        INSRVMOD:   YES
                 RANGE:      NA        DEFVALUE:   NA
                 UNITS:      NA        SPARSE:     NA
                 DESCR:      NA "
::= { eponOntMngEntry 11 }

eponOntMngCommRead  OBJECT-TYPE
	SYNTAX 	OCTET STRING 
	ACCESS	read-write
	STATUS	mandatory
	DESCRIPTION 
		"this object indicates Community string for read.
		ALCATEL NOTE:
                 ACCESS:     NA        USAGE:      OPT
                 PERSIST:    NO        INSRVMOD:   YES
                 RANGE:      NA        DEFVALUE:   NA
                 UNITS:      NA        SPARSE:     NA
                 DESCR:      NA "
::= { eponOntMngEntry 12 }

eponOntMngCommWrite  OBJECT-TYPE
	SYNTAX 	OCTET STRING 
	ACCESS	read-write
	STATUS	mandatory
	DESCRIPTION 
		"this object indicates Community string for write.
		ALCATEL NOTE:
                 ACCESS:     NA        USAGE:      OPT
                 PERSIST:    NO        INSRVMOD:   YES
                 RANGE:      NA        DEFVALUE:   NA
                 UNITS:      NA        SPARSE:     NA
                 DESCR:      NA "
::= { eponOntMngEntry 13 }

-- *********************************************
eponOntMACMappingTable   OBJECT-TYPE
        SYNTAX SEQUENCE OF EponOntMACMappingEntry
        ACCESS  not-accessible
        STATUS  mandatory
        DESCRIPTION
         "  This entry is for search onuId by Onu MAC. 
            For search onuId in NE's provisioned ONT 
            sets according a specified MAC.

         ALCATEL NOTE:
             SUPPORT: YES   TABLESIZE: DEP"
        ::= { eponOntGroup 8 }
eponOntMACMappingEntry  OBJECT-TYPE
        SYNTAX  EponOntMACMappingEntry
        ACCESS  not-accessible
        STATUS  mandatory
        DESCRIPTION
         "An entry in eponOntMACMappingTable.
          For search onuId
.
          ALCATEL NOTE:
             SUPPORT: YES"
INDEX { eponOntMappingMacAddress,
        eponMacMappingIfIndex }
       ::= {eponOntMACMappingTable 1}
EponOntMACMappingEntry  ::= SEQUENCE {
    eponOntMappingMacAddress     MacAddress,
    eponMacMappingIfIndex           INTEGER,
    eponOntMACMappingOntId         INTEGER
}
eponOntMappingMacAddress OBJECT-TYPE
        SYNTAX  MacAddress
        ACCESS  not-accessible
        STATUS  mandatory
        DESCRIPTION
            "This object stores the base MAC address of ONT. It is a 6 octet st
ring
as defined in Bridge-MIB. At least one of eponOntMacAddress and eponOntMacAddre
ss must be configured
when planning ONT.
 ALCATEL NOTE:
                 ACCESS: NA        usage: NA
         persistent: YES   INSRVMOD:NO
         RANGE:NA        DEFVALUE: NA
         UNITS: NA         SPARSE: NA  "
::= {eponOntMACMappingEntry 1}
eponMacMappingIfIndex  OBJECT-TYPE
        SYNTAX  INTEGER  
        ACCESS  not-accessible
        STATUS  mandatory
        DESCRIPTION
            "This object stores the ifIndex of the pon.
 ALCATEL NOTE:   
                 ACCESS: NA        usage: NA
         persistent: YES   INSRVMOD:NO
         RANGE:NA        DEFVALUE: NA
         UNITS: NA         SPARSE: NA  "
::= {eponOntMACMappingEntry 2}
eponOntMACMappingOntId OBJECT-TYPE
      SYNTAX  INTEGER
      ACCESS  read-only
      STATUS mandatory
      DESCRIPTION
        "This object display the OntId of the ONT.
 ALCATEL NOTE:  
                 ACCESS: NA        usage: NA
         persistent: YES   INSRVMOD:NO
         RANGE:NA        DEFVALUE: NA
         UNITS: NA         SPARSE: NA  " 
::= {eponOntMACMappingEntry 3}
-- *********************************************
eponOntSNMappingTable   OBJECT-TYPE
        SYNTAX SEQUENCE OF EponOntSNMappingEntry
        ACCESS  not-accessible
        STATUS  mandatory
        DESCRIPTION
         "  This entry is for search onuId by Onu SN.
            For search onuId in NE's provisioned ONT 
            sets according a specified serial number.

         ALCATEL NOTE:
             SUPPORT: YES   TABLESIZE: DEP"
        ::= { eponOntGroup 9 }
eponOntSNMappingEntry  OBJECT-TYPE
        SYNTAX  EponOntSNMappingEntry
        ACCESS  not-accessible
        STATUS  mandatory
        DESCRIPTION
         "An entry in eponOntSNMappingTable.
          For search onuId
.
          ALCATEL NOTE:
             SUPPORT: YES"
INDEX { eponOntSN,
        eponSnMappingIfIndex }
       ::= {eponOntSNMappingTable 1}
EponOntSNMappingEntry  ::= SEQUENCE {
    eponOntSN     OCTET STRING (SIZE(24)),
    eponSnMappingIfIndex           INTEGER,
    eponOntSNMappingOntId               INTEGER
}
eponOntSN OBJECT-TYPE
        SYNTAX  OCTET STRING (SIZE(24))
        ACCESS  not-accessible
        STATUS  mandatory
        DESCRIPTION
            "This object stores the logic Authentication Id (SN)  of ONT. It is a 24 octet string
 ALCATEL NOTE:
                 ACCESS: NA        usage: NA
         persistent: YES   INSRVMOD:NO
         RANGE:NA        DEFVALUE: NA
         UNITS: NA         SPARSE: NA  "
::= {eponOntSNMappingEntry 1}
eponSnMappingIfIndex  OBJECT-TYPE
        SYNTAX  INTEGER
        ACCESS  not-accessible
        STATUS  mandatory
        DESCRIPTION
            "This object stores the ifIndex of the pon.
 ALCATEL NOTE:
                 ACCESS: NA        usage: NA
         persistent: YES   INSRVMOD:NO
         RANGE:NA        DEFVALUE: NA
         UNITS: NA         SPARSE: NA  "
::= {eponOntSNMappingEntry 2}
eponOntSNMappingOntId OBJECT-TYPE
      SYNTAX  INTEGER
      ACCESS  read-only
      STATUS mandatory
      DESCRIPTION
        "This object display the OntId of the ONT.
 ALCATEL NOTE:
                 ACCESS: NA        usage: NA
         persistent: YES   INSRVMOD:NO
         RANGE:NA        DEFVALUE: NA
         UNITS: NA         SPARSE: NA  "
::= {eponOntSNMappingEntry 3}

-- *********************************************
--
-- EPON ONT RMS TABLE
--
-- This table contains a row for configure an ONT RMS.
--*********************************************

eponOntRmsTable   OBJECT-TYPE
    SYNTAX SEQUENCE OF EponOntRmsEntry 
    ACCESS  not-accessible
    STATUS  mandatory
    DESCRIPTION
     "  this table contains a row for configure an ONT RMS.
     ALCATEL NOTE:
         SUPPORT: YES   TABLESIZE: DEP"
    ::= { eponOntGroup 10 }

eponOntRmsEntry OBJECT-TYPE
    SYNTAX  EponOntRmsEntry
    ACCESS  not-accessible
    STATUS  mandatory
    DESCRIPTION
     "An entry in the eponOntRmsTable.
      ALCATEL NOTE:
         SUPPORT: YES"
    INDEX   { eponOntIndex }
    ::= { eponOntRmsTable 1 }

EponOntRmsEntry ::= SEQUENCE {
    eponOntRmsIpMode                  INTEGER,
    eponOntRmsIpAddr                  IpAddress,
    eponOntRmsSubnetNetMask           IpAddress,
    eponOntRmsDefGw                   IpAddress,
    eponOntRmsPppoeMode               INTEGER,
    eponOntRmsPppoeUsername           DisplayString,
    eponOntRmsPppoePassword           DisplayString,
    eponOntRmsTaggedMode              INTEGER,
    eponOntRmsCvlan                   INTEGER,
    eponOntRmsSvlan                   INTEGER,
    eponOntRmsDot1P                   EponSystemPriority,
    eponOntRmsURL                     OCTET STRING (SIZE (0..256)),
    eponOntRmsRowStatus               RowStatus
}

eponOntRmsIpMode  OBJECT-TYPE 
    SYNTAX  INTEGER
    ACCESS  read-write
    STATUS  mandatory
    DESCRIPTION
    "This object is the voice IP config mode .
                0 = static IP 
                1 = DHCP 
                2 = PPPoE/PPPOE+
                
    ALCATEL NOTE:
        ACCESS: NA        usage: NA
        persistent: YES   INSRVMOD:YES
        RANGE:0...2       DEFVALUE: 1  
        UNITS: NA         SPARSE: NA  "
::= { eponOntRmsEntry  1}

eponOntRmsIpAddr  OBJECT-TYPE
    SYNTAX  IpAddress
    ACCESS  read-write
    STATUS  mandatory
    DESCRIPTION 
    " The manually provisioned IP Address of the
        Network Media Gateway. NOTE: If eponOntRmsIpMode
        is not static IP, this parameter has no meaning, and take the
        value zero.
 
    ALCATEL NOTE:
        ACCESS: NA        usage: NA
        persistent: YES   INSRVMOD:YES
        RANGE:NA       DEFVALUE: NA  
        UNITS: NA         SPARSE: NA "
::= { eponOntRmsEntry  2 }


eponOntRmsSubnetNetMask OBJECT-TYPE
    SYNTAX  IpAddress
    ACCESS  read-write
    STATUS  mandatory
    DESCRIPTION 
    " The manually provisioned subnet mask of the
        Network Media Gateway. NOTE: If eponOntRmsIpMode
        is not static IP, this parameter has no meaning, and take the
        value zero.
 
    ALCATEL NOTE:
        ACCESS: NA        usage: NA
        persistent: YES   INSRVMOD:YES
        RANGE:NA          DEFVALUE: NA  
        UNITS: NA         SPARSE: NA "
::= { eponOntRmsEntry  3 }

eponOntRmsDefGw OBJECT-TYPE
    SYNTAX  IpAddress
    ACCESS  read-write
    STATUS  mandatory
    DESCRIPTION 
    " The manually provisioned def GW of the
        Network Media Gateway. NOTE: If eponOntRmsIpMode
        is not static IP, this parameter has no meaning, and take the
        value zero.
 
    ALCATEL NOTE:
        ACCESS: NA        usage: NA
        persistent: YES   INSRVMOD:YES
        RANGE:NA          DEFVALUE: NA  
        UNITS: NA         SPARSE: NA "
::= { eponOntRmsEntry  4 }

eponOntRmsPppoeMode  OBJECT-TYPE 
    SYNTAX  INTEGER
    ACCESS  read-write
    STATUS  mandatory
    DESCRIPTION
    "This object is the voice IP config mode .
                0 = AUTO 
                1 = CHAP 
                2 = PAP
                
                Default = 0 = AUTO
    ALCATEL NOTE:
        ACCESS: NA        usage: NA
        persistent: YES   INSRVMOD:YES
        RANGE:0...2       DEFVALUE: 0  
        UNITS: NA         SPARSE: NA  "
::= { eponOntRmsEntry  5}

eponOntRmsPppoeUsername  OBJECT-TYPE
    SYNTAX  DisplayString (SIZE(0..32))
    ACCESS  read-write
    STATUS  mandatory
    DESCRIPTION 
    "This is a textual string that contains the Username
        required for authentication with Pppoe.

        Default - null string. 
    ALCATEL NOTE:
        ACCESS: NA        usage: NA
        persistent: YES   INSRVMOD:YES
        RANGE:NA          DEFVALUE: NULL  
        UNITS: NA         SPARSE: NA   "
::= { eponOntRmsEntry  6 }


eponOntRmsPppoePassword  OBJECT-TYPE
    SYNTAX  DisplayString (SIZE(0..32))
    ACCESS  read-write
    STATUS  mandatory
    DESCRIPTION 
    "This is a textual string that contains the Password
        required for authentication with the Pppoe.

        Default - null string. 

    ALCATEL NOTE:
        ACCESS: NA        usage: NA
        persistent: YES   INSRVMOD:YES
        RANGE:NA          DEFVALUE: NULL  
        UNITS: NA         SPARSE: NA    "
::= { eponOntRmsEntry  7 }

eponOntRmsTaggedMode  OBJECT-TYPE 
    SYNTAX  INTEGER
    ACCESS  read-write
    STATUS  mandatory
    DESCRIPTION
    "This object is the voice IP config mode .
                0 = Transparent 
                1 = Tag 
                2 = Vlan stacking
                
                Default = 1 = Tag
    ALCATEL NOTE:
        ACCESS: NA        usage: NA
        persistent: YES   INSRVMOD:YES
        RANGE:0...2       DEFVALUE: 1  
        UNITS: NA         SPARSE: NA  "
::= { eponOntRmsEntry  8 }

eponOntRmsCvlan OBJECT-TYPE 
    SYNTAX  INTEGER
    ACCESS  read-write
    STATUS  mandatory
    DESCRIPTION
    "This object is used to reference the C-VLAN ID with
        which this service is associated. 

        No default since value must be supplied by manager.
    ALCATEL NOTE:
        ACCESS: NA        usage: NA
        persistent: YES   INSRVMOD:YES
        RANGE: 2...4090   DEFVALUE:NA 	  
        UNITS: NA         SPARSE: NA  "
::= { eponOntRmsEntry  9 }

eponOntRmsSvlan OBJECT-TYPE 
    SYNTAX  INTEGER
    ACCESS  read-write
    STATUS  mandatory
    DESCRIPTION
    "This object is used to reference the S-VLAN ID 
        with which this service is associated. 

        Range is 0,2 - 4090.

        No default since value must be supplied by manager.
        If tag mode is not stack, this parameter should take
        the value zero

    ALCATEL NOTE:
        ACCESS: NA        usage: NA
        persistent: YES   INSRVMOD:YES
        RANGE: 0,2...4090   DEFVALUE: 0 "
::= { eponOntRmsEntry  10 }

eponOntRmsDot1P  OBJECT-TYPE
    SYNTAX  EponSystemPriority
    ACCESS  read-write
    STATUS  mandatory
    DESCRIPTION 
    " Indicates the default pbit this service is associated.

    ALCATEL NOTE:
        ACCESS: NA        usage:NA
        persistent: YES   INSRVMOD:NA      
        RANGE:0..7        DEFVALUE: 7        
        UNITS: NA         SPARSE: NA  "
::= { eponOntRmsEntry 11 } 

eponOntRmsURL  OBJECT-TYPE 
    SYNTAX  OCTET STRING (SIZE (0..256))
    ACCESS  read-write
    STATUS  mandatory
    DESCRIPTION
    "
    ALCATEL NOTE:
        ACCESS: NA        usage: NA
        persistent: YES   INSRVMOD:YES
        RANGE:NA       DEFVALUE: NA  
        UNITS: NA         SPARSE: NA  "
::= { eponOntRmsEntry  12 }

eponOntRmsRowStatus OBJECT-TYPE 
    SYNTAX  RowStatus
    ACCESS  read-write
    STATUS  mandatory
    DESCRIPTION
    "This object is used to create a new row or delete an row.
        ALCATEL NOTE:
        ACCESS: NA        usage: MAND
        persistent: YES   INSRVMOD:YES
        RANGE:1,4,6       DEFVALUE: NA  
        UNITS: NA         SPARSE: NA  "
::= { eponOntRmsEntry  13 }

-- *********************************************
--
-- EPON LOGICAL LINK TABLE
--
-- This table contains a row for each provisioned Logical Link on an ONT
-- Rows are created by operator via Create-and-go. Note that the base logical link
--will be created by sytem automatically when planning ONT. 
--*********************************************

eponLogicalLinkTable  OBJECT-TYPE
	SYNTAX SEQUENCE OF EponLogicalLinkEntry
	ACCESS	not-accessible
	STATUS	mandatory  
	DESCRIPTION 
	 "  this table indicates logical link table.
	 ALCATEL NOTE:
             SUPPORT: YES   TABLESIZE: DEP"
	::= { eponLinkGroup 1 }


eponLogicalLinkEntry  OBJECT-TYPE
	SYNTAX 	EponLogicalLinkEntry
	ACCESS	not-accessible
	STATUS	mandatory   
	DESCRIPTION
         "An entry in the eponLogicalLinkTable. 
          Row creation : an entry is created  when operator configure logical link. 
          Row deletion : an entry is deleted  when operator delete logical link.  
          ALCATEL NOTE:
             SUPPORT: YES"
	INDEX	{ eponOntIndex,
	          eponLogicalLinkId}
	::= { eponLogicalLinkTable 1 }

EponLogicalLinkEntry  ::= SEQUENCE { 
    eponLogicalLinkId                   INTEGER,   
    eponLogcalLinkIfindex               INTEGER,
    eponLogicalLinkRowStatus		RowStatus,
    eponLogicalLinkONTUPQueueNum        INTEGER, 
    eponLogicalLinkONTUPQueueProfileId  AsamProfilePointer,
    eponLogicalLinkAdminState           PonAdminState,
    eponLogicalLinkOperState            PonOperState,
    eponLogicalLinkChurningAdmin        INTEGER,  
    eponLogicalLinkChurningTimer        INTEGER, 
    eponLogicalLinkKeyExTimer           INTEGER,
    eponLogicalLinkLoopbackAdmin        INTEGER,
    eponLogicalLinkDBAPollingLevel      INTEGER,
    eponLogicalLinkRateLimitProfileId               INTEGER,
    eponLogicalLinkDisablePortAsPkgOverload         Boolean,
    eponLogicalLinkGroupId               INTEGER,
    eponLogicalLinkAssignedSerialNum               INTEGER
}


eponLogicalLinkId OBJECT-TYPE
	SYNTAX	INTEGER
	ACCESS  read-only
	STATUS	mandatory
	DESCRIPTION
		" Each row is also indexed by a number of the logical link.
                Range 1 for EPON, range 1-8 for DPOE. 
			ALCATEL NOTE:
                 ACCESS:     NA       USAGE:      NA
                 PERSIST:    YES      INSRVMOD:   NO
                 RANGE:      NA       DEFVALUE:   NA
                 UNITS:      NA       SPARSE:     NA
                "

::= { eponLogicalLinkEntry  1}

eponLogcalLinkIfindex OBJECT-TYPE
	SYNTAX	INTEGER
	ACCESS  read-only
	STATUS	mandatory
	DESCRIPTION
		"Indicates the ifindex of Logical Link. 
			ALCATEL NOTE:
                 ACCESS:     NA       USAGE:      NA
                 PERSIST:    NO      INSRVMOD:   NO
                 RANGE:      NA       DEFVALUE:   NA
                 UNITS:      NA       SPARSE:     NA
                "

::= { eponLogicalLinkEntry  2}

eponLogicalLinkRowStatus  OBJECT-TYPE
	SYNTAX 	RowStatus
	ACCESS	read-write
	STATUS	mandatory
	DESCRIPTION 
		"This object is used to create row or delete row in  eponLogicalLinkTable.
		 ALCATEL NOTE:
		 ACCESS: NA        usage: MAND
         persistent: YES   INSRVMOD:YES
         RANGE:1,4,6       DEFVALUE: NA  
         UNITS: NA         SPARSE: NA  "

::= { eponLogicalLinkEntry  3 }



   
eponLogicalLinkONTUPQueueNum OBJECT-TYPE
	SYNTAX 	INTEGER
	ACCESS	read-only
	STATUS	mandatory
	DESCRIPTION 
		" this objcet indicates the supported queue number for logical link ID. 
		currently, 4 queues for one LLID.
		    ALCATEL NOTE:
                 ACCESS:     NA       USAGE:    OPT
                 PERSIST:    YES      INSRVMOD: NA
                 RANGE:     NA     DEFVALUE:  NA
                 UNITS:      NA       SPARSE:     NA
                  "                 

	::= { eponLogicalLinkEntry 7}

eponLogicalLinkONTUPQueueProfileId OBJECT-TYPE
	SYNTAX	AsamProfilePointer
	ACCESS read-write
	STATUS	mandatory
	DESCRIPTION
		" The value of this object identifies queue profile for this logical link.
		  this value is the row eponQueueProfileTable .
		   ALCATEL NOTE:
                 ACCESS:     NA       USAGE:    OPT
                 PERSIST:    YES      INSRVMOD: YES
                 RANGE:     NA       DEFVALUE:  1
                 UNITS:      NA       SPARSE:     NA
                  "       
::= { eponLogicalLinkEntry  8}


eponLogicalLinkAdminState  OBJECT-TYPE
	SYNTAX 	PonAdminState
	ACCESS	read-write
	STATUS	mandatory
	DESCRIPTION 
		"This attribute used to enable or disable Admin State for the logical Link.  
		  ALCATEL NOTE:
                 ACCESS:     NA       USAGE:    OPT
                 PERSIST:    YES      INSRVMOD: YES
                 RANGE:     NA       DEFVALUE:  1
                 UNITS:      NA       SPARSE:     NA
                  Note: NOT SUPPORTED in R4230 release, replaced by entry in ifMIB"   
	::= { eponLogicalLinkEntry 9 }

eponLogicalLinkOperState  OBJECT-TYPE
	SYNTAX 	PonOperState
	ACCESS	read-only
	STATUS	mandatory
	DESCRIPTION 
		"Indicates operational state of the
		  Logical Link.
         ALCATEL NOTE:
                 ACCESS:     NA       USAGE:    NA
                 PERSIST:    NA      INSRVMOD: NA
                 RANGE:     NA       DEFVALUE:  NA
                 UNITS:      NA       SPARSE:     NA
                  Note: NOT SUPPORTED in R4230 release, replaced by entry in ifMIB" 
	::= { eponLogicalLinkEntry 10 }    
	
eponLogicalLinkChurningAdmin  OBJECT-TYPE
	SYNTAX 	INTEGER
	ACCESS	read-write
	STATUS	mandatory
	DESCRIPTION 
		"Enable/Disable churning encryption.  
	enable(1)
	disable	(2)
		ALCATEL NOTE:
                 ACCESS:     NA       USAGE:   OPT
                 PERSIST:    YES     INSRVMOD: YES
                 RANGE:     1..2      DEFVALUE:  2
                 UNITS:      NA       SPARSE:     NA
                  " 
	::= { eponLogicalLinkEntry  11 }     

eponLogicalLinkChurningTimer  OBJECT-TYPE
	SYNTAX 	INTEGER(0..65535)
	ACCESS	read-write
	STATUS	mandatory
	DESCRIPTION 
		" this object is valid when eponLogicalLinkChurningAdmin is enabale. it is Used to set key churning timer for this ONT.  
		 Generally, eponLogicalLinkChurningTimer should 
		 be less than eponLogicalLinkKeyExTimer.
		  ALCATEL NOTE:
                 ACCESS:     NA       USAGE:      OPT
                 PERSIST:    YES      INSRVMOD:   YES
                 RANGE:      NA       DEFVALUE:   3
                 UNITS:      Sec       SPARSE:     NA
                	 "
::= { eponLogicalLinkEntry  12 }

eponLogicalLinkKeyExTimer  OBJECT-TYPE
	SYNTAX 	INTEGER(0..65535)
	ACCESS	read-write
	STATUS	mandatory
	DESCRIPTION 
		" this object is valid when eponLogicalLinkChurningAdmin is enabale. it is Used to set key exchanging timer for this ONT.  
		 Generally, eponLogicalLinkChurningTimer should 
		 be less than eponLogicalLinkKeyExTimer.
		  ALCATEL NOTE:
                 ACCESS:     NA       USAGE:      OPT
                 PERSIST:    YES      INSRVMOD:   YES
                 RANGE:      NA       DEFVALUE:   10
                 UNITS:      Sec       SPARSE:     NA
                	 "
::= { eponLogicalLinkEntry  13 }

eponLogicalLinkLoopbackAdmin  OBJECT-TYPE
	SYNTAX 	INTEGER
	ACCESS	write-only
	STATUS	mandatory
	DESCRIPTION 
		"Enable/Disable Loopback function .
		enable(1)
		disable(2)
		ALCATEL NOTE:
                 ACCESS:     NA       USAGE:      OPT
                 PERSIST:    YES      INSRVMOD:   YES
                 RANGE:      NA       DEFVALUE:   2
                 UNITS:      NA      SPARSE:     NA
                	 "

	::= { eponLogicalLinkEntry  14 }     


  
eponLogicalLinkDBAPollingLevel  OBJECT-TYPE
	SYNTAX 	INTEGER
	ACCESS	read-write
	STATUS	mandatory
	DESCRIPTION 
		" Specify  DBA polling level for logical link.
		  Range: 0..7		  
		  ALCATEL NOTE:
                 ACCESS:     NA       USAGE:      OPT
                 PERSIST:    YES      INSRVMOD:   YES
                 RANGE:     0..7      DEFVALUE:   2
                 UNITS:      NA       SPARSE:     NA
                 DESCR:      NA
 "
::= { eponLogicalLinkEntry  16 }

eponLogicalLinkRateLimitProfileId OBJECT-TYPE
        SYNTAX  INTEGER
        ACCESS  read-write
        STATUS  mandatory
        DESCRIPTION
                "Indicate the Protocol Rate Limit profile, refer to qosRateLimitProfileTable.
                 0 means not associate any profile.
                 1 means associate default profile.
                 default value is 1.
                ALCATEL NOTE:
                 ACCESS: YES       usage: OPT
                 persistent: YES   INSRVMOD:YES
                 RANGE:0..250      DEFVALUE: 1
                 UNITS: NA         SPARSE: NA  "
        DEFVAL { 1 }
::= { eponLogicalLinkEntry 17}

eponLogicalLinkDisablePortAsPkgOverload  OBJECT-TYPE
        SYNTAX  Boolean
        ACCESS  read-write
        STATUS  mandatory
        DESCRIPTION
                "Indicates whether disable LLID port when receive protocol packages number exceed the thershold value.
                 0 means no action when overload .
                 1 measn close LLID port when overload.
                Defaultly, NOT to close LLID port when protocol packages overload.
                 ALCATEL NOTE:
                 ACCESS: YES       usage: OPT
                 persistent: YES   INSRVMOD:NA
                 RANGE:0..1        DEFVALUE: 0
                 UNITS: NA         SPARSE: NA "
      DEFVAL { 0 }
::= { eponLogicalLinkEntry 18 }

eponLogicalLinkGroupId  OBJECT-TYPE
	SYNTAX 	INTEGER
	ACCESS	read-only
	STATUS	mandatory
	DESCRIPTION 
		"Indicates LLIDGroupId the
		  Logical Link belongs to.
         ALCATEL NOTE:
                 ACCESS:     NA       USAGE:    NA
                 PERSIST:    NO      INSRVMOD: NA
                 RANGE:     1..2       DEFVALUE:  NA
                 UNITS:      NA       SPARSE:     NA
                  Note: NA" 
	::= { eponLogicalLinkEntry 19 } 

eponLogicalLinkAssignedSerialNum  OBJECT-TYPE 
	SYNTAX INTEGER
	ACCESS read-only
	STATUS mandatory
	DESCRIPTION
	    	"This object indicates the assigned serial number for this link.
	    	ALCATEL NOTE:
                 ACCESS:     NA       USAGE:      NA
                 PERSIST:    NO       INSRVMOD:   NA
                 RANGE:      NA       DEFVALUE: NA           
                 UNITS:      NA      SPARSE:     NA
                 DESCR:      NA"

::= {eponLogicalLinkEntry 20} 

-- *********************************************
--
-- EPON LAN ETHERNET PORT TABLE
--
-- This table contains a row for each provisioned Ethernet port on an ONT
-- Rows are created  by operator via Create-and-go. 
--   
--
-- *********************************************

eponLanEtherPortTable  OBJECT-TYPE
	SYNTAX SEQUENCE OF EponLanEtherPortEntry
	ACCESS	not-accessible
	STATUS	mandatory 
	DESCRIPTION 
	 "  this table indicates Ethernet port interface at ONT.
	 ALCATEL NOTE:
             SUPPORT: YES   TABLESIZE: DEP"
	::= { eponLanGroup 1 }


eponLanEtherPortEntry  OBJECT-TYPE
	SYNTAX 	EponLanEtherPortEntry
	ACCESS	not-accessible
	STATUS	mandatory      
	DESCRIPTION
         "An entry in the eponLanEtherPortTable. 
          Row creation : an entry is created when creating ethernet port. 
          Row deletion : an entry is deleted when deleteing ethernet port.
          ALCATEL NOTE:
             SUPPORT: YES"
	INDEX	{eponOntIndex,
	         eponLanEtherPortId}
	::= { eponLanEtherPortTable 1 }

EponLanEtherPortEntry ::= SEQUENCE {
	eponLanEtherPortId                      INTEGER, 
	eponLanEtherPortIfindex                 INTEGER,
	eponLanEtherPortRowStatus	        RowStatus,
	eponLanEtherPortAutoDetectAdmin	        INTEGER, 
	eponLanEtherPortReAutoDetect            INTEGER, 
	eponLanEtherPortAutoDetectOper          INTEGER,
	eponLanEtherPortAutoNegAbility          INTEGER,
	eponLanEtherPortAdminState	        PonAdminState,
	eponLanEtherPortOperState	        PonOperState,
	eponLanEtherPortVlanMode	        INTEGER,
        eponLanEtherPortDefVlan		        INTEGER,
        eponLanEtherPortDefDot1p                EponSystemPriority,
        eponLanEtherPortPauseAdmin              INTEGER,
	eponLanEtherPortPolicyUpAdmin	        INTEGER,
        eponLanEtherPortPolicyUpCIR             INTEGER,
	eponLanEtherPortPolicyUpBucket          INTEGER,
	eponLanEtherPortPolicyUpExBrSize        INTEGER,
	eponLanEtherPortPolicyDnAdmin           INTEGER,
        eponLanEtherPortPolicyDnCIR             INTEGER,
        eponLanEtherPortPolicyDnPIR             INTEGER,
	eponLanEtherPortMulticastCfg            INTEGER,
	eponLanEtherPortLearntMacNum            INTEGER,
	eponLanEtherPortMaxGroup                INTEGER,
	eponLanEtherPortPmCollectInd	        INTEGER,
	eponLanEtherPortLpbackAdmin	        INTEGER,
	eponLanEtherPortMaxMcastBw	        INTEGER,
	eponLanEtherPortmode                    INTEGER,
        eponLanEtherPortLoopShutoff             INTEGER,
        eponLanEtherPortAutoNegAdvertisedTechnologyAbility  INTEGER,
        eponLanEtherPortAutoNegRst              INTEGER
}

	
eponLanEtherPortId  OBJECT-TYPE
	SYNTAX 	INTEGER (0..4294967295)
	ACCESS	read-only
	STATUS	mandatory
	DESCRIPTION 
		"Each row is also indexed by a number of the Ethernet UNI port number. 
		 the higher 16 bits means slotID, the lower 16 bits means portID.
		 
		ALCATEL NOTE:
                 ACCESS:     NA       USAGE:      NA
                 PERSIST:    YES      INSRVMOD:   NO
                 RANGE:      NA       DEFVALUE:   NA
                 UNITS:      NA       SPARSE:     NA
                "
	::= { eponLanEtherPortEntry 1 }

eponLanEtherPortIfindex  OBJECT-TYPE
	SYNTAX 	INTEGER
	ACCESS	read-only
	STATUS	mandatory
	DESCRIPTION 
		"Ifindex of the UNI port 
		ALCATEL NOTE:
                 ACCESS:     NA       USAGE:      NA
                 PERSIST:    NA      INSRVMOD:   NA
                 RANGE:      NA       DEFVALUE:   NA
                 UNITS:      NA       SPARSE:     NA
                "
	::= { eponLanEtherPortEntry 2 }

eponLanEtherPortRowStatus  OBJECT-TYPE
	SYNTAX 	RowStatus
	ACCESS	read-write
	STATUS	mandatory
	DESCRIPTION 
		"This object is used to create a new row or delete an
	 ALCATEL NOTE:
		 ACCESS: NA        usage: MAND
         persistent: YES   INSRVMOD:YES
         RANGE:1,4,6       DEFVALUE: NA  
         UNITS: NA         SPARSE: NA  "
	::= { eponLanEtherPortEntry 3 }

eponLanEtherPortAutoDetectAdmin  OBJECT-TYPE
	SYNTAX 	INTEGER
	ACCESS	read-write
	STATUS	mandatory
	DESCRIPTION 
		" Used to enable or disable auto negotiation.
		 enable (1)
		 disable(2)
		 		
		 ALCATEL NOTE:
		 ACCESS: NA        usage:OPT
         persistent: YES   INSRVMOD:YES
         RANGE:1..2      DEFVALUE: 1
         UNITS: NA         SPARSE: NA  "

	::= { eponLanEtherPortEntry 4 }   
	
eponLanEtherPortReAutoDetect  OBJECT-TYPE
SYNTAX 	INTEGER
ACCESS	write-only
STATUS	mandatory
DESCRIPTION 
	"this object is valid when eponLanEtherPortAutoDetectAdmin equal to enable.
	Used to restart auto negotiation
		 1 = restart
		ALCATEL NOTE:
		 ACCESS: NA        usage:OPT
         persistent: YES   INSRVMOD:YES
         RANGE:1           DEFVALUE: NA
         UNITS: NA         SPARSE: NA  "
	::= { eponLanEtherPortEntry 5 }   
	
	
eponLanEtherPortAutoDetectOper  OBJECT-TYPE
	SYNTAX 	INTEGER
	ACCESS	read-only
	STATUS	mandatory
	DESCRIPTION 
		" Indicates the operational state of
		the auto negotiation
		enable (1)
		disable(2)
		ALCATEL NOTE:
		 ACCESS: NA        usage:NA
		 persistent: NA   INSRVMOD:NA       
		 RANGE:1..2      DEFVALUE: NA
         UNITS: NA         SPARSE: NA  "
	::= { eponLanEtherPortEntry 6 }
	
eponLanEtherPortAutoNegAbility  OBJECT-TYPE
	SYNTAX 	INTEGER
	ACCESS	read-only
	STATUS	mandatory
	DESCRIPTION 
		" Indicates the ability of the auto negotiation, each number as follows have to be interpreted as bit position in the bitmap. 
       
        bit0=Global
        bit1=Other
        bit2=Unkown
        bit4=10T
        bit5=10TFD
        bit6=100T4
        bit7=100TX
        bit8=100TXFD
        bit9=100T2
        bit10=100T2FD
        bit11=1000X
        bit12=1000XFD
        bit13=1000T
        bit14=1000TFD
        bit15=FdxPause
        bit16=FdxAPause
        bit17=FdxSPause
        bit18=FdxBPause
        bit19=RemFault1
        bit20=RemFault2
        bit21=IsoEthernet
	ALCATEL NOTE:
		 ACCESS: NA        usage:NA
		 persistent: NA   INSRVMOD:NA       
		 RANGE:NA       DEFVALUE: NA
         UNITS: NA         SPARSE: NA  "
	::= { eponLanEtherPortEntry 7}
	
eponLanEtherPortAdminState  OBJECT-TYPE
	SYNTAX 	PonAdminState
	ACCESS	read-write
	STATUS	mandatory
	DESCRIPTION 
		"Enable or disable port admin state, NOT SUPPORTED in R4230 release, replaced by entry in ifMIB		 
		 ALCATEL NOTE:
		 ACCESS: NA        usage:OPT
		 persistent: YES    INSRVMOD:YES      
		 RANGE:1..2        DEFVALUE: 1         
		 UNITS: NA         SPARSE: NA  "
	::= { eponLanEtherPortEntry 8 }

eponLanEtherPortOperState  OBJECT-TYPE
	SYNTAX 	PonOperState
	ACCESS	read-only
	STATUS	mandatory
	DESCRIPTION 
		"Indicates operational state of the ethernet port, NOT SUPPORTED in R4230 release, replaced by entry in ifMIB.
    ALCATEL NOTE:
		 ACCESS: NA        usage:NA
		 persistent: NA    INSRVMOD:NA       
		 RANGE:1..2        DEFVALUE: NA         
		 UNITS: NA         SPARSE: NA  "
	::= { eponLanEtherPortEntry 9 }


eponLanEtherPortVlanMode  OBJECT-TYPE
	SYNTAX 	INTEGER
	ACCESS	read-write
	STATUS	mandatory
	DESCRIPTION 
		" This is used to specify  vlan mode for ethernet port.
		
		0 = VLAN mode transparent
		1 = VLAN mode tag
		2 = Vlan mode translate
3 = Vlan trunk
		4 = Vlan aggregation
		 ALCATEL NOTE:
		 ACCESS: NA        usage:OPT
		persistent: YES    INSRVMOD:NA       
		 RANGE:0..4        DEFVALUE: 0         
		 UNITS: NA         SPARSE: NA
		 "

	::= { eponLanEtherPortEntry 10 }
	
eponLanEtherPortDefVlan  OBJECT-TYPE
	SYNTAX 	INTEGER
	ACCESS	read-write
	STATUS	mandatory
	DESCRIPTION 
		" This is used for untagged packet in case of  eponLanEtherPortVlanMode=vlan mode tag or
		eponLanEtherPortVlanMode=Vlan mode translate
		 range is 1 - 4093,4097 

		 ALCATEL NOTE:
		 ACCESS: NA        usage:OPT
		persistent: YES    INSRVMOD:NA      
		 RANGE:1..4093,4097      DEFVALUE:4097        
		 UNITS: NA         SPARSE: NA  "

	::= { eponLanEtherPortEntry 11 } 
	
eponLanEtherPortDefDot1p  OBJECT-TYPE
	SYNTAX 	EponSystemPriority
	ACCESS	read-write
	STATUS	mandatory
	DESCRIPTION 
		" Indicates the default pbit of the Ethernet port .
		 ALCATEL NOTE:
		 ACCESS: NA        usage:OPT
		 persistent: YES    INSRVMOD:NA      
		 RANGE:0..7      DEFVALUE: 0        
		 UNITS: NA         SPARSE: NA  "

	::= { eponLanEtherPortEntry 12 } 
	
eponLanEtherPortPauseAdmin   OBJECT-TYPE
	SYNTAX 	PonAdminState
	ACCESS	read-write
	STATUS	mandatory
	DESCRIPTION 
		" This indicates whether flow control
		   should be enabled or disabled.
	
       ALCATEL NOTE:
		 ACCESS: NA        usage:OPT
		 persistent: YES    INSRVMOD:YES      
		 RANGE:1..2     DEFVALUE: 2        
		 UNITS: NA         SPARSE: NA  "
	::= { eponLanEtherPortEntry 13 }
	     
eponLanEtherPortPolicyUpAdmin  OBJECT-TYPE
	SYNTAX 	PonAdminState
	ACCESS	read-write
	STATUS	mandatory
	DESCRIPTION 
		" This indicates whether rate limit
		  should be enabled or not in upstream direction
		  
		  
         ALCATEL NOTE:
		 ACCESS: NA        usage:OPT
		 persistent: YES    INSRVMOD:NA      
		 RANGE: 1..2        DEFVALUE: 2       
		 UNITS: NA         SPARSE: NA  "
	::= { eponLanEtherPortEntry 14 }

eponLanEtherPortPolicyUpCIR  OBJECT-TYPE
	SYNTAX 	INTEGER
	ACCESS	read-write
	STATUS	mandatory
	DESCRIPTION 
		" This object identifies the committed information rate of the port in Kbps
           in upstream direction. 
      ALCATEL NOTE:
		 ACCESS: NA        usage:OPT
		 persistent: YES    INSRVMOD:NA      
		 RANGE:NA           DEFVALUE: 0        
		 UNITS: Kbps        SPARSE: NA  "

	::= { eponLanEtherPortEntry 15 }
	
eponLanEtherPortPolicyUpBucket  OBJECT-TYPE
	SYNTAX 	INTEGER
	ACCESS	read-write
	STATUS	mandatory
	DESCRIPTION 
		" This object identifies the depth of this token
           bucket to be tolerant of a certain burst size
          in upstream direction.
         ALCATEL NOTE:
		 ACCESS: NA        usage:OPT
		 persistent: YES    INSRVMOD:NA      
		 RANGE:NA        DEFVALUE: 0        
		 UNITS: Bytes         SPARSE: NA  "

	::= { eponLanEtherPortEntry 16 }
	
eponLanEtherPortPolicyUpExBrSize  OBJECT-TYPE
	SYNTAX 	INTEGER
	ACCESS	read-write
	STATUS	mandatory
	DESCRIPTION 
		" This object identifies an extra token to
                 permit the forwarding engine to finish the packet
                 being sent when the CBS is exhausted in upstream direction.
         ALCATEL NOTE:
		 ACCESS: NA        usage:OPT
		 persistent: YES    INSRVMOD:NA      
		 RANGE:NA        DEFVALUE: 0      
		 UNITS: Bytes         SPARSE: NA  "

	::= { eponLanEtherPortEntry 17 }
	
eponLanEtherPortPolicyDnAdmin  OBJECT-TYPE
	SYNTAX 	PonAdminState
	ACCESS	read-write
	STATUS	mandatory
	DESCRIPTION 
		" This indicates whether rate limit
		   should be enabled in downstream direction.
		
		ALCATEL NOTE:
                 ACCESS:     NA       USAGE:      OPT
                 PERSIST:    YES      INSRVMOD:   NA
                 RANGE:      1..2    DEFVALUE:     2
                 UNITS:      NA       SPARSE:     NA "
	::= { eponLanEtherPortEntry 18 }

eponLanEtherPortPolicyDnCIR  OBJECT-TYPE
	SYNTAX 	INTEGER
	ACCESS	read-write
	STATUS	mandatory
	DESCRIPTION 
		" This object identifies the committed information rate of the port in Kbps 
for downstream direction.
	ALCATEL NOTE:
                 ACCESS:     NA       USAGE:      OPT
                 PERSIST:    YES      INSRVMOD:   NA
                 RANGE:      NA       DEFVALUE: 0
                 UNITS:     Kbps     SPARSE:     NA"
	::= { eponLanEtherPortEntry 19 }
	
eponLanEtherPortPolicyDnPIR  OBJECT-TYPE
	SYNTAX 	INTEGER
	ACCESS	read-write
	STATUS	mandatory
	DESCRIPTION 
		" This object identifies the peak information rate of the port in Kbps
 for downstream direction.
	ALCATEL NOTE:
                 ACCESS:     NA       USAGE:      OPT
                 PERSIST:    YES      INSRVMOD:   NA
                 RANGE:      NA    DEFVALUE: 0
                 UNITS:     Kbps     SPARSE:     NA"
	::= { eponLanEtherPortEntry 20 }
		
eponLanEtherPortMulticastCfg  OBJECT-TYPE
	SYNTAX	INTEGER
	ACCESS  read-write
	STATUS	mandatory
	DESCRIPTION
		" This object is used to determine whether the ONU removes the VLAN tag on 
		multicast traffic on a paticular port.
		
		Attribute values are as follows:
		
		  		  1 - Strip Vlan tag  
		  		  2 - Not strip Vlan tag
                   3 - Translation

	 ALCATEL NOTE:
                 ACCESS:     NA       USAGE:      OPT
                 PERSIST:    YES      INSRVMOD:   NA
                 RANGE:     1..3    DEFVALUE:  1
                 UNITS:     NA     SPARSE:     NA"
	::= { eponLanEtherPortEntry 21 }


eponLanEtherPortLearntMacNum  OBJECT-TYPE
	SYNTAX 	INTEGER (0..64)
	ACCESS	read-write
	STATUS	mandatory
	DESCRIPTION 
		" This object identifies Mac learning limit on 
		a UNI port.
		 ALCATEL NOTE:
                 ACCESS:     NA       USAGE:      OPT
                 PERSIST:    YES      INSRVMOD:   NA
                 RANGE:     0..64    DEFVALUE:  0
                 UNITS:     NA     SPARSE:     NA"
	::= { eponLanEtherPortEntry 22}
	
	
eponLanEtherPortMaxGroup  OBJECT-TYPE
	SYNTAX 	INTEGER (0..64)
	ACCESS	read-write
	STATUS	mandatory
	DESCRIPTION 
		" This object identifies Max Group on 
		a UNI port. 
		ALCATEL NOTE:
                 ACCESS:     NA       USAGE:      OPT
                 PERSIST:    YES      INSRVMOD:   NA
                 RANGE:     0..64     DEFVALUE:   16
                 UNITS:     NA        SPARSE:     NA"

       	::= { eponLanEtherPortEntry 23 }	
	
 eponLanEtherPortPmCollectInd  OBJECT-TYPE
	SYNTAX 	INTEGER
	ACCESS	read-write
	STATUS	mandatory
	DESCRIPTION 
		" This indicates whether Ethernet Performance Monitors
		   should be collected for this Ethernet Port.
	
		  1 = PM collection enabled
		  2 = PM collection disabled
     ALCATEL NOTE:
                 ACCESS:     NA       USAGE:      OPT
                 PERSIST:    YES      INSRVMOD:   NA
                 RANGE:     1..2      DEFVALUE:  2
                 UNITS:     NA        SPARSE:     NA"

	::= { eponLanEtherPortEntry 24 }


  eponLanEtherPortLpbackAdmin  OBJECT-TYPE
  	SYNTAX 	INTEGER
	ACCESS	read-write
	STATUS	mandatory
	DESCRIPTION 
		" This indicates whether This indicates whether enable loopback
		  or not for this Ethernet Port. If the eponLanEtherPortLpbackAdmin is disable, 
		  the eponLanEtherPortLoopShutoff mean nothing. 
		  It's value is valid only when eponLanEtherPortLpbackAdmin is enable
		  
		  1 = loopback enabled
		  2 = loopback disabled

		 ALCATEL NOTE:
                 ACCESS:     NA       USAGE:      OPT
                 PERSIST:    YES      INSRVMOD:   NA
                 RANGE:     1..2    DEFVALUE:  2
                 UNITS:     NA     SPARSE:     NA"

	::= { eponLanEtherPortEntry 25 }
	
  eponLanEtherPortMaxMcastBw  OBJECT-TYPE
  	SYNTAX 	INTEGER
	ACCESS	read-write
	STATUS	mandatory
	DESCRIPTION 
		" This indicates the max multicast Bandwidth 
		per Enet port
Notes: NOT SUPPORTED in R4230 release.
 "
	::= { eponLanEtherPortEntry 26 }

  eponLanEtherPortmode  OBJECT-TYPE
  	SYNTAX 	INTEGER
	ACCESS	read-write
	STATUS	mandatory
	DESCRIPTION 
		" This indicates Enet port mode.		
		  supported modes are:		
		  
		  0x01 = 10M-Half
		  0x02 = 10M-Full
		  0x03 = 100M-Half
		  0x04 = 100M-Full
		  0x05 = 1G 

 ALCATEL NOTE:		  
		 ACCESS: NA        usage:OPT
		 persistent: YES    INSRVMOD:YES      
		 RANGE:1..5        DEFVALUE: 4         
		 UNITS: NA         SPARSE: NA  "		
		   
	::= { eponLanEtherPortEntry 27 }

eponLanEtherPortLoopShutoff  OBJECT-TYPE
    SYNTAX 	INTEGER
    ACCESS	read-write
    STATUS	mandatory
    DESCRIPTION
        " This indicates whether the port can be shut down when detect loopback
        0 = disabled
        1 = enabled
        ALCATEL NOTE:
        ACCESS: NA         usage:OPT
        persistent: YES    INSRVMOD:NA
        RANGE:0..1         DEFVALUE: 1
        UNITS: NA         SPARSE: NA  "
        DEFVAL { 1 }
::= { eponLanEtherPortEntry 28 }

eponLanEtherPortAutoNegAdvertisedTechnologyAbility  OBJECT-TYPE
       SYNTAX INTEGER
       ACCESS read-write
       STATUS mandatory
       DESCRIPTION
           " allowed auto negotiation advertised technology ability of Ethernet port:
              bit0=Global
              bit1=Other
              bit2=Unkown
              bit4=10T
              bit5=10TFD
              bit6=100T4
              bit7=100TX
              bit8=100TXFD
              bit9=100T2
              bit10=100T2FD
              bit11=1000X
              bit12=1000XFD
              bit13=1000T
              bit14=1000TFD
              bit15=FdxPause
              bit16=FdxAPause
              bit17=FdxSPause
              bit18=FdxBPause
              bit19=RemFault1
              bit20=RemFault2
              bit21=IsoEthernet

         Bit0, the right-most one, is LSB. bit0, bit1 and bit2 cannot write.
             
       ALCATEL NOTE:
           ACCESS: NA        usage:OPT
           persistent: YES    INSRVMOD:YES
           RANGE:NA          DEFVALUE: 4
           UNITS: NA         SPARSE: NA  "
::= { eponLanEtherPortEntry 29 }

eponLanEtherPortAutoNegRst  OBJECT-TYPE
       SYNTAX INTEGER
       ACCESS read-only
       STATUS mandatory
       DESCRIPTION
           " allowed auto negotiation advertised technology ability of
Ethernet port:
              bit0=Global
              bit1=Other
              bit2=Unkown
              bit4=10T
              bit5=10TFD
              bit6=100T4
              bit7=100TX
              bit8=100TXFD
              bit9=100T2
              bit10=100T2FD
              bit11=1000X
              bit12=1000XFD
              bit13=1000T
              bit14=1000TFD
              bit15=FdxPause
              bit16=FdxAPause
              bit17=FdxSPause
              bit18=FdxBPause
              bit19=RemFault1
              bit20=RemFault2
              bit21=IsoEthernet

         Bit0, the right-most one, is LSB. bit0, bit1 and bit2 cannot
write.

       ALCATEL NOTE:
           ACCESS: NA        usage:OPT
           persistent: YES    INSRVMOD:YES
           RANGE:NA          DEFVALUE: 4
           UNITS: NA         SPARSE: NA  "
::= { eponLanEtherPortEntry 30 }


-- *********************************************
--
-- EPON LAN ETHERNET PORT SNOOPING VLAN TABLE
--
-- This table is used to associate multicast vlans with a physical UNI port,
-- Only valid for IGMP Snooping mode  
--
-- *********************************************

eponLanEtherPortSnoopingMcVlanTable  OBJECT-TYPE
	SYNTAX SEQUENCE OF EponLanEtherPortSnoopingMcVlanEntry
	ACCESS	not-accessible
	STATUS	mandatory 
	DESCRIPTION 
	 "  this table indicates allowed multicast vlan for ethernet port.
	 ALCATEL NOTE:
             SUPPORT: YES   TABLESIZE: DEP"
	::= { eponLanGroup 2 }


eponLanEtherPortSnoopingMcVlanEntry  OBJECT-TYPE
	SYNTAX 	EponLanEtherPortSnoopingMcVlanEntry
	ACCESS	not-accessible
	STATUS	mandatory  
	DESCRIPTION
         "An entry in the eponPonConfigTable. 
          Row creation : an entry is created when operator configures MC vlan for ethernet port. 
          Row deletion : an entry is created when operator deletes MC vlan for ethernet port.
          ALCATEL NOTE:
             SUPPORT: YES"
	INDEX	{ eponLanEtherPortIfindex,
	          eponLanEtherPortSnoopingMcVlan }
	::= { eponLanEtherPortSnoopingMcVlanTable 1 }

EponLanEtherPortSnoopingMcVlanEntry ::= SEQUENCE {
	eponLanEtherPortSnoopingMcVlan 	            INTEGER,
	eponLanEtherPortSnoopingMcVlanRowStatus		RowStatus
}


	
eponLanEtherPortSnoopingMcVlan  OBJECT-TYPE
	SYNTAX 	INTEGER (1..4093)
	ACCESS	read-only
	STATUS	mandatory
	DESCRIPTION 
		"This index is used to define a multicast VLAN ID, range is 1 - 4093.
		ALCATEL NOTE:
                 ACCESS:     NA       USAGE:      NA
                 PERSIST:    YES      INSRVMOD:   NO
                 RANGE:      NA       DEFVALUE:   NA
                 UNITS:      NA       SPARSE:     NA
                "
	::= { eponLanEtherPortSnoopingMcVlanEntry 1 }
	
eponLanEtherPortSnoopingMcVlanRowStatus  OBJECT-TYPE
	SYNTAX 	RowStatus
	ACCESS	read-write
	STATUS	mandatory
	DESCRIPTION 
	"This object is used to create a new row or delete an
	 ALCATEL NOTE:
		 ACCESS: NA        usage: MAND
         persistent: YES   INSRVMOD:YES
         RANGE:1,4,6       DEFVALUE: NA  
         UNITS: NA         SPARSE: NA  "
	::= { eponLanEtherPortSnoopingMcVlanEntry 2 }
	
	
	
eponLanEtherPortVlanModeTable  OBJECT-TYPE
	SYNTAX SEQUENCE OF EponLanEtherPortVlanModeEntry
	ACCESS	not-accessible
	STATUS	mandatory  
	DESCRIPTION 
	 "  this table indicates vlan translation entry for ethernet port.
	 ALCATEL NOTE:
             SUPPORT: YES   TABLESIZE: DEP"

	::= { eponLanGroup 3 }


eponLanEtherPortVlanModeEntry  OBJECT-TYPE
	SYNTAX 	EponLanEtherPortVlanModeEntry
	ACCESS	not-accessible
	STATUS	mandatory  
	DESCRIPTION
         "An entry in the eponLanEtherPortVlanModeTable . 
          Row creation : an entry is created when operator configures vlan translation for ethernet port. 
          Row deletion : an entry is created when operator deletes vlan translation for ethernet port.
          ALCATEL NOTE:
             SUPPORT: YES"
	INDEX	{ eponLanEtherPortIfindex,
	          eponLanEtherPortUniSideVlan}
	::= { eponLanEtherPortVlanModeTable 1 }

EponLanEtherPortVlanModeEntry ::= SEQUENCE {
	eponLanEtherPortUniSideVlan                 INTEGER,
	eponLanEtherPortNetworkSideVlan		       INTEGER,
	eponLanEtherPortVlanRowStatus               RowStatus
}


eponLanEtherPortUniSideVlan  OBJECT-TYPE
	SYNTAX 	INTEGER (1..4093)
	ACCESS	read-only
	STATUS	mandatory
	DESCRIPTION 
		"This index is used to define userside VLAN ID for physical UNI.
		ALCATEL NOTE:
                 ACCESS:     NA       USAGE:      NA
                 PERSIST:    YES      INSRVMOD:   NO
                 RANGE:      1..4093  DEFVALUE:   NA
                 UNITS:      NA       SPARSE:     NA
                "

	::= { eponLanEtherPortVlanModeEntry 1 }
	
eponLanEtherPortNetworkSideVlan  OBJECT-TYPE
	SYNTAX 	INTEGER  (1..4093)
	ACCESS	read-write
	STATUS	mandatory
	DESCRIPTION 
		"This attribute is the networkside VLAN of the physical UNI.
				ALCATEL NOTE:
                 ACCESS:     NA       USAGE:      NA
                 PERSIST:    YES      INSRVMOD:   NO
                 RANGE:      1..4093  DEFVALUE:   NA
                 UNITS:      NA       SPARSE:     NA
                "

	::= { eponLanEtherPortVlanModeEntry 2 }

	
eponLanEtherPortVlanRowStatus OBJECT-TYPE 
	SYNTAX	RowStatus
	ACCESS	read-write
	STATUS  mandatory
	DESCRIPTION
         	"This object is used to create a new row or delete an
 	  ALCATEL NOTE:
 	       ACCESS: NA        usage: MAND
 	       persistent: YES   INSRVMOD:YES
 	       RANGE:1,4,6       DEFVALUE: NA  
 	       UNITS: NA         SPARSE: NA " 

::= { eponLanEtherPortVlanModeEntry 3 }	

-- *********************************************
--
-- EPON EPON LAN ETHER PORT MCVLAN TRANSALTION TABLE
--
-- This table is used to create mc vlan translation table 
-- on a given UNI port. Rows are created 
-- dynamically by operator via Create-and-go
-- 
--*********************************************

eponLanEtherPortMcVlanTranTable  OBJECT-TYPE
	SYNTAX SEQUENCE OF EponLanEtherPortMcVlanTranEntry
	ACCESS	not-accessible
	STATUS	mandatory  
	DESCRIPTION 
	 "  this table indicates Mcast vlan translation entry for ethernet port.
	 ALCATEL NOTE:
             SUPPORT: YES   TABLESIZE: DEP"

	::= { eponLanGroup 4 }


eponLanEtherPortMcVlanTranEntry  OBJECT-TYPE
	SYNTAX 	EponLanEtherPortMcVlanTranEntry
	ACCESS	not-accessible
	STATUS	mandatory  
	DESCRIPTION
         "An entry in the eponLanEtherPortMcVlanTranTable . 
          Row creation : an entry is created when operator configures vlan translation for ethernet port. 
          Row deletion : an entry is created when operator deletes vlan translation for ethernet port.
          ALCATEL NOTE:
             SUPPORT: YES"
	INDEX	{ eponLanEtherPortIfindex,
	          eponLanEtherPortMcVlanId}
	::= { eponLanEtherPortMcVlanTranTable 1 }

EponLanEtherPortMcVlanTranEntry ::= SEQUENCE {
	eponLanEtherPortMcVlanId                 INTEGER,
	eponLanEtherPortUserVlan		          INTEGER,
	eponLanEtherPortMcVlanTranRowStatus      RowStatus
}

eponLanEtherPortMcVlanId  OBJECT-TYPE
	SYNTAX 	INTEGER (1..4093)
	ACCESS	read-only
	STATUS	mandatory
	DESCRIPTION 
		"This index is used to define macst VLAN ID for physical UNI.
		ALCATEL NOTE:
                 ACCESS:     NA       USAGE:      NA
                 PERSIST:    YES      INSRVMOD:   NO
                 RANGE:      1..4093  DEFVALUE:   NA
                 UNITS:      NA       SPARSE:     NA
                "

	::= { eponLanEtherPortMcVlanTranEntry 1 }
	
eponLanEtherPortUserVlan  OBJECT-TYPE
	SYNTAX 	INTEGER  (1..4093)
	ACCESS	read-write
	STATUS	mandatory
	DESCRIPTION 
		"This index is the userside VLAN of the physical UNI.
				ALCATEL NOTE:
                 ACCESS:     NA       USAGE:      NA
                 PERSIST:    YES      INSRVMOD:   NO
                 RANGE:      1..4093  DEFVALUE:   NA
                 UNITS:      NA       SPARSE:     NA
                "

	::= { eponLanEtherPortMcVlanTranEntry 2 }
	
eponLanEtherPortMcVlanTranRowStatus OBJECT-TYPE 
	SYNTAX	RowStatus
	ACCESS	read-write
	STATUS  mandatory
	DESCRIPTION
         	"This object is used to create a new row or delete an
 	  ALCATEL NOTE:
 	       ACCESS: NA        usage: MAND
 	       persistent: YES   INSRVMOD:YES
 	       RANGE:1,4,6       DEFVALUE: NA  
 	       UNITS: NA         SPARSE: NA " 

::= { eponLanEtherPortMcVlanTranEntry 3 }

-- EPON EPON LAN ETHER PORT FDB TABLE
--
-- This table is used to retrieve MAC learned
-- on a given UNI port and vlan
-- 
--*********************************************

eponLanEtherPortFdbTable  OBJECT-TYPE
	SYNTAX SEQUENCE OF EponLanEtherPortFdbEntry
	ACCESS	not-accessible
	STATUS	mandatory  
	DESCRIPTION 
	 "  this table indicates Fdb entry for ethernet port.
	 ALCATEL NOTE:
             SUPPORT: YES   TABLESIZE: DEP"

	::= { eponLanGroup 5 }


eponLanEtherPortFdbEntry  OBJECT-TYPE
	SYNTAX 	EponLanEtherPortFdbEntry
	ACCESS	not-accessible
	STATUS	mandatory  
	DESCRIPTION
         "An entry in the eponLanEtherPortFdbTable . 
          ALCATEL NOTE:
             SUPPORT: YES"
	INDEX	{ eponLanEtherPortIfindex ,
	          eponLanEtherPortFdbVlan ,
              eponLanEtherPortFdbMac}
	::= { eponLanEtherPortFdbTable 1 }

EponLanEtherPortFdbEntry ::= SEQUENCE {
	eponLanEtherPortFdbVlan          INTEGER,
	eponLanEtherPortFdbMac          MacAddress,
	eponLanEtherPortFdbStatus             INTEGER
}

eponLanEtherPortFdbVlan          OBJECT-TYPE
	SYNTAX 	INTEGER (1..4093)
	ACCESS	read-only
	STATUS	mandatory
	DESCRIPTION 
		"This index is used to define VLAN ID in Fdb table for physical UNI.
		ALCATEL NOTE:
                 ACCESS:     NA       USAGE:      NA
                 PERSIST:    NO      INSRVMOD:   NO
                 RANGE:      1..4093  DEFVALUE:   NA
                 UNITS:      NA       SPARSE:     NA
                "

	::= { eponLanEtherPortFdbEntry 1 }

eponLanEtherPortFdbMac          OBJECT-TYPE
	SYNTAX 	MacAddress
	ACCESS	read-only
	STATUS	mandatory
	DESCRIPTION 
		"This index is used to define Mac address in Fdb table for physical UNI.
		ALCATEL NOTE:
                 ACCESS:     NA       USAGE:      NA
                 PERSIST:    NO      INSRVMOD:   NO
                 RANGE:      NA      DEFVALUE:   NA
                 UNITS:      NA       SPARSE:     NA
                "

	::= { eponLanEtherPortFdbEntry 2 }

eponLanEtherPortFdbStatus             OBJECT-TYPE
	SYNTAX 	INTEGER
	ACCESS	read-only
	STATUS	mandatory
	DESCRIPTION 
		"This object is used to define fdb status in Fdb table for physical UNI.
                  1 = other, none of the following.
                  2 = invalid, this entry is no longer valid.
                  3 = learned,  the value of the corresponding instance of fdb table was learned and is being used.
                  4 = self, the value of the corresponding instance fdb table represents one of the device addresses.
                  5 = mgmt, the value of the corresponding instance of fdb is manually configured.

		ALCATEL NOTE:
                 ACCESS:     NA       USAGE:      NA
                 PERSIST:    NO      INSRVMOD:   NO
                 RANGE:      1|2|3|4|5      DEFVALUE:  NA
                 UNITS:      NA       SPARSE:     NA
                "

	::= { eponLanEtherPortFdbEntry 3 }


-- *********************************************
--
-- EPON ONT Filter TABLE
--
-- This table is used to create ONT flow table 
-- on a given UNI port. Rows are created 
-- dynamically by operator via Create-and-go
-- 
--*********************************************
eponOntFilterTable  OBJECT-TYPE
	SYNTAX SEQUENCE OF EponOntFilterEntry
	ACCESS	not-accessible
	STATUS	mandatory  
	DESCRIPTION 
	 "  this table indicates flow at ONT.
	 ALCATEL NOTE:
             SUPPORT: YES   TABLESIZE: DEP"
	::= { eponServicesGroup  9}


eponOntFilterEntry  OBJECT-TYPE
	SYNTAX 	EponOntFilterEntry
	ACCESS	not-accessible
	STATUS	mandatory 
	DESCRIPTION  
	"An entry in the eponOntFilterTable. 
          Row creation : an entry is created  when operator configure one fllter. 
          Row deletion : an entry is created  when operator delete one filter. 
           ALCATEL NOTE:
             SUPPORT: YES"
	INDEX	{ eponLanEtherPortIfindex,
	          eponOntFilterId}
	::= { eponOntFilterTable 1 }

EponOntFilterEntry ::= SEQUENCE {
	eponOntFilterId                   INTEGER,
	eponOntFilterRowStatus            RowStatus,
	eponOntFilterOntFilterProfileId          AsamProfilePointer,
	eponOntFilterPrecedence           INTEGER,
	eponOntFilterAcl                  INTEGER,
	eponOntFilterDot1p                EponOntPriority,
	eponOntFilterLlid                 INTEGER,
	eponOntFilterQueueId              INTEGER,
	eponOntFilterProfileType          INTEGER   
}


eponOntFilterId  OBJECT-TYPE
	SYNTAX 	INTEGER (1..8)
	ACCESS	read-only
	STATUS	mandatory
	DESCRIPTION 
		"This index is the number of the filter on the physical UNI,
		Range is 1 - 8 .
		ALCATEL NOTE:
                 ACCESS:     NA       USAGE:      NA
                 PERSIST:    YES      INSRVMOD:   NO
                 RANGE:     1..8      DEFVALUE:   NA
                 UNITS:  NA       SPARSE:     NA
                "
	::= { eponOntFilterEntry 1 }
	
eponOntFilterRowStatus OBJECT-TYPE 
	SYNTAX	RowStatus
	ACCESS	read-write
	STATUS  mandatory
	DESCRIPTION
		"This object is used to create/modify/delete an ONT flow in this table. 
	 	 ALCATEL NOTE:
		 ACCESS: NA        usage: MAND
         persistent: YES   INSRVMOD:YES
         RANGE:1,4,6       DEFVALUE: NA  
         UNITS: NA         SPARSE: NA  "
::= { eponOntFilterEntry 2 }
	
	
eponOntFilterOntFilterProfileId  OBJECT-TYPE
	SYNTAX 	AsamProfilePointer
	ACCESS	read-write
	STATUS	mandatory
	DESCRIPTION 
		" this object indicates the traffic classification.
		this indicate the profile entry in eponTcProfileTable. 
		Note that for each ont flow, the value of eponOntFlowTcProfileId could not be changed.
		ALCATEL NOTE:
		 ACCESS: NA        usage: MAN
         persistent: YES   INSRVMOD:NA
         RANGE:NA          DEFVALUE: NA  
         UNITS: NA         SPARSE: NA  "

	::= { eponOntFilterEntry 3 }

eponOntFilterPrecedence OBJECT-TYPE
	SYNTAX 	INTEGER 
	ACCESS	read-write
	STATUS	mandatory
	DESCRIPTION 
		"This element specify the associated profile(rule) precedence .

		ALCATEL NOTE:
		 ACCESS: NA        usage: MAN
		 persistent: YES   INSRVMOD:NA
         RANGE:1..8        DEFVALUE: NA  
         UNITS: NA         SPARSE: NA  "

	::= { eponOntFilterEntry 4 }
	
eponOntFilterAcl OBJECT-TYPE
	SYNTAX 	INTEGER 
	ACCESS	read-write
	STATUS	mandatory
	DESCRIPTION 
		"indicate the flow behaviour.
		 pass=1
		 drop=2
		 ALCATEL NOTE:
		 ACCESS: NA        usage: MAN
         persistent: YES   INSRVMOD:NA
         RANGE:1..2       DEFVALUE: NA  
         UNITS: NA         SPARSE: NA  "
	::= { eponOntFilterEntry 5 }

eponOntFilterDot1p OBJECT-TYPE 
	SYNTAX  EponOntPriority
	ACCESS  read-write
	STATUS  mandatory
	DESCRIPTION
	       "This object stores the remarking pbit value for this flow in a upstream direction.
		ALCATEL NOTE:
		 ACCESS: NA        usage: OPT
         persistent: YES   INSRVMOD:NA
         RANGE:0..7,255       DEFVALUE: 255 
         UNITS: NA       SPARSE: NA  "
::= { eponOntFilterEntry  6}

eponOntFilterLlid OBJECT-TYPE
	SYNTAX 	INTEGER 
	ACCESS	read-write
	STATUS	mandatory
	DESCRIPTION 
		"This element specify the LLID that this flow applied to  
		ALCATEL NOTE:
		 ACCESS: NA        usage: MAN
         persistent: YES   INSRVMOD:NA
         RANGE:1       DEFVALUE: NA  
         UNITS: NA       SPARSE: NA  "
	::= { eponOntFilterEntry 7}

eponOntFilterQueueId  OBJECT-TYPE
	SYNTAX 	INTEGER
	ACCESS	read-write
	STATUS	mandatory
	DESCRIPTION 
		"This element specify the Queue ID that this flow applied to .
		ALCATEL NOTE:
		 ACCESS: NA        usage: MAN
         persistent: YES   INSRVMOD:NA
         RANGE:1..4       DEFVALUE: NA  
         UNITS: NA       SPARSE: NA  "
	::= { eponOntFilterEntry 8}

eponOntFilterProfileType  OBJECT-TYPE
	SYNTAX 	INTEGER
	ACCESS	read-write
	STATUS	mandatory
	DESCRIPTION 
		"This element specify the ONT filter type
		  0:IPV4
		  1:IPV6.
		 ALCATEL NOTE:
		 ACCESS: NA        usage: MAN
         persistent: YES   INSRVMOD:NA
         RANGE:0..1        DEFVALUE: 0  
         UNITS: NA       SPARSE: NA  "
	::= { eponOntFilterEntry 9}

-- *********************************************
--
-- EPON Voice ONU Common Parameter Table
--
-- This table contains voice common parameter apply to ONU level
-- for both H.248 and SIP
--
-- 
-- *********************************************

eponVoiceONUCommParaTable OBJECT-TYPE
	SYNTAX	SEQUENCE OF EponVoiceONUCommParaEntry
	ACCESS	not-accessible
	STATUS	mandatory
	DESCRIPTION
		"This object contains a table for defining epon voice ONU common
		 parameters for both H.248 and SIP configured by operator. 
		 ALCATEL NOTE:
             SUPPORT: YES   TABLESIZE: DEP"
::= { eponServicesGroup 6 }

eponVoiceONUCommParaEntry OBJECT-TYPE
	SYNTAX 	EponVoiceONUCommParaEntry
	ACCESS	not-accessible
	STATUS	mandatory
	DESCRIPTION
		 "An entry in the eponVoiceONUCommParaTable. 
          Row creation : an entry is created  when operator creates .
          Row deletion : an entry is created  when operator deletes .
          ALCATEL NOTE:
             SUPPORT: YES"
	INDEX {eponOntIndex}
::= {eponVoiceONUCommParaTable 1}

EponVoiceONUCommParaEntry ::=
	SEQUENCE { 
		eponVoiceONUCommParaRowStatus 	    RowStatus,
		eponVoiceONUCommParaIpMode            INTEGER,
		eponVoiceONUCommParaIpAddr            IpAddress,
		eponVoiceONUCommParaSubnetNetMask     IpAddress,
		eponVoiceONUCommParaDefGw             IpAddress,	
		eponVoiceONUCommParaPppoeMode         INTEGER,
		eponVoiceONUCommParaPppoeUsername     DisplayString,
		eponVoiceONUCommParaPppoePassword     DisplayString,
		eponVoiceONUCommParaTaggedMode        INTEGER,
		eponVoiceONUCommParaCvlan             INTEGER,
		eponVoiceONUCommParaSvlan             INTEGER,
		eponVoiceONUCommParaDot1P             EponSystemPriority,
		eponVoiceONUCommParaT38Admin          INTEGER,
		eponVoiceONUCommParaFaxmodemCtrl      INTEGER,	
		eponVoiceONUCommParaIADOperation      INTEGER,
		eponVoiceONUCommParaDML               INTEGER,
		eponVoiceONUCommParaDSL  							INTEGER
}

eponVoiceONUCommParaRowStatus OBJECT-TYPE 
	SYNTAX	RowStatus
	ACCESS	read-write
	STATUS  mandatory
	DESCRIPTION
		"This object is used to create a new row or delete an row.
	 ALCATEL NOTE:
		 ACCESS: NA        usage: MAND
         persistent: YES   INSRVMOD:YES
         RANGE:1,4,6       DEFVALUE: NA  
         UNITS: NA         SPARSE: NA  "
::= { eponVoiceONUCommParaEntry  1}

eponVoiceONUCommParaIpMode  OBJECT-TYPE 
	SYNTAX	INTEGER
	ACCESS	read-write
	STATUS  mandatory
	DESCRIPTION
		"This object is the voice IP config mode .
		0 = static IP 
                1 = DHCP 
                2 = PPPoE/PPPOE+
                
                Default = 0 = static IP
	 ALCATEL NOTE:
		 ACCESS: NA        usage: NA
		 persistent: YES   INSRVMOD:YES
         RANGE:0..2       DEFVALUE: 0  
         UNITS: NA         SPARSE: NA  "
::= { eponVoiceONUCommParaEntry  2}

eponVoiceONUCommParaIpAddr  OBJECT-TYPE
	SYNTAX 	IpAddress
	ACCESS	read-write
	STATUS	mandatory
	DESCRIPTION 
		" The manually provisioned IP Address of the
		  Network Media Gateway. NOTE: If eponVoiceONUCommParaIpMode
		  is not static IP, this parameter has no meaning, and take the
		  value zero.
 
    	 ALCATEL NOTE:
		 ACCESS: NA        usage: NA
		 persistent: YES   INSRVMOD:YES
         RANGE:NA       DEFVALUE: NA  
         UNITS: NA         SPARSE: NA "
::= { eponVoiceONUCommParaEntry  3 }


eponVoiceONUCommParaSubnetNetMask OBJECT-TYPE
	SYNTAX 	IpAddress
	ACCESS	read-write
	STATUS	mandatory
	DESCRIPTION 
		" The manually provisioned subnet mask of the
		  Network Media Gateway. NOTE: If eponVoiceONUCommParaIpMode
		  is not static IP, this parameter has no meaning, and take the
		  value zero.
 
    	 ALCATEL NOTE:
		 ACCESS: NA        usage: NA
		 persistent: YES   INSRVMOD:YES
         RANGE:NA       DEFVALUE: NA  
         UNITS: NA         SPARSE: NA "
::= { eponVoiceONUCommParaEntry  4 }

eponVoiceONUCommParaDefGw OBJECT-TYPE
	SYNTAX 	IpAddress
	ACCESS	read-write
	STATUS	mandatory
	DESCRIPTION 
		" The manually provisioned def GW of the
		  Network Media Gateway. NOTE: If eponVoiceONUCommParaIpMode
		  is not static IP, this parameter has no meaning, and take the
		  value zero.
 
    	 ALCATEL NOTE:
		 ACCESS: NA        usage: NA
		 persistent: YES   INSRVMOD:YES
         RANGE:NA       DEFVALUE: NA  
         UNITS: NA         SPARSE: NA "
::= { eponVoiceONUCommParaEntry  5 }

eponVoiceONUCommParaPppoeMode  OBJECT-TYPE 
	SYNTAX	INTEGER
	ACCESS	read-write
	STATUS  mandatory
	DESCRIPTION
		"This object is the voice IP config mode .
		0 = AUTO 
                1 = CHAP 
                2 = PAP
                
                Default = 0 = AUTO
	ALCATEL NOTE:
		 ACCESS: NA        usage: NA
		 persistent: YES   INSRVMOD:YES
         RANGE:0..2       DEFVALUE: 0  
         UNITS: NA         SPARSE: NA  "
::= { eponVoiceONUCommParaEntry  6}

eponVoiceONUCommParaPppoeUsername  OBJECT-TYPE
	SYNTAX 	DisplayString (SIZE(0..32))
	ACCESS	read-write
	STATUS	mandatory
	DESCRIPTION 
		"This is a textual string that contains the Username
		 required for authentication with Pppoe.

		 Default - null string. 
	 ALCATEL NOTE:
	 ACCESS: NA        usage: NA
	 persistent: YES   INSRVMOD:YES
         RANGE:NA       DEFVALUE: NULL  
         UNITS: NA         SPARSE: NA   "
::= { eponVoiceONUCommParaEntry  7 }


eponVoiceONUCommParaPppoePassword  OBJECT-TYPE
	SYNTAX 	DisplayString (SIZE(0..32))
	ACCESS	read-write
	STATUS	mandatory
	DESCRIPTION 
		"This is a textual string that contains the Password
		 required for authentication with the Pppoe.

		 Default - null string. 

        ALCATEL NOTE:
	 ACCESS: NA        usage: NA
	 persistent: YES   INSRVMOD:YES
         RANGE:NA       DEFVALUE: NULL  
         UNITS: NA         SPARSE: NA    "
::= { eponVoiceONUCommParaEntry  8 }

eponVoiceONUCommParaTaggedMode  OBJECT-TYPE 
	SYNTAX	INTEGER
	ACCESS	read-write
	STATUS  mandatory
	DESCRIPTION
		"This object is the voice IP config mode .
		0 = Transparent 
                1 = Tag 
                2 = Vlan stacking
                
                Default = 1 = Tag
	 ALCATEL NOTE:
	 ACCESS: NA        usage: NA
	 persistent: YES   INSRVMOD:YES
         RANGE:0..2       DEFVALUE: 1  
         UNITS: NA         SPARSE: NA  "
::= { eponVoiceONUCommParaEntry  9}	

eponVoiceONUCommParaCvlan OBJECT-TYPE 
	SYNTAX	INTEGER
	ACCESS	read-write
	STATUS  mandatory
	DESCRIPTION
		"This object is used to reference the C-VLAN ID with
		 which this service is associated. 

		 Range is 1 - 4093.
		
		 No default since value must be supplied by manager.
        ALCATEL NOTE:
	 ACCESS: NA        usage: NA
	 persistent: YES   INSRVMOD:YES
         RANGE: 1..4093    DEFVALUE: 0  
         UNITS: NA         SPARSE: NA  "
::= { eponVoiceONUCommParaEntry  10}

eponVoiceONUCommParaSvlan OBJECT-TYPE 
	SYNTAX	INTEGER
	ACCESS	read-write
	STATUS  mandatory
	DESCRIPTION
		"This object is used to reference the S-VLAN ID 
		 with which this service is associated. 

		 Range is 0,2 - 4093.
		
		 No default since value must be supplied by manager.
		 If tag mode is not stack, this parameter should take
		 the value zero
		 
        ALCATEL NOTE:
	 ACCESS: NA        usage: NA
	 persistent: YES   INSRVMOD:YES
         RANGE: 0,2..4093   DEFVALUE: 0  
         UNITS: NA         SPARSE: NA  "
::= { eponVoiceONUCommParaEntry  11}

eponVoiceONUCommParaDot1P  OBJECT-TYPE
	SYNTAX 	EponSystemPriority
	ACCESS	read-write
	STATUS	mandatory
	DESCRIPTION 
		" Indicates the default pbit this service is associated.
		 Default = 5 
		
		 ALCATEL NOTE:
		 ACCESS: NA        usage:NA
		 persistent: YES    INSRVMOD:NA      
		 RANGE:0..7      DEFVALUE: 5        
		 UNITS: NA         SPARSE: NA  "

::= { eponVoiceONUCommParaEntry 12 } 

eponVoiceONUCommParaT38Admin  OBJECT-TYPE 
	SYNTAX	INTEGER
	ACCESS	read-write
	STATUS  mandatory
	DESCRIPTION
		"This object is used to enable/disable T38 .
		0 = T30 transparent mode 
        1 = T38 
		
                Default = 0 = T30
	 ALCATEL NOTE:
	 ACCESS: NA        usage: NA
	 persistent: YES   INSRVMOD:YES
         RANGE:0..1       DEFVALUE: 0  
         UNITS: NA         SPARSE: NA  "
::= { eponVoiceONUCommParaEntry  13 }

eponVoiceONUCommParaFaxmodemCtrl  OBJECT-TYPE 
	SYNTAX	INTEGER
	ACCESS	read-write
	STATUS  mandatory
	DESCRIPTION
		"This object is the link negotiation mode .
		0 = Negotiation 
                1 = auto VBD 
                
                Default = 0 = Negotiation
	 ALCATEL NOTE:
	 ACCESS: NA        usage: NA
	 persistent: YES   INSRVMOD:YES
         RANGE:0..1       DEFVALUE: 0  
         UNITS: NA         SPARSE: NA  "
::= { eponVoiceONUCommParaEntry  14 }

eponVoiceONUCommParaIADOperation  OBJECT-TYPE 
	SYNTAX	INTEGER
	ACCESS	write-only
	STATUS  mandatory
	DESCRIPTION
		"The action to ONU voice module. When use
 	        for ONU which take SIP protocol, the action
 	        apply to all voice ports on the ONU. .
		    0 = re-register
 	        1 = de-register
 	        2 = reset, only apply to voice module 
                
	 ALCATEL NOTE:
	 ACCESS: NA        usage: NA
	 persistent: NO   INSRVMOD:YES
         RANGE:0..2       DEFVALUE: NA  
         UNITS: NA         SPARSE: NA  "
::= { eponVoiceONUCommParaEntry  15}

eponVoiceONUCommParaDML  OBJECT-TYPE 
  SYNTAX  INTEGER  
  ACCESS  read-write
  STATUS  mandatory
  DESCRIPTION
    "This attribute indicate long timer for digitmap.
   ALCATEL NOTE:
	 ACCESS: NA        usage: NA
	 persistent: NO   INSRVMOD:YES
         RANGE:1..40       DEFVALUE: 20  
         UNITS: Second     SPARSE: NA  "
::= { eponVoiceONUCommParaEntry  16 }

eponVoiceONUCommParaDSL  OBJECT-TYPE 
  SYNTAX  INTEGER  
  ACCESS  read-write
  STATUS  mandatory
  DESCRIPTION
    "This attribute indicate short timer for digitmap.
   ALCATEL NOTE:
	 ACCESS: NA        usage: NA
	 persistent: NO   INSRVMOD:YES
         RANGE:1..40       DEFVALUE: 5  
         UNITS: Second     SPARSE: NA  "
::= { eponVoiceONUCommParaEntry  17 }
	
-- *********************************************
--
-- EPON MEDIA GATEWAY TABLE
--
-- This table contains media gateway corresponding para
-- 
--
-- 
-- *********************************************

eponMediaGatewayTable OBJECT-TYPE
	SYNTAX	SEQUENCE OF EponMediaGatewayEntry
	ACCESS	not-accessible
	STATUS	mandatory
	DESCRIPTION
		"This object contains a table for defining media gateway
		 by operator. 
		 ALCATEL NOTE:
             SUPPORT: YES   TABLESIZE: DEP"
::= { eponServicesGroup 7 }

eponMediaGatewayEntry OBJECT-TYPE
	SYNTAX 	EponMediaGatewayEntry
	ACCESS	not-accessible
	STATUS	mandatory
	DESCRIPTION
		 "An entry in the eponMediaGatewayTable. 
          Row creation : an entry is created  when operator creates .
          Row deletion : an entry is created  when operator deletes .
          ALCATEL NOTE:
             SUPPORT: YES"
	INDEX {eponOntIndex}
::= {eponMediaGatewayTable 1}

EponMediaGatewayEntry ::=
	SEQUENCE { 
		eponMediaGatewayRowStatus 	   RowStatus,
		eponMediaGatewayUDPPort            INTEGER,
		eponMedGwyCtrlrPrimaryIPAddress    IpAddress,
		eponMedGwyCtrlrPrimaryUDPPort      INTEGER,
		eponMedGwyCtrlrSecondaryIPAddress  IpAddress,
		eponMedGwyCtrlrSecondaryUDPPort    INTEGER,
		eponMedGwyCtrlrActive              INTEGER,
		eponMediaGatewayRegMode            INTEGER,
	        eponMediaGatewayIdentifier         DisplayString (SIZE(0..64)),
		eponMedGwyHeartbeatMode            PonAdminState,
		eponMedGwyHeartbeatCycle           INTEGER,
		eponMedGwyHeartbeatCount           INTEGER,
		eponMedGwyRtpTidNum                INTEGER,
		eponMedGwyRtpTidPrefix             DisplayString (SIZE(0..16)),
		eponMedGwyRtpTidDigitBegin         INTEGER,
		eponMedGwyRtpTidMode               INTEGER,
		eponMedGwyRtpTidDigitLength        INTEGER,
		eponMedGwyActualRtpTidNum          INTEGER,
		eponMedGwyFirstRtpTidName          DisplayString (SIZE(0..32)),
		eponMedGwyIadOperation             INTEGER		
}

eponMediaGatewayRowStatus OBJECT-TYPE 
	SYNTAX	RowStatus
	ACCESS	read-write
	STATUS  mandatory
	DESCRIPTION
"This object is used to create a new row or delete an row.
	 ALCATEL NOTE:
		 ACCESS: NA        usage: MAND
         persistent: YES   INSRVMOD:YES
         RANGE:1,4,6       DEFVALUE: NA  
         UNITS: NA         SPARSE: NA  "
::= { eponMediaGatewayEntry  1}


eponMediaGatewayUDPPort  OBJECT-TYPE
	SYNTAX 	INTEGER
	ACCESS	read-write
	STATUS	mandatory
	DESCRIPTION 
		"The UDP Port used for signalling.

		Default = 2944 
		ALCATEL NOTE:
		 ACCESS: NA        usage:OPT
		 persistent: YES    INSRVMOD:NA      
		 RANGE:0..65535      DEFVALUE: 2944        
		 UNITS: NA         SPARSE: NA  "
::= { eponMediaGatewayEntry  2 }

eponMedGwyCtrlrPrimaryIPAddress  OBJECT-TYPE
	SYNTAX 	IpAddress
	ACCESS	read-write
	STATUS	mandatory
	DESCRIPTION 
		" The manually provisioned IP Address of the
		  primary Network Media Gateway controller. 
 
    	 ALCATEL NOTE:
		 ACCESS: NA        usage: NA
		 persistent: YES   INSRVMOD:YES
         RANGE:NA       DEFVALUE: NA  
         UNITS: NA         SPARSE: NA "
::= { eponMediaGatewayEntry  3 }

eponMedGwyCtrlrPrimaryUDPPort  OBJECT-TYPE
	SYNTAX 	INTEGER
	ACCESS	read-write
	STATUS	mandatory
	DESCRIPTION 
		"The UDP Port used for the
		  primary Network Media Gateway controller.

		Default = 2944 
		ALCATEL NOTE:
		 ACCESS: NA        usage:OPT
		 persistent: YES    INSRVMOD:NA      
		 RANGE:0..65535      DEFVALUE: 2944        
		 UNITS: NA         SPARSE: NA  "
::= { eponMediaGatewayEntry  4 }

eponMedGwyCtrlrSecondaryIPAddress  OBJECT-TYPE
	SYNTAX 	IpAddress
	ACCESS	read-write
	STATUS	mandatory
	DESCRIPTION 
		" The manually provisioned IP Address of the
		  secondary Network Media Gateway controller. 
 
    	 ALCATEL NOTE:
		 ACCESS: NA        usage: NA
		 persistent: YES   INSRVMOD:YES
         RANGE:NA       DEFVALUE: NA  
         UNITS: NA         SPARSE: NA "
::= { eponMediaGatewayEntry  5 }

eponMedGwyCtrlrSecondaryUDPPort  OBJECT-TYPE
	SYNTAX 	INTEGER
	ACCESS	read-write
	STATUS	mandatory
	DESCRIPTION 
		"The UDP Port used for the
		  secondary Network Media Gateway controller.

		Default = 2944 
		ALCATEL NOTE:
		 ACCESS: NA        usage:OPT
		 persistent: YES    INSRVMOD:NA      
		 RANGE:0..65535      DEFVALUE: 2944        
		 UNITS: NA         SPARSE: NA  "
::= { eponMediaGatewayEntry  6 }

eponMedGwyCtrlrActive  OBJECT-TYPE 
	SYNTAX	INTEGER
	ACCESS	read-write
	STATUS  mandatory
	DESCRIPTION
		"This object is the current active media gateway controller .
		 For set operation, ONU ignore the parameter, for get operation,
		 ONU reponse the current active media gateway controller
		0 = Secondary 
                1 = Primary 
                2 = Unknown
                
	ALCATEL NOTE:
		 ACCESS: NA        usage: NA
		 persistent: NO   INSRVMOD:YES
         RANGE:0..2       DEFVALUE: NA  
         UNITS: NA         SPARSE: NA  "
::= { eponMediaGatewayEntry  7 }

eponMediaGatewayRegMode  OBJECT-TYPE 
	SYNTAX	INTEGER
	ACCESS	read-write
	STATUS  mandatory
	DESCRIPTION
		"This object is the registering mode .
		0 = IP 
                1 = domain 
                2 = Equip
                
                Default = 0 = IP
	 ALCATEL NOTE:
	 ACCESS: NA        usage: NA
	 persistent: YES   INSRVMOD:YES
         RANGE:0..2       DEFVALUE: 0  
         UNITS: NA         SPARSE: NA  "
::= { eponMediaGatewayEntry  8 }

eponMediaGatewayIdentifier 	OBJECT-TYPE 
	SYNTAX	DisplayString (SIZE(0..64))
	ACCESS  read-write
	STATUS  mandatory
	DESCRIPTION
	    "The corresponding ID for a given Media Gw.
       It is only valid if eponMediaGatewayRegMode is
       domain or equip
       ALCATEL NOTE:
                 ACCESS:     NA       USAGE:      NA
                 PERSIST:    YES      INSRVMOD:   NO
                 RANGE:      NA       DEFVALUE:   NA
                 UNITS:      NA       SPARSE:     NA
                "
::= {eponMediaGatewayEntry 9 }	

eponMedGwyHeartbeatMode  OBJECT-TYPE 
	SYNTAX	PonAdminState
	ACCESS	read-write
	STATUS  mandatory
	DESCRIPTION
		"This object is the link checking mode .
		            
                Default = enable
	 ALCATEL NOTE:
	 ACCESS: NA        usage: NA
	 persistent: YES   INSRVMOD:YES
         RANGE:1..2       DEFVALUE: 1  
         UNITS: NA         SPARSE: NA  "
::= { eponMediaGatewayEntry  10 }

eponMedGwyHeartbeatCycle  OBJECT-TYPE 
	SYNTAX	INTEGER
	ACCESS	read-write
	STATUS  mandatory
	DESCRIPTION
		"This object is the heart beat cycle .
		
		range:
                
                Default = 60s
	 ALCATEL NOTE:
	 ACCESS: NA        usage: NA
	 persistent: YES   INSRVMOD:YES
         RANGE:NA       DEFVALUE: 60  
         UNITS: Second     SPARSE: NA  "
::= { eponMediaGatewayEntry  11 }

eponMedGwyHeartbeatCount  OBJECT-TYPE 
	SYNTAX	INTEGER
	ACCESS	read-write
	STATUS  mandatory
	DESCRIPTION
		"This object is the heart beat times .
		
		range:
                
                Default = 3
	 ALCATEL NOTE:
	 ACCESS: NA        usage: NA
	 persistent: YES   INSRVMOD:YES
         RANGE:NA       DEFVALUE: 3  
         UNITS: NA         SPARSE: NA  "
::= { eponMediaGatewayEntry  12 }

eponMedGwyRtpTidNum  OBJECT-TYPE 
	SYNTAX	INTEGER
	ACCESS	read-write
	STATUS  mandatory
	DESCRIPTION
		"This object is the number of Rtp Tid .		
		
	 ALCATEL NOTE:
	 ACCESS: NA        usage: NA
	 persistent: YES   INSRVMOD:YES
         RANGE:0..255       DEFVALUE: NA  
         UNITS: NA         SPARSE: NA  "
::= { eponMediaGatewayEntry  13 }

eponMedGwyRtpTidPrefix OBJECT-TYPE 
	SYNTAX	DisplayString (SIZE(0..16)) 
	ACCESS	read-write
	STATUS  mandatory
	DESCRIPTION 
		" Used to specify the prefix of RTP Tid.
		ALCATEL NOTE:
	 ACCESS: NA        usage: NA
	 persistent: YES   INSRVMOD:YES
         RANGE:NA       DEFVALUE: NA  
         UNITS: NA         SPARSE: NA
     "
::= { eponMediaGatewayEntry  14 }

eponMedGwyRtpTidDigitBegin  OBJECT-TYPE 
	SYNTAX	INTEGER
	ACCESS	read-write
	STATUS  mandatory
	DESCRIPTION
		"This object is the begin number of TidDigit.
                
	 ALCATEL NOTE:
	 ACCESS: NA        usage: NA
	 persistent: YES   INSRVMOD:YES
         RANGE:NA       DEFVALUE: NA  
         UNITS: NA         SPARSE: NA  "
::= { eponMediaGatewayEntry  15 }

eponMedGwyRtpTidMode  OBJECT-TYPE 
	SYNTAX	INTEGER
	ACCESS	read-write
	STATUS  mandatory
	DESCRIPTION
		"This object is the Tid digit lineup mode .
		0 = in line 
                1 = not in line 
                
	 ALCATEL NOTE:
	 ACCESS: NA        usage: NA
	 persistent: YES   INSRVMOD:YES
         RANGE:0..1       DEFVALUE: NA  
         UNITS: NA         SPARSE: NA  "
::= { eponMediaGatewayEntry  16 }

eponMedGwyRtpTidDigitLength  OBJECT-TYPE 
	SYNTAX	INTEGER
	ACCESS	read-write
	STATUS  mandatory
	DESCRIPTION
		"This object is the length of TidDigit.
		 applicable when eponMedGwyRtpTid Mode is in line
                
	 ALCATEL NOTE:
	 ACCESS: NA        usage: NA
	 persistent: YES   INSRVMOD:YES
         RANGE:0..255       DEFVALUE: NA  
         UNITS: NA         SPARSE: NA  "
::= { eponMediaGatewayEntry  17 }


eponMedGwyActualRtpTidNum  OBJECT-TYPE 
	SYNTAX	INTEGER
	ACCESS	read-only
	STATUS  mandatory
	DESCRIPTION
		"This object is the RTP Tid number get from the IAD, 
		 refer the H.248 RTP TIDInfo message in CTC standard.
		
	 ALCATEL NOTE:
	 ACCESS: NA        usage: NA
	 persistent: NO    INSRVMOD:YES
         RANGE:NA       DEFVALUE: NA 
         UNITS: NA         SPARSE: NA  "
::= { eponMediaGatewayEntry  18 }


eponMedGwyFirstRtpTidName  OBJECT-TYPE 
	SYNTAX	DisplayString (SIZE(0..32))
	ACCESS	read-only
	STATUS  mandatory
	DESCRIPTION
		"This object is the first RTP Tid name in the IAD .
                
	 ALCATEL NOTE:
	 ACCESS: NA        usage: NA
	 persistent: NO    INSRVMOD:YES
         RANGE:NA       DEFVALUE: NA 
         UNITS: NA         SPARSE: NA  "
::= { eponMediaGatewayEntry  19 }

eponMedGwyIadOperation  OBJECT-TYPE 
	SYNTAX	INTEGER
	ACCESS	read-only
	STATUS  mandatory
	DESCRIPTION
		"This object is the IAD operation mode .
		        0 = registering 
                1 = register success
                2 = IAD failure
                3 = deregister
                4 = IAD reset
          
	 ALCATEL NOTE:
	 ACCESS: NA        usage: NA
	 persistent: NO    INSRVMOD:YES
         RANGE:0..4       DEFVALUE: NA 
         UNITS: NA         SPARSE: NA  "
::= { eponMediaGatewayEntry  20 }	
		
-- *********************************************
--
-- EPON SIP AGENT TABLE
--
-- This table contains sip agent corresponding para
-- 
--
-- 
-- *********************************************

eponSipUserAgentTable OBJECT-TYPE
	SYNTAX	SEQUENCE OF EponSipUserAgentEntry
	ACCESS	not-accessible
	STATUS	mandatory
	DESCRIPTION
		"This object contains a table for defining Sip Agent
		 by operator. 
		 ALCATEL NOTE:
             SUPPORT: YES   TABLESIZE: DEP"
::= { eponServicesGroup 8 }

eponSipUserAgentEntry OBJECT-TYPE
	SYNTAX 	EponSipUserAgentEntry
	ACCESS	not-accessible
	STATUS	mandatory
	DESCRIPTION
		 "An entry in the eponSipUserAgentTable. 
          Row creation : an entry is created  when operator creates .
          Row deletion : an entry is created  when operator deletes .
          ALCATEL NOTE:
             SUPPORT: YES"
	INDEX {eponOntIndex }
::= {eponSipUserAgentTable 1}

EponSipUserAgentEntry ::=
	SEQUENCE { 
		eponSipUserAgentRowStatus 	         RowStatus,
		eponSipUserAgentUDPPort                  INTEGER,
		eponSipUserAgentProxyPrimaryIPAddress    IpAddress,
		eponSipUserAgentProxyPrimaryUDPPort      INTEGER,
		eponSipUserAgentProxySecondaryIPAddress  IpAddress,
		eponSipUserAgentProxySecondaryUDPPort    INTEGER,
		eponSipUserAgentProxyActive              INTEGER,
		eponSipUserAgentRegPrimaryIPAddress      IpAddress,
		eponSipUserAgentRegPrimaryUDPPort        INTEGER,
		eponSipUserAgentRegSecondaryIPAddress    IpAddress,
		eponSipUserAgentRegSecondaryUDPPort      INTEGER,
		eponSipUserAgentOutBoundIpAddr           IpAddress,
		eponSipUserAgentOutBoundUDPPort          INTEGER,
		eponSipUserAgentRegInterval              INTEGER,
		eponSipUserAgentHeartbeatMode            PonAdminState,
		eponSipUserAgentHeartbeatCycle           INTEGER,
		eponSipUserAgentHeartbeatCount           INTEGER,
		eponSipUserAgentDigitMap                 AsamProfileIndex
}

eponSipUserAgentRowStatus OBJECT-TYPE 
	SYNTAX	RowStatus
	ACCESS	read-write
	STATUS  mandatory
	DESCRIPTION
"This object is used to create a new row or delete an row.
	 ALCATEL NOTE:
		 ACCESS: NA        usage: MAND
                 persistent: YES   INSRVMOD:YES
                 RANGE:1,4,6       DEFVALUE: NA  
                 UNITS: NA         SPARSE: NA  "
::= { eponSipUserAgentEntry  1}

eponSipUserAgentUDPPort  OBJECT-TYPE
	SYNTAX 	INTEGER
	ACCESS	read-write
	STATUS	mandatory
	DESCRIPTION 
		"The UDP Port used for signalling.

		Default = 5060 
	ALCATEL NOTE:
		 ACCESS: NA        usage:OPT
		 persistent: YES    INSRVMOD:NA      
		 RANGE:0..65535      DEFVALUE: 5060        
		 UNITS: NA         SPARSE: NA  "
::= { eponSipUserAgentEntry  2 }

eponSipUserAgentProxyPrimaryIPAddress  OBJECT-TYPE
	SYNTAX 	IpAddress
	ACCESS	read-write
	STATUS	mandatory
	DESCRIPTION 
		" The manually provisioned IP Address of the
		  primary SIP proxy server. 
 
    	 ALCATEL NOTE:
		 ACCESS: NA        usage: NA
		 persistent: YES   INSRVMOD:YES
         RANGE:NA       DEFVALUE: NA  
         UNITS: NA         SPARSE: NA "
::= { eponSipUserAgentEntry  3 }

eponSipUserAgentProxyPrimaryUDPPort  OBJECT-TYPE
	SYNTAX 	INTEGER
	ACCESS	read-write
	STATUS	mandatory
	DESCRIPTION 
		"The UDP Port used for the
		  primary SIP proxy server.
		 
	ALCATEL NOTE:
		 ACCESS: NA        usage:OPT
		 persistent: YES    INSRVMOD:NA      
		 RANGE:0..65535      DEFVALUE: NA        
		 UNITS: NA         SPARSE: NA  "
::= { eponSipUserAgentEntry  4 }

eponSipUserAgentProxySecondaryIPAddress  OBJECT-TYPE
	SYNTAX 	IpAddress
	ACCESS	read-write
	STATUS	mandatory
	DESCRIPTION 
		" The manually provisioned IP Address of the
		  secondary SIP proxy server. 
 
    	 ALCATEL NOTE:
		 ACCESS: NA        usage: NA
		 persistent: YES   INSRVMOD:YES
         RANGE:NA       DEFVALUE: NA  
         UNITS: NA         SPARSE: NA "
::= { eponSipUserAgentEntry  5 }

eponSipUserAgentProxySecondaryUDPPort  OBJECT-TYPE
	SYNTAX 	INTEGER
	ACCESS	read-write
	STATUS	mandatory
	DESCRIPTION 
		"The UDP Port used for the
		  secondary SIP proxy server.
 
	ALCATEL NOTE:
		 ACCESS: NA        usage:OPT
		 persistent: YES    INSRVMOD:NA      
		 RANGE:0..65535      DEFVALUE: NA        
		 UNITS: NA         SPARSE: NA  "
::= { eponSipUserAgentEntry  6 }

eponSipUserAgentProxyActive  OBJECT-TYPE 
	SYNTAX	INTEGER
	ACCESS	read-write
	STATUS  mandatory
	DESCRIPTION
		"This object is the current active SIP server .
		For set operation, ONU ignore the parameter, for get operation,
		ONU reponse the current active SIP server
		
		0 = Secondary 
                1 = Primary 
                2 = Unknown 
	ALCATEL NOTE:
		 ACCESS: NA        usage: NA
		 persistent: NO   INSRVMOD:YES
                 RANGE:0..2       DEFVALUE: NA  
                 UNITS: NA         SPARSE: NA  "
::= { eponSipUserAgentEntry  7}

eponSipUserAgentRegPrimaryIPAddress  OBJECT-TYPE
	SYNTAX 	IpAddress
	ACCESS	read-write
	STATUS	mandatory
	DESCRIPTION 
		" The manually provisioned IP Address of the
		  primary Network SIP Register server. 
 
    	 ALCATEL NOTE:
		 ACCESS: NA        usage: NA
		 persistent: YES   INSRVMOD:YES
                 RANGE:NA       DEFVALUE: NA  
                 UNITS: NA         SPARSE: NA "
::= { eponSipUserAgentEntry  8 }

eponSipUserAgentRegPrimaryUDPPort  OBJECT-TYPE
	SYNTAX 	INTEGER
	ACCESS	read-write
	STATUS	mandatory
	DESCRIPTION 
		"The UDP Port used for the
		  primary Network SIP Register server.

		ALCATEL NOTE:
		 ACCESS: NA        usage:OPT
		 persistent: YES    INSRVMOD:NA      
		 RANGE:0..65535      DEFVALUE: NA       
		 UNITS: NA         SPARSE: NA  "
::= { eponSipUserAgentEntry  9 }

eponSipUserAgentRegSecondaryIPAddress  OBJECT-TYPE
	SYNTAX 	IpAddress
	ACCESS	read-write
	STATUS	mandatory
	DESCRIPTION 
		" The manually provisioned IP Address of the
		  secondary SIP Register server. 
 
    	 ALCATEL NOTE:
		 ACCESS: NA        usage: NA
		 persistent: YES   INSRVMOD:YES
                 RANGE:NA       DEFVALUE: NA  
                 UNITS: NA         SPARSE: NA "
::= { eponSipUserAgentEntry  10 }

eponSipUserAgentRegSecondaryUDPPort  OBJECT-TYPE
	SYNTAX 	INTEGER
	ACCESS	read-write
	STATUS	mandatory
	DESCRIPTION 
		"The UDP Port used for the
		  secondary SIP Register server.

		ALCATEL NOTE:
		 ACCESS: NA        usage:OPT
		 persistent: YES    INSRVMOD:NA      
		 RANGE:0..65535      DEFVALUE: NA        
		 UNITS: NA         SPARSE: NA  "
::= { eponSipUserAgentEntry  11 }

eponSipUserAgentOutBoundIpAddr  OBJECT-TYPE
	SYNTAX 	IpAddress
	ACCESS	read-write
	STATUS	mandatory
	DESCRIPTION 
		" The manually provisioned IP Address of the
		  SIP outbound server.
 
    	 ALCATEL NOTE:
		 ACCESS: NA        usage: NA
		 persistent: YES   INSRVMOD:YES
         RANGE:NA       DEFVALUE: NA  
         UNITS: NA         SPARSE: NA "
::= { eponSipUserAgentEntry  12 }


eponSipUserAgentOutBoundUDPPort  OBJECT-TYPE
	SYNTAX 	INTEGER
	ACCESS	read-write
	STATUS	mandatory
	DESCRIPTION 
		"The UDP Port used for the
		  secondary SIP Register server.

		ALCATEL NOTE:
		 ACCESS: NA        usage:OPT
		 persistent: YES    INSRVMOD:NA      
		 RANGE:0..65535      DEFVALUE: NA        
		 UNITS: NA         SPARSE: NA  "
::= { eponSipUserAgentEntry  13 }

eponSipUserAgentRegInterval  OBJECT-TYPE 
	SYNTAX	INTEGER
	ACCESS	read-write
	STATUS  mandatory
	DESCRIPTION
		"This object is the registering refresh period .
		Default = 3600 
                
	 ALCATEL NOTE:
	 ACCESS: NA        usage: NA
	 persistent: YES   INSRVMOD:YES
         RANGE:NA          DEFVALUE: 3600  
         UNITS: Second     SPARSE: NA  "
::= { eponSipUserAgentEntry  14}

eponSipUserAgentHeartbeatMode  OBJECT-TYPE 
	SYNTAX	PonAdminState
	ACCESS	read-write
	STATUS  mandatory
	DESCRIPTION
		"This object is the heart beat mode .
		 1 = enable heartbeat
		 2 = disable heartbeat
                
	 ALCATEL NOTE:
	 ACCESS: NA        usage: NA
	 persistent: YES   INSRVMOD:YES
         RANGE:1..2       DEFVALUE: NA  
         UNITS: NA         SPARSE: NA  "
::= { eponSipUserAgentEntry  15}

eponSipUserAgentHeartbeatCycle  OBJECT-TYPE 
	SYNTAX	INTEGER
	ACCESS	read-write
	STATUS  mandatory
	DESCRIPTION
		"This object is the heart beat cycle .
                Default = 60s

	 ALCATEL NOTE:
	 ACCESS: NA        usage: NA
	 persistent: YES   INSRVMOD:YES
         RANGE:0..65535       DEFVALUE: 60  
         UNITS: Second         SPARSE: NA  "
::= { eponSipUserAgentEntry  16}

eponSipUserAgentHeartbeatCount  OBJECT-TYPE 
	SYNTAX	INTEGER
	ACCESS	read-write
	STATUS  mandatory
	DESCRIPTION
		"This object is the heart beat times .
                Default = 3

	 ALCATEL NOTE:
	 ACCESS: NA        usage: NA
	 persistent: YES   INSRVMOD:YES
         RANGE:0..65535   DEFVALUE: 3  
         UNITS: NA         SPARSE: NA  "
::= { eponSipUserAgentEntry  17}
	
eponSipUserAgentDigitMap OBJECT-TYPE 
	SYNTAX	AsamProfileIndex 
	ACCESS	read-write
	STATUS  mandatory
	DESCRIPTION 
		" Used to specify the Digit Map.
		ALCATEL NOTE:
	 ACCESS: NA        usage: NA
	 persistent: YES   INSRVMOD:YES
         RANGE:NA       DEFVALUE: NA  
         UNITS: NA         SPARSE: NA
     "
::= { eponSipUserAgentEntry  18}

-- *********************************************
--
-- EPON Voice Ping TABLE
--
-- This table is used to set ONT Voice Ping Params 
-- 
--*********************************************
eponVoicePingTable  OBJECT-TYPE
	SYNTAX SEQUENCE OF EponVoicePingEntry
	ACCESS	not-accessible
	STATUS	mandatory  
	DESCRIPTION 
	 "  this table indicates voice Ping at ONT.
	 ALCATEL NOTE:
             SUPPORT: YES   TABLESIZE: DEP"
	::= { eponServicesGroup 10}

eponVoicePingEntry  OBJECT-TYPE
	SYNTAX 	EponVoicePingEntry
	ACCESS	not-accessible
	STATUS	mandatory 
	DESCRIPTION  
	"An entry in the eponVoicePingTable. 
          Row creation : an entry is created automatically when ONT is planned. 
          Row deletion : an entry is deleted automatically when ONT is unplanned.
           ALCATEL NOTE:
             SUPPORT: YES"
	INDEX	{ eponOntIndex }
	::= { eponVoicePingTable 1 }

EponVoicePingEntry ::= SEQUENCE {
eponVoiceONUPingadmin	                 INTEGER,
eponVoiceONUPingIpAddr	               IpAddress, 
eponVoiceONUPingtimes	                 INTEGER,
eponVoiceONUPingpksize	               INTEGER, 
eponVoiceONUPingtimeout	               INTEGER,
eponVoiceONUPingresult	               INTEGER,
eponVoiceONUPingTxpkt	                 INTEGER,
eponVoiceONUPingRxpkt	                 INTEGER,
eponVoiceONUPingLosspkt	               INTEGER,
eponVoiceONUPingLosspktration	         INTEGER,
eponVoiceONUPingMindelay	             INTEGER,
eponVoiceONUPingMaxdelay	             INTEGER, 
eponVoiceONUPingAvedelay	             INTEGER
}


eponVoiceONUPingadmin  OBJECT-TYPE
	SYNTAX 	INTEGER {
		start(1),
		stop (2)
	}
	ACCESS	read-write
	STATUS	mandatory
	DESCRIPTION 
		"This object is used to start or stop ping test.
		 ALCATEL NOTE:
		 Default = 2 = Stop 
		 
ALCATEL NOTE:
	  ACCESS:     NA     usage:    OPT
	  persistent: NO    INSRVMOD: YES
	  RANGE:      1..2  DEFVALUE: 2  
	  UNITS:      NA     SPARSE:   NA  
    DESCR:      NA "		 
		 
	::= { eponVoicePingEntry 1 }
	
eponVoiceONUPingIpAddr OBJECT-TYPE 
	SYNTAX 	IpAddress 
	ACCESS	read-write
	STATUS	mandatory
	DESCRIPTION 
		"this object indicates IP Addr that to ping.
		ALCATEL NOTE:
                 ACCESS:    NA       USAGE:    OPT
                 PERSIST:   NO      INSRVMOD:	YES
                 RANGE:     NA       DEFVALUE:  NA
                 UNITS:     NA       SPARSE:     NA
                 DESCR:     NA "

  ::= { eponVoicePingEntry 2 }
	
	
eponVoiceONUPingtimes  OBJECT-TYPE
	SYNTAX  INTEGER
	ACCESS	read-write
	STATUS  mandatory
	DESCRIPTION
		"This object is used to set ping times .
		Default = 4 
                
	 ALCATEL NOTE:
	 ACCESS: NA        usage: OPT
	 persistent: NO   INSRVMOD:YES
         RANGE:1..10          DEFVALUE: 4  
         UNITS: times     SPARSE: NA  "
	::= { eponVoicePingEntry 3 }

eponVoiceONUPingpksize OBJECT-TYPE
	SYNTAX  INTEGER
	ACCESS	read-write
	STATUS  mandatory
	DESCRIPTION
		"This object is used to set ping packet size .
		Default = 32 
                
	 ALCATEL NOTE:
	 ACCESS: NA        usage: OPT
	 persistent: NO   INSRVMOD:YES
         RANGE:1..65535          DEFVALUE: 32  
         UNITS: bytes     SPARSE: NA  "

	::= { eponVoicePingEntry 4 }
	
eponVoiceONUPingtimeout OBJECT-TYPE
	SYNTAX 	INTEGER 
	ACCESS	read-write
	STATUS	mandatory
	DESCRIPTION 
		"This object is used to set ping timeout value.
		Default = 2000 
                
	 ALCATEL NOTE:
	 ACCESS: NA        usage: OPT
	 persistent: NO   INSRVMOD:YES
         RANGE:1..2000          DEFVALUE: 2000  
         UNITS: millisecond     SPARSE: NA  "

	::= { eponVoicePingEntry 5 }

eponVoiceONUPingresult OBJECT-TYPE 
	SYNTAX 	INTEGER 
	ACCESS	read-only
	STATUS	mandatory
	DESCRIPTION 
		"This object indicates the ONT ping test result.
		 suppport results are:		 
       0x00 = end of test
       0x01 = ping test is in progress, not yet completed
       0x02 = waitint for the order to begin testing
       0x03 = unknown error
       0x04 = unknown destination address
       0x05 = no route
       0x06 = destination port is not active
       0x07 = ARP failed
       0x08 = Exceeds the maximum number of concurrent users
       0x09 = DNS cannot resolve
       0x0A = invalid host address

		 ALCATEL NOTE:
		 ACCESS: NA        usage: NA
		 persistent: NO   INSRVMOD:NA
         RANGE:NA        DEFVALUE: NA
         UNITS: NA         SPARSE: NA "

::= { eponVoicePingEntry  6}

eponVoiceONUPingTxpkt OBJECT-TYPE
	SYNTAX 	INTEGER 
	ACCESS	read-only
	STATUS	mandatory
	DESCRIPTION 
		"This object indicates the ONT tx packet for ping.

		 ALCATEL NOTE:
		 ACCESS: NA        usage: NA
		 persistent: NO   INSRVMOD:NA
         RANGE:NA        DEFVALUE: NA
         UNITS: NA         SPARSE: NA "

	::= { eponVoicePingEntry 7}

eponVoiceONUPingRxpkt OBJECT-TYPE
	SYNTAX 	INTEGER 
	ACCESS	read-only
	STATUS	mandatory
	DESCRIPTION 
		"This object indicates the ONT rx packet for ping.

		 ALCATEL NOTE:
		 ACCESS: NA        usage: NA
		 persistent: NO   INSRVMOD:NA
         RANGE:NA        DEFVALUE: NA
         UNITS: NA         SPARSE: NA "

	::= { eponVoicePingEntry 8}

eponVoiceONUPingLosspkt OBJECT-TYPE
	SYNTAX 	INTEGER 
	ACCESS	read-only
	STATUS	mandatory
	DESCRIPTION 
		"This object indicates the ONT loss packet for ping.

		 ALCATEL NOTE:
		 ACCESS: NA        usage: NA
		 persistent: NO   INSRVMOD:NA
         RANGE:NA        DEFVALUE: NA
         UNITS: NA         SPARSE: NA "

	::= { eponVoicePingEntry 9}

eponVoiceONUPingLosspktration OBJECT-TYPE
	SYNTAX 	INTEGER 
	ACCESS	read-only
	STATUS	mandatory
	DESCRIPTION 
		"This object indicates the ONT loss packet ratio for ping.

		 ALCATEL NOTE:
		 ACCESS: NA        usage: NA
		 persistent: NO   INSRVMOD:NA
         RANGE:NA        DEFVALUE: NA
         UNITS: NA         SPARSE: NA "

	::= { eponVoicePingEntry 10}

eponVoiceONUPingMindelay OBJECT-TYPE
	SYNTAX 	INTEGER 
	ACCESS	read-only
	STATUS	mandatory
	DESCRIPTION 
		"This object indicates the ONT min delay for ping..

		 ALCATEL NOTE:
		 ACCESS: NA        usage: NA
		 persistent: NO   INSRVMOD:NA
         RANGE:0..2000        DEFVALUE: NA
         UNITS: millisecond         SPARSE: NA "

	::= { eponVoicePingEntry 11}

eponVoiceONUPingMaxdelay OBJECT-TYPE
	SYNTAX 	INTEGER 
	ACCESS	read-only
	STATUS	mandatory
	DESCRIPTION 
		"This object indicates the ONT max delay for ping..

		 ALCATEL NOTE:
		 ACCESS: NA        usage: NA
		 persistent: NO   INSRVMOD:NA
         RANGE:0..2000        DEFVALUE: NA
         UNITS: millisecond         SPARSE: NA "

	::= { eponVoicePingEntry 12}

eponVoiceONUPingAvedelay OBJECT-TYPE
	SYNTAX 	INTEGER 
	ACCESS	read-only
	STATUS	mandatory
	DESCRIPTION 
		"This object indicates the ONT average delay for ping.

		 ALCATEL NOTE:
		 ACCESS: NA        usage: NA
		 persistent: NO   INSRVMOD:NA
         RANGE:0..2000        DEFVALUE: NA
         UNITS: millisecond         SPARSE: NA "

	::= { eponVoicePingEntry 13}

-- *********************************************
--
-- EPON QUEUE PROFILE TABLE
--
-- This table contains information  on an
-- ONT.  Using this information, the OLT can determine 
-- the following exchanges with the ONT:  
-- 1)  Number of queues needed and 2) Relative weight for each queue
-- 3)Relative threshold for each queue.  Rows are created by the operator.
--
-- 
-- *********************************************
eponQueueProfileTable OBJECT-TYPE
	SYNTAX	SEQUENCE OF EponQueueProfileEntry
	ACCESS	not-accessible
	STATUS	mandatory
	DESCRIPTION
		"This object contains a table for queue profiles. A Queue profile is used to associate with
		 logical link. 
		1) Number of queues needed.
		2) Relative weight for each queue.
		3) Relative threshold for each queue.  
	 
	 ALCATEL NOTE:currently the queue number and threshold could not be configued at ONT. hence, it will
	 always use default queue profile. it does not allow to create/modify/delete entry in this table.
             SUPPORT: YES   TABLESIZE: DEP"
::= { eponProfilesGroup 1 }

eponQueueProfileEntry
 OBJECT-TYPE
	SYNTAX 	EponQueueProfileEntry
	ACCESS	not-accessible
	STATUS	mandatory
	DESCRIPTION
         "An entry in the eponQueueProfileTable. 
          Row creation : an entry is created  when operator creates queue profile. 
          Row deletion : an entry is deleted  when operator deletes queue profile.
          ALCATEL NOTE:
             SUPPORT: YES"
INDEX {eponQueueProfileIndex }
::= {eponQueueProfileTable 1}

EponQueueProfileEntry ::=
	SEQUENCE { 
		eponQueueProfileIndex		   AsamProfileIndex,
		eponQueueProfileName		   AsamProfileName,
		eponQueueProfileRefCount	   AsamProfileRefCount,
		eponQueueProfileRowStatus 	   RowStatus,
		eponQueueProfileQ1Weight		INTEGER,
		eponQueueProfileQ2Weight		INTEGER,
		eponQueueProfileQ3Weight		INTEGER,
		eponQueueProfileQ4Weight		INTEGER,
		eponQueueProfileQ5Weight		INTEGER,
		eponQueueProfileQ6Weight		INTEGER,
		eponQueueProfileQ7Weight		INTEGER,
		eponQueueProfileQ8Weight		INTEGER,
		eponQueueProfileQ1Threshold		INTEGER,
		eponQueueProfileQ2Threshold		INTEGER,
		eponQueueProfileQ3Threshold		INTEGER,
		eponQueueProfileQ4Threshold		INTEGER,
		eponQueueProfileQ5Threshold		INTEGER,
		eponQueueProfileQ6Threshold		INTEGER,
		eponQueueProfileQ7Threshold		INTEGER,
		eponQueueProfileQ8Threshold		INTEGER
}

eponQueueProfileIndex OBJECT-TYPE 
	SYNTAX AsamProfileIndex
	ACCESS not-accessible
	STATUS mandatory
	DESCRIPTION
	    "This object is the index to the eponQueueProfileTable.
	    ALCATEL NOTE:
                 ACCESS:     NA       USAGE:      NA
                 PERSIST:    YES      INSRVMOD:   NO
                 RANGE:      NA       DEFVALUE:   NA
                 UNITS:      NA       SPARSE:     NA
                "
::= { eponQueueProfileEntry 1}

eponQueueProfileName 	OBJECT-TYPE 
	SYNTAX	AsamProfileName
	ACCESS read-write
	STATUS mandatory
	DESCRIPTION
	   "The corresponding name for a given profile id.
        The name corresponding to the ProfileId must also be unique.
	    ALCATEL NOTE:
                 ACCESS:     NA       USAGE:      NA
                 PERSIST:    YES      INSRVMOD:   NO
                 RANGE:      NA       DEFVALUE:   NA
                 UNITS:      NA       SPARSE:     NA
                "
::= {eponQueueProfileEntry 2}

eponQueueProfileRefCount OBJECT-TYPE
	SYNTAX	AsamProfileRefCount
	ACCESS read-only
	STATUS	mandatory
	DESCRIPTION
		" Indicates the number of entities using this profile. If the
          reference count is greater than 0, then this profile is 'in use',
          and may NOT be deleted. If the value is 0, then this profile is
          'not in use', and can be deleted.
          ALCATEL NOTE:
             ALCATEL NOTE:
                 ACCESS:     NA       USAGE:      NA
                 PERSIST:    NA     INSRVMOD:   NO
                 RANGE:      NA       DEFVALUE:   NA
                 UNITS:      NA       SPARSE:     NA "

::= { eponQueueProfileEntry  3}

eponQueueProfileRowStatus OBJECT-TYPE 
	SYNTAX	RowStatus
	ACCESS	read-write
	STATUS  mandatory
	DESCRIPTION
	"This object is used to create a new row or delete an row.
	 ALCATEL NOTE:
		 ACCESS: NA        usage: MAND
         persistent: YES   INSRVMOD:YES
         RANGE:1,4,6       DEFVALUE: NA  
         UNITS: NA         SPARSE: NA  "
::= { eponQueueProfileEntry  4}


eponQueueProfileQ1Weight OBJECT-TYPE 
	SYNTAX INTEGER
	ACCESS read-write
	STATUS mandatory
	DESCRIPTION
	    	"This object stores the relative weight for the 1st 
		 Queue needed. 
		 Range is 0 - 256.
		 0 means treat as strict priority - highest.
		 1 - 255 means treat as WRR priority - 255 is lowest.
		 256 - means this queue number is not used for the logical Link.
		 After the first value of 256, all subsequent queue numbers
		 can only have a value of 256 . 
		 ALCATEL NOTE:
		 ACCESS: NA        usage: MAND
         persistent: YES   INSRVMOD:YES
         RANGE:0..256      DEFVALUE: NA  
         UNITS: NA         SPARSE: NA  "

::= { eponQueueProfileEntry  5}


eponQueueProfileQ2Weight OBJECT-TYPE 
	SYNTAX INTEGER
	ACCESS read-write
	STATUS mandatory
	DESCRIPTION
	    	"This object stores the relative weight for the 2nd 
		 Queue needed for the logical Link. 
		 Range is 0 - 256.
		 0 means treat as strict priority - highest.
		 1 - 255 means treat as WRR priority - 255 is lowest.
		 256 - means this queue number is not used for the logical Link.
		 After the first value of 256, all subsequent queue numbers
		 can only have a value of 256 . 
		  ALCATEL NOTE:
		 ACCESS: NA        usage: OPT
		 persistent: YES   INSRVMOD:YES
         RANGE:0..256      DEFVALUE: 256  
         UNITS: NA         SPARSE: NA  "

::= { eponQueueProfileEntry  6}

eponQueueProfileQ3Weight OBJECT-TYPE 
	SYNTAX INTEGER
	ACCESS read-write
	STATUS mandatory
	DESCRIPTION
	    	"This object stores the relative weight for the 3th 
		 Queue needed for the logical Link. 
		 Range is 0 - 256.
		 0 means treat as strict priority - highest.
		 1 - 255 means treat as WRR priority - 255 is lowest.
		 256 - means this queue number is not used for the logical Link.
		 After the first value of 256, all subsequent queue numbers
		 can only have a value of 256 . 
		  ALCATEL NOTE:
		 ACCESS: NA        usage: OPT
		 persistent: YES   INSRVMOD:YES
         RANGE:0..256      DEFVALUE: 256  
         UNITS: NA         SPARSE: NA  "

::= { eponQueueProfileEntry  7}

eponQueueProfileQ4Weight OBJECT-TYPE 
	SYNTAX INTEGER
	ACCESS read-write
	STATUS mandatory
	DESCRIPTION
	    	"This object stores the relative weight for the 4th 
		 Queue needed for the logical Link. 
		 Range is 0 - 256.
		 0 means treat as strict priority - highest.
		 1 - 255 means treat as WRR priority - 255 is lowest.
		 256 - means this queue number is not used for the logical Link.
		 After the first value of 256, all subsequent queue numbers
		 can only have a value of 256. 
		  ALCATEL NOTE:
		 ACCESS: NA        usage: OPT
		 persistent: YES   INSRVMOD:YES
         RANGE:0..256      DEFVALUE: 256 
         UNITS: NA         SPARSE: NA  "

::= { eponQueueProfileEntry  8}

eponQueueProfileQ5Weight OBJECT-TYPE 
	SYNTAX INTEGER
	ACCESS read-write
	STATUS mandatory
	DESCRIPTION
	    	"This object stores the relative weight for the 5th 
		 Queue needed for the logical Link. 
		 Range is 0 - 256.
		 0 means treat as strict priority - highest.
		 1 - 255 means treat as WRR priority - 255 is lowest.
		 256 - means this queue number is not used for the logical Link.
		 After the first value of 256, all subsequent queue numbers
		 can only have a value of 256 . 
		  ALCATEL NOTE:
		 ACCESS: NA        usage: OPT
		 persistent: YES   INSRVMOD:YES
         RANGE:0..256      DEFVALUE: 256  
         UNITS: NA         SPARSE: NA  "

::= { eponQueueProfileEntry  9}

eponQueueProfileQ6Weight OBJECT-TYPE 
	SYNTAX INTEGER
	ACCESS read-write
	STATUS mandatory
	DESCRIPTION
	    	"This object stores the relative weight for the 6th
		 Queue needed for the logical Link. 
		 Range is 0 - 256.
		 0 means treat as strict priority - highest.
		 1 - 255 means treat as WRR priority - 255 is lowest.
		 256 - means this queue number is not used for the logical Link.
		 After the first value of 256, all subsequent queue numbers
		 can only have a value of 256 . 
		  ALCATEL NOTE:
		 ACCESS: NA        usage: OPT
		 persistent: YES   INSRVMOD:YES
         RANGE:0..256      DEFVALUE: 256  
         UNITS: NA         SPARSE: NA  "

::= { eponQueueProfileEntry  10}

eponQueueProfileQ7Weight OBJECT-TYPE 
	SYNTAX INTEGER
	ACCESS read-write
	STATUS mandatory
	DESCRIPTION
	    	"This object stores the relative weight for the 7th 
		 Queue needed for the logical Link. 
		 Range is 0 - 256.
		 0 means treat as strict priority - highest.
		 1 - 255 means treat as WRR priority - 255 is lowest.
		 256 - means this queue number is not used for the logical Link.
		 After the first value of 256, all subsequent queue numbers
		 can only have a value of 256. 
		  ALCATEL NOTE:
		 ACCESS: NA        usage: OPT
		 persistent: YES   INSRVMOD:YES
         RANGE:0..256      DEFVALUE: 256  
         UNITS: NA         SPARSE: NA  "

::= { eponQueueProfileEntry  11}

eponQueueProfileQ8Weight OBJECT-TYPE 
	SYNTAX INTEGER
	ACCESS read-write
	STATUS mandatory
	DESCRIPTION
	    	"This object stores the relative weight for the 8th 
		 Queue needed for the logical Link. 
		 Range is 0 - 256.
		 0 means treat as strict priority - highest.
		 1 - 255 means treat as WRR priority - 255 is lowest.
		 256 - means this queue number is not used for the logical Link.
		 After the first value of 256, all subsequent queue numbers
		 can only have a value of 256. 
		  ALCATEL NOTE:
		 ACCESS: NA        usage: OPT
		 persistent: YES   INSRVMOD:YES
         RANGE:0..256      DEFVALUE: 256  
         UNITS: NA         SPARSE: NA  "

::= { eponQueueProfileEntry  12}

eponQueueProfileQ1Threshold OBJECT-TYPE 
	SYNTAX INTEGER (0..65535)
	ACCESS read-write
	STATUS mandatory
	DESCRIPTION
	    	"This object stores the relative threshold for the 1st 
		 Queue. 
		 ALCATEL NOTE:
		 ACCESS: NA        usage: OPT
		 persistent: YES   INSRVMOD:YES
         RANGE:0..65535         DEFVALUE: 0  
         UNITS: Bytes         SPARSE: NA  "

::= { eponQueueProfileEntry  13}

eponQueueProfileQ2Threshold OBJECT-TYPE 
	SYNTAX INTEGER (0..65535)
	ACCESS read-write
	STATUS mandatory
	DESCRIPTION
	    	"This object stores the relative threshold for the 2nd 
		 Queue.
		 ALCATEL NOTE:
		 ACCESS: NA        usage: OPT
		 persistent: YES   INSRVMOD:YES
         RANGE:0..65535          DEFVALUE: 0  
         UNITS: Bytes         SPARSE: NA  "
::= { eponQueueProfileEntry  14}

eponQueueProfileQ3Threshold OBJECT-TYPE 
	SYNTAX INTEGER  (0..65535)
	ACCESS read-write
	STATUS mandatory
	DESCRIPTION
	    	"This object stores the relative threshold for the 3th
		 Queue.
		 ALCATEL NOTE:
		 ACCESS: NA        usage: OPT
		 persistent: YES   INSRVMOD:YES
         RANGE:0..65535          DEFVALUE: 0  
         UNITS: Bytes         SPARSE: NA  "

::= { eponQueueProfileEntry  15}

eponQueueProfileQ4Threshold OBJECT-TYPE 
	SYNTAX INTEGER   (0..65535)
	ACCESS read-write
	STATUS mandatory
	DESCRIPTION
	    	"This object stores the relative threshold for the 4th 
		 Queue .
		 ALCATEL NOTE:
		 ACCESS: NA        usage: OPT
		 persistent: YES   INSRVMOD:YES
         RANGE:0..65535         DEFVALUE: 0  
         UNITS: Bytes         SPARSE: NA  "
::= { eponQueueProfileEntry  16}

eponQueueProfileQ5Threshold OBJECT-TYPE 
	SYNTAX INTEGER (0..65535)
	ACCESS read-write
	STATUS mandatory
	DESCRIPTION
	    	"This object stores the relative threshold for the 5th 
		 Queue .
		 ALCATEL NOTE:
		 ACCESS: NA        usage: OPT
		 persistent: YES   INSRVMOD:YES
         RANGE:0..65535         DEFVALUE: 0  
         UNITS: Bytes         SPARSE: NA  "
::= { eponQueueProfileEntry  17}

eponQueueProfileQ6Threshold OBJECT-TYPE 
	SYNTAX INTEGER
	ACCESS read-write
	STATUS mandatory
	DESCRIPTION
	    	"This object stores the relative threshold for the 6th 
		 Queue.
		 ALCATEL NOTE:
		 ACCESS: NA        usage: OPT
		 persistent: YES   INSRVMOD:YES
         RANGE:0..65535          DEFVALUE: 0  
         UNITS: Bytes         SPARSE: NA  "
::= { eponQueueProfileEntry  18}

eponQueueProfileQ7Threshold OBJECT-TYPE 
	SYNTAX INTEGER (0..65535)
	ACCESS read-write
	STATUS mandatory
	DESCRIPTION
	    	"This object stores the relative threshold for the 7th 
		 Queue.
		 ALCATEL NOTE:
		 ACCESS: NA        usage: OPT
		 persistent: YES   INSRVMOD:YES
         RANGE:0..65535         DEFVALUE:0 
         UNITS: Bytes         SPARSE: NA  "
::= { eponQueueProfileEntry  19}

eponQueueProfileQ8Threshold OBJECT-TYPE 
	SYNTAX INTEGER (0..65535)
	ACCESS read-write
	STATUS mandatory
	DESCRIPTION
	    	"This object stores the relative threshold for the 8th 
		 Queue .
		 ALCATEL NOTE:
		 ACCESS: NA        usage: OPT
		 persistent: YES   INSRVMOD:YES
         RANGE:0..65535          DEFVALUE: 0  
         UNITS: Bytes         SPARSE: NA  "
::= { eponQueueProfileEntry  20}

eponQueueProfileIndexNext        OBJECT-TYPE
        	SYNTAX          AsamNextProfileIndex
        	ACCESS          read-only
        	STATUS          mandatory
        	DESCRIPTION     
        	"This object contains an appropriate value to be used for 
         		eponQueueProfileIndex when creating entries in the
         		eponQueueProfileTable. 
         		The value 0 indicates that no unassigned entries are available. To 
         		obtain the next index value for a new entry, the
        		 manager issues a management protocol retrieval operation to obtain the
         		current value of this object.  After each retrieval, the agent should
        		 modify the value to the next unassigned index. 
        		 ALCATEL NOTE:
		 ACCESS: NA        usage: NA
		 persistent: NA  INSRVMOD:NA
		 RANGE:NA          DEFVALUE: NA  
         UNITS: NA        SPARSE: NA  "

::= {eponProfilesGroup 2 }


eponQueueProfileMaxIndex        OBJECT-TYPE
      	SYNTAX            AsamMaxProfileIndex
      	ACCESS            read-only
     	 STATUS            mandatory
      	DESCRIPTION
            	"This object represents the maximum number of
            	eponQueueProfiles that can be created. The object
             	 eponQueueProfileIndexNext will have values ranging
                 from 0 to the value represented by this object.  
		         ALCATEL NOTE:
		 ACCESS: NA        usage: NA
		 persistent: NA  INSRVMOD:NA
		 RANGE:NA          DEFVALUE: NA  
         UNITS: NA       SPARSE: NA  "

::= {eponProfilesGroup 3 }


-- *********************************************
--
-- EPON ONT FILTER PROFILE TABLE
--
-- This table contains the classification and filter rules on an
-- LanEtherFilter physical UNI port or user VLAN Interface
--
-- 
-- *********************************************

eponOntFilterProfileTable OBJECT-TYPE
	SYNTAX	SEQUENCE OF EponOntFilterProfileEntry
	ACCESS	not-accessible
	STATUS	mandatory
	DESCRIPTION
		"This object contains a table for defining classfication
		and filter rules by operator. The max field for one rule could be 
		specified is 4.
		 ALCATEL NOTE:
             SUPPORT: YES   TABLESIZE: DEP"
::= { eponProfilesGroup 16 }

eponOntFilterProfileEntry OBJECT-TYPE
	SYNTAX 	EponOntFilterProfileEntry
	ACCESS	not-accessible
	STATUS	mandatory
	DESCRIPTION
		 "An entry in the eponOntFilterProfileTable. 
          Row creation : an entry is created  when operator creates OntFilter profile.
          Row deletion : an entry is created  when operator deletes OntFilter profile.
          ALCATEL NOTE:
             SUPPORT: YES"
	INDEX {eponOntFilterProfileIndex }
::= {eponOntFilterProfileTable 1}

EponOntFilterProfileEntry ::=
	SEQUENCE { 
		eponOntFilterProfileIndex		           AsamProfileIndex,
		eponOntFilterProfileName		           AsamProfileName,
		eponOntFilterProfileRefCount              AsamProfileRefCount,
		eponOntFilterProfileRowStatus 	           RowStatus,
		eponOntFilterProfileClassfierNum          INTEGER,
		eponOntFilterProfileClassfierFields1      EponTcClassfierFields,
		eponOntFilterProfileClassfierValue1       OCTET STRING (SIZE (16)),
		eponOntFilterProfileClassfierOperators1   EponTcClassfierOperators,	
		eponOntFilterProfileClassfierFields2      EponTcClassfierFields,
		eponOntFilterProfileClassfierValue2       OCTET STRING (SIZE (16)),
		eponOntFilterProfileClassfierOperators2   EponTcClassfierOperators,
		eponOntFilterProfileClassfierFields3      EponTcClassfierFields,
		eponOntFilterProfileClassfierValue3       OCTET STRING (SIZE (16)),
		eponOntFilterProfileClassfierOperators3   EponTcClassfierOperators,
		eponOntFilterProfileClassfierFields4      EponTcClassfierFields,
		eponOntFilterProfileClassfierValue4       OCTET STRING (SIZE (16)),
		eponOntFilterProfileClassfierOperators4   EponTcClassfierOperators
}

eponOntFilterProfileIndex OBJECT-TYPE 
	SYNTAX AsamProfileIndex
	ACCESS not-accessible
	STATUS mandatory
	DESCRIPTION
	    "This object is the index to the eponOntFilterProfileTable.
	    ALCATEL NOTE:
                 ACCESS:     NA       USAGE:      NA
                 PERSIST:    YES      INSRVMOD:   NO
                 RANGE:      NA       DEFVALUE:   NA
                 UNITS:      NA       SPARSE:     NA
"
::= { eponOntFilterProfileEntry 1}

eponOntFilterProfileName 	OBJECT-TYPE 
	SYNTAX	AsamProfileName
	ACCESS  read-write
	STATUS  mandatory
	DESCRIPTION
	    "The corresponding name for a given profile id.
        The name corresponding to the ProfileId must also be unique.
	    ALCATEL NOTE:
                 ACCESS:     NA       USAGE:      NA
                 PERSIST:    YES      INSRVMOD:   NO
                 RANGE:      NA       DEFVALUE:   NA
                 UNITS:      NA       SPARSE:     NA
                "
::= {eponOntFilterProfileEntry 2}

eponOntFilterProfileRefCount OBJECT-TYPE
	SYNTAX	AsamProfileRefCount
	ACCESS  read-only
	STATUS	mandatory
	DESCRIPTION
	" Indicates the number of entities using this profile. If the
          reference count is greater than 0, then this profile is 'in use',
          and may NOT be deleted. If the value is 0, then this profile is
          'not in use', and can be deleted.
          ALCATEL NOTE:
             ALCATEL NOTE:
                 ACCESS:     NA       USAGE:      NA
                 PERSIST:    NA     INSRVMOD:   NO
                 RANGE:      NA       DEFVALUE:   NA
                 UNITS:      NA       SPARSE:     NA "
::= { eponOntFilterProfileEntry  3}

eponOntFilterProfileRowStatus OBJECT-TYPE 
	SYNTAX	RowStatus
	ACCESS	read-write
	STATUS  mandatory
	DESCRIPTION
"This object is used to create a new row or delete an row.
	 ALCATEL NOTE:
		 ACCESS: NA        usage: MAND
         persistent: YES   INSRVMOD:YES
         RANGE:1,4,6       DEFVALUE: NA  
         UNITS: NA         SPARSE: NA  "
::= { eponOntFilterProfileEntry  4}

eponOntFilterProfileClassfierNum  OBJECT-TYPE 
	SYNTAX	INTEGER
	ACCESS	read-only
	STATUS  mandatory
	DESCRIPTION
		"This object is the filed  numbers used for this rule .
		ALCATEL NOTE:
		 ACCESS: NA        usage: NA
		 persistent: NA   INSRVMOD:YES
         RANGE:NA       DEFVALUE: NA  
         UNITS: NA         SPARSE: NA  "
::= { eponOntFilterProfileEntry  5}


eponOntFilterProfileClassfierFields1 OBJECT-TYPE
	SYNTAX	EponTcClassfierFields
	ACCESS	read-write
	STATUS	mandatory
	DESCRIPTION
		"The first Classfier field used for this rule. If the value is default(255),
     the eponOntFilterProfileClassfierValue1 value should be 65535.
		ALCATEL NOTE:
		 ACCESS: NA        usage: MAN
		persistent: YES   INSRVMOD:YES
         RANGE:NA       DEFVALUE: 255  
         UNITS: NA         SPARSE: NA  "

	::= { eponOntFilterProfileEntry  6 }

eponOntFilterProfileClassfierValue1	OBJECT-TYPE
		SYNTAX	OCTET STRING (SIZE (16))
		ACCESS  read-write
		STATUS	mandatory
		DESCRIPTION
			"The value for the fist Classfier field. If eponOntFilterProfileClassfierFields1 
			value is 255,The eponOntFilterProfileClassfierValue1 should be 65535.
  
	  ALCATEL NOTE:
		 ACCESS: NA        usage: MAN
		persistent: YES   INSRVMOD:YES
         RANGE:NA       DEFVALUE: NA  
         UNITS: NA         SPARSE: NA  "

	::= { eponOntFilterProfileEntry  7 }


eponOntFilterProfileClassfierOperators1 OBJECT-TYPE
	SYNTAX	EponTcClassfierOperators
	ACCESS	read-write
	STATUS	mandatory
	DESCRIPTION
		"The Classfier operator for the first field.   
		 ALCATEL NOTE:
		 ACCESS: NA        usage: MAN
		 persistent: YES   INSRVMOD:YES
         RANGE:NA       DEFVALUE: 255  
         UNITS: NA         SPARSE: NA  "
	::= { eponOntFilterProfileEntry  8 }
	
eponOntFilterProfileClassfierFields2 OBJECT-TYPE
	SYNTAX	EponTcClassfierFields
	ACCESS	read-write
	STATUS	mandatory
	DESCRIPTION
			"The second Classfier field used for this rule. If the value is default(255), 
			 the eponOntFilterProfileClassfierValue2 value should be 65535.
		ALCATEL NOTE:
		 ACCESS: NA        usage: OPT
		 persistent: YES   INSRVMOD:YES
         RANGE:NA       DEFVALUE: 255  
         UNITS: NA         SPARSE: NA  "
	::= { eponOntFilterProfileEntry  9 }

eponOntFilterProfileClassfierValue2	OBJECT-TYPE
		SYNTAX	OCTET STRING (SIZE (16))
		ACCESS  read-write
		STATUS	mandatory
		DESCRIPTION
			"The value for the second Classfier field. If eponOntFilterProfileClassfierFields2 
			value is 255,The eponOntFilterProfileClassfierValue2 should be 65535.
   
	  ALCATEL NOTE:
		 ACCESS: NA        usage: OPT
		 persistent: YES   INSRVMOD:YES
         RANGE:NA       DEFVALUE: NA  
         UNITS: NA         SPARSE: NA  "
		::= { eponOntFilterProfileEntry  10 }

eponOntFilterProfileClassfierOperators2 OBJECT-TYPE
	SYNTAX	EponTcClassfierOperators
	ACCESS	read-write
	STATUS	mandatory
	DESCRIPTION
		"The Classfier operator for the second field. 
  
		 ALCATEL NOTE:
		 ACCESS: NA        usage: OPT
		 persistent: YES   INSRVMOD:YES
         RANGE:NA       DEFVALUE: 255  
         UNITS: NA         SPARSE: NA  "
	::= { eponOntFilterProfileEntry  11 }
	
eponOntFilterProfileClassfierFields3 OBJECT-TYPE
	SYNTAX	EponTcClassfierFields
	ACCESS	read-write
	STATUS	mandatory
	DESCRIPTION
		"The third Classfier field used for this rule. If the value is default(255), 
		 the eponOntFilterProfileClassfierValue3 value should be 65535.
		ALCATEL NOTE:
		 ACCESS: NA        usage: OPT
		 persistent: YES   INSRVMOD:YES
         RANGE:NA       DEFVALUE: 255  
         UNITS: NA         SPARSE: NA  "
	::= { eponOntFilterProfileEntry  12 }

eponOntFilterProfileClassfierValue3	OBJECT-TYPE
		SYNTAX	OCTET STRING (SIZE (16))
		ACCESS  read-write
		STATUS	mandatory
		DESCRIPTION
		"The value for the third Classfier field.  If eponOntFilterProfileClassfierFields3 
		 value is 255,The eponOntFilterProfileClassfierValue3 should be 65535. 
	  ALCATEL NOTE:
		 ACCESS: NA        usage: OPT
		 persistent: YES   INSRVMOD:YES
         RANGE:NA       DEFVALUE: NA  
         UNITS: NA         SPARSE: NA  "
		::= { eponOntFilterProfileEntry  13 }

eponOntFilterProfileClassfierOperators3 OBJECT-TYPE
	SYNTAX	EponTcClassfierOperators
	ACCESS	read-write
	STATUS	mandatory
	DESCRIPTION
			"The Classfier operator for the third field.   
		 ALCATEL NOTE:
		 ACCESS: NA        usage: OPT
		 persistent: YES   INSRVMOD:YES
         RANGE:NA       DEFVALUE: 255  
         UNITS: NA         SPARSE: NA  "
	::= { eponOntFilterProfileEntry  14 }
	
eponOntFilterProfileClassfierFields4 OBJECT-TYPE
	SYNTAX	EponTcClassfierFields
	ACCESS	read-write
	STATUS	mandatory
	DESCRIPTION
		"The fourth Classfier field used for this rule. If the value is default(255), 
		 the eponOntFilterProfileClassfierValue4 value should be 65535.
		ALCATEL NOTE:
		 ACCESS: NA        usage: OPT
		 persistent: YES   INSRVMOD:YES
         RANGE:NA       DEFVALUE: 255  
         UNITS: NA         SPARSE: NA  "
	::= { eponOntFilterProfileEntry  15 }

eponOntFilterProfileClassfierValue4	OBJECT-TYPE
		SYNTAX	OCTET STRING (SIZE (16))
		ACCESS  read-write
		STATUS	mandatory
		DESCRIPTION
			"The value for the fourth Classfier field. If eponOntFilterProfileClassfierFields4 
			 value is 255,The eponOntFilterProfileClassfierValue4 should be 65535.
	  ALCATEL NOTE:
		 ACCESS: NA        usage: OPT
		 persistent: YES   INSRVMOD:YES
         RANGE:NA       DEFVALUE: NA  
         UNITS: NA         SPARSE: NA  "
		::= { eponOntFilterProfileEntry  16 }

eponOntFilterProfileClassfierOperators4 OBJECT-TYPE
	SYNTAX	EponTcClassfierOperators
	ACCESS	read-write
	STATUS	mandatory
	DESCRIPTION
		"The Classfier operator for the third field.   
		 ALCATEL NOTE:
		 ACCESS: NA        usage: OPT
		 persistent: YES   INSRVMOD:YES
         RANGE:NA       DEFVALUE: 255  
         UNITS: NA         SPARSE: NA  "
	::= { eponOntFilterProfileEntry  17 }



eponOntFilterProfileIndexNext        OBJECT-TYPE
        	SYNTAX          AsamNextProfileIndex
        	ACCESS          read-only
        	STATUS          mandatory
        	DESCRIPTION     
        	"This object contains an appropriate value to be used for 
         		eponTcProfileIndex when creating entries in the
         	  eponTcProfileTable. 
         		The value 0 indicates that no unassigned entries are available. To 
         		obtain the next index value for a new entry, the
        		 manager issues a management protocol retrieval operation to obtain the
         		current value of this object.  After each retrieval, the agent should
        		 modify the value to the next unassigned index. 
        		 ALCATEL NOTE:
		 ACCESS: NA        usage: NA
		 persistent: NA  INSRVMOD:NA
		 RANGE:NA          DEFVALUE: NA  
         UNITS: NA        SPARSE: NA  "
::= {eponProfilesGroup 5 }


eponOntFilterProfileMaxIndex        OBJECT-TYPE
      	SYNTAX            AsamMaxProfileIndex
      	ACCESS            read-only
     	 STATUS            mandatory
      	DESCRIPTION
         "This object represents the maximum number of
          eponTcProfileProfiles that can be created. The object
          eponTcProfileIndexNext will have values ranging
           from 0 to the value represented by this object. 
         ALCATEL NOTE:
		 ACCESS: NA        usage: NA
		 persistent: NA  INSRVMOD:NA
		 RANGE:NA          DEFVALUE: NA  
         UNITS: NA        SPARSE: NA  "
::= {eponProfilesGroup 6 }


-- *********************************************
--
-- EPON SIP Digit map PROFILE TABLE
--
-- This table contains the SIP digit map apply to an
-- ONU
--
-- 
-- *********************************************

eponSIPDigitMapProfileTable OBJECT-TYPE
	SYNTAX	SEQUENCE OF EponSIPDigitMapProfileEntry
	ACCESS	not-accessible
	STATUS	mandatory
	DESCRIPTION
		"This object contains a table for defining digit map
		by operator.
		 ALCATEL NOTE:
             SUPPORT: YES   TABLESIZE: DEP"
::= { eponProfilesGroup 10 }

eponSIPDigitMapProfileEntry OBJECT-TYPE
	SYNTAX 	EponSIPDigitMapProfileEntry
	ACCESS	not-accessible
	STATUS	mandatory
	DESCRIPTION
		 "An entry in the eponSIPDigitMapProfileTable. 
          Row creation : an entry is created  when operator creates SIP Digit Map profile.
          Row deletion : an entry is created  when operator deletes SIP Digit Map profile.
          ALCATEL NOTE:
             SUPPORT: YES"
	INDEX {eponSIPDigitMapProfileIndex,
               eponSIPDigitMapSubStrIndex }
::= {eponSIPDigitMapProfileTable 1}

EponSIPDigitMapProfileEntry ::=
	SEQUENCE { 
		eponSIPDigitMapProfileIndex		    AsamProfileIndex,
                eponSIPDigitMapSubStrIndex                  AsamProfileIndex,
		eponSIPDigitMapProfileName		    AsamProfileName,
		eponSIPDigitMapProfileRowStatus 	    RowStatus,
		eponSIPDigitMapProfileString                DisplayString (SIZE(0..256)),
                eponSIPDigitMapProfileRefCount              AsamProfileRefCount

}

eponSIPDigitMapProfileIndex OBJECT-TYPE 
	SYNTAX AsamProfileIndex
	ACCESS not-accessible
	STATUS mandatory
	DESCRIPTION
	    "This object is the index to the eponSIPDigitMapProfileTable.
	    ALCATEL NOTE:
                 ACCESS:     NA       USAGE:      NA
                 PERSIST:    YES      INSRVMOD:   NO
                 RANGE:      NA       DEFVALUE:   NA
                 UNITS:      NA       SPARSE:     NA
"
::= { eponSIPDigitMapProfileEntry 1}

eponSIPDigitMapSubStrIndex OBJECT-TYPE
        SYNTAX AsamProfileIndex
        ACCESS not-accessible
        STATUS  mandatory
        DESCRIPTION
            "This object is the sub string index to the eponSIPDigitMapProfileTable.
            ALCATEL NOTE:
                 ACCESS:     NA       USAGE:      NA
                 PERSIST:    YES      INSRVMOD:   NO
                 RANGE:      NA       DEFVALUE:   NA
                 UNITS:      NA       SPARSE:     NA
                "
::= {eponSIPDigitMapProfileEntry 2}

eponSIPDigitMapProfileName 	OBJECT-TYPE 
	SYNTAX	AsamProfileName
	ACCESS  read-write
	STATUS  mandatory
	DESCRIPTION
	    "The corresponding name for a given profile id.
        The name corresponding to the ProfileId must also be unique.
	    ALCATEL NOTE:
                 ACCESS:     NA       USAGE:      NA
                 PERSIST:    YES      INSRVMOD:   NO
                 RANGE:      NA       DEFVALUE:   NA
                 UNITS:      NA       SPARSE:     NA
                "
::= {eponSIPDigitMapProfileEntry 3}

eponSIPDigitMapProfileRowStatus OBJECT-TYPE 
	SYNTAX	RowStatus
	ACCESS	read-write
	STATUS  mandatory
	DESCRIPTION
"This object is used to create a new row or delete an row.
	 ALCATEL NOTE:
		 ACCESS: NA        usage: MAND
         persistent: YES   INSRVMOD:YES
         RANGE:1,4,6       DEFVALUE: NA  
         UNITS: NA         SPARSE: NA  "
::= { eponSIPDigitMapProfileEntry  4}

eponSIPDigitMapProfileString	OBJECT-TYPE
		SYNTAX	DisplayString (SIZE(0..256))
		ACCESS  read-write
		STATUS	mandatory
		DESCRIPTION
			"The SIP Digit Map string  
	  ALCATEL NOTE:
		 ACCESS: NA        usage: MAN
		persistent: YES   INSRVMOD:YES
         RANGE:NA       DEFVALUE: NA  
         UNITS: NA         SPARSE: NA  "

::= { eponSIPDigitMapProfileEntry  5 }

eponSIPDigitMapProfileRefCount OBJECT-TYPE
        SYNTAX  AsamProfileRefCount
        ACCESS  read-only        
        STATUS  mandatory        
        DESCRIPTION     
        " Indicates the number of entities using this profile. If the
          reference count is greater than 0, then this profile is 'in use',
          and may NOT be deleted. If the value is 0, then this profile is
          'not in use', and can be deleted.
          ALCATEL NOTE:          
             ALCATEL NOTE:       
                 ACCESS:     NA       USAGE:      NA
                 PERSIST:    NA     INSRVMOD:   NO
                 RANGE:      NA       DEFVALUE:   NA
                 UNITS:      NA       SPARSE:     NA "
::= { eponSIPDigitMapProfileEntry  6}



eponSIPDigitMapProfileIndexNext        OBJECT-TYPE
        	SYNTAX          AsamNextProfileIndex
        	ACCESS          read-only
        	STATUS          mandatory
        	DESCRIPTION     
        	"This object contains an appropriate value to be used for 
         		eponSIPDigitMapProfileIndex when creating entries in the
         	  eponSIPDigitMapProfileTable. 
         		The value 0 indicates that no unassigned entries are available. To 
         		obtain the next index value for a new entry, the
        		 manager issues a management protocol retrieval operation to obtain the
         		current value of this object.  After each retrieval, the agent should
        		 modify the value to the next unassigned index. 
        		 ALCATEL NOTE:
		 ACCESS: NA        usage: NA
		 persistent: NA  INSRVMOD:NA
		 RANGE:NA          DEFVALUE: NA  
         UNITS: NA        SPARSE: NA  "
::= {eponProfilesGroup 11 }


eponSIPDigitMapProfileMaxIndex        OBJECT-TYPE
      	SYNTAX            AsamMaxProfileIndex
      	ACCESS            read-only
     	 STATUS            mandatory
      	DESCRIPTION
         "This object represents the maximum number of
          eponSIPDigitMapProfileProfiles that can be created. The object
          eponSIPDigitMapProfileIndexNext will have values ranging
           from 0 to the value represented by this object. 
         ALCATEL NOTE:
		 ACCESS: NA        usage: NA
		 persistent: NA  INSRVMOD:NA
		 RANGE:NA          DEFVALUE: NA  
         UNITS: NA        SPARSE: NA  "
::= {eponProfilesGroup 12 }

-- *********************************************
--
-- EPON ONT IPV6 FILTER PROFILE TABLE
--
-- This table contains the classification and filter rules on an
-- LanEtherFilter physical UNI port or user VLAN Interface
--
-- 
-- *********************************************

eponOntIpv6FilterProfileTable OBJECT-TYPE
	SYNTAX	SEQUENCE OF EponOntIpv6FilterProfileEntry
	ACCESS	not-accessible
	STATUS	mandatory
	DESCRIPTION
		"This object contains a table for defining classfication
		and filter rules by operator. The max field for one rule could be 
		specified is 4.
		 ALCATEL NOTE:
             SUPPORT: YES   TABLESIZE: DEP"
::= { eponProfilesGroup 26 }

eponOntIpv6FilterProfileEntry OBJECT-TYPE
	SYNTAX 	EponOntIpv6FilterProfileEntry
	ACCESS	not-accessible
	STATUS	mandatory
	DESCRIPTION
		 "An entry in the eponOntFilterProfileTable. 
          Row creation : an entry is created  when operator creates OntIpv6Filter profile.
          Row deletion : an entry is created  when operator deletes OntIpv6Filter profile.
          ALCATEL NOTE:
             SUPPORT: YES"
	INDEX {eponOntIpv6FilterProfileIndex }
::= {eponOntIpv6FilterProfileTable 1}

EponOntIpv6FilterProfileEntry ::=
	SEQUENCE { 
		eponOntIpv6FilterProfileIndex		              AsamProfileIndex,
		eponOntIpv6FilterProfileName		              AsamProfileName,
		eponOntIpv6FilterProfileRefCount              AsamProfileRefCount,
		eponOntIpv6FilterProfileRowStatus 	          RowStatus,
		eponOntIpv6FilterProfileClassfierNum          INTEGER,
		eponOntIpv6FilterProfileClassfierFields1      EponTcClassfierFields,
		eponOntIpv6FilterProfileClassfierValue1       OCTET STRING (SIZE (16)),
		eponOntIpv6FilterProfileClassfierOperators1   EponTcClassfierOperators,	
		eponOntIpv6FilterProfileClassfierFields2      EponTcClassfierFields,
		eponOntIpv6FilterProfileClassfierValue2       OCTET STRING (SIZE (16)),
		eponOntIpv6FilterProfileClassfierOperators2   EponTcClassfierOperators,
		eponOntIpv6FilterProfileClassfierFields3      EponTcClassfierFields,
		eponOntIpv6FilterProfileClassfierValue3       OCTET STRING (SIZE (16)),
		eponOntIpv6FilterProfileClassfierOperators3   EponTcClassfierOperators,
		eponOntIpv6FilterProfileClassfierFields4      EponTcClassfierFields,
		eponOntIpv6FilterProfileClassfierValue4       OCTET STRING (SIZE (16)),
		eponOntIpv6FilterProfileClassfierOperators4   EponTcClassfierOperators
}

eponOntIpv6FilterProfileIndex OBJECT-TYPE 
	SYNTAX AsamProfileIndex
	ACCESS not-accessible
	STATUS mandatory
	DESCRIPTION
	    "This object is the index to the eponOntIpv6FilterProfileTable.
	    ALCATEL NOTE:
                 ACCESS:     NA       USAGE:      NA
                 PERSIST:    YES      INSRVMOD:   NO
                 RANGE:      NA       DEFVALUE:   NA
                 UNITS:      NA       SPARSE:     NA
"
::= { eponOntIpv6FilterProfileEntry 1}

eponOntIpv6FilterProfileName 	OBJECT-TYPE 
	SYNTAX	AsamProfileName
	ACCESS  read-write
	STATUS  mandatory
	DESCRIPTION
	    "The corresponding name for a given profile id.
        The name corresponding to the ProfileId must also be unique.
	    ALCATEL NOTE:
                 ACCESS:     NA       USAGE:      NA
                 PERSIST:    YES      INSRVMOD:   NO
                 RANGE:      NA       DEFVALUE:   NA
                 UNITS:      NA       SPARSE:     NA
                "
::= {eponOntIpv6FilterProfileEntry 2}

eponOntIpv6FilterProfileRefCount OBJECT-TYPE
	SYNTAX	AsamProfileRefCount
	ACCESS  read-only
	STATUS	mandatory
	DESCRIPTION
	" Indicates the number of entities using this profile. If the
          reference count is greater than 0, then this profile is 'in use',
          and may NOT be deleted. If the value is 0, then this profile is
          'not in use', and can be deleted.
          ALCATEL NOTE:
             ALCATEL NOTE:
                 ACCESS:     NA       USAGE:      NA
                 PERSIST:    NA     INSRVMOD:   NO
                 RANGE:      NA       DEFVALUE:   NA
                 UNITS:      NA       SPARSE:     NA "
::= { eponOntIpv6FilterProfileEntry  3}

eponOntIpv6FilterProfileRowStatus OBJECT-TYPE 
	SYNTAX	RowStatus
	ACCESS	read-write
	STATUS  mandatory
	DESCRIPTION
"This object is used to create a new row or delete an row.
	 ALCATEL NOTE:
		 ACCESS: NA        usage: MAND
         persistent: YES   INSRVMOD:YES
         RANGE:1,4,6       DEFVALUE: NA  
         UNITS: NA         SPARSE: NA  "
::= { eponOntIpv6FilterProfileEntry  4}

eponOntIpv6FilterProfileClassfierNum  OBJECT-TYPE 
	SYNTAX	INTEGER
	ACCESS	read-only
	STATUS  mandatory
	DESCRIPTION
		"This object is the filed  numbers used for this rule .
		ALCATEL NOTE:
		 ACCESS: NA        usage: NA
		 persistent: NA   INSRVMOD:YES
         RANGE:NA       DEFVALUE: NA  
         UNITS: NA         SPARSE: NA  "
::= { eponOntIpv6FilterProfileEntry  5}


eponOntIpv6FilterProfileClassfierFields1 OBJECT-TYPE
	SYNTAX	EponTcClassfierFields
	ACCESS	read-write
	STATUS	mandatory
	DESCRIPTION
		"The first Classfier field used for this rule.
		ALCATEL NOTE:
		 ACCESS: NA        usage: MAN
		persistent: YES   INSRVMOD:YES
         RANGE:NA       DEFVALUE: NA  
         UNITS: NA         SPARSE: NA  "

	::= { eponOntIpv6FilterProfileEntry  6 }

eponOntIpv6FilterProfileClassfierValue1	OBJECT-TYPE
		SYNTAX	OCTET STRING (SIZE (16))
		ACCESS  read-write
		STATUS	mandatory
		DESCRIPTION
			"The value for the fist Classfier field.   
	  ALCATEL NOTE:
		 ACCESS: NA        usage: MAN
		persistent: YES   INSRVMOD:YES
         RANGE:NA       DEFVALUE: NA  
         UNITS: NA         SPARSE: NA  "

	::= { eponOntIpv6FilterProfileEntry  7 }

eponOntIpv6FilterProfileClassfierOperators1 OBJECT-TYPE
	SYNTAX	EponTcClassfierOperators
	ACCESS	read-write
	STATUS	mandatory
	DESCRIPTION
		"The Classfier operator for the first field.   
		 ALCATEL NOTE:
		 ACCESS: NA        usage: MAN
		 persistent: YES   INSRVMOD:YES
         RANGE:NA       DEFVALUE: NA  
         UNITS: NA         SPARSE: NA  "
	::= { eponOntIpv6FilterProfileEntry  8 }
	
eponOntIpv6FilterProfileClassfierFields2 OBJECT-TYPE
	SYNTAX	EponTcClassfierFields
	ACCESS	read-write
	STATUS	mandatory
	DESCRIPTION
			"The second Classfier field used for this rule.
		ALCATEL NOTE:
		 ACCESS: NA        usage: OPT
		 persistent: YES   INSRVMOD:YES
         RANGE:NA       DEFVALUE: NA  
         UNITS: NA         SPARSE: NA  "
	::= { eponOntIpv6FilterProfileEntry  9 }

eponOntIpv6FilterProfileClassfierValue2	OBJECT-TYPE
		SYNTAX	OCTET STRING (SIZE (16))
		ACCESS  read-write
		STATUS	mandatory
		DESCRIPTION
			"The value for the second Classfier field.   
	  ALCATEL NOTE:
		 ACCESS: NA        usage: OPT
		 persistent: YES   INSRVMOD:YES
         RANGE:NA       DEFVALUE: NA  
         UNITS: NA         SPARSE: NA  "
		::= { eponOntIpv6FilterProfileEntry  10 }

eponOntIpv6FilterProfileClassfierOperators2 OBJECT-TYPE
	SYNTAX	EponTcClassfierOperators
	ACCESS	read-write
	STATUS	mandatory
	DESCRIPTION
		"The Classfier operator for the second field.   
		 ALCATEL NOTE:
		 ACCESS: NA        usage: OPT
		 persistent: YES   INSRVMOD:YES
         RANGE:NA       DEFVALUE: NA  
         UNITS: NA         SPARSE: NA  "
	::= { eponOntIpv6FilterProfileEntry  11 }
	
eponOntIpv6FilterProfileClassfierFields3 OBJECT-TYPE
	SYNTAX	EponTcClassfierFields
	ACCESS	read-write
	STATUS	mandatory
	DESCRIPTION
		"The third Classfier field used for this rule.
		ALCATEL NOTE:
		 ACCESS: NA        usage: OPT
		 persistent: YES   INSRVMOD:YES
         RANGE:NA       DEFVALUE: NA  
         UNITS: NA         SPARSE: NA  "
	::= { eponOntIpv6FilterProfileEntry  12 }

eponOntIpv6FilterProfileClassfierValue3	OBJECT-TYPE
		SYNTAX	OCTET STRING (SIZE (16))
		ACCESS  read-write
		STATUS	mandatory
		DESCRIPTION
		"The value for the third Classfier field.   
	  ALCATEL NOTE:
		 ACCESS: NA        usage: OPT
		 persistent: YES   INSRVMOD:YES
         RANGE:NA       DEFVALUE: NA  
         UNITS: NA         SPARSE: NA  "
		::= { eponOntIpv6FilterProfileEntry  13 }

eponOntIpv6FilterProfileClassfierOperators3 OBJECT-TYPE
	SYNTAX	EponTcClassfierOperators
	ACCESS	read-write
	STATUS	mandatory
	DESCRIPTION
			"The Classfier operator for the third field.   
		 ALCATEL NOTE:
		 ACCESS: NA        usage: OPT
		 persistent: YES   INSRVMOD:YES
         RANGE:NA       DEFVALUE: NA  
         UNITS: NA         SPARSE: NA  "
	::= { eponOntIpv6FilterProfileEntry  14 }
	
eponOntIpv6FilterProfileClassfierFields4 OBJECT-TYPE
	SYNTAX	EponTcClassfierFields
	ACCESS	read-write
	STATUS	mandatory
	DESCRIPTION
		"The fourth Classfier field used for this rule.
		ALCATEL NOTE:
		 ACCESS: NA        usage: OPT
		 persistent: YES   INSRVMOD:YES
         RANGE:NA       DEFVALUE: NA  
         UNITS: NA         SPARSE: NA  "
	::= { eponOntIpv6FilterProfileEntry  15 }

eponOntIpv6FilterProfileClassfierValue4	OBJECT-TYPE
		SYNTAX	OCTET STRING (SIZE (16))
		ACCESS  read-write
		STATUS	mandatory
		DESCRIPTION
			"The value for the fourth Classfier field.   
	  ALCATEL NOTE:
		 ACCESS: NA        usage: OPT
		 persistent: YES   INSRVMOD:YES
         RANGE:NA       DEFVALUE: NA  
         UNITS: NA         SPARSE: NA  "
		::= { eponOntIpv6FilterProfileEntry  16 }

eponOntIpv6FilterProfileClassfierOperators4 OBJECT-TYPE
	SYNTAX	EponTcClassfierOperators
	ACCESS	read-write
	STATUS	mandatory
	DESCRIPTION
		"The Classfier operator for the third field.   
		 ALCATEL NOTE:
		 ACCESS: NA        usage: OPT
		 persistent: YES   INSRVMOD:YES
         RANGE:NA       DEFVALUE: NA  
         UNITS: NA         SPARSE: NA  "
	::= { eponOntIpv6FilterProfileEntry  17 }
	
eponOntIpv6FilterProfileIndexNext        OBJECT-TYPE
        	SYNTAX          AsamNextProfileIndex
        	ACCESS          read-only
        	STATUS          mandatory
        	DESCRIPTION     
        	"This object contains an appropriate value to be used for 
         		eponTcProfileIndex when creating entries in the
         	  eponTcProfileTable. 
         		The value 0 indicates that no unassigned entries are available. To 
         		obtain the next index value for a new entry, the
        		 manager issues a management protocol retrieval operation to obtain the
         		current value of this object.  After each retrieval, the agent should
        		 modify the value to the next unassigned index. 
        		 ALCATEL NOTE:
		 ACCESS: NA        usage: NA
		 persistent: NA  INSRVMOD:NA
		 RANGE:NA          DEFVALUE: NA  
         UNITS: NA        SPARSE: NA  "
::= {eponProfilesGroup 27 }

eponOntIpv6FilterProfileMaxIndex        OBJECT-TYPE
      	SYNTAX            AsamMaxProfileIndex
      	ACCESS            read-only
     	 STATUS            mandatory
      	DESCRIPTION
         "This object represents the maximum number of
          eponTcProfileProfiles that can be created. The object
          eponTcProfileIndexNext will have values ranging
           from 0 to the value represented by this object. 
         ALCATEL NOTE:
		 ACCESS: NA        usage: NA
		 persistent: NA  INSRVMOD:NA
		 RANGE:NA          DEFVALUE: NA  
         UNITS: NA        SPARSE: NA  "
::= {eponProfilesGroup 28 }	

-- *********************************************
--
-- EPON ONU Alarm ID Ctrl PROFILE TABLE
--
-- This table control the Alarm IDs should be reported by the EPON ONU
--
--
-- 
-- *********************************************

eponONUAlarmIDCtrlProfileTable OBJECT-TYPE
	SYNTAX	SEQUENCE OF EponONUAlarmIDCtrlProfileEntry
	ACCESS	not-accessible
	STATUS	mandatory
	DESCRIPTION
		"This object contains a table for defining the Alarm IDs should be
		reported by the EPON ONU.
		 ALCATEL NOTE:
             SUPPORT: YES   TABLESIZE: DEP"
::= { eponProfilesGroup 29 }

eponONUAlarmIDCtrlProfileEntry OBJECT-TYPE
	SYNTAX 	EponONUAlarmIDCtrlProfileEntry
	ACCESS	not-accessible
	STATUS	mandatory
	DESCRIPTION
		 "An entry in the eponONUAlarmIDCtrlProfileTable. 
          Row creation : an entry is created  when operator creates EPON ONU Alarm ID Ctrl profile.
          Row deletion : an entry is created  when operator deletes EPON ONU Alarm ID Ctrl profile.
          ALCATEL NOTE:
             SUPPORT: YES"
	INDEX {eponONUAlarmIDCtrlProfileIndex}
::= {eponONUAlarmIDCtrlProfileTable 1}

EponONUAlarmIDCtrlProfileEntry ::=
	SEQUENCE { 
		eponONUAlarmIDCtrlProfileIndex		    AsamProfileIndex,
		eponONUAlarmIDCtrlProfileName		    AsamProfileName,
		eponONUAlarmIDCtrlProfileRowStatus 	    RowStatus,
		eponONUAlarmIDCtrlProfileString                OCTET STRING (SIZE(0..16)),
                eponONUAlarmIDCtrlProfileRefCount              AsamProfileRefCount
}

eponONUAlarmIDCtrlProfileIndex OBJECT-TYPE 
	SYNTAX AsamProfileIndex
	ACCESS not-accessible
	STATUS mandatory
	DESCRIPTION
	    "This object is the index to the eponONUAlarmIDCtrlProfileTable.
	    ALCATEL NOTE:
                 ACCESS:     NA       USAGE:      NA
                 PERSIST:    YES      INSRVMOD:   NO
                 RANGE:      NA       DEFVALUE:   NA
                 UNITS:      NA       SPARSE:     NA
"
::= { eponONUAlarmIDCtrlProfileEntry 1}

eponONUAlarmIDCtrlProfileName 	OBJECT-TYPE 
	SYNTAX	AsamProfileName
	ACCESS  read-write
	STATUS  mandatory
	DESCRIPTION
	    "The corresponding name for a given profile id.
        The name corresponding to the ProfileId must also be unique.
	    ALCATEL NOTE:
                 ACCESS:     NA       USAGE:      NA
                 PERSIST:    YES      INSRVMOD:   NO
                 RANGE:      NA       DEFVALUE:   NA
                 UNITS:      NA       SPARSE:     NA
                "
::= {eponONUAlarmIDCtrlProfileEntry 2}

eponONUAlarmIDCtrlProfileRowStatus OBJECT-TYPE 
	SYNTAX	RowStatus
	ACCESS	read-write
	STATUS  mandatory
	DESCRIPTION
"This object is used to create a new row or delete an row.
	 ALCATEL NOTE:
		 ACCESS: NA        usage: MAND
         persistent: YES   INSRVMOD:YES
         RANGE:1,4,6       DEFVALUE: NA  
         UNITS: NA         SPARSE: NA  "
::= { eponONUAlarmIDCtrlProfileEntry  3}

eponONUAlarmIDCtrlProfileString	OBJECT-TYPE
		SYNTAX	OCTET STRING (SIZE(0..16))
		ACCESS  read-write
		STATUS	mandatory
		DESCRIPTION
			"The EPON ONU Alarm ID Ctrl string
			BITMAP for the ONU alarm control
			currently following bits are defined, other bits are reserved.
			BIT  Alarmname                  AlarmID
			0    EquipmentAlarm             0x0001
			1    PowerAlarm                 0x0002
			2    BatteryMissing             0x0003
			3    BatteryFailure             0x0004
			4    BatteryVoltLow             0x0005
			5    PhysicalIntrusionAlarm     0x0006
			6    ONUSelfTestFailure         0x0007
			7    ONUTempHighAlarm           0x0009
			8    ONUTempLowAlarm            0x000A
			9    IADConnectionFailure       0x000B
			10   PON_IF Switch              0x000C

			11   RXPowerHighAlarm           0x0101
			12   RXPowerLowAlarm            0x0102
			13   TXPowerHighAlarm           0x0103
			14   TXPowerLowAlarm            0x0104
			15   TXBiasHighAlarm            0x0105
			16   TXBiasLowAlarm             0x0106
			17   VccHighAlarm               0x0107
			18   VccLowAlarm                0x0108
			19   TempHighAlarm              0x0109
			20   TempLowAlarm               0x010A
			21   RXPowerHighWarning         0x010B
			22   RXPowerLowWarning          0x010C
			23   TXPowerHighWarning         0x010D
			24   TXPowerLowWarning          0x010E
			25   TXBiasHighWarning          0x010F
			26   TXBiasLowWarning           0x0110
			27   VccHighWarning             0x0111
			28   VccLowWarning              0x0112
			29   TempHighWarning            0x0113
			30   TempLowWarning             0x0114
			
			31   EthPortAutoNegFailure      0x0301
			32   EthPortLOS                 0x0302
			33   EthPortFailure             0x0303
			34   EthPortLoopback            0x0303
			35   EthPortCongestion          0x0303
			
			36   POTSPortFailure            0x0401
			
			37   E1PortFailure              0x0501
			38   E1TimingUnlock             0x0502
			39   E1 LOS                     0x0503

 	         1 - ON    0 - OFF
                  ASAM MIB convention, the bitmap shall function as follows:
                  MSB                                LSB
                  byte 0 :  7  6  5  4  3  2  1  0
                  byte 1 : 15 14 13 12 11 10  9  8
                  byte 2 : 23 22 21 20 19 18 17 16 
                  byte 3 : 31 30 29 28 27 26 25 24
                  byte 4 : 39 38 37 36 35 34 33 32
                  byte 5 : 47 46 45 44 43 42 41 40
                  byte 6 : 55 54 53 52 51 50 49 48
                  byte 7 : 63 62 61 60 59 58 57 56
                  ... ... ... ... ... ... ... ...

 	         			  
	  ALCATEL NOTE:
		 ACCESS: NA        usage: MAN
		persistent: YES   INSRVMOD:YES
         RANGE:NA       DEFVALUE: NA  
         UNITS: NA         SPARSE: NA  "

::= { eponONUAlarmIDCtrlProfileEntry  4 }

eponONUAlarmIDCtrlProfileRefCount OBJECT-TYPE
        SYNTAX  AsamProfileRefCount
        ACCESS  read-only        
        STATUS  mandatory        
        DESCRIPTION     
        " Indicates the number of entities using this profile. If the
          reference count is greater than 0, then this profile is 'in use',
          and may NOT be deleted or modified. If the value is 0, then this profile is
          'not in use', and can be deleted.
          ALCATEL NOTE:          
             ALCATEL NOTE:       
                 ACCESS:     NA       USAGE:      NA
                 PERSIST:    NA     INSRVMOD:   NO
                 RANGE:      NA       DEFVALUE:   NA
                 UNITS:      NA       SPARSE:     NA "
::= { eponONUAlarmIDCtrlProfileEntry  5}

eponONUAlarmIDCtrlProfileIndexNext        OBJECT-TYPE
        	SYNTAX          AsamNextProfileIndex
        	ACCESS          read-only
        	STATUS          mandatory
        	DESCRIPTION     
        	"This object contains an appropriate value to be used for 
         		eponONUAlarmIDCtrlProfileIndex when creating entries in the
         	  eponONUAlarmIDCtrlProfileTable. 
         		The value 0 indicates that no unassigned entries are available. To 
         		obtain the next index value for a new entry, the
        		 manager issues a management protocol retrieval operation to obtain the
         		current value of this object.  After each retrieval, the agent should
        		 modify the value to the next unassigned index. 
        		 ALCATEL NOTE:
		 ACCESS: NA        usage: NA
		 persistent: NA  INSRVMOD:NA
		 RANGE:NA          DEFVALUE: NA  
         UNITS: NA        SPARSE: NA  "
::= {eponProfilesGroup 30 }


eponONUAlarmIDCtrlProfileMaxIndex        OBJECT-TYPE
      	SYNTAX            AsamMaxProfileIndex
      	ACCESS            read-only
     	 STATUS            mandatory
      	DESCRIPTION
         "This object represents the maximum number of
          eponONUAlarmIDCtrlProfileProfiles that can be created. The object
          eponONUAlarmIDCtrlProfileIndexNext will have values ranging
           from 0 to the value represented by this object. 
         ALCATEL NOTE:
		 ACCESS: NA        usage: NA
		 persistent: NA  INSRVMOD:NA
		 RANGE:NA          DEFVALUE: NA  
         UNITS: NA        SPARSE: NA  "
::= {eponProfilesGroup 31 }

-- eponONUAlarmCtrlProfile name mapping table

eponONUAlarmIDCtrlProfileMappingTable OBJECT-TYPE
	SYNTAX	SEQUENCE OF EponONUAlarmIDCtrlProfileMappingEntry
	ACCESS	not-accessible
	STATUS	mandatory
	DESCRIPTION
		"This object contains a table for Query ont AlarmIDCtrlProfile id by name "
::= { eponProfilesGroup 32 }

eponONUAlarmIDCtrlProfileMappingEntry OBJECT-TYPE
	SYNTAX 	EponONUAlarmIDCtrlProfileMappingEntry
	ACCESS	not-accessible
	STATUS	mandatory
	DESCRIPTION
		 "An entry in the EponONUAlarmIDCtrlProfileMappingTable. 
          Row creation : an entry is created, when a eponONUAlarmIDCtrlProfileEntry is created.
          Row deletion : an entry is deleted  when operator deletes a EPON ONU Alarm ID Ctrl profile.
          ALCATEL NOTE:
             SUPPORT: YES"
	INDEX {eponONUAlarmIDCtrlProfileMappingName }
::= {eponONUAlarmIDCtrlProfileMappingTable  1}

EponONUAlarmIDCtrlProfileMappingEntry ::=
    SEQUENCE { 
		eponONUAlarmIDCtrlProfileMappingName AsamProfileName,
	        eponONUAlarmIDCtrlProfileMappingIndex   AsamProfileIndex
}

eponONUAlarmIDCtrlProfileMappingName OBJECT-TYPE 
	SYNTAX AsamProfileName
	ACCESS not-accessible
	STATUS mandatory
	DESCRIPTION
	    "This object is the index to the eponONUAlarmIDCtrlProfileMappingTable. A text string containing the name of the profile. string length: 1 to 32." 
::= { eponONUAlarmIDCtrlProfileMappingEntry 1}

eponONUAlarmIDCtrlProfileMappingIndex 	OBJECT-TYPE 
	SYNTAX	INTEGER
	ACCESS  read-only
	STATUS  mandatory
	DESCRIPTION
	    "The profile id corresponding to the ProfileName also be unique. index of the profile.
	    ALCATEL NOTE:
                 ACCESS:     NA       USAGE:      NA
                 PERSIST:    NO      INSRVMOD:   NO
                 RANGE:      1..250       DEFVALUE:   NA
                 UNITS:      NA       SPARSE:     NA
                "
::= {eponONUAlarmIDCtrlProfileMappingEntry 2}

-- *********************************************
--
-- EPON OLT PON Performance TABLE
--
-- Table of number of previous statistics intervals for the traffic on a 
-- OLT PON port
--
-- 
-- *********************************************

eponOLTPonPerfInfoTable     OBJECT-TYPE 
        SYNTAX    SEQUENCE OF EponOLTPonPerfInfoEntry 
        ACCESS    not-accessible 
        STATUS    mandatory 
        DESCRIPTION 
            "Table of number of previous statistics intervals for the traffic on a 
            OLT PON interface.  
            ALCATEL NOTE:
             SUPPORT: YES   TABLESIZE: DEP"
::= {eponStatisticsGroup 1 } 

eponOLTPonPerfInfoEntry OBJECT-TYPE 
        SYNTAX    EponOLTPonPerfInfoEntry 
        ACCESS    not-accessible 
        STATUS    mandatory 
        DESCRIPTION 
             "An entry in theeponOLTPonPerfInfoTable . 
          Row creation : an entry is created by the system when OLT pon level statistics enable. 
          Row creation : an entry is created by the system when OLT pon level statistics enable. 
            ALCATEL NOTE:
             SUPPORT: YES"    
INDEX   { eponPonConfigIfIndex } 
::= { eponOLTPonPerfInfoTable 1 } 

EponOLTPonPerfInfoEntry ::= 
       SEQUENCE{ 
                 eponOLTPonPerfInfo15MinValidIntervals    INTEGER, 
                 eponOLTPonPerfInfo1DayValidIntervals     INTEGER 
                }    
                
    
eponOLTPonPerfInfo15MinValidIntervals OBJECT-TYPE 
        SYNTAX    INTEGER 
        ACCESS    read-only 
        STATUS    mandatory 
        DESCRIPTION 
           	"Number of previous 15 minutes intervals
             ALCATEL NOTE:
                 ACCESS:     NA       USAGE:      NA
                 PERSIST:    NO       INSRVMOD:   NO
                 RANGE:      NA       DEFVALUE:   0
                 UNITS:      NA       SPARSE:     NA
                 DESCR:      NA"
        ::= { eponOLTPonPerfInfoEntry 1 } 
        
eponOLTPonPerfInfo1DayValidIntervals OBJECT-TYPE 
        SYNTAX    INTEGER 
        ACCESS     read-only 
        STATUS    mandatory 
        DESCRIPTION 
           "Number of previous 1 day intervals
             ALCATEL NOTE:
                 ACCESS:     NA       USAGE:      NA
                 PERSIST:    NO       INSRVMOD:   NO
                 RANGE:      NA       DEFVALUE:   0
                 UNITS:      NA       SPARSE:     NA
                 DESCR:      NA"
        ::= { eponOLTPonPerfInfoEntry 2 }  
        
-- *********************************************

-- EPON PON OLT PERFORMANCE TABLE
--
-- This table contains current 15 min performance counters specific to
-- a specific PON port on OLT side. 

-- *********************************************

eponOLTPonCurrent15MinIntervalTable  OBJECT-TYPE
	SYNTAX SEQUENCE OF EponOLTPonCurrent15MinIntervalEntry
	ACCESS	not-accessible
	STATUS	mandatory   
  DESCRIPTION 
	 "15 Minutes current statistics for pon interface.
	 ALCATEL NOTE:
             SUPPORT: YES   TABLESIZE: DEP"	
 ::= { eponStatisticsGroup 2 }                                                  

eponOLTPonCurrent15MinIntervalEntry  OBJECT-TYPE
	SYNTAX 	EponOLTPonCurrent15MinIntervalEntry
	ACCESS	not-accessible
	STATUS	mandatory  
     DESCRIPTION
         "Table entry for the current 15 minutes statistics counters for OLT pon interface.
          Row creation : an entry is created by the system when this pon interfaces statistics enabled.
          Row deletion :an entry is created by the system when this pon interfaces statistics disabled.
           ALCATEL NOTE:
             SUPPORT: YES"
	INDEX	{eponPonConfigIfIndex }
	::= { eponOLTPonCurrent15MinIntervalTable 1 }

EponOLTPonCurrent15MinIntervalEntry ::= SEQUENCE { 
	    eponOLTPonCurrent15MinIntervalTimeElapsed                INTEGER,                
	    eponOLTPonCurrent15MinIntervalTimeMeasured               INTEGER, 
        eponOLTPonCurrent15MinIntervalOctetsTransUp		         OCTET STRING (SIZE (8)),
        eponOLTPonCurrent15MinIntervalTotalFramesTransUp	     OCTET STRING (SIZE (8)),
        eponOLTPonCurrent15MinIntervalFirstSegOctetFramesUp      OCTET STRING (SIZE (8)),
        eponOLTPonCurrent15MinIntervalSecondSegOctetFramesUp     OCTET STRING (SIZE (8)),
        eponOLTPonCurrent15MinIntervalThirdSegOctetFramesUp      OCTET STRING (SIZE (8)),
        eponOLTPonCurrent15MinIntervalFourthSegOctetFramesUp     OCTET STRING (SIZE (8)),
        eponOLTPonCurrent15MinIntervalFifthSegOctetFramesUp      OCTET STRING (SIZE (8)),
        eponOLTPonCurrent15MinIntervalSixthSegOctetFramesUp      OCTET STRING (SIZE (8)),
        eponOLTPonCurrent15MinIntervalLastSegOctetFramesUp       OCTET STRING (SIZE (8)),
        eponOLTPonCurrent15MinIntervalOctetsTransDn		         OCTET STRING (SIZE (8)),
        eponOLTPonCurrent15MinIntervalTotalFramesTransDn	     OCTET STRING (SIZE (8)),
        eponOLTPonCurrent15MinIntervalFirstSegOctetFramesDn      OCTET STRING (SIZE (8)),
        eponOLTPonCurrent15MinIntervalSecondSegOctetFramesDn     OCTET STRING (SIZE (8)),
        eponOLTPonCurrent15MinIntervalThirdSegOctetFramesDn      OCTET STRING (SIZE (8)),
        eponOLTPonCurrent15MinIntervalFourthSegOctetFramesDn     OCTET STRING (SIZE (8)),
        eponOLTPonCurrent15MinIntervalFifthSegOctetFramesDn      OCTET STRING (SIZE (8)),
        eponOLTPonCurrent15MinIntervalSixthSegOctetFramesDn      OCTET STRING (SIZE (8)),
        eponOLTPonCurrent15MinIntervalLastSegOctetFramesDn       OCTET STRING (SIZE (8)),
        eponOLTPonCurrent15MinIntervalCRCErrorframe              OCTET STRING (SIZE (8)),
        eponOLTPonCurrent15MinIntervalUndersizeframesUp          OCTET STRING (SIZE (8)),
        eponOLTPonCurrent15MinIntervalUndersizeframesDn          OCTET STRING (SIZE (8)),
        eponOLTPonCurrent15MinIntervalOversizeframesUp           OCTET STRING (SIZE (8)),
        eponOLTPonCurrent15MinIntervalOversizeframesDn           OCTET STRING (SIZE (8)),
        eponOLTPonCurrent15MinIntervalErrorframesUp              OCTET STRING (SIZE (8)),
        eponOLTPonCurrent15MinIntervalErrorframesDn              OCTET STRING (SIZE (8)),
        eponOLTPonCurrent15MinIntervalDiscardframesUP            OCTET STRING (SIZE (8)),
        eponOLTPonCurrent15MinIntervalDiscardframesDn            OCTET STRING (SIZE (8)),
        eponOLTPonCurrent15MinIntervalUcastframesUP              OCTET STRING (SIZE (8)),
        eponOLTPonCurrent15MinIntervalUcastframesDn              OCTET STRING (SIZE (8)),
        eponOLTPonCurrent15MinIntervalMulticastframesUp          OCTET STRING (SIZE (8)),
        eponOLTPonCurrent15MinIntervalMulticastframesDn          OCTET STRING (SIZE (8)),
        eponOLTPonCurrent15MinIntervalBroardcastFramesUp         OCTET STRING (SIZE (8)),
        eponOLTPonCurrent15MinIntervalBroardcastFramesDn         OCTET STRING (SIZE (8)),
        eponOLTPonCurrent15MinIntervalDropEventsUP                   OCTET STRING (SIZE (8)),
        eponOLTPonCurrent15MinIntervalDropEventsDn                    OCTET STRING (SIZE (8)),
        eponOLTPonCurrent15MinIntervalFragmentsUP                     OCTET STRING (SIZE (8)),
        eponOLTPonCurrent15MinIntervalFragmentsDn                     OCTET STRING (SIZE (8)),
        eponOLTPonCurrent15MinIntervalJabberFramesUP               OCTET STRING (SIZE (8)),
        eponOLTPonCurrent15MinIntervalJabberFramesDn               OCTET STRING (SIZE (8)),
        eponOLTPonCurrent15MinIntervalStatuschange                     OCTET STRING (SIZE (8))
}


eponOLTPonCurrent15MinIntervalTimeElapsed  OBJECT-TYPE 
        SYNTAX    INTEGER 
        ACCESS    read-only 
        STATUS    mandatory 
        DESCRIPTION 
            "Elapsed time in interval (seconds)
            ALCATEL NOTE:
                ACCESS:     NA       USAGE:      NA
                PERSIST:    NO       INSRVMOD:   NO
                RANGE:      NA       DEFVALUE:   NA
                UNITS:      seconds  SPARSE:     NA
                DESCR:      NA"
::= { eponOLTPonCurrent15MinIntervalEntry 1 } 

eponOLTPonCurrent15MinIntervalTimeMeasured  OBJECT-TYPE 
        SYNTAX    INTEGER 
        ACCESS    read-only 
        STATUS    mandatory 
        DESCRIPTION 
           "Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
 
::= { eponOLTPonCurrent15MinIntervalEntry 2 } 

eponOLTPonCurrent15MinIntervalOctetsTransUp  OBJECT-TYPE
	SYNTAX 	OCTET STRING (SIZE (8)) 	
	ACCESS	read-only
	STATUS	mandatory
	DESCRIPTION 
		"The object indicates octets transferred in upstream direction on a PON port.
		  ALCATEL NOTE:
                 ACCESS:     NA       USAGE:      NA
                 PERSIST:    NO       INSRVMOD:   NO
                 RANGE:      NA       DEFVALUE:   0
                 UNITS:      NA       SPARSE:     NA
                 DESCR:      NA"

::= { eponOLTPonCurrent15MinIntervalEntry 3 }


eponOLTPonCurrent15MinIntervalTotalFramesTransUp  OBJECT-TYPE
	SYNTAX 	OCTET STRING (SIZE (8)) 	
	ACCESS	read-only
	STATUS	mandatory
	DESCRIPTION 
		"The object indicates Total Frames transferred 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 4 }
	
	
eponOLTPonCurrent15MinIntervalFirstSegOctetFramesUp	  OBJECT-TYPE
	SYNTAX 	OCTET STRING (SIZE (8)) 	
	ACCESS	read-only
	STATUS	mandatory
	DESCRIPTION 
		"The object indicates 64 Octet Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 5 }
	
eponOLTPonCurrent15MinIntervalSecondSegOctetFramesUp	  OBJECT-TYPE
	SYNTAX 	OCTET STRING (SIZE (8)) 	
	ACCESS	read-only
	STATUS	mandatory
	DESCRIPTION 
		"The object indicates 65-127 Octet Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 6 }
	
eponOLTPonCurrent15MinIntervalThirdSegOctetFramesUp	  OBJECT-TYPE
	SYNTAX 	OCTET STRING (SIZE (8)) 	
	ACCESS	read-only
	STATUS	mandatory
	DESCRIPTION 
		"The object indicates 128-255 Octet Frames 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 7 }
	
eponOLTPonCurrent15MinIntervalFourthSegOctetFramesUp	  OBJECT-TYPE
	SYNTAX 	OCTET STRING (SIZE (8)) 	
	ACCESS	read-only
	STATUS	mandatory
	DESCRIPTION 
		"The object indicates 256-511 Octet Frames 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 8 }
	
eponOLTPonCurrent15MinIntervalFifthSegOctetFramesUp	  OBJECT-TYPE
	SYNTAX 	OCTET STRING (SIZE (8)) 	
	ACCESS	read-only
	STATUS	mandatory
	DESCRIPTION 
		"The object indicates 512-1023 Octet Frames	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 9 }
	
eponOLTPonCurrent15MinIntervalSixthSegOctetFramesUp	  OBJECT-TYPE
	SYNTAX 	OCTET STRING (SIZE (8)) 	
	ACCESS	read-only
	STATUS	mandatory
	DESCRIPTION 
		"The object indicates 1024-1518 Octet Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 10 }
	
eponOLTPonCurrent15MinIntervalLastSegOctetFramesUp	  OBJECT-TYPE
	SYNTAX 	OCTET STRING (SIZE (8)) 	
	ACCESS	read-only
	STATUS	mandatory
	DESCRIPTION 
		"The object indicates 1519+ Octet Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 11 }
	
eponOLTPonCurrent15MinIntervalOctetsTransDn  OBJECT-TYPE
	SYNTAX 	OCTET STRING (SIZE (8)) 	
	ACCESS	read-only
	STATUS	mandatory
	DESCRIPTION 
		"The object indicates octets transferred in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 12 }


eponOLTPonCurrent15MinIntervalTotalFramesTransDn  OBJECT-TYPE
	SYNTAX 	OCTET STRING (SIZE (8)) 	
	ACCESS	read-only
	STATUS	mandatory
	DESCRIPTION 
		"The object indicates Total Frames transferred 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 13 }
	
	
eponOLTPonCurrent15MinIntervalFirstSegOctetFramesDn	  OBJECT-TYPE
	SYNTAX 	OCTET STRING (SIZE (8)) 	
	ACCESS	read-only
	STATUS	mandatory
	DESCRIPTION 
		"The object indicates 64 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 14 }
	
eponOLTPonCurrent15MinIntervalSecondSegOctetFramesDn	  OBJECT-TYPE
	SYNTAX 	OCTET STRING (SIZE (8)) 	
	ACCESS	read-only
	STATUS	mandatory
	DESCRIPTION 
		"The object indicates 65-127 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 15 }
	
eponOLTPonCurrent15MinIntervalThirdSegOctetFramesDn	  OBJECT-TYPE
	SYNTAX 	OCTET STRING (SIZE (8)) 	
	ACCESS	read-only
	STATUS	mandatory
	DESCRIPTION 
		"The object indicates 128-255 Octet Frames	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 16 }
	
eponOLTPonCurrent15MinIntervalFourthSegOctetFramesDn	  OBJECT-TYPE
	SYNTAX 	OCTET STRING (SIZE (8)) 	
	ACCESS	read-only
	STATUS	mandatory
	DESCRIPTION 
		"The object indicates 256-511 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 17 }
	
eponOLTPonCurrent15MinIntervalFifthSegOctetFramesDn	  OBJECT-TYPE
	SYNTAX 	OCTET STRING (SIZE (8)) 	
	ACCESS	read-only
	STATUS	mandatory
	DESCRIPTION 
		"The object indicates 512-1023 Octet Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 18 }
	
eponOLTPonCurrent15MinIntervalSixthSegOctetFramesDn	  OBJECT-TYPE
	SYNTAX 	OCTET STRING (SIZE (8)) 	
	ACCESS	read-only
	STATUS	mandatory
	DESCRIPTION 
		"The object indicates 1024-1518 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 19 }
	
eponOLTPonCurrent15MinIntervalLastSegOctetFramesDn	  OBJECT-TYPE
	SYNTAX 	OCTET STRING (SIZE (8)) 	
	ACCESS	read-only
	STATUS	mandatory
	DESCRIPTION 
		"The object indicates 1519+ Octet Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 20 }         
	
	eponOLTPonCurrent15MinIntervalCRCErrorframe	  OBJECT-TYPE
	SYNTAX 	OCTET STRING (SIZE (8)) 	
	ACCESS	read-only
	STATUS	mandatory
	DESCRIPTION 
		"The object indicates CRC error Frames on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 21 }   
	      
eponOLTPonCurrent15MinIntervalUndersizeframesUp	  OBJECT-TYPE
	SYNTAX 	OCTET STRING (SIZE (8)) 	
	ACCESS	read-only
	STATUS	mandatory
	DESCRIPTION 
		"The object indicates less than 64 bytes bytes Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 22 }     
	    
eponOLTPonCurrent15MinIntervalUndersizeframesDn	  OBJECT-TYPE
	SYNTAX 	OCTET STRING (SIZE (8)) 	
	ACCESS	read-only
	STATUS	mandatory
	DESCRIPTION 
		"The object indicates less than 64 bytes Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 23 }     
	    
eponOLTPonCurrent15MinIntervalOversizeframesUp	  OBJECT-TYPE
	SYNTAX 	OCTET STRING (SIZE (8)) 	
	ACCESS	read-only
	STATUS	mandatory
	DESCRIPTION 
		"The object indicates 1526+ Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 24 }     
	    
eponOLTPonCurrent15MinIntervalOversizeframesDn	  OBJECT-TYPE
	SYNTAX 	OCTET STRING (SIZE (8)) 	
	ACCESS	read-only
	STATUS	mandatory
	DESCRIPTION 
		"The object indicates 1526+ Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 25 }     
	    
eponOLTPonCurrent15MinIntervalErrorframesUp	  OBJECT-TYPE
	SYNTAX 	OCTET STRING (SIZE (8)) 	
	ACCESS	read-only
	STATUS	mandatory
	DESCRIPTION 
		"The object indicates error Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 26 }     
	    
eponOLTPonCurrent15MinIntervalErrorframesDn	  OBJECT-TYPE
	SYNTAX 	OCTET STRING (SIZE (8)) 	
	ACCESS	read-only
	STATUS	mandatory
	DESCRIPTION 
		"The object indicates error Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 27 }     
	    
eponOLTPonCurrent15MinIntervalDiscardframesUP	  OBJECT-TYPE
	SYNTAX 	OCTET STRING (SIZE (8)) 	
	ACCESS	read-only
	STATUS	mandatory
	DESCRIPTION 
		"The object indicates discard Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 28 }     
	    
eponOLTPonCurrent15MinIntervalDiscardframesDn	  OBJECT-TYPE
	SYNTAX 	OCTET STRING (SIZE (8)) 	
	ACCESS	read-only
	STATUS	mandatory
	DESCRIPTION 
		"The object indicates discard Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 29 }     
	    
eponOLTPonCurrent15MinIntervalUcastframesUP	  OBJECT-TYPE
	SYNTAX 	OCTET STRING (SIZE (8)) 	
	ACCESS	read-only
	STATUS	mandatory
	DESCRIPTION 
		"The object indicates unicast Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 30 }     
	    
eponOLTPonCurrent15MinIntervalUcastframesDn	  OBJECT-TYPE
	SYNTAX 	OCTET STRING (SIZE (8)) 	
	ACCESS	read-only
	STATUS	mandatory
	DESCRIPTION 
		"The object indicates unicast Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 31 }     
	    
eponOLTPonCurrent15MinIntervalMulticastframesUp	  OBJECT-TYPE
	SYNTAX 	OCTET STRING (SIZE (8)) 	
	ACCESS	read-only
	STATUS	mandatory
	DESCRIPTION 
		"The object indicates multicast Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 32 }     
	    
eponOLTPonCurrent15MinIntervalMulticastframesDn	  OBJECT-TYPE
	SYNTAX 	OCTET STRING (SIZE (8)) 	
	ACCESS	read-only
	STATUS	mandatory
	DESCRIPTION 
		"The object indicates multicast Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 33 }     
	    
eponOLTPonCurrent15MinIntervalBroardcastFramesUp	  OBJECT-TYPE
	SYNTAX 	OCTET STRING (SIZE (8)) 	
	ACCESS	read-only
	STATUS	mandatory
	DESCRIPTION 
		"The object indicates boardcast Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 34 }     
	    
eponOLTPonCurrent15MinIntervalBroardcastFramesDn	  OBJECT-TYPE
	SYNTAX 	OCTET STRING (SIZE (8)) 	
	ACCESS	read-only
	STATUS	mandatory
	DESCRIPTION 
		"The object indicates boardcast Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 35 }     
	    

eponOLTPonCurrent15MinIntervalDropEventsUP	  OBJECT-TYPE
	SYNTAX 	OCTET STRING (SIZE (8)) 	
	ACCESS	read-only
	STATUS	mandatory
	DESCRIPTION 
		"The object indicates drop event in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 36 }     

eponOLTPonCurrent15MinIntervalDropEventsDn	  OBJECT-TYPE
	SYNTAX 	OCTET STRING (SIZE (8)) 	
	ACCESS	read-only
	STATUS	mandatory
	DESCRIPTION 
		"The object indicates drop event in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 37 }     

eponOLTPonCurrent15MinIntervalFragmentsUP	  OBJECT-TYPE
	SYNTAX 	OCTET STRING (SIZE (8)) 	
	ACCESS	read-only
	STATUS	mandatory
	DESCRIPTION 
		"The object indicates fragment frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 38 }     

eponOLTPonCurrent15MinIntervalFragmentsDn	  OBJECT-TYPE
	SYNTAX 	OCTET STRING (SIZE (8)) 	
	ACCESS	read-only
	STATUS	mandatory
	DESCRIPTION 
		"The object indicates fragment frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 39 }     

eponOLTPonCurrent15MinIntervalJabberFramesUP    OBJECT-TYPE
	SYNTAX 	OCTET STRING (SIZE (8)) 	
	ACCESS	read-only
	STATUS	mandatory
	DESCRIPTION 
		"The object indicates jabber  frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 40 }     

eponOLTPonCurrent15MinIntervalJabberFramesDn      OBJECT-TYPE
	SYNTAX 	OCTET STRING (SIZE (8)) 	
	ACCESS	read-only
	STATUS	mandatory
	DESCRIPTION 
		"The object indicates jabber  frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 41 }     

eponOLTPonCurrent15MinIntervalStatuschange   OBJECT-TYPE
	SYNTAX 	OCTET STRING (SIZE (8)) 	
	ACCESS	read-only
	STATUS	mandatory
	DESCRIPTION 
		"The object indicates the number of status change on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent15MinIntervalEntry 42 }     

-- *********************************************

-- EPON PON OLT PERFORMANCE TABLE
--
-- This table contains current 1 day performance counters specific to
-- a specific PON port on OLT side. 

-- *********************************************

eponOLTPonCurrent1DayIntervalTable  OBJECT-TYPE
	SYNTAX SEQUENCE OF EponOLTPonCurrent1DayIntervalEntry
	ACCESS	not-accessible
	STATUS	mandatory  
	DESCRIPTION 
	 "1 day current statistics for pon interface.
	 ALCATEL NOTE:
             SUPPORT: YES   TABLESIZE: DEP"	
	::= { eponStatisticsGroup 3 }                                                  

eponOLTPonCurrent1DayIntervalEntry  OBJECT-TYPE
	SYNTAX 	EponOLTPonCurrent1DayIntervalEntry
	ACCESS	not-accessible
	STATUS	mandatory   
	DESCRIPTION
         "Table entry for the current 1 day statistics counters for OLT pon interface.
          Row creation : an entry is created by the system when this pon interfaces statistics enabled.
          Row deletion :an entry is created by the system when this pon interfaces statistics disabled.
           ALCATEL NOTE:
             SUPPORT: YES"
	INDEX	{ eponPonConfigIfIndex }
	::= { eponOLTPonCurrent1DayIntervalTable 1 }

EponOLTPonCurrent1DayIntervalEntry ::= SEQUENCE {
	    
	    eponOLTPonCurrent1DayIntervalTimeElapsed                INTEGER,                
	    eponOLTPonCurrent1DayIntervalTimeMeasured               INTEGER, 
        eponOLTPonCurrent1DayIntervalOctetsTransUp		         OCTET STRING (SIZE (8)),
        eponOLTPonCurrent1DayIntervalTotalFramesTransUp	         OCTET STRING (SIZE (8)),
        eponOLTPonCurrent1DayIntervalFirstSegOctetFramesUp      OCTET STRING (SIZE (8)),
        eponOLTPonCurrent1DayIntervalSecondSegOctetFramesUp     OCTET STRING (SIZE (8)),
        eponOLTPonCurrent1DayIntervalThirdSegOctetFramesUp      OCTET STRING (SIZE (8)),
        eponOLTPonCurrent1DayIntervalFourthSegOctetFramesUp     OCTET STRING (SIZE (8)),
        eponOLTPonCurrent1DayIntervalFifthSegOctetFramesUp      OCTET STRING (SIZE (8)),
        eponOLTPonCurrent1DayIntervalSixthSegOctetFramesUp      OCTET STRING (SIZE (8)),
        eponOLTPonCurrent1DayIntervalLastSegOctetFramesUp       OCTET STRING (SIZE (8)),
        eponOLTPonCurrent1DayIntervalOctetsTransDn		         OCTET STRING (SIZE (8)),
        eponOLTPonCurrent1DayIntervalTotalFramesTransDn	        OCTET STRING (SIZE (8)),
        eponOLTPonCurrent1DayIntervalFirstSegOctetFramesDn      OCTET STRING (SIZE (8)),
        eponOLTPonCurrent1DayIntervalSecondSegOctetFramesDn     OCTET STRING (SIZE (8)),
        eponOLTPonCurrent1DayIntervalThirdSegOctetFramesDn      OCTET STRING (SIZE (8)),
        eponOLTPonCurrent1DayIntervalFourthSegOctetFramesDn     OCTET STRING (SIZE (8)),
        eponOLTPonCurrent1DayIntervalFifthSegOctetFramesDn      OCTET STRING (SIZE (8)),
        eponOLTPonCurrent1DayIntervalSixthSegOctetFramesDn      OCTET STRING (SIZE (8)),
        eponOLTPonCurrent1DayIntervalLastSegOctetFramesDn       OCTET STRING (SIZE (8)),
        eponOLTPonCurrent1DayIntervalCRCErrorframe              OCTET STRING (SIZE (8)),
        eponOLTPonCurrent1DayIntervalUndersizeframesUp          OCTET STRING (SIZE (8)),
        eponOLTPonCurrent1DayIntervalUndersizeframesDn          OCTET STRING (SIZE (8)),
        eponOLTPonCurrent1DayIntervalOversizeframesUp           OCTET STRING (SIZE (8)),
        eponOLTPonCurrent1DayIntervalOversizeframesDn           OCTET STRING (SIZE (8)),
        eponOLTPonCurrent1DayIntervalErrorframesUp              OCTET STRING (SIZE (8)),
        eponOLTPonCurrent1DayIntervalErrorframesDn              OCTET STRING (SIZE (8)),
        eponOLTPonCurrent1DayIntervalDiscardframesUP            OCTET STRING (SIZE (8)),
        eponOLTPonCurrent1DayIntervalDiscardframesDn            OCTET STRING (SIZE (8)),
        eponOLTPonCurrent1DayIntervalUcastframesUP              OCTET STRING (SIZE (8)),
        eponOLTPonCurrent1DayIntervalUcastframesDn              OCTET STRING (SIZE (8)),
        eponOLTPonCurrent1DayIntervalMulticastframesUp          OCTET STRING (SIZE (8)),
        eponOLTPonCurrent1DayIntervalMulticastframesDn          OCTET STRING (SIZE (8)),
        eponOLTPonCurrent1DayBroardcastFramesUp                 OCTET STRING (SIZE (8)),
        eponOLTPonCurrent1DayBroardcastFramesDn                 OCTET STRING (SIZE (8)),
        eponOLTPonCurrent1DayIntervalDropEventsUP                OCTET STRING (SIZE (8)),
        eponOLTPonCurrent1DayIntervalDropEventsDn                OCTET STRING (SIZE (8)),
        eponOLTPonCurrent1DayIntervalFragmentsUP                 OCTET STRING (SIZE (8)),
        eponOLTPonCurrent1DayIntervalFragmentsDn                 OCTET STRING (SIZE (8)),
        eponOLTPonCurrent1DayIntervalJabberFramesUP           OCTET STRING (SIZE (8)),
        eponOLTPonCurrent1DayIntervalJabberFramesDn           OCTET STRING (SIZE (8)),
        eponOLTPonCurrent1DayIntervalStatuschange                 OCTET STRING (SIZE (8))
}


eponOLTPonCurrent1DayIntervalTimeElapsed  OBJECT-TYPE 
        SYNTAX    INTEGER 
        ACCESS    read-only 
        STATUS    mandatory 
        DESCRIPTION 
           "Elapsed time in interval (seconds)
            ALCATEL NOTE:
                ACCESS:     NA       USAGE:      NA
                PERSIST:    NO       INSRVMOD:   NO
                RANGE:      NA       DEFVALUE:   NA
                UNITS:      seconds  SPARSE:     NA
                DESCR:      NA"
     ::= { eponOLTPonCurrent1DayIntervalEntry 1 } 

eponOLTPonCurrent1DayIntervalTimeMeasured  OBJECT-TYPE 
        SYNTAX    INTEGER 
        ACCESS    read-only 
        STATUS    mandatory 
        DESCRIPTION 
            "Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
::= { eponOLTPonCurrent1DayIntervalEntry 2 } 

eponOLTPonCurrent1DayIntervalOctetsTransUp  OBJECT-TYPE
	SYNTAX 	OCTET STRING (SIZE (8)) 	
	ACCESS	read-only
	STATUS	mandatory
	DESCRIPTION 
		"The object indicates octets transferred  
		 in upstream direction on a PON port.
		 ALCATEL NOTE:
                 ACCESS:     NA       USAGE:      NA
                 PERSIST:    NO       INSRVMOD:   NO
                 RANGE:      NA       DEFVALUE:   0
                 UNITS:      NA       SPARSE:     NA
                 DESCR:      NA"

::= { eponOLTPonCurrent1DayIntervalEntry 3 }


eponOLTPonCurrent1DayIntervalTotalFramesTransUp  OBJECT-TYPE
	SYNTAX 	OCTET STRING (SIZE (8)) 	
	ACCESS	read-only
	STATUS	mandatory
	DESCRIPTION 
		"The object indicates Total Frames transferred 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 4 }
	
	
eponOLTPonCurrent1DayIntervalFirstSegOctetFramesUp	  OBJECT-TYPE
	SYNTAX 	OCTET STRING (SIZE (8)) 	
	ACCESS	read-only
	STATUS	mandatory
	DESCRIPTION 
		"The object indicates 64 Octet Frames	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 5 }
	
eponOLTPonCurrent1DayIntervalSecondSegOctetFramesUp	  OBJECT-TYPE
	SYNTAX 	OCTET STRING (SIZE (8)) 	
	ACCESS	read-only
	STATUS	mandatory
	DESCRIPTION 
		"The object indicates 65-127 Octet Frames	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 6 }
	
eponOLTPonCurrent1DayIntervalThirdSegOctetFramesUp	  OBJECT-TYPE
	SYNTAX 	OCTET STRING (SIZE (8)) 	
	ACCESS	read-only
	STATUS	mandatory
	DESCRIPTION 
		"The object indicates 128-255 Octet Frames 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 7 }
	
eponOLTPonCurrent1DayIntervalFourthSegOctetFramesUp	  OBJECT-TYPE
	SYNTAX 	OCTET STRING (SIZE (8)) 	
	ACCESS	read-only
	STATUS	mandatory
	DESCRIPTION 
		"The object indicates 256-511 Octet Frames 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 8 }
	
eponOLTPonCurrent1DayIntervalFifthSegOctetFramesUp	  OBJECT-TYPE
	SYNTAX 	OCTET STRING (SIZE (8)) 	
	ACCESS	read-only
	STATUS	mandatory
	DESCRIPTION 
		"The object indicates 512-1023 Octet Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 9 }
	
eponOLTPonCurrent1DayIntervalSixthSegOctetFramesUp	  OBJECT-TYPE
	SYNTAX 	OCTET STRING (SIZE (8)) 	
	ACCESS	read-only
	STATUS	mandatory
	DESCRIPTION 
		"The object indicates 1024-1518 Octet Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 10 }
	
eponOLTPonCurrent1DayIntervalLastSegOctetFramesUp	  OBJECT-TYPE
	SYNTAX 	OCTET STRING (SIZE (8)) 	
	ACCESS	read-only
	STATUS	mandatory
	DESCRIPTION 
		"The object indicates 1519+ Octet Frames 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 11 }
	
eponOLTPonCurrent1DayIntervalOctetsTransDn  OBJECT-TYPE
	SYNTAX 	OCTET STRING (SIZE (8)) 	
	ACCESS	read-only
	STATUS	mandatory
	DESCRIPTION 
		"The object indicates octets transferred in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 12 }


eponOLTPonCurrent1DayIntervalTotalFramesTransDn  OBJECT-TYPE
	SYNTAX 	OCTET STRING (SIZE (8)) 	
	ACCESS	read-only
	STATUS	mandatory
	DESCRIPTION 
		"The object indicates Total Frames transferred 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 13 }
	
	
eponOLTPonCurrent1DayIntervalFirstSegOctetFramesDn	  OBJECT-TYPE
	SYNTAX 	OCTET STRING (SIZE (8)) 	
	ACCESS	read-only
	STATUS	mandatory
	DESCRIPTION 
		"The object indicates 64 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 14 }
	
eponOLTPonCurrent1DayIntervalSecondSegOctetFramesDn	  OBJECT-TYPE
	SYNTAX 	OCTET STRING (SIZE (8)) 	
	ACCESS	read-only
	STATUS	mandatory
	DESCRIPTION 
		"The object indicates 65-127 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 15 }
	
eponOLTPonCurrent1DayIntervalThirdSegOctetFramesDn	  OBJECT-TYPE
	SYNTAX 	OCTET STRING (SIZE (8)) 	
	ACCESS	read-only
	STATUS	mandatory
	DESCRIPTION 
		"The object indicates 128-255 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 16 }
	
eponOLTPonCurrent1DayIntervalFourthSegOctetFramesDn	  OBJECT-TYPE
	SYNTAX 	OCTET STRING (SIZE (8)) 	
	ACCESS	read-only
	STATUS	mandatory
	DESCRIPTION 
		"The object indicates 256-511 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 17 }
	
eponOLTPonCurrent1DayIntervalFifthSegOctetFramesDn	  OBJECT-TYPE
	SYNTAX 	OCTET STRING (SIZE (8)) 	
	ACCESS	read-only
	STATUS	mandatory
	DESCRIPTION 
		"The object indicates 512-1023 Octet Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 18 }
	
eponOLTPonCurrent1DayIntervalSixthSegOctetFramesDn	  OBJECT-TYPE
	SYNTAX 	OCTET STRING (SIZE (8)) 	
	ACCESS	read-only
	STATUS	mandatory
	DESCRIPTION 
		"The object indicates 1024-1518 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 19 }
	
eponOLTPonCurrent1DayIntervalLastSegOctetFramesDn	  OBJECT-TYPE
	SYNTAX 	OCTET STRING (SIZE (8)) 	
	ACCESS	read-only
	STATUS	mandatory
	DESCRIPTION 
		"The object indicates 1519+ Octet Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 20 }

eponOLTPonCurrent1DayIntervalCRCErrorframe	  OBJECT-TYPE
	SYNTAX 	OCTET STRING (SIZE (8)) 	
	ACCESS	read-only
	STATUS	mandatory
	DESCRIPTION 
		"The object indicates CRC error on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 21 }
	
eponOLTPonCurrent1DayIntervalUndersizeframesUp	  OBJECT-TYPE
	SYNTAX 	OCTET STRING (SIZE (8)) 	
	ACCESS	read-only
	STATUS	mandatory
	DESCRIPTION 
		"The object indicates less than 64 bytes Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 22 }
	
eponOLTPonCurrent1DayIntervalUndersizeframesDn	  OBJECT-TYPE
	SYNTAX 	OCTET STRING (SIZE (8)) 	
	ACCESS	read-only
	STATUS	mandatory
	DESCRIPTION 
		"The object indicates less than 64 bytes Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 23 }
	
eponOLTPonCurrent1DayIntervalOversizeframesUp	  OBJECT-TYPE
	SYNTAX 	OCTET STRING (SIZE (8)) 	
	ACCESS	read-only
	STATUS	mandatory
	DESCRIPTION 
		"The object indicates 1526+ Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 24 }
	
eponOLTPonCurrent1DayIntervalOversizeframesDn	  OBJECT-TYPE
	SYNTAX 	OCTET STRING (SIZE (8)) 	
	ACCESS	read-only
	STATUS	mandatory
	DESCRIPTION 
		"The object indicates 1526+ Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 25 }
	
eponOLTPonCurrent1DayIntervalErrorframesUp	  OBJECT-TYPE
	SYNTAX 	OCTET STRING (SIZE (8)) 	
	ACCESS	read-only
	STATUS	mandatory
	DESCRIPTION 
		"The object indicates error Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 26 }
	
eponOLTPonCurrent1DayIntervalErrorframesDn	  OBJECT-TYPE
	SYNTAX 	OCTET STRING (SIZE (8)) 	
	ACCESS	read-only
	STATUS	mandatory
	DESCRIPTION 
		"The object indicates error Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 27 }
	
eponOLTPonCurrent1DayIntervalDiscardframesUP	  OBJECT-TYPE
	SYNTAX 	OCTET STRING (SIZE (8)) 	
	ACCESS	read-only
	STATUS	mandatory
	DESCRIPTION 
		"The object indicates discard Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 28 }
	
eponOLTPonCurrent1DayIntervalDiscardframesDn	  OBJECT-TYPE
	SYNTAX 	OCTET STRING (SIZE (8)) 	
	ACCESS	read-only
	STATUS	mandatory
	DESCRIPTION 
		"The object indicates discard Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 29 }
	
eponOLTPonCurrent1DayIntervalUcastframesUP	  OBJECT-TYPE
	SYNTAX 	OCTET STRING (SIZE (8)) 	
	ACCESS	read-only
	STATUS	mandatory
	DESCRIPTION 
		"The object indicates unicast Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 30 }
	
eponOLTPonCurrent1DayIntervalUcastframesDn	  OBJECT-TYPE
	SYNTAX 	OCTET STRING (SIZE (8)) 	
	ACCESS	read-only
	STATUS	mandatory
	DESCRIPTION 
		"The object indicates unicast Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 31 }
	
eponOLTPonCurrent1DayIntervalMulticastframesUp	  OBJECT-TYPE
	SYNTAX 	OCTET STRING (SIZE (8)) 	
	ACCESS	read-only
	STATUS	mandatory
	DESCRIPTION 
		"The object indicates multicast Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 32 }
	
eponOLTPonCurrent1DayIntervalMulticastframesDn	  OBJECT-TYPE
	SYNTAX 	OCTET STRING (SIZE (8)) 	
	ACCESS	read-only
	STATUS	mandatory
	DESCRIPTION 
		"The object indicates multicast Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 33 }
	
eponOLTPonCurrent1DayBroardcastFramesUp	  OBJECT-TYPE
	SYNTAX 	OCTET STRING (SIZE (8)) 	
	ACCESS	read-only
	STATUS	mandatory
	DESCRIPTION 
		"The object indicates broadcast Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 34 }
	
eponOLTPonCurrent1DayBroardcastFramesDn	  OBJECT-TYPE
	SYNTAX 	OCTET STRING (SIZE (8)) 	
	ACCESS	read-only
	STATUS	mandatory
	DESCRIPTION 
		"The object indicates boardcast Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 35 }


eponOLTPonCurrent1DayIntervalDropEventsUP  OBJECT-TYPE
	SYNTAX 	OCTET STRING (SIZE (8)) 	
	ACCESS	read-only
	STATUS	mandatory
	DESCRIPTION 
		"The object indicates drop event in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 36 }     

eponOLTPonCurrent1DayIntervalDropEventsDn   OBJECT-TYPE
	SYNTAX 	OCTET STRING (SIZE (8)) 	
	ACCESS	read-only
	STATUS	mandatory
	DESCRIPTION 
		"The object indicates drop event in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 37 }     

eponOLTPonCurrent1DayIntervalFragmentsUP  OBJECT-TYPE
	SYNTAX 	OCTET STRING (SIZE (8)) 	
	ACCESS	read-only
	STATUS	mandatory
	DESCRIPTION 
		"The object indicates fragment frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 38 }     

eponOLTPonCurrent1DayIntervalFragmentsDn	  OBJECT-TYPE
	SYNTAX 	OCTET STRING (SIZE (8)) 	
	ACCESS	read-only
	STATUS	mandatory
	DESCRIPTION 
		"The object indicates fragment frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 39 }     

eponOLTPonCurrent1DayIntervalJabberFramesUP       OBJECT-TYPE
	SYNTAX 	OCTET STRING (SIZE (8)) 	
	ACCESS	read-only
	STATUS	mandatory
	DESCRIPTION 
		"The object indicates jabber  frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 40 }     

eponOLTPonCurrent1DayIntervalJabberFramesDn      OBJECT-TYPE
	SYNTAX 	OCTET STRING (SIZE (8)) 	
	ACCESS	read-only
	STATUS	mandatory
	DESCRIPTION 
		"The object indicates jabber  frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 41 }     

eponOLTPonCurrent1DayIntervalStatuschange         OBJECT-TYPE
	SYNTAX 	OCTET STRING (SIZE (8)) 	
	ACCESS	read-only
	STATUS	mandatory
	DESCRIPTION 
		"The object indicates the number of status change on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonCurrent1DayIntervalEntry 42 }     


-- *********************************************

-- EPON PON OLT PERFORMANCE TABLE
--
-- This table contains previous 15 min performance counters specific to
-- a specific PON port on OLT side. 

-- *********************************************

eponOLTPonPrevious15MinIntervalTable  OBJECT-TYPE
	SYNTAX SEQUENCE OF EponOLTPonPrevious15MinIntervalEntry
	ACCESS	not-accessible
	STATUS	mandatory   
	DESCRIPTION 
	 "15 Minutes previous statistics for pon interface.
	 ALCATEL NOTE:
             SUPPORT: YES   TABLESIZE: DEP"
	::= { eponStatisticsGroup 4 }                                                  

eponOLTPonPrevious15MinIntervalEntry  OBJECT-TYPE
	SYNTAX 	EponOLTPonPrevious15MinIntervalEntry
	ACCESS	not-accessible
	STATUS	mandatory  
	DESCRIPTION
	 "	Table entry for the previous 15 minutes statistics counters for OLT pon interface.
          Row creation : an entry is created by the system when this pon interfaces statistics enabled.
          Row deletion :an entry is created by the system when this pon interfaces statistics disabled.
           ALCATEL NOTE:
             SUPPORT: YES"
	INDEX	{ eponPonConfigIfIndex,
	          eponOLTPonPrevious15MinIntervalNumber }
	::= { eponOLTPonPrevious15MinIntervalTable 1 }

EponOLTPonPrevious15MinIntervalEntry ::= SEQUENCE { 
	    eponOLTPonPrevious15MinIntervalNumber                     INTEGER,                
	    eponOLTPonPrevious15MinIntervalTimeMeasured               INTEGER, 
        eponOLTPonPrevious15MinIntervalOctetsTransUp		      OCTET STRING (SIZE (8)),
        eponOLTPonPrevious15MinIntervalTotalFramesTransUp	      OCTET STRING (SIZE (8)),
        eponOLTPonPrevious15MinIntervalFirstSegOctetFramesUp      OCTET STRING (SIZE (8)),
        eponOLTPonPrevious15MinIntervalSecondSegOctetFramesUp     OCTET STRING (SIZE (8)),
        eponOLTPonPrevious15MinIntervalThirdSegOctetFramesUp      OCTET STRING (SIZE (8)),
        eponOLTPonPrevious15MinIntervalFourthSegOctetFramesUp     OCTET STRING (SIZE (8)),
        eponOLTPonPrevious15MinIntervalFifthSegOctetFramesUp      OCTET STRING (SIZE (8)),
        eponOLTPonPrevious15MinIntervalSixthSegOctetFramesUp      OCTET STRING (SIZE (8)),
        eponOLTPonPrevious15MinIntervalLastSegOctetFramesUp       OCTET STRING (SIZE (8)),
        eponOLTPonPrevious15MinIntervalOctetsTransDn		      OCTET STRING (SIZE (8)),
        eponOLTPonPrevious15MinIntervalTotalFramesTransDn	      OCTET STRING (SIZE (8)),
        eponOLTPonPrevious15MinIntervalFirstSegOctetFramesDn      OCTET STRING (SIZE (8)),
        eponOLTPonPrevious15MinIntervalSecondSegOctetFramesDn     OCTET STRING (SIZE (8)),
        eponOLTPonPrevious15MinIntervalThirdSegOctetFramesDn      OCTET STRING (SIZE (8)),
        eponOLTPonPrevious15MinIntervalFourthSegOctetFramesDn     OCTET STRING (SIZE (8)),
        eponOLTPonPrevious15MinIntervalFifthSegOctetFramesDn      OCTET STRING (SIZE (8)),
        eponOLTPonPrevious15MinIntervalSixthSegOctetFramesDn      OCTET STRING (SIZE (8)),
        eponOLTPonPrevious15MinIntervalLastSegOctetFramesDn       OCTET STRING (SIZE (8)),
        eponOLTPonPrevious15MinIntervalCRCErrorframe              OCTET STRING (SIZE (8)),
        eponOLTPonPrevious15MinIntervalUndersizeframesUp          OCTET STRING (SIZE (8)),
        eponOLTPonPrevious15MinIntervalUndersizeframesDn          OCTET STRING (SIZE (8)),
        eponOLTPonPrevious15MinIntervalOversizeframesUp           OCTET STRING (SIZE (8)),
        eponOLTPonPrevious15MinIntervalOversizeframesDn           OCTET STRING (SIZE (8)),
        eponOLTPonPrevious15MinIntervalErrorframesUp              OCTET STRING (SIZE (8)),
        eponOLTPonPrevious15MinIntervalErrorframesDn              OCTET STRING (SIZE (8)),
        eponOLTPonPrevious15MinIntervalDiscardframesUP            OCTET STRING (SIZE (8)),
        eponOLTPonPrevious15MinIntervalDiscardframesDn            OCTET STRING (SIZE (8)),
        eponOLTPonPrevious15MinIntervalUcastframesUP              OCTET STRING (SIZE (8)),
        eponOLTPonPrevious15MinIntervalUcastframesDn              OCTET STRING (SIZE (8)),
        eponOLTPonPrevious15MinIntervalMulticastframesUp          OCTET STRING (SIZE (8)),
        eponOLTPonPrevious15MinIntervalMulticastframesDn          OCTET STRING (SIZE (8)),
        eponOLTPonPrevious15MinIntervalBroardcastFramesUp         OCTET STRING (SIZE (8)),
        eponOLTPonPrevious15MinIntervalBroardcastFramesDn         OCTET STRING (SIZE (8)),
        eponOLTPonPrevious15MinIntervalDropEventsUP                   OCTET STRING (SIZE (8)),
        eponOLTPonPrevious15MinIntervalDropEventsDn                    OCTET STRING (SIZE (8)),
        eponOLTPonPrevious15MinIntervalFragmentsUP                     OCTET STRING (SIZE (8)),
        eponOLTPonPrevious15MinIntervalFragmentsDn                     OCTET STRING (SIZE (8)),
        eponOLTPonPrevious15MinIntervalJabberFramesUP               OCTET STRING (SIZE (8)),
        eponOLTPonPrevious15MinIntervalJabberFramesDn               OCTET STRING (SIZE (8)),
        eponOLTPonPrevious15MinIntervalStatuschange                     OCTET STRING (SIZE (8))    
}


eponOLTPonPrevious15MinIntervalNumber  OBJECT-TYPE 
        SYNTAX    INTEGER 
        ACCESS    not-accessible 
        STATUS    mandatory 
        DESCRIPTION 
            "Previous interval reference
             ALCATEL NOTE:
                 ACCESS:     NA       USAGE:      NA
                 PERSIST:    NO       INSRVMOD:   NO
                 RANGE:      1..192       DEFVALUE:   NA
                 UNITS:      NA       SPARSE:     NA
                 DESCR:      NA"
::= { eponOLTPonPrevious15MinIntervalEntry 1 } 

eponOLTPonPrevious15MinIntervalTimeMeasured  OBJECT-TYPE 
        SYNTAX    INTEGER 
        ACCESS    read-only 
        STATUS    mandatory 
        DESCRIPTION 
           "Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
::= { eponOLTPonPrevious15MinIntervalEntry 2 } 

eponOLTPonPrevious15MinIntervalOctetsTransUp  OBJECT-TYPE
	SYNTAX 	OCTET STRING (SIZE (8)) 	
	ACCESS	read-only
	STATUS	mandatory
	DESCRIPTION 
		"The object indicates octets transferred in upstream direction on a PON port
		 ALCATEL NOTE:
                 ACCESS:     NA       USAGE:      NA
                 PERSIST:    NO       INSRVMOD:   NO
                 RANGE:      NA       DEFVALUE:   0
                 UNITS:      NA       SPARSE:     NA
                 DESCR:      NA"

::= { eponOLTPonPrevious15MinIntervalEntry 3 }


eponOLTPonPrevious15MinIntervalTotalFramesTransUp  OBJECT-TYPE
	SYNTAX 	OCTET STRING (SIZE (8)) 	
	ACCESS	read-only
	STATUS	mandatory
	DESCRIPTION 
		"The object indicates Total Frames transferred 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 4 }
	
	
eponOLTPonPrevious15MinIntervalFirstSegOctetFramesUp	  OBJECT-TYPE
	SYNTAX 	OCTET STRING (SIZE (8)) 	
	ACCESS	read-only
	STATUS	mandatory
	DESCRIPTION 
		"The object indicates 64 Octet Frames 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 5 }
	
eponOLTPonPrevious15MinIntervalSecondSegOctetFramesUp	  OBJECT-TYPE
	SYNTAX 	OCTET STRING (SIZE (8)) 	
	ACCESS	read-only
	STATUS	mandatory
	DESCRIPTION 
		"The object indicates 65-127 Octet Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 6 }
	
eponOLTPonPrevious15MinIntervalThirdSegOctetFramesUp	  OBJECT-TYPE
	SYNTAX 	OCTET STRING (SIZE (8)) 	
	ACCESS	read-only
	STATUS	mandatory
	DESCRIPTION 
		"The object indicates 128-255 Octet Frames 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 7 }
	
eponOLTPonPrevious15MinIntervalFourthSegOctetFramesUp	  OBJECT-TYPE
	SYNTAX 	OCTET STRING (SIZE (8)) 	
	ACCESS	read-only
	STATUS	mandatory
	DESCRIPTION 
		"The object indicates 256-511 Octet Frames 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 8 }
	
eponOLTPonPrevious15MinIntervalFifthSegOctetFramesUp	  OBJECT-TYPE
	SYNTAX 	OCTET STRING (SIZE (8)) 	
	ACCESS	read-only
	STATUS	mandatory
	DESCRIPTION 
		"The object indicates 512-1023 Octet Frames 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 9 }
	
eponOLTPonPrevious15MinIntervalSixthSegOctetFramesUp	  OBJECT-TYPE
	SYNTAX 	OCTET STRING (SIZE (8)) 	
	ACCESS	read-only
	STATUS	mandatory
	DESCRIPTION 
		"The object indicates 1024-1518 Octet Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 10 }
	
eponOLTPonPrevious15MinIntervalLastSegOctetFramesUp	  OBJECT-TYPE
	SYNTAX 	OCTET STRING (SIZE (8)) 	
	ACCESS	read-only
	STATUS	mandatory
	DESCRIPTION 
		"The object indicates 1519+ Octet Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 11 }
	
eponOLTPonPrevious15MinIntervalOctetsTransDn  OBJECT-TYPE
	SYNTAX 	OCTET STRING (SIZE (8)) 	
	ACCESS	read-only
	STATUS	mandatory
	DESCRIPTION 
		"The object indicates octets transferred in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 12 }


eponOLTPonPrevious15MinIntervalTotalFramesTransDn  OBJECT-TYPE
	SYNTAX 	OCTET STRING (SIZE (8)) 	
	ACCESS	read-only
	STATUS	mandatory
	DESCRIPTION 
		"The object indicates Total Frames transferred 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 13 }
	
	
eponOLTPonPrevious15MinIntervalFirstSegOctetFramesDn	  OBJECT-TYPE
	SYNTAX 	OCTET STRING (SIZE (8)) 	
	ACCESS	read-only
	STATUS	mandatory
	DESCRIPTION 
		"The object indicates 64 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 14 }
	
eponOLTPonPrevious15MinIntervalSecondSegOctetFramesDn	  OBJECT-TYPE
	SYNTAX 	OCTET STRING (SIZE (8)) 	
	ACCESS	read-only
	STATUS	mandatory
	DESCRIPTION 
		"The object indicates 65-127 Octet Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 15 }
	
eponOLTPonPrevious15MinIntervalThirdSegOctetFramesDn	  OBJECT-TYPE
	SYNTAX 	OCTET STRING (SIZE (8)) 	
	ACCESS	read-only
	STATUS	mandatory
	DESCRIPTION 
		"The object indicates 128-255 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 16 }
	
eponOLTPonPrevious15MinIntervalFourthSegOctetFramesDn	  OBJECT-TYPE
	SYNTAX 	OCTET STRING (SIZE (8)) 	
	ACCESS	read-only
	STATUS	mandatory
	DESCRIPTION 
		"The object indicates 256-511 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 17 }
	
eponOLTPonPrevious15MinIntervalFifthSegOctetFramesDn	  OBJECT-TYPE
	SYNTAX 	OCTET STRING (SIZE (8)) 	
	ACCESS	read-only
	STATUS	mandatory
	DESCRIPTION 
		"The object indicates 512-1023 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 18 }
	
eponOLTPonPrevious15MinIntervalSixthSegOctetFramesDn	  OBJECT-TYPE
	SYNTAX 	OCTET STRING (SIZE (8)) 	
	ACCESS	read-only
	STATUS	mandatory
	DESCRIPTION 
		"The object indicates 1024-1518 Octet Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 19 }
	
eponOLTPonPrevious15MinIntervalLastSegOctetFramesDn	  OBJECT-TYPE
	SYNTAX 	OCTET STRING (SIZE (8)) 	
	ACCESS	read-only
	STATUS	mandatory
	DESCRIPTION 
		"The object indicates 1519+ Octet Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 20 }         
	
eponOLTPonPrevious15MinIntervalCRCErrorframe	  OBJECT-TYPE
	SYNTAX 	OCTET STRING (SIZE (8)) 	
	ACCESS	read-only
	STATUS	mandatory
	DESCRIPTION 
		"The object indicates CRC error Frames on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 21 }         
	
eponOLTPonPrevious15MinIntervalUndersizeframesUp	  OBJECT-TYPE
	SYNTAX 	OCTET STRING (SIZE (8)) 	
	ACCESS	read-only
	STATUS	mandatory
	DESCRIPTION 
		"The object indicates less than 64 bytes Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 22 }         
	
eponOLTPonPrevious15MinIntervalUndersizeframesDn	  OBJECT-TYPE
	SYNTAX 	OCTET STRING (SIZE (8)) 	
	ACCESS	read-only
	STATUS	mandatory
	DESCRIPTION 
		"The object indicates less than 64 bytes Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 23 }         
	
eponOLTPonPrevious15MinIntervalOversizeframesUp	  OBJECT-TYPE
	SYNTAX 	OCTET STRING (SIZE (8)) 	
	ACCESS	read-only
	STATUS	mandatory
	DESCRIPTION 
		"The object indicates 1526+ Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 24 }         
	
eponOLTPonPrevious15MinIntervalOversizeframesDn	  OBJECT-TYPE
	SYNTAX 	OCTET STRING (SIZE (8)) 	
	ACCESS	read-only
	STATUS	mandatory
	DESCRIPTION 
		"The object indicates 1526+ Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 25 }         
	
eponOLTPonPrevious15MinIntervalErrorframesUp	  OBJECT-TYPE
	SYNTAX 	OCTET STRING (SIZE (8)) 	
	ACCESS	read-only
	STATUS	mandatory
	DESCRIPTION 
		"The object indicates error Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 26 }         
	
eponOLTPonPrevious15MinIntervalErrorframesDn	  OBJECT-TYPE
	SYNTAX 	OCTET STRING (SIZE (8)) 	
	ACCESS	read-only
	STATUS	mandatory
	DESCRIPTION 
		"The object indicates error Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 27 }         
	
eponOLTPonPrevious15MinIntervalDiscardframesUP	  OBJECT-TYPE
	SYNTAX 	OCTET STRING (SIZE (8)) 	
	ACCESS	read-only
	STATUS	mandatory
	DESCRIPTION 
		"The object indicates discard Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 28 }         
	
eponOLTPonPrevious15MinIntervalDiscardframesDn	  OBJECT-TYPE
	SYNTAX 	OCTET STRING (SIZE (8)) 	
	ACCESS	read-only
	STATUS	mandatory
	DESCRIPTION 
		"The object indicates discard Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 29 }         
	
eponOLTPonPrevious15MinIntervalUcastframesUP	  OBJECT-TYPE
	SYNTAX 	OCTET STRING (SIZE (8)) 	
	ACCESS	read-only
	STATUS	mandatory
	DESCRIPTION 
		"The object indicates unicast Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 30 }         
	
eponOLTPonPrevious15MinIntervalUcastframesDn	  OBJECT-TYPE
	SYNTAX 	OCTET STRING (SIZE (8)) 	
	ACCESS	read-only
	STATUS	mandatory
	DESCRIPTION 
		"The object indicates unicast Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 31 }         
	
eponOLTPonPrevious15MinIntervalMulticastframesUp	  OBJECT-TYPE
	SYNTAX 	OCTET STRING (SIZE (8)) 	
	ACCESS	read-only
	STATUS	mandatory
	DESCRIPTION 
		"The object indicates nulticast Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 32 }         
	
eponOLTPonPrevious15MinIntervalMulticastframesDn	  OBJECT-TYPE
	SYNTAX 	OCTET STRING (SIZE (8)) 	
	ACCESS	read-only
	STATUS	mandatory
	DESCRIPTION 
		"The object indicates nulticast Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 33 }         
	
eponOLTPonPrevious15MinIntervalBroardcastFramesUp	  OBJECT-TYPE
	SYNTAX 	OCTET STRING (SIZE (8)) 	
	ACCESS	read-only
	STATUS	mandatory
	DESCRIPTION 
		"The object indicates broadcast Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 34 }         
	
eponOLTPonPrevious15MinIntervalBroardcastFramesDn	  OBJECT-TYPE
	SYNTAX 	OCTET STRING (SIZE (8)) 	
	ACCESS	read-only
	STATUS	mandatory
	DESCRIPTION 
		"The object indicates boardcast Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 35 }         

eponOLTPonPrevious15MinIntervalDropEventsUP	  OBJECT-TYPE
	SYNTAX 	OCTET STRING (SIZE (8)) 	
	ACCESS	read-only
	STATUS	mandatory
	DESCRIPTION 
		"The object indicates drop event in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 36 }     

eponOLTPonPrevious15MinIntervalDropEventsDn	  OBJECT-TYPE
	SYNTAX 	OCTET STRING (SIZE (8)) 	
	ACCESS	read-only
	STATUS	mandatory
	DESCRIPTION 
		"The object indicates drop event in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 37 }     

eponOLTPonPrevious15MinIntervalFragmentsUP	  OBJECT-TYPE
	SYNTAX 	OCTET STRING (SIZE (8)) 	
	ACCESS	read-only
	STATUS	mandatory
	DESCRIPTION 
		"The object indicates fragment frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 38 }     

eponOLTPonPrevious15MinIntervalFragmentsDn	  OBJECT-TYPE
	SYNTAX 	OCTET STRING (SIZE (8)) 	
	ACCESS	read-only
	STATUS	mandatory
	DESCRIPTION 
		"The object indicates fragment frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 39 }     

eponOLTPonPrevious15MinIntervalJabberFramesUP    OBJECT-TYPE
	SYNTAX 	OCTET STRING (SIZE (8)) 	
	ACCESS	read-only
	STATUS	mandatory
	DESCRIPTION 
		"The object indicates jabber  frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 40 }     

eponOLTPonPrevious15MinIntervalJabberFramesDn      OBJECT-TYPE
	SYNTAX 	OCTET STRING (SIZE (8)) 	
	ACCESS	read-only
	STATUS	mandatory
	DESCRIPTION 
		"The object indicates jabber  frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 41 }     

eponOLTPonPrevious15MinIntervalStatuschange   OBJECT-TYPE
	SYNTAX 	OCTET STRING (SIZE (8)) 	
	ACCESS	read-only
	STATUS	mandatory
	DESCRIPTION 
		"The object indicates the number of status change on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious15MinIntervalEntry 42 }     


-- *********************************************

-- EPON PON OLT PERFORMANCE TABLE
--
-- This table contains Previous 1 day performance counters specific to
-- a specific PON port on OLT side. 

-- *********************************************

eponOLTPonPrevious1DayIntervalTable  OBJECT-TYPE
	SYNTAX SEQUENCE OF EponOLTPonPrevious1DayIntervalEntry
	ACCESS	not-accessible
	STATUS	mandatory  
	DESCRIPTION 
	 "1 day previous statistics for pon interface.
	 ALCATEL NOTE:
             SUPPORT: YES   TABLESIZE: DEP"
	::= { eponStatisticsGroup 5 }                                                  

eponOLTPonPrevious1DayIntervalEntry  OBJECT-TYPE
	SYNTAX 	EponOLTPonPrevious1DayIntervalEntry
	ACCESS	not-accessible
	STATUS	mandatory    
	 DESCRIPTION
         "	Table entry for the previous 1 day statistics counters for OLT pon interface.
          Row creation : an entry is created by the system when this pon interfaces statistics enabled.
          Row deletion :an entry is created by the system when this pon interfaces statistics disabled.
           ALCATEL NOTE:
             SUPPORT: YES"
	INDEX	{ eponPonConfigIfIndex,
	         eponOLTPonPrevious1DayIntervalNumber }
	::= { eponOLTPonPrevious1DayIntervalTable 1 }

EponOLTPonPrevious1DayIntervalEntry ::= SEQUENCE {
	    eponOLTPonPrevious1DayIntervalNumber                     INTEGER,                
	    eponOLTPonPrevious1DayIntervalTimeMeasured               INTEGER, 
        eponOLTPonPrevious1DayIntervalOctetsTransUp		         OCTET STRING (SIZE (8)),
        eponOLTPonPrevious1DayIntervalTotalFramesTransUp	     OCTET STRING (SIZE (8)),
        eponOLTPonPrevious1DayIntervalFirstSegOctetFramesUp      OCTET STRING (SIZE (8)),
        eponOLTPonPrevious1DayIntervalSecondSegOctetFramesUp     OCTET STRING (SIZE (8)),
        eponOLTPonPrevious1DayIntervalThirdSegOctetFramesUp      OCTET STRING (SIZE (8)),
        eponOLTPonPrevious1DayIntervalFourthSegOctetFramesUp     OCTET STRING (SIZE (8)),
        eponOLTPonPrevious1DayIntervalFifthSegOctetFramesUp      OCTET STRING (SIZE (8)),
        eponOLTPonPrevious1DayIntervalSixthSegOctetFramesUp      OCTET STRING (SIZE (8)),
        eponOLTPonPrevious1DayIntervalLastSegOctetFramesUp       OCTET STRING (SIZE (8)),
        eponOLTPonPrevious1DayIntervalOctetsTransDn		         OCTET STRING (SIZE (8)),
        eponOLTPonPrevious1DayIntervalTotalFramesTransDn	     OCTET STRING (SIZE (8)),
        eponOLTPonPrevious1DayIntervalFirstSegOctetFramesDn      OCTET STRING (SIZE (8)),
        eponOLTPonPrevious1DayIntervalSecondSegOctetFramesDn     OCTET STRING (SIZE (8)),
        eponOLTPonPrevious1DayIntervalThirdSegOctetFramesDn      OCTET STRING (SIZE (8)),
        eponOLTPonPrevious1DayIntervalFourthSegOctetFramesDn     OCTET STRING (SIZE (8)),
        eponOLTPonPrevious1DayIntervalFifthSegOctetFramesDn      OCTET STRING (SIZE (8)),
        eponOLTPonPrevious1DayIntervalSixthSegOctetFramesDn      OCTET STRING (SIZE (8)),
        eponOLTPonPrevious1DayIntervalLastSegOctetFramesDn       OCTET STRING (SIZE (8)),
        eponOLTPonPreviousDayIntervalCRCErrorframe               OCTET STRING (SIZE (8)),
        eponOLTPonPrevious1DayIntervalUndersizeframesUp          OCTET STRING (SIZE (8)),
        eponOLTPonPrevious1DayIntervalUndersizeframesDn          OCTET STRING (SIZE (8)),
        eponOLTPonPrevious1DayIntervalOversizeframesUp           OCTET STRING (SIZE (8)),
        eponOLTPonPrevious1DayIntervalOversizeframesDn           OCTET STRING (SIZE (8)),
        eponOLTPonPrevious1DayIntervalErrorframesUp              OCTET STRING (SIZE (8)),
        eponOLTPonPrevious1DayIntervalErrorframesDn              OCTET STRING (SIZE (8)),
        eponOLTPonPrevious1DayIntervalDiscardframesUP            OCTET STRING (SIZE (8)),
        eponOLTPonPrevious1DayIntervalDiscardframesDn            OCTET STRING (SIZE (8)),
        eponOLTPonPrevious1DayIntervalUcastframesUP              OCTET STRING (SIZE (8)),
        eponOLTPonPrevious1DayIntervalUcastframesDn              OCTET STRING (SIZE (8)),
        eponOLTPonPrevious1DayIntervalMulticastframesUp          OCTET STRING (SIZE (8)),
        eponOLTPonPrevious1DayIntervalMulticastframesDn          OCTET STRING (SIZE (8)),
        eponOLTPonPrevious1DayBroardcastFramesUp                 OCTET STRING (SIZE (8)),
        eponOLTPonPrevious1DayBroardcastFramesDn                 OCTET STRING (SIZE (8)),
        eponOLTPonPrevious1DayIntervalDropEventsUP                   OCTET STRING (SIZE (8)),
        eponOLTPonPrevious1DayIntervalDropEventsDn                    OCTET STRING (SIZE (8)),
        eponOLTPonPrevious1DayIntervalFragmentsUP                     OCTET STRING (SIZE (8)),
        eponOLTPonPrevious1DayIntervalFragmentsDn                     OCTET STRING (SIZE (8)),
        eponOLTPonPrevious1DayIntervalJabberFramesUP               OCTET STRING (SIZE (8)),
        eponOLTPonPrevious1DayIntervalJabberFramesDn               OCTET STRING (SIZE (8)),
        eponOLTPonPrevious1DayIntervalStatuschange                     OCTET STRING (SIZE (8))
}


eponOLTPonPrevious1DayIntervalNumber  OBJECT-TYPE 
        SYNTAX    INTEGER 
        ACCESS    not-accessible 
        STATUS    mandatory 
        DESCRIPTION 
           "Previous interval reference
             ALCATEL NOTE:
                 ACCESS:     NA       USAGE:      NA
                 PERSIST:    NO       INSRVMOD:   NO
                 RANGE:      1..2       DEFVALUE:   NA
                 UNITS:      NA       SPARSE:     NA
                 DESCR:      NA"
::= { eponOLTPonPrevious1DayIntervalEntry 1 } 

eponOLTPonPrevious1DayIntervalTimeMeasured  OBJECT-TYPE 
        SYNTAX    INTEGER 
        ACCESS    read-only 
        STATUS    mandatory 
        DESCRIPTION 
           "Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
::= { eponOLTPonPrevious1DayIntervalEntry 2 } 

eponOLTPonPrevious1DayIntervalOctetsTransUp  OBJECT-TYPE
	SYNTAX 	OCTET STRING (SIZE (8)) 	
	ACCESS	read-only
	STATUS	mandatory
	DESCRIPTION 
		"The object indicates octets transferred in upstream direction on a PON port.
		  ALCATEL NOTE:
                 ACCESS:     NA       USAGE:      NA
                 PERSIST:    NO       INSRVMOD:   NO
                 RANGE:      NA       DEFVALUE:   0
                 UNITS:      NA       SPARSE:     NA
                 DESCR:      NA"

::= { eponOLTPonPrevious1DayIntervalEntry 3 }


eponOLTPonPrevious1DayIntervalTotalFramesTransUp  OBJECT-TYPE
	SYNTAX 	OCTET STRING (SIZE (8)) 	
	ACCESS	read-only
	STATUS	mandatory
	DESCRIPTION 
		"The object indicates Total Frames transferred 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 4 }
	
	
eponOLTPonPrevious1DayIntervalFirstSegOctetFramesUp	  OBJECT-TYPE
	SYNTAX 	OCTET STRING (SIZE (8)) 	
	ACCESS	read-only
	STATUS	mandatory
	DESCRIPTION 
		"The object indicates 64 Octet Frames 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 5 }
	
eponOLTPonPrevious1DayIntervalSecondSegOctetFramesUp	  OBJECT-TYPE
	SYNTAX 	OCTET STRING (SIZE (8)) 	
	ACCESS	read-only
	STATUS	mandatory
	DESCRIPTION 
		"The object indicates 65-127 Octet Frames 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 6 }
	
eponOLTPonPrevious1DayIntervalThirdSegOctetFramesUp	  OBJECT-TYPE
	SYNTAX 	OCTET STRING (SIZE (8)) 	
	ACCESS	read-only
	STATUS	mandatory
	DESCRIPTION 
		"The object indicates 128-255 Octet Frames 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 7 }
	
eponOLTPonPrevious1DayIntervalFourthSegOctetFramesUp	  OBJECT-TYPE
	SYNTAX 	OCTET STRING (SIZE (8)) 	
	ACCESS	read-only
	STATUS	mandatory
	DESCRIPTION 
		"The object indicates 256-511 Octet Frames 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 8 }
	
eponOLTPonPrevious1DayIntervalFifthSegOctetFramesUp	  OBJECT-TYPE
	SYNTAX 	OCTET STRING (SIZE (8)) 	
	ACCESS	read-only
	STATUS	mandatory
	DESCRIPTION 
		"The object indicates 512-1023 Octet Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 9 }
	
eponOLTPonPrevious1DayIntervalSixthSegOctetFramesUp	  OBJECT-TYPE
	SYNTAX 	OCTET STRING (SIZE (8)) 	
	ACCESS	read-only
	STATUS	mandatory
	DESCRIPTION 
		"The object indicates 1024-1518 Octet Frames 	in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 10 }
	
eponOLTPonPrevious1DayIntervalLastSegOctetFramesUp	  OBJECT-TYPE
	SYNTAX 	OCTET STRING (SIZE (8)) 	
	ACCESS	read-only
	STATUS	mandatory
	DESCRIPTION 
		"The object indicates 1519+ Octet Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 11 }
	
eponOLTPonPrevious1DayIntervalOctetsTransDn  OBJECT-TYPE
	SYNTAX 	OCTET STRING (SIZE (8)) 	
	ACCESS	read-only
	STATUS	mandatory
	DESCRIPTION 
		"The object indicates octets transferred in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 12 }


eponOLTPonPrevious1DayIntervalTotalFramesTransDn  OBJECT-TYPE
	SYNTAX 	OCTET STRING (SIZE (8)) 	
	ACCESS	read-only
	STATUS	mandatory
	DESCRIPTION 
		"The object indicates Total Frames transferred 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 13 }
	
	
eponOLTPonPrevious1DayIntervalFirstSegOctetFramesDn	  OBJECT-TYPE
	SYNTAX 	OCTET STRING (SIZE (8)) 	
	ACCESS	read-only
	STATUS	mandatory
	DESCRIPTION 
		"The object indicates 64 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 14 }
	
eponOLTPonPrevious1DayIntervalSecondSegOctetFramesDn	  OBJECT-TYPE
	SYNTAX 	OCTET STRING (SIZE (8)) 	
	ACCESS	read-only
	STATUS	mandatory
	DESCRIPTION 
		"The object indicates 65-127 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 15 }
	
eponOLTPonPrevious1DayIntervalThirdSegOctetFramesDn	  OBJECT-TYPE
	SYNTAX 	OCTET STRING (SIZE (8)) 	
	ACCESS	read-only
	STATUS	mandatory
	DESCRIPTION 
		"The object indicates 128-255 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 16 }
	
eponOLTPonPrevious1DayIntervalFourthSegOctetFramesDn	  OBJECT-TYPE
	SYNTAX 	OCTET STRING (SIZE (8)) 	
	ACCESS	read-only
	STATUS	mandatory
	DESCRIPTION 
		"The object indicates 256-511 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 17 }
	
eponOLTPonPrevious1DayIntervalFifthSegOctetFramesDn	  OBJECT-TYPE
	SYNTAX 	OCTET STRING (SIZE (8)) 	
	ACCESS	read-only
	STATUS	mandatory
	DESCRIPTION 
		"The object indicates 512-1023 Octet Frames 	in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 18 }
	
eponOLTPonPrevious1DayIntervalSixthSegOctetFramesDn	  OBJECT-TYPE
	SYNTAX 	OCTET STRING (SIZE (8)) 	
	ACCESS	read-only
	STATUS	mandatory
	DESCRIPTION 
		"The object indicates 1024-1518 Octet Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 19 }
	
eponOLTPonPrevious1DayIntervalLastSegOctetFramesDn	  OBJECT-TYPE
	SYNTAX 	OCTET STRING (SIZE (8)) 	
	ACCESS	read-only
	STATUS	mandatory
	DESCRIPTION 
		"The object indicates 1519+ Octet Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 20 }

eponOLTPonPreviousDayIntervalCRCErrorframe	  OBJECT-TYPE
	SYNTAX 	OCTET STRING (SIZE (8)) 	
	ACCESS	read-only
	STATUS	mandatory
	DESCRIPTION 
		"The object indicates CRC error Frames on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 21 }

eponOLTPonPrevious1DayIntervalUndersizeframesUp	  OBJECT-TYPE
	SYNTAX 	OCTET STRING (SIZE (8)) 	
	ACCESS	read-only
	STATUS	mandatory
	DESCRIPTION 
		"The object indicates less than 64 bytes Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 22 }

eponOLTPonPrevious1DayIntervalUndersizeframesDn	  OBJECT-TYPE
	SYNTAX 	OCTET STRING (SIZE (8)) 	
	ACCESS	read-only
	STATUS	mandatory
	DESCRIPTION 
		"The object indicates less than 64 bytes Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 23 }

eponOLTPonPrevious1DayIntervalOversizeframesUp	  OBJECT-TYPE
	SYNTAX 	OCTET STRING (SIZE (8)) 	
	ACCESS	read-only
	STATUS	mandatory
	DESCRIPTION 
		"The object indicates 1526+ Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 24 }

eponOLTPonPrevious1DayIntervalOversizeframesDn	  OBJECT-TYPE
	SYNTAX 	OCTET STRING (SIZE (8)) 	
	ACCESS	read-only
	STATUS	mandatory
	DESCRIPTION 
		"The object indicates 1526+ Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 25 }

eponOLTPonPrevious1DayIntervalErrorframesUp	  OBJECT-TYPE
	SYNTAX 	OCTET STRING (SIZE (8)) 	
	ACCESS	read-only
	STATUS	mandatory
	DESCRIPTION 
		"The object indicates error Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 26 }

eponOLTPonPrevious1DayIntervalErrorframesDn	  OBJECT-TYPE
	SYNTAX 	OCTET STRING (SIZE (8)) 	
	ACCESS	read-only
	STATUS	mandatory
	DESCRIPTION 
		"The object indicates error Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 27 }

eponOLTPonPrevious1DayIntervalDiscardframesUP	  OBJECT-TYPE
	SYNTAX 	OCTET STRING (SIZE (8)) 	
	ACCESS	read-only
	STATUS	mandatory
	DESCRIPTION 
		"The object indicates discard Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 28 }

eponOLTPonPrevious1DayIntervalDiscardframesDn	  OBJECT-TYPE
	SYNTAX 	OCTET STRING (SIZE (8)) 	
	ACCESS	read-only
	STATUS	mandatory
	DESCRIPTION 
		"The object indicates discard Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 29 }

eponOLTPonPrevious1DayIntervalUcastframesUP	  OBJECT-TYPE
	SYNTAX 	OCTET STRING (SIZE (8)) 	
	ACCESS	read-only
	STATUS	mandatory
	DESCRIPTION 
		"The object indicates unicast Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 30 }

eponOLTPonPrevious1DayIntervalUcastframesDn	  OBJECT-TYPE
	SYNTAX 	OCTET STRING (SIZE (8)) 	
	ACCESS	read-only
	STATUS	mandatory
	DESCRIPTION 
		"The object indicates unicast Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 31 }

eponOLTPonPrevious1DayIntervalMulticastframesUp	  OBJECT-TYPE
	SYNTAX 	OCTET STRING (SIZE (8)) 	
	ACCESS	read-only
	STATUS	mandatory
	DESCRIPTION 
		"The object indicates multicast Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 32 }

eponOLTPonPrevious1DayIntervalMulticastframesDn	  OBJECT-TYPE
	SYNTAX 	OCTET STRING (SIZE (8)) 	
	ACCESS	read-only
	STATUS	mandatory
	DESCRIPTION 
		"The object indicates multicast Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 33 }

eponOLTPonPrevious1DayBroardcastFramesUp	  OBJECT-TYPE
	SYNTAX 	OCTET STRING (SIZE (8)) 	
	ACCESS	read-only
	STATUS	mandatory
	DESCRIPTION 
		"The object indicates boardcast Frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 34 }

eponOLTPonPrevious1DayBroardcastFramesDn	  OBJECT-TYPE
	SYNTAX 	OCTET STRING (SIZE (8)) 	
	ACCESS	read-only
	STATUS	mandatory
	DESCRIPTION 
		"The object indicates boardcast Frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 35 }


eponOLTPonPrevious1DayIntervalDropEventsUP	  OBJECT-TYPE
	SYNTAX 	OCTET STRING (SIZE (8)) 	
	ACCESS	read-only
	STATUS	mandatory
	DESCRIPTION 
		"The object indicates drop event in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 36 }     

eponOLTPonPrevious1DayIntervalDropEventsDn	  OBJECT-TYPE
	SYNTAX 	OCTET STRING (SIZE (8)) 	
	ACCESS	read-only
	STATUS	mandatory
	DESCRIPTION 
		"The object indicates drop event in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 37 }     

eponOLTPonPrevious1DayIntervalFragmentsUP	  OBJECT-TYPE
	SYNTAX 	OCTET STRING (SIZE (8)) 	
	ACCESS	read-only
	STATUS	mandatory
	DESCRIPTION 
		"The object indicates fragment frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 38 }     

eponOLTPonPrevious1DayIntervalFragmentsDn	  OBJECT-TYPE
	SYNTAX 	OCTET STRING (SIZE (8)) 	
	ACCESS	read-only
	STATUS	mandatory
	DESCRIPTION 
		"The object indicates fragment frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 39 }     

eponOLTPonPrevious1DayIntervalJabberFramesUP    OBJECT-TYPE
	SYNTAX 	OCTET STRING (SIZE (8)) 	
	ACCESS	read-only
	STATUS	mandatory
	DESCRIPTION 
		"The object indicates jabber  frames in upstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 40 }     

eponOLTPonPrevious1DayIntervalJabberFramesDn      OBJECT-TYPE
	SYNTAX 	OCTET STRING (SIZE (8)) 	
	ACCESS	read-only
	STATUS	mandatory
	DESCRIPTION 
		"The object indicates jabber  frames in downstream direction on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 41 }     

eponOLTPonPrevious1DayIntervalStatuschange   OBJECT-TYPE
	SYNTAX 	OCTET STRING (SIZE (8)) 	
	ACCESS	read-only
	STATUS	mandatory
	DESCRIPTION 
		"The object indicates the number of status change on a PON port
ALCATEL NOTE:
                 ACCESS:     NA       USAGE:      NA
                 PERSIST:    NO       INSRVMOD:   NO
                 RANGE:      NA       DEFVALUE:   0
                 UNITS:      NA       SPARSE:     NA
                 DESCR:      NA"
	::= { eponOLTPonPrevious1DayIntervalEntry 42 }     


-- *********************************************
--
-- EPON ONT PON Performance TABLE
--
-- Table of number of previous statistics intervals for the traffic on a 
-- ONT PON port
--
-- 
-- *********************************************

eponONTPonPerfInfoTable     OBJECT-TYPE 
        SYNTAX    SEQUENCE OF EponONTPonPerfInfoEntry 
        ACCESS    not-accessible 
        STATUS    mandatory 
        DESCRIPTION 
             "Table of number of previous statistics intervals for the traffic on a 
            ONT PON interface.  
            ALCATEL NOTE:
             SUPPORT: YES   TABLESIZE: DEP"

::= {eponStatisticsGroup 6 } 

eponONTPonPerfInfoEntry OBJECT-TYPE 
        SYNTAX    EponONTPonPerfInfoEntry 
        ACCESS    not-accessible 
        STATUS    mandatory 
        DESCRIPTION 
             "An entry in the eponONTPonPerfInfoTable . 
          Row creation : an entry is created by the system when ONT pon level statistics enable. 
          Row creation : an entry is created by the system when ONT pon level statistics enable. 
            ALCATEL NOTE:
             SUPPORT: YES" 
        INDEX   { eponOntIndex } 
::= { eponONTPonPerfInfoTable 1 } 

EponONTPonPerfInfoEntry ::= 
       SEQUENCE{ 
                 eponONTPonPerfInfo15MinValidIntervals    INTEGER, 
                 eponONTPonPerfInfo1DayValidIntervals     INTEGER 
                }    
                

    
eponONTPonPerfInfo15MinValidIntervals OBJECT-TYPE 
        SYNTAX    INTEGER 
        ACCESS    read-only 
        STATUS    mandatory 
        DESCRIPTION 
            "Number of previous 15 minutes intervals
             ALCATEL NOTE:
                 ACCESS:     NA       USAGE:      NA
                 PERSIST:    NO       INSRVMOD:   NO
                 RANGE:      NA       DEFVALUE:   0
                 UNITS:      NA       SPARSE:     NA
                 DESCR:      NA"
        ::= { eponONTPonPerfInfoEntry 1 } 
        
eponONTPonPerfInfo1DayValidIntervals OBJECT-TYPE 
        SYNTAX    INTEGER 
        ACCESS     read-only 
        STATUS    mandatory 
        DESCRIPTION 
            "Number of previous 1 day intervals. 
             ALCATEL NOTE:
                 ACCESS:     NA       USAGE:      NA
                 PERSIST:    NO       INSRVMOD:   NO
                 RANGE:      NA       DEFVALUE:   0
                 UNITS:      NA       SPARSE:     NA
                 DESCR:      NA"

        ::= { eponONTPonPerfInfoEntry 2 }  
        
-- *********************************************

-- EPON PON ONT PERFORMANCE TABLE
--
-- This table contains current 15 min performance counters specific to
-- a specific PON port on ONT side. 

-- *********************************************

eponONTPonCurrent15MinIntervalTable  OBJECT-TYPE
	SYNTAX SEQUENCE OF EponONTPonCurrent15MinIntervalEntry
	ACCESS	not-accessible
	STATUS	mandatory    
	DESCRIPTION
	"15 Minutes current statistics for ONT pon interface.
	 ALCATEL NOTE:
             SUPPORT: YES   TABLESIZE: DEP"	

	::= { eponStatisticsGroup 7 }                                                  

eponONTPonCurrent15MinIntervalEntry  OBJECT-TYPE
	SYNTAX 	EponONTPonCurrent15MinIntervalEntry
	ACCESS	not-accessible
	STATUS	mandatory    
	 DESCRIPTION
         "Table entry for the current 15 minutes statistics counters for ONT pon interface.
          Row creation : an entry is created by the system when this pon interfaces statistics enabled.
          Row deletion :an entry is created by the system when this pon interfaces statistics disabled.
           ALCATEL NOTE:
             SUPPORT: YES"

	INDEX	{ eponOntIndex }
	::= { eponONTPonCurrent15MinIntervalTable 1 }

EponONTPonCurrent15MinIntervalEntry ::= SEQUENCE { 
	    eponONTPonCurrent15MinIntervalTimeElapsed                INTEGER,                
	    eponONTPonCurrent15MinIntervalTimeMeasured               INTEGER, 
        eponONTPonCurrent15MinIntervalOctetsTransUp		         OCTET STRING (SIZE (8)),
        eponONTPonCurrent15MinIntervalTotalFramesTransUp	     OCTET STRING (SIZE (8)),
        eponONTPonCurrent15MinIntervalFirstSegOctetFramesUp      OCTET STRING (SIZE (8)),
        eponONTPonCurrent15MinIntervalSecondSegOctetFramesUp     OCTET STRING (SIZE (8)),
        eponONTPonCurrent15MinIntervalThirdSegOctetFramesUp      OCTET STRING (SIZE (8)),
        eponONTPonCurrent15MinIntervalFourthSegOctetFramesUp     OCTET STRING (SIZE (8)),
        eponONTPonCurrent15MinIntervalFifthSegOctetFramesUp      OCTET STRING (SIZE (8)),
        eponONTPonCurrent15MinIntervalSixthSegOctetFramesUp      OCTET STRING (SIZE (8)),
        eponONTPonCurrent15MinIntervalLastSegOctetFramesUp       OCTET STRING (SIZE (8)),
        eponONTPonCurrent15MinIntervalOctetsTransDn		         OCTET STRING (SIZE (8)),
        eponONTPonCurrent15MinIntervalTotalFramesTransDn	     OCTET STRING (SIZE (8)),
        eponONTPonCurrent15MinIntervalFirstSegOctetFramesDn      OCTET STRING (SIZE (8)),
        eponONTPonCurrent15MinIntervalSecondSegOctetFramesDn     OCTET STRING (SIZE (8)),
        eponONTPonCurrent15MinIntervalThirdSegOctetFramesDn      OCTET STRING (SIZE (8)),
        eponONTPonCurrent15MinIntervalFourthSegOctetFramesDn     OCTET STRING (SIZE (8)),
        eponONTPonCurrent15MinIntervalFifthSegOctetFramesDn      OCTET STRING (SIZE (8)),
        eponONTPonCurrent15MinIntervalSixthSegOctetFramesDn      OCTET STRING (SIZE (8)),
        eponONTPonCurrent15MinIntervalLastSegOctetFramesDn       OCTET STRING (SIZE (8)),
        eponONTPonCurrent15MinIntervalCRCErrorframe              OCTET STRING (SIZE (8)),
        eponONTPonCurrent15MinIntervalUndersizeframesUp          OCTET STRING (SIZE (8)),
        eponONTPonCurrent15MinIntervalUndersizeframesDn          OCTET STRING (SIZE (8)),
        eponONTPonCurrent15MinIntervalOversizeframesUp           OCTET STRING (SIZE (8)),
        eponONTPonCurrent15MinIntervalOversizeframesDn           OCTET STRING (SIZE (8)),
        eponONTPonCurrent15MinIntervalErrorframesUp              OCTET STRING (SIZE (8)),
        eponONTPonCurrent15MinIntervalErrorframesDn              OCTET STRING (SIZE (8)),
        eponONTPonCurrent15MinIntervalDiscardframesUP            OCTET STRING (SIZE (8)),
        eponONTPonCurrent15MinIntervalDiscardframesDn            OCTET STRING (SIZE (8)),
        eponONTPonCurrent15MinIntervalUcastframesUP              OCTET STRING (SIZE (8)),
        eponONTPonCurrent15MinIntervalUcastframesDn              OCTET STRING (SIZE (8)),
        eponONTPonCurrent15MinIntervalMulticastframesUp          OCTET STRING (SIZE (8)),
        eponONTPonCurrent15MinIntervalMulticastframesDn          OCTET STRING (SIZE (8)),
        eponONTPonCurrent15MinIntervalBroardcastFramesUp         OCTET STRING (SIZE (8)),
        eponONTPonCurrent15MinIntervalBroardcastFramesDn         OCTET STRING (SIZE (8)),
        eponONTPonCurrent15MinIntervalDropEventsUP                   OCTET STRING (SIZE (8)),
        eponONTPonCurrent15MinIntervalDropEventsDn                    OCTET STRING (SIZE (8)),
        eponONTPonCurrent15MinIntervalFragmentsUP                     OCTET STRING (SIZE (8)),
        eponONTPonCurrent15MinIntervalFragmentsDn                     OCTET STRING (SIZE (8)),
        eponONTPonCurrent15MinIntervalJabberFramesUP               OCTET STRING (SIZE (8)),
        eponONTPonCurrent15MinIntervalJabberFramesDn               OCTET STRING (SIZE (8)),
        eponONTPonCurrent15MinIntervalStatuschange                     OCTET STRING (SIZE (8)),
	eponONTPonCurrent15MinIntervalFECcorrectFrames           OCTET STRING (SIZE (8)),
        eponONTPonCurrent15MinIntervalFECuncorrectFrames         OCTET STRING (SIZE (8)),
        eponONTPonCurrent15MinIntervalMPCPFramesUP               OCTET STRING (SIZE (8)),
        eponONTPonCurrent15MinIntervalMPCPFramesDW               OCTET STRING (SIZE (8)),
        eponONTPonCurrent15MinIntervalMPCPTxregisterframes       OCTET STRING (SIZE (8)),
        eponONTPonCurrent15MinIntervalMPCPTxregrequestframes    OCTET STRING (SIZE (8)),
        eponONTPonCurrent15MinIntervalMPCPTxreportframes         OCTET STRING (SIZE (8)),
        eponONTPonCurrent15MinIntervalMPCPRxgateframes           OCTET STRING (SIZE (8)),
        eponONTPonCurrent15MinIntervalMPCPRxregisterframes       OCTET STRING (SIZE (8))        
}


eponONTPonCurrent15MinIntervalTimeElapsed  OBJECT-TYPE 
        SYNTAX    INTEGER 
        ACCESS    read-only 
        STATUS    mandatory 
        DESCRIPTION 
            "Elapsed time in interval (seconds)
            ALCATEL NOTE:
                ACCESS:     NA       USAGE:      NA
                PERSIST:    NO       INSRVMOD:   NO
                RANGE:      NA       DEFVALUE:   NA
                UNITS:      seconds  SPARSE:     NA
                DESCR:      NA"

::= { eponONTPonCurrent15MinIntervalEntry 1 } 

eponONTPonCurrent15MinIntervalTimeMeasured  OBJECT-TYPE 
        SYNTAX    INTEGER 
        ACCESS    read-only 
        STATUS    mandatory 
        DESCRIPTION 
             "Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
::= { eponONTPonCurrent15MinIntervalEntry 2 } 

eponONTPonCurrent15MinIntervalOctetsTransUp  OBJECT-TYPE
	SYNTAX 	OCTET STRING (SIZE (8)) 	
	ACCESS	read-only
	STATUS	mandatory
	DESCRIPTION 
		"The object indicates octets transferred in upstream direction on a ONT PON port.
		 ALCATEL NOTE:
                 ACCESS:     NA       USAGE:      NA
                 PERSIST:    NO       INSRVMOD:   NO
                 RANGE:      NA       DEFVALUE:   0
                 UNITS:      NA       SPARSE:     NA
                 DESCR:      NA"

::= { eponONTPonCurrent15MinIntervalEntry 3 }


eponONTPonCurrent15MinIntervalTotalFramesTransUp  OBJECT-TYPE
	SYNTAX 	OCTET STRING (SIZE (8)) 	
	ACCESS	read-only
	STATUS	mandatory
	DESCRIPTION 
		"The object indicates Total Frames transferred 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 4 }
	
	
eponONTPonCurrent15MinIntervalFirstSegOctetFramesUp	  OBJECT-TYPE
	SYNTAX 	OCTET STRING (SIZE (8)) 	
	ACCESS	read-only
	STATUS	mandatory
	DESCRIPTION 
		"The object indicates 64 Octet Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 5 }
	
eponONTPonCurrent15MinIntervalSecondSegOctetFramesUp	  OBJECT-TYPE
	SYNTAX 	OCTET STRING (SIZE (8)) 	
	ACCESS	read-only
	STATUS	mandatory
	DESCRIPTION 
		"The object indicates 65-127 Octet Frames in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 6 }
	
eponONTPonCurrent15MinIntervalThirdSegOctetFramesUp	  OBJECT-TYPE
	SYNTAX 	OCTET STRING (SIZE (8)) 	
	ACCESS	read-only
	STATUS	mandatory
	DESCRIPTION 
		"The object indicates 128-255 Octet Frames in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 7 }
	
eponONTPonCurrent15MinIntervalFourthSegOctetFramesUp	  OBJECT-TYPE
	SYNTAX 	OCTET STRING (SIZE (8)) 	
	ACCESS	read-only
	STATUS	mandatory
	DESCRIPTION 
		"The object indicates 256-511 Octet Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 8 }
	
eponONTPonCurrent15MinIntervalFifthSegOctetFramesUp	  OBJECT-TYPE
	SYNTAX 	OCTET STRING (SIZE (8)) 	
	ACCESS	read-only
	STATUS	mandatory
	DESCRIPTION 
		"The object indicates 512-1023 Octet Frames in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 9 }
	
eponONTPonCurrent15MinIntervalSixthSegOctetFramesUp	  OBJECT-TYPE
	SYNTAX 	OCTET STRING (SIZE (8)) 	
	ACCESS	read-only
	STATUS	mandatory
	DESCRIPTION 
		"The object indicates 1024-1518 Octet Frames in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 10 }
	
eponONTPonCurrent15MinIntervalLastSegOctetFramesUp	  OBJECT-TYPE
	SYNTAX 	OCTET STRING (SIZE (8)) 	
	ACCESS	read-only
	STATUS	mandatory
	DESCRIPTION 
		"The object indicates 1519+ Octet Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 11}
	
eponONTPonCurrent15MinIntervalOctetsTransDn  OBJECT-TYPE
	SYNTAX 	OCTET STRING (SIZE (8)) 	
	ACCESS	read-only
	STATUS	mandatory
	DESCRIPTION 
		"The object indicates octets transferred 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 12 }


eponONTPonCurrent15MinIntervalTotalFramesTransDn  OBJECT-TYPE
	SYNTAX 	OCTET STRING (SIZE (8)) 	
	ACCESS	read-only
	STATUS	mandatory
	DESCRIPTION 
		"The object indicates Total Frames transferred 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 13 }
	
	
eponONTPonCurrent15MinIntervalFirstSegOctetFramesDn	  OBJECT-TYPE
	SYNTAX 	OCTET STRING (SIZE (8)) 	
	ACCESS	read-only
	STATUS	mandatory
	DESCRIPTION 
		"The object indicates 64 Octet Frames 	in downstream direction ONT a PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 14 }
	
eponONTPonCurrent15MinIntervalSecondSegOctetFramesDn	  OBJECT-TYPE
	SYNTAX 	OCTET STRING (SIZE (8)) 	
	ACCESS	read-only
	STATUS	mandatory
	DESCRIPTION 
		"The object indicates 65-127 Octet Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 15 }
	
eponONTPonCurrent15MinIntervalThirdSegOctetFramesDn	  OBJECT-TYPE
	SYNTAX 	OCTET STRING (SIZE (8)) 	
	ACCESS	read-only
	STATUS	mandatory
	DESCRIPTION 
		"The object indicates 128-255 Octet Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 16 }
	
eponONTPonCurrent15MinIntervalFourthSegOctetFramesDn	  OBJECT-TYPE
	SYNTAX 	OCTET STRING (SIZE (8)) 	
	ACCESS	read-only
	STATUS	mandatory
	DESCRIPTION 
		"The object indicates 256-511 Octet Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 17 }
	
eponONTPonCurrent15MinIntervalFifthSegOctetFramesDn	  OBJECT-TYPE
	SYNTAX 	OCTET STRING (SIZE (8)) 	
	ACCESS	read-only
	STATUS	mandatory
	DESCRIPTION 
		"The object indicates 512-1023 Octet Frames in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 18 }
	
eponONTPonCurrent15MinIntervalSixthSegOctetFramesDn	  OBJECT-TYPE
	SYNTAX 	OCTET STRING (SIZE (8)) 	
	ACCESS	read-only
	STATUS	mandatory
	DESCRIPTION 
		"The object indicates 1024-1518 Octet Frames	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 19 }
	
eponONTPonCurrent15MinIntervalLastSegOctetFramesDn	  OBJECT-TYPE
	SYNTAX 	OCTET STRING (SIZE (8)) 	
	ACCESS	read-only
	STATUS	mandatory
	DESCRIPTION 
		"The object indicates 1519+ Octet Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 20 }         
	
eponONTPonCurrent15MinIntervalCRCErrorframe	  OBJECT-TYPE
	SYNTAX 	OCTET STRING (SIZE (8)) 	
	ACCESS	read-only
	STATUS	mandatory
	DESCRIPTION 
		"The object indicates CRC error Frames on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 21 }         

eponONTPonCurrent15MinIntervalUndersizeframesUp	  OBJECT-TYPE
	SYNTAX 	OCTET STRING (SIZE (8)) 	
	ACCESS	read-only
	STATUS	mandatory
	DESCRIPTION 
		"The object indicates less than 64 bytes Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 22 }         

eponONTPonCurrent15MinIntervalUndersizeframesDn	  OBJECT-TYPE
	SYNTAX 	OCTET STRING (SIZE (8)) 	
	ACCESS	read-only
	STATUS	mandatory
	DESCRIPTION 
		"The object indicates less than 64 bytes Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 23 }         

eponONTPonCurrent15MinIntervalOversizeframesUp	  OBJECT-TYPE
	SYNTAX 	OCTET STRING (SIZE (8)) 	
	ACCESS	read-only
	STATUS	mandatory
	DESCRIPTION 
		"The object indicates 1526+ Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 24 }         

eponONTPonCurrent15MinIntervalOversizeframesDn	  OBJECT-TYPE
	SYNTAX 	OCTET STRING (SIZE (8)) 	
	ACCESS	read-only
	STATUS	mandatory
	DESCRIPTION 
		"The object indicates 1526+ Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 25 }         

eponONTPonCurrent15MinIntervalErrorframesUp	  OBJECT-TYPE
	SYNTAX 	OCTET STRING (SIZE (8)) 	
	ACCESS	read-only
	STATUS	mandatory
	DESCRIPTION 
		"The object indicates error Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 26 }         

eponONTPonCurrent15MinIntervalErrorframesDn	  OBJECT-TYPE
	SYNTAX 	OCTET STRING (SIZE (8)) 	
	ACCESS	read-only
	STATUS	mandatory
	DESCRIPTION 
		"The object indicates error Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 27 }         

eponONTPonCurrent15MinIntervalDiscardframesUP	  OBJECT-TYPE
	SYNTAX 	OCTET STRING (SIZE (8)) 	
	ACCESS	read-only
	STATUS	mandatory
	DESCRIPTION 
		"The object indicates discard Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 28 }         

eponONTPonCurrent15MinIntervalDiscardframesDn	  OBJECT-TYPE
	SYNTAX 	OCTET STRING (SIZE (8)) 	
	ACCESS	read-only
	STATUS	mandatory
	DESCRIPTION 
		"The object indicates discard Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 29 }         

eponONTPonCurrent15MinIntervalUcastframesUP	  OBJECT-TYPE
	SYNTAX 	OCTET STRING (SIZE (8)) 	
	ACCESS	read-only
	STATUS	mandatory
	DESCRIPTION 
		"The object indicates unicast Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 30 }         

eponONTPonCurrent15MinIntervalUcastframesDn	  OBJECT-TYPE
	SYNTAX 	OCTET STRING (SIZE (8)) 	
	ACCESS	read-only
	STATUS	mandatory
	DESCRIPTION 
		"The object indicates unicast Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 31 }         

eponONTPonCurrent15MinIntervalMulticastframesUp	  OBJECT-TYPE
	SYNTAX 	OCTET STRING (SIZE (8)) 	
	ACCESS	read-only
	STATUS	mandatory
	DESCRIPTION 
		"The object indicates multicast Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 32 }         

eponONTPonCurrent15MinIntervalMulticastframesDn	  OBJECT-TYPE
	SYNTAX 	OCTET STRING (SIZE (8)) 	
	ACCESS	read-only
	STATUS	mandatory
	DESCRIPTION 
		"The object indicates multicast Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 33 }         

eponONTPonCurrent15MinIntervalBroardcastFramesUp	  OBJECT-TYPE
	SYNTAX 	OCTET STRING (SIZE (8)) 	
	ACCESS	read-only
	STATUS	mandatory
	DESCRIPTION 
		"The object indicates boardcast Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 34 }         

eponONTPonCurrent15MinIntervalBroardcastFramesDn	  OBJECT-TYPE
	SYNTAX 	OCTET STRING (SIZE (8)) 	
	ACCESS	read-only
	STATUS	mandatory
	DESCRIPTION 
		"The object indicates boardcast Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 35 }       
	

eponONTPonCurrent15MinIntervalDropEventsUP	  OBJECT-TYPE
	SYNTAX 	OCTET STRING (SIZE (8)) 	
	ACCESS	read-only
	STATUS	mandatory
	DESCRIPTION 
		"The object indicates drop event in upstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 36 }     

eponONTPonCurrent15MinIntervalDropEventsDn	  OBJECT-TYPE
	SYNTAX 	OCTET STRING (SIZE (8)) 	
	ACCESS	read-only
	STATUS	mandatory
	DESCRIPTION 
		"The object indicates drop event in downstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 37 }     

eponONTPonCurrent15MinIntervalFragmentsUP	  OBJECT-TYPE
	SYNTAX 	OCTET STRING (SIZE (8)) 	
	ACCESS	read-only
	STATUS	mandatory
	DESCRIPTION 
		"The object indicates fragment frames in upstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 38 }     

eponONTPonCurrent15MinIntervalFragmentsDn	  OBJECT-TYPE
	SYNTAX 	OCTET STRING (SIZE (8)) 	
	ACCESS	read-only
	STATUS	mandatory
	DESCRIPTION 
		"The object indicates fragment frames in downstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 39 }     

eponONTPonCurrent15MinIntervalJabberFramesUP    OBJECT-TYPE
	SYNTAX 	OCTET STRING (SIZE (8)) 	
	ACCESS	read-only
	STATUS	mandatory
	DESCRIPTION 
		"The object indicates jabber  frames in upstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 40 }     

eponONTPonCurrent15MinIntervalJabberFramesDn      OBJECT-TYPE
	SYNTAX 	OCTET STRING (SIZE (8)) 	
	ACCESS	read-only
	STATUS	mandatory
	DESCRIPTION 
		"The object indicates MPCP  Frames in downstream direction on  ONT PON port.
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 41 }     

eponONTPonCurrent15MinIntervalStatuschange   OBJECT-TYPE
	SYNTAX 	OCTET STRING (SIZE (8)) 	
	ACCESS	read-only
	STATUS	mandatory
	DESCRIPTION 
		"The object indicates the number of status change on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent15MinIntervalEntry 42 }     

eponONTPonCurrent15MinIntervalFECcorrectFrames  OBJECT-TYPE
  SYNTAX  OCTET STRING (SIZE (8)) 	
  ACCESS  read-only
  STATUS  mandatory
  DESCRIPTION 
    "The object indicates FEC correct Frames on ONT PON port."
  ::= { eponONTPonCurrent15MinIntervalEntry 43 }

eponONTPonCurrent15MinIntervalFECuncorrectFrames  OBJECT-TYPE
  SYNTAX  OCTET STRING (SIZE (8)) 	
  ACCESS  read-only
  STATUS  mandatory
  DESCRIPTION 
    "The object indicates FEC uncorrect Frames on ONT PON port."
  ::= { eponONTPonCurrent15MinIntervalEntry 44 }
  
eponONTPonCurrent15MinIntervalMPCPFramesUP  OBJECT-TYPE
  SYNTAX  OCTET STRING (SIZE (8)) 	
  ACCESS  read-only
  STATUS  mandatory
  DESCRIPTION 
    "The object indicates MPCP Frames in upstream direction on ONT PON port."
  ::= { eponONTPonCurrent15MinIntervalEntry 45 }
  
eponONTPonCurrent15MinIntervalMPCPFramesDW  OBJECT-TYPE
  SYNTAX  OCTET STRING (SIZE (8)) 	
  ACCESS  read-only
  STATUS  mandatory
  DESCRIPTION 
    "The object indicates MPCP Frames in downstream direction on ONT PON port."
  ::= { eponONTPonCurrent15MinIntervalEntry 46 }

eponONTPonCurrent15MinIntervalMPCPTxregisterframes  OBJECT-TYPE
  SYNTAX  OCTET STRING (SIZE (8)) 	
  ACCESS  read-only
  STATUS  mandatory
  DESCRIPTION 
    "The object indicates Tx MPCP register Frames on ONT PON port."
  ::= { eponONTPonCurrent15MinIntervalEntry 47 }

eponONTPonCurrent15MinIntervalMPCPTxregrequestframes  OBJECT-TYPE
  SYNTAX  OCTET STRING (SIZE (8)) 	
  ACCESS  read-only
  STATUS  mandatory
  DESCRIPTION 
    "The object indicates Tx MPCP registe request Frames on ONT PON port."
  ::= { eponONTPonCurrent15MinIntervalEntry 48 }
  
eponONTPonCurrent15MinIntervalMPCPTxreportframes  OBJECT-TYPE
  SYNTAX  OCTET STRING (SIZE (8)) 	
  ACCESS  read-only
  STATUS  mandatory
  DESCRIPTION 
    "The object indicates Tx MPCP report Frames on ONT PON port."
  ::= { eponONTPonCurrent15MinIntervalEntry 49 }

eponONTPonCurrent15MinIntervalMPCPRxgateframes  OBJECT-TYPE
  SYNTAX  OCTET STRING (SIZE (8)) 	
  ACCESS  read-only
  STATUS  mandatory
  DESCRIPTION 
    "The object indicates Rx MPCP gate Frames on ONT PON port."
  ::= { eponONTPonCurrent15MinIntervalEntry 50 }
  
eponONTPonCurrent15MinIntervalMPCPRxregisterframes  OBJECT-TYPE
  SYNTAX  OCTET STRING (SIZE (8)) 	
  ACCESS  read-only
  STATUS  mandatory
  DESCRIPTION 
    "The object indicates Rx MPCP register Frames on ONT PON port."
  ::= { eponONTPonCurrent15MinIntervalEntry 51 }      

-- *********************************************

-- EPON PON ONT PERFORMANCE TABLE
--
-- This table contains current 1 day performance counters specific to
-- a specific PON port on ONT side. 

-- *********************************************

eponONTPonCurrent1DayIntervalTable  OBJECT-TYPE
	SYNTAX SEQUENCE OF EponONTPonCurrent1DayIntervalEntry
	ACCESS	not-accessible  
	STATUS	mandatory  
	DESCRIPTION
	"1 day current statistics for ONT pon interface.
	 ALCATEL NOTE:
             SUPPORT: YES   TABLESIZE: DEP"	
	::= { eponStatisticsGroup 8 }                                                  

eponONTPonCurrent1DayIntervalEntry  OBJECT-TYPE
	SYNTAX 	EponONTPonCurrent1DayIntervalEntry
	ACCESS	not-accessible
	STATUS	mandatory 
	DESCRIPTION
	 "Table entry for the current 1 day statistics counters for ONT pon interface.
          Row creation : an entry is created by the system when this pon interfaces statistics enabled.
          Row deletion :an entry is created by the system when this pon interfaces statistics disabled.
           ALCATEL NOTE:
             SUPPORT: YES"

	INDEX	{eponOntIndex }
	::= { eponONTPonCurrent1DayIntervalTable 1 }

EponONTPonCurrent1DayIntervalEntry ::= SEQUENCE {
	    
	    eponONTPonCurrent1DayIntervalTimeElapsed                INTEGER,                
	    eponONTPonCurrent1DayIntervalTimeMeasured               INTEGER, 
        eponONTPonCurrent1DayIntervalOctetsTransUp		         OCTET STRING (SIZE (8)),
        eponONTPonCurrent1DayIntervalTotalFramesTransUp	     OCTET STRING (SIZE (8)),
        eponONTPonCurrent1DayIntervalFirstSegOctetFramesUp      OCTET STRING (SIZE (8)),
        eponONTPonCurrent1DayIntervalSecondSegOctetFramesUp     OCTET STRING (SIZE (8)),
        eponONTPonCurrent1DayIntervalThirdSegOctetFramesUp      OCTET STRING (SIZE (8)),
        eponONTPonCurrent1DayIntervalFourthSegOctetFramesUp     OCTET STRING (SIZE (8)),
        eponONTPonCurrent1DayIntervalFifthSegOctetFramesUp      OCTET STRING (SIZE (8)),
        eponONTPonCurrent1DayIntervalSixthSegOctetFramesUp      OCTET STRING (SIZE (8)),
        eponONTPonCurrent1DayIntervalLastSegOctetFramesUp       OCTET STRING (SIZE (8)),
        eponONTPonCurrent1DayIntervalOctetsTransDn		         OCTET STRING (SIZE (8)),
        eponONTPonCurrent1DayIntervalTotalFramesTransDn	     OCTET STRING (SIZE (8)),
        eponONTPonCurrent1DayIntervalFirstSegOctetFramesDn      OCTET STRING (SIZE (8)),
        eponONTPonCurrent1DayIntervalSecondSegOctetFramesDn     OCTET STRING (SIZE (8)),
        eponONTPonCurrent1DayIntervalThirdSegOctetFramesDn      OCTET STRING (SIZE (8)),
        eponONTPonCurrent1DayIntervalFourthSegOctetFramesDn     OCTET STRING (SIZE (8)),
        eponONTPonCurrent1DayIntervalFifthSegOctetFramesDn      OCTET STRING (SIZE (8)),
        eponONTPonCurrent1DayIntervalSixthSegOctetFramesDn      OCTET STRING (SIZE (8)),
        eponONTPonCurrent1DayIntervalLastSegOctetFramesDn       OCTET STRING (SIZE (8)),
        eponONTPonCurrent1DayIntervalCRCErrorframe              OCTET STRING (SIZE (8)),
        eponONTPonCurrent1DayIntervalUndersizeframesUp          OCTET STRING (SIZE (8)),
        eponONTPonCurrent1DayIntervalUndersizeframesDn          OCTET STRING (SIZE (8)),
        eponONTPonCurrent1DayIntervalOversizeframesUp           OCTET STRING (SIZE (8)),
        eponONTPonCurrent1DayIntervalOversizeframesDn           OCTET STRING (SIZE (8)),
        eponONTPonCurrent1DayIntervalErrorframesUp              OCTET STRING (SIZE (8)),
        eponONTPonCurrent1DayIntervalErrorframesDn              OCTET STRING (SIZE (8)),
        eponONTPonCurrent1DayIntervalDiscardframesUP            OCTET STRING (SIZE (8)),
        eponONTPonCurrent1DayIntervalDiscardframesDn            OCTET STRING (SIZE (8)),
        eponONTPonCurrent1DayIntervalUcastframesUP              OCTET STRING (SIZE (8)),
        eponONTPonCurrent1DayIntervalUcastframesDn              OCTET STRING (SIZE (8)),
        eponONTPonCurrent1DayIntervalMulticastframesUp          OCTET STRING (SIZE (8)),
        eponONTPonCurrent1DayIntervalMulticastframesDn          OCTET STRING (SIZE (8)),
        eponONTPonCurrent1DayIntervalBroardcastFramesUp         OCTET STRING (SIZE (8)),
        eponONTPonCurrent1DayIntervalBroardcastFramesDn         OCTET STRING (SIZE (8)),
        eponONTPonCurrent1DayIntervalDropEventsUP                OCTET STRING (SIZE (8)),
        eponONTPonCurrent1DayIntervalDropEventsDn                OCTET STRING (SIZE (8)),
        eponONTPonCurrent1DayIntervalFragmentsUP                 OCTET STRING (SIZE (8)),
        eponONTPonCurrent1DayIntervalFragmentsDn                 OCTET STRING (SIZE (8)),
        eponONTPonCurrent1DayIntervalJabberFramesUP           OCTET STRING (SIZE (8)),
        eponONTPonCurrent1DayIntervalJabberFramesDn           OCTET STRING (SIZE (8)),
	eponONTPonCurrent1DayIntervalStatuschange                 OCTET STRING (SIZE (8)),
	eponONTPonCurrent1DayIntervalFECcorrectFrames           OCTET STRING (SIZE (8)),
        eponONTPonCurrent1DayIntervalFECuncorrectFrames         OCTET STRING (SIZE (8)),
        eponONTPonCurrent1DayIntervalMPCPFramesUP               OCTET STRING (SIZE (8)),
        eponONTPonCurrent1DayIntervalMPCPFramesDW               OCTET STRING (SIZE (8)),
        eponONTPonCurrent1DayIntervalMPCPTxregisterframes       OCTET STRING (SIZE (8)),
        eponONTPonCurrent1DayIntervalMPCPTxregrequestframes    OCTET STRING (SIZE (8)),
        eponONTPonCurrent1DayIntervalMPCPTxreportframes         OCTET STRING (SIZE (8)),
        eponONTPonCurrent1DayIntervalMPCPRxgateframes           OCTET STRING (SIZE (8)),
        eponONTPonCurrent1DayIntervalMPCPRxregisterframes       OCTET STRING (SIZE (8))         
}


eponONTPonCurrent1DayIntervalTimeElapsed  OBJECT-TYPE 
        SYNTAX    INTEGER 
        ACCESS    read-only 
        STATUS    mandatory 
        DESCRIPTION 
            "Elapsed time in interval (seconds)
            ALCATEL NOTE:
                ACCESS:     NA       USAGE:      NA
                PERSIST:    NO       INSRVMOD:   NO
                RANGE:      NA       DEFVALUE:   NA
                UNITS:      seconds  SPARSE:     NA
                DESCR:      NA"
::= { eponONTPonCurrent1DayIntervalEntry 1 } 

eponONTPonCurrent1DayIntervalTimeMeasured  OBJECT-TYPE 
        SYNTAX    INTEGER 
        ACCESS    read-only 
        STATUS    mandatory 
        DESCRIPTION 
            "Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
::= { eponONTPonCurrent1DayIntervalEntry 2 } 

eponONTPonCurrent1DayIntervalOctetsTransUp  OBJECT-TYPE
	SYNTAX 	OCTET STRING (SIZE (8)) 	
	ACCESS	read-only
	STATUS	mandatory
	DESCRIPTION 
		"The object indicates octets transferred	in upstream direction on ONT PON port.
		 ALCATEL NOTE:
                 ACCESS:     NA       USAGE:      NA
                 PERSIST:    NO       INSRVMOD:   NO
                 RANGE:      NA       DEFVALUE:   0
                 UNITS:      NA       SPARSE:     NA
                 DESCR:      NA"

::= { eponONTPonCurrent1DayIntervalEntry 3 }


eponONTPonCurrent1DayIntervalTotalFramesTransUp  OBJECT-TYPE
	SYNTAX 	OCTET STRING (SIZE (8)) 	
	ACCESS	read-only
	STATUS	mandatory
	DESCRIPTION 
		"The object indicates Total Frames transferred 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 4 }
	
	
eponONTPonCurrent1DayIntervalFirstSegOctetFramesUp	  OBJECT-TYPE
	SYNTAX 	OCTET STRING (SIZE (8)) 	
	ACCESS	read-only
	STATUS	mandatory
	DESCRIPTION 
		"The object indicates 64 Octet Frames	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 5 }
	
eponONTPonCurrent1DayIntervalSecondSegOctetFramesUp	  OBJECT-TYPE
	SYNTAX 	OCTET STRING (SIZE (8)) 	
	ACCESS	read-only
	STATUS	mandatory
	DESCRIPTION 
		"The object indicates 65-127 Octet Frames in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 6 }
	
eponONTPonCurrent1DayIntervalThirdSegOctetFramesUp	  OBJECT-TYPE
	SYNTAX 	OCTET STRING (SIZE (8)) 	
	ACCESS	read-only
	STATUS	mandatory
	DESCRIPTION 
		"The object indicates 128-255 Octet Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 7 }
	
eponONTPonCurrent1DayIntervalFourthSegOctetFramesUp	  OBJECT-TYPE
	SYNTAX 	OCTET STRING (SIZE (8)) 	
	ACCESS	read-only
	STATUS	mandatory
	DESCRIPTION 
		"The object indicates 256-511 Octet Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 8 }
	
eponONTPonCurrent1DayIntervalFifthSegOctetFramesUp	  OBJECT-TYPE
	SYNTAX 	OCTET STRING (SIZE (8)) 	
	ACCESS	read-only
	STATUS	mandatory
	DESCRIPTION 
		"The object indicates 512-1023 Octet Frames in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 9}
	
eponONTPonCurrent1DayIntervalSixthSegOctetFramesUp	  OBJECT-TYPE
	SYNTAX 	OCTET STRING (SIZE (8)) 	
	ACCESS	read-only
	STATUS	mandatory
	DESCRIPTION 
		"The object indicates 1024-1518 Octet Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 10 }
	
eponONTPonCurrent1DayIntervalLastSegOctetFramesUp	  OBJECT-TYPE
	SYNTAX 	OCTET STRING (SIZE (8)) 	
	ACCESS	read-only
	STATUS	mandatory
	DESCRIPTION 
		"The object indicates 1519+ Octet Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 11 }
	
eponONTPonCurrent1DayIntervalOctetsTransDn  OBJECT-TYPE
	SYNTAX 	OCTET STRING (SIZE (8)) 	
	ACCESS	read-only
	STATUS	mandatory
	DESCRIPTION 
		"The object indicates octets transferred  in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 12 }


eponONTPonCurrent1DayIntervalTotalFramesTransDn  OBJECT-TYPE
	SYNTAX 	OCTET STRING (SIZE (8)) 	
	ACCESS	read-only
	STATUS	mandatory
	DESCRIPTION 
		"The object indicates Total Frames transferred 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 13 }
	
	
eponONTPonCurrent1DayIntervalFirstSegOctetFramesDn	  OBJECT-TYPE
	SYNTAX 	OCTET STRING (SIZE (8)) 	
	ACCESS	read-only
	STATUS	mandatory
	DESCRIPTION 
		"The object indicates 64 Octet Frames in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 14 }
	
eponONTPonCurrent1DayIntervalSecondSegOctetFramesDn	  OBJECT-TYPE
	SYNTAX 	OCTET STRING (SIZE (8)) 	
	ACCESS	read-only
	STATUS	mandatory
	DESCRIPTION 
		"The object indicates 65-127 Octet Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 15 }
	
eponONTPonCurrent1DayIntervalThirdSegOctetFramesDn	  OBJECT-TYPE
	SYNTAX 	OCTET STRING (SIZE (8)) 	
	ACCESS	read-only
	STATUS	mandatory
	DESCRIPTION 
		"The object indicates 128-255 Octet Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 16 }
	
eponONTPonCurrent1DayIntervalFourthSegOctetFramesDn	  OBJECT-TYPE
	SYNTAX 	OCTET STRING (SIZE (8)) 	
	ACCESS	read-only
	STATUS	mandatory
	DESCRIPTION 
		"The object indicates 256-511 Octet Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 17 }
	
eponONTPonCurrent1DayIntervalFifthSegOctetFramesDn	  OBJECT-TYPE
	SYNTAX 	OCTET STRING (SIZE (8)) 	
	ACCESS	read-only
	STATUS	mandatory
	DESCRIPTION 
		"The object indicates 512-1023 Octet Frames in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 18 }
	
eponONTPonCurrent1DayIntervalSixthSegOctetFramesDn	  OBJECT-TYPE
	SYNTAX 	OCTET STRING (SIZE (8)) 	
	ACCESS	read-only
	STATUS	mandatory
	DESCRIPTION 
		"The object indicates 1024-1518 Octet Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 19 }
	
eponONTPonCurrent1DayIntervalLastSegOctetFramesDn	  OBJECT-TYPE
	SYNTAX 	OCTET STRING (SIZE (8)) 	
	ACCESS	read-only
	STATUS	mandatory
	DESCRIPTION 
		"The object indicates 1519+ Octet Frames in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 20 }

eponONTPonCurrent1DayIntervalCRCErrorframe	  OBJECT-TYPE
	SYNTAX 	OCTET STRING (SIZE (8)) 	
	ACCESS	read-only
	STATUS	mandatory
	DESCRIPTION 
		"The object indicates CRC error Frames on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 21 }         

eponONTPonCurrent1DayIntervalUndersizeframesUp	  OBJECT-TYPE
	SYNTAX 	OCTET STRING (SIZE (8)) 	
	ACCESS	read-only
	STATUS	mandatory
	DESCRIPTION 
		"The object indicates less than 64 bytes Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 22 }         

eponONTPonCurrent1DayIntervalUndersizeframesDn	  OBJECT-TYPE
	SYNTAX 	OCTET STRING (SIZE (8)) 	
	ACCESS	read-only
	STATUS	mandatory
	DESCRIPTION 
		"The object indicates less than 64 bytes Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 23 }         

eponONTPonCurrent1DayIntervalOversizeframesUp	  OBJECT-TYPE
	SYNTAX 	OCTET STRING (SIZE (8)) 	
	ACCESS	read-only
	STATUS	mandatory
	DESCRIPTION 
		"The object indicates 1526+ Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 24 }         

eponONTPonCurrent1DayIntervalOversizeframesDn	  OBJECT-TYPE
	SYNTAX 	OCTET STRING (SIZE (8)) 	
	ACCESS	read-only
	STATUS	mandatory
	DESCRIPTION 
		"The object indicates 1526+ Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 25 }         

eponONTPonCurrent1DayIntervalErrorframesUp	  OBJECT-TYPE
	SYNTAX 	OCTET STRING (SIZE (8)) 	
	ACCESS	read-only
	STATUS	mandatory
	DESCRIPTION 
		"The object indicates error Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 26 }         

eponONTPonCurrent1DayIntervalErrorframesDn	  OBJECT-TYPE
	SYNTAX 	OCTET STRING (SIZE (8)) 	
	ACCESS	read-only
	STATUS	mandatory
	DESCRIPTION 
		"The object indicates error Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 27 }         

eponONTPonCurrent1DayIntervalDiscardframesUP	  OBJECT-TYPE
	SYNTAX 	OCTET STRING (SIZE (8)) 	
	ACCESS	read-only
	STATUS	mandatory
	DESCRIPTION 
		"The object indicates discard Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 28 }         

eponONTPonCurrent1DayIntervalDiscardframesDn	  OBJECT-TYPE
	SYNTAX 	OCTET STRING (SIZE (8)) 	
	ACCESS	read-only
	STATUS	mandatory
	DESCRIPTION 
		"The object indicates discard Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 29 }         

eponONTPonCurrent1DayIntervalUcastframesUP	  OBJECT-TYPE
	SYNTAX 	OCTET STRING (SIZE (8)) 	
	ACCESS	read-only
	STATUS	mandatory
	DESCRIPTION 
		"The object indicates unicast Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 30 }         

eponONTPonCurrent1DayIntervalUcastframesDn	  OBJECT-TYPE
	SYNTAX 	OCTET STRING (SIZE (8)) 	
	ACCESS	read-only
	STATUS	mandatory
	DESCRIPTION 
		"The object indicates unicast Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 31 }         

eponONTPonCurrent1DayIntervalMulticastframesUp	  OBJECT-TYPE
	SYNTAX 	OCTET STRING (SIZE (8)) 	
	ACCESS	read-only
	STATUS	mandatory
	DESCRIPTION 
		"The object indicates multicast Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 32 }         

eponONTPonCurrent1DayIntervalMulticastframesDn	  OBJECT-TYPE
	SYNTAX 	OCTET STRING (SIZE (8)) 	
	ACCESS	read-only
	STATUS	mandatory
	DESCRIPTION 
		"The object indicates multicast Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 33 }         

eponONTPonCurrent1DayIntervalBroardcastFramesUp	  OBJECT-TYPE
	SYNTAX 	OCTET STRING (SIZE (8)) 	
	ACCESS	read-only
	STATUS	mandatory
	DESCRIPTION 
		"The object indicates boardcast Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 34 }         

eponONTPonCurrent1DayIntervalBroardcastFramesDn	  OBJECT-TYPE
	SYNTAX 	OCTET STRING (SIZE (8)) 	
	ACCESS	read-only
	STATUS	mandatory
	DESCRIPTION 
		"The object indicates boardcast Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 35 } 

eponONTPonCurrent1DayIntervalDropEventsUP  OBJECT-TYPE
	SYNTAX 	OCTET STRING (SIZE (8)) 	
	ACCESS	read-only
	STATUS	mandatory
	DESCRIPTION 
		"The object indicates drop event in upstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 36 }     

eponONTPonCurrent1DayIntervalDropEventsDn   OBJECT-TYPE
	SYNTAX 	OCTET STRING (SIZE (8)) 	
	ACCESS	read-only
	STATUS	mandatory
	DESCRIPTION 
		"The object indicates drop event in downstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 37 }     

eponONTPonCurrent1DayIntervalFragmentsUP  OBJECT-TYPE
	SYNTAX 	OCTET STRING (SIZE (8)) 	
	ACCESS	read-only
	STATUS	mandatory
	DESCRIPTION 
		"The object indicates fragment frames in upstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 38 }     

eponONTPonCurrent1DayIntervalFragmentsDn	  OBJECT-TYPE
	SYNTAX 	OCTET STRING (SIZE (8)) 	
	ACCESS	read-only
	STATUS	mandatory
	DESCRIPTION 
		"The object indicates fragment frames in downstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 39 }     

eponONTPonCurrent1DayIntervalJabberFramesUP       OBJECT-TYPE
	SYNTAX 	OCTET STRING (SIZE (8)) 	
	ACCESS	read-only
	STATUS	mandatory
	DESCRIPTION 
		"The object indicates jabber  frames in upstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 40 }     

eponONTPonCurrent1DayIntervalJabberFramesDn      OBJECT-TYPE
	SYNTAX 	OCTET STRING (SIZE (8)) 	
	ACCESS	read-only
	STATUS	mandatory
	DESCRIPTION 
		"The object indicates jabber  frames in downstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 41 }     

eponONTPonCurrent1DayIntervalStatuschange         OBJECT-TYPE
	SYNTAX 	OCTET STRING (SIZE (8)) 	
	ACCESS	read-only
	STATUS	mandatory
	DESCRIPTION 
		"The object indicates the number of status change on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonCurrent1DayIntervalEntry 42 }     

eponONTPonCurrent1DayIntervalFECcorrectFrames  OBJECT-TYPE
  SYNTAX  OCTET STRING (SIZE (8)) 	
  ACCESS  read-only
  STATUS  mandatory
  DESCRIPTION 
    "eponONTPonCurrent1DayIntervalFECcorrectFrames"
  ::= { eponONTPonCurrent1DayIntervalEntry 43 }

eponONTPonCurrent1DayIntervalFECuncorrectFrames  OBJECT-TYPE
  SYNTAX  OCTET STRING (SIZE (8)) 	
  ACCESS  read-only
  STATUS  mandatory
  DESCRIPTION 
    "eponONTPonCurrent1DayIntervalFECuncorrectFrames"
  ::= { eponONTPonCurrent1DayIntervalEntry 44 }
  
eponONTPonCurrent1DayIntervalMPCPFramesUP  OBJECT-TYPE
  SYNTAX  OCTET STRING (SIZE (8)) 	
  ACCESS  read-only
  STATUS  mandatory
  DESCRIPTION 
    "eponONTPonCurrent1DayIntervalMPCPFramesUP"
  ::= { eponONTPonCurrent1DayIntervalEntry 45 }
  
eponONTPonCurrent1DayIntervalMPCPFramesDW  OBJECT-TYPE
  SYNTAX  OCTET STRING (SIZE (8)) 	
  ACCESS  read-only
  STATUS  mandatory
  DESCRIPTION 
    "eponONTPonCurrent1DayIntervalMPCPFramesDW"
  ::= { eponONTPonCurrent1DayIntervalEntry 46 }

eponONTPonCurrent1DayIntervalMPCPTxregisterframes  OBJECT-TYPE
  SYNTAX  OCTET STRING (SIZE (8)) 	
  ACCESS  read-only
  STATUS  mandatory
  DESCRIPTION 
    "eponONTPonCurrent1DayIntervalMPCPTxregisterframes"
  ::= { eponONTPonCurrent1DayIntervalEntry 47 }

eponONTPonCurrent1DayIntervalMPCPTxregrequestframes  OBJECT-TYPE
  SYNTAX  OCTET STRING (SIZE (8)) 	
  ACCESS  read-only
  STATUS  mandatory
  DESCRIPTION 
    "eponONTPonCurrent1DayIntervalMPCPTxregrequestframes"
  ::= { eponONTPonCurrent1DayIntervalEntry 48 }
  
eponONTPonCurrent1DayIntervalMPCPTxreportframes  OBJECT-TYPE
  SYNTAX  OCTET STRING (SIZE (8)) 	
  ACCESS  read-only
  STATUS  mandatory
  DESCRIPTION 
    "eponONTPonCurrent1DayIntervalMPCPTxreportframes"
  ::= { eponONTPonCurrent1DayIntervalEntry 49 }

eponONTPonCurrent1DayIntervalMPCPRxgateframes  OBJECT-TYPE
  SYNTAX  OCTET STRING (SIZE (8)) 	
  ACCESS  read-only
  STATUS  mandatory
  DESCRIPTION 
    "eponONTPonCurrent1DayIntervalMPCPRxgateframes"
  ::= { eponONTPonCurrent1DayIntervalEntry 50 }
  
eponONTPonCurrent1DayIntervalMPCPRxregisterframes  OBJECT-TYPE
  SYNTAX  OCTET STRING (SIZE (8)) 	
  ACCESS  read-only
  STATUS  mandatory
  DESCRIPTION 
    "eponONTPonCurrent1DayIntervalMPCPRxregisterframes"
  ::= { eponONTPonCurrent1DayIntervalEntry 51 }          

-- *********************************************

-- EPON PON ONT PERFORMANCE TABLE
--
-- This table contains previous 15 min performance counters specific to
-- a specific PON port on ONT side. 

-- *********************************************

eponONTPonPrevious15MinIntervalTable  OBJECT-TYPE
	SYNTAX SEQUENCE OF EponONTPonPrevious15MinIntervalEntry
	ACCESS	not-accessible
	STATUS	mandatory  
	DESCRIPTION
	"15 Minutes previous statistics for ONT pon interface.
	 ALCATEL NOTE:
             SUPPORT: YES   TABLESIZE: DEP"

	::= { eponStatisticsGroup 9 }                                                  

eponONTPonPrevious15MinIntervalEntry  OBJECT-TYPE
	SYNTAX 	EponONTPonPrevious15MinIntervalEntry
	ACCESS	not-accessible
	STATUS	mandatory 
	DESCRIPTION 
	 "	Table entry for the previous 15 minutes statistics counters for ONT pon interface.
          Row creation : an entry is created by the system when this pon interfaces statistics enabled.
          Row deletion :an entry is created by the system when this pon interfaces statistics disabled.
           ALCATEL NOTE:
             SUPPORT: YES"

	INDEX	{ eponOntIndex,
	          eponONTPonPrevious15MinIntervalNumber }
	::= { eponONTPonPrevious15MinIntervalTable 1 }

EponONTPonPrevious15MinIntervalEntry ::= SEQUENCE {
	  
	    eponONTPonPrevious15MinIntervalNumber                     INTEGER,                
	    eponONTPonPrevious15MinIntervalTimeMeasured               INTEGER, 
        eponONTPonPrevious15MinIntervalOctetsTransUp		      OCTET STRING (SIZE (8)),
        eponONTPonPrevious15MinIntervalTotalFramesTransUp	      OCTET STRING (SIZE (8)),
        eponONTPonPrevious15MinIntervalFirstSegOctetFramesUp      OCTET STRING (SIZE (8)),
        eponONTPonPrevious15MinIntervalSecondSegOctetFramesUp     OCTET STRING (SIZE (8)),
        eponONTPonPrevious15MinIntervalThirdSegOctetFramesUp      OCTET STRING (SIZE (8)),
        eponONTPonPrevious15MinIntervalFourthSegOctetFramesUp     OCTET STRING (SIZE (8)),
        eponONTPonPrevious15MinIntervalFifthSegOctetFramesUp      OCTET STRING (SIZE (8)),
        eponONTPonPrevious15MinIntervalSixthSegOctetFramesUp      OCTET STRING (SIZE (8)),
        eponONTPonPrevious15MinIntervalLastSegOctetFramesUp       OCTET STRING (SIZE (8)),
        eponONTPonPrevious15MinIntervalOctetsTransDn		      OCTET STRING (SIZE (8)),
        eponONTPonPrevious15MinIntervalTotalFramesTransDn	      OCTET STRING (SIZE (8)),
        eponONTPonPrevious15MinIntervalFirstSegOctetFramesDn      OCTET STRING (SIZE (8)),
        eponONTPonPrevious15MinIntervalSecondSegOctetFramesDn     OCTET STRING (SIZE (8)),
        eponONTPonPrevious15MinIntervalThirdSegOctetFramesDn      OCTET STRING (SIZE (8)),
        eponONTPonPrevious15MinIntervalFourthSegOctetFramesDn     OCTET STRING (SIZE (8)),
        eponONTPonPrevious15MinIntervalFifthSegOctetFramesDn      OCTET STRING (SIZE (8)),
        eponONTPonPrevious15MinIntervalSixthSegOctetFramesDn      OCTET STRING (SIZE (8)),
        eponONTPonPrevious15MinIntervalLastSegOctetFramesDn       OCTET STRING (SIZE (8)),
        eponONTPonPrevious15MinIntervalCRCErrorframe              OCTET STRING (SIZE (8)),
        eponONTPonPrevious15MinIntervalUndersizeframesUp          OCTET STRING (SIZE (8)),
        eponONTPonPrevious15MinIntervalUndersizeframesDn          OCTET STRING (SIZE (8)),
        eponONTPonPrevious15MinIntervalOversizeframesUp           OCTET STRING (SIZE (8)),
        eponONTPonPrevious15MinIntervalOversizeframesDn           OCTET STRING (SIZE (8)),
        eponONTPonPrevious15MinIntervalErrorframesUp              OCTET STRING (SIZE (8)),
        eponONTPonPrevious15MinIntervalErrorframesDn              OCTET STRING (SIZE (8)),
        eponONTPonPrevious15MinIntervalDiscardframesUP            OCTET STRING (SIZE (8)),
        eponONTPonPrevious15MinIntervalDiscardframesDn            OCTET STRING (SIZE (8)),
        eponONTPonPrevious15MinIntervalUcastframesUP              OCTET STRING (SIZE (8)),
        eponONTPonPrevious15MinIntervalUcastframesDn              OCTET STRING (SIZE (8)),
        eponONTPonPrevious15MinIntervalMulticastframesUp          OCTET STRING (SIZE (8)),
        eponONTPonPrevious15MinIntervalMulticastframesDn           OCTET STRING (SIZE (8)),
        eponONTPonPrevious15MinIntervalBroardcastFramesUp         OCTET STRING (SIZE (8)),
        eponONTPonPrevious15MinIntervalBroardcastFramesDn         OCTET STRING (SIZE (8)),
        eponONTPonPrevious15MinIntervalDropEventsUP                   OCTET STRING (SIZE (8)),
        eponONTPonPrevious15MinIntervalDropEventsDn                    OCTET STRING (SIZE (8)),
        eponONTPonPrevious15MinIntervalFragmentsUP                     OCTET STRING (SIZE (8)),
        eponONTPonPrevious15MinIntervalFragmentsDn                     OCTET STRING (SIZE (8)),
        eponONTPonPrevious15MinIntervalJabberFramesUP               OCTET STRING (SIZE (8)),
        eponONTPonPrevious15MinIntervalJabberFramesDn               OCTET STRING (SIZE (8)),
        eponONTPonPrevious15MinIntervalStatuschange                     OCTET STRING (SIZE (8)), 
        eponONTPonPrevious15MinIntervalFECcorrectFrames           OCTET STRING (SIZE (8)),
        eponONTPonPrevious15MinIntervalFECuncorrectFrames         OCTET STRING (SIZE (8)),
        eponONTPonPrevious15MinIntervalMPCPFramesUP               OCTET STRING (SIZE (8)),
        eponONTPonPrevious15MinIntervalMPCPFramesDW               OCTET STRING (SIZE (8)),
        eponONTPonPrevious15MinIntervalMPCPTxregisterframes       OCTET STRING (SIZE (8)),
        eponONTPonPrevious15MinIntervalMPCPTxregrequestframes    OCTET STRING (SIZE (8)),
        eponONTPonPrevious15MinIntervalMPCPTxreportframes         OCTET STRING (SIZE (8)),
        eponONTPonPrevious15MinIntervalMPCPRxgateframes           OCTET STRING (SIZE (8)),
        eponONTPonPrevious15MinIntervalMPCPRxregisterframes       OCTET STRING (SIZE (8)) 
        
}


eponONTPonPrevious15MinIntervalNumber  OBJECT-TYPE 
        SYNTAX    INTEGER  (1..192)
        ACCESS    not-accessible 
        STATUS    mandatory 
        DESCRIPTION 
            "Previous interval reference
             ALCATEL NOTE:
                 ACCESS:     NA       USAGE:      NA
                 PERSIST:    NO       INSRVMOD:   NO
                 RANGE:      1..192       DEFVALUE:   NA
                 UNITS:      NA       SPARSE:     NA
                 DESCR:      NA"
::= { eponONTPonPrevious15MinIntervalEntry 1 } 

eponONTPonPrevious15MinIntervalTimeMeasured  OBJECT-TYPE 
        SYNTAX    INTEGER 
        ACCESS    read-only 
        STATUS    mandatory 
        DESCRIPTION 
           "Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
::= { eponONTPonPrevious15MinIntervalEntry 2 } 

eponONTPonPrevious15MinIntervalOctetsTransUp  OBJECT-TYPE
	SYNTAX 	OCTET STRING (SIZE (8)) 	
	ACCESS	read-only
	STATUS	mandatory
	DESCRIPTION 
		"The object indicates octets transferredin upstream direction on ONT PON port.
		 ALCATEL NOTE:
                 ACCESS:     NA       USAGE:      NA
                 PERSIST:    NO       INSRVMOD:   NO
                 RANGE:      NA       DEFVALUE:   0
                 UNITS:      NA       SPARSE:     NA
                 DESCR:      NA"
::= { eponONTPonPrevious15MinIntervalEntry 3 }


eponONTPonPrevious15MinIntervalTotalFramesTransUp  OBJECT-TYPE
	SYNTAX 	OCTET STRING (SIZE (8)) 	
	ACCESS	read-only
	STATUS	mandatory
	DESCRIPTION 
		"The object indicates Total Frames transferred 	in upstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 4 }
	
	
eponONTPonPrevious15MinIntervalFirstSegOctetFramesUp	  OBJECT-TYPE
	SYNTAX 	OCTET STRING (SIZE (8)) 	
	ACCESS	read-only
	STATUS	mandatory
	DESCRIPTION 
		"The object indicates 64 Octet Frames	in upstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 5 }
	
eponONTPonPrevious15MinIntervalSecondSegOctetFramesUp	  OBJECT-TYPE
	SYNTAX 	OCTET STRING (SIZE (8)) 	
	ACCESS	read-only
	STATUS	mandatory
	DESCRIPTION 
		"The object indicates 65-127 Octet Frames 	in upstream direction on ONT PON port
ALCATEL NOTE:
                 ACCESS:     NA       USAGE:      NA
                 PERSIST:    NO       INSRVMOD:   NO
                 RANGE:      NA       DEFVALUE:   NA
                 UNITS:      NA       SPARSE:     NA
                 DESCR:      NA
"
	::= { eponONTPonPrevious15MinIntervalEntry 6 }
	
eponONTPonPrevious15MinIntervalThirdSegOctetFramesUp	  OBJECT-TYPE
	SYNTAX 	OCTET STRING (SIZE (8)) 	
	ACCESS	read-only
	STATUS	mandatory
	DESCRIPTION 
		"The object indicates 128-255 Octet Frames in upstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 7 }
	
eponONTPonPrevious15MinIntervalFourthSegOctetFramesUp	  OBJECT-TYPE
	SYNTAX 	OCTET STRING (SIZE (8)) 	
	ACCESS	read-only
	STATUS	mandatory
	DESCRIPTION 
		"The object indicates 256-511 Octet Frames 	in upstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 8 }
	
eponONTPonPrevious15MinIntervalFifthSegOctetFramesUp	  OBJECT-TYPE
	SYNTAX 	OCTET STRING (SIZE (8)) 	
	ACCESS	read-only
	STATUS	mandatory
	DESCRIPTION 
		"The object indicates 512-1023 Octet Frames in upstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 9 }
	
eponONTPonPrevious15MinIntervalSixthSegOctetFramesUp	  OBJECT-TYPE
	SYNTAX 	OCTET STRING (SIZE (8)) 	
	ACCESS	read-only
	STATUS	mandatory
	DESCRIPTION 
		"The object indicates 1024-1518 Octet Framesin upstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 10 }
	
eponONTPonPrevious15MinIntervalLastSegOctetFramesUp	  OBJECT-TYPE
	SYNTAX 	OCTET STRING (SIZE (8)) 	
	ACCESS	read-only
	STATUS	mandatory
	DESCRIPTION 
		"The object indicates 1519+ Octet Frames in upstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 11 }
	
eponONTPonPrevious15MinIntervalOctetsTransDn  OBJECT-TYPE
	SYNTAX 	OCTET STRING (SIZE (8)) 	
	ACCESS	read-only
	STATUS	mandatory
	DESCRIPTION 
		"The object indicates octets transferred 	 in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 12 }


eponONTPonPrevious15MinIntervalTotalFramesTransDn  OBJECT-TYPE
	SYNTAX 	OCTET STRING (SIZE (8)) 	
	ACCESS	read-only
	STATUS	mandatory
	DESCRIPTION 
		"The object indicates Total Frames transferred 	in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 13 }
	
	
eponONTPonPrevious15MinIntervalFirstSegOctetFramesDn	  OBJECT-TYPE
	SYNTAX 	OCTET STRING (SIZE (8)) 	
	ACCESS	read-only
	STATUS	mandatory
	DESCRIPTION 
		"The object indicates 64 Octet Frames in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 14 }
	
eponONTPonPrevious15MinIntervalSecondSegOctetFramesDn	  OBJECT-TYPE
	SYNTAX 	OCTET STRING (SIZE (8)) 	
	ACCESS	read-only
	STATUS	mandatory
	DESCRIPTION 
		"The object indicates 65-127 Octet Frames 	in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 15 }
	
eponONTPonPrevious15MinIntervalThirdSegOctetFramesDn	  OBJECT-TYPE
	SYNTAX 	OCTET STRING (SIZE (8)) 	
	ACCESS	read-only
	STATUS	mandatory
	DESCRIPTION 
		"The object indicates 128-255 Octet Frames 	in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 16 }
	
eponONTPonPrevious15MinIntervalFourthSegOctetFramesDn	  OBJECT-TYPE
	SYNTAX 	OCTET STRING (SIZE (8)) 	
	ACCESS	read-only
	STATUS	mandatory
	DESCRIPTION 
		"The object indicates 256-511 Octet Frames 	in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 17 }
	
eponONTPonPrevious15MinIntervalFifthSegOctetFramesDn	  OBJECT-TYPE
	SYNTAX 	OCTET STRING (SIZE (8)) 	
	ACCESS	read-only
	STATUS	mandatory
	DESCRIPTION 
		"The object indicates 512-1023 Octet Frames 	in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 18 }
	
eponONTPonPrevious15MinIntervalSixthSegOctetFramesDn	  OBJECT-TYPE
	SYNTAX 	OCTET STRING (SIZE (8)) 	
	ACCESS	read-only
	STATUS	mandatory
	DESCRIPTION 
		"The object indicates 1024-1518 Octet Framesin downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 19}
	
eponONTPonPrevious15MinIntervalLastSegOctetFramesDn	  OBJECT-TYPE
	SYNTAX 	OCTET STRING (SIZE (8)) 	
	ACCESS	read-only
	STATUS	mandatory
	DESCRIPTION 
		"The object indicates 1519+ Octet Frames in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 20}         
	
eponONTPonPrevious15MinIntervalCRCErrorframe	  OBJECT-TYPE
	SYNTAX 	OCTET STRING (SIZE (8)) 	
	ACCESS	read-only
	STATUS	mandatory
	DESCRIPTION 
		"The object indicates CRC error Frames on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 21 }         

eponONTPonPrevious15MinIntervalUndersizeframesUp	  OBJECT-TYPE
	SYNTAX 	OCTET STRING (SIZE (8)) 	
	ACCESS	read-only
	STATUS	mandatory
	DESCRIPTION 
		"The object indicates less than 64 bytes Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 22 }         

eponONTPonPrevious15MinIntervalUndersizeframesDn	  OBJECT-TYPE
	SYNTAX 	OCTET STRING (SIZE (8)) 	
	ACCESS	read-only
	STATUS	mandatory
	DESCRIPTION 
		"The object indicates less than 64 bytes Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 23 }         

eponONTPonPrevious15MinIntervalOversizeframesUp	  OBJECT-TYPE
	SYNTAX 	OCTET STRING (SIZE (8)) 	
	ACCESS	read-only
	STATUS	mandatory
	DESCRIPTION 
		"The object indicates 1526+ Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 24 }         

eponONTPonPrevious15MinIntervalOversizeframesDn	  OBJECT-TYPE
	SYNTAX 	OCTET STRING (SIZE (8)) 	
	ACCESS	read-only
	STATUS	mandatory
	DESCRIPTION 
		"The object indicates 1526+ Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 25 }         

eponONTPonPrevious15MinIntervalErrorframesUp	  OBJECT-TYPE
	SYNTAX 	OCTET STRING (SIZE (8)) 	
	ACCESS	read-only
	STATUS	mandatory
	DESCRIPTION 
		"The object indicates error Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 26 }         

eponONTPonPrevious15MinIntervalErrorframesDn	  OBJECT-TYPE
	SYNTAX 	OCTET STRING (SIZE (8)) 	
	ACCESS	read-only
	STATUS	mandatory
	DESCRIPTION 
		"The object indicates error Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 27 }         

eponONTPonPrevious15MinIntervalDiscardframesUP	  OBJECT-TYPE
	SYNTAX 	OCTET STRING (SIZE (8)) 	
	ACCESS	read-only
	STATUS	mandatory
	DESCRIPTION 
		"The object indicates discard Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 28 }         

eponONTPonPrevious15MinIntervalDiscardframesDn	  OBJECT-TYPE
	SYNTAX 	OCTET STRING (SIZE (8)) 	
	ACCESS	read-only
	STATUS	mandatory
	DESCRIPTION 
		"The object indicates discard Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 29 }         

eponONTPonPrevious15MinIntervalUcastframesUP	  OBJECT-TYPE
	SYNTAX 	OCTET STRING (SIZE (8)) 	
	ACCESS	read-only
	STATUS	mandatory
	DESCRIPTION 
		"The object indicates unicast Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 30 }         

eponONTPonPrevious15MinIntervalUcastframesDn	  OBJECT-TYPE
	SYNTAX 	OCTET STRING (SIZE (8)) 	
	ACCESS	read-only
	STATUS	mandatory
	DESCRIPTION 
		"The object indicates unicast Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 31 }         

eponONTPonPrevious15MinIntervalMulticastframesUp	  OBJECT-TYPE
	SYNTAX 	OCTET STRING (SIZE (8)) 	
	ACCESS	read-only
	STATUS	mandatory
	DESCRIPTION 
		"The object indicates multicast Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 32 }         

eponONTPonPrevious15MinIntervalMulticastframesDn	  OBJECT-TYPE
	SYNTAX 	OCTET STRING (SIZE (8)) 	
	ACCESS	read-only
	STATUS	mandatory
	DESCRIPTION 
		"The object indicates multicast Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 33 }         

eponONTPonPrevious15MinIntervalBroardcastFramesUp	  OBJECT-TYPE
	SYNTAX 	OCTET STRING (SIZE (8)) 	
	ACCESS	read-only
	STATUS	mandatory
	DESCRIPTION 
		"The object indicates boardcast Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 34 }         

eponONTPonPrevious15MinIntervalBroardcastFramesDn	  OBJECT-TYPE
	SYNTAX 	OCTET STRING (SIZE (8)) 	
	ACCESS	read-only
	STATUS	mandatory
	DESCRIPTION 
		"The object indicates boardcast Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 35 }         

eponONTPonPrevious15MinIntervalDropEventsUP	  OBJECT-TYPE
	SYNTAX 	OCTET STRING (SIZE (8)) 	
	ACCESS	read-only
	STATUS	mandatory
	DESCRIPTION 
		"The object indicates drop event in upstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 36 }     

eponONTPonPrevious15MinIntervalDropEventsDn	  OBJECT-TYPE
	SYNTAX 	OCTET STRING (SIZE (8)) 	
	ACCESS	read-only
	STATUS	mandatory
	DESCRIPTION 
		"The object indicates drop event in downstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 37 }     

eponONTPonPrevious15MinIntervalFragmentsUP	  OBJECT-TYPE
	SYNTAX 	OCTET STRING (SIZE (8)) 	
	ACCESS	read-only
	STATUS	mandatory
	DESCRIPTION 
		"The object indicates fragment frames in upstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 38 }     

eponONTPonPrevious15MinIntervalFragmentsDn	  OBJECT-TYPE
	SYNTAX 	OCTET STRING (SIZE (8)) 	
	ACCESS	read-only
	STATUS	mandatory
	DESCRIPTION 
		"The object indicates fragment frames in downstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 39 }     

eponONTPonPrevious15MinIntervalJabberFramesUP    OBJECT-TYPE
	SYNTAX 	OCTET STRING (SIZE (8)) 	
	ACCESS	read-only
	STATUS	mandatory
	DESCRIPTION 
		"The object indicates jabber  frames in upstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 40 }     

eponONTPonPrevious15MinIntervalJabberFramesDn      OBJECT-TYPE
	SYNTAX 	OCTET STRING (SIZE (8)) 	
	ACCESS	read-only
	STATUS	mandatory
	DESCRIPTION 
		"The object indicates jabber  frames in downstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 41 }     

eponONTPonPrevious15MinIntervalStatuschange   OBJECT-TYPE
	SYNTAX 	OCTET STRING (SIZE (8)) 	
	ACCESS	read-only
	STATUS	mandatory
	DESCRIPTION 
		"The object indicates the number of status change on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious15MinIntervalEntry 42 }     

eponONTPonPrevious15MinIntervalFECcorrectFrames  OBJECT-TYPE
  SYNTAX  OCTET STRING (SIZE (8)) 	
  ACCESS  read-only
  STATUS  mandatory
  DESCRIPTION 
    "eponONTPonPrevious15MinIntervalFECcorrectFrames"
  ::= { eponONTPonPrevious15MinIntervalEntry 43 }  

eponONTPonPrevious15MinIntervalFECuncorrectFrames  OBJECT-TYPE
  SYNTAX  OCTET STRING (SIZE (8)) 	
  ACCESS  read-only
  STATUS  mandatory
  DESCRIPTION 
    "eponONTPonPrevious15MinIntervalFECuncorrectFrames"
  ::= { eponONTPonPrevious15MinIntervalEntry 44 }

eponONTPonPrevious15MinIntervalMPCPFramesUP  OBJECT-TYPE
  SYNTAX  OCTET STRING (SIZE (8)) 	
  ACCESS  read-only
  STATUS  mandatory
  DESCRIPTION 
    "eponONTPonPrevious15MinIntervalMPCPFramesUP"
  ::= { eponONTPonPrevious15MinIntervalEntry 45 }  
  
eponONTPonPrevious15MinIntervalMPCPFramesDW  OBJECT-TYPE
  SYNTAX  OCTET STRING (SIZE (8)) 	
  ACCESS  read-only
  STATUS  mandatory
  DESCRIPTION 
    "eponONTPonPrevious15MinIntervalMPCPFramesDW"
  ::= { eponONTPonPrevious15MinIntervalEntry 46 }

eponONTPonPrevious15MinIntervalMPCPTxregisterframes  OBJECT-TYPE
  SYNTAX  OCTET STRING (SIZE (8)) 	
  ACCESS  read-only
  STATUS  mandatory
  DESCRIPTION 
    "eponONTPonPrevious15MinIntervalMPCPTxregisterframes"
  ::= { eponONTPonPrevious15MinIntervalEntry 47 }

eponONTPonPrevious15MinIntervalMPCPTxregrequestframes  OBJECT-TYPE
  SYNTAX  OCTET STRING (SIZE (8)) 	
  ACCESS  read-only
  STATUS  mandatory
  DESCRIPTION 
    "eponONTPonPrevious15MinIntervalMPCPTxregrequestframes"
  ::= { eponONTPonPrevious15MinIntervalEntry 48 } 

eponONTPonPrevious15MinIntervalMPCPTxreportframes  OBJECT-TYPE
  SYNTAX  OCTET STRING (SIZE (8)) 	
  ACCESS  read-only
  STATUS  mandatory
  DESCRIPTION 
    "eponONTPonPrevious15MinIntervalMPCPTxreportframes"
  ::= { eponONTPonPrevious15MinIntervalEntry 49 } 

eponONTPonPrevious15MinIntervalMPCPRxgateframes  OBJECT-TYPE
  SYNTAX  OCTET STRING (SIZE (8)) 	
  ACCESS  read-only
  STATUS  mandatory
  DESCRIPTION 
    "eponONTPonPrevious15MinIntervalMPCPRxgateframes"
  ::= { eponONTPonPrevious15MinIntervalEntry 50 } 
  
eponONTPonPrevious15MinIntervalMPCPRxregisterframes  OBJECT-TYPE
  SYNTAX  OCTET STRING (SIZE (8)) 	
  ACCESS  read-only
  STATUS  mandatory
  DESCRIPTION 
    "eponONTPonPrevious15MinIntervalMPCPRxregisterframes"
  ::= { eponONTPonPrevious15MinIntervalEntry 51 }

-- *********************************************

-- EPON PON ONT PERFORMANCE TABLE
--
-- This table contains Previous 1 day performance counters specific to
-- a specific PON port on ONT side. 

-- *********************************************

eponONTPonPrevious1DayIntervalTable  OBJECT-TYPE
	SYNTAX SEQUENCE OF EponONTPonPrevious1DayIntervalEntry
	ACCESS	not-accessible
	STATUS	mandatory 
	DESCRIPTION  
	"1 day previous statistics for ONT pon interface.
	 ALCATEL NOTE:
             SUPPORT: YES   TABLESIZE: DEP"

	::= { eponStatisticsGroup 10 }                                                  

eponONTPonPrevious1DayIntervalEntry  OBJECT-TYPE
	SYNTAX 	EponONTPonPrevious1DayIntervalEntry
	ACCESS	not-accessible
	STATUS	mandatory
	DESCRIPTION    
	 "	Table entry for the previous 1 day statistics counters for ONT pon interface.
          Row creation : an entry is created by the system when this pon interfaces statistics enabled.
          Row deletion :an entry is created by the system when this pon interfaces statistics disabled.
           ALCATEL NOTE:
             SUPPORT: YES"

	INDEX	{eponOntIndex,
	         eponONTPonPrevious1DayIntervalNumber}
	::= { eponONTPonPrevious1DayIntervalTable 1 }

EponONTPonPrevious1DayIntervalEntry ::= SEQUENCE {
	   
	    eponONTPonPrevious1DayIntervalNumber                     INTEGER,                
	    eponONTPonPrevious1DayIntervalTimeMeasured               INTEGER, 
        eponONTPonPrevious1DayIntervalOctetsTransUp		         OCTET STRING (SIZE (8)),
        eponONTPonPrevious1DayIntervalTotalFramesTransUp	     OCTET STRING (SIZE (8)),
        eponONTPonPrevious1DayIntervalFirstSegOctetFramesUp      OCTET STRING (SIZE (8)),
        eponONTPonPrevious1DayIntervalSecondSegOctetFramesUp     OCTET STRING (SIZE (8)),
        eponONTPonPrevious1DayIntervalThirdSegOctetFramesUp      OCTET STRING (SIZE (8)),
        eponONTPonPrevious1DayIntervalFourthSegOctetFramesUp     OCTET STRING (SIZE (8)),
        eponONTPonPrevious1DayIntervalFifthSegOctetFramesUp      OCTET STRING (SIZE (8)),
        eponONTPonPrevious1DayIntervalSixthSegOctetFramesUp      OCTET STRING (SIZE (8)),
        eponONTPonPrevious1DayIntervalLastSegOctetFramesUp       OCTET STRING (SIZE (8)),
        eponONTPonPrevious1DayIntervalOctetsTransDn		         OCTET STRING (SIZE (8)),
        eponONTPonPrevious1DayIntervalTotalFramesTransDn	     OCTET STRING (SIZE (8)),
        eponONTPonPrevious1DayIntervalFirstSegOctetFramesDn      OCTET STRING (SIZE (8)),
        eponONTPonPrevious1DayIntervalSecondSegOctetFramesDn     OCTET STRING (SIZE (8)),
        eponONTPonPrevious1DayIntervalThirdSegOctetFramesDn      OCTET STRING (SIZE (8)),
        eponONTPonPrevious1DayIntervalFourthSegOctetFramesDn     OCTET STRING (SIZE (8)),
        eponONTPonPrevious1DayIntervalFifthSegOctetFramesDn      OCTET STRING (SIZE (8)),
        eponONTPonPrevious1DayIntervalSixthSegOctetFramesDn      OCTET STRING (SIZE (8)),
        eponONTPonPrevious1DayIntervalLastSegOctetFramesDn       OCTET STRING (SIZE (8)),
        eponONTPonPrevious1DayIntervalCRCErrorframe              OCTET STRING (SIZE (8)),
        eponONTPonPrevious1DayIntervalUndersizeframesUp          OCTET STRING (SIZE (8)),
        eponONTPonPrevious1DayIntervalUndersizeframesDn          OCTET STRING (SIZE (8)),
        eponONTPonPrevious1DayIntervalOversizeframesUp           OCTET STRING (SIZE (8)),
        eponONTPonPrevious1DayIntervalOversizeframesDn           OCTET STRING (SIZE (8)),
        eponONTPonPrevious1DayIntervalErrorframesUp              OCTET STRING (SIZE (8)),
        eponONTPonPrevious1DayIntervalErrorframesDn              OCTET STRING (SIZE (8)),
        eponONTPonPrevious1DayIntervalDiscardframesUP            OCTET STRING (SIZE (8)),
        eponONTPonPrevious1DayIntervalDiscardframesDn            OCTET STRING (SIZE (8)),
        eponONTPonPrevious1DayIntervalUcastframesUP              OCTET STRING (SIZE (8)),
        eponONTPonPrevious1DayIntervalUcastframesDn              OCTET STRING (SIZE (8)),
        eponONTPonPrevious1DayIntervalMulticastframesUp          OCTET STRING (SIZE (8)),
        eponONTPonPrevious1DayIntervalMulticastframesDn          OCTET STRING (SIZE (8)),
        eponONTPonPrevious1DayIntervalBroardcastFramesUp         OCTET STRING (SIZE (8)),
        eponONTPonPrevious1DayIntervalBroardcastFramesDn         OCTET STRING (SIZE (8)),
        eponONTPonPrevious1DayIntervalDropEventsUP                   OCTET STRING (SIZE (8)),
        eponONTPonPrevious1DayIntervalDropEventsDn                    OCTET STRING (SIZE (8)),
        eponONTPonPrevious1DayIntervalFragmentsUP                     OCTET STRING (SIZE (8)),
        eponONTPonPrevious1DayIntervalFragmentsDn                     OCTET STRING (SIZE (8)),
        eponONTPonPrevious1DayIntervalJabberFramesUP               OCTET STRING (SIZE (8)),
        eponONTPonPrevious1DayIntervalJabberFramesDn               OCTET STRING (SIZE (8)),
        eponONTPonPrevious1DayIntervalStatuschange                     OCTET STRING (SIZE (8)),
	eponONTPonPrevious1DayIntervalFECcorrectFrames           OCTET STRING (SIZE (8)),
        eponONTPonPrevious1DayIntervalFECuncorrectFrames         OCTET STRING (SIZE (8)),
        eponONTPonPrevious1DayIntervalMPCPFramesUP               OCTET STRING (SIZE (8)),
        eponONTPonPrevious1DayIntervalMPCPFramesDW               OCTET STRING (SIZE (8)),
        eponONTPonPrevious1DayIntervalMPCPTxregisterframes       OCTET STRING (SIZE (8)),
        eponONTPonPrevious1DayIntervalMPCPTxregrequestframes    OCTET STRING (SIZE (8)),
        eponONTPonPrevious1DayIntervalMPCPTxreportframes         OCTET STRING (SIZE (8)),
        eponONTPonPrevious1DayIntervalMPCPRxgateframes           OCTET STRING (SIZE (8)),
        eponONTPonPrevious1DayIntervalMPCPRxregisterframes       OCTET STRING (SIZE (8)) 
}


eponONTPonPrevious1DayIntervalNumber  OBJECT-TYPE 
        SYNTAX    INTEGER  (1..2)
        ACCESS    not-accessible 
        STATUS    mandatory 
        DESCRIPTION 
            "Previous interval reference 
            ALCATEL NOTE:
 	    ACCESS:     NA       USAGE:      NA
 	    PERSIST:    NO       INSRVMOD:   NO
 	    RANGE:      1..2       DEFVALUE:   NA
 	    UNITS:      NA       SPARSE:     NA
 	    DESCR:      NA

            " 
::= { eponONTPonPrevious1DayIntervalEntry 1 } 

eponONTPonPrevious1DayIntervalTimeMeasured  OBJECT-TYPE 
        SYNTAX    INTEGER 
        ACCESS    read-only 
        STATUS    mandatory 
        DESCRIPTION 
             "Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
::= { eponONTPonPrevious1DayIntervalEntry 2 } 

eponONTPonPrevious1DayIntervalOctetsTransUp  OBJECT-TYPE
	SYNTAX 	OCTET STRING (SIZE (8)) 	
	ACCESS	read-only
	STATUS	mandatory
	DESCRIPTION 
		"The object indicates octets transferred  in upstream direction on ONT PON port.
		 		  ALCATEL NOTE:
                 ACCESS:     NA       USAGE:      NA
                 PERSIST:    NO       INSRVMOD:   NO
                 RANGE:      NA       DEFVALUE:   0
                 UNITS:      NA       SPARSE:     NA
                 DESCR:      NA"

::= { eponONTPonPrevious1DayIntervalEntry 3 }


eponONTPonPrevious1DayIntervalTotalFramesTransUp  OBJECT-TYPE
	SYNTAX 	OCTET STRING (SIZE (8)) 	
	ACCESS	read-only
	STATUS	mandatory
	DESCRIPTION 
		"The object indicates Total Frames transferred 	in upstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 4 }
	
	
eponONTPonPrevious1DayIntervalFirstSegOctetFramesUp	  OBJECT-TYPE
	SYNTAX 	OCTET STRING (SIZE (8)) 	
	ACCESS	read-only
	STATUS	mandatory
	DESCRIPTION 
		"The object indicates 64 Octet Frames 	in upstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 5 }
	
eponONTPonPrevious1DayIntervalSecondSegOctetFramesUp	  OBJECT-TYPE
	SYNTAX 	OCTET STRING (SIZE (8)) 	
	ACCESS	read-only
	STATUS	mandatory
	DESCRIPTION 
		"The object indicates 65-127 Octet Framesin upstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 6 }
	
eponONTPonPrevious1DayIntervalThirdSegOctetFramesUp	  OBJECT-TYPE
	SYNTAX 	OCTET STRING (SIZE (8)) 	
	ACCESS	read-only
	STATUS	mandatory
	DESCRIPTION 
		"The object indicates 128-255 Octet Frames 	in upstream direction on ONT PON port
 ALCATEL NOTE:
                 ACCESS:     NA       USAGE:      NA
                 PERSIST:    NO       INSRVMOD:   NO
                 RANGE:      NA       DEFVALUE:   0
                 UNITS:      NA       SPARSE:     NA
                 DESCR:      NA"

	::= { eponONTPonPrevious1DayIntervalEntry 7 }
	
eponONTPonPrevious1DayIntervalFourthSegOctetFramesUp	  OBJECT-TYPE
	SYNTAX 	OCTET STRING (SIZE (8)) 	
	ACCESS	read-only
	STATUS	mandatory
	DESCRIPTION 
		"The object indicates 256-511 Octet Frames 	in upstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 8 }
	
eponONTPonPrevious1DayIntervalFifthSegOctetFramesUp	  OBJECT-TYPE
	SYNTAX 	OCTET STRING (SIZE (8)) 	
	ACCESS	read-only
	STATUS	mandatory
	DESCRIPTION 
		"The object indicates 512-1023 Octet Frames in upstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 9 }
	
eponONTPonPrevious1DayIntervalSixthSegOctetFramesUp	  OBJECT-TYPE
	SYNTAX 	OCTET STRING (SIZE (8)) 	
	ACCESS	read-only
	STATUS	mandatory
	DESCRIPTION 
		"The object indicates 1024-1518 Octet Frames 	in upstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 10 }
	
eponONTPonPrevious1DayIntervalLastSegOctetFramesUp	  OBJECT-TYPE
	SYNTAX 	OCTET STRING (SIZE (8)) 	
	ACCESS	read-only
	STATUS	mandatory
	DESCRIPTION 
		"The object indicates 1519+ Octet Frames in upstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 11 }
	
eponONTPonPrevious1DayIntervalOctetsTransDn  OBJECT-TYPE
	SYNTAX 	OCTET STRING (SIZE (8)) 	
	ACCESS	read-only
	STATUS	mandatory
	DESCRIPTION 
		"The object indicates octets transferred in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 12 }


eponONTPonPrevious1DayIntervalTotalFramesTransDn  OBJECT-TYPE
	SYNTAX 	OCTET STRING (SIZE (8)) 	
	ACCESS	read-only
	STATUS	mandatory
	DESCRIPTION 
		"The object indicates Total Frames transferred 	in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 13 }
	
	
eponONTPonPrevious1DayIntervalFirstSegOctetFramesDn	  OBJECT-TYPE
	SYNTAX 	OCTET STRING (SIZE (8)) 	
	ACCESS	read-only
	STATUS	mandatory
	DESCRIPTION 
		"The object indicates 64 Octet Frames 	in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"

	::= { eponONTPonPrevious1DayIntervalEntry 14 }
	
eponONTPonPrevious1DayIntervalSecondSegOctetFramesDn	  OBJECT-TYPE
	SYNTAX 	OCTET STRING (SIZE (8)) 	
	ACCESS	read-only
	STATUS	mandatory
	DESCRIPTION 
		"The object indicates 65-127 Octet Frames 	in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 15 }
	
eponONTPonPrevious1DayIntervalThirdSegOctetFramesDn	  OBJECT-TYPE
	SYNTAX 	OCTET STRING (SIZE (8)) 	
	ACCESS	read-only
	STATUS	mandatory
	DESCRIPTION 
		"The object indicates 128-255 Octet Frames 	in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 16 }
	
eponONTPonPrevious1DayIntervalFourthSegOctetFramesDn	  OBJECT-TYPE
	SYNTAX 	OCTET STRING (SIZE (8)) 	
	ACCESS	read-only
	STATUS	mandatory
	DESCRIPTION 
		"The object indicates 256-511 Octet Frames 	in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 17 }
	
eponONTPonPrevious1DayIntervalFifthSegOctetFramesDn	  OBJECT-TYPE
	SYNTAX 	OCTET STRING (SIZE (8)) 	
	ACCESS	read-only
	STATUS	mandatory
	DESCRIPTION 
		"The object indicates 512-1023 Octet Frames 	in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 18 }
	
eponONTPonPrevious1DayIntervalSixthSegOctetFramesDn	  OBJECT-TYPE
	SYNTAX 	OCTET STRING (SIZE (8)) 	
	ACCESS	read-only
	STATUS	mandatory
	DESCRIPTION 
		"The object indicates 1024-1518 Octet Frames in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 19}
	
eponONTPonPrevious1DayIntervalLastSegOctetFramesDn	  OBJECT-TYPE
	SYNTAX 	OCTET STRING (SIZE (8)) 	
	ACCESS	read-only
	STATUS	mandatory
	DESCRIPTION 
		"The object indicates 1519+ Octet Frames 	in downstream direction on ONT PON port
 ALCATEL NOTE:
                 ACCESS:     NA       USAGE:      NA
                 PERSIST:    NO       INSRVMOD:   NO
                 RANGE:      NA       DEFVALUE:   0
                 UNITS:      NA       SPARSE:     NA
                 DESCR:      NA"

	::= { eponONTPonPrevious1DayIntervalEntry 20 }

eponONTPonPrevious1DayIntervalCRCErrorframe	  OBJECT-TYPE
	SYNTAX 	OCTET STRING (SIZE (8)) 	
	ACCESS	read-only
	STATUS	mandatory
	DESCRIPTION 
		"The object indicates CRC error Frames on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 21 }         

eponONTPonPrevious1DayIntervalUndersizeframesUp	  OBJECT-TYPE
	SYNTAX 	OCTET STRING (SIZE (8)) 	
	ACCESS	read-only
	STATUS	mandatory
	DESCRIPTION 
		"The object indicates less than 64 bytes Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 22 }         

eponONTPonPrevious1DayIntervalUndersizeframesDn	  OBJECT-TYPE
	SYNTAX 	OCTET STRING (SIZE (8)) 	
	ACCESS	read-only
	STATUS	mandatory
	DESCRIPTION 
		"The object indicates less than 64 bytes Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 23 }         

eponONTPonPrevious1DayIntervalOversizeframesUp	  OBJECT-TYPE
	SYNTAX 	OCTET STRING (SIZE (8)) 	
	ACCESS	read-only
	STATUS	mandatory
	DESCRIPTION 
		"The object indicates 1526+ Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 24 }         

eponONTPonPrevious1DayIntervalOversizeframesDn	  OBJECT-TYPE
	SYNTAX 	OCTET STRING (SIZE (8)) 	
	ACCESS	read-only
	STATUS	mandatory
	DESCRIPTION 
		"The object indicates 1526+ Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 25 }         

eponONTPonPrevious1DayIntervalErrorframesUp	  OBJECT-TYPE
	SYNTAX 	OCTET STRING (SIZE (8)) 	
	ACCESS	read-only
	STATUS	mandatory
	DESCRIPTION 
		"The object indicates error Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 26 }         

eponONTPonPrevious1DayIntervalErrorframesDn	  OBJECT-TYPE
	SYNTAX 	OCTET STRING (SIZE (8)) 	
	ACCESS	read-only
	STATUS	mandatory
	DESCRIPTION 
		"The object indicates error Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 27 }         

eponONTPonPrevious1DayIntervalDiscardframesUP	  OBJECT-TYPE
	SYNTAX 	OCTET STRING (SIZE (8)) 	
	ACCESS	read-only
	STATUS	mandatory
	DESCRIPTION 
		"The object indicates discard Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 28 }         

eponONTPonPrevious1DayIntervalDiscardframesDn	  OBJECT-TYPE
	SYNTAX 	OCTET STRING (SIZE (8)) 	
	ACCESS	read-only
	STATUS	mandatory
	DESCRIPTION 
		"The object indicates discard Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 29 }         

eponONTPonPrevious1DayIntervalUcastframesUP	  OBJECT-TYPE
	SYNTAX 	OCTET STRING (SIZE (8)) 	
	ACCESS	read-only
	STATUS	mandatory
	DESCRIPTION 
		"The object indicates unicast Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 30 }         

eponONTPonPrevious1DayIntervalUcastframesDn	  OBJECT-TYPE
	SYNTAX 	OCTET STRING (SIZE (8)) 	
	ACCESS	read-only
	STATUS	mandatory
	DESCRIPTION 
		"The object indicates unicast Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 31 }         

eponONTPonPrevious1DayIntervalMulticastframesUp	  OBJECT-TYPE
	SYNTAX 	OCTET STRING (SIZE (8)) 	
	ACCESS	read-only
	STATUS	mandatory
	DESCRIPTION 
		"The object indicates multicast Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 32 }         

eponONTPonPrevious1DayIntervalMulticastframesDn	  OBJECT-TYPE
	SYNTAX 	OCTET STRING (SIZE (8)) 	
	ACCESS	read-only
	STATUS	mandatory
	DESCRIPTION 
		"The object indicates multicast Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 33 }         

eponONTPonPrevious1DayIntervalBroardcastFramesUp	  OBJECT-TYPE
	SYNTAX 	OCTET STRING (SIZE (8)) 	
	ACCESS	read-only
	STATUS	mandatory
	DESCRIPTION 
		"The object indicates boardcast Frames 	in upstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 34 }         

eponONTPonPrevious1DayIntervalBroardcastFramesDn	  OBJECT-TYPE
	SYNTAX 	OCTET STRING (SIZE (8)) 	
	ACCESS	read-only
	STATUS	mandatory
	DESCRIPTION 
		"The object indicates boardcast Frames 	in downstream direction on ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 35 }    

eponONTPonPrevious1DayIntervalDropEventsUP	  OBJECT-TYPE
	SYNTAX 	OCTET STRING (SIZE (8)) 	
	ACCESS	read-only
	STATUS	mandatory
	DESCRIPTION 
		"The object indicates drop event in upstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 36 }     

eponONTPonPrevious1DayIntervalDropEventsDn	  OBJECT-TYPE
	SYNTAX 	OCTET STRING (SIZE (8)) 	
	ACCESS	read-only
	STATUS	mandatory
	DESCRIPTION 
		"The object indicates drop event in downstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 37 }     

eponONTPonPrevious1DayIntervalFragmentsUP	  OBJECT-TYPE
	SYNTAX 	OCTET STRING (SIZE (8)) 	
	ACCESS	read-only
	STATUS	mandatory
	DESCRIPTION 
		"The object indicates fragment frames in upstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 38 }     

eponONTPonPrevious1DayIntervalFragmentsDn	  OBJECT-TYPE
	SYNTAX 	OCTET STRING (SIZE (8)) 	
	ACCESS	read-only
	STATUS	mandatory
	DESCRIPTION 
		"The object indicates fragment frames in downstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 39 }     

eponONTPonPrevious1DayIntervalJabberFramesUP    OBJECT-TYPE
	SYNTAX 	OCTET STRING (SIZE (8)) 	
	ACCESS	read-only
	STATUS	mandatory
	DESCRIPTION 
		"The object indicates jabber  frames in upstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 40 }     

eponONTPonPrevious1DayIntervalJabberFramesDn      OBJECT-TYPE
	SYNTAX 	OCTET STRING (SIZE (8)) 	
	ACCESS	read-only
	STATUS	mandatory
	DESCRIPTION 
		"The object indicates jabber  frames in downstream direction on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 41 }     

eponONTPonPrevious1DayIntervalStatuschange   OBJECT-TYPE
	SYNTAX 	OCTET STRING (SIZE (8)) 	
	ACCESS	read-only
	STATUS	mandatory
	DESCRIPTION 
		"The object indicates the number of status change on a ONT PON port
ALCATEL NOTE:
                 ACCESS:     NA       USAGE:      NA
                 PERSIST:    NO       INSRVMOD:   NO
                 RANGE:      NA       DEFVALUE:   0
                 UNITS:      NA       SPARSE:     NA
                 DESCR:      NA"
	::= { eponONTPonPrevious1DayIntervalEntry 42 }   
	
eponONTPonPrevious1DayIntervalFECcorrectFrames  OBJECT-TYPE
  SYNTAX  OCTET STRING (SIZE (8)) 	
  ACCESS  read-only
  STATUS  mandatory
  DESCRIPTION 
    "eponONTPonPrevious1DayIntervalFECcorrectFrames"
	::= { eponONTPonPrevious1DayIntervalEntry 43 }

eponONTPonPrevious1DayIntervalFECuncorrectFrames  OBJECT-TYPE
  SYNTAX  OCTET STRING (SIZE (8)) 	
  ACCESS  read-only
  STATUS  mandatory
  DESCRIPTION 
    "eponONTPonPrevious1DayIntervalFECuncorrectFrames"
	::= { eponONTPonPrevious1DayIntervalEntry 44 }

eponONTPonPrevious1DayIntervalMPCPFramesUP  OBJECT-TYPE
  SYNTAX  OCTET STRING (SIZE (8)) 	
  ACCESS  read-only
  STATUS  mandatory
  DESCRIPTION 
    "eponONTPonPrevious1DayIntervalMPCPFramesUP"
	::= { eponONTPonPrevious1DayIntervalEntry 45 }

eponONTPonPrevious1DayIntervalMPCPFramesDW  OBJECT-TYPE
  SYNTAX  OCTET STRING (SIZE (8)) 	
  ACCESS  read-only
  STATUS  mandatory
  DESCRIPTION 
    "eponONTPonPrevious1DayIntervalMPCPFramesDW"
	::= { eponONTPonPrevious1DayIntervalEntry 46 }

eponONTPonPrevious1DayIntervalMPCPTxregisterframes  OBJECT-TYPE
  SYNTAX  OCTET STRING (SIZE (8)) 	
  ACCESS  read-only
  STATUS  mandatory
  DESCRIPTION 
    "eponONTPonPrevious1DayIntervalMPCPTxregrequestframes"
	::= { eponONTPonPrevious1DayIntervalEntry 47 }

eponONTPonPrevious1DayIntervalMPCPTxregrequestframes  OBJECT-TYPE
  SYNTAX  OCTET STRING (SIZE (8)) 	
  ACCESS  read-only
  STATUS  mandatory
  DESCRIPTION 
    "eponONTPonPrevious1DayIntervalMPCPTxregrequestframes"
	::= { eponONTPonPrevious1DayIntervalEntry 48 }

eponONTPonPrevious1DayIntervalMPCPTxreportframes  OBJECT-TYPE
  SYNTAX  OCTET STRING (SIZE (8)) 	
  ACCESS  read-only
  STATUS  mandatory
  DESCRIPTION 
    "eponONTPonPrevious1DayIntervalMPCPTxreportframes"
	::= { eponONTPonPrevious1DayIntervalEntry 49 }

eponONTPonPrevious1DayIntervalMPCPRxgateframes  OBJECT-TYPE
  SYNTAX  OCTET STRING (SIZE (8)) 	
  ACCESS  read-only
  STATUS  mandatory
  DESCRIPTION 
    "eponONTPonPrevious1DayIntervalMPCPRxgateframes"
	::= { eponONTPonPrevious1DayIntervalEntry 50 }

eponONTPonPrevious1DayIntervalMPCPRxregisterframes  OBJECT-TYPE
  SYNTAX  OCTET STRING (SIZE (8)) 	
  ACCESS  read-only
  STATUS  mandatory
  DESCRIPTION 
    "eponONTPonPrevious1DayIntervalMPCPRxregisterframes"
	::= { eponONTPonPrevious1DayIntervalEntry 51 }    

-- *********************************************
--
-- EPON ONT UNI Port Performance TABLE
--
-- Table of number of previous statistics intervals for the traffic on a 
-- ONT UNI Port
--
-- 
-- *********************************************

eponLanEtherPortPerfInfoTable     OBJECT-TYPE 
        SYNTAX    SEQUENCE OF EponLanEtherPortPerfInfoEntry 
        ACCESS    not-accessible 
        STATUS    mandatory 
        DESCRIPTION 
             "Table of number of previous statistics intervals for the traffic on a 
            ONT ethernet interface.  
            ALCATEL NOTE:
             SUPPORT: YES   TABLESIZE: DEP"
::= {eponStatisticsGroup 11 } 

eponLanEtherPortPerfInfoEntry OBJECT-TYPE 
        SYNTAX    EponLanEtherPortPerfInfoEntry 
        ACCESS    not-accessible 
        STATUS    mandatory 
        DESCRIPTION 
            "An entry in the eponLanEtherPortPerfInfoTable  . 
          Row creation : an entry is created by the system when ONT ethernet port level statistics enable. 
          Row creation : an entry is created by the system when ONT ethernet port level statistics enable. 
            ALCATEL NOTE:
             SUPPORT: YES"      
             INDEX   { eponLanEtherPortIfindex } 
::= { eponLanEtherPortPerfInfoTable 1 } 

EponLanEtherPortPerfInfoEntry ::= 
       SEQUENCE{ 
                eponLanEtherPortPerfInfo15MinValidIntervals    INTEGER, 
                 eponLanEtherPortPerfInfo1DayValidIntervals     INTEGER 
                }    
                
 
    
eponLanEtherPortPerfInfo15MinValidIntervals OBJECT-TYPE 
        SYNTAX    INTEGER 
        ACCESS    read-only 
        STATUS    mandatory 
        DESCRIPTION 
           	"Number of previous 15 minutes intervals
             ALCATEL NOTE:
                 ACCESS:     NA       USAGE:      NA
                 PERSIST:    NO       INSRVMOD:   NO
                 RANGE:      NA       DEFVALUE:   0
                 UNITS:      NA       SPARSE:     NA
                 DESCR:      NA"
        ::= { eponLanEtherPortPerfInfoEntry 1 } 
        
eponLanEtherPortPerfInfo1DayValidIntervals OBJECT-TYPE 
        SYNTAX    INTEGER 
        ACCESS     read-only 
        STATUS    mandatory 
        DESCRIPTION 
           	"Number of previous 1 day intervals
             ALCATEL NOTE:
                 ACCESS:     NA       USAGE:      NA
                 PERSIST:    NO       INSRVMOD:   NO
                 RANGE:      NA       DEFVALUE:   0
                 UNITS:      NA       SPARSE:     NA
                 DESCR:      NA"
        ::= { eponLanEtherPortPerfInfoEntry 2 }  
        
-- *********************************************

-- EPON ONT UNI PERFORMANCE TABLE
--
-- This table contains current 15 min performance counters specific to
-- a specific UNI port . 

-- *********************************************

eponLanEtherPortCurrent15MinIntervalTable  OBJECT-TYPE
	SYNTAX SEQUENCE OF EponLanEtherPortCurrent15MinIntervalEntry
	ACCESS	not-accessible 
	STATUS	mandatory 
	DESCRIPTION 
	 "15 Minutes current statistics for ONT ethernet port interface.
	 ALCATEL NOTE:
             SUPPORT: YES   TABLESIZE: DEP"	
	::= { eponStatisticsGroup 12 }                                                  

eponLanEtherPortCurrent15MinIntervalEntry  OBJECT-TYPE
	SYNTAX 	EponLanEtherPortCurrent15MinIntervalEntry
	ACCESS	not-accessible
	STATUS	mandatory 
	DESCRIPTION 
	"Table entry for the current 15 minutes statistics counters for ONT ethernet port interface.
          Row creation : an entry is created by the system when this ONT ethernet port statistics enabled.
          Row deletion :an entry is created by the system when this ONT ethernet port statistics disabled.
           ALCATEL NOTE:
             SUPPORT: YES"

	INDEX	{ eponLanEtherPortIfindex }
	::= { eponLanEtherPortCurrent15MinIntervalTable 1 }

EponLanEtherPortCurrent15MinIntervalEntry ::= SEQUENCE {
	   
	    eponLanEtherPortCurrent15MinIntervalTimeElapsed                INTEGER,                
	    eponLanEtherPortCurrent15MinIntervalTimeMeasured               INTEGER, 
        eponLanEtherPortCurrent15MinIntervalOctetsTransUp		       OCTET STRING (SIZE (8)),
        eponLanEtherPortCurrent15MinIntervalTotalFramesTransUp	       OCTET STRING (SIZE (8)), 
        eponLanEtherPortCurrent15MinBroardFramesTransUp	               OCTET STRING (SIZE (8)),
        eponLanEtherPortCurrent15MinCRCErrorUp	                       OCTET STRING (SIZE (8)),
        eponLanEtherPortCurrent15MinPauseFramesUp	                   OCTET STRING (SIZE (8)),
        eponLanEtherPortCurrent15MinIntervalFirstSegOctetFramesUp      OCTET STRING (SIZE (8)),
        eponLanEtherPortCurrent15MinIntervalSecondSegOctetFramesUp     OCTET STRING (SIZE (8)),
        eponLanEtherPortCurrent15MinIntervalThirdSegOctetFramesUp      OCTET STRING (SIZE (8)),
        eponLanEtherPortCurrent15MinIntervalFourthSegOctetFramesUp     OCTET STRING (SIZE (8)),
        eponLanEtherPortCurrent15MinIntervalFifthSegOctetFramesUp      OCTET STRING (SIZE (8)),
        eponLanEtherPortCurrent15MinIntervalSixthSegOctetFramesUp      OCTET STRING (SIZE (8)),
        eponLanEtherPortCurrent15MinIntervalLastSegOctetFramesUp       OCTET STRING (SIZE (8)),
        eponLanEtherPortCurrent15MinIntervalOctetsTransDn		       OCTET STRING (SIZE (8)),
        eponLanEtherPortCurrent15MinIntervalTotalFramesTransDn	       OCTET STRING (SIZE (8)),
        eponLanEtherPortCurrent15MinBroardFramesTransDn	               OCTET STRING (SIZE (8)),
        eponLanEtherPortCurrent15MinCRCErrorDn	                       OCTET STRING (SIZE (8)),
        eponLanEtherPortCurrent15MinPauseFramesDn	                   OCTET STRING (SIZE (8)),
        eponLanEtherPortCurrent15MinIntervalFirstSegOctetFramesDn      OCTET STRING (SIZE (8)),
        eponLanEtherPortCurrent15MinIntervalSecondSegOctetFramesDn     OCTET STRING (SIZE (8)),
        eponLanEtherPortCurrent15MinIntervalThirdSegOctetFramesDn      OCTET STRING (SIZE (8)),
        eponLanEtherPortCurrent15MinIntervalFourthSegOctetFramesDn     OCTET STRING (SIZE (8)),
        eponLanEtherPortCurrent15MinIntervalFifthSegOctetFramesDn      OCTET STRING (SIZE (8)),
        eponLanEtherPortCurrent15MinIntervalSixthSegOctetFramesDn      OCTET STRING (SIZE (8)),
        eponLanEtherPortCurrent15MinIntervalLastSegOctetFramesDn       OCTET STRING (SIZE (8)),
        eponLanEtherPortCurrent15MinIntervalUcastframesUP	             OCTET STRING (SIZE (8)), 
        eponLanEtherPortCurrent15MinIntervalNUcastframesUP             OCTET STRING (SIZE (8)),
        eponLanEtherPortCurrent15MinIntervalDiscardframesUP	           OCTET STRING (SIZE (8)),        
        eponLanEtherPortCurrent15MinIntervalUcastframesDn	             OCTET STRING (SIZE (8)), 
        eponLanEtherPortCurrent15MinIntervalNUcastframesDw             OCTET STRING (SIZE (8)),       
        eponLanEtherPortCurrent15MinIntervalDiscardframesDn            OCTET STRING (SIZE (8)), 
        eponLanEtherPortCurrent15MinIntervalUndersizeframesUp          OCTET STRING (SIZE (8)),         
        eponLanEtherPortCurrent15MinIntervalUndersizeframesDn	         OCTET STRING (SIZE (8)), 
        eponLanEtherPortCurrent15MinIntervalOversizeframesUp	         OCTET STRING (SIZE (8)), 
        eponLanEtherPortCurrent15MinIntervalOversizeframesDn	         OCTET STRING (SIZE (8)), 
        eponLanEtherPortCurrent15MinIntervalErrorframesUp              OCTET STRING (SIZE (8)), 
        eponLanEtherPortCurrent15MinIntervalErrorframesDn	             OCTET STRING (SIZE (8)), 
        eponLanEtherPortCurrent15MinIntervalMulticastframesUp          OCTET STRING (SIZE (8)), 
        eponLanEtherPortCurrent15MinIntervalMulticastframesDn	         OCTET STRING (SIZE (8)), 
        eponLanEtherPortCurrent15MinIntervalStatuschange	             OCTET STRING (SIZE (8)),
        eponLanEtherPortCurrent15MinIntervalDropEventsUP                   OCTET STRING (SIZE (8)),
        eponLanEtherPortCurrent15MinIntervalDropEventsDn                    OCTET STRING (SIZE (8)),
        eponLanEtherPortCurrent15MinIntervalFragmentsUP                     OCTET STRING (SIZE (8)),
        eponLanEtherPortCurrent15MinIntervalFragmentsDn                     OCTET STRING (SIZE (8)),
        eponLanEtherPortCurrent15MinIntervalJabberFramesUP               OCTET STRING (SIZE (8)),
        eponLanEtherPortCurrent15MinIntervalJabberFramesDn               OCTET STRING (SIZE (8))
}


eponLanEtherPortCurrent15MinIntervalTimeElapsed  OBJECT-TYPE 
        SYNTAX    INTEGER 
        ACCESS    read-only 
        STATUS    mandatory 
        DESCRIPTION 
             "Elapsed time in interval (seconds)
            ALCATEL NOTE:
                ACCESS:     NA       USAGE:      NA
                PERSIST:    NO       INSRVMOD:   NO
                RANGE:      NA       DEFVALUE:   NA
                UNITS:      seconds  SPARSE:     NA
                DESCR:      NA"
::= { eponLanEtherPortCurrent15MinIntervalEntry 1 } 

eponLanEtherPortCurrent15MinIntervalTimeMeasured  OBJECT-TYPE 
        SYNTAX    INTEGER 
        ACCESS    read-only 
        STATUS    mandatory 
        DESCRIPTION 
            "Measured time in interval (seconds).
             ALCATEL NOTE:
                ACCESS:     NA       USAGE:      NA
                PERSIST:    NO       INSRVMOD:   NO
                RANGE:      NA       DEFVALUE:   NA
                UNITS:      seconds  SPARSE:     NA
                DESCR:      NA"

::= { eponLanEtherPortCurrent15MinIntervalEntry 2 } 

eponLanEtherPortCurrent15MinIntervalOctetsTransUp  OBJECT-TYPE
	SYNTAX 	OCTET STRING (SIZE (8)) 	
	ACCESS	read-only
	STATUS	mandatory
	DESCRIPTION 
		"The object indicates octets transferred in upstream direction on a ont ethernet port.
		 ALCATEL NOTE:
                 ACCESS:     NA       USAGE:      NA
                 PERSIST:    NO       INSRVMOD:   NO
                 RANGE:      NA       DEFVALUE:   0
                 UNITS:      NA       SPARSE:     NA
                 DESCR:      NA"


::= { eponLanEtherPortCurrent15MinIntervalEntry 3 }


eponLanEtherPortCurrent15MinIntervalTotalFramesTransUp  OBJECT-TYPE
	SYNTAX 	OCTET STRING (SIZE (8)) 	
	ACCESS	read-only
	STATUS	mandatory
	DESCRIPTION 
		"The object indicates Total Frames transferred	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"

	::= { eponLanEtherPortCurrent15MinIntervalEntry 4 }    
	
eponLanEtherPortCurrent15MinBroardFramesTransUp  OBJECT-TYPE
	SYNTAX 	OCTET STRING (SIZE (8)) 	
	ACCESS	read-only
	STATUS	mandatory
	DESCRIPTION 
			"The object indicates Broadcast Frames transferred	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortCurrent15MinIntervalEntry 5 }


eponLanEtherPortCurrent15MinCRCErrorUp  OBJECT-TYPE
	SYNTAX 	OCTET STRING (SIZE (8)) 	
	ACCESS	read-only
	STATUS	mandatory
	DESCRIPTION 
	"The object indicates CRC error frames transferred	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 6 }

eponLanEtherPortCurrent15MinPauseFramesUp  OBJECT-TYPE
	SYNTAX 	OCTET STRING (SIZE (8)) 	
	ACCESS	read-only
	STATUS	mandatory
	DESCRIPTION 
		"The object indicates pause Frames transferred	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortCurrent15MinIntervalEntry 7 }	
	
eponLanEtherPortCurrent15MinIntervalFirstSegOctetFramesUp	  OBJECT-TYPE
	SYNTAX 	OCTET STRING (SIZE (8)) 	
	ACCESS	read-only
	STATUS	mandatory
	DESCRIPTION 
		"The object indicates 64 Octet Frames 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 8 }
	
eponLanEtherPortCurrent15MinIntervalSecondSegOctetFramesUp	  OBJECT-TYPE
	SYNTAX 	OCTET STRING (SIZE (8)) 	
	ACCESS	read-only
	STATUS	mandatory
	DESCRIPTION 
		"The object indicates 65-127 Octet Frames 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 9 }
	
eponLanEtherPortCurrent15MinIntervalThirdSegOctetFramesUp	  OBJECT-TYPE
	SYNTAX 	OCTET STRING (SIZE (8)) 	
	ACCESS	read-only
	STATUS	mandatory
	DESCRIPTION 
		"The object indicates 128-255 Octet Frames 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 10 }
	
eponLanEtherPortCurrent15MinIntervalFourthSegOctetFramesUp	  OBJECT-TYPE
	SYNTAX 	OCTET STRING (SIZE (8)) 	
	ACCESS	read-only
	STATUS	mandatory
	DESCRIPTION 
		"The object indicates 256-511 Octet Frames 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 11 }
	
eponLanEtherPortCurrent15MinIntervalFifthSegOctetFramesUp	  OBJECT-TYPE
	SYNTAX 	OCTET STRING (SIZE (8)) 	
	ACCESS	read-only
	STATUS	mandatory
	DESCRIPTION 
		"The object indicates 512-1023 Octet Frames	in upstream direction on ONE ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 12 }
	
eponLanEtherPortCurrent15MinIntervalSixthSegOctetFramesUp	  OBJECT-TYPE
	SYNTAX 	OCTET STRING (SIZE (8)) 	
	ACCESS	read-only
	STATUS	mandatory
	DESCRIPTION 
		"The object indicates 1024-1518 Octet Frames in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 13 }
	
eponLanEtherPortCurrent15MinIntervalLastSegOctetFramesUp	  OBJECT-TYPE
	SYNTAX 	OCTET STRING (SIZE (8)) 	
	ACCESS	read-only
	STATUS	mandatory
	DESCRIPTION 
		"The object indicates 1519+ Octet Frames 	in upstream direction on ONt ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 14 }
	
eponLanEtherPortCurrent15MinIntervalOctetsTransDn  OBJECT-TYPE
	SYNTAX 	OCTET STRING (SIZE (8)) 	
	ACCESS	read-only
	STATUS	mandatory
	DESCRIPTION 
		"The object indicates octets transferred in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 15 }


eponLanEtherPortCurrent15MinIntervalTotalFramesTransDn  OBJECT-TYPE
	SYNTAX 	OCTET STRING (SIZE (8)) 	
	ACCESS	read-only
	STATUS	mandatory
	DESCRIPTION 
		"The object indicates Total Frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"

	::= { eponLanEtherPortCurrent15MinIntervalEntry 16 }
	
eponLanEtherPortCurrent15MinBroardFramesTransDn  OBJECT-TYPE
	SYNTAX 	OCTET STRING (SIZE (8)) 	
	ACCESS	read-only
	STATUS	mandatory
	DESCRIPTION 
	"The object indicates broadcast frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortCurrent15MinIntervalEntry 17 }


eponLanEtherPortCurrent15MinCRCErrorDn  OBJECT-TYPE
	SYNTAX 	OCTET STRING (SIZE (8)) 	
	ACCESS	read-only
	STATUS	mandatory
	DESCRIPTION 
"The object indicates CRC errors frames transferred in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 18 }

eponLanEtherPortCurrent15MinPauseFramesDn  OBJECT-TYPE
	SYNTAX 	OCTET STRING (SIZE (8)) 	
	ACCESS	read-only
	STATUS	mandatory
	DESCRIPTION 
	"The object indicates pause frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortCurrent15MinIntervalEntry 19 }	
	
eponLanEtherPortCurrent15MinIntervalFirstSegOctetFramesDn	  OBJECT-TYPE
	SYNTAX 	OCTET STRING (SIZE (8)) 	
	ACCESS	read-only
	STATUS	mandatory
	DESCRIPTION 
		"The object indicates 64 Octet Frames counters in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 20 }
	
eponLanEtherPortCurrent15MinIntervalSecondSegOctetFramesDn	  OBJECT-TYPE
	SYNTAX 	OCTET STRING (SIZE (8)) 	
	ACCESS	read-only
	STATUS	mandatory
	DESCRIPTION 
		"The object indicates 65-127 Octet Frames 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 21 }
	
eponLanEtherPortCurrent15MinIntervalThirdSegOctetFramesDn	  OBJECT-TYPE
	SYNTAX 	OCTET STRING (SIZE (8)) 	
	ACCESS	read-only
	STATUS	mandatory
	DESCRIPTION 
		"The object indicates 128-255 Octet Frames 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 22 }
	
eponLanEtherPortCurrent15MinIntervalFourthSegOctetFramesDn	  OBJECT-TYPE
	SYNTAX 	OCTET STRING (SIZE (8)) 	
	ACCESS	read-only
	STATUS	mandatory
	DESCRIPTION 
		"The object indicates 256-511 Octet Frames 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 23 }
	
eponLanEtherPortCurrent15MinIntervalFifthSegOctetFramesDn	  OBJECT-TYPE
	SYNTAX 	OCTET STRING (SIZE (8)) 	
	ACCESS	read-only
	STATUS	mandatory
	DESCRIPTION 
		"The object indicates 512-1023 Octet Frames 		in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 24 }
	
eponLanEtherPortCurrent15MinIntervalSixthSegOctetFramesDn	  OBJECT-TYPE
	SYNTAX 	OCTET STRING (SIZE (8)) 	
	ACCESS	read-only
	STATUS	mandatory
	DESCRIPTION 
		"The object indicates 1024-1518 Octet Frames 	in downstream direction on ONT ethernet  port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 25 }
	
eponLanEtherPortCurrent15MinIntervalLastSegOctetFramesDn	  OBJECT-TYPE
	SYNTAX 	OCTET STRING (SIZE (8)) 	
	ACCESS	read-only
	STATUS	mandatory
	DESCRIPTION 
		"The object indicates 1519+ Octet Frames 	in downstream direction on ONt ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 26 }         
	
eponLanEtherPortCurrent15MinIntervalUcastframesUP	  OBJECT-TYPE
	SYNTAX 	OCTET STRING (SIZE (8)) 	
	ACCESS	read-only
	STATUS	mandatory
	DESCRIPTION 
		"The object indicates Unicast Frames transferred 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 27 }  
	
eponLanEtherPortCurrent15MinIntervalNUcastframesUP  OBJECT-TYPE
  SYNTAX 	OCTET STRING (SIZE (8)) 	
  ACCESS  read-only
  STATUS  mandatory
  DESCRIPTION 
    "The object indicates not Unicast Frames transferred 	in upstream direction on ONT ethernet port"
  ::= { eponLanEtherPortCurrent15MinIntervalEntry 28 }  	

eponLanEtherPortCurrent15MinIntervalDiscardframesUP	  OBJECT-TYPE
	SYNTAX 	OCTET STRING (SIZE (8)) 	
	ACCESS	read-only
	STATUS	mandatory
	DESCRIPTION 
		"The object indicates Discard Frames transferred 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 29 }    

eponLanEtherPortCurrent15MinIntervalUcastframesDn    OBJECT-TYPE
	SYNTAX 	OCTET STRING (SIZE (8)) 	
	ACCESS	read-only
	STATUS	mandatory
	DESCRIPTION 
		"The object indicates Unicast Frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 30 }    
	
eponLanEtherPortCurrent15MinIntervalNUcastframesDw  OBJECT-TYPE
  SYNTAX 	OCTET STRING (SIZE (8)) 	
  ACCESS  read-only
  STATUS  mandatory
  DESCRIPTION 
    "The object indicates not Unicast Frames transferred 	in downstream direction on ONT ethernet port"
  ::= { eponLanEtherPortCurrent15MinIntervalEntry 31 }  

eponLanEtherPortCurrent15MinIntervalDiscardframesDn	  OBJECT-TYPE
	SYNTAX 	OCTET STRING (SIZE (8)) 	
	ACCESS	read-only
	STATUS	mandatory
	DESCRIPTION 
		"The object indicates Discard Frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 32 }    

eponLanEtherPortCurrent15MinIntervalUndersizeframesUp	  OBJECT-TYPE
	SYNTAX 	OCTET STRING (SIZE (8)) 	
	ACCESS	read-only
	STATUS	mandatory
	DESCRIPTION 
		"The object indicates less than 64 bytes Frames transferred in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 33 }    

eponLanEtherPortCurrent15MinIntervalUndersizeframesDn	  OBJECT-TYPE
	SYNTAX 	OCTET STRING (SIZE (8)) 	
	ACCESS	read-only
	STATUS	mandatory
	DESCRIPTION 
		"The object indicates less than 64 bytes Frames transferred in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 34 }    

eponLanEtherPortCurrent15MinIntervalOversizeframesUp	  OBJECT-TYPE
	SYNTAX 	OCTET STRING (SIZE (8)) 	
	ACCESS	read-only
	STATUS	mandatory
	DESCRIPTION 
		"The object indicates 1526+ Frames transferred in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 35 }    

eponLanEtherPortCurrent15MinIntervalOversizeframesDn	  OBJECT-TYPE
	SYNTAX 	OCTET STRING (SIZE (8)) 	
	ACCESS	read-only
	STATUS	mandatory
	DESCRIPTION 
		"The object indicates 1526+ Frames transferred in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 36 }    

eponLanEtherPortCurrent15MinIntervalErrorframesUp	  OBJECT-TYPE
	SYNTAX 	OCTET STRING (SIZE (8)) 	
	ACCESS	read-only
	STATUS	mandatory
	DESCRIPTION 
		"The object indicates Error Frames transferred 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 37 }    

eponLanEtherPortCurrent15MinIntervalErrorframesDn	  OBJECT-TYPE
	SYNTAX 	OCTET STRING (SIZE (8)) 	
	ACCESS	read-only
	STATUS	mandatory
	DESCRIPTION 
		"The object indicates Error Frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 38 }    

eponLanEtherPortCurrent15MinIntervalMulticastframesUp	  OBJECT-TYPE
	SYNTAX 	OCTET STRING (SIZE (8)) 	
	ACCESS	read-only
	STATUS	mandatory
	DESCRIPTION 
		"The object indicates Multicast Frames transferred 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 39 }    

eponLanEtherPortCurrent15MinIntervalMulticastframesDn	  OBJECT-TYPE
	SYNTAX 	OCTET STRING (SIZE (8)) 	
	ACCESS	read-only
	STATUS	mandatory
	DESCRIPTION 
		"The object indicates Multicast Frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 40 }    

eponLanEtherPortCurrent15MinIntervalStatuschange	  OBJECT-TYPE
	SYNTAX 	OCTET STRING (SIZE (8)) 	
	ACCESS	read-only
	STATUS	mandatory
	DESCRIPTION 
		"The object indicates port status change times
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 41 }    

eponLanEtherPortCurrent15MinIntervalDropEventsUP	  OBJECT-TYPE
	SYNTAX 	OCTET STRING (SIZE (8)) 	
	ACCESS	read-only
	STATUS	mandatory
	DESCRIPTION 
		"The object indicates drop event in upstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 42 }     

eponLanEtherPortCurrent15MinIntervalDropEventsDn	  OBJECT-TYPE
	SYNTAX 	OCTET STRING (SIZE (8)) 	
	ACCESS	read-only
	STATUS	mandatory
	DESCRIPTION 
		"The object indicates drop event in downstream direction on ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 43 }     

eponLanEtherPortCurrent15MinIntervalFragmentsUP	  OBJECT-TYPE
	SYNTAX 	OCTET STRING (SIZE (8)) 	
	ACCESS	read-only
	STATUS	mandatory
	DESCRIPTION 
		"The object indicates fragment frames in upstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 44 }     

eponLanEtherPortCurrent15MinIntervalFragmentsDn	  OBJECT-TYPE
	SYNTAX 	OCTET STRING (SIZE (8)) 	
	ACCESS	read-only
	STATUS	mandatory
	DESCRIPTION 
		"The object indicates fragment frames in downstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 45 }     

eponLanEtherPortCurrent15MinIntervalJabberFramesUP    OBJECT-TYPE
	SYNTAX 	OCTET STRING (SIZE (8)) 	
	ACCESS	read-only
	STATUS	mandatory
	DESCRIPTION 
		"The object indicates jabber  frames in upstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 46 }     

eponLanEtherPortCurrent15MinIntervalJabberFramesDn      OBJECT-TYPE
	SYNTAX 	OCTET STRING (SIZE (8)) 	
	ACCESS	read-only
	STATUS	mandatory
	DESCRIPTION 
		"The object indicates jabber  frames in downstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent15MinIntervalEntry 47 }     

	
-- *********************************************

-- EPON ONT UNI PERFORMANCE TABLE
--
-- This table contains current 1 day performance counters specific to
-- a specific UNI port . 

-- *********************************************

eponLanEtherPortCurrent1DayIntervalTable  OBJECT-TYPE
	SYNTAX SEQUENCE OF EponLanEtherPortCurrent1DayIntervalEntry
	ACCESS	not-accessible
	STATUS	mandatory   
	DESCRIPTION 
	 "1 day current statistics for ONT ethernet interface.
	 ALCATEL NOTE:
             SUPPORT: YES   TABLESIZE: DEP"	

	::= { eponStatisticsGroup 13 }                                                  

eponLanEtherPortCurrent1DayIntervalEntry  OBJECT-TYPE
	SYNTAX 	EponLanEtherPortCurrent1DayIntervalEntry
	ACCESS	not-accessible
	STATUS	mandatory   
		DESCRIPTION
         "Table entry for the current 1 day statistics counters for ONT ethernet interface.
          Row creation : an entry is created by the system when this ONT ethernet  interfaces statistics enabled.
          Row deletion :an entry is created by the system when this ONT ethernet  interfaces statistics disabled.
           ALCATEL NOTE:
             SUPPORT: YES"

	INDEX	{ eponLanEtherPortIfindex }
	::= { eponLanEtherPortCurrent1DayIntervalTable 1 }

EponLanEtherPortCurrent1DayIntervalEntry ::= SEQUENCE {
	  
	    eponLanEtherPortCurrent1DayIntervalTimeElapsed                INTEGER,                
	    eponLanEtherPortCurrent1DayIntervalTimeMeasured               INTEGER, 
        eponLanEtherPortCurrent1DayIntervalOctetsTransUp		       OCTET STRING (SIZE (8)),
        eponLanEtherPortCurrent1DayIntervalTotalFramesTransUp	       OCTET STRING (SIZE (8)), 
        eponLanEtherPortCurrent1DayBroardFramesTransUp	              OCTET STRING (SIZE (8)),
        eponLanEtherPortCurrent1DayCRCErrorUp	                       OCTET STRING (SIZE (8)),
        eponLanEtherPortCurrent1DayPauseFramesUp	                   OCTET STRING (SIZE (8)),
        eponLanEtherPortCurrent1DayIntervalFirstSegOctetFramesUp      OCTET STRING (SIZE (8)),
        eponLanEtherPortCurrent1DayIntervalSecondSegOctetFramesUp     OCTET STRING (SIZE (8)),
        eponLanEtherPortCurrent1DayIntervalThirdSegOctetFramesUp      OCTET STRING (SIZE (8)),
        eponLanEtherPortCurrent1DayIntervalFourthSegOctetFramesUp     OCTET STRING (SIZE (8)),
        eponLanEtherPortCurrent1DayIntervalFifthSegOctetFramesUp      OCTET STRING (SIZE (8)),
        eponLanEtherPortCurrent1DayIntervalSixthSegOctetFramesUp      OCTET STRING (SIZE (8)),
        eponLanEtherPortCurrent1DayIntervalLastSegOctetFramesUp       OCTET STRING (SIZE (8)),
        eponLanEtherPortCurrent1DayIntervalOctetsTransDn		       OCTET STRING (SIZE (8)),
        eponLanEtherPortCurrent1DayIntervalTotalFramesTransDn	       OCTET STRING (SIZE (8)),
        eponLanEtherPortCurrent1DayBroardFramesTransDn	              OCTET STRING (SIZE (8)),
        eponLanEtherPortCurrent1DayCRCErrorDn	                       OCTET STRING (SIZE (8)),
        eponLanEtherPortCurrent1DayPauseFramesDn	                   OCTET STRING (SIZE (8)),
        eponLanEtherPortCurrent1DayIntervalFirstSegOctetFramesDn      OCTET STRING (SIZE (8)),
        eponLanEtherPortCurrent1DayIntervalSecondSegOctetFramesDn     OCTET STRING (SIZE (8)),
        eponLanEtherPortCurrent1DayIntervalThirdSegOctetFramesDn      OCTET STRING (SIZE (8)),
        eponLanEtherPortCurrent1DayIntervalFourthSegOctetFramesDn     OCTET STRING (SIZE (8)),
        eponLanEtherPortCurrent1DayIntervalFifthSegOctetFramesDn      OCTET STRING (SIZE (8)),
        eponLanEtherPortCurrent1DayIntervalSixthSegOctetFramesDn      OCTET STRING (SIZE (8)),
        eponLanEtherPortCurrent1DayIntervalLastSegOctetFramesDn       OCTET STRING (SIZE (8)),
        eponLanEtherPortCurrent1DayIntervalUcastframesUP              OCTET STRING (SIZE (8)), 
        eponLanEtherPortCurrent1DayIntervalNUcastframesUP             OCTET STRING (SIZE (8)),     
        eponLanEtherPortCurrent1DayIntervalDiscardframesUP            OCTET STRING (SIZE (8)),      
        eponLanEtherPortCurrent1DayIntervalUcastframesDn              OCTET STRING (SIZE (8)), 
        eponLanEtherPortCurrent1DayIntervalNUcastframesDw             OCTET STRING (SIZE (8)),     
        eponLanEtherPortCurrent1DayIntervalDiscardframesDn            OCTET STRING (SIZE (8)),      
        eponLanEtherPortCurrent1DayIntervalUndersizeframesUp          OCTET STRING (SIZE (8)),      
        eponLanEtherPortCurrent1DayIntervalUndersizeframesDn          OCTET STRING (SIZE (8)),      
        eponLanEtherPortCurrent1DayIntervalOversizeframesUp           OCTET STRING (SIZE (8)),      
        eponLanEtherPortCurrent1DayIntervalOversizeframesDn           OCTET STRING (SIZE (8)),
        eponLanEtherPortCurrent1DayIntervalErrorframesUp              OCTET STRING (SIZE (8)),
        eponLanEtherPortCurrent1DayIntervalErrorframesDn              OCTET STRING (SIZE (8)),
        eponLanEtherPortCurrent1DayIntervalMulticastframesUp          OCTET STRING (SIZE (8)),
        eponLanEtherPortCurrent1DayIntervalMulticastframesDn          OCTET STRING (SIZE (8)),
        eponLanEtherPortCurrent1DayIntervalStatuschange               OCTET STRING (SIZE (8)),
        eponLanEtherPortCurrent1DayIntervalDropEventsUP                   OCTET STRING (SIZE (8)),
        eponLanEtherPortCurrent1DayIntervalDropEventsDn                    OCTET STRING (SIZE (8)),
        eponLanEtherPortCurrent1DayIntervalFragmentsUP                     OCTET STRING (SIZE (8)),
        eponLanEtherPortCurrent1DayIntervalFragmentsDn                     OCTET STRING (SIZE (8)),
        eponLanEtherPortCurrent1DayIntervalJabberFramesUP               OCTET STRING (SIZE (8)),
        eponLanEtherPortCurrent1DayIntervalJabberFramesDn               OCTET STRING (SIZE (8)) 
}


eponLanEtherPortCurrent1DayIntervalTimeElapsed  OBJECT-TYPE 
        SYNTAX    INTEGER 
        ACCESS    read-only 
        STATUS    mandatory 
        DESCRIPTION 
             "Elapsed time in interval (seconds)
            ALCATEL NOTE:
                ACCESS:     NA       USAGE:      NA
                PERSIST:    NO       INSRVMOD:   NO
                RANGE:      NA       DEFVALUE:   NA
                UNITS:      seconds  SPARSE:     NA
                DESCR:      NA"
::= { eponLanEtherPortCurrent1DayIntervalEntry 1 } 

eponLanEtherPortCurrent1DayIntervalTimeMeasured  OBJECT-TYPE 
        SYNTAX    INTEGER 
        ACCESS    read-only 
        STATUS    mandatory 
        DESCRIPTION 
            "Measured time in interval (seconds).
            ALCATEL NOTE:
                ACCESS:     NA       USAGE:      NA
                PERSIST:    NO       INSRVMOD:   NO
                RANGE:      NA       DEFVALUE:   NA
                UNITS:      seconds  SPARSE:     NA
                DESCR:      NA"

::= { eponLanEtherPortCurrent1DayIntervalEntry 2 } 

eponLanEtherPortCurrent1DayIntervalOctetsTransUp  OBJECT-TYPE
	SYNTAX 	OCTET STRING (SIZE (8)) 	
	ACCESS	read-only
	STATUS	mandatory
	DESCRIPTION 
		"The object indicates octets transferred in upstream direction on ONT ethernet port.
		 ALCATEL NOTE:
                 ACCESS:     NA       USAGE:      NA
                 PERSIST:    NO       INSRVMOD:   NO
                 RANGE:      NA       DEFVALUE:   0
                 UNITS:      NA       SPARSE:     NA
                 DESCR:      NA"

::= { eponLanEtherPortCurrent1DayIntervalEntry 3}


eponLanEtherPortCurrent1DayIntervalTotalFramesTransUp  OBJECT-TYPE
	SYNTAX 	OCTET STRING (SIZE (8)) 	
	ACCESS	read-only
	STATUS	mandatory
	DESCRIPTION 
		"The object indicates Total Frames transferred 	in upstream direction on ONT ethernet port
ALCATEL NOTE:
                 ACCESS:     NA       USAGE:      NA
                 PERSIST:    NO       INSRVMOD:   NO
                 RANGE:      NA       DEFVALUE:   0       
                 UNITS:      NA       SPARSE:     NA
                 DESCR:      NA
"
	::= { eponLanEtherPortCurrent1DayIntervalEntry 4 }    
	
eponLanEtherPortCurrent1DayBroardFramesTransUp  OBJECT-TYPE
	SYNTAX 	OCTET STRING (SIZE (8)) 	
	ACCESS	read-only
	STATUS	mandatory
	DESCRIPTION 
			"The object indicates broadcast Frames transferred 	in upstream direction on ONT ethernet port
ALCATEL NOTE:
                 ACCESS:     NA       USAGE:      NA
                 PERSIST:    NO       INSRVMOD:   NO
                 RANGE:      NA       DEFVALUE:  0
                 UNITS:      NA       SPARSE:     NA
                 DESCR:      NA
"
::= { eponLanEtherPortCurrent1DayIntervalEntry 5 }


eponLanEtherPortCurrent1DayCRCErrorUp  OBJECT-TYPE
	SYNTAX 	OCTET STRING (SIZE (8)) 	
	ACCESS	read-only
	STATUS	mandatory
	DESCRIPTION 
	"The object indicates CRC error Frames transferred 	in upstream direction on ONT ethernet port
ALCATEL NOTE:
                 ACCESS:     NA       USAGE:      NA
                 PERSIST:    NO       INSRVMOD:   NO
                 RANGE:      NA       DEFVALUE:   0
                  UNITS:      NA       SPARSE:     NA
                 DESCR:      NA
"
	::= { eponLanEtherPortCurrent1DayIntervalEntry 6 }

eponLanEtherPortCurrent1DayPauseFramesUp  OBJECT-TYPE
	SYNTAX 	OCTET STRING (SIZE (8)) 	
	ACCESS	read-only
	STATUS	mandatory
	DESCRIPTION 
		"The object indicates pause Frames transferred 	in upstream direction on ONT ethernet port
ALCATEL NOTE:
                 ACCESS:     NA       USAGE:      NA
                 PERSIST:    NO       INSRVMOD:   NO
                 RANGE:      NA       DEFVALUE:  0        
                 UNITS:      NA       SPARSE:     NA
                 DESCR:      NA
"
::= { eponLanEtherPortCurrent1DayIntervalEntry 7 }	
	
eponLanEtherPortCurrent1DayIntervalFirstSegOctetFramesUp	  OBJECT-TYPE
	SYNTAX 	OCTET STRING (SIZE (8)) 	
	ACCESS	read-only
	STATUS	mandatory
	DESCRIPTION 
		"The object indicates 64 Octet Frames	in upstream direction on ONT ethernet port
ALCATEL NOTE:
                 ACCESS:     NA       USAGE:      NA
                 PERSIST:    NO       INSRVMOD:   NO
                 RANGE:      NA       DEFVALUE:  0
                  UNITS:      NA       SPARSE:     NA
                 DESCR:      NA
"
	::= { eponLanEtherPortCurrent1DayIntervalEntry 8 }
	
eponLanEtherPortCurrent1DayIntervalSecondSegOctetFramesUp	  OBJECT-TYPE
	SYNTAX 	OCTET STRING (SIZE (8)) 	
	ACCESS	read-only
	STATUS	mandatory
	DESCRIPTION 
		"The object indicates 65-127 Octet Frames in upstream direction on ONt ethernet port
ALCATEL NOTE:
                 ACCESS:     NA       USAGE:      NA
                 PERSIST:    NO       INSRVMOD:   NO
                 RANGE:      NA       DEFVALUE:  0
                 UNITS:      NA       SPARSE:     NA
                 DESCR:      NA
"
	::= { eponLanEtherPortCurrent1DayIntervalEntry 9 }
	
eponLanEtherPortCurrent1DayIntervalThirdSegOctetFramesUp	  OBJECT-TYPE
	SYNTAX 	OCTET STRING (SIZE (8)) 	
	ACCESS	read-only
	STATUS	mandatory
	DESCRIPTION 
		"The object indicates 128-255 Octet Frames 	in upstream direction on ONT ethernet port
ALCATEL NOTE:
                 ACCESS:     NA       USAGE:      NA
                 PERSIST:    NO       INSRVMOD:   NO
                 RANGE:      NA       DEFVALUE: 0
                 UNITS:      NA       SPARSE:     NA
                 DESCR:      NA
"
	::= { eponLanEtherPortCurrent1DayIntervalEntry 10 }
	
eponLanEtherPortCurrent1DayIntervalFourthSegOctetFramesUp	  OBJECT-TYPE
	SYNTAX 	OCTET STRING (SIZE (8)) 	
	ACCESS	read-only
	STATUS	mandatory
	DESCRIPTION 
		"The object indicates 256-511 Octet Frames 	in upstream direction on ONT ethernet port
ALCATEL NOTE:
                 ACCESS:     NA       USAGE:      NA
                 PERSIST:    NO       INSRVMOD:   NO
                 RANGE:      NA       DEFVALUE:   0
                  UNITS:      NA       SPARSE:     NA
                 DESCR:      NA
"
	::= { eponLanEtherPortCurrent1DayIntervalEntry 11 }
	
eponLanEtherPortCurrent1DayIntervalFifthSegOctetFramesUp	  OBJECT-TYPE
	SYNTAX 	OCTET STRING (SIZE (8)) 	
	ACCESS	read-only
	STATUS	mandatory
	DESCRIPTION 
		"The object indicates 512-1023 Octet Frames in upstream direction on ONT ethernet port
ALCATEL NOTE:
                 ACCESS:     NA       USAGE:      NA
                 PERSIST:    NO       INSRVMOD:   NO
                 RANGE:      NA       DEFVALUE:  0
                 UNITS:      NA       SPARSE:     NA
                 DESCR:      NA
"
	::= { eponLanEtherPortCurrent1DayIntervalEntry 12 }
	
eponLanEtherPortCurrent1DayIntervalSixthSegOctetFramesUp	  OBJECT-TYPE
	SYNTAX 	OCTET STRING (SIZE (8)) 	
	ACCESS	read-only
	STATUS	mandatory
	DESCRIPTION 
		"The object indicates 1024-1518 Octet Frames 	in upstream direction on ONt ethernet port
ALCATEL NOTE:
                 ACCESS:     NA       USAGE:      NA
                 PERSIST:    NO       INSRVMOD:   NO
                 RANGE:      NA       DEFVALUE:  0
                  UNITS:      NA       SPARSE:     NA
                 DESCR:      NA
"
	::= { eponLanEtherPortCurrent1DayIntervalEntry 13 }
	
eponLanEtherPortCurrent1DayIntervalLastSegOctetFramesUp	  OBJECT-TYPE
	SYNTAX 	OCTET STRING (SIZE (8)) 	
	ACCESS	read-only
	STATUS	mandatory
	DESCRIPTION 
		"The object indicates 1519+ Octet Frames in upstream direction on ONT ethernet port
ALCATEL NOTE:
                 ACCESS:     NA       USAGE:      NA
                 PERSIST:    NO       INSRVMOD:   NO
                 RANGE:      NA       DEFVALUE:  0
                  UNITS:      NA       SPARSE:     NA
                 DESCR:      NA
"
	::= { eponLanEtherPortCurrent1DayIntervalEntry 14 }
	
eponLanEtherPortCurrent1DayIntervalOctetsTransDn  OBJECT-TYPE
	SYNTAX 	OCTET STRING (SIZE (8)) 	
	ACCESS	read-only
	STATUS	mandatory
	DESCRIPTION 
		"The object indicates octets transferred in downstream direction on ONt ethernet  port
ALCATEL NOTE:
                 ACCESS:     NA       USAGE:      NA
                 PERSIST:    NO       INSRVMOD:   NO
                 RANGE:      NA       DEFVALUE:  0
                   UNITS:      NA       SPARSE:     NA
                 DESCR:      NA
"
	::= { eponLanEtherPortCurrent1DayIntervalEntry 15 }


eponLanEtherPortCurrent1DayIntervalTotalFramesTransDn  OBJECT-TYPE
	SYNTAX 	OCTET STRING (SIZE (8)) 	
	ACCESS	read-only
	STATUS	mandatory
	DESCRIPTION 
		"The object indicates Total Frames transferred 	in downstream direction on ONt ethernet port
ALCATEL NOTE:
                 ACCESS:     NA       USAGE:      NA
                 PERSIST:    NO       INSRVMOD:   NO
                 RANGE:      NA       DEFVALUE:   0
                 UNITS:      NA       SPARSE:     NA
                 DESCR:      NA
"
	::= { eponLanEtherPortCurrent1DayIntervalEntry 16 }
	
eponLanEtherPortCurrent1DayBroardFramesTransDn  OBJECT-TYPE
	SYNTAX 	OCTET STRING (SIZE (8)) 	
	ACCESS	read-only
	STATUS	mandatory
	DESCRIPTION 
			"The object indicates broadcast Frames transferred 	in downstream direction on ONt ethernet port
ALCATEL NOTE:
                 ACCESS:     NA       USAGE:      NA
                 PERSIST:    NO       INSRVMOD:   NO
                 RANGE:      NA       DEFVALUE:   0
                 UNITS:      NA       SPARSE:     NA
                 DESCR:      NA
"
::= { eponLanEtherPortCurrent1DayIntervalEntry 17 }


eponLanEtherPortCurrent1DayCRCErrorDn  OBJECT-TYPE
	SYNTAX 	OCTET STRING (SIZE (8)) 	
	ACCESS	read-only
	STATUS	mandatory
	DESCRIPTION 
		"The object indicates CRC erro Frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA
"
	::= { eponLanEtherPortCurrent1DayIntervalEntry 18 }

eponLanEtherPortCurrent1DayPauseFramesDn  OBJECT-TYPE
	SYNTAX 	OCTET STRING (SIZE (8)) 	
	ACCESS	read-only
	STATUS	mandatory
	DESCRIPTION 
	"The object indicates pause Frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA
"
::= { eponLanEtherPortCurrent1DayIntervalEntry 19 }	
	
eponLanEtherPortCurrent1DayIntervalFirstSegOctetFramesDn	  OBJECT-TYPE
	SYNTAX 	OCTET STRING (SIZE (8)) 	
	ACCESS	read-only
	STATUS	mandatory
	DESCRIPTION 
		"The object indicates 64 Octet Frames 	in downstream direction on ONT ethernet port
ALCATEL NOTE:
                 ACCESS:     NA       USAGE:      NA
                 PERSIST:    NO       INSRVMOD:   NA
                 RANGE:      NA       DEFVALUE:   0
                UNITS:      NA       SPARSE:     NA
                 DESCR:      NA
"
	::= { eponLanEtherPortCurrent1DayIntervalEntry 20 }
	
eponLanEtherPortCurrent1DayIntervalSecondSegOctetFramesDn	  OBJECT-TYPE
	SYNTAX 	OCTET STRING (SIZE (8)) 	
	ACCESS	read-only
	STATUS	mandatory
	DESCRIPTION 
		"The object indicates 65-127 Octet Frames 	in downstream direction on ONT ethernet port
ALCATEL NOTE:
                 ACCESS:     NA       USAGE:      NA
                 PERSIST:    NO       INSRVMOD:   NA
                 RANGE:      NA       DEFVALUE:   0      
                 UNITS:      NA       SPARSE:     NA
                 DESCR:      NA
"
	::= { eponLanEtherPortCurrent1DayIntervalEntry 21 }
	
eponLanEtherPortCurrent1DayIntervalThirdSegOctetFramesDn	  OBJECT-TYPE
	SYNTAX 	OCTET STRING (SIZE (8)) 	
	ACCESS	read-only
	STATUS	mandatory
	DESCRIPTION 
		"The object indicates 128-255 Octet Frames 	in downstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 22 }
	
eponLanEtherPortCurrent1DayIntervalFourthSegOctetFramesDn	  OBJECT-TYPE
	SYNTAX 	OCTET STRING (SIZE (8)) 	
	ACCESS	read-only
	STATUS	mandatory
	DESCRIPTION 
		"The object indicates 256-511 Octet Frames 	in downstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 23 }
	
eponLanEtherPortCurrent1DayIntervalFifthSegOctetFramesDn	  OBJECT-TYPE
	SYNTAX 	OCTET STRING (SIZE (8)) 	
	ACCESS	read-only
	STATUS	mandatory
	DESCRIPTION 
		"The object indicates 512-1023 Octet Frames in downstream direction on ONt ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 24 }
	
eponLanEtherPortCurrent1DayIntervalSixthSegOctetFramesDn	  OBJECT-TYPE
	SYNTAX 	OCTET STRING (SIZE (8)) 	
	ACCESS	read-only
	STATUS	mandatory
	DESCRIPTION 
		"The object indicates 1024-1518 Octet Frames in downstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 25 }
	
eponLanEtherPortCurrent1DayIntervalLastSegOctetFramesDn	  OBJECT-TYPE
	SYNTAX 	OCTET STRING (SIZE (8)) 	
	ACCESS	read-only
	STATUS	mandatory
	DESCRIPTION 
		"The object indicates 1519+ Octet Frames 	in downstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 26 }         

eponLanEtherPortCurrent1DayIntervalUcastframesUP	  OBJECT-TYPE
	SYNTAX 	OCTET STRING (SIZE (8)) 	
	ACCESS	read-only
	STATUS	mandatory
	DESCRIPTION 
		"The object indicates Unicast Frames 	in upstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 27 }         
	
eponLanEtherPortCurrent1DayIntervalNUcastframesUP  OBJECT-TYPE
  SYNTAX  OCTET STRING (SIZE (8)) 	
  ACCESS  read-only
  STATUS  mandatory
  DESCRIPTION 
    "The object indicates not Unicast Frames 	in upstream direction on ONT ethernet port"
  ::= { eponLanEtherPortCurrent1DayIntervalEntry 28 } 	

eponLanEtherPortCurrent1DayIntervalDiscardframesUP	  OBJECT-TYPE
	SYNTAX 	OCTET STRING (SIZE (8)) 	
	ACCESS	read-only
	STATUS	mandatory
	DESCRIPTION 
		"The object indicates Discard Frames 	in upstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 29 }         

eponLanEtherPortCurrent1DayIntervalUcastframesDn	  OBJECT-TYPE
	SYNTAX 	OCTET STRING (SIZE (8)) 	
	ACCESS	read-only
	STATUS	mandatory
	DESCRIPTION 
		"The object indicates Unicast Frames 	in downstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 30 }  
	
eponLanEtherPortCurrent1DayIntervalNUcastframesDw  OBJECT-TYPE
  SYNTAX  OCTET STRING (SIZE (8)) 	
  ACCESS  read-only
  STATUS  mandatory
  DESCRIPTION 
    "The object indicates not Unicast Frames 	in downstream direction on ONT ethernet por"
  ::= { eponLanEtherPortCurrent1DayIntervalEntry 31 }        
	
eponLanEtherPortCurrent1DayIntervalDiscardframesDn	  OBJECT-TYPE
	SYNTAX 	OCTET STRING (SIZE (8)) 	
	ACCESS	read-only
	STATUS	mandatory
	DESCRIPTION 
		"The object indicates Discard Frames 	in downstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 32 }         
	
eponLanEtherPortCurrent1DayIntervalUndersizeframesUp	  OBJECT-TYPE
	SYNTAX 	OCTET STRING (SIZE (8)) 	
	ACCESS	read-only
	STATUS	mandatory
	DESCRIPTION 
		"The object indicates less than 64 bytes Frames 	in upstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 33 }         
	
eponLanEtherPortCurrent1DayIntervalUndersizeframesDn	  OBJECT-TYPE
	SYNTAX 	OCTET STRING (SIZE (8)) 	
	ACCESS	read-only
	STATUS	mandatory
	DESCRIPTION 
		"The object indicates less than 64 bytes Frames 	in downstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 34 }      
	   
eponLanEtherPortCurrent1DayIntervalOversizeframesUp	  OBJECT-TYPE
	SYNTAX 	OCTET STRING (SIZE (8)) 	
	ACCESS	read-only
	STATUS	mandatory
	DESCRIPTION 
		"The object indicates 1526+ Frames 	in upstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 35 }     
	    
eponLanEtherPortCurrent1DayIntervalOversizeframesDn	  OBJECT-TYPE
	SYNTAX 	OCTET STRING (SIZE (8)) 	
	ACCESS	read-only
	STATUS	mandatory
	DESCRIPTION 
		"The object indicates 1526+ Frames 	in downstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 36 }     
	    
eponLanEtherPortCurrent1DayIntervalErrorframesUp	  OBJECT-TYPE
	SYNTAX 	OCTET STRING (SIZE (8)) 	
	ACCESS	read-only
	STATUS	mandatory
	DESCRIPTION 
		"The object indicates error Frames 	in upstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 37 }     
	    
eponLanEtherPortCurrent1DayIntervalErrorframesDn	  OBJECT-TYPE
	SYNTAX 	OCTET STRING (SIZE (8)) 	
	ACCESS	read-only
	STATUS	mandatory
	DESCRIPTION 
		"The object indicates Error Frames 	in downstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 38 }   
	      
eponLanEtherPortCurrent1DayIntervalMulticastframesUp	  OBJECT-TYPE
	SYNTAX 	OCTET STRING (SIZE (8)) 	
	ACCESS	read-only
	STATUS	mandatory
	DESCRIPTION 
		"The object indicates Multicast Frames 	in upstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 39 }    
	     
eponLanEtherPortCurrent1DayIntervalMulticastframesDn	  OBJECT-TYPE
	SYNTAX 	OCTET STRING (SIZE (8)) 	
	ACCESS	read-only
	STATUS	mandatory
	DESCRIPTION 
		"The object indicates Multicast Frames 	in downstream direction on ONT ethernet port
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 40 }    
	     
eponLanEtherPortCurrent1DayIntervalStatuschange	  OBJECT-TYPE
	SYNTAX 	OCTET STRING (SIZE (8)) 	
	ACCESS	read-only
	STATUS	mandatory
	DESCRIPTION 
		"The object indicates port status change times.
ALCATEL NOTE:
                 ACCESS:     NA       USAGE:      NA
                 PERSIST:    NO       INSRVMOD:   NA
                 RANGE:      NA       DEFVALUE:  0
                 UNITS:      NA       SPARSE:     NA
                 DESCR:      NA
"
	::= { eponLanEtherPortCurrent1DayIntervalEntry 41 }    

eponLanEtherPortCurrent1DayIntervalDropEventsUP	  OBJECT-TYPE
	SYNTAX 	OCTET STRING (SIZE (8)) 	
	ACCESS	read-only
	STATUS	mandatory
	DESCRIPTION 
		"The object indicates drop event in upstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent1DayIntervalEntry 42 }     

eponLanEtherPortCurrent1DayIntervalDropEventsDn	  OBJECT-TYPE
	SYNTAX 	OCTET STRING (SIZE (8)) 	
	ACCESS	read-only
	STATUS	mandatory
	DESCRIPTION 
		"The object indicates drop event in downstream direction on ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent1DayIntervalEntry 43 }     

eponLanEtherPortCurrent1DayIntervalFragmentsUP	  OBJECT-TYPE
	SYNTAX 	OCTET STRING (SIZE (8)) 	
	ACCESS	read-only
	STATUS	mandatory
	DESCRIPTION 
		"The object indicates fragment frames in upstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent1DayIntervalEntry 44 }     

eponLanEtherPortCurrent1DayIntervalFragmentsDn	  OBJECT-TYPE
	SYNTAX 	OCTET STRING (SIZE (8)) 	
	ACCESS	read-only
	STATUS	mandatory
	DESCRIPTION 
		"The object indicates fragment frames in downstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent1DayIntervalEntry 45 }     

eponLanEtherPortCurrent1DayIntervalJabberFramesUP    OBJECT-TYPE
	SYNTAX 	OCTET STRING (SIZE (8)) 	
	ACCESS	read-only
	STATUS	mandatory
	DESCRIPTION 
		"The object indicates jabber  frames in upstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent1DayIntervalEntry 46 }     

eponLanEtherPortCurrent1DayIntervalJabberFramesDn      OBJECT-TYPE
	SYNTAX 	OCTET STRING (SIZE (8)) 	
	ACCESS	read-only
	STATUS	mandatory
	DESCRIPTION 
		"The object indicates jabber  frames in downstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortCurrent1DayIntervalEntry 47 }     
 
-- *********************************************

-- EPON ONT UNI PERFORMANCE TABLE
--
-- This table contains Previous 15 min performance counters specific to
-- a specific UNI port . 

-- *********************************************

eponLanEtherPortPrevious15MinIntervalTable  OBJECT-TYPE
	SYNTAX SEQUENCE OF EponLanEtherPortPrevious15MinIntervalEntry
	ACCESS	not-accessible
	STATUS	mandatory    
	DESCRIPTION 
	 "15 Minutes previous statistics for ONT ethernet interface.
	 ALCATEL NOTE:
             SUPPORT: YES   TABLESIZE: DEP"

	::= { eponStatisticsGroup 14 }                                                  

eponLanEtherPortPrevious15MinIntervalEntry  OBJECT-TYPE
	SYNTAX 	EponLanEtherPortPrevious15MinIntervalEntry
	ACCESS	not-accessible
	STATUS	mandatory  
	DESCRIPTION   
	 "	Table entry for the previous 15 minutes statistics counters for ONT ethernet interface.
          Row creation : an entry is created by the system when this pon interfaces statistics enabled.
          Row deletion :an entry is created by the system when this pon interfaces statistics disabled.
           ALCATEL NOTE:
             SUPPORT: YES"

	INDEX	{ eponLanEtherPortIfindex,
	          eponLanEtherPortPrevious15MinIntervalNumber }
	::= { eponLanEtherPortPrevious15MinIntervalTable 1 }

EponLanEtherPortPrevious15MinIntervalEntry ::= SEQUENCE {
	  
	    eponLanEtherPortPrevious15MinIntervalNumber                     INTEGER,                
	    eponLanEtherPortPrevious15MinIntervalTimeMeasured               INTEGER, 
        eponLanEtherPortPrevious15MinIntervalOctetsTransUp		        OCTET STRING (SIZE (8)),
        eponLanEtherPortPrevious15MinIntervalTotalFramesTransUp	        OCTET STRING (SIZE (8)), 
        eponLanEtherPortPrevious15MinBroardFramesTransUp	            OCTET STRING (SIZE (8)),
        eponLanEtherPortPrevious15MinCRCErrorUp	                        OCTET STRING (SIZE (8)),
        eponLanEtherPortPrevious15MinPauseFramesUp	                    OCTET STRING (SIZE (8)),
        eponLanEtherPortPrevious15MinIntervalFirstSegOctetFramesUp      OCTET STRING (SIZE (8)),
        eponLanEtherPortPrevious15MinIntervalSecondSegOctetFramesUp     OCTET STRING (SIZE (8)),
        eponLanEtherPortPrevious15MinIntervalThirdSegOctetFramesUp      OCTET STRING (SIZE (8)),
        eponLanEtherPortPrevious15MinIntervalFourthSegOctetFramesUp     OCTET STRING (SIZE (8)),
        eponLanEtherPortPrevious15MinIntervalFifthSegOctetFramesUp      OCTET STRING (SIZE (8)),
        eponLanEtherPortPrevious15MinIntervalSixthSegOctetFramesUp      OCTET STRING (SIZE (8)),
        eponLanEtherPortPrevious15MinIntervalLastSegOctetFramesUp       OCTET STRING (SIZE (8)),
        eponLanEtherPortPrevious15MinIntervalOctetsTransDn		       OCTET STRING (SIZE (8)),
        eponLanEtherPortPrevious15MinIntervalTotalFramesTransDn	       OCTET STRING (SIZE (8)),
        eponLanEtherPortPrevious15MinBroardFramesTransDn	           OCTET STRING (SIZE (8)),
        eponLanEtherPortPrevious15MinCRCErrorDn	                       OCTET STRING (SIZE (8)),
        eponLanEtherPortPrevious15MinPauseFramesDn	                   OCTET STRING (SIZE (8)),
        eponLanEtherPortPrevious15MinIntervalFirstSegOctetFramesDn      OCTET STRING (SIZE (8)),
        eponLanEtherPortPrevious15MinIntervalSecondSegOctetFramesDn     OCTET STRING (SIZE (8)),
        eponLanEtherPortPrevious15MinIntervalThirdSegOctetFramesDn      OCTET STRING (SIZE (8)),
        eponLanEtherPortPrevious15MinIntervalFourthSegOctetFramesDn     OCTET STRING (SIZE (8)),
        eponLanEtherPortPrevious15MinIntervalFifthSegOctetFramesDn      OCTET STRING (SIZE (8)),
        eponLanEtherPortPrevious15MinIntervalSixthSegOctetFramesDn      OCTET STRING (SIZE (8)),
        eponLanEtherPortPrevious15MinIntervalLastSegOctetFramesDn       OCTET STRING (SIZE (8)),
        eponLanEtherPortPrevious15MinIntervalUcastframesUP              OCTET STRING (SIZE (8)),
        eponLanEtherPortPrevious15MinIntervalNUcastframesUP             OCTET STRING (SIZE (8)),        
        eponLanEtherPortPrevious15MinIntervalDiscardframesUP            OCTET STRING (SIZE (8)),
        eponLanEtherPortPrevious15MinIntervalUcastframesDn              OCTET STRING (SIZE (8)),
        eponLanEtherPortPrevious15MinIntervalNUcastframesDw             OCTET STRING (SIZE (8)),        
        eponLanEtherPortPrevious15MinIntervalDiscardframesDn            OCTET STRING (SIZE (8)),
        eponLanEtherPortPrevious15MinIntervalUndersizeframesUp          OCTET STRING (SIZE (8)),
        eponLanEtherPortPrevious15MinIntervalUndersizeframesDn          OCTET STRING (SIZE (8)),
        eponLanEtherPortPrevious15MinIntervalOversizeframesUp           OCTET STRING (SIZE (8)),
        eponLanEtherPortPrevious15MinIntervalOversizeframesDn           OCTET STRING (SIZE (8)),
        eponLanEtherPortPrevious15MinIntervalErrorframesUp              OCTET STRING (SIZE (8)),
        eponLanEtherPortPrevious15MinIntervalErrorframesDn              OCTET STRING (SIZE (8)),
        eponLanEtherPortPrevious15MinIntervalMulticastframesUp          OCTET STRING (SIZE (8)),
        eponLanEtherPortPrevious15MinIntervalMulticastframesDn          OCTET STRING (SIZE (8)),
        eponLanEtherPortPrevious15MinIntervalStatuschange               OCTET STRING (SIZE (8)),
        eponLanEtherPortPrevious15MinIntervalDropEventsUP                   OCTET STRING (SIZE (8)),
        eponLanEtherPortPrevious15MinIntervalDropEventsDn                    OCTET STRING (SIZE (8)),
        eponLanEtherPortPrevious15MinIntervalFragmentsUP                     OCTET STRING (SIZE (8)),
        eponLanEtherPortPrevious15MinIntervalFragmentsDn                     OCTET STRING (SIZE (8)),
        eponLanEtherPortPrevious15MinIntervalJabberFramesUP               OCTET STRING (SIZE (8)),
        eponLanEtherPortPrevious15MinIntervalJabberFramesDn               OCTET STRING (SIZE (8))
}


eponLanEtherPortPrevious15MinIntervalNumber  OBJECT-TYPE 
        SYNTAX    INTEGER (1..192)
        ACCESS    not-accessible 
        STATUS    mandatory 
        DESCRIPTION 
            "Previous interval reference
             ALCATEL NOTE:
                 ACCESS:     NA       USAGE:      NA
                 PERSIST:    NO       INSRVMOD:   NO
                 RANGE:      1..192       DEFVALUE:   NA
                 UNITS:      NA       SPARSE:     NA
                 DESCR:      NA"
::= { eponLanEtherPortPrevious15MinIntervalEntry 1 } 

eponLanEtherPortPrevious15MinIntervalTimeMeasured  OBJECT-TYPE 
        SYNTAX    INTEGER 
        ACCESS    read-only 
        STATUS    mandatory 
        DESCRIPTION 
           "Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
::= { eponLanEtherPortPrevious15MinIntervalEntry 2 } 

eponLanEtherPortPrevious15MinIntervalOctetsTransUp  OBJECT-TYPE
	SYNTAX 	OCTET STRING (SIZE (8)) 	
	ACCESS	read-only
	STATUS	mandatory
	DESCRIPTION 
		"The object indicates octets transferred 
		 in upstream direction on ONT ethernet port.
		 ALCATEL NOTE:
                 ACCESS:     NA       USAGE:      NA
                 PERSIST:    NO       INSRVMOD:   NO
                 RANGE:      NA       DEFVALUE:   0
                 UNITS:      NA       SPARSE:     NA
                 DESCR:      NA"

::= { eponLanEtherPortPrevious15MinIntervalEntry 3 }


eponLanEtherPortPrevious15MinIntervalTotalFramesTransUp  OBJECT-TYPE
	SYNTAX 	OCTET STRING (SIZE (8)) 	
	ACCESS	read-only
	STATUS	mandatory
	DESCRIPTION 
		"The object indicates Total Frames transferred 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 4 }    
	
eponLanEtherPortPrevious15MinBroardFramesTransUp  OBJECT-TYPE
	SYNTAX 	OCTET STRING (SIZE (8)) 	
	ACCESS	read-only
	STATUS	mandatory
	DESCRIPTION 
		"The object indicates broadcastFrames transferred 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 5 }


eponLanEtherPortPrevious15MinCRCErrorUp  OBJECT-TYPE
	SYNTAX 	OCTET STRING (SIZE (8)) 	
	ACCESS	read-only
	STATUS	mandatory
	DESCRIPTION 
	"The object indicates CRC error Frames transferred 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 6 }

eponLanEtherPortPrevious15MinPauseFramesUp  OBJECT-TYPE
	SYNTAX 	OCTET STRING (SIZE (8)) 	
	ACCESS	read-only
	STATUS	mandatory
	DESCRIPTION 
		"The object indicates pause Frames transferred 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 7 }	
	
eponLanEtherPortPrevious15MinIntervalFirstSegOctetFramesUp	  OBJECT-TYPE
	SYNTAX 	OCTET STRING (SIZE (8)) 	
	ACCESS	read-only
	STATUS	mandatory
	DESCRIPTION 
		"The object indicates 64 Octet Frames n upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 8 }
	
eponLanEtherPortPrevious15MinIntervalSecondSegOctetFramesUp	  OBJECT-TYPE
	SYNTAX 	OCTET STRING (SIZE (8)) 	
	ACCESS	read-only
	STATUS	mandatory
	DESCRIPTION 
		"The object indicates 65-127 Octet Frames in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 9 }
	
eponLanEtherPortPrevious15MinIntervalThirdSegOctetFramesUp	  OBJECT-TYPE
	SYNTAX 	OCTET STRING (SIZE (8)) 	
	ACCESS	read-only
	STATUS	mandatory
	DESCRIPTION 
		"The object indicates 128-255 Octet Frames 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 10 }
	
eponLanEtherPortPrevious15MinIntervalFourthSegOctetFramesUp	  OBJECT-TYPE
	SYNTAX 	OCTET STRING (SIZE (8)) 	
	ACCESS	read-only
	STATUS	mandatory
	DESCRIPTION 
		"The object indicates 256-511 Octet Frames 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 11 }
	
eponLanEtherPortPrevious15MinIntervalFifthSegOctetFramesUp	  OBJECT-TYPE
	SYNTAX 	OCTET STRING (SIZE (8)) 	
	ACCESS	read-only
	STATUS	mandatory
	DESCRIPTION 
		"The object indicates 512-1023 Octet Frames in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 12 }
	
eponLanEtherPortPrevious15MinIntervalSixthSegOctetFramesUp	  OBJECT-TYPE
	SYNTAX 	OCTET STRING (SIZE (8)) 	
	ACCESS	read-only
	STATUS	mandatory
	DESCRIPTION 
		"The object indicates 1024-1518 Octet Frames 	in upstream direction on ONt ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 13 }
	
eponLanEtherPortPrevious15MinIntervalLastSegOctetFramesUp	  OBJECT-TYPE
	SYNTAX 	OCTET STRING (SIZE (8)) 	
	ACCESS	read-only
	STATUS	mandatory
	DESCRIPTION 
		"The object indicates 1519+ Octet Frames in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 14 }
	
eponLanEtherPortPrevious15MinIntervalOctetsTransDn  OBJECT-TYPE
	SYNTAX 	OCTET STRING (SIZE (8)) 	
	ACCESS	read-only
	STATUS	mandatory
	DESCRIPTION 
		"The object indicates octets transferred in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 15 }


eponLanEtherPortPrevious15MinIntervalTotalFramesTransDn  OBJECT-TYPE
	SYNTAX 	OCTET STRING (SIZE (8)) 	
	ACCESS	read-only
	STATUS	mandatory
	DESCRIPTION 
		"The object indicates Total Frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 16 }
	
eponLanEtherPortPrevious15MinBroardFramesTransDn  OBJECT-TYPE
	SYNTAX 	OCTET STRING (SIZE (8)) 	
	ACCESS	read-only
	STATUS	mandatory
	DESCRIPTION 
			"The object indicates broadcast Frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 17 }


eponLanEtherPortPrevious15MinCRCErrorDn  OBJECT-TYPE
	SYNTAX 	OCTET STRING (SIZE (8)) 	
	ACCESS	read-only
	STATUS	mandatory
	DESCRIPTION 
	"The object indicates CRC error Frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 18 }

eponLanEtherPortPrevious15MinPauseFramesDn  OBJECT-TYPE
	SYNTAX 	OCTET STRING (SIZE (8)) 	
	ACCESS	read-only
	STATUS	mandatory
	DESCRIPTION 
			"The object indicates pause Frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 19 }	
	
eponLanEtherPortPrevious15MinIntervalFirstSegOctetFramesDn	  OBJECT-TYPE
	SYNTAX 	OCTET STRING (SIZE (8)) 	
	ACCESS	read-only
	STATUS	mandatory
	DESCRIPTION 
		"The object indicates 64 Octet Frames 	in downstream direction on ONt ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 20 }
	
eponLanEtherPortPrevious15MinIntervalSecondSegOctetFramesDn	  OBJECT-TYPE
	SYNTAX 	OCTET STRING (SIZE (8)) 	
	ACCESS	read-only
	STATUS	mandatory
	DESCRIPTION 
		"The object indicates 65-127 Octet Frames	in downstream direction on ONt ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 21 }
	
eponLanEtherPortPrevious15MinIntervalThirdSegOctetFramesDn	  OBJECT-TYPE
	SYNTAX 	OCTET STRING (SIZE (8)) 	
	ACCESS	read-only
	STATUS	mandatory
	DESCRIPTION 
		"The object indicates 128-255 Octet Frames 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 22 }
	
eponLanEtherPortPrevious15MinIntervalFourthSegOctetFramesDn	  OBJECT-TYPE
	SYNTAX 	OCTET STRING (SIZE (8)) 	
	ACCESS	read-only
	STATUS	mandatory
	DESCRIPTION 
		"The object indicates 256-511 Octet Frames 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 23 }
	
eponLanEtherPortPrevious15MinIntervalFifthSegOctetFramesDn	  OBJECT-TYPE
	SYNTAX 	OCTET STRING (SIZE (8)) 	
	ACCESS	read-only
	STATUS	mandatory
	DESCRIPTION 
		"The object indicates 512-1023 Octet Frames in downstream direction on ONE ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 24 }
	
eponLanEtherPortPrevious15MinIntervalSixthSegOctetFramesDn	  OBJECT-TYPE
	SYNTAX 	OCTET STRING (SIZE (8)) 	
	ACCESS	read-only
	STATUS	mandatory
	DESCRIPTION 
		"The object indicates 1024-1518 Octet Frames in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 25 }
	
eponLanEtherPortPrevious15MinIntervalLastSegOctetFramesDn	  OBJECT-TYPE
	SYNTAX 	OCTET STRING (SIZE (8)) 	
	ACCESS	read-only
	STATUS	mandatory
	DESCRIPTION 
		"The object indicates 1519+ Octet Frames in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 26 }         
	
eponLanEtherPortPrevious15MinIntervalUcastframesUP  OBJECT-TYPE
	SYNTAX 	OCTET STRING (SIZE (8)) 	
	ACCESS	read-only
	STATUS	mandatory
	DESCRIPTION 
			"The object indicates unicast Frames transferred 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 27 }

eponLanEtherPortPrevious15MinIntervalNUcastframesUP  OBJECT-TYPE
  SYNTAX  OCTET STRING (SIZE (8)) 	
  ACCESS  read-only
  STATUS  mandatory
  DESCRIPTION 
    "The object indicates not unicast Frames transferred 	in upstream direction on ONT ethernet port"
  ::= { eponLanEtherPortPrevious15MinIntervalEntry 28 }

eponLanEtherPortPrevious15MinIntervalDiscardframesUP  OBJECT-TYPE
	SYNTAX 	OCTET STRING (SIZE (8)) 	
	ACCESS	read-only
	STATUS	mandatory
	DESCRIPTION 
			"The object indicates discard Frames transferred 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 29 }

eponLanEtherPortPrevious15MinIntervalUcastframesDn  OBJECT-TYPE
	SYNTAX 	OCTET STRING (SIZE (8)) 	
	ACCESS	read-only
	STATUS	mandatory
	DESCRIPTION 
			"The object indicates unicast Frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 30 }

eponLanEtherPortPrevious15MinIntervalNUcastframesDw  OBJECT-TYPE
  SYNTAX  OCTET STRING (SIZE (8)) 	
  ACCESS  read-only
  STATUS  mandatory
  DESCRIPTION 
    "The object indicates not unicast Frames transferred 	in downstream direction on ONT ethernet port"
  ::= { eponLanEtherPortPrevious15MinIntervalEntry 31 }

eponLanEtherPortPrevious15MinIntervalDiscardframesDn  OBJECT-TYPE
	SYNTAX 	OCTET STRING (SIZE (8)) 	
	ACCESS	read-only
	STATUS	mandatory
	DESCRIPTION 
			"The object indicates discard Frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 32 }

eponLanEtherPortPrevious15MinIntervalUndersizeframesUp  OBJECT-TYPE
	SYNTAX 	OCTET STRING (SIZE (8)) 	
	ACCESS	read-only
	STATUS	mandatory
	DESCRIPTION 
			"The object indicates less than 64 bytes Frames transferred in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 33 }

eponLanEtherPortPrevious15MinIntervalUndersizeframesDn  OBJECT-TYPE
	SYNTAX 	OCTET STRING (SIZE (8)) 	
	ACCESS	read-only
	STATUS	mandatory
	DESCRIPTION 
			"The object indicates less than 64 bytes Frames transferred in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 34 }

eponLanEtherPortPrevious15MinIntervalOversizeframesUp  OBJECT-TYPE
	SYNTAX 	OCTET STRING (SIZE (8)) 	
	ACCESS	read-only
	STATUS	mandatory
	DESCRIPTION 
			"The object indicates 1526+ Frames transferred in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 35 }

eponLanEtherPortPrevious15MinIntervalOversizeframesDn  OBJECT-TYPE
	SYNTAX 	OCTET STRING (SIZE (8)) 	
	ACCESS	read-only
	STATUS	mandatory
	DESCRIPTION 
			"The object indicates 1526+ Frames transferred in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 36 }

eponLanEtherPortPrevious15MinIntervalErrorframesUp  OBJECT-TYPE
	SYNTAX 	OCTET STRING (SIZE (8)) 	
	ACCESS	read-only
	STATUS	mandatory
	DESCRIPTION 
			"The object indicates error Frames transferred 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 37 }

eponLanEtherPortPrevious15MinIntervalErrorframesDn  OBJECT-TYPE
	SYNTAX 	OCTET STRING (SIZE (8)) 	
	ACCESS	read-only
	STATUS	mandatory
	DESCRIPTION 
			"The object indicates error Frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 38 }

eponLanEtherPortPrevious15MinIntervalMulticastframesUp  OBJECT-TYPE
	SYNTAX 	OCTET STRING (SIZE (8)) 	
	ACCESS	read-only
	STATUS	mandatory
	DESCRIPTION 
			"The object indicates multicast Frames transferred 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 39 }

eponLanEtherPortPrevious15MinIntervalMulticastframesDn  OBJECT-TYPE
	SYNTAX 	OCTET STRING (SIZE (8)) 	
	ACCESS	read-only
	STATUS	mandatory
	DESCRIPTION 
			"The object indicates multicast Frames transferred 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 40 }

eponLanEtherPortPrevious15MinIntervalStatuschange  OBJECT-TYPE
	SYNTAX 	OCTET STRING (SIZE (8)) 	
	ACCESS	read-only
	STATUS	mandatory
	DESCRIPTION 
			"The object indicates port status change times.
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious15MinIntervalEntry 41 }
                                     
eponLanEtherPortPrevious15MinIntervalDropEventsUP	  OBJECT-TYPE
	SYNTAX 	OCTET STRING (SIZE (8)) 	
	ACCESS	read-only
	STATUS	mandatory
	DESCRIPTION 
		"The object indicates drop event in upstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 42 }     

eponLanEtherPortPrevious15MinIntervalDropEventsDn	  OBJECT-TYPE
	SYNTAX 	OCTET STRING (SIZE (8)) 	
	ACCESS	read-only
	STATUS	mandatory
	DESCRIPTION 
		"The object indicates drop event in downstream direction on ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 43 }     

eponLanEtherPortPrevious15MinIntervalFragmentsUP	  OBJECT-TYPE
	SYNTAX 	OCTET STRING (SIZE (8)) 	
	ACCESS	read-only
	STATUS	mandatory
	DESCRIPTION 
		"The object indicates fragment frames in upstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 44 }     

eponLanEtherPortPrevious15MinIntervalFragmentsDn	  OBJECT-TYPE
	SYNTAX 	OCTET STRING (SIZE (8)) 	
	ACCESS	read-only
	STATUS	mandatory
	DESCRIPTION 
		"The object indicates fragment frames in downstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 45 }     

eponLanEtherPortPrevious15MinIntervalJabberFramesUP    OBJECT-TYPE
	SYNTAX 	OCTET STRING (SIZE (8)) 	
	ACCESS	read-only
	STATUS	mandatory
	DESCRIPTION 
		"The object indicates jabber  frames in upstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 46 }     

eponLanEtherPortPrevious15MinIntervalJabberFramesDn      OBJECT-TYPE
	SYNTAX 	OCTET STRING (SIZE (8)) 	
	ACCESS	read-only
	STATUS	mandatory
	DESCRIPTION 
		"The object indicates jabber  frames in downstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious15MinIntervalEntry 47 }     


-- *********************************************

-- EPON ONT UNI PERFORMANCE TABLE
--
-- This table contains Previous 1 day performance counters specific to
-- a specific UNI port . 

-- *********************************************

eponLanEtherPortPrevious1DayIntervalTable  OBJECT-TYPE
	SYNTAX SEQUENCE OF EponLanEtherPortPrevious1DayIntervalEntry
	ACCESS	not-accessible
	STATUS	mandatory   
	DESCRIPTION 
	 "1 day previous statistics for ONT ethernet interface.
	 ALCATEL NOTE:
             SUPPORT: YES   TABLESIZE: DEP"

	::= { eponStatisticsGroup 15 }                                                  

eponLanEtherPortPrevious1DayIntervalEntry  OBJECT-TYPE
	SYNTAX 	EponLanEtherPortPrevious1DayIntervalEntry
	ACCESS	not-accessible
	STATUS	mandatory 
	DESCRIPTION
         "	Table entry for the previous 1 day statistics counters for ONT ethernet interface.
          Row creation : an entry is created by the system when this ONT ethernet  statistics enabled.
          Row deletion :an entry is created by the system when this ONT ethernet  statistics disabled.
           ALCATEL NOTE:
             SUPPORT: YES"

	INDEX	{ eponLanEtherPortIfindex,
	          eponLanEtherPortPrevious1DayIntervalNumber }
	::= { eponLanEtherPortPrevious1DayIntervalTable 1 }

EponLanEtherPortPrevious1DayIntervalEntry ::= SEQUENCE {
	eponLanEtherPortPrevious1DayIntervalNumber                  INTEGER,                
	eponLanEtherPortPrevious1DayIntervalTimeMeasured               INTEGER, 
        eponLanEtherPortPrevious1DayIntervalOctetsTransUp		       OCTET STRING (SIZE (8)),
        eponLanEtherPortPrevious1DayIntervalTotalFramesTransUp	       OCTET STRING (SIZE (8)), 
        eponLanEtherPortPrevious1DayBroardFramesTransUp	               OCTET STRING (SIZE (8)),
        eponLanEtherPortPrevious1DayCRCErrorUp	                       OCTET STRING (SIZE (8)),
        eponLanEtherPortPrevious1DayPauseFramesUp	                   OCTET STRING (SIZE (8)),
        eponLanEtherPortPrevious1DayIntervalFirstSegOctetFramesUp      OCTET STRING (SIZE (8)),
        eponLanEtherPortPrevious1DayIntervalSecondSegOctetFramesUp     OCTET STRING (SIZE (8)),
        eponLanEtherPortPrevious1DayIntervalThirdSegOctetFramesUp      OCTET STRING (SIZE (8)),
        eponLanEtherPortPrevious1DayIntervalFourthSegOctetFramesUp     OCTET STRING (SIZE (8)),
        eponLanEtherPortPrevious1DayIntervalFifthSegOctetFramesUp      OCTET STRING (SIZE (8)),
        eponLanEtherPortPrevious1DayIntervalSixthSegOctetFramesUp      OCTET STRING (SIZE (8)),
        eponLanEtherPortPrevious1DayIntervalLastSegOctetFramesUp       OCTET STRING (SIZE (8)),
        eponLanEtherPortPrevious1DayIntervalOctetsTransDn		       OCTET STRING (SIZE (8)),
        eponLanEtherPortPrevious1DayIntervalTotalFramesTransDn	       OCTET STRING (SIZE (8)),
        eponLanEtherPortPrevious1DayBroardFramesTransDn	               OCTET STRING (SIZE (8)),
        eponLanEtherPortPrevious1DayCRCErrorDn	                       OCTET STRING (SIZE (8)),
        eponLanEtherPortPrevious1DayPauseFramesDn	                   OCTET STRING (SIZE (8)),
        eponLanEtherPortPrevious1DayIntervalFirstSegOctetFramesDn      OCTET STRING (SIZE (8)),
        eponLanEtherPortPrevious1DayIntervalSecondSegOctetFramesDn     OCTET STRING (SIZE (8)),
        eponLanEtherPortPrevious1DayIntervalThirdSegOctetFramesDn      OCTET STRING (SIZE (8)),
        eponLanEtherPortPrevious1DayIntervalFourthSegOctetFramesDn     OCTET STRING (SIZE (8)),
        eponLanEtherPortPrevious1DayIntervalFifthSegOctetFramesDn      OCTET STRING (SIZE (8)),
        eponLanEtherPortPrevious1DayIntervalSixthSegOctetFramesDn      OCTET STRING (SIZE (8)),
        eponLanEtherPortPrevious1DayIntervalLastSegOctetFramesDn       OCTET STRING (SIZE (8)),
        eponLanEtherPortPrevious1DayIntervalUcastframesUP              OCTET STRING (SIZE (8)),
        eponLanEtherPortPrevious1DayIntervalNUcastframesUP             OCTET STRING (SIZE (8)),        
        eponLanEtherPortPrevious1DayIntervalDiscardframesUP            OCTET STRING (SIZE (8)),
        eponLanEtherPortPrevious1DayIntervalUcastframesDn              OCTET STRING (SIZE (8)),
        eponLanEtherPortPrevious1DayIntervalNUcastframesDw             OCTET STRING (SIZE (8)),
        eponLanEtherPortPrevious1DayIntervalDiscardframesDn            OCTET STRING (SIZE (8)),
        eponLanEtherPortPrevious1DayIntervalUndersizeframesUp          OCTET STRING (SIZE (8)),
        eponLanEtherPortPrevious1DayIntervalUndersizeframesDn          OCTET STRING (SIZE (8)),
        eponLanEtherPortPrevious1DayIntervalOversizeframesUp           OCTET STRING (SIZE (8)),
        eponLanEtherPortPrevious1DayIntervalOversizeframesDn           OCTET STRING (SIZE (8)),
        eponLanEtherPortPrevious1DayIntervalErrorframesUp              OCTET STRING (SIZE (8)),
        eponLanEtherPortPrevious1DayIntervalErrorframesDn              OCTET STRING (SIZE (8)),
        eponLanEtherPortPrevious1DayIntervalMulticastframesUp          OCTET STRING (SIZE (8)), 
        eponLanEtherPortPrevious1DayIntervalMulticastframesDn          OCTET STRING (SIZE (8)),              
        eponLanEtherPortPrevious1DayIntervalStatuschange               OCTET STRING (SIZE (8)),
        eponLanEtherPortPrevious1DayIntervalDropEventsUP                   OCTET STRING (SIZE (8)),
        eponLanEtherPortPrevious1DayIntervalDropEventsDn                    OCTET STRING (SIZE (8)),
        eponLanEtherPortPrevious1DayIntervalFragmentsUP                     OCTET STRING (SIZE (8)),
        eponLanEtherPortPrevious1DayIntervalFragmentsDn                     OCTET STRING (SIZE (8)),
        eponLanEtherPortPrevious1DayIntervalJabberFramesUP               OCTET STRING (SIZE (8)),
        eponLanEtherPortPrevious1DayIntervalJabberFramesDn               OCTET STRING (SIZE (8))        
}


eponLanEtherPortPrevious1DayIntervalNumber  OBJECT-TYPE 
        SYNTAX    INTEGER  (1..2)
        ACCESS    not-accessible
        STATUS    mandatory 
        DESCRIPTION 
            "Previous interval reference
             ALCATEL NOTE:
                 ACCESS:     NA       USAGE:      NA
                 PERSIST:    NO       INSRVMOD:   NO
                 RANGE:      1..2       DEFVALUE:   NA
                 UNITS:      NA       SPARSE:     NA
                 DESCR:      NA"
::= { eponLanEtherPortPrevious1DayIntervalEntry 1 } 

eponLanEtherPortPrevious1DayIntervalTimeMeasured  OBJECT-TYPE 
        SYNTAX    INTEGER 
        ACCESS    read-only 
        STATUS    mandatory 
        DESCRIPTION 
            "Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
::= { eponLanEtherPortPrevious1DayIntervalEntry 2 } 

eponLanEtherPortPrevious1DayIntervalOctetsTransUp  OBJECT-TYPE
	SYNTAX 	OCTET STRING (SIZE (8)) 	
	ACCESS	read-only
	STATUS	mandatory
	DESCRIPTION 
		"The object indicates octets transferred 
		 in upstream direction on ONT ethernet port.
		 ALCATEL NOTE:
                 ACCESS:     NA       USAGE:      NA
                 PERSIST:    NO       INSRVMOD:   NO
                 RANGE:      NA       DEFVALUE:   0
                 UNITS:      NA       SPARSE:     NA
                 DESCR:      NA"

::= { eponLanEtherPortPrevious1DayIntervalEntry 3 }


eponLanEtherPortPrevious1DayIntervalTotalFramesTransUp  OBJECT-TYPE
	SYNTAX 	OCTET STRING (SIZE (8)) 	
	ACCESS	read-only
	STATUS	mandatory
	DESCRIPTION 
		"The object indicates Total Frames transferred in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 4 }    
	
eponLanEtherPortPrevious1DayBroardFramesTransUp  OBJECT-TYPE
	SYNTAX 	OCTET STRING (SIZE (8)) 	
	ACCESS	read-only
	STATUS	mandatory
	DESCRIPTION 
		"The object indicates boradcast Frames transferred in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 5 }


eponLanEtherPortPrevious1DayCRCErrorUp  OBJECT-TYPE
	SYNTAX 	OCTET STRING (SIZE (8)) 	
	ACCESS	read-only
	STATUS	mandatory
	DESCRIPTION 
		"The object indicates CRC error Frames transferred in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 6 }

eponLanEtherPortPrevious1DayPauseFramesUp  OBJECT-TYPE
	SYNTAX 	OCTET STRING (SIZE (8)) 	
	ACCESS	read-only
	STATUS	mandatory
	DESCRIPTION 
			"The object indicates pause Frames transferred in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 7}	
	
eponLanEtherPortPrevious1DayIntervalFirstSegOctetFramesUp	  OBJECT-TYPE
	SYNTAX 	OCTET STRING (SIZE (8)) 	
	ACCESS	read-only
	STATUS	mandatory
	DESCRIPTION 
		"The object indicates 64 Octet Frames 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 8 }
	
eponLanEtherPortPrevious1DayIntervalSecondSegOctetFramesUp	  OBJECT-TYPE
	SYNTAX 	OCTET STRING (SIZE (8)) 	
	ACCESS	read-only
	STATUS	mandatory
	DESCRIPTION 
		"The object indicates 65-127 Octet Frames 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 9 }
	
eponLanEtherPortPrevious1DayIntervalThirdSegOctetFramesUp	  OBJECT-TYPE
	SYNTAX 	OCTET STRING (SIZE (8)) 	
	ACCESS	read-only
	STATUS	mandatory
	DESCRIPTION 
		"The object indicates 128-255 Octet Frames 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 10 }
	
eponLanEtherPortPrevious1DayIntervalFourthSegOctetFramesUp	  OBJECT-TYPE
	SYNTAX 	OCTET STRING (SIZE (8)) 	
	ACCESS	read-only
	STATUS	mandatory
	DESCRIPTION 
		"The object indicates 256-511 Octet Frames 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 11 }
	
eponLanEtherPortPrevious1DayIntervalFifthSegOctetFramesUp	  OBJECT-TYPE
	SYNTAX 	OCTET STRING (SIZE (8)) 	
	ACCESS	read-only
	STATUS	mandatory
	DESCRIPTION 
		"The object indicates 512-1023 Octet Frames in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 12 }
	
eponLanEtherPortPrevious1DayIntervalSixthSegOctetFramesUp	  OBJECT-TYPE
	SYNTAX 	OCTET STRING (SIZE (8)) 	
	ACCESS	read-only
	STATUS	mandatory
	DESCRIPTION 
		"The object indicates 1024-1518 Octet Frames in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 13 }
	
eponLanEtherPortPrevious1DayIntervalLastSegOctetFramesUp	  OBJECT-TYPE
	SYNTAX 	OCTET STRING (SIZE (8)) 	
	ACCESS	read-only
	STATUS	mandatory
	DESCRIPTION 
		"The object indicates 1519+ Octet Frames 	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 14 }
	
eponLanEtherPortPrevious1DayIntervalOctetsTransDn  OBJECT-TYPE
	SYNTAX 	OCTET STRING (SIZE (8)) 	
	ACCESS	read-only
	STATUS	mandatory
	DESCRIPTION 
		"The object indicates octets transferred 
		 in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 15 }


eponLanEtherPortPrevious1DayIntervalTotalFramesTransDn  OBJECT-TYPE
	SYNTAX 	OCTET STRING (SIZE (8)) 	
	ACCESS	read-only
	STATUS	mandatory
	DESCRIPTION 
		"The object indicates Total Frames transferred	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 16 }
	
eponLanEtherPortPrevious1DayBroardFramesTransDn  OBJECT-TYPE
	SYNTAX 	OCTET STRING (SIZE (8)) 	
	ACCESS	read-only
	STATUS	mandatory
	DESCRIPTION 
			"The object indicates broadcast Frames transferred	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 17 }


eponLanEtherPortPrevious1DayCRCErrorDn  OBJECT-TYPE
	SYNTAX 	OCTET STRING (SIZE (8)) 	
	ACCESS	read-only
	STATUS	mandatory
	DESCRIPTION 
		"The object indicates CRC error Frames transferred	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 18 }

eponLanEtherPortPrevious1DayPauseFramesDn  OBJECT-TYPE
	SYNTAX 	OCTET STRING (SIZE (8)) 	
	ACCESS	read-only
	STATUS	mandatory
	DESCRIPTION 
		"The object indicates pause Frames transferred	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 19 }	
	
eponLanEtherPortPrevious1DayIntervalFirstSegOctetFramesDn	  OBJECT-TYPE
	SYNTAX 	OCTET STRING (SIZE (8)) 	
	ACCESS	read-only
	STATUS	mandatory
	DESCRIPTION 
		"The object indicates 64 Octet Frames 	in downstream direction on ONt ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 20 }
	
eponLanEtherPortPrevious1DayIntervalSecondSegOctetFramesDn	  OBJECT-TYPE
	SYNTAX 	OCTET STRING (SIZE (8)) 	
	ACCESS	read-only
	STATUS	mandatory
	DESCRIPTION 
		"The object indicates 65-127 Octet Frames 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 21 }
	
eponLanEtherPortPrevious1DayIntervalThirdSegOctetFramesDn	  OBJECT-TYPE
	SYNTAX 	OCTET STRING (SIZE (8)) 	
	ACCESS	read-only
	STATUS	mandatory
	DESCRIPTION 
		"The object indicates 128-255 Octet Frames 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 22 }
	
eponLanEtherPortPrevious1DayIntervalFourthSegOctetFramesDn	  OBJECT-TYPE
	SYNTAX 	OCTET STRING (SIZE (8)) 	
	ACCESS	read-only
	STATUS	mandatory
	DESCRIPTION 
		"The object indicates 256-511 Octet Frames 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 23 }
	
eponLanEtherPortPrevious1DayIntervalFifthSegOctetFramesDn	  OBJECT-TYPE
	SYNTAX 	OCTET STRING (SIZE (8)) 	
	ACCESS	read-only
	STATUS	mandatory
	DESCRIPTION 
		"The object indicates 512-1023 Octet Frames 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 24 }
	
eponLanEtherPortPrevious1DayIntervalSixthSegOctetFramesDn	  OBJECT-TYPE
	SYNTAX 	OCTET STRING (SIZE (8)) 	
	ACCESS	read-only
	STATUS	mandatory
	DESCRIPTION 
		"The object indicates 1024-1518 Octet Frames 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 25 }
	
eponLanEtherPortPrevious1DayIntervalLastSegOctetFramesDn	  OBJECT-TYPE
	SYNTAX 	OCTET STRING (SIZE (8)) 	
	ACCESS	read-only
	STATUS	mandatory
	DESCRIPTION 
		"The object indicates 1519+ Octet Frames 	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 26 }         
    
eponLanEtherPortPrevious1DayIntervalUcastframesUP  OBJECT-TYPE
	SYNTAX 	OCTET STRING (SIZE (8)) 	
	ACCESS	read-only
	STATUS	mandatory
	DESCRIPTION 
			"The object indicates unicast Frames transferred	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 27 }

eponLanEtherPortPrevious1DayIntervalNUcastframesUP  OBJECT-TYPE
  SYNTAX  OCTET STRING (SIZE (8)) 	
  ACCESS  read-only
  STATUS  mandatory
  DESCRIPTION 
    "The object indicates not unicast Frames transferred	in upstream direction on ONT ethernet port."
  ::= { eponLanEtherPortPrevious1DayIntervalEntry 28 }

eponLanEtherPortPrevious1DayIntervalDiscardframesUP  OBJECT-TYPE
	SYNTAX 	OCTET STRING (SIZE (8)) 	
	ACCESS	read-only
	STATUS	mandatory
	DESCRIPTION 
			"The object indicates discard Frames transferred	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 29 }

eponLanEtherPortPrevious1DayIntervalUcastframesDn  OBJECT-TYPE
	SYNTAX 	OCTET STRING (SIZE (8)) 	
	ACCESS	read-only
	STATUS	mandatory
	DESCRIPTION 
			"The object indicates unicast Frames transferred	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 30 }

eponLanEtherPortPrevious1DayIntervalNUcastframesDw  OBJECT-TYPE
  SYNTAX  OCTET STRING (SIZE (8)) 	
  ACCESS  read-only
  STATUS  mandatory
  DESCRIPTION 
    "The object indicates not unicast Frames transferred	in downstream direction on ONT ethernet port."
  ::= { eponLanEtherPortPrevious1DayIntervalEntry 31 }

eponLanEtherPortPrevious1DayIntervalDiscardframesDn  OBJECT-TYPE
	SYNTAX 	OCTET STRING (SIZE (8)) 	
	ACCESS	read-only
	STATUS	mandatory
	DESCRIPTION 
			"The object indicates disacrd Frames transferred	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 32 }

eponLanEtherPortPrevious1DayIntervalUndersizeframesUp  OBJECT-TYPE
	SYNTAX 	OCTET STRING (SIZE (8)) 	
	ACCESS	read-only
	STATUS	mandatory
	DESCRIPTION 
			"The object indicates less than 64 bytes Frames transferred	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 33 }

eponLanEtherPortPrevious1DayIntervalUndersizeframesDn  OBJECT-TYPE
	SYNTAX 	OCTET STRING (SIZE (8)) 	
	ACCESS	read-only
	STATUS	mandatory
	DESCRIPTION 
			"The object indicates less than 64 bytes Frames transferred	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 34 }

eponLanEtherPortPrevious1DayIntervalOversizeframesUp  OBJECT-TYPE
	SYNTAX 	OCTET STRING (SIZE (8)) 	
	ACCESS	read-only
	STATUS	mandatory
	DESCRIPTION 
			"The object indicates 1526+ Frames transferred	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 35 }

eponLanEtherPortPrevious1DayIntervalOversizeframesDn  OBJECT-TYPE
	SYNTAX 	OCTET STRING (SIZE (8)) 	
	ACCESS	read-only
	STATUS	mandatory
	DESCRIPTION 
			"The object indicates 1526+ Frames transferred	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 36 }

eponLanEtherPortPrevious1DayIntervalErrorframesUp  OBJECT-TYPE
	SYNTAX 	OCTET STRING (SIZE (8)) 	
	ACCESS	read-only
	STATUS	mandatory
	DESCRIPTION 
			"The object indicates error Frames transferred	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 37 }

eponLanEtherPortPrevious1DayIntervalErrorframesDn  OBJECT-TYPE
	SYNTAX 	OCTET STRING (SIZE (8)) 	
	ACCESS	read-only
	STATUS	mandatory
	DESCRIPTION 
			"The object indicates error Frames transferred	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 38 }

eponLanEtherPortPrevious1DayIntervalMulticastframesUp  OBJECT-TYPE
	SYNTAX 	OCTET STRING (SIZE (8)) 	
	ACCESS	read-only
	STATUS	mandatory
	DESCRIPTION 
			"The object indicates multicast Frames transferred	in upstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 39 }

eponLanEtherPortPrevious1DayIntervalMulticastframesDn  OBJECT-TYPE
	SYNTAX 	OCTET STRING (SIZE (8)) 	
	ACCESS	read-only
	STATUS	mandatory
	DESCRIPTION 
			"The object indicates multicast Frames transferred	in downstream direction on ONT ethernet port
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 40 }

eponLanEtherPortPrevious1DayIntervalStatuschange  OBJECT-TYPE
	SYNTAX 	OCTET STRING (SIZE (8)) 	
	ACCESS	read-only
	STATUS	mandatory
	DESCRIPTION 
			"The object indicates port status change times.
ALCATEL NOTE:
                 ACCESS:     NA       USAGE:      NA
                 PERSIST:    NO       INSRVMOD:   NO
                 RANGE:      NA       DEFVALUE:   0
                 UNITS:      NA       SPARSE:     NA
                 DESCR:      NA"
::= { eponLanEtherPortPrevious1DayIntervalEntry 41 }

eponLanEtherPortPrevious1DayIntervalDropEventsUP	  OBJECT-TYPE
	SYNTAX 	OCTET STRING (SIZE (8)) 	
	ACCESS	read-only
	STATUS	mandatory
	DESCRIPTION 
		"The object indicates drop event in upstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 42 }     

eponLanEtherPortPrevious1DayIntervalDropEventsDn	  OBJECT-TYPE
	SYNTAX 	OCTET STRING (SIZE (8)) 	
	ACCESS	read-only
	STATUS	mandatory
	DESCRIPTION 
		"The object indicates drop event in downstream direction on ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 43 }     

eponLanEtherPortPrevious1DayIntervalFragmentsUP	  OBJECT-TYPE
	SYNTAX 	OCTET STRING (SIZE (8)) 	
	ACCESS	read-only
	STATUS	mandatory
	DESCRIPTION 
		"The object indicates fragment frames in upstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 44 }     

eponLanEtherPortPrevious1DayIntervalFragmentsDn	  OBJECT-TYPE
	SYNTAX 	OCTET STRING (SIZE (8)) 	
	ACCESS	read-only
	STATUS	mandatory
	DESCRIPTION 
		"The object indicates fragment frames in downstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 45 }     

eponLanEtherPortPrevious1DayIntervalJabberFramesUP    OBJECT-TYPE
	SYNTAX 	OCTET STRING (SIZE (8)) 	
	ACCESS	read-only
	STATUS	mandatory
	DESCRIPTION 
		"The object indicates jabber  frames in upstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 46 }     

eponLanEtherPortPrevious1DayIntervalJabberFramesDn      OBJECT-TYPE
	SYNTAX 	OCTET STRING (SIZE (8)) 	
	ACCESS	read-only
	STATUS	mandatory
	DESCRIPTION 
		"The object indicates jabber  frames in downstream direction on a ONT ethernet port.
ALCATEL NOTE:
                 ACCESS:     NA       USAGE:      NA
                 PERSIST:    NO       INSRVMOD:   NO
                 RANGE:      NA       DEFVALUE:   0
                 UNITS:      NA       SPARSE:     NA
                 DESCR:      NA"
	::= { eponLanEtherPortPrevious1DayIntervalEntry 47 }     
	
-- *********************************************
--
-- EPON ONT POTS Port Performance TABLE
--
-- Table of number of previous statistics intervals for the traffic on a 
-- ONT POTS Port
--
-- 
-- *********************************************

eponPOTSPerfInfoTable    OBJECT-TYPE 
        SYNTAX    SEQUENCE OF EponPOTSPerfInfoEntry 
        ACCESS    not-accessible
        STATUS    mandatory 
        DESCRIPTION 
             "Table of number of previous statistics intervals for the traffic on a 
            ONT POTS interface.  
            ALCATEL NOTE:
             SUPPORT: YES   TABLESIZE: DEP"
::= {eponStatisticsGroup 16 } 

eponPOTSPerfInfoEntry OBJECT-TYPE 
        SYNTAX    EponPOTSPerfInfoEntry 
        ACCESS    not-accessible 
        STATUS    mandatory 
        DESCRIPTION 
            "An entry in the eponPOTSPerfInfoEntry. 
          Row creation : an entry is created by the system when ONT pots port level statistics enable. 
            ALCATEL NOTE:
             SUPPORT: YES"      
             INDEX   { eponOntIndex, eponPotsPortId } 
::= { eponPOTSPerfInfoTable 1 } 

EponPOTSPerfInfoEntry ::= 
       SEQUENCE{ 
                eponPOTSPerfInfo15MinValidIntervals    INTEGER, 
                eponPOTSPerfInfo1DayValidIntervals     INTEGER 
                }    
                
 
    
eponPOTSPerfInfo15MinValidIntervals OBJECT-TYPE 
        SYNTAX    INTEGER 
        ACCESS    read-only 
        STATUS    mandatory 
        DESCRIPTION 
        "Number of previous 15 minutes intervals
             ALCATEL NOTE:
                 ACCESS:     NA       USAGE:      NA
                 PERSIST:    NO       INSRVMOD:   NO
                 RANGE:      NA       DEFVALUE:   0
                 UNITS:      NA       SPARSE:     NA
                 DESCR:      NA"
        ::= { eponPOTSPerfInfoEntry 1 } 

eponPOTSPerfInfo1DayValidIntervals OBJECT-TYPE 
        SYNTAX    INTEGER 
        ACCESS    read-only 
        STATUS    mandatory 
        DESCRIPTION 
        "Number of previous 1 day intervals
             ALCATEL NOTE:
                 ACCESS:     NA       USAGE:      NA
                 PERSIST:    NO       INSRVMOD:   NO
                 RANGE:      NA       DEFVALUE:   0
                 UNITS:      NA       SPARSE:     NA
                 DESCR:      NA"
        ::= { eponPOTSPerfInfoEntry 2 }  
        
-- *********************************************

-- EPON ONT POTS Current 15 Minutes Interval TABLE
--
-- This table contains current 15 Minutes performance counters specific to
-- a specific POTS port . 

-- *********************************************

eponPOTSCurrent15MinIntervalTable  OBJECT-TYPE
    SYNTAX SEQUENCE OF EponPOTSCurrent15MinIntervalEntry
    ACCESS  not-accessible 
    STATUS  mandatory 
    DESCRIPTION 
    "15 Minutes current statistics for ONT pots port interface.
     ALCATEL NOTE:
             SUPPORT: YES   TABLESIZE: DEP"
    ::= { eponStatisticsGroup 17 }                                                  

eponPOTSCurrent15MinIntervalEntry  OBJECT-TYPE
    SYNTAX  EponPOTSCurrent15MinIntervalEntry
    ACCESS  not-accessible
    STATUS  mandatory 
    DESCRIPTION 
    "Table entry for the current 15 minutes statistics counters for ONT POTS port interface.
          Row creation : an entry is created by the system when this ONT POTS port statistics enabled.
          Row deletion : an entry is created by the system when this ONT POTS port statistics disabled.
          ALCATEL NOTE :
          SUPPORT: YES"

    INDEX   { eponOntIndex, eponPotsPortId }
    ::= { eponPOTSCurrent15MinIntervalTable 1 }

EponPOTSCurrent15MinIntervalEntry ::= SEQUENCE {
   
        eponPOTSCurrent15MinIntervalTimeElapsed                INTEGER,                
        eponPOTSCurrent15MinIntervalTimeMeasured               INTEGER, 
        eponPOTSCurrent15MinIntervalTotalFramesTransUp         OCTET STRING (SIZE (8)),
        eponPOTSCurrent15MinIntervalTotalFramesTransDn         OCTET STRING (SIZE (8)), 
        eponPOTSCurrent15MinIntervalTotalMeanDelay             OCTET STRING (SIZE (8)),
        eponPOTSCurrent15MinIntervalTotalMeanJitter            OCTET STRING (SIZE (8)),
        eponPOTSCurrent15MinIntervalTotalLosspktRatio         OCTET STRING (SIZE (8))
}

eponPOTSCurrent15MinIntervalTimeElapsed  OBJECT-TYPE 
        SYNTAX    INTEGER 
        ACCESS    read-only 
        STATUS    mandatory 
        DESCRIPTION 
        "Elapsed time in interval (seconds)
             ALCATEL NOTE:
                ACCESS:     NA       USAGE:      NA
                PERSIST:    NO       INSRVMOD:   NO
                RANGE:      NA       DEFVALUE:   NA
                UNITS:      seconds  SPARSE:     NA
                DESCR:      NA"             
::= { eponPOTSCurrent15MinIntervalEntry 1 }

eponPOTSCurrent15MinIntervalTimeMeasured  OBJECT-TYPE 
        SYNTAX    INTEGER 
        ACCESS    read-only 
        STATUS    mandatory 
        DESCRIPTION 
        "Measured time in interval (seconds).
             ALCATEL NOTE:
                ACCESS:     NA       USAGE:      NA
                PERSIST:    NO       INSRVMOD:   NO
                RANGE:      NA       DEFVALUE:   NA
                UNITS:      seconds  SPARSE:     NA
                DESCR:      NA"
::= { eponPOTSCurrent15MinIntervalEntry 2 } 

eponPOTSCurrent15MinIntervalTotalFramesTransUp  OBJECT-TYPE
    SYNTAX  OCTET STRING (SIZE (8))
    ACCESS  read-only
    STATUS  mandatory
    DESCRIPTION 
    "The object indicates octets transferred in upstream direction on a ont pots port.
     ALCATEL NOTE:
                 ACCESS:     NA       USAGE:      NA
                 PERSIST:    NO       INSRVMOD:   NO
                 RANGE:      NA       DEFVALUE:   0
                 UNITS:      NA       SPARSE:     NA
                 DESCR:      NA"
::= { eponPOTSCurrent15MinIntervalEntry 3 }

eponPOTSCurrent15MinIntervalTotalFramesTransDn  OBJECT-TYPE
    SYNTAX  OCTET STRING (SIZE (8))
    ACCESS  read-only
    STATUS  mandatory
    DESCRIPTION 
    "The object indicates octets transferred in downstream direction on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSCurrent15MinIntervalEntry 4 }

eponPOTSCurrent15MinIntervalTotalMeanDelay  OBJECT-TYPE
    SYNTAX  OCTET STRING (SIZE (8))
    ACCESS  read-only
    STATUS  mandatory
    DESCRIPTION 
    "The object min delay on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSCurrent15MinIntervalEntry 5 }

eponPOTSCurrent15MinIntervalTotalMeanJitter  OBJECT-TYPE
    SYNTAX  OCTET STRING (SIZE (8))
    ACCESS  read-only
    STATUS  mandatory
    DESCRIPTION 
    "The object max delay on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSCurrent15MinIntervalEntry 6 }

eponPOTSCurrent15MinIntervalTotalLosspktRatio  OBJECT-TYPE
    SYNTAX  OCTET STRING (SIZE (8))
    ACCESS  read-only
    STATUS  mandatory
    DESCRIPTION 
    "The object loss ratio on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSCurrent15MinIntervalEntry 7 }

-- *********************************************

-- EPON ONT POTS Current 1 Day Interval TABLE
--
-- This table contains current 1 day performance counters specific to
-- a specific POTS port . 

-- *********************************************

eponPOTSCurrent1DayIntervalTable  OBJECT-TYPE
    SYNTAX SEQUENCE OF EponPOTSCurrent1DayIntervalEntry
    ACCESS  not-accessible 
    STATUS  mandatory 
    DESCRIPTION 
    "15 Minutes current statistics for ONT pots port interface.
     ALCATEL NOTE:
             SUPPORT: YES   TABLESIZE: DEP"
    ::= { eponStatisticsGroup 18 }                                                  

eponPOTSCurrent1DayIntervalEntry  OBJECT-TYPE
    SYNTAX  EponPOTSCurrent1DayIntervalEntry
    ACCESS  not-accessible
    STATUS  mandatory 
    DESCRIPTION 
    "Table entry for the current 15 minutes statistics counters for ONT POTS port interface.
          Row creation : an entry is created by the system when this ONT POTS port statistics enabled.
          Row deletion : an entry is created by the system when this ONT POTS port statistics disabled.
          ALCATEL NOTE :
          SUPPORT: YES"

    INDEX   { eponOntIndex, eponPotsPortId }
    ::= { eponPOTSCurrent1DayIntervalTable 1 }

EponPOTSCurrent1DayIntervalEntry ::= SEQUENCE {
   
        eponPOTSCurrent1DayIntervalTimeElapsed                INTEGER,                
        eponPOTSCurrent1DayIntervalTimeMeasured               INTEGER, 
        eponPOTSCurrent1DayIntervalTotalFramesTransUp         OCTET STRING (SIZE (8)),
        eponPOTSCurrent1DayIntervalTotalFramesTransDn         OCTET STRING (SIZE (8)), 
        eponPOTSCurrent1DayIntervalTotalMeanDelay             OCTET STRING (SIZE (8)),
        eponPOTSCurrent1DayIntervalTotalMeanJitter            OCTET STRING (SIZE (8)),
        eponPOTSCurrent1DayIntervalTotalLosspktRatio         OCTET STRING (SIZE (8))
}

eponPOTSCurrent1DayIntervalTimeElapsed  OBJECT-TYPE 
        SYNTAX    INTEGER 
        ACCESS    read-only 
        STATUS    mandatory 
        DESCRIPTION 
        "Elapsed time in interval (seconds)
             ALCATEL NOTE:
                ACCESS:     NA       USAGE:      NA
                PERSIST:    NO       INSRVMOD:   NO
                RANGE:      NA       DEFVALUE:   NA
                UNITS:      seconds  SPARSE:     NA
                DESCR:      NA"             
::= { eponPOTSCurrent1DayIntervalEntry 1 }

eponPOTSCurrent1DayIntervalTimeMeasured  OBJECT-TYPE 
        SYNTAX    INTEGER 
        ACCESS    read-only 
        STATUS    mandatory 
        DESCRIPTION 
        "Measured time in interval (seconds).
             ALCATEL NOTE:
                ACCESS:     NA       USAGE:      NA
                PERSIST:    NO       INSRVMOD:   NO
                RANGE:      NA       DEFVALUE:   NA
                UNITS:      seconds  SPARSE:     NA
                DESCR:      NA"
::= { eponPOTSCurrent1DayIntervalEntry 2 } 

eponPOTSCurrent1DayIntervalTotalFramesTransUp  OBJECT-TYPE
    SYNTAX  OCTET STRING (SIZE (8))
    ACCESS  read-only
    STATUS  mandatory
    DESCRIPTION 
    "The object indicates octets transferred in upstream direction on a ont pots port.
     ALCATEL NOTE:
                 ACCESS:     NA       USAGE:      NA
                 PERSIST:    NO       INSRVMOD:   NO
                 RANGE:      NA       DEFVALUE:   0
                 UNITS:      NA       SPARSE:     NA
                 DESCR:      NA"
::= { eponPOTSCurrent1DayIntervalEntry 3 }

eponPOTSCurrent1DayIntervalTotalFramesTransDn  OBJECT-TYPE
    SYNTAX  OCTET STRING (SIZE (8))
    ACCESS  read-only
    STATUS  mandatory
    DESCRIPTION 
    "The object indicates octets transferred in downstream direction on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSCurrent1DayIntervalEntry 4 }

eponPOTSCurrent1DayIntervalTotalMeanDelay  OBJECT-TYPE
    SYNTAX  OCTET STRING (SIZE (8))
    ACCESS  read-only
    STATUS  mandatory
    DESCRIPTION 
    "The object min delay on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSCurrent1DayIntervalEntry 5 }

eponPOTSCurrent1DayIntervalTotalMeanJitter  OBJECT-TYPE
    SYNTAX  OCTET STRING (SIZE (8))
    ACCESS  read-only
    STATUS  mandatory
    DESCRIPTION 
    "The object max delay on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSCurrent1DayIntervalEntry 6 }

eponPOTSCurrent1DayIntervalTotalLosspktRatio  OBJECT-TYPE
    SYNTAX  OCTET STRING (SIZE (8))
    ACCESS  read-only
    STATUS  mandatory
    DESCRIPTION 
    "The object loss ratio on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSCurrent1DayIntervalEntry 7 }

-- *********************************************

-- EPON ONT POTS Previous 15 Minutes Interval TABLE
--
-- This table contains previous 15 Minutes performance counters specific to
-- a specific POTS port . 

-- *********************************************

eponPOTSPrevious15MinIntervalTable  OBJECT-TYPE
    SYNTAX SEQUENCE OF EponPOTSPrevious15MinIntervalEntry
    ACCESS  not-accessible 
    STATUS  mandatory 
    DESCRIPTION 
    "15 Minutes previous statistics for ONT pots port interface.
     ALCATEL NOTE:
             SUPPORT: YES   TABLESIZE: DEP"
    ::= { eponStatisticsGroup 19 }                                                  

eponPOTSPrevious15MinIntervalEntry  OBJECT-TYPE
    SYNTAX  EponPOTSPrevious15MinIntervalEntry
    ACCESS  not-accessible
    STATUS  mandatory 
    DESCRIPTION 
    "Table entry for the previous 15 minutes statistics counters for ONT POTS port interface.
          Row creation : an entry is created by the system when this ONT POTS port statistics enabled.
          Row deletion : an entry is created by the system when this ONT POTS port statistics disabled.
          ALCATEL NOTE :
          SUPPORT: YES"

    INDEX   { eponOntIndex, eponPotsPortId, eponPOTSPrevious15MinIntervalNumber }
    ::= { eponPOTSPrevious15MinIntervalTable 1 }

EponPOTSPrevious15MinIntervalEntry ::= SEQUENCE {
   
        eponPOTSPrevious15MinIntervalNumber                     INTEGER,                
        eponPOTSPrevious15MinIntervalTimeMeasured               INTEGER, 
        eponPOTSPrevious15MinIntervalTotalFramesTransUp         OCTET STRING (SIZE (8)),
        eponPOTSPrevious15MinIntervalTotalFramesTransDn         OCTET STRING (SIZE (8)), 
        eponPOTSPrevious15MinIntervalTotalMeanDelay             OCTET STRING (SIZE (8)),
        eponPOTSPrevious15MinIntervalTotalMeanJitter            OCTET STRING (SIZE (8)),
        eponPOTSPrevious15MinIntervalTotalLosspktRatio         OCTET STRING (SIZE (8))
}

eponPOTSPrevious15MinIntervalNumber  OBJECT-TYPE 
        SYNTAX    INTEGER 
        ACCESS    read-only 
        STATUS    mandatory 
        DESCRIPTION 
        "Elapsed time in interval (seconds)
             ALCATEL NOTE:
                ACCESS:     NA       USAGE:      NA
                PERSIST:    NO       INSRVMOD:   NO
                RANGE:      NA       DEFVALUE:   NA
                UNITS:      seconds  SPARSE:     NA
                DESCR:      NA"             
::= { eponPOTSPrevious15MinIntervalEntry 1 }

eponPOTSPrevious15MinIntervalTimeMeasured  OBJECT-TYPE 
        SYNTAX    INTEGER 
        ACCESS    read-only 
        STATUS    mandatory 
        DESCRIPTION 
        "Measured time in interval (seconds).
             ALCATEL NOTE:
                ACCESS:     NA       USAGE:      NA
                PERSIST:    NO       INSRVMOD:   NO
                RANGE:      NA       DEFVALUE:   NA
                UNITS:      seconds  SPARSE:     NA
                DESCR:      NA"
::= { eponPOTSPrevious15MinIntervalEntry 2 } 

eponPOTSPrevious15MinIntervalTotalFramesTransUp  OBJECT-TYPE
    SYNTAX  OCTET STRING (SIZE (8))
    ACCESS  read-only
    STATUS  mandatory
    DESCRIPTION 
    "The object indicates octets transferred in upstream direction on a ont pots port.
     ALCATEL NOTE:
                 ACCESS:     NA       USAGE:      NA
                 PERSIST:    NO       INSRVMOD:   NO
                 RANGE:      NA       DEFVALUE:   0
                 UNITS:      NA       SPARSE:     NA
                 DESCR:      NA"
::= { eponPOTSPrevious15MinIntervalEntry 3 }

eponPOTSPrevious15MinIntervalTotalFramesTransDn  OBJECT-TYPE
    SYNTAX  OCTET STRING (SIZE (8))
    ACCESS  read-only
    STATUS  mandatory
    DESCRIPTION 
    "The object indicates octets transferred in downstream direction on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSPrevious15MinIntervalEntry 4 }

eponPOTSPrevious15MinIntervalTotalMeanDelay  OBJECT-TYPE
    SYNTAX  OCTET STRING (SIZE (8))
    ACCESS  read-only
    STATUS  mandatory
    DESCRIPTION 
    "The object min delay on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSPrevious15MinIntervalEntry 5 }

eponPOTSPrevious15MinIntervalTotalMeanJitter  OBJECT-TYPE
    SYNTAX  OCTET STRING (SIZE (8))
    ACCESS  read-only
    STATUS  mandatory
    DESCRIPTION 
    "The object max delay on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSPrevious15MinIntervalEntry 6 }

eponPOTSPrevious15MinIntervalTotalLosspktRatio  OBJECT-TYPE
    SYNTAX  OCTET STRING (SIZE (8))
    ACCESS  read-only
    STATUS  mandatory
    DESCRIPTION 
    "The object loss ratio on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSPrevious15MinIntervalEntry 7 }

-- *********************************************

-- EPON ONT POTS Previous 1 Day Interval TABLE
--
-- This table contains previous 1 Day performance counters specific to
-- a specific POTS port . 

-- *********************************************

eponPOTSPrevious1DayIntervalTable  OBJECT-TYPE
    SYNTAX SEQUENCE OF EponPOTSPrevious1DayIntervalEntry
    ACCESS  not-accessible 
    STATUS  mandatory 
    DESCRIPTION 
    "15 Minutes previous statistics for ONT pots port interface.
     ALCATEL NOTE:
             SUPPORT: YES   TABLESIZE: DEP"
    ::= { eponStatisticsGroup 20 }                                                  

eponPOTSPrevious1DayIntervalEntry  OBJECT-TYPE
    SYNTAX  EponPOTSPrevious1DayIntervalEntry
    ACCESS  not-accessible
    STATUS  mandatory 
    DESCRIPTION 
    "Table entry for the previous 15 minutes statistics counters for ONT POTS port interface.
          Row creation : an entry is created by the system when this ONT POTS port statistics enabled.
          Row deletion : an entry is created by the system when this ONT POTS port statistics disabled.
          ALCATEL NOTE :
          SUPPORT: YES"

    INDEX   { eponOntIndex, eponPotsPortId, eponPOTSPrevious1DayIntervalNumber }
    ::= { eponPOTSPrevious1DayIntervalTable 1 }

EponPOTSPrevious1DayIntervalEntry ::= SEQUENCE {
   
        eponPOTSPrevious1DayIntervalNumber                     INTEGER,                
        eponPOTSPrevious1DayIntervalTimeMeasured               INTEGER, 
        eponPOTSPrevious1DayIntervalTotalFramesTransUp         OCTET STRING (SIZE (8)),
        eponPOTSPrevious1DayIntervalTotalFramesTransDn         OCTET STRING (SIZE (8)), 
        eponPOTSPrevious1DayIntervalTotalMeanDelay             OCTET STRING (SIZE (8)),
        eponPOTSPrevious1DayIntervalTotalMeanJitter            OCTET STRING (SIZE (8)),
        eponPOTSPrevious1DayIntervalTotalLosspktRatio         OCTET STRING (SIZE (8))
}

eponPOTSPrevious1DayIntervalNumber  OBJECT-TYPE 
        SYNTAX    INTEGER 
        ACCESS    read-only 
        STATUS    mandatory 
        DESCRIPTION 
        "Elapsed time in interval (seconds)
             ALCATEL NOTE:
                ACCESS:     NA       USAGE:      NA
                PERSIST:    NO       INSRVMOD:   NO
                RANGE:      NA       DEFVALUE:   NA
                UNITS:      seconds  SPARSE:     NA
                DESCR:      NA"             
::= { eponPOTSPrevious1DayIntervalEntry 1 }

eponPOTSPrevious1DayIntervalTimeMeasured  OBJECT-TYPE 
        SYNTAX    INTEGER 
        ACCESS    read-only 
        STATUS    mandatory 
        DESCRIPTION 
        "Measured time in interval (seconds).
             ALCATEL NOTE:
                ACCESS:     NA       USAGE:      NA
                PERSIST:    NO       INSRVMOD:   NO
                RANGE:      NA       DEFVALUE:   NA
                UNITS:      seconds  SPARSE:     NA
                DESCR:      NA"
::= { eponPOTSPrevious1DayIntervalEntry 2 } 

eponPOTSPrevious1DayIntervalTotalFramesTransUp  OBJECT-TYPE
    SYNTAX  OCTET STRING (SIZE (8))
    ACCESS  read-only
    STATUS  mandatory
    DESCRIPTION 
    "The object indicates octets transferred in upstream direction on a ont pots port.
     ALCATEL NOTE:
                 ACCESS:     NA       USAGE:      NA
                 PERSIST:    NO       INSRVMOD:   NO
                 RANGE:      NA       DEFVALUE:   0
                 UNITS:      NA       SPARSE:     NA
                 DESCR:      NA"
::= { eponPOTSPrevious1DayIntervalEntry 3 }

eponPOTSPrevious1DayIntervalTotalFramesTransDn  OBJECT-TYPE
    SYNTAX  OCTET STRING (SIZE (8))
    ACCESS  read-only
    STATUS  mandatory
    DESCRIPTION 
    "The object indicates octets transferred in downstream direction on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSPrevious1DayIntervalEntry 4 }

eponPOTSPrevious1DayIntervalTotalMeanDelay  OBJECT-TYPE
    SYNTAX  OCTET STRING (SIZE (8))
    ACCESS  read-only
    STATUS  mandatory
    DESCRIPTION 
    "The object min delay on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSPrevious1DayIntervalEntry 5 }

eponPOTSPrevious1DayIntervalTotalMeanJitter  OBJECT-TYPE
    SYNTAX  OCTET STRING (SIZE (8))
    ACCESS  read-only
    STATUS  mandatory
    DESCRIPTION 
    "The object max delay on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSPrevious1DayIntervalEntry 6 }

eponPOTSPrevious1DayIntervalTotalLosspktRatio  OBJECT-TYPE
    SYNTAX  OCTET STRING (SIZE (8))
    ACCESS  read-only
    STATUS  mandatory
    DESCRIPTION 
    "The object loss ratio on a ont pots port.
        ALCATEL NOTE:
                 ACCESS:     NA       USAGE:      NA
                 PERSIST:    NO       INSRVMOD:   NO
                 RANGE:      NA       DEFVALUE:   0
                 UNITS:      NA       SPARSE:     NA
                 DESCR:      NA"
::= { eponPOTSPrevious1DayIntervalEntry 7 }
      

-- *********************************************
--
-- EPON SYSTEM TABLE
--
--
-- 
-- *********************************************

eponPmCollectInd  OBJECT-TYPE
	SYNTAX 	INTEGER
	ACCESS	read-write
	STATUS	mandatory
	DESCRIPTION 
		" This indicates whether 
		  Performance Monitors should be collected for all ONTs.
	
		  1 = PM collection enabled
		  2 = PM collection disabled

		 Default = 1 = enabled.   "
	::= { eponSystemGroup 1 }
	

eponRogueONTAdmin  OBJECT-TYPE
	SYNTAX 	INTEGER
	ACCESS	read-write
	STATUS	mandatory
	DESCRIPTION 
		" This attribute allows the manager to choose auto or manual  
		  	   disable a rogue onu.
		  1 =  autodisable. If an onu is detected as rogue onu, system 
					will auto disable the onu tx power control.
		  2 =  manualdisable. If an onu is detected as rogue onu, system 
					will do nothing for the onu. Suggest manager manual disable
					the onu.
		 Default = 2  "
	::= { eponSystemGroup 3 }
	
eponOnuSnConflictLevel  OBJECT-TYPE
	SYNTAX 	INTEGER
	ACCESS	read-write
	STATUS	mandatory
	DESCRIPTION 
		"  This indicates ONT SN conflict level.		
		   0  = pon level 
			 1  = board level
 			 DF = 0"
	::= { eponSystemGroup 4 }
		       
-- *********************************************
-- EPON ONU ALARM FLAG TABLE
--
-- This table contains a list of software versions, firmware versions and alarm states of the ONT.
-- When OLT receives an CTC2.1 alarm from ONT, and this ONT SW version matches one of the entries in this table, 
-- OLT will parse the alarm state according to the value of the entrys,
-- eponOnuAlmFlagAlarmState. CTC2.1 define that alarm state bit 1 means alarm clear and 0 means alarm report. 
--
-- *********************************************

eponOnuAlmFlagTable  OBJECT-TYPE
	SYNTAX	SEQUENCE OF EponOnuAlmFlagEntry
	ACCESS	not-accessible
	STATUS	mandatory
	DESCRIPTION
		"This object contains a table for alarm state of ONT Software version and firmware version\
            ALCATEL NOTE:
             SUPPORT: YES   TABLESIZE: 250"
::= { eponSystemGroup 5 }

eponOnuAlmFlagEntry OBJECT-TYPE
	SYNTAX 	EponOnuAlmFlagEntry
	ACCESS	not-accessible
	STATUS	mandatory
	DESCRIPTION
		"Rows of this table contain information about alarm state of ONT SW version and firmware version. 
            ALCATEL NOTE:
             SUPPORT: YES"    
	INDEX {eponOnuAlmFlagIndex }
::= { eponOnuAlmFlagTable  1}

EponOnuAlmFlagEntry ::=
	SEQUENCE { 
		eponOnuAlmFlagIndex            INTEGER,
		eponOnuAlmFlagRowStatus        RowStatus,
		eponOnuAlmFlagSwVersion	       OCTET STRING (SIZE(0..16)),
                eponOnuAlmFlagFwVersion        OCTET STRING (SIZE(0..16)),
		eponOnuAlmFlagAlarmState       INTEGER
		}

eponOnuAlmFlagIndex OBJECT-TYPE 
	SYNTAX INTEGER
	ACCESS not-accessible
	STATUS mandatory
	DESCRIPTION
	    "This object is the index to the eponOnuAlmFlagTable.
	     Range is 1 .. 250  
		ALCATEL NOTE:
                 ACCESS:     NA       USAGE:      NA
                 PERSIST:    YES      INSRVMOD:   NO
                 RANGE:      1-250       DEFVALUE:   NA
                 UNITS:      NA       SPARSE:     NA"
::= { eponOnuAlmFlagEntry 1}

eponOnuAlmFlagRowStatus  OBJECT-TYPE
	SYNTAX 	RowStatus
	ACCESS	read-write
	STATUS	mandatory
	DESCRIPTION 
		"This object indicates the status of this entry.
		 ALCATEL NOTE:
		 ACCESS: read-write       usage: MAND
         persistent: YES   INSRVMOD:YES
         RANGE:1,4,6       DEFVALUE: NA  
         UNITS: NA         SPARSE: NA  "
::= { eponOnuAlmFlagEntry 2 }

eponOnuAlmFlagSwVersion OBJECT-TYPE
	SYNTAX 	OCTET STRING (SIZE(0..16))
	ACCESS	read-write
	STATUS	mandatory
	DESCRIPTION 
		" This attribute contains the ONT Software Version identifier.
		 ALCATEL NOTE:
		 ACCESS: read-write usage: NA
		 persistent: YES   INSRVMOD:NA
         RANGE:NA        DEFVALUE: NA
         UNITS: NA         SPARSE: NA
"
::= { eponOnuAlmFlagEntry 3}

eponOnuAlmFlagFwVersion OBJECT-TYPE
	SYNTAX 	OCTET STRING (SIZE(0..16))
	ACCESS	read-write
	STATUS	mandatory
	DESCRIPTION 
		" This attribute contains the ONT firmware Version identifier.
		 ALCATEL NOTE:
		 ACCESS: read-write usage: NA
		 persistent: YES   INSRVMOD:NA
         RANGE:NA        DEFVALUE: NA
         UNITS: NA         SPARSE: NA
"
::= { eponOnuAlmFlagEntry 4}

eponOnuAlmFlagAlarmState       OBJECT-TYPE 
	SYNTAX 	INTEGER
	ACCESS	read-write
	STATUS	mandatory
	DESCRIPTION 
		"Indicates whether the ONT's alarm state is same as ctc .
		 0 means same as ctc2.1
		 1 means different with ctc2.1
		 ALCATEL NOTE:
		 ACCESS: read-write usage: NA
		 persistent: YES   INSRVMOD:NA
         RANGE:NA        DEFVALUE: NA
         UNITS: NA         SPARSE: NA "
::= { eponOnuAlmFlagEntry 5}

eponOperatorType  OBJECT-TYPE
	SYNTAX  INTEGER
	ACCESS	read-write
	STATUS	mandatory
	DESCRIPTION 
		"This attribute indicates two OLT run methods, CTC standard or CU standard, 
		 for manager choosing.	
		   
		   1  means according to CTC standard 
		   2  means according to CU standard
		   
		 ALCATEL NOTE:
                   ACCESS:     read-write       USAGE:      NA
                   PERSIST:    YES              INSRVMOD:   NA
                   RANGE:      1-2              DEFVALUE:   1
                   UNITS:      NA               SPARSE:     NA"
	::= { eponSystemGroup 6 }
	
eponSnAutoBundleTimer  OBJECT-TYPE
	SYNTAX 	INTEGER
	ACCESS	read-write
	STATUS	mandatory
	DESCRIPTION 
		"This is used to specify SN bundle timer for each ONT under auto-bundle mode.	
Range is 1 - 72 in hours.
		  Default: 24 hours
ALCATEL NOTE:
		 ACCESS:  NA       USAGE:OPT
		 persistent:  YES    INSRVMOD:YES      
		 RANGE: 1..72    DEFVALUE: 24         
		 UNITS:  Hours    SPARSE: NA  "		 
	::= { eponSystemGroup 7 }
 
-- *********************************************
--
-- EPON ONUID for DHCP/PPP OPTION 
--
--
-- 
-- *********************************************

eponAccessLoopONUIDMethod  OBJECT-TYPE
	SYNTAX 	INTEGER
	ACCESS	read-write
	STATUS	mandatory
	DESCRIPTION 
		"This indicates which value should be filled in ONUID for DHCP/PPP option.	
		  1 = mac
		  2 = loid
		 Default = 1 = mac.   
		 
 ALCATEL NOTE:
		 ACCESS: NA        usage:OPT
		 persistent: YES    INSRVMOD:YES      
		 RANGE:1..2        DEFVALUE: 1         
		 UNITS: NA         SPARSE: NA  "		 
	::= { eponSystemGroup 2 }
    
-- *********************************************
--
-- EPON POTS PORT TABLE
--

-- This table contains a row for each provisioned POTS port on a
-- specific ONT. Rows are created dynamically by operator via
-- Create-and-go.  Some parameters are changeable once created.  
--

--
-- *********************************************

eponPotsPortTable  OBJECT-TYPE
	SYNTAX SEQUENCE OF EponPotsPortEntry
	ACCESS	not-accessible
	STATUS	mandatory
	::= { eponPotsGroup 1 }


eponPotsPortEntry  OBJECT-TYPE
	SYNTAX 	EponPotsPortEntry
	ACCESS	not-accessible
	STATUS	mandatory
	INDEX	{ eponOntIndex,
		  eponPotsPortId }
	::= { eponPotsPortTable 1 }

EponPotsPortEntry ::= SEQUENCE {
	eponPotsPortId                      INTEGER, 
	eponPotsPortRowStatus		    RowStatus,
	eponPotsPortAdminState              PonAdminState,
	eponPotsPortOperState		    PonOperState,
	eponPotsPortUseraccount             DisplayString (SIZE(0..16)),
	eponPotsPortUsername                DisplayString (SIZE(0..32)),
	eponPotsPortPassword                DisplayString (SIZE(0..16)),
	eponPotsPortTidName                 DisplayString (SIZE(0..32)),
	eponPotsPortState	            INTEGER,
	eponPotsPortServiceState	    INTEGER,
	eponPotsPortCodecMode	            INTEGER,
	eponPotsPortEchoCancel	            INTEGER,
	eponPotsPortReversedPolarity	    INTEGER,
	eponPotsPortTxGain	            INTEGER,
	eponPotsPortRxGain	            INTEGER,
	eponPotsPortIfIndex         INTEGER

}

eponPotsPortId  OBJECT-TYPE
	SYNTAX 	INTEGER (0..4294967295)
	ACCESS	read-only
	STATUS	mandatory
	DESCRIPTION 
		"Each row is also indexed by a number of the POTS UNI port number. 
		 the higher 16 bits means slotID, the lower 16 bits means portID.
		 
		ALCATEL NOTE:
                 ACCESS:     NA       USAGE:      NA
                 PERSIST:    YES      INSRVMOD:   NO
                 RANGE:      NA       DEFVALUE:   NA
                 UNITS:      NA       SPARSE:     NA
                "
	::= { eponPotsPortEntry 1 }

eponPotsPortRowStatus  OBJECT-TYPE
	SYNTAX 	RowStatus
	ACCESS	read-write
	STATUS	mandatory
	DESCRIPTION 
		"This object is used to create a new row or delete an exsited row
	 ALCATEL NOTE:
		 ACCESS: NA        usage: MAND
         persistent: YES   INSRVMOD:YES
         RANGE:1,4,6       DEFVALUE: NA  
         UNITS: NA         SPARSE: NA  "
	::= { eponPotsPortEntry 2 }

eponPotsPortAdminState  OBJECT-TYPE
	SYNTAX 	PonAdminState
	ACCESS	read-write
	STATUS	mandatory
	DESCRIPTION 
		"enable or disable port admin state, NOT SUPPORTED in R4230 release, replaced by entry in ifMIB		 
		 ALCATEL NOTE:
		 ACCESS: NA        usage:OPT
		 persistent: YES    INSRVMOD:YES      
		 RANGE:1..2        DEFVALUE: 1         
		 UNITS: NA         SPARSE: NA  "
	::= { eponPotsPortEntry 3 }

eponPotsPortOperState  OBJECT-TYPE
	SYNTAX 	PonOperState
	ACCESS	read-only
	STATUS	mandatory
	DESCRIPTION 
		"Indicates operational state of the Pots port, NOT SUPPORTED in R4230 release, replaced by entry in ifMIB
    ALCATEL NOTE:
		 ACCESS: NA        usage:NA
		 persistent: NA    INSRVMOD:NA       
		 RANGE:1..2        DEFVALUE: NA         
		 UNITS: NA         SPARSE: NA  "
	::= { eponPotsPortEntry 4 }
	
eponPotsPortUseraccount  OBJECT-TYPE
	SYNTAX 	DisplayString (SIZE(0..25))
	ACCESS	read-write
	STATUS	mandatory
	DESCRIPTION 
		"This is a textual string that contains the SIP Useraccount
		 required.

		 Default - null string. 
	 ALCATEL NOTE:
	 ACCESS: NA        usage: NA
	 persistent: YES   INSRVMOD:YES
         RANGE:NA       DEFVALUE: NULL  
         UNITS: NA         SPARSE: NA   "
	::= { eponPotsPortEntry  5 }
 
eponPotsPortUsername  OBJECT-TYPE
	SYNTAX 	DisplayString (SIZE(0..32))
	ACCESS	read-write
	STATUS	mandatory
	DESCRIPTION 
		"This is a textual string that contains the SIP Username
		 required .

		 Default - null string. 
	 ALCATEL NOTE:
	 ACCESS: NA        usage: NA
	 persistent: YES   INSRVMOD:YES
         RANGE:NA       DEFVALUE: NULL  
         UNITS: NA         SPARSE: NA   "
	::= { eponPotsPortEntry  6 }


eponPotsPortPassword  OBJECT-TYPE
	SYNTAX 	DisplayString (SIZE(0..16))
	ACCESS	read-write
	STATUS	mandatory
	DESCRIPTION 
		"This is a textual string that contains the SIP Password
		 required .

		 Default - null string. 

        ALCATEL NOTE:
	 ACCESS: NA        usage: NA
	 persistent: YES   INSRVMOD:YES
         RANGE:NA       DEFVALUE: NULL  
         UNITS: NA         SPARSE: NA    "
	::= { eponPotsPortEntry  7 } 
	
eponPotsPortTidName  OBJECT-TYPE
	SYNTAX 	DisplayString (SIZE(0..32))
	ACCESS	read-write
	STATUS	mandatory
	DESCRIPTION 
		"This is a textual string that contains the H.248 TID name.

		 Default - null string. 
	 ALCATEL NOTE:
	 ACCESS: NA        usage: NA
	 persistent: YES   INSRVMOD:YES
         RANGE:NA       DEFVALUE: NULL  
         UNITS: NA         SPARSE: NA   "
	::= { eponPotsPortEntry  8 }

eponPotsPortState  OBJECT-TYPE
	SYNTAX 	INTEGER 
	ACCESS	read-only
	STATUS	mandatory
	DESCRIPTION 
		"POTS port state
		
		0: registering
                1: idle
                2: offhook
                3: dialing
                4: ringing
                5: rinback
                6: connecting
                7: connected
                8: disconnecting
                9: register fail
                10: inactive 

		 
		ALCATEL NOTE:
                 ACCESS:     NA       USAGE:      NA
                 PERSIST:    NO       INSRVMOD:   NO
                 RANGE:      NA       DEFVALUE:   NA
                 UNITS:      NA       SPARSE:     NA
                "
	::= { eponPotsPortEntry 9 }
	
eponPotsPortServiceState  OBJECT-TYPE
	SYNTAX 	INTEGER 
	ACCESS	read-only
	STATUS	mandatory
	DESCRIPTION 
		"POTS port service state
		
		0: endLocal, operator disable the port
                1: endRemote, MGC command end the port
                2: endAuto, auto end caused by MGC failure
                3: normal, in service status
                
		 
		ALCATEL NOTE:
                 ACCESS:     NA       USAGE:      NA
                 PERSIST:    NO       INSRVMOD:   NO
                 RANGE:      NA       DEFVALUE:   NA
                 UNITS:      NA       SPARSE:     NA
                "
	::= { eponPotsPortEntry 10 }
	
eponPotsPortCodecMode  OBJECT-TYPE
	SYNTAX 	INTEGER 
	ACCESS	read-only
	STATUS	mandatory
	DESCRIPTION 
		"POTS port coding mode
		
		0: G.711 A
                1: G.729
                2: G.711U
                3: G.723
                4: G.726
                5: T.38
               255: UNKNOWN

		 
		ALCATEL NOTE:
                 ACCESS:     NA       USAGE:      NA
                 PERSIST:    NO       INSRVMOD:   NO
                 RANGE:      NA       DEFVALUE:   NA
                 UNITS:      NA       SPARSE:     NA
                "
	::= { eponPotsPortEntry 11 }

	eponPotsPortEchoCancel  OBJECT-TYPE
	SYNTAX 	INTEGER 
        {
              enable(1),
              disable(2)
        }
	ACCESS	read-only
	STATUS	mandatory
	DESCRIPTION 
		"indicate the echo cancel is enable or disable on this pots port.
		 
		ALCATEL NOTE:
                 ACCESS:     NA       USAGE:      NA
                 PERSIST:    NO       INSRVMOD:   NO
                 RANGE:      1|2       DEFVALUE:   NA
                 UNITS:      NA       SPARSE:     NA
                "
	::= { eponPotsPortEntry 12 }

eponPotsPortReversedPolarity OBJECT-TYPE
	SYNTAX 	INTEGER 
        {
              enable(1),
              disable(2)
        }
	ACCESS	read-only
	STATUS	mandatory
	DESCRIPTION 
		"indicate the reversed polarity is enable or disable on this pots port.
		 
		ALCATEL NOTE:
                 ACCESS:     NA       USAGE:      NA
                 PERSIST:    NO       INSRVMOD:   NO
                 RANGE:      1|2       DEFVALUE:   NA
                 UNITS:      NA       SPARSE:     NA
                "
	::= { eponPotsPortEntry 13 }

eponPotsPortTxGain OBJECT-TYPE
	SYNTAX 	INTEGER(-20..20)
	ACCESS	read-only
	STATUS	mandatory
	DESCRIPTION 
		"indicate transmission gain on this pots port.
		 
		ALCATEL NOTE:
                 ACCESS:     NA       USAGE:      NA
                 PERSIST:    NO       INSRVMOD:   NO
                 RANGE:    -20..20       DEFVALUE:   NA
                 UNITS:      db       SPARSE:     NA
                "
	::= { eponPotsPortEntry 14 }

eponPotsPortRxGain OBJECT-TYPE
	SYNTAX 	INTEGER(-20..20)
	ACCESS	read-only
	STATUS	mandatory
	DESCRIPTION 
		" indicate receive gain on this pots port.
		 
		ALCATEL NOTE:
                 ACCESS:     NA       USAGE:      NA
                 PERSIST:    NO       INSRVMOD:   NO
                 RANGE:      -20..20       DEFVALUE:   NA
                 UNITS:      db       SPARSE:     NA
                "
	::= { eponPotsPortEntry 15 }
	
eponPotsPortIfIndex  OBJECT-TYPE
	SYNTAX 	INTEGER
	ACCESS	read-only
	STATUS	mandatory
	DESCRIPTION 
		"Ifindex of the pots port 
		ALCATEL NOTE:
                 ACCESS:     NA       USAGE:      NA
                 PERSIST:    NA      INSRVMOD:   NA
                 RANGE:      NA       DEFVALUE:   NA
                 UNITS:      NA       SPARSE:     NA
                "
	::= { eponPotsPortEntry 16 }


eponPotsStatsTable OBJECT-TYPE
	SYNTAX SEQUENCE OF EponPotsStatsEntry
	ACCESS	not-accessible
	STATUS	mandatory
	::= { eponPotsGroup 2 }

eponPotsStatsEntry OBJECT-TYPE
	SYNTAX EponPotsStatsEntry
	ACCESS not-accessible
	STATUS mandatory
	INDEX { eponOntIndex,
                 eponPotsPortId}
	::= { eponPotsStatsTable 1 }

EponPotsStatsEntry ::= 
        SEQUENCE {
	eponPotsStatsTimestamp            NetworkTimeInSeconds, 
	eponPotsStatsRTCPTotalFramesTransUp   OCTET STRING (SIZE (8)),
	eponPotsStatsRTCPTotalFramesTransDn                   OCTET STRING (SIZE (8)),
	eponPotsStatsRTCPTotalMeanDelay     INTEGER,
	eponPotsStatsRTCPTotalMeanJitter                INTEGER,
	eponPotsStatsRTCPTotalLosspktRation    INTEGER
        }
	
eponPotsStatsTimestamp  OBJECT-TYPE
	SYNTAX 	NetworkTimeInSeconds
	ACCESS	read-only
	STATUS	mandatory
	DESCRIPTION 
		" Time value in seconds when the statistics start
		 
		ALCATEL NOTE:
                 ACCESS:     NA       USAGE:      NA
                 PERSIST:    NO      INSRVMOD:   NA
                 RANGE:      NA       DEFVALUE:   NA
                 UNITS:      seconds       SPARSE:     NA
                "
	::= { eponPotsStatsEntry 1 }

eponPotsStatsRTCPTotalFramesTransUp OBJECT-TYPE
	SYNTAX 	OCTET STRING (SIZE (8))
	ACCESS	read-only
	STATUS	mandatory
	DESCRIPTION 
		" The object indicates octets transferred in upstream direction on a ont pots port.
		 
		ALCATEL NOTE:
                 ACCESS:     NA       USAGE:      NA
                 PERSIST:    NO      INSRVMOD:   NA
                 RANGE:      NA       DEFVALUE:   0
                 UNITS:      NA       SPARSE:     NA
                "
	::= { eponPotsStatsEntry 2 }

eponPotsStatsRTCPTotalFramesTransDn     OBJECT-TYPE
	SYNTAX 	OCTET STRING (SIZE (8))
	ACCESS	read-only
	STATUS	mandatory
	DESCRIPTION 
		" The object indicates octets transferred in downstream direction on a ont pots port.
		 
		ALCATEL NOTE:
                 ACCESS:     NA       USAGE:      NA
                 PERSIST:    NO      INSRVMOD:   NA
                 RANGE:      NA       DEFVALUE:   0
                 UNITS:      NA       SPARSE:     NA
                "
	::= { eponPotsStatsEntry 3 }

eponPotsStatsRTCPTotalMeanDelay        OBJECT-TYPE
	SYNTAX  INTEGER
	ACCESS	read-only
	STATUS	mandatory
	DESCRIPTION 
		" The object indicates RTCP packets total mean delay on a ont pots port.
		 
		ALCATEL NOTE:
                 ACCESS:     NA       USAGE:      NA
                 PERSIST:    NO      INSRVMOD:   NA
                 RANGE:      0..65535       DEFVALUE:   0
                 UNITS:      MILLISECOND  SPARSE:     NA
                "
	::= { eponPotsStatsEntry 4 }

eponPotsStatsRTCPTotalMeanJitter    OBJECT-TYPE
	SYNTAX  INTEGER
	ACCESS	read-only
	STATUS	mandatory
	DESCRIPTION 
		" The object indicates RTCP packets total mean jitter on a ont pots port.
		 
		ALCATEL NOTE:
                 ACCESS:     NA       USAGE:      NA
                 PERSIST:    NO      INSRVMOD:   NA
                 RANGE:      0..65535       DEFVALUE:   0
                 UNITS:      MILLISECOND  SPARSE:     NA
                "
	::= { eponPotsStatsEntry 5 }

eponPotsStatsRTCPTotalLosspktRation    OBJECT-TYPE
	SYNTAX  INTEGER(0..100)
	ACCESS	read-only
	STATUS	mandatory
	DESCRIPTION 
		" The object indicates the total loss ration of lost RTCP packets on a ont pots port.
		 
		ALCATEL NOTE:
                 ACCESS:     NA       USAGE:      NA
                 PERSIST:    NO      INSRVMOD:   NA
                 RANGE:      (0..100)       DEFVALUE:   0
                 UNITS:      Percentage SPARSE:     NA
                "
	::= { eponPotsStatsEntry 6 }

-- *********************************************
-- EPON ONT SOFTWARE VERSION CONTROL TABLE
--
--
-- This table associates ONT HW Version/Variant with appropriate
-- ONT SW Version (download and planned).  The instructions in this table are used when
-- the following are TRUE: 
-- 1) Either Planned SW Version and/or Download SW Version (in ONT Table) are set to AUTO,
-- 2) Actual HW Version and specified SW Variant (in ONT Table) have a match in this table.
-- When such case is TRUE,  the logic behaves as if the appropriate AUTO selection (in ONT Table)
-- was instead replaced by the respective SW Version specified in this table.
--
--  Rows are created by the operator.
--
-- *********************************************

eponOntSwVerCtlTable OBJECT-TYPE
	SYNTAX	SEQUENCE OF EponOntSwVerCtlEntry
	ACCESS	not-accessible
	STATUS	mandatory
	DESCRIPTION
		"This object contains a table for automating the download
		and activation of ONT software (based on ONT HW version). "
::= { eponOntSwGroup 1 }

eponOntSwVerCtlEntry OBJECT-TYPE
	SYNTAX 	EponOntSwVerCtlEntry
	ACCESS	not-accessible
	STATUS	mandatory
	DESCRIPTION
		"Rows of this table contain ONT HW version keys and
		 associated ONT SW versions. "
	INDEX {eponOntSwVerCtlIndex }
::= {eponOntSwVerCtlTable 1}

EponOntSwVerCtlEntry ::=
	SEQUENCE { 
		eponOntSwVerCtlIndex		          INTEGER,
		eponOntSwVerCtlRowStatus 	          RowStatus,
		eponOntSwVerCtlHwVersion		  DisplayString(SIZE(0..8)),
		eponOntSwVerCtlPlannedSwVersion 	  DisplayString(SIZE(0..16)),
                eponOntSwVerCtrlUpgradeMode               INTEGER,
                eponOntSwVerCtlPlannedVariant DisplayString(SIZE(0..16))
                
		}

eponOntSwVerCtlIndex OBJECT-TYPE 
	SYNTAX INTEGER
	ACCESS not-accessible
	STATUS mandatory
	DESCRIPTION
	    "This object is the index to the eponOntSwVerCtlTable.
	     Range is 1 .. 500  "
::= { eponOntSwVerCtlEntry 1}

eponOntSwVerCtlRowStatus OBJECT-TYPE 
	SYNTAX	RowStatus
	ACCESS	read-write
	STATUS  mandatory
	DESCRIPTION
		"This object is used to create a new row or modify or
         		delete an existing row in this table. "
::= { eponOntSwVerCtlEntry  2}

eponOntSwVerCtlHwVersion 	OBJECT-TYPE 
	SYNTAX 	DisplayString(SIZE(0..8))
	ACCESS	read-write
	STATUS	mandatory
	DESCRIPTION 
		" This is the ONT Hardware Version. Has same connotation as bponOntVersionNumber
		  attribute in eponOntTable.  This attribute is a key in this table.  The 
		  attribute MUST be unique, otherwise it is rejected.

		  Modification is NOT permitted (i.e. CANNOT a key field). 

		  No default - must be supplied by operator.  "
::= {eponOntSwVerCtlEntry 3}


eponOntSwVerCtlPlannedSwVersion  OBJECT-TYPE
	SYNTAX 	DisplayString(SIZE(0..16))
	ACCESS	read-write
	STATUS	mandatory
	DESCRIPTION 
		" This attribute has same connotation as eponOntSwPlannedVersion attribute in eponOntTable. When eponOntSwPlannedVersion is set to special value AUTO, and that ONT's hardware version have a match in this table, then this attribute is used in place of the eponOntSwPlannedVersion.
		  
		  Modification is permitted.
"
::= {eponOntSwVerCtlEntry 4}

eponOntSwVerCtrlUpgradeMode             OBJECT-TYPE
	SYNTAX 	INTEGER
	ACCESS	read-write
	STATUS	mandatory
	DESCRIPTION 
		" 
		  This attribute is used to specify  Software upgarde Mode    
                   NONE (0)
		   CTC (1)
		   TK  (2)
		  
		 ALCATEL NOTE:
		 ACCESS: NA        usage: NA
		 persistent: NA    INSRVMOD:NA
         RANGE:0..2        DEFVALUE: 1
         UNITS: NA         SPARSE: NA "
	::= { eponOntSwVerCtlEntry 5 }  

eponOntSwVerCtlPlannedVariant   OBJECT-TYPE
        SYNTAX  DisplayString
        ACCESS  read-write
        STATUS  mandatory
        DESCRIPTION
                " This attribute has same connotation as eponOntPlannedVariant attribute in eponOntTable.   
                  This attribute is a key in this table.  The combination of this attribute and the
                  eponOntSwVerCtlHwVersion attribute MUST be unique, otherwise it is rejected.
      
                  Modification is permitted (i.e. CANNOT a key field).
      
                  Maximum of 16 displayable characters.
      
                  Default = null string.  "
::= {eponOntSwVerCtlEntry 6}
eponOntSwVerCtlIndexNext    OBJECT-TYPE
        	SYNTAX          INTEGER
        	ACCESS          read-only
        	STATUS          mandatory
        	DESCRIPTION     
        	        	" This object contains an appropriate value to be used for eponOntSwVerCtlIndex 
		   when creating entries in the eponOntSwVerCtlTable. 
		   Range is 0 .. 500.
         		   The value 0 indicates that no unassigned entries are available. To 
         		   obtain the next avaialble index value for a new entry, the
        		   manager can issue a management protocol retrieval operation to obtain the
         		   current value of this object.  After each retrieval, the agent should
        		   modify the value to the next unassigned index. "
::= {eponOntSwGroup 5 }


-- *********************************************
-- EPON ONT SOFTWARE VERSION INFO TABLE
--
-- This table contains a listing of ONT Software Versions that are currently resident on the 
-- the NT file system.
--
-- For this initial GET of the 1st row, the OLT agent will delay
-- the GET-RESPONSE while it replenishes the entire
-- table with fresh information
--
-- *********************************************

eponOntSwVerInfoTable OBJECT-TYPE
	SYNTAX	SEQUENCE OF EponOntSwVerInfoEntry
	ACCESS	not-accessible
	STATUS	mandatory
	DESCRIPTION
		"This object contains a table for listing the ONT Software version
		 files currently resident on the NT file system "
::= { eponOntSwGroup 2 }

eponOntSwVerInfoEntry OBJECT-TYPE
	SYNTAX 	EponOntSwVerInfoEntry
	ACCESS	not-accessible
	STATUS	mandatory
	DESCRIPTION
		"Rows of this table contain information about ONT SW version
		 files resident on the NT file system. "
	INDEX {eponOntSwVerInfoIndex }
::= {eponOntSwVerInfoTable 1}

EponOntSwVerInfoEntry ::=
	SEQUENCE { 
		eponOntSwVerInfoIndex		    INTEGER,
		eponOntSwVerInfoSwVersion	    DisplayString,
		eponOntSwVerInfoSwVersionSize 	INTEGER
		}

eponOntSwVerInfoIndex OBJECT-TYPE 
	SYNTAX INTEGER
	ACCESS not-accessible
	STATUS mandatory
	DESCRIPTION
	    "This object is the index to the eponOntSwVerInfoTable.
	     Range is 1 .. 250  "
::= { eponOntSwVerInfoEntry 1}

eponOntSwVerInfoSwVersion  OBJECT-TYPE
	SYNTAX 	DisplayString
	ACCESS	read-only
	STATUS	mandatory
	DESCRIPTION 
		" This attribute contains the ONT Software Version identifier.

		   If there are no ONT software version files on the NT system, or if the information
		   is unobtainable for any reason - then this attribute contains the null string. "
::= {eponOntSwVerInfoEntry 2}


eponOntSwVerInfoSwVersionSize	OBJECT-TYPE 
	SYNTAX 	INTEGER (0..4294967295)
	ACCESS	read-only
	STATUS	mandatory
	DESCRIPTION 
		" This attribute contains the ONT Software Version size (in bytes).

		   If there are no ONT software version files on the NT system, or if the information
		   is unobtainable for any reason - then this attribute contains the value 0. "
::= {eponOntSwVerInfoEntry 3}

-- *********************************************
-- EPON ONT SOFTWARE VERSION DELETE COMMAND SCALAR
--
-- This scalar is used to identify an ONT Software Version that manager wants deleted from
-- the NT file system
--
-- *********************************************

eponOntSwVerDeleteCmd OBJECT-TYPE
	SYNTAX 	DisplayString
	ACCESS	read-write
	STATUS	mandatory
	DESCRIPTION 
		" This attribute is used to specify an ONT Software Version that manager wants deleted.
		  from the NT file system.

		  Default = null string "
::= { eponOntSwGroup 3 }


-- *********************************************
-- EPON ONT SOFTWARE VERSION DELETE COMMAND STATUS SCALAR
--
-- This scalar is used to post the status of the last ONT Software Version
-- deletion command (i.e. the previous SET of eponOntSwVerDeleteCmd).
--
-- *********************************************

eponOntSwVerDeleteCmdStatus OBJECT-TYPE
	SYNTAX 	INTEGER
	ACCESS	read-only
	STATUS	mandatory
	DESCRIPTION 
		" This attribute is used to post the status of the last ONT Software Version
		  deletion command (i.e. the previous SET of eponOntSwVerDeleteCmd).

		  0 =  Command has never been issued (this is the DEFAULT)
		  1 =  In progress (agent will post this status until deletion request is determined to be 
		         successful or unsuccessful).
		  2 =  Success (file successfully deleted)
		  3 =  Failed (unable to delete file)

		  Default = 0  "
::= { eponOntSwGroup 4 }

END
