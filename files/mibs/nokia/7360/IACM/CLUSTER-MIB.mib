--  neClustering MIB
-- ============================================================================
--  This specification is published by Alcatel under Non-Disclosure
--  Agreement(s) (NDA) with specific parties and has to be considered as
--  Confidential Information as defined in such NDA.
--  Alcatel reserves the right to revise this document for any reason,
--  including but not limited to conformity with standards promulgated by
--  various agencies, utilization of advances in the state of the technical
--  areas, or the reflection of changes in the design of any equipment,
--  techniques, or procedures described or referred to herein.
--  The product specifications and other technical or performance information
--  contained herein are subject to change without notice.
--  Updates of this document will be issued under the above NDA's.
--  Alcatel makes no representation or warranty, expressed or implied, with
--  respect to the sufficiency, accuracy, or utility of any information or
--  opinion contained herein. Alcatel expressly advises that any use of for 
--  any purpose or reliance upon this technical reference is at the risk of
--  the user and that Alcatel shall not be liable for any damage or injury
--  incurred by any person arising out of the sufficiency, accuracy, or
--  utility of any information or opinion contained herein.
--  This document is not to be construed as a suggestion to any manufacturer
--  to modify or change any of its products, nor does this document represent
--  any commitment by Alcatel to sell or purchase any product.
--  Nothing contained herein shall be construed as conferring by implication,
--  estoppel, or otherwise any license or right under any patent, whether or
--  not the use of any information herein necessarily employs an invention of
--  any existing or later issued patent.
--  Alcatel reserves the right not to offer any or all of these products and
--  to withdraw any or all of them at any future time.
--  Copyright (C) 2003, Alcatel. All Rights Reserved.
-- ============================================================================

-- MODULE-IDENTITY
-- LAST-UPDATED "200408250000Z"
-- ORGANIZATION "Alcatel"
-- CONTACT-INFO 
--
--         Email: asam.mibsupport@alcatel.be
--
--
-- DESCRIPTION:
--    "This MIB Module defines Alcatel proprietary Cluster Management in iSAM."

-- ============================================================================
--
-- HISTORY:
--
-- Date: 17/05/06 - Version: 3FE24378EAAA_V3.2.0.0.0
-- Editor: Yingzhong Miao 
-- Comments: Add Alcatel Note for ISAM R3.2 OPEN SNMP

-- Date: 25/08/04 - Version: 3FE24378EAAA_V1.0.0.0.3
-- Editor: Yingzhong Miao 
-- Comments: first version produced for iSAM R2.3 
--
-- ============================================================================


CLUSTER-MIB DEFINITIONS ::= BEGIN

IMPORTS

    OBJECT-TYPE
        FROM RFC-1212
    Counter 
        FROM RFC1155-SMI
    asam
        FROM SYSTEM-MIB
    RowStatus, MacAddress
        FROM SNMPv2-TC
    ifIndex
        FROM ITF-MIB
    DisplayString
        FROM RFC1213-MIB
;
  
-- ============================================================================

-- Textual Conventions
-- ===================


neClustering OBJECT IDENTIFIER ::= { asam 53 }


-- ============================================================================
-- Cluster Management System Configuration
-- ============================================================================

clusterSystemConfig OBJECT IDENTIFIER ::= { neClustering 1 }
 
clusterName OBJECT-TYPE
     SYNTAX  DisplayString (SIZE (0..255))
     ACCESS  read-write
     STATUS  mandatory
     DESCRIPTION
        "This object contains name of cluster which the NE joins. The
        length is restricted to 64 bytes. Value NULL indicates that no
        unassigned cluster name for this NE. 
        ALCATEL NOTE:
            ACCESS:      NA           USAGE:       NA
            PERSIST:     YES          INSRVMOD:    YES
            RANGE:       NA           DEFVALUE:    NULL
            UNITS:       NA           SPARSE:      NA
            DESCR:       NA"
     DEFVAL { "" }
     ::= { clusterSystemConfig 1 }


clusterRole OBJECT-TYPE
     SYNTAX  INTEGER
        {
          command(1),
          member(2),
          backup(3),
          candidate(16)            
        }  
     ACCESS  read-write
     STATUS  mandatory
     DESCRIPTION
        "This object contains the role of the NE.
        ALCATEL NOTE:
            ACCESS:      NA           USAGE:       NA
            PERSIST:     YES          INSRVMOD:    YES
            RANGE:       NA           DEFVALUE:    candidate
            UNITS:       NA           SPARSE:      NA
            DESCR:       NA"
     DEFVAL { candidate }
     ::= { clusterSystemConfig 2 }


-- ============================================================================
-- Neighbour Discovery Configuration
-- ============================================================================

neighbourDiscoveryConfig OBJECT IDENTIFIER ::= { neClustering 2 }
 
neighbourDiscoverySystemMode OBJECT-TYPE
     SYNTAX INTEGER
       {
         enable(1),
         disable(2)
       }
     ACCESS  read-write
     STATUS  mandatory
     DESCRIPTION
        "The neighbour discovery function can be enabled or disabled.
        ALCATEL NOTE:
            ACCESS:      NA           USAGE:       NA
            PERSIST:     YES          INSRVMOD:    YES
            RANGE:       NA           DEFVALUE:    enable
            UNITS:       NA           SPARSE:      NA
            DESCR:       NA"
     DEFVAL { enable }
     ::= { neighbourDiscoveryConfig 1 }

neighbourDiscoveryInterval OBJECT-TYPE
     SYNTAX INTEGER (1..2147483647)
     ACCESS  read-write
     STATUS  mandatory
     DESCRIPTION
        "The object contains the interval to send the neighbour discovery 
         packet to neighbour devices in terms of second.
         ALCATEL NOTE:
             ACCESS:      NA           USAGE:       NA
             PERSIST:     YES          INSRVMOD:    YES
             RANGE:       NA           DEFVALUE:    60
             UNITS:       seconds      SPARSE:      NA
             DESCR:       NA"
     DEFVAL { 60 }
     ::= { neighbourDiscoveryConfig 2 }


neighbourDiscoveryHoldTime OBJECT-TYPE
     SYNTAX INTEGER  (1.. 255)
     ACCESS  read-write
     STATUS  mandatory
     DESCRIPTION
        "The object contains the time filled in neighbour discovery 
        packet (TTL field). The receipt of the neighbour discovery
        packet shall discard the packet after the aging time in terms
        of second.
        ALCATEL NOTE:
            ACCESS:      NA           USAGE:       NA
            PERSIST:     YES          INSRVMOD:    YES
            RANGE:       NA           DEFVALUE:    180
            UNITS:       seconds      SPARSE:      NA
            DESCR:       NA"
     DEFVAL { 180 }
     ::= { neighbourDiscoveryConfig 3 }


-- ============================================================================
-- Topology Collection Configuration
-- ============================================================================

topologyCollectionConfig OBJECT IDENTIFIER ::= { neClustering 3 }
 
topologyCollectionSystemMode OBJECT-TYPE
     SYNTAX INTEGER
       {
         enable(1),
         disable(2)
       }
     ACCESS  read-write
     STATUS  mandatory
     DESCRIPTION
        "The topology collection function can be enabled or disabled.
        ALCATEL NOTE:
            ACCESS:      NA           USAGE:       NA
            PERSIST:     YES          INSRVMOD:    YES 
            RANGE:       NA           DEFVALUE:    enable
            UNITS:       NA           SPARSE:      NA
            DESCR:       NA"
     DEFVAL { enable }
     ::= { topologyCollectionConfig 1 }

topologyCollectionHopDelay OBJECT-TYPE
     SYNTAX INTEGER (1.. 65535)
     ACCESS  read-write
     STATUS  mandatory
     DESCRIPTION
        "The object contains the duration for receipt between receiving
        of topology request packet and forwarding on its first port in 
        terms of millisecond.
        ALCATEL NOTE:
            ACCESS:    NA             USAGE:       NA
            PERSIST:   YES            INSRVMOD:    YES
            RANGE:     NA             DEFVALUE:    200
            UNITS:     milliseconds   SPARSE:      NA
            DESCR:    NA"
     DEFVAL { 200 }
     ::= { topologyCollectionConfig 2 }


topologyCollectionPortDelay OBJECT-TYPE
     SYNTAX INTEGER (1.. 65535)
     ACCESS  read-write
     STATUS  mandatory
     DESCRIPTION
        "The object contains the duration for receipt of topology request 
        packet to forward on its adjacent ports in terms of millisecond.
        ALCATEL NOTE:
           ACCESS:    NA                USAGE:       NA
           PERSIST:   YES               INSRVMOD:    YES
           RANGE:     NA                DEFVALUE:    20
           UNITS:     milliseconds      SPARSE:      NA
           DESCR:    NA"
     DEFVAL { 20 }
     ::= { topologyCollectionConfig 3 }

topologyCollectionScope OBJECT-TYPE
     SYNTAX INTEGER (1..10)
     ACCESS  read-write
     STATUS  mandatory
     DESCRIPTION
        "The object contains the scope of topology collection in terms of
        hop number which the topology request packet go through.
        ALCATEL NOTE:
            ACCESS:      NA              USAGE:       NA
            PERSIST:     YES             INSRVMOD:    YES
            RANGE:       NA              DEFVALUE:    3
            UNITS:       hop number      SPARSE:      NA
            DESCR:       NA"
     DEFVAL { 3 }
     ::= { topologyCollectionConfig 4 }


topologyCollectionInterval OBJECT-TYPE
     SYNTAX INTEGER (0.. 2147483647)
     ACCESS  read-write
     STATUS  mandatory
     DESCRIPTION
        "The object contains the interval to send topology request packet in terms of second.
        ALCATEL NOTE:
            ACCESS:      NA           USAGE:       NA
            PERSIST:     YES          INSRVMOD:    YES
            RANGE:       NA           DEFVALUE:    0
            UNITS:       seconds      SPARSE:      NA
            DESCR:       NA"
     DEFVAL { 0 }
     ::= { topologyCollectionConfig 5 }


topologyCollectionManualMode OBJECT-TYPE
     SYNTAX INTEGER
       {
         enable(1),
         disable(2)        
       }
     ACCESS  read-write
     STATUS  mandatory
     DESCRIPTION
        "The topology collection is able to be triggered manually.
        ALCATEL NOTE:
            ACCESS:      NA           USAGE:       NA
            PERSIST:     NO           INSRVMOD:    YES
            RANGE:       NA           DEFVALUE:    disable
            UNITS:       NA           SPARSE:      NA
            DESCR:      NA"
     DEFVAL { disable }
     ::= { topologyCollectionConfig 6 }


-- ============================================================================
-- Cluster port Configuration
-- ============================================================================

clusterPort OBJECT IDENTIFIER ::= { neClustering 4 }
	
 
clusterManagementPortTable OBJECT-TYPE
     SYNTAX  SEQUENCE OF ClusterManagementPortEntry
     ACCESS  not-accessible
     STATUS  mandatory
     DESCRIPTION
        "This table contains information on cluster management function 
        parameters. 
        ALCATEL NOTE:
            TABLESIZE: DEP (logical port number)
            DESCR: NA"
     ::= { clusterPort 1 }

clusterManagementPortEntry OBJECT-TYPE
    SYNTAX  ClusterManagementPortEntry
    ACCESS  not-accessible
    STATUS  mandatory
    DESCRIPTION
           "This list contains information on cluster port parameters."
    INDEX   { ifIndex }
    ::= { clusterManagementPortTable  1 }

ClusterManagementPortEntry ::=
     SEQUENCE {
        neighbourDiscoveryPortMode        INTEGER,
        topologyCollectionPortMode        INTEGER,
        portModeRowStatus                 RowStatus
     }

neighbourDiscoveryPortMode OBJECT-TYPE
     SYNTAX  INTEGER
        {
         enable(1),
         disable(2)        
        }
     ACCESS  read-write
     STATUS  mandatory
     DESCRIPTION
        "The neighbour discovery function can be enable or disable on the
        port.
        ALCATEL NOTE:
            ACCESS:      NA           USAGE:       MAND
            PERSIST:     YES          INSRVMOD:    YES
            RANGE:       NA           DEFVALUE:    enable
            UNITS:       NA           SPARSE:      NA
            DESCR:      NA"
     DEFVAL { enable }
     ::= { clusterManagementPortEntry 1}

topologyCollectionPortMode OBJECT-TYPE
     SYNTAX  INTEGER
         {
         enable(1),
         disable(2)        
         }
     ACCESS  read-write
     STATUS  mandatory
     DESCRIPTION
        "The topology collection function can be enable or disable on the
        port.
        ALCATEL NOTE:
            ACCESS:      NA           USAGE:       MAND
            PERSIST:     YES          INSRVMOD:    YES
            RANGE:       NA           DEFVALUE:    enable
            UNITS:       NA           SPARSE:      NA
            DESCR:      NA"
     DEFVAL { enable }
     ::= { clusterManagementPortEntry 2}


portModeRowStatus OBJECT-TYPE
     SYNTAX  RowStatus
     ACCESS  read-write
     STATUS  mandatory
     DESCRIPTION
        "The object is used to create a new row or modify or delete an existing 
        row in this table, i.e. active(1), createAdGo(4) and destroy(6) shall be supported.
        ALCATEL NOTE:
            ACCESS:      NA           USAGE:       NA
            PERSIST:     YES          INSRVMOD:    YES
            RANGE:       1,4,6        DEFVALUE:    NA
            UNITS:       NA           SPARSE:      NA
            DESCR:      NA"
     ::= { clusterManagementPortEntry 3} 


-- ============================================================================
-- Cluster port PM
-- ============================================================================


clusterManagementPortCounterTable OBJECT-TYPE
     SYNTAX  SEQUENCE OF ClusterManagementPortCounterEntry
     ACCESS  not-accessible
     STATUS  mandatory
     DESCRIPTION
        "This table contains counter on cluster management traffic. 
        ALCATEL NOTE:
            TABLESIZE: DEP (logical port number)
            DESCR: NA"
     ::= { clusterPort 2 }

clusterManagementPortCounterEntry OBJECT-TYPE
    SYNTAX  ClusterManagementPortCounterEntry
    ACCESS  not-accessible
    STATUS  mandatory
    DESCRIPTION
       "This list contains information on counters per cluster 
       port with its ifIndex/port number as the index."
    INDEX   { ifIndex }
    ::= { clusterManagementPortCounterTable  1 }

ClusterManagementPortCounterEntry ::=
     SEQUENCE {
        neighbourDiscoveryPortInTotal         Counter,
        neighbourDiscoveryPortOutTotal        Counter,
        neighbourDiscoveryPortDiscard         Counter,
        topologyRequestPortInTotal            Counter,
        topologyRequestPortOutTotal           Counter,
        topologyRequestPortLoopDiscard        Counter,
        topologyRequestPortIndexDiscard       Counter,
        topologyRequestPortOtherDiscard       Counter,
        topologyResponsePortInTotal           Counter,
        topologyResponsePortOutTotal          Counter,
        topologyResponsePortDiscard           Counter,
        counterReset                          INTEGER
     }

neighbourDiscoveryPortInTotal OBJECT-TYPE
     SYNTAX  Counter
     ACCESS  read-only
     STATUS  mandatory
     DESCRIPTION
        "The number of received neighbour discovery packets on the
        port.
        ALCATEL NOTE:
            ACCESS:      NA           USAGE:       NA
            PERSIST:     NO           INSRVMOD:    NA
            RANGE:       NA           DEFVALUE:    0
            UNITS:       packets      SPARSE:      NA
            DESCR:       NA"
    ::= { clusterManagementPortCounterEntry 1}

neighbourDiscoveryPortOutTotal OBJECT-TYPE
     SYNTAX  Counter
     ACCESS  read-only
     STATUS  mandatory
     DESCRIPTION
        "The number of transmitted neighbour discovery packets on the
        port.
        ALCATEL NOTE:
            ACCESS:      NA           USAGE:       NA
            PERSIST:     NO           INSRVMOD:    NA
            RANGE:       NA           DEFVALUE:    0
            UNITS:       packets      SPARSE:      NA
            DESCR:       NA"
     ::= { clusterManagementPortCounterEntry 2}

neighbourDiscoveryPortDiscard OBJECT-TYPE
     SYNTAX  Counter
     ACCESS  read-only
     STATUS  mandatory
     DESCRIPTION
        "The number of discarded neighbour discovery packets due to invalid
        packets on the port.
        ALCATEL NOTE:
            ACCESS:      NA           USAGE:       NA
            PERSIST:     NO           INSRVMOD:    NA
            RANGE:       NA           DEFVALUE:    0
            UNITS:       packets      SPARSE:      NA
            DESCR:       NA"
    ::= { clusterManagementPortCounterEntry 3}

topologyRequestPortInTotal OBJECT-TYPE
     SYNTAX  Counter
     ACCESS  read-only
     STATUS  mandatory
     DESCRIPTION
        "The number of received topology request packets on the
        port.
        ALCATEL NOTE:
            ACCESS:      NA           USAGE:       NA
            PERSIST:     NO           INSRVMOD:    NA
            RANGE:       NA           DEFVALUE:    0
            UNITS:       packets      SPARSE:      NA
            DESCR:       NA"
    ::= { clusterManagementPortCounterEntry 4}

topologyRequestPortOutTotal OBJECT-TYPE
     SYNTAX  Counter
     ACCESS  read-only
     STATUS  mandatory
     DESCRIPTION
        "The number of transmitted topology request packets on the
        port.
        ALCATEL NOTE:
            ACCESS:      NA           USAGE:       NA
            PERSIST:     NO           INSRVMOD:    NA
            RANGE:       NA           DEFVALUE:    0
            UNITS:       packets      SPARSE:      NA
            DESCR:       NA"
    ::= { clusterManagementPortCounterEntry 5}

topologyRequestPortLoopDiscard OBJECT-TYPE
     SYNTAX  Counter
     ACCESS  read-only
     STATUS  mandatory
     DESCRIPTION
        "The number of discarded topology request packets due to loop
        on the port.
        ALCATEL NOTE:
            ACCESS:      NA           USAGE:       NA
            PERSIST:     NO           INSRVMOD:    NA
            RANGE:       NA           DEFVALUE:    0
            UNITS:       packets      SPARSE:      NA
            DESCR:       NA"
    ::= { clusterManagementPortCounterEntry 6}

topologyRequestPortIndexDiscard OBJECT-TYPE
     SYNTAX  Counter
     ACCESS  read-only
     STATUS  mandatory
     DESCRIPTION
        "The number of discarded duplicate topology request packets 
        on the port.
        ALCATEL NOTE:
            ACCESS:      NA           USAGE:       NA
            PERSIST:     NO           INSRVMOD:    NA
            RANGE:       NA           DEFVALUE:    0
            UNITS:       packets      SPARSE:      NA
            DESCR:       NA"
     ::= { clusterManagementPortCounterEntry 7}

topologyRequestPortOtherDiscard OBJECT-TYPE
     SYNTAX  Counter
     ACCESS  read-only
     STATUS  mandatory
     DESCRIPTION
        "The number of discarded topology request packets due to error checksum, version etc. on the port.
        ALCATEL NOTE:
            ACCESS:      NA           USAGE:       NA
            PERSIST:     NO           INSRVMOD:    NA
            RANGE:       NA           DEFVALUE:    0
            UNITS:       packets      SPARSE:      NA
            DESCR:       NA"
     ::= { clusterManagementPortCounterEntry 8}

topologyResponsePortInTotal OBJECT-TYPE
     SYNTAX  Counter
     ACCESS  read-only
     STATUS  mandatory
     DESCRIPTION
        "The number of received topology response packets on the
        port.
        ALCATEL NOTE:
            ACCESS:      NA           USAGE:       NA
            PERSIST:     NO           INSRVMOD:    NA
            RANGE:       NA           DEFVALUE:    0
            UNITS:       packets      SPARSE:      NA
            DESCR:       NA"
    ::= { clusterManagementPortCounterEntry 9}

topologyResponsePortOutTotal OBJECT-TYPE
     SYNTAX  Counter
     ACCESS  read-only
     STATUS  mandatory
     DESCRIPTION
        "The number of transmitted topology response packets on the
        port.
        ALCATEL NOTE:
            ACCESS:      NA           USAGE:       NA
            PERSIST:     NO           INSRVMOD:    NA
            RANGE:       NA           DEFVALUE:    0
            UNITS:       packets      SPARSE:      NA
            DESCR:       NA"
     ::= { clusterManagementPortCounterEntry 10}

topologyResponsePortDiscard OBJECT-TYPE
     SYNTAX  Counter
     ACCESS  read-only
     STATUS  mandatory
     DESCRIPTION
        "The number of discarded topology response packets on the port.
        ALCATEL NOTE:
            ACCESS:      NA           USAGE:       NA
            PERSIST:     NO           INSRVMOD:    NA
            RANGE:       NA           DEFVALUE:    0
            UNITS:       packets      SPARSE:      NA
            DESCR:       NA"
     ::= { clusterManagementPortCounterEntry 11}

counterReset OBJECT-TYPE
    SYNTAX  INTEGER
     {
         reset(1),
         hold(2)
     }
    ACCESS  read-write
    STATUS  mandatory
    DESCRIPTION
       "The flag to reset all counters on the port.
       ALCATEL NOTE:
           ACCESS:      NA           USAGE:       NA
           PERSIST:     NO           INSRVMOD:    NA
           RANGE:       NA           DEFVALUE:    NA
           UNITS:       NA           SPARSE:      NA
           DESCR:       NA"
    ::= { clusterManagementPortCounterEntry 12}

-- ============================================================================
-- Neighbour information
-- ============================================================================

neighbourInfor OBJECT IDENTIFIER ::= { neClustering 5 }
	
 
neighbourDeviceTable OBJECT-TYPE
     SYNTAX  SEQUENCE OF NeighbourDeviceEntry
     ACCESS  not-accessible
     STATUS  mandatory
     DESCRIPTION
        "This table contains information of neighbour node.
        ALCATEL NOTE:
            TABLESIZE: DEP (logical port number)
            DESCR: NA"
     ::= { neighbourInfor 1 }

neighbourDeviceEntry OBJECT-TYPE
    SYNTAX  NeighbourDeviceEntry
    ACCESS  not-accessible
    STATUS  mandatory
    DESCRIPTION
       "This list contains information on neighbour node with the ifIndex/port number of port as the index."
    INDEX   { ifIndex }
    ::= { neighbourDeviceTable  1 }

NeighbourDeviceEntry ::=
     SEQUENCE {
        neighbourDeviceID                      MacAddress,
        neighbourPortID                        INTEGER,
        neighbourHostName                      DisplayString,
        neighbourSystemDescription             DisplayString,
        neighbourPortSTPState		             INTEGER
     }

neighbourDeviceID OBJECT-TYPE
     SYNTAX  MacAddress
     ACCESS  read-only
     STATUS  mandatory
     DESCRIPTION
        "The neighbour device ID on the port. The device ID is the MAC address
        of the neighbour node.
        ALCATEL NOTE:
            ACCESS:      NA           USAGE:       NA
            PERSIST:     NO           INSRVMOD:    NA
            RANGE:       NA           DEFVALUE:    NA
            UNITS:       NA           SPARSE:      NA
            DESCR:       NA"
     ::= { neighbourDeviceEntry 1}


neighbourPortID OBJECT-TYPE
     SYNTAX  INTEGER (1..65535)
     ACCESS  read-only
     STATUS  mandatory
     DESCRIPTION
        "The port identifier of neighbour node connected on the port. The port ID
        is the port number of the port.
        ALCATEL NOTE:
            ACCESS:      NA           USAGE:       NA
            PERSIST:     NO           INSRVMOD:    NA
            RANGE:       NA           DEFVALUE:    NA
            UNITS:       NA           SPARSE:      NA
            DESCR:       NA"
     ::= { neighbourDeviceEntry 2}

neighbourHostName OBJECT-TYPE
     SYNTAX   DisplayString (SIZE (0..255))
     ACCESS  read-only
     STATUS  mandatory
     DESCRIPTION
        "The host name of neighbour node on the port.
        ALCATEL NOTE:
            ACCESS:      NA           USAGE:       NA
            PERSIST:     NO           INSRVMOD:    NA
            RANGE:       NA           DEFVALUE:    NA
            UNITS:       NA           SPARSE:      NA
            DESCR:       NA"
     ::= { neighbourDeviceEntry 3}

neighbourSystemDescription OBJECT-TYPE
     SYNTAX   DisplayString (SIZE (0..255))
     ACCESS  read-only
     STATUS  mandatory
     DESCRIPTION
        "The system description of neighbour node on the port.
        ALCATEL NOTE:
            ACCESS:      NA           USAGE:       NA
            PERSIST:     NO           INSRVMOD:    NA
            RANGE:       NA           DEFVALUE:    NA
            UNITS:       NA           SPARSE:      NA
            DESCR:       NA"
     ::= { neighbourDeviceEntry 4}

neighbourPortSTPState OBJECT-TYPE
     SYNTAX  INTEGER
        {
         disabled(1),
         blocking(2),
         listening(3),
         learning(4),
         forwarding(5),
         broken(6)
         }
     ACCESS  read-only
     STATUS  mandatory
     DESCRIPTION
        "The port's current state as defined by application of the 
        Spanning Tree Protocol. 
        ALCATEL NOTE:
            ACCESS:      NA           USAGE:       NA
            PERSIST:     NO           INSRVMOD:    NA
            RANGE:       NA           DEFVALUE:    NA
            UNITS:       NA           SPARSE:      NA
            DESCR:       NA"
     ::= { neighbourDeviceEntry 5}

-- ============================================================================
-- Topology Device information
-- ============================================================================

topologyInfor OBJECT IDENTIFIER ::= { neClustering 6 }

topologyDeviceTable OBJECT-TYPE
     SYNTAX  SEQUENCE OF TopologyDeviceEntry
     ACCESS  not-accessible
     STATUS  mandatory
     DESCRIPTION
        "This table contains information of nodes within the connected
        environment in which the command node is.
        ALCATEL NOTE:
            TABLESIZE: NA
            DESCR: NA"
     ::= { topologyInfor 1 }

topologyDeviceEntry OBJECT-TYPE
    SYNTAX  TopologyDeviceEntry
    ACCESS  not-accessible
    STATUS  mandatory
    DESCRIPTION
           "This list contains information on connected node."
    INDEX   { topologyDeviceID }
    ::= { topologyDeviceTable  1 }

TopologyDeviceEntry ::=
     SEQUENCE {
        topologyDeviceID                  MacAddress,
        topologyHostName                  DisplayString,
        topologySystemDescription         DisplayString,
        topologyClusterName               DisplayString,
        topologyClusterRole               INTEGER
     }

topologyDeviceID OBJECT-TYPE
     SYNTAX  MacAddress
     ACCESS  read-only
     STATUS  mandatory
     DESCRIPTION
        "The device ID i.e. MAC address of connected node.
        ALCATEL NOTE:
            ACCESS:      NA           USAGE:       NA
            PERSIST:     NO           INSRVMOD:    NA
            RANGE:       NA           DEFVALUE:    NA
            UNITS:       NA           SPARSE:      NA
            DESCR:       NA"
     ::= { topologyDeviceEntry 1}

topologyHostName OBJECT-TYPE
     SYNTAX  DisplayString (SIZE (0..255))
     ACCESS  read-only
     STATUS  mandatory
     DESCRIPTION
        "The host name and management IP address of connected node formatted
        as hostname@ipaddress, in which IP address is coded as Decimal Dotted
        Notation.
        ALCATEL NOTE:
            ACCESS:      NA           USAGE:       NA
            PERSIST:     NO           INSRVMOD:    NA
            RANGE:       NA           DEFVALUE:    NA
            UNITS:       NA           SPARSE:      NA
            DESCR:       NA"
    ::= { topologyDeviceEntry 2}

topologySystemDescription OBJECT-TYPE
     SYNTAX   DisplayString (SIZE (0..255))
     ACCESS  read-only
     STATUS  mandatory
     DESCRIPTION
        "The system description of connected node.
        ALCATEL NOTE:
            ACCESS:      NA           USAGE:       NA
            PERSIST:     NO           INSRVMOD:    NA
            RANGE:       NA           DEFVALUE:    NA
            UNITS:       NA           SPARSE:      NA
            DESCR:       NA"
    ::= { topologyDeviceEntry 3}

topologyClusterName OBJECT-TYPE
     SYNTAX   DisplayString (SIZE (0..255))
     ACCESS  read-only
     STATUS  mandatory
     DESCRIPTION
        "The cluster name of connected node.
        ALCATEL NOTE:
            ACCESS:      NA           USAGE:       NA
            PERSIST:     NO           INSRVMOD:    NA
            RANGE:       NA           DEFVALUE:    NA
            UNITS:       NA           SPARSE:      NA
            DESCR:       NA"
     ::= { topologyDeviceEntry 4}

topologyClusterRole OBJECT-TYPE
     SYNTAX  INTEGER 
        {
          command(1),
          member(2),
          backup(3),
          candidate(16)            
        }
     ACCESS  read-only
     STATUS  mandatory
     DESCRIPTION
        "The role of connected node.
        ALCATEL NOTE:
            ACCESS:      NA           USAGE:       NA
            PERSIST:     NO           INSRVMOD:    NA
            RANGE:       NA           DEFVALUE:    NA
            UNITS:       NA           SPARSE:      NA
            DESCR:       NA"
     ::= { topologyDeviceEntry 5}



-- ============================================================================
-- Topology Connection information
-- ============================================================================


topologyConnectTable OBJECT-TYPE
     SYNTAX  SEQUENCE OF TopologyConnectEntry
     ACCESS  not-accessible
     STATUS  mandatory
     DESCRIPTION
        "This table contains connected information of nodes within 
        the connected environment in which the command node is.
        ALCATEL NOTE:
            TABLESIZE: NA
            DESCR: NA"
     ::= { topologyInfor 2 }

topologyConnectEntry OBJECT-TYPE
    SYNTAX  TopologyConnectEntry
    ACCESS  not-accessible
    STATUS  mandatory
    DESCRIPTION
       "This list contains connected information between nodes."
    INDEX   { nativeDeviceID, nativePortID }
    ::= { topologyConnectTable  1 }

TopologyConnectEntry ::=
     SEQUENCE {
        nativeDeviceID                MacAddress,
        nativePortID                  INTEGER,
        peerDeviceID                  MacAddress,
        peerPortID                    INTEGER,
        portSTPstate                  INTEGER
     }

nativeDeviceID OBJECT-TYPE
     SYNTAX  MacAddress
     ACCESS  read-only
     STATUS  mandatory
     DESCRIPTION
        "The device ID i.e. the MAC address of native node.
        ALCATEL NOTE:
            ACCESS:      NA           USAGE:       NA
            PERSIST:     NO           INSRVMOD:    NA
            RANGE:       NA           DEFVALUE:    NA
            UNITS:       NA           SPARSE:      NA
            DESCR:       NA"
    ::= { topologyConnectEntry 1}

nativePortID OBJECT-TYPE
     SYNTAX  INTEGER (1..65535)
     ACCESS  read-only
     STATUS  mandatory
     DESCRIPTION
        "The port ID i.e. the port number of the port of native node.
        ALCATEL NOTE:
            ACCESS:      NA           USAGE:       NA
            PERSIST:     NO           INSRVMOD:    NA
            RANGE:       NA           DEFVALUE:    NA
            UNITS:       NA           SPARSE:      NA
            DESCR:       NA"
     ::= { topologyConnectEntry 2}

peerDeviceID OBJECT-TYPE
     SYNTAX  MacAddress
     ACCESS  read-only
     STATUS  mandatory
     DESCRIPTION
        "The device ID i.e. the MAC address of connected node with the native 
        node.
        ALCATEL NOTE:
         ACCESS:      NA           USAGE:       NA
         PERSIST:     NO           INSRVMOD:    NA
         RANGE:       NA           DEFVALUE:    NA
         UNITS:       NA           SPARSE:      NA
         DESCR:       NA"
     ::= { topologyConnectEntry 3}

peerPortID OBJECT-TYPE
     SYNTAX  INTEGER (1..65535)
     ACCESS  read-only
     STATUS  mandatory
     DESCRIPTION
        "The port id i.e. the port number of the port of connected node with the 
        native node.
        ALCATEL NOTE:
            ACCESS:      NA           USAGE:       NA
            PERSIST:     NO           INSRVMOD:    NA
            RANGE:       NA           DEFVALUE:    NA
            UNITS:       NA           SPARSE:      NA
            DESCR:       NA"
    ::= { topologyConnectEntry 4}

portSTPstate OBJECT-TYPE
     SYNTAX  INTEGER
      {
        disabled(1),
        blocking(2),
        listening(3),
        learning(4),
        forwarding(5),
        broken(6)
      }
     ACCESS  read-only
     STATUS  mandatory
     DESCRIPTION
        "The STP state of port.
        ALCATEL NOTE:
            ACCESS:      NA           USAGE:       NA
            PERSIST:     NO           INSRVMOD:    NA
            RANGE:       NA           DEFVALUE:    NA
            UNITS:       NA           SPARSE:      NA
            DESCR:       NA"
     ::= { topologyConnectEntry 5}


-- ============================================================================
-- Topology Change Counter
-- ============================================================================

topologyCounter OBJECT IDENTIFIER ::= { neClustering 7 }
 
topologyNumberOfChanges OBJECT-TYPE
     SYNTAX Counter       
     ACCESS  read-only
     STATUS  mandatory
     DESCRIPTION
        "Wrap around counter which indicates the number of sent Traps,
        i.e. the number of topology changed. This counter is incremented
        each time the topology changed Trap is sent to EMS.
        ALCATEL NOTE:
            ACCESS:      NA           USAGE:       NA 
            PERSIST:     NO           INSRVMOD:    NA
            RANGE:       NA           DEFVALUE:    NA
            UNITS:       NA           SPARSE:      NA
            DESCR:       NA"
     ::= { topologyCounter 1 }



END
