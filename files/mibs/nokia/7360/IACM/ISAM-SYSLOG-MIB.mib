-- SYSLOG MIB
-- =====================================================================
-- This specification is published by Alcatel Sbell under Non-Disclosure
-- Agreement(s) (NDA) with specific parties and has to be considered as
-- Confidential Information as defined in such NDA. Alcatel Sbell reserves
-- the right to revise this document for any reason, including but
-- notlimited to conformity with standards promulgated by various agencies,
-- utilisation of advances in the state of the technical areas, or
-- thereflection of changes in the design of any equipment, techniques, or
-- procedures described or referred to herein. The product specifications
-- and other technical or performance information contained herein are
-- subject to change without notice. Updates of this document will be
-- issued under the above NDA's.
-- Alcatel Sbell makes no representation or warranty, expressed or implied,
-- with respect to the sufficiency, accuracy, or utility of any information
-- or opinion contained herein. Alcatel Sbell expressly advises that any
-- use of for any purpose or reliance upon this technical reference is at
-- the risk of the user and that Alcatel Sbell shall not be liable for any
-- damage or injury incurred by any person arising out of the sufficiency,
-- accuracy, or utility of any information or opinion contained herein.
-- This document is not to be construed as a suggestion to any manufacturer
-- to modify or change any of its products, nor does this document
-- represent any commitment by Alcatel Sbell to sell or purchase any
-- product. Nothing contained herein shall be construed as conferring by
-- implication, estoppel, or otherwise any license or right under any
-- patent, whether or not the use of any information herein necessarily
-- employs an invention of any existing or later issued patent.
-- Alcatel Sbell reserves the right not to offer any or all of these
-- products and to withdraw any or all of them at any future time.
-- Copyright (C) 2006, Alcatel Sbell. All Rights Reserved.
-- =====================================================================


-- MODULE IDENTITY
-- ORGANIZATION "Alcatel"
-- CONTACT-INFO "email:asam.mibsupport@alcatel.be"
--
-- REVISION "201010121200Z"
-- ORIGINATOR "Kevin Mather"
-- DESCRIPTION
-- Update the SYSLOG MIB to incorporate support for OMCI events
--  per RCR ALU00747313
--
-- REVISION "201005211200Z"
-- ORIGINATOR "Kris Van Bos and Tom Batsele"
-- DESCRIPTION
-- Update the SYSLOG MIB to incorporate support for Lawful intercept
--  feature as per RCR ALU00124460
--
-- REVISION "200910021200Z"
-- ORIGINATOR "M. Todd"
-- DESCRIPTION
-- Update the SYSLOG MIB to incorporate support for FTTU features per RCR 
--  BDFam52637
--
-- REVISION "200611171200Z"
-- ORIGINATOR "Kris Van Bos and Kaini Miao"
-- DESCRIPTION
-- The SYSLOG MIB allows to manage the System Security Log application in
-- iSAM. This is a centralized application for logging event notification
-- messages generated by subsystems.

--=========================================================================
-- HISTORY:
--
-- date: 12 October 2010
-- version: Updates for OMCI events logging
-- editor: Kevin Mather
-- Produced for Alcatel ISAM R4.2.02
--
-- ========================================================================

--=========================================================================
-- HISTORY:
--
-- date: 21 May 2010
-- version: Updates for Lawful intercepd feature
-- editor: Kris Van Bos
-- Produced for Alcatel ISAM R4.2
--
-- ========================================================================

--=========================================================================
-- HISTORY:
--
-- date: 02 Oct 2009
-- version: Updates for FTTU features
-- editor: M. Todd
-- Produced for Alcatel ISAM R4.0.10
--
-- ========================================================================

--=========================================================================
-- HISTORY:
--
-- date: 17 Nov 2006
-- version: First Version
-- editor: Kris Van Bos and Kaini Miao
-- Produced for Alcatel ISAM R3.3
--
-- ========================================================================

ISAM-SYSLOG-MIB DEFINITIONS ::= BEGIN

IMPORTS
OBJECT-TYPE
                FROM RFC-1212
DisplayString
                        FROM RFC1213-MIB
asam
                    FROM SYSTEM-MIB
IpAddress
                        FROM RFC1155-SMI

DisplayString
                    FROM RFC1213-MIB
RowStatus
                    FROM SNMPv2-TC

AsamProfileName
                FROM ASAM-TC-MIB;


isamSyslog              OBJECT IDENTIFIER ::= {asam 62}


IsamSyslogSeverityType ::= OCTET STRING (SIZE (4))


IsamSyslogServerIndexType ::= INTEGER(1..64)


IsamSyslogServerIndexPointerType ::= INTEGER(1..64)


IsamSyslogServerType ::= INTEGER {
           file(1),                     -- local logging
           udp(2),                      -- remote logging
           all-cli(3),                  -- user CLI users terminal logging
           all-tl1(4),                  -- user TL1 users terminal logging
           cli-user (5),                -- for a particular CLI user 
                                        -- Not supported in this release
           cli-profile(6),              -- for a cli group 
                                        -- Not supported in this release
           tl1-user(7),                 -- for a tl1 user
           all-users(8),                -- all CLI and TL1 users
           trace (9)                    -- to the trace shell   
                                        -- Not supported in this release
}

IsamSysLogModeType ::= INTEGER {
       enabled(1),
       disabled(2)
}

IsamSyslogMessageType ::= INTEGER {
       all(1),
       authActions (2),    -- Authentication Actions
       cliConfigChgs (3),  -- ClI configuration changes
       tl1ConfigChgs (4),  -- TL1 configuration changes
       cliMsgs (5),        -- ClI Messages
       tl1Msgs (6),         -- TL1 Messages
       tracing1 (7),       -- Protocol Tracing messages1
       tracing2 (8),       -- Protocol Tracing messages2
       tracing3 (9),       -- Protocol Tracing messages3
       videoCDR (10),       -- Video CDR messages
       reservedIpsecMsg (11),       -- UNUSED in ISAM IPsec security logs – reserved to keep enum spacing 
       eqpt     (12),       -- Use for eqpt event, e.g. protection switch
       liConfigChgs (13),   -- Lawful Intercept configuration changes
       omciEvents(14),      -- OMCI events
       docsisEvents(15)     -- core23 docsis events
}

IsamSyslogFacility ::= INTEGER {
           kern (0),  
           user (1),  
           mail (2),  
           daemon (3),
           auth (4),  
           syslog (5),
           pr (6),    
           news (7),  
           uucp (8),  
           cron (15), 
           local0 (16),
           local1 (17),
           local2 (18),
           local3 (19),
           local4 (20),
           local5 (21),
           local6 (22),
           local7 (23) 
}

--========================================================================
--                           SCALARS FOR SYSLOG                          |
--========================================================================

isamSyslogGetFreeIndex OBJECT-TYPE
   SYNTAX  INTEGER 
   ACCESS  read-only
   STATUS  mandatory
   DESCRIPTION
        "This value of this MIB object is the next available free syslog
         server Index, using which a manager can create new row in 
         isamSyslogServerTable.If the number of servers exceeds the limit,
         this object returns a value of zero.

   ALCATEL NOTE:
             SUPPORT: YES   INSRVMOD: NA                 RANGE: See above
             PERSIST: NO    DEFVALUE: NA                 UNITS: NA"

   ::= { isamSyslog 1 }


isamSyslogMaxMsgSize OBJECT-TYPE
SYNTAX  INTEGER
ACCESS  read-only
STATUS  mandatory
  DESCRIPTION
       "This value of this object is the maximum size of a syslog message.

  ALCATEL NOTE:
             SUPPORT: YES   INSRVMOD: NA  RANGE: See above
             PERSIST: YES   DEFVALUE: NA  UNITS: bytes"   

::= { isamSyslog 2 }


isamSyslogTotalStorageSize OBJECT-TYPE
SYNTAX  INTEGER
ACCESS  read-only
STATUS  mandatory
  DESCRIPTION
       "The value of this object is the maximum storage allocated to
        store the messages locally in files. 

  ALCATEL NOTE:
             SUPPORT: YES   INSRVMOD: NA  RANGE: See above
             PERSIST: NO    DEFVALUE: NA  UNITS: bytes"   

::= { isamSyslog 3 }


isamSyslogInUseStorageSize OBJECT-TYPE
SYNTAX  INTEGER
ACCESS  read-only
STATUS  mandatory
  DESCRIPTION
       "The value of this object is the memory in bytes, utilized for
        storing syslog messages locally in files.

  ALCATEL NOTE:
             SUPPORT: YES   INSRVMOD: NA  RANGE: See above
             PERSIST: NO    DEFVALUE: NA  UNITS: bytes"   

::= { isamSyslog 4 }


isamSyslogReservedStorageSize OBJECT-TYPE
SYNTAX  INTEGER
ACCESS  read-only
STATUS  mandatory
  DESCRIPTION
       "The value of this object is the memory in bytes reserved
        during creation of a syslog server entry for the local server type

  ALCATEL NOTE:
             SUPPORT: YES   INSRVMOD: NA  RANGE: See above
             PERSIST: NO    DEFVALUE: NA  UNITS: bytes"   

::= { isamSyslog 5 }


isamSyslogFreeStorageSize OBJECT-TYPE
SYNTAX  INTEGER
ACCESS  read-only
STATUS  mandatory
  DESCRIPTION
       "The value of this object is the free memory in bytes,
        available for storing syslog messages from total allocated memory.

  ALCATEL NOTE:
             SUPPORT: YES   INSRVMOD: NA  RANGE: See above
             PERSIST: NO    DEFVALUE: NO  UNITS: bytes"   

::= { isamSyslog 6 }

--======================================================================
--+++++++++++++++++++++++++++ END OF SCALARS  ++++++++++++++++++++++++++|
--====================================================================== 



--=========================================================================
-- ###################  SYSLOG SERVER TABLE BEGINS #######################|
--=========================================================================

isamSyslogServerTable OBJECT-TYPE
   SYNTAX  SEQUENCE OF IsamSyslogServerTableEntry
   ACCESS  not-accessible
   STATUS  mandatory
   DESCRIPTION
        "Table of syslog servers. A maximum of 64 servers can be created.

   ALCATEL NOTE:
             SUPPORT: YES   TABLESIZE: DEP as described above"
   ::= { isamSyslog 7}


isamSyslogServerTableEntry OBJECT-TYPE
   SYNTAX IsamSyslogServerTableEntry  
   ACCESS  not-accessible
   STATUS  mandatory
   DESCRIPTION
      "Syslog table entry. A Manager can delete an entry in this table
       if there is are no configuration entries associated with this entry
       in the isamSyslogConfigTable.If this entry has server type local,  
       then the corresponding file stored in the system will be deleted.  

   ALCATEL NOTE:
             SUPPORT: YES"

INDEX { isamSyslogServerIndex }

::= { isamSyslogServerTable 1 }


IsamSyslogServerTableEntry ::=
   SEQUENCE {
                isamSyslogServerIndex       IsamSyslogServerIndexType,
                isamSyslogServerIdentity    AsamProfileName,
                isamSyslogServerType        IsamSyslogServerType,
                isamSyslogServerAddress     IpAddress,
                isamSyslogServerName        DisplayString,
                isamSyslogServerValue       INTEGER,
                isamSyslogEnable            IsamSysLogModeType,
                isamSyslogServerRate        INTEGER,
                isamSyslogServerRotate      INTEGER,
                isamSyslogServerUploadPath     DisplayString,
                isamSyslogServerUploadOnRotate IsamSysLogModeType,
                isamSyslogServerRowStatus   RowStatus
   }


isamSyslogServerIndex OBJECT-TYPE
   SYNTAX  IsamSyslogServerIndexType
   ACCESS  not-accessible
   STATUS  mandatory
   DESCRIPTION
        "Index to the syslog server table.

   ALCATEL NOTE:
             SUPPORT: YES   INSRVMOD: NA   RANGE: See above
             PERSIST: NO    DEFVALUE: NA   UNITS: NA"

   ::= { isamSyslogServerTableEntry 1 }


isamSyslogServerIdentity OBJECT-TYPE
   SYNTAX  AsamProfileName
   ACCESS  read-write
   STATUS  mandatory 
   DESCRIPTION
        "A textual name identifying the Server. This name has to be unique.

   ALCATEL NOTE:
             SUPPORT: YES   INSRVMOD: NA   RANGE: See above
             PERSIST: YES   DEFVALUE: NA   UNITS: NA"

   ::= { isamSyslogServerTableEntry 2 }


isamSyslogServerType OBJECT-TYPE
   SYNTAX IsamSyslogServerType  
   ACCESS  read-write
   STATUS  mandatory 
   DESCRIPTION
        "Type of syslog server.Option file will be used to store the
         logs locally; udp is used to send the logs to a remote
         server; all-cli, all-tl1 and all-users options are used to display
         the syslog message on terminals; cli-user,tl1-user,trace and 
         cli-profile is not supported.

   ALCATEL NOTE:
             SUPPORT: YES   INSRVMOD: NA   RANGE: See above
             PERSIST: YES   DEFVALUE: NA   UNITS: NA"

   ::= { isamSyslogServerTableEntry 3 }


isamSyslogServerAddress OBJECT-TYPE
   SYNTAX  IpAddress
   ACCESS  read-write
   STATUS  mandatory 
   DESCRIPTION
        "The IP address of the syslog server for udp or upload-on-rotate
         logs. If isamSyslogServerType is other file or 
         isamSyslogServerUploadOnRotate is disabled, then the server 
         address will be set to 0.0.0.0.


   ALCATEL NOTE:
             SUPPORT: YES   INSRVMOD: NA        RANGE: See above
             PERSIST: YES   DEFVALUE: 0.0.0.0   UNITS: NA"

   ::= { isamSyslogServerTableEntry 4 }


isamSyslogServerUploadPath OBJECT-TYPE
   SYNTAX  DisplayString (SIZE (0..64))
   ACCESS  read-write
   STATUS  mandatory
   DESCRIPTION
        "This MIB object indicates the path on isamSyslogServerAddress
         for storage of uploaded files, if isamSyslogServerUploadOnRotate 
		 is enabled. 

   ALCATEL NOTE:
             SUPPORT: YES   INSRVMOD: YES  		 RANGE: NA
             PERSIST: YES   DEFVALUE: NULL		 UNITS: NA"

   ::= { isamSyslogServerTableEntry 12 }


isamSyslogServerName OBJECT-TYPE
   SYNTAX  DisplayString
   ACCESS  read-write   
   STATUS  mandatory    
   DESCRIPTION
        "If the server type is file, this object is the filename in which
         messages should be logged. If the server type is cli_useror cli
         profile, this object will have the login name of the user. This
         object will be empty for other server types.

   ALCATEL NOTE:
             SUPPORT: YES   INSRVMOD: NA   RANGE: See above
             PERSIST: YES   DEFVALUE: NA   UNITS: NA"

   ::= { isamSyslogServerTableEntry 5 }


isamSyslogServerValue OBJECT-TYPE
   SYNTAX  INTEGER
   ACCESS  read-write
   STATUS  mandatory 
   DESCRIPTION
        "If the server type is file, the value of this object is the size
         of the file as reserved by the manager. If the server type is
         remote server, this object will have the port on the remote server
         on which it is listening for syslog messages. Max size of file
         name is restricted to 12 chars.The characters set is {[a-zA-Z0-9]
         - _ .}. File name should have atleast one character other than
         dot.It is preferred to give the file name in the format <filename>
         + dot + <extension - max 3 chars>. Port number varies from
         1..65535.

   ALCATEL NOTE:
             SUPPORT: YES   INSRVMOD: NA   RANGE: See above
             PERSIST: YES   DEFVALUE: NA   UNITS: NA"

   ::= { isamSyslogServerTableEntry 6 }


isamSyslogEnable OBJECT-TYPE
   SYNTAX  IsamSysLogModeType
   ACCESS  read-write
   STATUS  mandatory 
   DESCRIPTION
        "Enable or disable system logging.

   ALCATEL NOTE:
             SUPPORT: YES   INSRVMOD: NA         RANGE: See above
             PERSIST: YES   DEFVALUE: enabled(1) UNITS: NA"

   DEFVAL { enabled }
   ::= { isamSyslogServerTableEntry 7 }



isamSyslogServerRate OBJECT-TYPE
   SYNTAX  INTEGER
   ACCESS  read-write
   STATUS  mandatory 
   DESCRIPTION
        "The value of this object is maximum number of messages that are
         allowed to transmit per second to the server. If unlimited server
         rate is needed then this object its value must be set to 0. This
         object is applicable if the server type is udp.

   ALCATEL NOTE:
             SUPPORT: NO   INSRVMOD: NA   RANGE: See above
             PERSIST: YES   DEFVALUE: 0   UNITS: messages per second"

   ::= { isamSyslogServerTableEntry 8 }


isamSyslogServerRotate OBJECT-TYPE
   SYNTAX  INTEGER
                                {
                                        rotate  (1),
                                        idle (2)
                                }
   ACCESS  write-only
   STATUS  mandatory
   DESCRIPTION
        "This mib object is used to rotate the files explicitly
         this is applicable if the server type is local.
         Value idle(2) will be returned when this variable
         is read by the operator. Only one backup file is supported.


   ALCATEL NOTE:
             SUPPORT: YES   INSRVMOD: NA   RANGE: See above
             PERSIST: NO    DEFVALUE: NA   UNITS: NA"

   ::= { isamSyslogServerTableEntry 9 }

isamSyslogServerUploadOnRotate OBJECT-TYPE
   SYNTAX  IsamSysLogModeType 
   ACCESS  read-write
   STATUS  mandatory
   DESCRIPTION
	"This mib object is used to enable upload of rotated 
	files to the server at isamSyslogServerAddress in 
	directory isamSyslogUploadPath. If the server does not 
	successfully upload the file, then ULFAILED alarm 
	is raised. The alarm is cleared when all rotated files 
	are successfully uploaded.

   ALCATEL NOTE:
             SUPPORT: YES   INSRVMOD: YES  RANGE: See above
             PERSIST: YES   DEFVALUE: Disabled(2) UNITS: NA"

   ::= { isamSyslogServerTableEntry 11 }



isamSyslogServerRowStatus OBJECT-TYPE
   SYNTAX  RowStatus
   ACCESS  read-write
   STATUS  mandatory 
   DESCRIPTION
        "Object to create and delete a row.

   ALCATEL NOTE:
             SUPPORT: YES  INSRVMOD: NA   RANGE: See above
             PERSIST: NO   DEFVALUE: NA   UNITS: NA"

   ::= { isamSyslogServerTableEntry 10 }


--=========================================================================
--++++++++++++++++++++++END OF SYSLOG SERVER TABLE++++++++++++++++++++++++|
--=========================================================================



--=========================================================================
--###################  SYSLOG CONFIG TABLE BEGAINS  ######################|
--=========================================================================

isamSyslogConfigTable OBJECT-TYPE
   SYNTAX  SEQUENCE OF IsamSyslogConfigTableEntry
   ACCESS  not-accessible
   STATUS  mandatory
   DESCRIPTION
        "Table of Syslog configuration entries.

   ALCATEL NOTE:
             SUPPORT: YES   TABLESIZE: DEP as described above"
   ::= { isamSyslog 8 }


isamSyslogConfigTableEntry OBJECT-TYPE
   SYNTAX IsamSyslogConfigTableEntry  
   ACCESS  not-accessible
   STATUS  mandatory
   DESCRIPTION
        "syslog configuration table entry.
         Some combinations of syslogServer & messageType are not allowed; in 
         which case an error inconsistentValue will be returned.
        
   ALCATEL NOTE:
             SUPPORT: YES"

   INDEX { isamSyslogServerIndexNbr,isamSyslogMessageType }

::= { isamSyslogConfigTable 1 }


IsamSyslogConfigTableEntry ::=
   SEQUENCE {
       isamSyslogServerIndexNbr     IsamSyslogServerIndexPointerType,
       isamSyslogMessageType        IsamSyslogMessageType,
       isamSyslogSeverity           IsamSyslogSeverityType,
       isamSyslogFacility           IsamSyslogFacility,
       isamSyslogConfigStatus       RowStatus
   }

isamSyslogServerIndexNbr OBJECT-TYPE
   SYNTAX  IsamSyslogServerIndexPointerType
   ACCESS  not-accessible
   STATUS  mandatory
   DESCRIPTION
        "Index into the syslog config table.

   ALCATEL NOTE:
             SUPPORT: YES   INSRVMOD: NA   RANGE: See above
             PERSIST: YES   DEFVALUE: NA   UNITS: NA"

   ::= { isamSyslogConfigTableEntry 1 }

isamSyslogMessageType OBJECT-TYPE
   SYNTAX  IsamSyslogMessageType 
   ACCESS  read-write
   STATUS  mandatory 
   DESCRIPTION
        "This object holds the type of message that the manager
         is interested in.

   ALCATEL NOTE:
             SUPPORT: YES   INSRVMOD: NA   RANGE: See above
             PERSIST: YES   DEFVALUE: NA   UNITS: NA"

   ::= { isamSyslogConfigTableEntry 2 }


isamSyslogSeverity OBJECT-TYPE
   SYNTAX  IsamSyslogSeverityType
   ACCESS  read-write
   STATUS  mandatory 
   DESCRIPTION
        "This object defines the System Log Severity allowed.
         It is coded in a bitmap defined as follows.More than
         one mode can be set simultaneously.The respective Log
         types correspond to the following integer values in the
         bitmap,other bit positions are reserved for future use.

         Octet 1 :
         1: emergency
         2: alert
         4: critical
         8: error   
        16: warning 
        32: notice  
        64: info    
       128: debug   

         Octet 2-4:  Reserved for future use

   ALCATEL NOTE:
             SUPPORT: YES   INSRVMOD: NA   RANGE: See above
             PERSIST: YES   DEFVALUE: NA   UNITS: NA"

   ::= { isamSyslogConfigTableEntry 3 }


isamSyslogFacility  OBJECT-TYPE
   SYNTAX   IsamSyslogFacility 
   ACCESS   read-write
   STATUS   mandatory 
   DESCRIPTION
        "This object is used to decouple the internal message type
         to the standard message type. The value of this object   
         will be used for sending out the request to the remote server
         instead of using internal message type.

   ALCATEL NOTE:
             SUPPORT: YES   INSRVMOD: NA   RANGE: See above
             PERSIST: YES   DEFVALUE: NA   UNITS: NA"

   ::= { isamSyslogConfigTableEntry 4 }


isamSyslogConfigStatus OBJECT-TYPE
   SYNTAX       RowStatus
   ACCESS       read-write
   STATUS       mandatory 
   DESCRIPTION
        "Object to create and delete a row in this config entry.

   ALCATEL NOTE:
             SUPPORT: YES  INSRVMOD: NA   RANGE: See above
             PERSIST: NO   DEFVALUE: NA   UNITS: NA"

   ::= { isamSyslogConfigTableEntry 5 }

--=========================================================================
--+++++++++++++++++++++++END OF SYSLOG CONFIG TABLE+++++++++++++++++++++++|
--=========================================================================


--=========================================================================
-- ###################  SYSLOG SERVER MAPPING TABLE ######################|
--========================================================================= 

isamSyslogServerMappingTable    OBJECT-TYPE
      SYNTAX     SEQUENCE OF IsamSyslogServerMappingEntry
      ACCESS     not-accessible
      STATUS     mandatory
      DESCRIPTION
           "The (conceptual) table listing the syslog server name to
            syslog server Index Mapping. 

      ALCATEL NOTE:
        SUPPORT: YES   TABLESIZE: DEP as described above"

      ::= {isamSyslog 9}

isamSyslogServerMappingEntry OBJECT-TYPE
      SYNTAX    IsamSyslogServerMappingEntry
      ACCESS    not-accessible
      STATUS    mandatory
      DESCRIPTION
           "An entry (conceptual row) representing the syslog
            server Name to syslog Index Mapping 

      ALCATEL NOTE:
             SUPPORT: YES"

      INDEX { isamSyslogServerMappingName }

      ::= { isamSyslogServerMappingTable 1 }


IsamSyslogServerMappingEntry ::=
    SEQUENCE {
         isamSyslogServerMappingName         AsamProfileName,
         isamSyslogServerMappingIndex        IsamSyslogServerIndexType
    }

isamSyslogServerMappingName  OBJECT-TYPE
          SYNTAX            AsamProfileName
          ACCESS             not-accessible
          STATUS             mandatory
          DESCRIPTION
            "The syslog server name.

          ALCATEL NOTE:
                SUPPORT: YES  INSRVMOD: NA   RANGE: See above
                PERSIST: NO   DEFVALUE: NA   UNITS: NA"

          ::= { isamSyslogServerMappingEntry 1 }


isamSyslogServerMappingIndex    OBJECT-TYPE
          SYNTAX                IsamSyslogServerIndexType
          ACCESS                read-only
          STATUS                mandatory
          DESCRIPTION
             "The Index of the corresponding server.

          ALCATEL NOTE:
             SUPPORT: YES  INSRVMOD: NA   RANGE: See above
             PERSIST: NO   DEFVALUE: NA   UNITS: NA"

          ::= { isamSyslogServerMappingEntry 2 }

--=========================================================================
--++++++++++++++++++++++++END OF SYSLOG SERVER MAPING TABLE+++++++++++++++|
--=========================================================================

END
