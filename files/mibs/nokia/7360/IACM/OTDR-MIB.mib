--
-- This SMIv1 module has been generated by smidump 0.4.5. Do not edit.
--

OTDR-MIB DEFINITIONS ::= BEGIN

IMPORTS
    ifIndex
        FROM ITF-MIB
    OBJECT-TYPE
        FROM RFC-1212
    Gauge
        FROM RFC1155-SMI
    asam
        FROM SYSTEM-MIB;

otdrMIB OBJECT IDENTIFIER
    ::= { asam 94 }

-- otdrMIB MODULE-IDENTITY
--     LAST-UPDATED "201106100000Z"
--     ORGANIZATION 
--         "Alcatel-Lucent"
--     CONTACT-INFO 
--         "Email:  asam.mibsupport@alcatel-lucent.com"
--     DESCRIPTION 
--         "This MIB module is implemented in Alcatel-Lucent's
--          ISAM for the OTDR functionality"
--     REVISION    "201106100000Z"
--     DESCRIPTION 
--         "Added otdrCollectionTable to be able to read
--          the time of the latest collection."
--     REVISION    "201102140000Z"
--     DESCRIPTION 
--         "Added otdrConfigCalibrNbrOfMeasPH and otdrConfigCalibrPeriod
--          attributes to the otdrConfigTable."
--     REVISION    "201101210000Z"
--     DESCRIPTION 
--         "Small updates in the description of the default
--          PRBS pattern and register settings."
--     REVISION    "201101060000Z"
--     DESCRIPTION 
--         "Small updates in the description of some MIB objects."
--     REVISION    "201011220000Z"
--     DESCRIPTION 
--         "Small updates in the description of some MIB objects."
--     REVISION    "201009030000Z"
--     DESCRIPTION 
--         "First version containing OTDR functionality."
--     REVISION    "201007200000Z"
--     DESCRIPTION 
--         "Initial version to start from."
--     ::= { asam 94 }


OtdrPRBSPatternType ::=
    OCTET STRING (SIZE(0..8192))

-- OtdrPRBSPatternType ::= TEXTUAL-CONVENTION
--     STATUS      mandatory
--     DESCRIPTION 
--         "This type defines how the PRBS pattern configured in the MONA
--          ASIC is represented in the MIB. It is a continuous array of
--          bytes that will be written as such in the PRBS pattern memory
--          of the ASIC."
--     SYNTAX      OCTET STRING (SIZE(0..8192))

OtdrRegistersConfigType ::=
    OCTET STRING (SIZE(0..1024))

-- OtdrRegistersConfigType ::= TEXTUAL-CONVENTION
--     STATUS      mandatory
--     DESCRIPTION 
--         "This type defines how the register settings of the MONA ASIC
--          is represented in the MIB. It is a continuous array of bytes
--          that consists of one or more records. Each record consists
--          of an address offset (2 bytes), length (2 bytes) and
--          register data (<length> bytes).
--          Each record contains values that need to be configured in
--          the ASIC registers at the indicated address offset, byte by
--          byte starting with the least significant byte first.
--          Records will be handled in the order as they appear in this
--          octet string."
--     SYNTAX      OCTET STRING (SIZE(0..1024))

OtdrRegistersReadType ::=
    OCTET STRING (SIZE(0..512))

-- OtdrRegistersReadType ::= TEXTUAL-CONVENTION
--     STATUS      mandatory
--     DESCRIPTION 
--         "This type defines how the registers of the MONA ASIC to be
--          read is represented in the MIB. It is a continuous array of
--          bytes that consists of one or more records. Each record
--          consists of an address offset (2 bytes) and length (2 bytes).
--          Each record contains the address offset and length of values
--          that need to be read from the ASIC.
--          Records will be handled in the order as they appear in this
--          octet string."
--     SYNTAX      OCTET STRING (SIZE(0..512))

otdrConfig OBJECT IDENTIFIER
    ::= { otdrMIB 1 }

otdrConfigAverages OBJECT-TYPE
    SYNTAX      Gauge (16..20)
--     UNITS       "power of 2"
    ACCESS      read-write
    STATUS      mandatory
    DESCRIPTION 
        "This object defines the number of averages the MONA ASIC
         will make during each OTDR measurement.
         ALCATEL-LUCENT NOTE:
         PERSIST: YES
         RANGE: 20..20
         DESCR: In this release the object will only accept value 20."
    ::= { otdrConfig 1 }

otdrConfigDefaultPRBSPattern OBJECT-TYPE
    SYNTAX      OtdrPRBSPatternType
    ACCESS      read-write
    STATUS      mandatory
    DESCRIPTION 
        "This object defines the default PRBS pattern that will be
         configured in the MONA ASIC in case no dedicated specific
         PRBS pattern have been specified for a certain OTDR SFP.
         It allows to enable OTDR of a certain SFP without any
         specific configuration settings.
         Any change of this object will only take effect when OTDR
         is enabled on a certain SFP while the previous state was
         disabled before and no specific PRBS pattern was
         configured for this SFP.
         This object will have an initial factory configured value
         which is suited for direct and inverse measurements
         with bit lengths of 2^n-1 bits with n between 9 and 14.
         ALCATEL-LUCENT NOTE:
         PERSIST: YES"
    ::= { otdrConfig 2 }

otdrConfigDefaultRegisters OBJECT-TYPE
    SYNTAX      OtdrRegistersConfigType
    ACCESS      read-write
    STATUS      mandatory
    DESCRIPTION 
        "This object defines the default register settings that will be
         configured in the MONA ASIC in case no dedicated specific
         register settings have been specified for a certain OTDR SFP.
         It allows to enable OTDR of a certain SFP without any
         specific configuration settings.
         Any change of this object will only take effect when OTDR
         is enabled on a certain SFP while the previous state was
         disabled before and no specific register settings was
         configured for this SFP.
         This object will have an initial factory configured value
         which is suited for doing standard measurements with bit
         length of 2^11-1 bits using the factory configured PRBS
         pattern.
         ALCATEL-LUCENT NOTE:
         PERSIST: YES"
    ::= { otdrConfig 3 }

otdrConfigTable OBJECT-TYPE
    SYNTAX      SEQUENCE OF OtdrConfigEntry
    ACCESS      not-accessible
    STATUS      mandatory
    DESCRIPTION 
        "This table contains all OTDR configuration data per SFP where
         OTDR functionality is supported by the system.
         ALCATEL-LUCENT NOTE:
         TABLESIZE: DEP (number of SFP's of planned OTDR capable LTs)"
    ::= { otdrConfig 4 }

otdrConfigEntry OBJECT-TYPE
    SYNTAX      OtdrConfigEntry
    ACCESS      not-accessible
    STATUS      mandatory
    DESCRIPTION 
        "An entry in the otdrConfigTable contains the configuration
         data of one SFP for which the system supports OTDR
         functionality in case an OTDR capable SFP is plugged in.
         Rows are automatically created by the system for each SFP
         belonging to a LT board for which the system supports OTDR
         functionality, when the board is planned.
         Rows are automatically deleted by the system for each SFP
         belonging to a LT board for which the system supports OTDR
         functionality, when the board is unplanned.
         An entry in the table is indexed with the ifIndex of
         the physical PON interface."
    INDEX       { ifIndex }
    ::= { otdrConfigTable 1 }

OtdrConfigEntry ::= SEQUENCE {
    otdrConfigMode                  INTEGER,
    otdrConfigPRBSPattern           OtdrPRBSPatternType,
    otdrConfigRegisters             OtdrRegistersConfigType,
    otdrConfigCalibrNbrOfMeasPH     INTEGER,
    otdrConfigCalibrPeriod          INTEGER
}

otdrConfigMode OBJECT-TYPE
    SYNTAX      INTEGER { enabled(1), disabled(2), test(3) }
    ACCESS      read-write
    STATUS      mandatory
    DESCRIPTION 
        "This object is used to enable or disable OTDR functionality on
         a certain OTDR capable SFP. Enabling OTDR on a certain SFP
         will be rejected in case the system can check that concerned
         SFP, currenty plugged in, is not OTDR capable. Enabling OTDR
         will also be rejected in case configuration data (either
         specific or default) is not configured yet.
         Test mode is only to be used in lab conditions."
    DEFVAL      { disabled }
    ::= { otdrConfigEntry 1 }

otdrConfigPRBSPattern OBJECT-TYPE
    SYNTAX      OtdrPRBSPatternType
    ACCESS      read-write
    STATUS      mandatory
    DESCRIPTION 
        "This object defines the specific PRBS pattern that will be
         configured in the MONA ASIC for this OTDR SFP. In case this
         object is empty, then the default PRBS pattern will apply.
         Change of this object is only allowed when OTDR is disabled
         for this OTDR SFP.
         ALCATEL-LUCENT NOTE:
         PERSIST: YES
         INSRVMOD: NO
         SPARSE: NO"
    DEFVAL      { "" }
    ::= { otdrConfigEntry 2 }

otdrConfigRegisters OBJECT-TYPE
    SYNTAX      OtdrRegistersConfigType
    ACCESS      read-write
    STATUS      mandatory
    DESCRIPTION 
        "This object defines the specific register settings that will
         be configured in the MONA ASIC for this OTDR SFP. In case
         this object is empty, then the default register settings will
         apply. Change of this object is only allowed when OTDR is
         disabled for this OTDR SFP.
         ALCATEL-LUCENT NOTE:
         PERSIST: YES
         INSRVMOD: NO
         SPARSE: NO"
    DEFVAL      { "" }
    ::= { otdrConfigEntry 3 }

otdrConfigCalibrNbrOfMeasPH OBJECT-TYPE
    SYNTAX      INTEGER (0..8)
    ACCESS      read-write
    STATUS      mandatory
    DESCRIPTION 
        "This object defines the number of calibration measurements that
         has to be done per Hour. Since only 8 measurements can be taken
         the number ranges from 0 till 8. Value 0 means no calibration
         measurements are taken. This object goes together with the object
         otdrConfigCalibrPeriod in case this object differs from 0.
         ALCATEL-LUCENT NOTE:
         PERSIST: YES
         INSRVMOD: NO
         SPARSE: NO"
    DEFVAL      { 0 }
    ::= { otdrConfigEntry 4 }

otdrConfigCalibrPeriod OBJECT-TYPE
    SYNTAX      INTEGER (1..120)
    ACCESS      read-write
    STATUS      mandatory
    DESCRIPTION 
        "This object defines the period during which the previous object is
         executed : every x hour. Calibration measurements can be taken
         every hour, every 2 hours, every 3 hours ... every x hour.
         The current max is set to 120 that is the equivalent of every
         5 days.
         ALCATEL-LUCENT NOTE:
         PERSIST: YES
         INSRVMOD: NO
         SPARSE: NO"
    DEFVAL      { 1 }
    ::= { otdrConfigEntry 5 }

otdrOperData OBJECT IDENTIFIER
    ::= { otdrMIB 2 }

otdrOperDefaultRegisterRead OBJECT-TYPE
    SYNTAX      OtdrRegistersReadType
    ACCESS      read-write
    STATUS      mandatory
    DESCRIPTION 
        "This object defines which default specific registers that will
         be read from the MONA ASIC in case no dedicated specific
         registers to read have been configured for a certain OTDR SFP.
         ALCATEL-LUCENT NOTE:          
         PERSIST: NO        
         DEFVALUE: NULL"
    ::= { otdrOperData 1 }

otdrOperRegisterTable OBJECT-TYPE
    SYNTAX      SEQUENCE OF OtdrOperRegisterEntry
    ACCESS      not-accessible
    STATUS      mandatory
    DESCRIPTION 
        "This table contains all OTDR operational ASIC register data
         per SFP where OTDR functionality is supported by the system.
         ALCATEL-LUCENT NOTE:
         TABLESIZE: DEP (number of SFP's of planned OTDR capable LTs)"
    ::= { otdrOperData 2 }

otdrOperRegisterEntry OBJECT-TYPE
    SYNTAX      OtdrOperRegisterEntry
    ACCESS      not-accessible
    STATUS      mandatory
    DESCRIPTION 
        "An entry in the otdrOperRegisterTable contains the operational
         ASIC register data of one SFP for which the system supports
         OTDR functionality in case an OTDR capable SFP is plugged in.
         Rows are automatically created by the system for each SFP
         belonging to a LT board for which the system supports OTDR
         functionality, when the board is planned.
         Rows are automatically deleted by the system for each SFP
         belonging to a LT board for which the system supports OTDR
         functionality, when the board is unplanned.
         An entry in the table is indexed with the ifIndex of
         the physical PON interface."
    INDEX       { ifIndex }
    ::= { otdrOperRegisterTable 1 }

OtdrOperRegisterEntry ::= SEQUENCE {
    otdrOperRegisterRead    OtdrRegistersReadType,
    otdrOperRegisterValues  OtdrRegistersConfigType
}

otdrOperRegisterRead OBJECT-TYPE
    SYNTAX      OtdrRegistersReadType
    ACCESS      read-write
    STATUS      mandatory
    DESCRIPTION 
        "This object defines which specific registers that will be read
         from the MONA ASIC for this OTDR SFP. In case this object is
         empty, the default registers will be read when reading the
         object that contains the values of the requested registers for
         this SFP.
         ALCATEL-LUCENT NOTE:
         PERSIST: NO
         INSRVMOD: YES
         SPARSE: NO"
    DEFVAL      { "" }
    ::= { otdrOperRegisterEntry 1 }

otdrOperRegisterValues OBJECT-TYPE
    SYNTAX      OtdrRegistersConfigType
    ACCESS      read-only
    STATUS      mandatory
    DESCRIPTION 
        "This object contains the values of the specific registers that
         have been read from the MONA ASIC for this OTDR SFP.
         Before reading this object, the specific registers that must
         be read are configured or the default registers to read are
         configured.
         ALCATEL-LUCENT NOTE:
         PERSIST: NO   
         INSRVMOD: NO
         SPARSE: NO  "
    ::= { otdrOperRegisterEntry 2 }

otdrClearMeasTable OBJECT-TYPE
    SYNTAX      SEQUENCE OF OtdrClearMeasEntry
    ACCESS      not-accessible
    STATUS      mandatory
    DESCRIPTION 
        "This table contains the attribute to clear all collected OTDR
         measurements per SFP where OTDR functionality is supported by
         the system.
         ALCATEL-LUCENT NOTE:
         TABLESIZE: DEP (number of SFP's of planned OTDR capable LTs)"
    ::= { otdrOperData 3 }

otdrClearMeasEntry OBJECT-TYPE
    SYNTAX      OtdrClearMeasEntry
    ACCESS      not-accessible
    STATUS      mandatory
    DESCRIPTION 
        "An entry in the otdrClearMeasTable contains the attribute to
         clear all collected OTDR measurements of one SFP for which
         the system supports OTDR functionality.
         Rows are automatically created by the system for each SFP
         belonging to a LT board for which the system supports OTDR
         functionality, when the board is planned.
         Rows are automatically deleted by the system for each SFP
         belonging to a LT board for which the system supports OTDR
         functionality, when the board is unplanned.
         An entry in the table is indexed with the ifIndex of
         the physical PON interface."
    INDEX       { ifIndex }
    ::= { otdrClearMeasTable 1 }

OtdrClearMeasEntry ::= SEQUENCE {
    otdrClearMeasAction     INTEGER
}

otdrClearMeasAction OBJECT-TYPE
    SYNTAX      INTEGER { noaction(1), clear(2) }
    ACCESS      read-write
    STATUS      mandatory
    DESCRIPTION 
        "This object is a button-like object and is used to clear all
         collected OTDR measurements of this SFP.
         Setting this object with value noaction will be accepted but
         has no effect.
         Value noaction will be returned always when read."
    DEFVAL      { noaction }
    ::= { otdrClearMeasEntry 1 }

otdrCollectionTable OBJECT-TYPE
    SYNTAX      SEQUENCE OF OtdrCollectionEntry
    ACCESS      not-accessible
    STATUS      mandatory
    DESCRIPTION 
        "This table contains the status info of the OTDR collections
         per SFP where OTDR functionality is supported by the system.
         ALCATEL-LUCENT NOTE:
         TABLESIZE: DEP (number of SFP's of planned OTDR capable LTs)"
    ::= { otdrOperData 4 }

otdrCollectionEntry OBJECT-TYPE
    SYNTAX      OtdrCollectionEntry
    ACCESS      not-accessible
    STATUS      mandatory
    DESCRIPTION 
        "An entry in the otdrCollectionTable contains the collection
         status of one SFP for which the system supports OTDR
         functionality.
         Rows are automatically created by the system for each SFP
         belonging to a LT board for which the system supports OTDR
         functionality, when the board is planned.
         Rows are automatically deleted by the system for each SFP
         belonging to a LT board for which the system supports OTDR
         functionality, when the board is unplanned.
         An entry in the table is indexed with the ifIndex of
         the physical PON interface."
    INDEX       { ifIndex }
    ::= { otdrCollectionTable 1 }

OtdrCollectionEntry ::= SEQUENCE {
    otdrLatestCollectionTimeSeconds     Gauge
}

otdrLatestCollectionTimeSeconds OBJECT-TYPE
    SYNTAX      Gauge
    ACCESS      read-only
    STATUS      mandatory
    DESCRIPTION 
        "This object contains the network time in seconds of the time
         when the latest OTDR measurements of this SFP has ended and
         the measurements were collected and stored by the software.
         It is the integer part of the NTP Timestamp which
         means the number of seconds since 0h on 1 January 1900.
         Value 0 is returned in case OTDR is disabled or when no
         measurements collection has taken place and stored yet.
         ALCATEL-LUCENT NOTE:
         PERSIST: NO
         INSRVMOD: NO
         SPARSE: NO"
    ::= { otdrCollectionEntry 1 }

END -- end of module OTDR-MIB.
