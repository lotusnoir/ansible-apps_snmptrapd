-- ALCATEL RFC1215-SMI MIB
-- ==========================================================================
-- This MIB module is implemented in Alcatel's ASAM 7301 System Rel 5.0
-- The following definition was extracted from rfc1215
-- and modified to reflect Alcatel's implementation.
--
         -- CONTACT-INFO "Marc Van Vlimmeren"
         -- Postal: Alcatel Bell Telephone
         -- Francis Wellesplein 1
         -- 2018 Antwerpen
         -- BELGIUM
-- ==========================================================================
--  HISTORY:
--
--  date: 2001-12-27  -  version: 3EC37310AAAA_E5.0.0.0
--  editor: Marc Van Vlimmeren 
--
-- Changes with respect to previous edition:
--      * added ALCATEL note for not supported traps.
-- ==========================================================================


RFC-1215 DEFINITIONS ::= BEGIN

IMPORTS
    ifIndex
	FROM ITF-MIB 

    snmp, egpNeighAddr
        FROM RFC1213-MIB;

--	SMI TRAP-TYPE
	
--          TRAP-TYPE MACRO ::=
--          BEGIN
--              TYPE NOTATION ::= "ENTERPRISE" value
--                                    (enterprise OBJECT IDENTIFIER)
--                                VarPart
--                                DescrPart
--                                ReferPart
--              VALUE NOTATION ::= value (VALUE INTEGER)
--
--              VarPart ::=
--                         "VARIABLES" "{" VarTypes "}"
--                              | empty
--              VarTypes ::=
--                         VarType | VarTypes "," VarType
--              VarType ::=
--                         value (vartype ObjectName)
--
--              DescrPart ::=
--                         "DESCRIPTION" value (description DisplayString)
--                              | empty
--
--              ReferPart ::=
--                         "REFERENCE" value (reference DisplayString)
--                              | empty
--
--          END


coldStart            TRAP-TYPE
    ENTERPRISE       snmp
    DESCRIPTION      "A coldStart trap signifies that the sending
                     protocol entity is reinitializing itself such 
                     that the agent's configuration or the protocol
                     entity implementation may be altered."
::= 0

warmStart            TRAP-TYPE
    ENTERPRISE       snmp
    DESCRIPTION      "A warmStart trap signifies that the sending 
                     protocol entity is reinitializing itself such 
                     that neither the agent's configuration nor the 
                     protocol entity implementation may be altered.

    ALCATEL NOTE: the ALCATEL ASAM does NOT support this trap."

::= 1

linkDown             TRAP-TYPE
    ENTERPRISE       snmp
    VARIABLES        { ifIndex }
    DESCRIPTION      "A linkDown trap signifies that the sending
                     protocol entity recognizes a failure in one of
                     the communication links represented in the
                     agent's configuration."

::= 2

linkUp               TRAP-TYPE     
    ENTERPRISE       snmp
    VARIABLES        { ifIndex }
    DESCRIPTION      "A linkUp trap signifies that the sending
                     protocol entity recognizes that one of the
                     communication links represented in the agent's
                     configuration has come up."
::= 3

authenticationFailure TRAP-TYPE
    ENTERPRISE        snmp
    DESCRIPTION       "An authenticationFailure trap signifies that
                    the sending protocol entity is the addressee
                    of a protocol message that is not properly
                    authenticated.  While implementations of the
                    SNMP must be capable of generating this trap,
                    they must also be capable of suppressing the
                    emission of such traps via an implementation-
                    specific mechanism."

::= 4

egpNeighborLoss      TRAP-TYPE
    ENTERPRISE       snmp
    VARIABLES        { egpNeighAddr }
    DESCRIPTION      "An egpNeighborLoss trap signifies that an EGP
                     neighbor for whom the sending protocol entity
                     was an EGP peer has been marked down and the
                     peer relationship no longer obtains.

    ALCATEL NOTE: the ALCATEL ASAM does NOT support this trap."

::= 5

END
