PLIM-ETHERNET-MIB DEFINITIONS ::= BEGIN

-- =======================================================================
--  This specification is published by Alcatel-Lucent under Non-Disclosure
--  Agreement(s) (NDA) with specific parties and has to be considered as
--  Confidential Information as defined in such NDA.
--  Alcatel-Lucent reserves the right to revise this document for any 
--  reason,including but not limited to conformity with standards 
--  promulgated by various agencies, utilisation of advances in the state 
--  of the technical areas, or the reflection of changes in the design of 
--  any equipment,techniques, or procedures described or referred to 
--  herein. The product specifications and other technical or performance 
--  information contained herein are subject to change without notice. 
--  Updates of this document will be issued under the above NDA's.
--  Alcatel-Lucent makes no representation or warranty, expressed or 
--  implied, with respect to the sufficiency, accuracy, or utility of any 
--  information or opinion contained herein. Alcatel-Lucent expressly 
--  advises that any use of for any purpose or reliance upon this technical 
--  reference is at the risk of the user and that Alcatel-Lucent shall not 
--  be liable for any damage or injury incurred by any person arising out 
--  of the sufficiency, accuracy, or utility of any information or opinion 
--  contained herein. This document is not to be construed as a suggestion 
--  to any manufacturer to modify or change any of its products, nor does 
--  this document represent any commitment by Alcatel-Lucent to sell or 
--  purchase any product.
--  Nothing contained herein shall be construed as conferring by 
--  implication, estoppel, or otherwise any license or right under any 
--  patent, whether or not the use of any information herein necessarily 
--  employs an invention of any existing or later issued patent. 
--  Alcatel-Lucent reserves the right not to offer any or all of these 
--  products and to withdraw any or all of them at any future time.
--  Copyright (C) 2014, Alcatel-Lucent. All Rights Reserved.
-- ========================================================================
--  MODULE-IDENTITY
--  LAST-UPDATED   "201612100000Z"
--  ORGANIZATION   "Alcatel"
--  CONTACT-INFO
--
--         Email:  asam.mibsupport@alcatel-lucent.be"
--
--  DESCRIPTION
--        "PLIM subsystem private defined MIB"
--
--  REVISION Dec 10,2016
--  DESCRIPTION
--	  "Version : 3EC37662EGAA_V5.6.0.0.4 
--	   Editor : KANNAN, Ezhilarasan
--	   Changes for RCR ALU02171369 -  L2 DHCP relay agent on NNI interfaces of MX/SX	
--	   Add description for extendAddDhcpOption82Nni and extendAddDhcpOption82Uplink
--
--  REVISION Sept 28,2016
--  DESCRIPTION
--         "Version : 3EC37662EGAA_V5.6.0.0.3
--          Editor :  Giridhararoopan Gangatharan
--          Changes for RCR ALU02171369 - L2 DHCP relay agent on NNI interfaces of MX/SX  
--          Add extendAddDhcpOption82Nni, extendAddDhcpOption82Uplink, extendRelayIdControl, 
--          extendRelayIdControlDhcpv6. Also add addorforward value in existing extendAddDhcpOption82.

--  REVISION June 07,2016
--  DESCRIPTION
--         "Version : 3EC37662EFAA_V5.5.0.0.0
--          Editor :  Tinghui Zhang
--          Changes for RCR ALU01765156 - Configurable Downstream p-bit translation behavior(OLT part)  
--          add extendVlanPortDSPbitMode to extendVlanPortTable "
--
-- REVISION Dec 28,2015
--  DESCRIPTION
--         "Version : 3EC37662EDAA_V5.4.0.0.2
--          Editor :  Xing Yudong
--          Changes for RCR ALU02093122 - Lightweight TPID Support On VULA  
--	        add extendVlanTpidTable
--          add extendVlanPortTPIDList to extendVlanPortTable
--          add extendPortVlanTPID to extendPortVlanAssociationTable
--          add extendPortVlanUpTpidDiscFrameCounter to extendPortVlanTroubleShootingExtensiveTable"
--
--  REVISION Dec 21,2015
--  DESCRIPTION
--         "Version : 3EC37662EDAA_V5.4.0.0.1
--         Editor :  Huang Jianfeng
--         Changes for RCR ALU02023389
--         change the range of extendVlanPortMaxNumMacAddresses. For FELT-B NNI port,
--         the range is 1 to 65535"
--
--  REVISION June 5,2015
--  DESCRIPTION
--         "Version : 3EC37662ECAA_V5.3.0.0.0
--          Editor :  ANAND AROKIARAJ
--          Changes for RCR ALU02085345 - Porting DTAG 5202 DHCP/PPPoE protocol 
--	    features to mainstream DHCPv6. Extended range of 
--	    extendDslLineRateInsertionForDhcpv6 from notAdd(1), 
--	    addAlllineParameters(2) to include addActualLineRate(3). The feature 
--	    is not supported in R5.2.01/R5.3 and earlier releases. Will be 
--	    supported in R5.2.02 and from R5.3.01 onwards. Corrected range in 
--	    MIB for extendRemoteIdControl and extendRemoteIdControlPppoe."
--
--  REVISION March 13,2015
--  DESCRIPTION
--         "Version : 3EC37662EBAA_V5.2.0.0.3
--         Editor :  Shiya Ashraf
--         Changes for RCR ALU01958417
--         Removed platform specific descriptions from the MIB for 
--	   extendPortVlanTunlProtoAwareMinCVLAN & extendPortVlanTunlProtoAwareMaxCVLAN"
--
--  REVISION January 9,2015
--  DESCRIPTION
--         "Version : 3EC37662EBAA_V5.2.0.0.2
--         Editor :  Ludwig Pauwels
--         Changes for RCR ALU01936333
--         Update extendPeripheralMgntVlanId applicability."
--  REVISION November 24, 2014
--  DESCRIPTION
--        "Version : 3EC37662ECAA_V5.2.0.0.1
--         Editor :  JAKIR REHMAN SAMSUDEEN
--         Change for RCR ALU01934775 - Port ALU01928640 - control protocol awareness per C-VLAN range 
--            for S-VLAN cross-connect to MS. Two new MIB objects extendPortVlanTunlProtoAwareMinCVLAN(22) 
--            and extendPortVlanTunlProtoAwareMaxCVLAN(23)are added in the extendPortVlanAssociationTable."
--
--  REVISION November 24, 2014
--  DESCRIPTION
--         "Version : 3EC37662ECAA_V5.2.0.0.0
--         Editor :  ANAND AROKIARAJ
--         Changes for RCR ALU01992540 - Changed description of the access loop 
--	   encapsulation related elements to reflect the increased scope - 
--	   DHCPv6 support and support on SX(7367)"
--
--  REVISION November 23,2014
--  DESCRIPTION
--         "Version : 3EC37662EBAA_V5.1.0.0.3
--         Editor :  Rommy Volders
--         Changes for RCR ALU01911020.
--         Update extendPeripheralMgntVlanId applicability."
--
--  REVISION November 7,2014
--    DESCRIPTION
--           "Version : 3EC37662EBAA_V5.1.0.0.2
--           Editor :  ANAND AROKIARAJ
--           Change for FR ALU02019436 - Added a note that 'learned(5) is currently 
--	     not support for extendAccessLoopEncaps1"
--
--  REVISION August 5,2014
--  DESCRIPTION
--        "Version:  3EC37662EBAA_V5.1.0.0.1
--         Editor:   ANAND AROKIARAJ
--         Changes for RCR ALU01877955 - Changed the value definition for the MIB objects   
--              - extendPppoeRelayVlanAware, extendDhcpRelayVlanAware and extendDhcpv6RelayVlanAware
--		  from inherit (3) to systemDefault (3). 
--
--  REVISION Jan 22,2014
--  DESCRIPTION
--        "Version:  3EC37662EAAA_V5.0.1
--         Editor:   JOHN D BOYLE
--         Changes for RCR ALU01876500 - Upstream summary and extensive troubleshooting counters per TC:  
--              - For extendPortVlanPbitTroubleshootTable, changed the policy such ifIndex can ONLY
--		  represent a VLAN. 
--
--  REVISION 201311200000Z
--  DESCRIPTION
--        "Version:  3EC37662EAAA_V5.0.0.0.0
--         Editor:   JOHN D BOYLE
--         Changes for RCR ALU01876500 - Upstream summary and extensive troubleshooting counters per TC:  
--              - Added extendPortVlanPbitTroubleshootTable at ::= { extendStatistics 18  }
--
--  REVISION 201311140000Z
--  DESCRIPTION
--        "Version:  3EC37662EAAA_V5.0.0.0.0
--         Editor:   ANAND AROKIARAJ
--         Changes for RCR ALU01900243:  
--              - Added three new objects to extendVlanStaticTable
--              - extendPppoeRelayVlanAware
--              - extendDhcpRelayVlanAware
--              - extendDhcpv6RelayVlanAware
--
--  REVISION 201311130000Z
--  DESCRIPTION
--        "Version:  3EC37662EAAA_V5.0.0.0.0
--         Editor:   JOHN D BOYLE
--         Changes for RCR ALU01928827 - MIB and database readiness for ALU01908580 
--			(which is titled - Forward C-VID of 4095 transparently - OLT impact):  
--              - Added extendVlanCVlan4095Passthru attribute to extendVlanStaticTable
--  
--  REVISION 201311110000Z
--  DESCRIPTION
--        "Version:  3EC37662EAAA_V5.0.0.0.0
--         Editor:   GAJULA PRADEEP KUMAR
--         Changes for RCR ALU01900245:  
--              - Added five new objects to extendVlanStaticTable
--              - extendPppoeAccessLoopEncap
--              - extendDhcpAccessLoopEncap
--              - extendDhcpv6AccessLoopEncap
--              - extendAccessLoopEncaps1
--              - extendAccessLoopEncaps2
--  
--  REVISION 201209130000Z
--  DESCRIPTION
--        "Version:  3EC37662EAAA_V4.5.0.0.1
--         Editor:   MA Liya
--         Changes for RCR ALU01808189:  
--          - add a new attribute extendVlanSVlanTagPriorityPolicy to the table extendVlanStaticTable    

--  REVISION 201209130000Z
--  DESCRIPTION
--        "Version:  3EC37662EAAA_V4.5.0.0.1
--         Editor:   hua cai
--         Changes for RCR ALU01821150:  
--          - add  plimL2PriorityRegenerationProfileMappingTable and entry   .  
--
--  REVISION 201203150000Z
--  DESCRIPTION
--        "Version:  3EC37662EAAA_V4.4.0.0.0
--         Editor:   Liu Li
--         Changes for RCR ALU00122517:  
--          - Extend extendVlanSecureForwardingControl value from 1,2 to 1,2,3,4,5       .  
--          - Extend extendVlanStaticBroadcastControl value from 1,2 to 1,2,3,4,5
--          - Modify extendVlanMacAgingTime description
--
--  REVISION 201101170000Z
--  DESCRIPTION
--        "Version:  3EC37662EAAA_V4.3.0.0.0
--         Editor:   Udaya Sivadanam
--         Changes:  
--          - Changed plimL2PriorityRegenerationProfileTable to increase the
--       .    table size from 10 to 32 for RCR ALU00886266
--          - Added new object plimL2PriorityRegenerationRefCount to the table
--          - plimL2PriorityRegenerationProfileTable.
--          - Added new object plimPriorityRegenerationProfileGetNextFree"
--
--
--  REVISION 201010250000Z
--  DESCRIPTION
--        "Version:  3EC37662EAAA_V4.3.0.0.0
--         Editor:   hua cai
--         Changes:  
--          - Add extendUniTroubleShootingTable and entry
--
--
--  REVISION 201006020000Z
--  DESCRIPTION
--        "Version:  3EC37662EAAA_V4.2.0.0.0
--         Editor:   Lucien Marcotte
--         Changes:  
--          - Changed range of DSLAMID value to 0..8191 to add
--            support for new vMAC format for PON LTs (ALU00123529).
--          - Removed unused vMAC configuration objects."
--
--
--  REVISION 200912020000Z
--  DESCRIPTION
--        "Version:  3EC37662EAAA_V4.2.0.0.0
--         Editor:   Li Jing
--         Changes:  
--              - Defined a 3rd bit in extendDot1vProtocolVlanGroupId 
--                to add support of a new protocol group IPv6oE.
--              - Added five new objects to extendVlanStaticTable 
--                 -extendInterfaceIdControlDhcpv6
--                 -extendRemoteIdControlDhcpv6 
--                 -extendTrustedPortControlDhcpv6
--                 -extendEnterpriseNumberDhcpv6
--                 -extendSecureFilterIcmpv6"
--              - Add a new object to
--                extendPortVlanTroubleshootingExtensiveTable
--                 -extendPortVlanUpIPv6SpoofingDiscFrameCounter
--
-- DESCRIPTION:
--             "Version: 3EC37662EAAA_V4.1.0.0.4
--             Editor: Johan Hermans
--             Change for ISAM R4.1 RCR ANTms55514
--             Rename object extendPortMgntVlanId to extendPeripheralMgntVlanId"           
--
--  DESCRIPTION:
--           "Version: 3EC37662EAAA_V4.1.0.0.3
--            Editor: Johan Hermans
--             Change for ISAM R4.1 RCR ANTms55514
--             Added object extendPortMgntVlanId " 
--
-- DESCRIPTION: 
--             "Version: 3EC37662EAAA_V4.1.0.0.2 
--             Editor: MA Liya 
--             Change for ISAM R4.1: RCR ANTmt62622 
--             Add a new field extendVlanStaticNoVmacInOpt61 in table 
--             extendVlanStaticTable." 
-- 
--
--   REVISION 200907030000Z
--  DESCRIPTION:
--           "Version: 3EC37662EAAA_V4.1.0.0.1
--            Editor: Geert Vantienen
--            Changes for ISAM R4.1: 
--            Added object extendVlanBcmNetworkVlanId,
--            Added object extendVlanCurBcmNetworkVlanId"
--
--  REVISION 200905190000Z
--  DESCRIPTION:
--           "Version: 3EC37662EAAA_V4.1.0.0.0
--            Editor: Qin zhenshu
--            Change for ISAM R4.1 RCR ANTmt33311
--            comment out tables used for supporting dynamic vlanport"
--
--  REVISION 200902170000Z
--  DESCRIPTION:
--           "Version: 3EC37662EAAA_V4.0.0.1.0
--            Editor: Karel Meijfroidt
--            Merged changes for ISAM R3.7.10: 
--            Added object extendVlanBcmStackingVlanId,
--            Added object extendVlanCurBcmStackingVlanId,
--            Modified object extendVlanMgntVlanId"
-- 
--  REVISION 200805270000Z
--  DESCRIPTION:
--            Version: 3EC37662EAAA_V3.7.0.0.1
--            Editor: Fu Jianhong
--            Changes: Add a new item in extendVlanPortTable in ISAM R3.7

--  REVISION 200803190000Z
--  DESCRIPTION: 
--           Version: 3EC37662EAAA_V3.7.0.0.0
--           Editor: MA Liya
--           Changes:Add a new item in extendVlanStaticTable in ISAM R3.7

--  REVISION 200710230000Z
--  DESCRIPTION
--        "Version:  3EC37662EAAA_V3.6.0.0.0
--         Editor:   Muthu Muthuraman
--         Changes:  Added extendBridgePortFdbTable"
--
--  REVISION 200708270000Z
--  DESCRIPTION
--        "Version:  3EC37662EAAA_V3.6.0.0.0
--         Editor:   MA LiYa
--         Changes:  Add new tables definition for troubleshooting 
--                   counters@user-side feature (RCR BDFhw85005)"

--
--  REVISION 
--  DESCRIPTION
--        "Version:  3EC37662EAAA_V3.5.0.0.1
--         Editor:   Bakri Aboukarr
--         Changes:  Modified vMAC format to resync with R3.4"

--- REVISION 200707040000Z
--  DESCRIPTION
--        "Version:  3EC37662EAAA_V3.5.0.0.0
--         Editor:   Lucien Marcotte
--         Changes:  Modified vMAC format for reuse by CFM OAM"
--
--  Datte: 14/05/07 - Version: 3EC 37660 EAAA E3500
-- Editor: Jia junjie
-- Version 
--   Update Alcatel Note for ISAM R3.5 72p ADSL2+ LT (IFX) feature (RCR ANTms27757)
--
--  REVISION 200606120000Z
--  DESCRIPTION
--        "Version:  3EC37662EAAA_V3.3.0.2.0
--         Editor:   Fu Jianhong
--         Changes:  Document modified for use on the Alcatel iSAM R3.3"
--  
-- =======================================================================

-- PLIM subsystem private defined MIB

IMPORTS
		Gauge, Counter
			FROM RFC1155-SMI
		OBJECT-TYPE
			FROM RFC-1212
		RowStatus, MacAddress
			FROM SNMPv2-TC
		ifIndex
        		FROM ITF-MIB
		dot1dBasePort
			FROM BRIDGE-MIB
		PortList, dot1qFdbId, dot1qVlanIndex, VlanId, VlanIndex, SnmpAdminString,
 		dot1vProtocolTemplateFrameType, dot1vProtocolTemplateProtocolValue, 
		dot1vProtocolPortGroupId
			FROM Q-BRIDGE-MIB
		asam
			FROM SYSTEM-MIB
		NetworkTimeInSeconds
			FROM	 ASAM-TC-MIB
                eqptSlotId 
                        FROM  ASAM-EQUIP-MIB
  AsamProfileRefCount  FROM ASAM-TC-MIB
		AtmVpIdentifier, AtmVcIdentifier
			FROM ATM-TC-MIB
                IpAddress, Gauge
                        FROM RFC1155-SMI
                InetAddress
                        FROM INET-ADDRESS-MIB;

	      --  Unsigned32
	       --      FROM SNMPv2-SMI;

IfIndex ::= INTEGER (1..2147483647)
-- asam OBJECT IDENTIFIER ::= { iso(1) identified-organization(3)
--                             dod(6) internet(1) private(4)
--                             enterprises(1) alcatel(637) asd(61)
--                             asam(1)}

-- ========================================================================
-- Textual Conventions
-- ========================================================================
PriorityBitList ::= OCTET STRING (SIZE(1))
        -- "Bitmap of 8 bits, relating to ExtendVlanSystemPriority.
        -- The MSB relates to priority value 0 (bestEffort),
        -- the LSB to priority value 7 (networkControl)."
 
VlanList ::= OCTET STRING
	-- "Each octet within this value specifies a set of eight
	-- vlans, with the first octet specifying VLAN index 1 through
	-- 8, the second octet specifying VLAN index 9 through 16, etc.
	-- Within each octet, the most significant bit represents
	-- the lowest numbered VLAN index, and the least significant bit
	-- represents the highest numbered VLAN index. Thus, each VLAN index
	-- of the bridge is represented by a single bit within the
	-- value of this object. If that bit has a value of '1'
	-- then that VLAN is included in the set of VLAN indexes; the VLAN
	-- is not included if its bit has a value of '0'."
	-- Note, in PLIM, there are 4095 valid VLAN index from 1 to 4094 and
	-- 4096 is also included. The bit for VLAN 4095 is in the bitlist but
	-- can never have the value of 1.

ExtendInterworkingEvent ::= OCTET STRING
-- "Each octet within this value specifies a set of eight
-- events, with one bit indicating a kind of event."
-- Note, in NBE, there are 6 kinds of events:
--	Bit0:	AAL5 error or FCS error;
	--	Bit1:	incorrect LLC format;
	--	Bit2:	upstream packets discarded due to MAC address could not be learnt;
--   Bit3:   a MAC address learnt from a port is repeated with the address  
--           of other port in the same VLAN domain;
--	Bit4:	new MAC address has been learnt;
	--	Bit5:	a MAC address has been aged out;
--	Bit6,7:	reserved for future use.
	-- One octet can satisfy the number of events in NBE. 
-- ========================================================================
-- Object definitions
-- ========================================================================

plimEthernet		OBJECT IDENTIFIER ::= { asam 31 }

plimSystemObject	OBJECT IDENTIFIER ::= { plimEthernet 1 }

	-- PLIM private system defined objects
--	bandwidthShaping OBJECT-TYPE
--		SYNTAX	INTEGER
--		ACCESS	read-write
--		STATUS	mandatory
--		DESCRIPTION
--			"aggregate traffic shaping bandwidth in the direction from the 
--			Ethernet-ATM interworking function to the ATM function. The 
--			unit is Mbit/s."
--		::= { plimSystemObject 1 }

	numPortsInPortList	OBJECT-TYPE
		SYNTAX	INTEGER
		ACCESS	read-only
		STATUS	mandatory
		DESCRIPTION
			"The object dot1dBaseNumPorts specifies the number of ports
			controlled by the bridging entity. This at the same time 
			determines the size of objects such as the object
			dot1qVlanStaticEgressPorts, more in general the objects of 
			the SYNTAX 'Portlist'. For those entities supporting many 
			Ports this would result in an object of a too big size. 
			The alternative is to split this object in a set of bitlists.
			The object numPortsInPortList identifies the number of 
			Ports in objects of the type 'PortList'.
             ALCATEL NOTE:
                 ACCESS:     NA       USAGE:      NA
                 PERSIST:    NO       INSRVMOD:   NO
                 RANGE:      NA       
                 DEFVALUE:   DEP [depends on the value of dot1dBaseNumPorts]
                 UNITS:      NA       SPARSE:     NA
                 DESCR:      NA"
		::= { plimSystemObject 2 }

--	availablePortsInPortList	OBJECT-TYPE
--		SYNTAX	PortList
--		ACCESS	read-only
--		STATUS	mandatory
--		DESCRIPTION
--			"It specifies which ports are available in the PortList.
--			Each bit represents a port. 1 indicates the corresponding
-- 			port is available (the VCL has been created for use). 0
--			indicates the corresponding port does not exist now."
--		::= { plimSystemObject 3 }

	extendVlanMgntMode OBJECT-TYPE
		SYNTAX	INTEGER
				{
				inband(1),
				outband(2)
				}
		ACCESS	read-only
		STATUS	mandatory
		DESCRIPTION
			"The selection of the management mode of the PLIM.
			In case inband is selected, the extendVlanMgntVlanId shall
			contain a valid	Mgnt VLAN id.
			In case outband is selected, the in-band management path
			is disabled
			The default (initial) value shall be in-band
             ALCATEL NOTE:
                 ACCESS:     NA       USAGE:      NA
                 PERSIST:    NO       INSRVMOD:   NO
                 RANGE:      1,2      DEFVALUE:   1[inband]
                 UNITS:      NA       SPARSE:     NA
                 DESCR:      NA"
		::= { plimSystemObject 4 }

	extendVlanMgntVlanId OBJECT-TYPE
		SYNTAX	INTEGER (0|1..4093)
--		ACCESS	read-only
-- The access is changed to read-write for the iSAM.
		ACCESS	read-write
		STATUS	mandatory
		DESCRIPTION
			"The VLAN-ID referring to the management VLAN.
			The instance of this object only exists when extendVlanMgntMode
			is set to in-band.
                        This object is meaningful when the NE comprises a SHUB or
	                for the 7367 ISAM SX (Stand-Alone Single-board Vectoring Remote Box) or
         	        for the 7363 ISAM MX (Next Generation Vectoring Remote).
                        When the NE comprises an IHUB, the value of this object is zero, 
         indicating 'not applicable'.
             ALCATEL NOTE:
                 ACCESS:     NA       USAGE:      NA
                 PERSIST:    NO       INSRVMOD:   YES
                 RANGE:      DEP| 
                             1-4093 in case of SHUB, 7367 ISAM SX or 7363 ISAM MX, 0 in case of IHUB
                 DEFVALUE:   DEP| 
                             4093 in case of SHUB, 7367 ISAM SX or 7363 ISAM MX, 0 in case of IHUB
                 UNITS:      NA       SPARSE:     NA
                 DESCR:      NA"
		::= { plimSystemObject 5 }

	systemBroadcastControl OBJECT-TYPE
		SYNTAX	INTEGER 
				{
				on (1),
				off (2)
				}
		ACCESS	read-write
		STATUS	mandatory
		DESCRIPTION
			"The object is used to control the downstream broadcast behaviour
			of the system. When it is 'off', all the downstream broadcast
			packets will be discarded for each VLAN domain.
			Note: except for broadcast packets of protocols for which a protocol
			specific behaviour is defined.
             ALCATEL NOTE:
                 ACCESS:     NA       USAGE:      NA
                 PERSIST:    YES      INSRVMOD:   YES
                 RANGE:      1,2      DEFVALUE:   1[on]
                 UNITS:      NA       SPARSE:     NA
                 DESCR:      NA"
		::= { plimSystemObject 6 }

--	cvlanTranslationControl OBJECT-TYPE
--		SYNTAX	INTEGER 
--				{
--				on (1),
--				off (2)
--				}
--		ACCESS	read-write
--		STATUS	mandatory
--		DESCRIPTION
--        "The object is used to control the CVlan translation behaviour
--        of the system
--         When it is off, the system support default ISAM behaviour.
--         When it is on, the system support CVlan translation.
--			The default (initial) value shall be off."
--             ALCATEL NOTE:
--                 ACCESS:     NA       USAGE:      NA
--                 PERSIST:    YES      INSRVMOD:   YES
--                 RANGE:      1,2      DEFVALUE:   2[off]
--                 UNITS:      NA       SPARSE:     NA
--                 DESCR:      NA"
--		::= { plimSystemObject 9 }

-- The following is added for information only.
-- extendVlanInternalVlanId OBJECT-TYPE
--     SYNTAX    VlanId
--     ACCESS    read-only
--     STATUS    mandatory
--     DESCRIPTION
--         "The VLAN-ID referring to the Internal VLAN for NT-SHUB
--          communication and for NT-LT communication.
--          The default value shall be 4094."
--     DEFVAL { 4094 }
--     ::= { plimSystemObject 10 }
--
 
   extendVlanTraceAndDebugVlanId OBJECT-TYPE 
      SYNTAX    INTEGER (0|1..4093)
      ACCESS read-write 
      STATUS mandatory 
      DESCRIPTION 
         "The VLAN-ID referring to the Trace and Debug VLAN for NT-ONT communication. 
          The default value shall be 0 which means no trace and debug VLAN. The 
          valid range shall be from (0..4093).
	  The object is not supported in products of the NGVR family.(7367 ISAM SX / 7363 ISAM MX).
             ALCATEL NOTE:
                 ACCESS:     NA       USAGE:      NA
                 PERSIST:    YES      INSRVMOD:   YES
                 RANGE:      0..4093  DEFVALUE:   0[none]
                 UNITS:      NA       SPARSE:     NA
                 DESCR:      NA"

       DEFVAL { 0 } 
          ::= { plimSystemObject 11 }


        extendVlanBcmStackingVlanId OBJECT-TYPE
            SYNTAX    INTEGER (0|1..4093)
            ACCESS    read-write    
            STATUS    mandatory
            DESCRIPTION   
"The VLAN-ID refers to the VLAN used for communicating between stacked Broadcom switching devices on the NTs. Multiple Broadcom switching devices are stacked or chained to act as one larger device. The stacking VLAN is required to communicate amongst the devices.
In case the value of the object is modified, the system will accept unless this VLAN is already configured for another purpose. When the configuration is accepted, the VLAN ID is reserved and is no longer available for other configurations.
Take care: a modification to this object will only take effect after a system reset has taken place.

This object is introduced in ISAM R3.7.10.
The object is only meaningful in case of an NE with IHUB, where Broadcom switches of one NT or NT-A and NT-B are stacked.
When the NE comprises an SHUB, 7367 ISAM SX or 7363 ISAM MX, the value of this object is zero, indicating not applicable.

             ALCATEL NOTE:
                 ACCESS:     NA       USAGE:      NA
                     PERSIST:    YES      INSRVMOD:   YES 
                     RANGE:      DEP|
                            1-4093 in case of IHUB, 0 in case of SHUB, 7367 ISAM SX or 7363 ISAM MX
                     DEFVALUE:   DEP|     
                            4092 in case of IHUB, 0 in case of SHUB, 7367 ISAM SX or 7363 ISAM MX
                     UNITS:      NA       SPARSE:     NA
                     DESCR:      NA"
        ::= { plimSystemObject 12 }
 
  
        extendVlanCurBcmStackingVlanId OBJECT-TYPE
            SYNTAX    INTEGER (0|1..4093)
            ACCESS    read-only
            STATUS    mandatory
            DESCRIPTION
"The VLAN-ID refers to the VLAN used for communicating between stacked Broadcom switching devices on the NTs.
This object has the same meaning as the extendVlanBcmStackingVlanId, except that it reflects the VLAN which is currently applied.

This object is introduced in ISAM R3.7.10.
The object is only meaningful in case of an NE with IHUB, where Broadcom switches of one NT or NT-A and NT-B are stacked.
When the NE comprises an SHUB, 7367 ISAM SX or 7363 ISAM MX, the value of this object is zero, indicating 'not applicable'.

             ALCATEL NOTE:
                 ACCESS:     NA       USAGE:      NA
                     PERSIST:    YES      INSRVMOD:   NA
                     RANGE:      DEP|
                                 1-4093 in case of IHUB, 0 in case of SHUB, 7367 ISAM SX or 7363 ISAM MX
                     DEFVALUE:   DEP|
                                 4092 in case of IHUB, 0 in case of SHUB, 7367 ISAM SX or 7363 ISAM MX
                     UNITS:      NA       SPARSE:     NA
                     DESCR:      NA"
        ::= { plimSystemObject 16 }

        extendVlanBcmNetworkVlanId OBJECT-TYPE
            SYNTAX    INTEGER (0|1..4093)
            ACCESS    read-write    
            STATUS    mandatory
            DESCRIPTION   
                "The VLAN-ID refers to the VLAN used for internal usage, i.e.
                 handling of packets from network ports at the Broadcom switching
                 device.
                 In case the value of the object is modified, the system will
                 accept unless this VLAN is already configured for another purpose.
                 When the configuration is accepted, the VLAN ID is reserved and is
                 no longer available for other configurations.
                 Take care: a modification to this object will only take effect
                 after a system reset has taken place.

                 This object is introduced in ISAM R4.1
                 The object is only meaningful in case of an NE with IHUB, even if 
                 no ports are used in network mode.
                 When the NE comprises an SHUB, 7367 ISAM SX or 7363 ISAM MX, the value of this object is zero,  
                 indicating not applicable.
                 
                 ALCATEL NOTE:   
                     ACCESS:     NA       USAGE:      NA
                     PERSIST:    YES      INSRVMOD:   YES 
                     RANGE:      DEP|
                            1-4093 in case of IHUB, 0 in case of SHUB, 7367 ISAM SX or 7363 ISAM MX
                     DEFVALUE:   DEP|     
                            4089 in case of IHUB, 0 in case of SHUB, 7367 ISAM SX or 7363 ISAM MX
                     UNITS:      NA       SPARSE:     NA
                     DESCR:      NA"
        ::= { plimSystemObject 17 }
 
  
        extendVlanCurBcmNetworkVlanId OBJECT-TYPE
            SYNTAX    INTEGER (0|1..4093)
            ACCESS    read-only
            STATUS    mandatory
            DESCRIPTION
                "The VLAN-ID refers to the VLAN used for internal handling of
                 packets from network ports at the Broadcom switching device.
                 This object has the same meaning as the
                 extendVlanBcmNetworkVlanId, 
                 except that it reflects the VLAN which is currently applied.
                 The initial value for this object equals the value of object 
                 extendVlanBcmNetworkVlanId.

                 This object is introduced in ISAM R4.1
                 The object is only meaningful in case of an NE with IHUB,even 
                 if no ports are used in network mode.
                 When the NE comprises an SHUB, 7367 ISAM SX or 7363 ISAM MX, the value of this object is zero, 
                 indicating not applicable.
   
                 ALCATEL NOTE:   
                     ACCESS:     NA       USAGE:      NA
                     PERSIST:    YES      INSRVMOD:   NA
                     RANGE:      DEP|
                                 1-4093 in case of IHUB, 0 in case of SHUB, 7367 ISAM SX or 7363 ISAM MX
                     DEFVALUE:   NA
                     UNITS:      NA       SPARSE:     NA
                     DESCR:      NA"
        ::= { plimSystemObject 18 }

        extendPeripheralMgntVlanId OBJECT-TYPE
                SYNTAX        INTEGER (0|1..4093)
                ACCESS        read-write
                STATUS        mandatory
                DESCRIPTION   
                 "The VLAN-ID referring to the Pheripheral management VLAN.
                 ISAM supports dedicated interfaces for the remote management of 
                 co-located 3rd party equipment through Ethernet connections. 
                 In case of FD-REM a 10/100 Base-T electronical interface is 
                 provided on the REM control board NRCD-x. 3rd party equipment can 
                 be connected to this Ethernet port. 
                 This object is the VLAN used for the corresponding management 
                 traffic. The value 0 of this object is indicating not configured. 
                 The object can not be written on systems that do not support a LEMI interface.
           
                 ALCATEL NOTE:
                   ACCESS:    NA      USAGE:      NA
                   PERSIST:   YES     INSRVMOD:   YES
                   RANGE:     0|1-4093| 
                       DEFVALUE:   0           
                       UNITS:      NA       
                   SPARSE:     NA
                   DESCR:      NA"
        ::= { plimSystemObject 19 }

        extendVlanSSMoutVlanId OBJECT-TYPE
              SYNTAX INTEGER (1..4093)
              ACCESS read-write
              STATUS mandatory
              DESCRIPTION     
               " this object allows the operator to reconfigure the internal SSM-VLAN
               from its default value 4088. This internal VLAN is needed between NT - LT 
               SSM-packet forwarding.
               The object is not supported in products of the NGVR family.

              ALCATEL NOTE: Applicable to NTs supporting the Enhanced clock mgmt
                     SUPPORT: YES    INSRVMOD: YES          RANGE: 1..4093
                     PERSIST: YES    DEFVALUE: 4088         UNITS: NA"

               DEFVAL { 4088 }
        ::= { plimSystemObject 20 }
        
        peripheralManagementControl OBJECT-TYPE
                SYNTAX INTEGER {
                        enabled (1),
                        disabled (2)
                }
                ACCESS read-write
                STATUS mandatory
                DESCRIPTION
                "Enable and disable the peripheral management service.
    
                ALCATEL-LUCENT NOTE:
                        SUPPORT: YES
                        PERSIST: YES
                    INSRVMOD: NA
                    RANGE: 1,2
                    DEFVALUE: 2                                                               
                    UNITS: NA"                                                                
                    DEFVAL { disabled }                                                       
                    ::= { plimSystemObject 21 }

         extendVlanUplinkOutbandMgntVlanId OBJECT-TYPE
              SYNTAX  INTEGER (0|1..4093)
              ACCESS  read-write
              STATUS  mandatory
              DESCRIPTION
               "The VLAN-ID referring to the uplink outband management VLAN.
                The instance of this object only exists when extendVlanMgntMode
                is set to in-band.
                The value 0 of this object is indicating not configured.
                This object is meaningful for the 7367 ISAM SX (Stand-Alone Single-board Vectoring Remote Box) 8F/16F/48U which have Spumante based IWF module or for the 7363 ISAM MX (Next Generation Vectoring Remote).
                For the rest case, the value of this object is zero, indicating 'not applicable'.
                               
                ALCATEL NOTE:
                        ACCESS:     NA       USAGE:      NA
                        PERSIST:    YES      INSRVMOD:   YES
                        RANGE:      0|1-4093 
                        DEFVALUE:   0
                        UNITS:      NA       SPARSE:     NA
                        DESCR:      NA"
        ::= { plimSystemObject 22 }

plimExtendVlan	OBJECT IDENTIFIER ::= {plimEthernet 2}

--PLIM extend Vlan group
--	extendVlanSystemMode OBJECT-TYPE
--		SYNTAX	INTEGER
--				{
--				crossconnect(1),
--				residentialBridge(2)
--				}
--		ACCESS	read-write
--		STATUS	mandatory
--		DESCRIPTION
--			"The PLIM can work in either cross-connect mode or
--			residential bridging mode."
--		::= { plimExtendVlan 1 }

	ExtendVlanSystemMode ::=	INTEGER
				{
				crossconnect(1),
				residentialBridge(2),
				qosAware (3),
            layer2terminated (4),
            mirroring (7)
				}

--	extendVlanSystemPriority OBJECT-TYPE
--		SYNTAX	INTEGER
--				{
--				bestEffort (0),
--				background (1),
--				spare (2),
--				excellentEffort (3),
--				controlledLoad (4),
--				videoLessThan100msLatencyAndJitter (5),
--				videoLessThan10msLatencyAndJitter (6),
--				networkControl (7)
--				}
--		ACCESS	read-write
--		STATUS	mandatory
--		DESCRIPTION
--			"The priority to be set in upstream frames sent
--			over the Ethernet interface"
--		::= { plimExtendVlan 2 }

	ExtendVlanSystemPriority ::=	INTEGER
				{
				bestEffort (0),
				background (1),
				spare (2),
				excellentEffort (3),
				controlledLoad (4),
				videoLessThan100msLatencyAndJitter (5),
				videoLessThan10msLatencyAndJitter (6),
				networkControl (7)
				}
	ExtendPortVlanUntagged ::= INTEGER
				{
				untagged (1),
				singletagged (2),
				prioritytagged (3)
				}



	extendVlanCurrentVlanList OBJECT-TYPE
		SYNTAX	VlanList
		ACCESS	read-only
		STATUS	mandatory
		DESCRIPTION
			"The current configured VLAN list in the PLIM. This is
			the set of VLANs for which an entry is available in
			the dot1qVlanStaticTable. A 1 indicates an entry for
			this VLAN exists in the dot1qVlanStaticTable, a 0
			indicates no corresponding entry exists.
			Note: in NBE, the object is only used for Local User VLANs.
			Note: it includes also those VLANs that are reserved for other
			purposes and for which there is no corresponding entry in
			dot1qVlanStaticTable. E.g. the VLAN reserved for inband management 
			in the iSAM.
             ALCATEL NOTE:
                 ACCESS:     NA       USAGE:      NA
                 PERSIST:    YES      INSRVMOD:   NO
                 RANGE:      NA       DEFVALUE:   NA
                 UNITS:      NA       SPARSE:     NA
                 DESCR:      NA"
		::= { plimExtendVlan 3}

-- ========================================================================
-- The Extend Static VLAN Database
-- ========================================================================

	extendVlanStaticTable OBJECT-TYPE
		SYNTAX	SEQUENCE OF ExtendVlanStaticEntry
		ACCESS	not-accessible
		STATUS	mandatory
		DESCRIPTION
			"A table containing configuration information for
			each VLAN configured into the device by (local or
			network) management.
			Note: in NBE, the table is only used for Local User VLANs.
             ALCATEL NOTE:
                 TABLESIZE:  DEP [depends on the value of dot1qVlanCurrentTable]
                 DESCR:      NA"
		::= { plimExtendVlan 4 }

	extendVlanStaticEntry OBJECT-TYPE
		SYNTAX	ExtendVlanStaticEntry
		ACCESS	not-accessible
		STATUS	mandatory
		DESCRIPTION
			"An entry in the extendVlanStaticTable used to augment
 			the table dot1qVlanStaticTable with information common to all Vlans."
		INDEX	{ dot1qVlanIndex }
		::= { extendVlanStaticTable 1 }

	ExtendVlanStaticEntry ::=
		SEQUENCE	{ 
--				extendVlanSetMaskPortList
--					PortList,
--				extendVlanClearMaskPortList
--					PortList,
				extendVlanStaticSystemMode
					ExtendVlanSystemMode,
--				extendVlanStaticCcEgressPort
--					INTEGER,
--				extendVlanStaticPortListId
--					INTEGER,
                                extendVlanStaticName
                                        SnmpAdminString,
                                extendVlanStaticRowStatus
                                        RowStatus,
				extendVlanStaticPriority
					ExtendVlanSystemPriority,
				extendVlanStaticBroadcastControl
					INTEGER,
				extendVlanStaticVersionNbr
					INTEGER,
				extendVlanRemoveAllPorts
					INTEGER,
				extendDot1vProtocolVlanGroupId
					OCTET STRING, 
				extendAddPppoeRelayTag
					INTEGER,
				extendNetworkIfIndex
					INTEGER,
				extendAddDhcpOption82
					INTEGER,
				extendCircuitIdControl
					INTEGER,
				extendRemoteIdControl
					INTEGER,
                                extendDslLineRateInsertionForDhcp
                                        INTEGER,	
                                extendDslLineRateInsertionForPppoe
                                        INTEGER,	
				extendCircuitIdControlPppoe
					INTEGER,
				extendRemoteIdControlPppoe
					INTEGER,
                                extendVlanSecureForwardingControl
					INTEGER,
                                extendVlanMacAgingTime
					INTEGER,
                                extendVlanStaticVirtualMac
                 	                INTEGER,
                                extendVlanStaticVMacSrcAddrDownstBlock
                 	                INTEGER,
                                extendVlanStaticL2CPTransparencyControl 
				        INTEGER,
				extendInterfaceIdControlDhcpv6
					INTEGER,
				extendRemoteIdControlDhcpv6
					INTEGER,
				extendTrustedPortControlDhcpv6
					INTEGER,
                                extendVlanStaticNoVmacInOpt61 
                INTEGER,
				extendEnterpriseNumberDhcpv6
					INTEGER,
				extendSecureFilterIcmpv6
		                        INTEGER,
             extendVlanStaticIPv4McastControl
                INTEGER,
             extendVlanStaticIPv6McastControl
                INTEGER,
             extendVlanStaticMacMcastControl
                INTEGER,
             extendVlanStaticIngressQosTcProfile
                INTEGER,
             extendVlanStaticProtocolControlFlags
                OCTET STRING,
             extendVlanStaticPortsNum
                INTEGER,
             extendVlanUnknownUnicastControl
               INTEGER,
             extendVlanIpAntispoofingEnable
               INTEGER,
	         extendDslLineRateInsertionForDhcpv6
               INTEGER,
             extendVlanSntpProxyEnable
               INTEGER,
             extendVlanPt2PtGemFlooding
               INTEGER,
             extendVlanMacMovementControl
               INTEGER,
             extendVlanSlaacLearningEnable
               INTEGER,
            extendVlanSVlanTagPriorityPolicy
               INTEGER,
            extendPppoeAccessLoopEncap
               INTEGER,
            extendDhcpAccessLoopEncap
               INTEGER,
            extendDhcpv6AccessLoopEncap
               INTEGER,
            extendAccessLoopEncaps1
               INTEGER,
            extendAccessLoopEncaps2
               INTEGER,
            extendPppoeRelayVlanAware
	       	INTEGER,
	    extendDhcpRelayVlanAware
	       	INTEGER,
	    extendDhcpv6RelayVlanAware
		INTEGER,
	    extendVlanVoiceUsage
		INTEGER,
            extendVlanCVlan4095Passthru 
            	INTEGER,
            extendRlySrvAtUsrSide
		INTEGER,
            extendVlanArpSnooping
                INTEGER,
            extendVlanArpPolling
                INTEGER,
            extendVlanArpPollingSrcIpAddress
                IpAddress,
              extendMacAuthDefaultFwd
              INTEGER,   
            extendAddDhcpOption82Nni
                INTEGER,
            extendAddDhcpOption82Uplink
                INTEGER,
            extendRelayIdControl
                INTEGER,
            extendRelayIdControlDhcpv6
 INTEGER
	    }

--	extendVlanSetMaskPortList OBJECT-TYPE
--		SYNTAX	PortList
--		ACCESS	write-only
--		STATUS	mandatory
--		DESCRIPTION
--			"This object has only a meaning in case the object
--			extendVlanStaticSystemMode has the value residentialBridge:
--			it represents the set of ports that should be set as EgressPorts 
--			for this VLAN.
--			A 1 indicates it shall be added, a 0 means no action.
--			Those systems for which the number of ports is small, will support 
--			the object dot1qVlanStaticEgressPorts.
--			Those systems for which the number of ports is large, will split 
--			this EgressPorts info into a set of bitlists supported by the 
--			object extendVlanStaticBrEgressPorts in the table
--			extendVlanStaticBrPortsTable. In that case this
-- 			extendVlanSetMaskPortList is to be used in combination with
--			the object extendVlanStaticPortListId. The last object identifies
--			in combination with the object dot1qVlanIndex the entry in the
--			table extendVlanStaticBrPortsTable on which the -SetMask- applies."
--		::= { extendVlanStaticEntry 1 }

--	extendVlanClearMaskPortList OBJECT-TYPE
--		SYNTAX	PortList
--		ACCESS	write-only
--		STATUS	mandatory
--		DESCRIPTION
--			"This object has only a meaning in case the object
--			extendVlanStaticSystemMode  has the value residentialBridge:
--			it represents the set of ports that should be cleared as EgressPorts 
--			for this VLAN.
--			A 1 indicates it shall be cleared, a 0 means no action.
--			Those systems for which the number of ports is small, will support 
--			the object dot1qVlanStaticEgressPorts.
--			Those systems for which the number of ports is large, will split 
--			this EgressPorts info into a set of bitlists supported by the 
--			object extendVlanStaticBrEgressPorts in the table
--			extendVlanStaticBrPortsTable. In that case this
-- 			extendVlanSetMaskPortList is to be used in combination with
--			the object extendVlanStaticPortListId. The last object identifies
--			in combination with the object dot1qVlanIndex the entry in the
--			table extendVlanStaticBrPortsTable on which the -ClearMask- applies."
--		::= { extendVlanStaticEntry 2 }

	extendVlanStaticSystemMode OBJECT-TYPE
		SYNTAX	ExtendVlanSystemMode
		ACCESS	read-write
		STATUS	mandatory
		DESCRIPTION
			"The Ethernet-ATM interworking function of this VLAN can work 
         in either cross-connect mode, residential bridging mode, QOS aware 
         or 'layer2Terminated' mode. Only cross-connect and residential
         bridging modes are supported in the 7367 ISAM SX / 7363 ISAM MX systems.
             ALCATEL NOTE:
                 ACCESS:     RO       USAGE:      MAND
                 PERSIST:    YES      INSRVMOD:   NO
                 RANGE:   1,2,3,4,7   DEFVALUE:   NA
                 UNITS:      NA       SPARSE:     NA
                 DESCR:      NA"

--		DEFVAL  { crossconnect}		in R5.0.10 for GE-LSM
--		DEFVAL  { residentialBridge }	in NBE
-- 		Conclusion: default value is system specific and not part of the MIB
		::= { extendVlanStaticEntry 3 }
--
--	extendVlanStaticCcEgressPort	OBJECT-TYPE
--		SYNTAX	INTEGER (0..65535)
--		ACCESS	read-write
--		STATUS	mandatory
--		DESCRIPTION
--			"This object has only a meaning in case the object
--			extendVlanStaticSystemMode has the value crossconnect:
--			It is the port number of the ATM PVC port associated to this VLAN.
--			The value 0 is used to indicate that no port is associated
--			to the VLAN."
--		::= { extendVlanStaticEntry 4}
--
--	extendVlanStaticPortListId	OBJECT-TYPE
--		SYNTAX	INTEGER
--		ACCESS	write-only
--		STATUS	mandatory
--		DESCRIPTION
--			"This object has only a meaning in case the object
--			extendVlanStaticSystemMode  has the value residentialBridge:
--			together with the object dot1qVlanIndex it identifies the 
--			entry in the extendVlanStaticBrPortsTable on which the manager
--			wants to perform a configuration action. The configuration 
--			action is determined by the use of the object 
--			extendVlanSetMaskPortList or extendVlanClearMaskPortList in 
--			the same PDU."
--		::= { extendVlanStaticEntry 5}
--
   extendVlanStaticName OBJECT-TYPE
      SYNTAX   SnmpAdminString (SIZE (0..80))
      ACCESS   read-write
      STATUS   mandatory
      DESCRIPTION
         "An administratively assigned string, which may be used
         to identify the VLAN."
      ::= { extendVlanStaticEntry 6 }

      extendVlanStaticRowStatus OBJECT-TYPE
      SYNTAX   RowStatus
      ACCESS  read-write
      STATUS   mandatory
      DESCRIPTION
         "This object indicates the status of this entry."
      ::= { extendVlanStaticEntry 7 }

	extendVlanStaticPriority	OBJECT-TYPE
		SYNTAX	ExtendVlanSystemPriority
		ACCESS	read-write
		STATUS	mandatory
		DESCRIPTION
      "For the untagged frames received over the ATM PVC port identified by
			the VLAN ID and to be sent upstream over the Ethernet 
			interface, this object specifies the Ethernet priority tag to 
			be set only in these untagged frames as default p-bit in 
             case priorityMappingSwitch is set to (1) vlan-id.
             ALCATEL NOTE:
                 ACCESS:     NA       USAGE:      OPT
                 PERSIST:    YES      INSRVMOD:   YES
                 RANGE:      0..7     DEFVALUE:   0[bestEffort]
                 UNITS:      NA       SPARSE:     NA
                 DESCR:      NA"
		::= { extendVlanStaticEntry 8 }

	extendVlanStaticBroadcastControl OBJECT-TYPE
		SYNTAX	INTEGER 
				{
				enableBC(3),
				disableBC(4),
				inherit(5)
				}
		ACCESS	read-write
		STATUS	mandatory
		DESCRIPTION
			"The object is used to control the downstream broadcast behaviour
			of the VLAN. When it is disabled, all the downstream broadcast
			packets of this VLAN domain will be discarded.
			Note: except for broadcast packets of protocols for which a protocol
			specific behaviour is defined.
			When applied to S+C Vlan:
                         (3): downstream broadcast forwarding is enabled on this S+C vlan
                         (4): downstream broadcast forwarding is disabled on this S+C vlan
                         (5): downstream broadcast forwarding behaviour of this S+C vlan is inherited from S vlan level configuration
                        When applied to S Vlan:
                         (3): downstream broadcast forwarding is enabled on this S vlan;It forces downstream broadcast forwarding to be enabled on those affiliated S+C vlans with extendVlanStaticBroadcastControl = (5)
                         (4): downstream broadcast forwarding is disabled on this S vlan;It forces downstream broadcast forwarding to be disabled on those affiliated S+C vlans with extendVlanStaticBroadcastControl = (5)
                         (5): downstream broadcast forwarding behaviour is inherited from the default system value which is disabled;It forces downstream broadcast forwarding to be disabled on those affiliated S+C vlans with extendVlanStaticBroadcastControl = (5)
                        When applied to C Vlan: 
                         (3): downstream broadcast forwarding is enabled on this C vlan
                         (4): downstream broadcast forwarding is disabled on this C vlan
                         (5): downstream broadcast forwarding behaviour is inherited from the default system value which is disabled
                          NOTE: system level downstream broadcast forwarding (NOT systemBroadcastControl ) is fixed to disable.
             ALCATEL NOTE:
                 ACCESS:     NA            USAGE:      OPT
                 PERSIST:    YES           INSRVMOD:   YES
                 RANGE:      3,4,5         DEFVALUE:   5[inherit]
                 UNITS:      NA            SPARSE:     NA
                 DESCR:      NA"
                DEFVAL { inherit }
		::= { extendVlanStaticEntry 9 }

	extendVlanStaticVersionNbr OBJECT-TYPE
		SYNTAX          INTEGER
		ACCESS          read-write
		STATUS          mandatory
		DESCRIPTION     
         "The manager can associate a version number to the VLAN data. 
         It is set to 1 when the VLAN is created and can be incremented 
         by the manager when the VLAN data is modified.
             ALCATEL NOTE:
                 ACCESS:     NA       USAGE:      OPT
                 PERSIST:    YES      INSRVMOD:   YES
                 RANGE:      NA       DEFVALUE:   1
                 UNITS:      NA       SPARSE:     NA
                 DESCR:      NA"
		::= {extendVlanStaticEntry 10}

	extendVlanRemoveAllPorts OBJECT-TYPE
		SYNTAX	INTEGER
				{
				clearAllPorts (0)
				}
		ACCESS	write-only
		STATUS	mandatory
		DESCRIPTION
			"Writing the value clearAllPorts to this object causes the system 
			to remove all port-VLAN associations for this port.
             ALCATEL NOTE:
                 ACCESS:     NA       USAGE:      NA
                 PERSIST:    NO       INSRVMOD:   NA
                 RANGE:      NA       DEFVALUE:   NA
                 UNITS:      NA       SPARSE:     NA
                 DESCR:      NA"
		::= { extendVlanStaticEntry 11 }

	extendDot1vProtocolVlanGroupId OBJECT-TYPE
		SYNTAX	OCTET STRING 
		ACCESS	read-write
		STATUS	mandatory
		DESCRIPTION
			"This filter is applicable on a RB ,CC or Qos aware VLAN.
			If the octet string contains all zeros, no filter is configured 
			(default value) In all other cases, only traffic belonging to a 
			dot1v protocol group of which the corresponding bit is set shall 
			be passed. All other traffic shall be deleted. The mapping of the
			protocol groups is as follows :
                Bit 0:  PPPoE 
                Bit 1:  IPoE		 
                Bit 2:  IPv6oE
                Bit 3 - 7: not used and set to 0
             ALCATEL NOTE:
                 ACCESS:     NA       USAGE:      OPT
                 PERSIST:    YES      INSRVMOD:   YES
                 RANGE:      0...7
                 DEFVALUE:   0        UNITS:      NA
                 SPARSE:     NA       DESCR:      NA"
		DEFVAL { "0" }
		::= { extendVlanStaticEntry 12 }

	extendAddPppoeRelayTag OBJECT-TYPE
	      SYNTAX INTEGER
	      {
       		true(1),
      		false(2),
	  	configurable(3)
      	      }
	      ACCESS	read-write
	      STATUS	mandatory
	      DESCRIPTION
         	  "Setting the object to true enables adding a proprietary relay
		   tag to be added to the PPPoE relayed traffic. 
             	    true(1) 	    means the current fixed format PPPoE tag will 
				    be added.
		    false(2) 	    means no PPPoE tag will be added.
		    configurable(3) means the PPPoE tag will be added with the 
				    format controlled by CircuitIdControlPppoe 
				    and RemoteIdControlPppoe to PPPoE relayed 
				    traffic (PPPoE discovery only).
                    ALCATEL NOTE:
                 	ACCESS:     NA       USAGE:      OPT
                 	PERSIST:    YES      INSRVMOD:   YES
                 	RANGE:      1,2,3    DEFVALUE:   2[false]
                 	UNITS:      NA       SPARSE:     NA
                 	DESCR:      NA"
	      DEFVAL { false }
	      ::= { extendVlanStaticEntry 13 }

	extendNetworkIfIndex OBJECT-TYPE
		SYNTAX  INTEGER 
		ACCESS  read-only
		STATUS  mandatory
		DESCRIPTION
			"This object returns the IfIndex of the IpoE interface at network side
 			of a layer 2 terminated VLAN. This object has no meaning for all other
 			VLAN types and will be set to 0
             ALCATEL NOTE:
                 ACCESS:     NA       USAGE:      NA
                 PERSIST:    YES      INSRVMOD:   NO
                 RANGE:      NA       DEFVALUE:   0
                 UNITS:      NA       SPARSE:     NA
                 DESCR:      NA"
		::= { extendVlanStaticEntry 14 }

	extendAddDhcpOption82 OBJECT-TYPE
		SYNTAX	INTEGER
		{
       		  enable(1),
      		  disable(2),
                  transparent(3),
		  addorreplace(4),
		  addorforward(5)
      		}
		ACCESS	read-write
		STATUS	mandatory
		DESCRIPTION
                "enable - Setting the object to enables enables adding option 82 to the DHCP packets in the upstream direction provided the packet is not having option 82 inserted already  and drops the packets if it has option-82. In downstream direction the option-82 tags are stripped before sending towards subscriber.
                disable- In case of RB forwarder setting the object to disable disables the addition of option-82 to the DCHP packets in the upstream direction and drops the packet if it has already option-82 inserted and in downstream if the packet has option-82 the packet will be dropped. In case of CC forwarder, if the packet already has an option 82,the packet is forwarded unmodified in upstream and downstream. 
                transparent - Setting the object to transparent allows the DHCP packet un modified in both upstream and downstream direction. For a CC forwarder the behaviour is same as setting the object to disable. 
                addorreplace - Setting the object to addorreplace allows ISAM to add DHCP option 82 in upstream direction in case the packet does not contain the option 82 and replace the option 82 when the packet containing option 82. In downstream direction the option 82 tags are stripped before sending towards subscriber. 
                addorforward - Setting the object to addorforward, allows ISAM to add DHCP option 82 in upstream direction in case the packet does not contain the option 82 and forwards when the packet contains option 82. In downstream direction the option 82 tags are stripped before sending towards subscriber, when it is added by the same node or forward as it is. 
 
	     ALCATEL NOTE:
                 ACCESS:     NA       USAGE:      OPT
                 PERSIST:    YES      INSRVMOD:   YES
                 RANGE:      1,2,3,4,5      DEFVALUE:   2[disable]
                 UNITS:      NA       SPARSE:     NA
                 DESCR:      NA"
		DEFVAL { disable }
		::= { extendVlanStaticEntry 15 }

        extendCircuitIdControl OBJECT-TYPE
                SYNTAX INTEGER
                       {
                        notAdd(1),
                        addCustomerId (2),
                        addPhysicalLineId (3),
                        addCcsaFormat (4)
                        }
                ACCESS read-write
                STATUS mandatory
                DESCRIPTION
                        "This object controls what content will be included in the 
                        CirciutId sub option of option 82.The following values are 
                        defined currently:
                        notAdd(1)             CircuitId sub option is not include 
                                              in the option 82.
                        addCustomerId(2)       The CustomerId will be included in 
                                              CircuitId sub option.
                        addPhysicalLineId(3)   A auto-generated PhysicalLineId will 
                                              be included in CircuitId sub option.
                        addCcsaFormat(4)       A auto-generated circuit ID as per 
                                              CCSA format will be included in 
                                              CircuitId sub option.
                        ALCATEL NOTE:
                            ACCESS:     NA       USAGE:      OPT
                            PERSIST:    YES      INSRVMOD:   YES
                            RANGE:      1,2,3,4  DEFVALUE:   1[notAdd]
                            UNITS:      NA       SPARSE:     NA
                            DESCR:      NA"
                DEFVAL { notAdd }
                ::= { extendVlanStaticEntry 16 }

        extendRemoteIdControl OBJECT-TYPE
              SYNTAX INTEGER
              {
              	notAdd(1),
                addCustomerId(2),
                addPhysicalLineId(3)
              }
              ACCESS read-write
              STATUS mandatory
              DESCRIPTION
                  "This object controls what content will be included in the 
                   RemoteId sub option of option 82.The following values are 
                   defined currently:
                        notAdd(1)               RemoteId sub option is not include 
                                                in the option 82.
                        addCustomerId(2)        The CustomerId will be included in 
                                                RemoteId sub option.
                        addPhysicalLineId(3)    An auto-generated PhysicalLineId
                                                be included in RemoteId sub option.
                        ALCATEL NOTE:
                            ACCESS:     NA       USAGE:      OPT
                            PERSIST:    YES      INSRVMOD:   YES
                            RANGE:      1,2,3    DEFVALUE:   1[notAdd]
                            UNITS:      NA       SPARSE:     NA
                            DESCR:      NA"
              DEFVAL { notAdd }
              ::= { extendVlanStaticEntry 17 }

        extendDslLineRateInsertionForDhcp OBJECT-TYPE
           	   SYNTAX	INTEGER
        		   {
               		 notAdd(1),
              		 addActualLineRate(2),
			        addAllLineParameters(3)
                }
        	       ACCESS	read-write
          	   STATUS	mandatory
           	   DESCRIPTION
                        "Setting the object to addActualLineRate or addAllLineParameters enables insertion 
                        of DSL parameters  as suboption of Option82 for Layer2 DHCP 
                        Relay. The following values are defined currently:
                        notAdd(1)              The insertion of DSL line rate will 
                                               be disabled as suboption in the 
                                               option 82.
                        addActualLineRate (2)  The insertion of DSL actual line up and down rate will 
                                               be enabled as suboption in the    
                                               option 82.
			addAllLineParameters (3) The insertion of DSL all line parameters will 
                                               be enabled as suboption in the    
                                               option 82.		       
					       
                        ALCATEL NOTE:
                            ACCESS:     NA       USAGE:      OPT
                            PERSIST:    YES      INSRVMOD:   YES
                            RANGE:      1,2,3    DEFVALUE:   1[notAdd]
                            UNITS:      NA       SPARSE:     NA
                            DESCR:      NA"
        	       DEFVAL { notAdd }
        	       ::= { extendVlanStaticEntry 19 }

        extendDslLineRateInsertionForPppoe OBJECT-TYPE
        	      SYNTAX	INTEGER
        		  {
               		 notAdd (1),
              		 addActualLineRate (2),
              		 addAllLineParameters (3)
              		}
        	      ACCESS	read-write
        	      STATUS	mandatory
        	      DESCRIPTION
                	"Setting the object to addActualLineRate or addAllLineParameters enables insertion of DSL
                 linerate as suboption of the vendor specific tag for PPPoE relay. 
                 The following values are defined currently:
                 notAdd(1)           The insertion of DSL line rate will be 
                                     disabled as suboption in vendor specific tag 
                                     for PPPoE.
                 addActualLineRate (2)  The insertion of DSL actual line up and down rate will be 
                                        enabled as suboption in vendor specific tag 
                                        for PPPoE. 
                 addAllLineParameters (3)  The insertion of DSL all line parameters will be 
                                        enabled as suboption in vendor specific tag 
                                        for PPPoE.                    
                 ALCATEL NOTE:
                     ACCESS:     NA       USAGE:      OPT
                     PERSIST:    YES      INSRVMOD:   YES
                     RANGE:      1,2,3      DEFVALUE:   1[notAdd]
                     UNITS:      NA       SPARSE:     NA
                     DESCR:      NA"
          	DEFVAL { notAdd }
        	    ::= { extendVlanStaticEntry 20 }
        
        extendCircuitIdControlPppoe OBJECT-TYPE
                SYNTAX INTEGER
                       {
                       notAdd(1),
                        addCustomerId (2),
                        addPhysicalLineId (3),
                        addCcsaFormat (4)
                        }
                ACCESS read-write
                STATUS mandatory
                DESCRIPTION
                        "This object controls what content will be included in the 
                        CirciutId sub option for PPPoE relay. The following values 
                        are defined currently:
                        notAdd(1)             CircuitId sub option is not include 
                                              in the option 82.
                        addCustomerId(2)       PPPoE relay will add the customerid 
                                              configured on PVC/DSL line to the 
                                              CircuitId sub-option.
                        addPhysicalLineId(3)   PPPoE relay will add the 
                                               AgentCircuitId string with the 
                                               string generated according to the 
                                               configured 
                                               port numbering method/offset, 
                                               transport classifier and syntax.
                        addCcsaFormat(4)       A auto-generated circuit ID as per 
                                               CCSA format will be included in 
                                               CircuitId sub option.
                        ALCATEL NOTE:
                            ACCESS:     NA       USAGE:      OPT
                            PERSIST:    YES      INSRVMOD:   YES
                            RANGE:      1,2,3,4  DEFVALUE:   1[notAdd]
                            UNITS:      NA       SPARSE:     NA
                            DESCR:      NA"
        
        	        DEFVAL { notAdd }
                ::= { extendVlanStaticEntry 21 }
        
        extendRemoteIdControlPppoe OBJECT-TYPE
              SYNTAX INTEGER
              {
              	notAdd(1),
                addCustomerId(2),
                addPhysicalLineId(3)
              }
                ACCESS read-write
                STATUS mandatory
                DESCRIPTION
                    "This object controls what content will be included in the 
                     RemoteId sub option for PPPoE relay.The following values 
                     are defined currently:
                        notAdd(1)            RemoteId sub-option is not included 
                              		     in the PPPoE Relay Tag.
                        addCustomerId(2)     PPPoE relay will add the customerid 
                                             configured on PVC/DSL line to the 
                                             RemoteId sub-option.
                        addPhysicalLineId(3) PPPoE relay will add an auto-
                                 	     generated PhysicalLineId in 
					     RemoteId sub option.
                        ALCATEL NOTE:
                            ACCESS:     NA       USAGE:      OPT
                            PERSIST:    YES      INSRVMOD:   YES
                            RANGE:      1,2,3    DEFVALUE:   1[notAdd]
                            UNITS:      NA       SPARSE:     NA
                            DESCR:      NA"
                DEFVAL { notAdd }
                ::= { extendVlanStaticEntry 22 }

        extendVlanSecureForwardingControl OBJECT-TYPE
				SYNTAX	INTEGER 
						{
						enableSF(3),
						disableSF(4),
						inherit(5)
						}
				ACCESS	read-write
				STATUS	mandatory
				DESCRIPTION
                                       " This object is used to enable IP anti-spoofing, DHCP session snooping and ARP relay.
				         When applied to S+C Vlan:
                                         (3): secureforwarding is enabled on this S+C vlan
                                         (4): secureforwarding is disabled on this S+C vlan
                                         (5): secureforwarding behaviour of this S+C vlan is inherited from S vlan level configuration.
                                         When applied to S Vlan:
                                         (4): secureforwarding is disabled on this S vlan;It forces secureforwarding to be disabled on those affiliated S+C vlans with extendVlanSecureForwardingControl = (5)
                                         (3): secureforwarding is enabled on this S vlan; It forces secureforwarding to be enabled on those affiliated S+C vlans with extendVlanSecureForwardingControl = (5)
                                         (5): secureforwarding behaviour is inherited from the default system value which is disabled;It forces secureforwarding to be disabled on those affiliated S+C vlans with extendVlanSecureForwardingControl = (5)
                                         When applied to C Vlan: 
                                         (4): secureforwarding is disabled on this C vlan
                                         (3): secureforwarding is enabled on this C vlan
                                         (5): the secureforwarding behaviour is inherited from the default system value which is disabled
                                         NOTE: system level secure forwarding is fixed to disable
                        ALCATEL NOTE:
                            ACCESS:     NA         USAGE:      OPT
                            PERSIST:    YES        INSRVMOD:   YES
                            RANGE:      3,4,5      DEFVALUE:   5[inherit]
                            UNITS:      NA         SPARSE:     NA
                            DESCR:      NA"
                DEFVAL { inherit }
                ::= { extendVlanStaticEntry 31 }

        extendVlanMacAgingTime OBJECT-TYPE
				SYNTAX	INTEGER
				ACCESS	read-write
				STATUS	mandatory
				DESCRIPTION
"This object is used to configure per VLAN Mac aging time 
in seconds. The default value -1 indicates to inherit the value from the higher level.
If -1 is configured on outer VLAN, e.g. S-VLAN or C-VLAN,indicating to inherit system level aging timer
If -1 is configured on S+C VLAN, indicating to inherit S level aging timer.
                        ALCATEL NOTE:
                            ACCESS:     NA       USAGE:      OPT
                            PERSIST:    YES      INSRVMOD:   YES
             RANGE:       -1, 10..1000000       DEFVALUE:   -1
                            UNITS:      seconds  SPARSE:     NA
                            DESCR:      NA"
                DEFVAL { -1 }
                ::= { extendVlanStaticEntry 32 }

          extendVlanStaticVirtualMac OBJECT-TYPE
                SYNTAX  INTEGER
                        {
                        true(1),
                        false(2)
                        }
                ACCESS  read-write
                STATUS  mandatory
                DESCRIPTION
                        "Setting the object to true enables virtual MAC address
        							  translation on a residential bridge or C-VLAN cross-connect or 
         							  SC-VLAN cross-connect mode VLAN.
ALCATEL NOTE:
ACCESS:     NA       USAGE:      OPT
 	PERSIST:    YES      INSRVMOD:   YES
  	RANGE:      1,2      DEFVALUE:   2[false]
 	UNITS:      NA       SPARSE:     NA
 	DESCR:      NA"
                DEFVAL { false }
                ::= { extendVlanStaticEntry 35 }

          extendVlanStaticVMacSrcAddrDownstBlock OBJECT-TYPE
                SYNTAX  INTEGER
                        {
                        true(1),
                        false(2)
                        }
                ACCESS  read-write
                STATUS  mandatory
                DESCRIPTION
                        "Setting the object to true enables the filter in LT . The 
filter will discard any Ethernet packets received from the 
          NT within the VLAN and where the MAC source address matches 
          the signature of the local virtual MAC address format.
ALCATEL NOTE:
ACCESS:     NA       USAGE:      OPT
PERSIST:    YES      INSRVMOD:   YES
   	RANGE:      1,2      DEFVALUE:   2[false]
 	UNITS:      NA       SPARSE:     NA
   	DESCR:      NA"
                DEFVAL { false }	
                ::= { extendVlanStaticEntry 36 }

        extendVlanStaticL2CPTransparencyControl  OBJECT-TYPE
              SYNTAX  INTEGER
                      {
                       enable(1),
                       disable(2)
                       }
              ACCESS  read-write
              STATUS  mandatory
              DESCRIPTION
         "Setting the object to enable means to transparently forward L2CP frames in this VLAN except PAUSE frames. Setting to disable will discard L2CP frames in this VLAN.
              ALCATEL NOTE:
                      ACCESS:     NA       USAGE:      OPT
                      PERSIST:    YES      INSRVMOD:   YES
                      RANGE:      1,2      DEFVALUE:   2[disable]
                      UNITS:      NA       SPARSE:     NA
                      DESCR:      NA"
              DEFVAL { disable }   
                ::= { extendVlanStaticEntry 37 }

   extendInterfaceIdControlDhcpv6 OBJECT-TYPE
      SYNTAX INTEGER
          {
          notAdd(1),
          addCustomerId (2),
          addPhysicalLineId (3),
          addCcsaFormat (4)
          }
      ACCESS read-write
      STATUS mandatory
      DESCRIPTION
         "This object controls what content will be included in the 
         DHCPv6 InterfaceId option (option-18). The following values 
         are currently defined:
         notAdd(1)                InterfaceId option will not be inserted 
                                  in DHCPv6 messages.
         addCustomerId(2)         The CustomerId will be inserted in
                                  InterfaceId option.  
         addPhysicalLineId(3)     A auto-generated PhysicalLineId will be
                                  included in InterfaceId option.
         addCcsaFormat(4)         A auto-generated circuit ID as per CCSA
                                  format will be included in InterfaceId
                                  option.
         ALCATEL NOTE:
             ACCESS:      NA       USAGE:      OPT
             PERSIST:     YES      INSRVMOD:   YES
             RANGE:       1,2,3,4  DEFVALUE:   1 [notAdd]
             UNITS:       NA       SPARSE:     NA
             DESCR:       NA"
      DEFVAL { notAdd }
      ::= { extendVlanStaticEntry 38 }

   extendRemoteIdControlDhcpv6 OBJECT-TYPE
      SYNTAX INTEGER
          {
          notAdd(1),
          addCustomerId(2) ,
          addPhysicalLineId(3)
          }
      ACCESS read-write
      STATUS mandatory
      DESCRIPTION
         "This object controls what content will be included in the
         DHCPv6 RemoteId option (option-37).The following values are
         currently defined:
         notAdd(1)               RemoteId option will not be included 
                                 in the DHCPv6 messages.
         addCustomerId(2)        The CustomerId will be included in 
                                 RemoteId option.
         addPhysicalLineId(3)    An auto-generated PhysicalLineId will 
                                 be included in RemoteId option.
         ALCATEL NOTE:
             ACCESS:     NA       USAGE:      OPT
             PERSIST:    YES      INSRVMOD:   YES
             RANGE:      1,2,3    DEFVALUE:   1[notAdd]
             UNITS:      NA       SPARSE:     NA
             DESCR:      NA"
      DEFVAL { notAdd }
      ::= { extendVlanStaticEntry 39 }

   extendTrustedPortControlDhcpv6 OBJECT-TYPE
	  SYNTAX	INTEGER 
          {
	      trusted (1),
	      untrusted (2)
	      }
	  ACCESS	read-write
	  STATUS	mandatory
	  DESCRIPTION
         "This object is used to configure a port as a DHCPv6 
         trusted port or untrusted port. The DHCPv6 Relay Agent 
         allows Relay-Forward messages received from a 
         client-facing trusted port to pass but discards 
         any Relay-Forward messages received from a 
         client-facing untrusted port. 
         ALCATEL NOTE:
             ACCESS:     NA       USAGE:      OPT
             PERSIST:    YES      INSRVMOD:   YES
             RANGE:      1,2      DEFVALUE:   1[untrusted]
             UNITS:      NA       SPARSE:     NA
             DESCR:      NA"
      DEFVAL { untrusted }
      ::= { extendVlanStaticEntry 40 }

extendVlanStaticNoVmacInOpt61 OBJECT-TYPE
      SYNTAX  INTEGER
         {
         true(1),
         false(2)
         }
      ACCESS  read-write
      STATUS  mandatory
      DESCRIPTION
         "Setting the object to true lets DHCP Option 61 keep the
          genuine user MAC@ even when vMAC is enabled.
          This object will be effective only to the entries 
          on which extendVlanStaticVirtualMac take effect, and 
          will work only when extendVlanStaticVirtualMac is enabled.
       ALCATEL NOTE:
            ACCESS:     NA       USAGE:      OPT
            PERSIST:    YES      INSRVMOD:   YES
            RANGE:      1,2      DEFVALUE:   2[false]
            UNITS:      NA       SPARSE:     NA
            DESCR:      NA"
      DEFVAL { false }
      ::= { extendVlanStaticEntry 41 }

   extendEnterpriseNumberDhcpv6 OBJECT-TYPE
	  SYNTAX	INTEGER (0..4294967295) 
	  ACCESS	read-write
	  STATUS	mandatory
	  DESCRIPTION
         " This parameter is used to specify the vendor's 
         registered Enterprise Number as registered with IANA. 
         ALCATEL NOTE:
             ACCESS:     NA       USAGE:      OPT
             PERSIST:    YES      INSRVMOD:   YES
             RANGE:      NA      DEFVALUE:   3561
             UNITS:      NA       SPARSE:     NA
             DESCR:      NA"
      DEFVAL { 3561 }
      ::= { extendVlanStaticEntry 55 }

   extendSecureFilterIcmpv6 OBJECT-TYPE
	  SYNTAX	INTEGER 
         {
         enable(1),
         disable(2)
         }
	  ACCESS	read-write
	  STATUS	mandatory
	  DESCRIPTION
         " This object is used to enable ICMPv6 secure filtering. 
         ALCATEL NOTE:
             ACCESS:     NA       USAGE:      OPT
             PERSIST:    YES      INSRVMOD:   YES
            RANGE:      1,2      DEFVALUE:   1[disable]
             UNITS:      NA       SPARSE:     NA
             DESCR:      NA"
      DEFVAL { disable }
      ::= { extendVlanStaticEntry 56 }

extendVlanStaticIPv4McastControl OBJECT-TYPE
      SYNTAX  INTEGER
         {
         enable(1),
         disable(2)
         }
      ACCESS  read-write
      STATUS  mandatory
      DESCRIPTION
         "Setting the object to enable means to transparently forward IPV4 multicast frames in this VLAN (multicast addresses not in the multicast tree) in both upstream and downstream directions. Setting the object to disable means to discard IPV4 multicast frames in this VLAN (multicast addresses not in the multicast tree). This setting affects only iBridge VLANs. 
          ALCATEL NOTE:
              ACCESS:     NA       USAGE:      OPT
              PERSIST:    YES      INSRVMOD:   YES
              RANGE:      1,2      DEFVALUE:   2[disable]
              UNITS:      NA       SPARSE:     NA
              DESCR:      NA"
      DEFVAL { disable }   
      ::= { extendVlanStaticEntry 49 }

extendVlanStaticIPv6McastControl OBJECT-TYPE
      SYNTAX  INTEGER
         {
         enable(1),
         disable(2)
         }
      ACCESS  read-write
      STATUS  mandatory
      DESCRIPTION
         "Setting the object to enable means to transparently forward IPV6 multicast frames in this VLAN in both upstream and downstream directions. Setting the object to disable means to discard IPV6 multicast frames in this VLAN. This setting affects only iBridge VLANs. 
          ALCATEL NOTE:
              ACCESS:     NA       USAGE:      OPT
              PERSIST:    YES      INSRVMOD:   YES
              RANGE:      1,2      DEFVALUE:   2[disable]
              UNITS:      NA       SPARSE:     NA
              DESCR:      NA"
      DEFVAL { disable }   
      ::= { extendVlanStaticEntry 50 }

extendVlanStaticMacMcastControl OBJECT-TYPE
      SYNTAX  INTEGER
         {
         enable(1),
         disable(2)
         }
      ACCESS  read-write
      STATUS  mandatory
      DESCRIPTION
         "Setting the object to enable means to transparently forward MAC multicast frames in this VLAN in both upstream and downstream directions (multicast frames that are neither IPV4, IPV6, nor L2CP but Ethernet multicast frames such as CFM). Setting the object to disable means to discard MAC multicast frames in this VLAN. This setting affects only iBridge VLANs. 
          ALCATEL NOTE:
              ACCESS:     NA       USAGE:      OPT
              PERSIST:    YES      INSRVMOD:   YES
              RANGE:      1,2      DEFVALUE:   2[disable]
              UNITS:      NA       SPARSE:     NA
              DESCR:      NA"
      DEFVAL { disable }   
      ::= { extendVlanStaticEntry 51 }

extendVlanStaticIngressQosTcProfile OBJECT-TYPE
      SYNTAX  INTEGER
      ACCESS  read-write
      STATUS  mandatory
      DESCRIPTION
         "It defines a pointer to the Ingress Qos Profile that maps pbits to TCs on a per forwarder basis. The Ingress QoS Profile exists in the QoS MIB.
          ALCATEL NOTE:
              ACCESS:     NA       USAGE:      OPT
              PERSIST:    YES      INSRVMOD:   YES
              RANGE:      1..32    DEFVALUE:   1
              UNITS:      NA       SPARSE:     NA
              DESCR:      NA"
      DEFVAL { 1 }   
      ::= { extendVlanStaticEntry 52 }

extendVlanStaticProtocolControlFlags OBJECT-TYPE
      SYNTAX  OCTET STRING (SIZE (2))
      ACCESS  read-write
      STATUS  mandatory
      DESCRIPTION
         "Protocol control bitmap that indicates whether a particular protocol has to be transparent in both upstream and downstream directions or not (if flooding of multicast or broadcast is disabled via the above flags). Rightnow RIP and NTP are supported. By default RIPV4 is enabled for forwarding. The bit map is 
<unused> <unused> <unused> <unused> <unused> <unused> <unused> <unused> <unused> <unused> <unused> <unused> <unused> <unused> <NTP> <RIP-V4> with RIP-V4 being the LSB of the octets.
          ALCATEL NOTE:
              ACCESS:     NA       USAGE:      OPT
              PERSIST:    YES      INSRVMOD:   YES
              RANGE:      0000 - FFFF      DEFVALUE:   0001
              UNITS:      NA       SPARSE:     NA
              DESCR:      NA"
      ::= { extendVlanStaticEntry 53 }

extendVlanStaticPortsNum OBJECT-TYPE
      SYNTAX  INTEGER
      ACCESS  read-only
      STATUS  mandatory
      DESCRIPTION
         "The number of ports that are attached on one specific Vlan.
          ALCATEL NOTE:
              ACCESS:     RO      USAGE:      NA
              PERSIST:    NO      INSRVMOD:  NO
              RANGE:     NA       DEFVALUE: NA  
              UNITS:      NA       SPARSE:     NA
              DESCR:      NA"                   
        ::= {extendVlanStaticEntry 54}

extendVlanUnknownUnicastControl OBJECT-TYPE
                       SYNTAX  INTEGER
                        {
                          enable (1),
                          disable(2)
                        }
                       ACCESS  read-write
                       STATUS  mandatory
                       DESCRIPTION
                          "Decide whether to flood unknown unicast to ONT or not
                       ALCATEL NOTE:
                           ACCESS:     NA      USAGE:      NA
                           PERSIST:    NO      INSRVMOD:  NO
                           RANGE:     1..2       DEFVALUE: 2(disable)  
                           UNITS:      NA       SPARSE:     NA
                           DESCR:      NA"                   
                       ::= {extendVlanStaticEntry 58}

   extendVlanIpAntispoofingEnable OBJECT-TYPE
         SYNTAX   INTEGER 
         {
           disable(1),
           enable (2)
         }
         ACCESS   read-write
         STATUS   mandatory
         DESCRIPTION
	     "This object is used to control if IP anti-spoofing is enable when 
	      extendVlanSecureForwardingControl is enable.
              ALCATEL NOTE:
             	ACCESS:     NA       USAGE:      OPT
             	PERSIST:    YES      INSRVMOD:   YES
             	RANGE:      1,2      DEFVALUE:   2[enable]
             	UNITS:      NA       SPARSE:     NA
             	DESCR:      NA"
         DEFVAL { enable }
         ::= { extendVlanStaticEntry 59 }

   extendDslLineRateInsertionForDhcpv6 OBJECT-TYPE
         SYNTAX   INTEGER
         {
           notAdd(1),
           addAllLineParameters(2),
	   addActualLineRate(3)
         }
        ACCESS   read-write
        STATUS   mandatory
        DESCRIPTION
            "Setting the object to addAlllineParameters enables insertion of 
	     DSL all line parameters  as suboption of Option17 for Layer2 
	     DHCPv6 Relay. The following values are defined currently:
         	notAdd(1)         	The insertion of DSL line parameters 
					will be disabled as suboption in the 
                      			option 17.
         	addAllLineParameters(2) The insertion of DSL all line 
					parameters will be enabled as 
					suboption in the option 17.
		addActualLineRate(3)	The insertion of DSL actual line up and 
					down rates as suboption in option 17
					will be enabled.
             ALCATEL NOTE:
             	ACCESS:     NA       USAGE:      OPT
             	PERSIST:    YES      INSRVMOD:   YES
             	RANGE:      1,2,3    DEFVALUE:   1[notAdd]
             	UNITS:      NA       SPARSE:     NA
             	DESCR:      NA"
        DEFVAL { notAdd }
        ::= { extendVlanStaticEntry 60 }

   extendVlanSntpProxyEnable OBJECT-TYPE
    SYNTAX  INTEGER
        {
         enabled(1),
         disabled(2)
        }
    ACCESS  read-write
    STATUS  mandatory
    DESCRIPTION
        "Enable SNTP proxy feature on a VLAN. Default value is Disabled
         
         ALCATEL NOTE:
             ACCESS:     NA       USAGE:      OPT
             PERSIST:    YES      INSRVMOD:   YES
             RANGE:      1,2      DEFVALUE:   2[disable]
             UNITS:      NA       SPARSE:     NA
             DESCR:      NA"
    DEFVAL  { disabled }
        ::= { extendVlanStaticEntry 61 }  


   extendVlanPt2PtGemFlooding OBJECT-TYPE
    SYNTAX  INTEGER
        {
         enabled(1),
         disabled(2)
        }  
    ACCESS  read-write
    STATUS  mandatory
    DESCRIPTION
        "This object is to explicitly configure the downstream flooding behavior in GPON OLT: using incidental GEM port or pt-to-pt GEM port.
        Enable:  replicate the downstream flooding traffic to every pt-to-pt GEM port in the forwarder. The replication times will be equal to the vlan.ports number in the forwarder.
        Disable: replicate the downstream flooding traffic to incidental GEM port N times with every different CVLAN, which will be used in ONU.
        Default value is Disabled
         
         ALCATEL NOTE:
             ACCESS:     NA       USAGE:      OPT
             PERSIST:    YES      INSRVMOD:   YES
             RANGE:      1,2      DEFVALUE:   2[disable]
             UNITS:      NA       SPARSE:     NA
             DESCR:      NA"
    DEFVAL  { disabled }
        ::= { extendVlanStaticEntry 68 } 
    
    extendVlanMacMovementControl OBJECT-TYPE
      SYNTAX  INTEGER
         {
         enable(1),
         disable(2)
         }
      ACCESS  read-write
      STATUS  mandatory
      DESCRIPTION
         "This object is used to enable or disable MAC address movement in forwarder.When it is enabled, the MAC address could be moved from one port to another port in the same forwarder without duplicate MAC alarm.  
	  This parameter is not applicable to the uplinks of the 7367 ISAM SX and 7363 ISAM MX for which MAC @ movement is unconditionally allowed on Uplinks without causing MAC@ duplicate alarms.  
          ALCATEL NOTE:
              ACCESS:     NA       USAGE:      OPT
              PERSIST:    YES      INSRVMOD:   YES
              RANGE:      1,2      DEFVALUE:   2[disable]
              UNITS:      NA       SPARSE:     NA
              DESCR:      NA"
      DEFVAL { disable }   
      ::= { extendVlanStaticEntry 69 } 

extendVlanSlaacLearningEnable OBJECT-TYPE
       SYNTAX   INTEGER 
        {
        disable(1),
        enable (2)
        }
       ACCESS   read-write
       STATUS   mandatory
       DESCRIPTION
" This object is used to control if SLAAC learning is enabled when extendVlanSecureForwardingControl is enable.
         ALCATEL NOTE:
             ACCESS:     NA       USAGE:      OPT
             PERSIST:    YES      INSRVMOD:   YES
             RANGE:      1,2      DEFVALUE:   2[enable]
             UNITS:      NA       SPARSE:     NA
             DESCR:      NA"
      DEFVAL { enable }
      ::= { extendVlanStaticEntry 70 }    

  

extendVlanSVlanTagPriorityPolicy OBJECT-TYPE
      SYNTAX  INTEGER
      {
         default(1),
         set(2),
         copy(3)
      }
      ACCESS  read-write
      STATUS  mandatory
      DESCRIPTION
         "This object is used to define the pbit  marking behaviour in S VLAN tag 
          in upstream direction. This attribute is no meaningful for a C-VLAN and 
          the value should always be 'default'. 

          'default' indicates to keep the pbit marking behaviour on S VLAN tag for
           backward compabitlity.  
          'set' indicates to mark the pbit  in the S VLAN tag with the configuration 
          of 'extendVlanStaticPriority'.
          'copy' indicates to copy remarked C-VLAN tag Pbit to S-VLAN tag Pbit.

          ALCATEL NOTE:
              ACCESS:     NA       USAGE:      OPT
              PERSIST:    YES      INSRVMOD:   YES
              RANGE:      1,2,3    DEFVALUE:   1[default]
              UNITS:      NA       SPARSE:     NA
              DESCR:      NA"
      DEFVAL { default }   
      ::= { extendVlanStaticEntry 71 }

extendPppoeAccessLoopEncap OBJECT-TYPE
      SYNTAX  INTEGER
      {
         notAdd(1),
         add(2)
      }
      ACCESS read-write
      STATUS mandatory
      DESCRIPTION
         "This object controls the inclusion of Access loop encapsulation sub-
	  option in PPPoE Relay Tag.The following values are defined currently:
           notAdd(1)    Access loop encapsulation sub-option is not                          
                        included in the PPPoE Relay Tag.
           add(2)    	Add the access loop encapsulation sub option as part
                       	of the PPPOE Relay Tag (vendor specific tag).                        
          ALCATEL NOTE:
              ACCESS:     NA       USAGE:      OPT
              PERSIST:    YES      INSRVMOD:   YES
              RANGE:      1,2      DEFVALUE:   1
              UNITS:      NA       SPARSE:     NA
              DESCR:      This attribute is not supported in R5.0. 
			  It is supported on 7363 (MX) from R5.1.01 
			  onwards and on 7367 (SX) from R5.2 onwards"
      DEFVAL { notAdd }
      ::= { extendVlanStaticEntry 72 }

extendDhcpAccessLoopEncap OBJECT-TYPE
      SYNTAX  INTEGER
      {
         notAdd(1),
         add(2)
      }
      ACCESS read-write
      STATUS mandatory
      DESCRIPTION
         "This object controls the inclusion of Access loop enacapsulation sub-
	  option part of DHCP option 82 vendor specific tag sub option.The 
	  following values are defined currently:
           notAdd(1) 	Access loop encapsulation sub-option is not                          
                       	included in the DHCP option 82 vendor specific sub option.
           add(2)       Add the access loop encapsulation sub option as part
                       	of the DHCP option 82 vendor specific sub option.                    
          ALCATEL NOTE:
              ACCESS:     NA       USAGE:      OPT
              PERSIST:    YES      INSRVMOD:   YES
              RANGE:      1,2      DEFVALUE:   1
              UNITS:      NA       SPARSE:     NA
              DESCR:      This attribute is not supported in R5.0. 
	 		  It is supported on 7363 (MX) from R5.1.01 
			  onwards and on 7367 (SX) from R5.2 onwards"
      DEFVAL { notAdd }
      ::= { extendVlanStaticEntry 73 }

extendDhcpv6AccessLoopEncap OBJECT-TYPE
      SYNTAX  INTEGER
      {
         notAdd(1),
         add(2)
      }
      ACCESS read-write
      STATUS mandatory
      DESCRIPTION
         "This object controls the inclusion of Access loop enacapsulation sub-
	  option for DHCPV6 option 17 sub option.The following values are 
	  defined currently:
           notAdd(1)  	Access loop encapsulation sub-option is not                          
                       	included in the DHCPV6 option 17 sub option.
           add(2)       Add the access loop encapsulation sub option as part
                        of the DHCPV6 option 17 sub option.
          ALCATEL NOTE:
              ACCESS:     NA       USAGE:      OPT
              PERSIST:    YES      INSRVMOD:   YES
              RANGE:      1,2      DEFVALUE:   1
              UNITS:      NA       SPARSE:     NA
              DESCR:      This attribute is not supported in R5.0 and R5.1. 
			  It is supported on 7363(MX) and 7367(SX) from R5.2 
			  onwards."
      DEFVAL { notAdd }
      ::= { extendVlanStaticEntry 74 }

extendAccessLoopEncaps1 OBJECT-TYPE
      SYNTAX  INTEGER
      {
         notApplicable(1),
         untagged(2),
         singleTagged(3),
         dualTagged(4),
         learned(5)
      }
      ACCESS read-write
      STATUS mandatory
      DESCRIPTION
         "This object controls the enacapsulation1 overhead on the Access
          loop.The following values are defined currently:
           notApplicable(1)     Not applicable
           untagged(2)  	encaps1 value represents untag traffic
           singleTagged(3) 	encaps1 value represents single tagged traffic
           dualTagged(4)	encaps1 value represents dual tagged traffic
           learned(5)     	encaps1 value is learned form the configuration
          ALCATEL NOTE:
              ACCESS:     NA           USAGE:      OPT
              PERSIST:    YES          INSRVMOD:   YES
              RANGE:      1,2,3,4,5    DEFVALUE:   1
              UNITS:      NA           SPARSE:     NA
              DESCR:      This attribute is not supported in R5.0. 
			  It is supported on 7363 (MX) from R5.1.01 
			  onwards and on 7367 (SX) from R5.2 onwards.
 			  Learned(5) option is currently not supported."
      DEFVAL { notApplicable }
      ::= { extendVlanStaticEntry 75 }

extendAccessLoopEncaps2 OBJECT-TYPE
      SYNTAX  INTEGER
      {
         notApplicable(1),
         learned(2)
      }
      ACCESS read-write
      STATUS mandatory
      DESCRIPTION
         "This object controls enacapsulation2 overhead on the Access loop.
          The following values are defined currently:
           notApplicable(1) 	encaps2 value is not applicable                                  
           learned(2)       	encaps2 value is learned from the
                           	configuration or auto learned.
          ALCATEL NOTE:
              ACCESS:     NA       USAGE:      OPT
              PERSIST:    YES      INSRVMOD:   YES
              RANGE:      1,2      DEFVALUE:   1
              UNITS:      NA       SPARSE:     NA
              DESCR:      This attribute is currently not supported. 
			  Will be supported in later releases."
      DEFVAL { notApplicable }
      ::= { extendVlanStaticEntry 76 }
     
extendPppoeRelayVlanAware OBJECT-TYPE
        SYNTAX INTEGER
        {
            upto1UserVlan (1),
            upto2UserVlans(2),
	    systemDefault (3),
            upto0UserVlan (4)
        }
        ACCESS read-write
        STATUS mandatory
        DESCRIPTION
	   "This object controls the VLAN tag awareness of the PPPoE relay agent.
	    The following values are currently defined:
	    upto1UserVlan (1)	PPPoE relay agent will accept packets with 
				upto 1 VLAN tag from the user                                                       
	    upto2UserVlans (2)	PPPoE relay agent will accept packets with 
				upto 2 VLAN tags from the user
	    systemDefault (3)	The number of VLAN tags that the PPPoE relay agent
				will accept from the user depends on the forwarder 
				type and the board type. The system default value 
				for each forwarder type and board type will be 
				available in the user manual.  
	    upto0UserVlan (4)	PPPoE relay agent will ONLY  accept packets with 
				upto untag from the user     
	    ALCATEL NOTE:
             	ACCESS:     NA       USAGE:      OPT
             	PERSIST:    YES      INSRVMOD:   YES
             	RANGE:      1,2,3,4  DEFVALUE:   3 [systemDefault]
             	UNITS:      NA       SPARSE:     NA
             	DESCR:      This attribute is not supported in R5.0. 
			    It is only supported from R5.1.01 onwards
			    This attribute(1,2,3) is only applicable  for MX. upto0UserVlan apply for S+C tunnel on fglt-b, fwlt-a fwlt-b"
         DEFVAL { systemDefault }
      ::= { extendVlanStaticEntry 82 }

extendDhcpRelayVlanAware OBJECT-TYPE
        SYNTAX INTEGER
        {
            upto1UserVlan (1),
            upto2UserVlans(2),
	    systemDefault (3),
	    upto0UserVlan (4)
        }
        ACCESS read-write
        STATUS mandatory
        DESCRIPTION
           "This object controls the VLAN tag awareness of the DHCP relay agent.
	    The following values are currently defined:
	    upto1UserVlan (1)	DHCP relay agent will accept packets with 
				upto 1 VLAN tag from the user 
	    upto2UserVlans (2)	DHCP relay agent will accept packets with 
				upto 2 VLAN tags from the user
	    systemDefault (3)	The number of VLAN tags that the DHCP relay agent
				will accept from the user depends on the forwarder 
				type and the board type. The system default value 
				for each forwarder type and board type will be 
				available in the user manual.  
	    upto0UserVlan (4)	DHCP relay agent will ONLY  accept packets with 
				upto untag from the user
  	 ALCATEL NOTE:
             ACCESS:     NA       USAGE:      OPT
             PERSIST:    YES      INSRVMOD:   YES
             RANGE:      1,2,3,4  DEFVALUE:   3 [systemDefault]
             UNITS:      NA       SPARSE:     NA
             DESCR:      This attribute is not supported in R5.0. 
			 It is only supported from R5.1.01 onwards
			 This attribute(1,2,3) is applicable only for MX. upto0UserVlan apply for S+C tunnel on fglt-b, fwlt-a fwlt-b"
         DEFVAL { systemDefault }
      ::= { extendVlanStaticEntry 83 }

extendDhcpv6RelayVlanAware OBJECT-TYPE
        SYNTAX INTEGER
        {
            upto1UserVlan (1),
            upto2UserVlans(2),
	    systemDefault (3),
	    upto0UserVlan (4)
        }
        ACCESS read-write
        STATUS mandatory
        DESCRIPTION
	   "This object controls the VLAN tag awareness of the DHCPv6 relay agent. 
	    The following values are currently defined:
	    upto1UserVlan (1)	DHCPv6 relay agent will accept packets with 
				upto 1 VLAN tag from the user                                                               
	    upto2UserVlans (2)	DHCPv6 relay agent will accept packets with 
				upto 2 VLAN tags from the user
	    systemDefault (3)	The number of VLAN tags that the DHCPv6 relay agent 
				will accept from the user depends on the forwarder 
				type and the board type. The system default value 
				for each forwarder type and board type will be 
				available in the user manual.  
	    upto0UserVlan (4)	DHCPv6 relay agent will ONLY  accept packets with 
				upto untag from the user
  	 ALCATEL NOTE:
             ACCESS:     NA       USAGE:      OPT
             PERSIST:    YES      INSRVMOD:   YES
             RANGE:      1,2,3,4    DEFVALUE:   3 [systemDefault]
             UNITS:      NA       SPARSE:     NA
             DESCR:      This attribute is not supported in R5.0 and R5.1. 
			 Will be supported in later releases."
         DEFVAL { systemDefault }
      ::= { extendVlanStaticEntry 84 }

extendVlanVoiceUsage OBJECT-TYPE
       SYNTAX   INTEGER
        {
         enabled(1),
         disabled(2)
        }
       ACCESS   read-write
       STATUS   mandatory
       DESCRIPTION
" This object is used to control whether the VLAN is used by voice.
        Enable:  the VLAN is used by voice.
        Disable: the VLAN isn't used by voice.
        Default value is Disabled
         ALCATEL NOTE:
             ACCESS:     NA       USAGE:      OPT
             PERSIST:    YES      INSRVMOD:   YES
             RANGE:      1,2      DEFVALUE:   2[disable]
             UNITS:      NA       SPARSE:     NA
             DESCR:      NA"
      DEFVAL { disabled }
      ::= { extendVlanStaticEntry 85 }

extendVlanCVlan4095Passthru OBJECT-TYPE
       SYNTAX   INTEGER
        {
         passThru(1),
         notApplicable(2)
        }
       ACCESS   read-write
       STATUS   mandatory
       DESCRIPTION
" This object is used specify CVLAN 4095 tunneling behavior for SVLANCC Forwarder.
  This object is only relevant for forwarders attached to GPON boards
        passThru:  Allow passthru of cvlan 4095 (TR156-Compliance)
        notApplicable: Legacy behavior, cvlan 4095 tag will be dropped by ONT.
        Default value is notApplicable
         ALCATEL NOTE:
             ACCESS:     NA       USAGE:      OPT
             PERSIST:    YES      INSRVMOD:   YES
             RANGE:      1,2      DEFVALUE:   2[notApplicable]
             UNITS:      NA       SPARSE:     NA
             DESCR:      NA"
      DEFVAL { notApplicable }
      ::= { extendVlanStaticEntry 86 }

extendRlySrvAtUsrSide OBJECT-TYPE
       SYNTAX   INTEGER
        {
         enabled(1),
         disabled(2)
        }
       ACCESS   read-write
       STATUS   mandatory
       DESCRIPTION
         "This object is used to control the transparency of DHCPv4/v6 Server at the user side and DHCPv4/v6 client at the server side when Option-82 for DHCPv4 or Option 17 for DHCPv6 is enabled. When enabled, DHCPv4 and DHCPv6 Server packets from the user side and the vice versa packets are transparently forwarded.This is applicable only for Cross connect forwarders.This cannot be enabled along with Secure forwarding and vMAC translation. Setting to disabled means transparency of DHCPv4/v6 server at the user side is disabled as a result legacy behaviour is retained.
         ALCATEL NOTE:
             ACCESS:     NA       USAGE:      OPT
             PERSIST:    YES      INSRVMOD:   YES
             RANGE:      1,2      DEFVALUE:   2[Disabled]
             UNITS:      NA       SPARSE:     NA
             DESCR:      NA"
      DEFVAL { disabled }
      ::= { extendVlanStaticEntry 87 }

      extendVlanArpSnooping OBJECT-TYPE
      SYNTAX  INTEGER
         {
         enabled(1),
         disabled(2)
         }
      ACCESS  read-write
      STATUS  mandatory
      DESCRIPTION
         "This object is used to enable ARP snooping, If extendVlanArpSnooping is enabled, ARP snooping will snoop downstream ARP reply packet and establish the ARP snooping table. 
          ALCATEL NOTE:
              ACCESS:     NA       USAGE:      OPT
              PERSIST:    YES      INSRVMOD:   YES
              RANGE:      1,2      DEFVALUE:   2[disabled]
              UNITS:      NA       SPARSE:     NA
              DESCR:      NA"
      DEFVAL { disabled }   
      ::= { extendVlanStaticEntry 88 }

extendVlanArpPolling OBJECT-TYPE
      SYNTAX  INTEGER
         {
         enabled(1),
         disabled(2)
         }
      ACCESS  read-write
      STATUS  mandatory
      DESCRIPTION
         "This object is used to enable ARP polling, If extendVlanArpPolling is enabled, ARP polling will poll DHCP sessions and static users and ARP snooping table to send ARP request downstream. 
          ALCATEL NOTE:
              ACCESS:     NA       USAGE:      OPT
              PERSIST:    YES      INSRVMOD:   YES
              RANGE:      1,2      DEFVALUE:   2[disabled]
              UNITS:      NA       SPARSE:     NA
              DESCR:      NA"
      DEFVAL { disabled }   
      ::= { extendVlanStaticEntry 89 }


extendVlanArpPollingSrcIpAddress	OBJECT-TYPE
      SYNTAX  IpAddress
      ACCESS  read-write
      STATUS  mandatory
      DESCRIPTION 
          "This object is used to configure src IP in ARP request packet.    
           ALCATEL NOTE:
                ACCESS:      RW            USAGE:       OPT
                PERSIST:     YES           INSRVMOD:    NO
                RANGE:       NA            DEFVALUE:    0
                UNITS:       NA            SPARSE:      NA
                DESCR:       NA"
        DEFVAL { '00000000'H }
	::= { extendVlanStaticEntry 90 }
	
extendMacAuthDefaultFwd OBJECT-TYPE
        SYNTAX  INTEGER { enabled(1),  disabled(2)       }
        ACCESS   read-write
        STATUS   mandatory
        DESCRIPTION "This command can be accessed by operators to attach default forwarding to this VLAN when mac-auth-enabled.
                      This attribute can not be modified after vlan is creation.
        ALCATEL NOTE:             ACCESS:     NA       USAGE:      OPT
                                 PERSIST:    YES      INSRVMOD:   YES
                                 RANGE:      1,2      DEFVALUE:   2[Disabled]
                                 UNITS:      NA       SPARSE:     NA
                                 DESCR:      NA"
        DEFVAL { disabled }
    ::= { extendVlanStaticEntry 91 }

extendAddDhcpOption82Nni OBJECT-TYPE
      SYNTAX  INTEGER
      { 
        enable(1),
        disable(2),
        transparent(3),     
        addorreplace(4),
        addorforward(5)
      }
     ACCESS  read-write
     STATUS  mandatory
     DESCRIPTION
        " enable(1)  		- Setting the object to enable, enables adding option 82 to the DHCP Client generated packet types provided the packet which is not having option 82 inserted already is received on a NNI interface, if option 82 inserted already, then the packets will be dropped.
         disable(2) 		- Setting the object to disable, disables addition and removal of option-82 in the upstream and downstream respectively. Packets will be forwarded.
         transparent(3)	- Setting the object to transparent, forwards the packet transparently as received. 
         addorreplace(4)	- Setting the object to addorreplace, enables adding option 82 to the DHCP Client generated packets provided the packet which is not having option 82 inserted already is received on a NNI interface and replace the packets if it already has option-82.
         addorforward(5) 	- Setting the object to addorforward, enables adding option 82 to the DHCP Client generated packets provided the packet which is not having option 82 inserted already is received on a NNI interface and forwards the packets if it already has option-82. Similarly for DHCP Server generated packet types,option-82 tags are stripped before sending towards NNI, if it was added by the RA. 
        When nni is considered as Trusted Ports, The client generated packet will be forwarded for Enable/Disable/Transparent/Addorreplace options irrespective of option82 inserted.
        
           ALCATEL NOTE:  
                ACCESS:     NA        USAGE:      OPT
                PERSIST:    YES       INSRVMOD:   YES
                RANGE:      1,2,3,4,5 DEFVALUE:   2[disable]
                UNITS:      NA        SPARSE:     NA
                DESCR:      NA"
       DEFVAL { disable }
       ::= { extendVlanStaticEntry 92 } 

extendAddDhcpOption82Uplink OBJECT-TYPE
      SYNTAX  INTEGER
      { 
         enable(1),
         disable(2),
         transparent(3),     
         addorreplace(4),
         addorforward(5)
      }
     ACCESS  read-write
     STATUS  mandatory
     DESCRIPTION
        "enable(1)  		- Setting the object to enable, enables adding option 82 to the DHCP Client generated packets provided the packet which is not having option 82 inserted already is received on a Uplink interface
         disable(2) 		- Setting the object to disable, disables addition and removal of option-82 in the upstream and downstream respectively. Packets will be forwarded.
         transparent(3)	- Setting the object to transparent, forwards the packet transparently as received. 
         addorreplace(4)	- Setting the object to addorreplace, enables adding option 82 to the DHCP Client generated packets provided the packet which is not having option 82 inserted already is received on a Uplink interface and replace the packets if it already has option-82.
         addorforward(5) 	- Setting the object to addorforward, enables adding option 82 to the DHCP Client generated packets provided the packet which is not having option 82 inserted already is received on a Uplink interface and forwards the packets if it already has option-82. Similarly for DHCP Server generated packet types, option-82 tags are stripped before sending towards Uplink, if it was added by the RA. 
        When Uplink is considered as Trusted Ports, The client generated packet will be forwarded for Enable/Disable/Transparent/Addorreplace options irrespective of option82 inserted.

           ALCATEL NOTE:  
                ACCESS:     NA        USAGE:      OPT
                PERSIST:    YES       INSRVMOD:   YES
                RANGE:      1,2,3,4,5 DEFVALUE:   2[disable]
                UNITS:      NA        SPARSE:     NA
                DESCR:      NA"
       DEFVAL { disable }
       ::= { extendVlanStaticEntry 93 } 

   extendRelayIdControl OBJECT-TYPE
      SYNTAX INTEGER
      {
        notAdd (1),
        addRelayId (2)
      }
      ACCESS read-write
      STATUS mandatory
      DESCRIPTION
         "This object included the content as per the relay id syntax in the 
         RelayId sub option of option-82. The following values are 
         defined currently:
         notAdd(1)              RelayId sub option is not included
                                in the dhcp-option82.
         addRelayId(2)          RelayId sub option will be included in   
                                the dhcp-option82.

         ALCATEL NOTE:
             ACCESS:     NA       USAGE:      OPT
             PERSIST:    YES      INSRVMOD:   YES
             RANGE:      1,2      DEFVALUE:   1[notAdd]
             UNITS:      NA       SPARSE:     NA
             DESCR:      NA"
      DEFVAL { notAdd }
      ::= { extendVlanStaticEntry 94 }

extendRelayIdControlDhcpv6 OBJECT-TYPE
       SYNTAX INTEGER
       {
         notAdd(1),
         addDuidLl(2)
       }
      ACCESS read-write
      STATUS mandatory
      DESCRIPTION
         "notAdd(1)    - Setting the object to disable, disables addition and removal of option-53 in the upstream and downstream respectively. Packets will be forwarded.
          addDuidLl(2) - Setting the object to addDuidLl, enables adding two octet network hardware type code, followed by the link-layer address to the DHCPv6 Client generated packet received as option-53. In downstream direction the option-53 tags are stripped before sending towards client, if it was added by the same node. 

           ALCATEL NOTE:  
             ACCESS:      NA       USAGE:      OPT
             PERSIST:     YES      INSRVMOD:   YES
             RANGE:       1,2      DEFVALUE:   1 [notAdd]
             UNITS:       NA       SPARSE:     NA
             DESCR:       NA"
      DEFVAL { notAdd }
      ::= { extendVlanStaticEntry 95 } 
-- ========================================================================
-- The Extend VLAN Port Database
-- ========================================================================
	extendVlanPortTable OBJECT-TYPE
		SYNTAX	SEQUENCE OF ExtendVlanPortEntry
		ACCESS	not-accessible
		STATUS	mandatory
		DESCRIPTION
			"A table containing port configuration information as an 
			extension to the table dot1qPortVlanTable.
             ALCATEL NOTE:
                 TABLESIZE:  DEP [depends on the value of dot1dBaseNumPorts]
                 DESCR:      NA"
		::= { plimExtendVlan 5 }

	extendVlanPortEntry OBJECT-TYPE
		SYNTAX	ExtendVlanPortEntry
		ACCESS	not-accessible
		STATUS	mandatory
		DESCRIPTION
			"The extended information for a port."
		INDEX	{ dot1dBasePort }
		::= { extendVlanPortTable 1 }

	ExtendVlanPortEntry ::=
		SEQUENCE	{
--				extendVlanPortVlanList
--					VlanList,
				extendVlanPortDefaultPriority
					ExtendVlanSystemPriority,
				extendVlanPortMaxNumMacAddresses
					Gauge,
				extendVlanPortAcceptableFrameTypes
					INTEGER,
--				extendVlanPortFirstFilterId
--					Gauge,
				extendVlanPortSelfLearnAdminStatus
					INTEGER,
--				extend8021XDemoAdminStatus
--					INTEGER,
				extendVlanPortIfIndex
					INTEGER,
				extendVlanPortQosProfile
					INTEGER,
				extendVlanPortPriorityRegenerationProfile
					INTEGER,
--				extendVlanPortCVlanTagMode
--				INTEGER,
--				extendVlanPortSVlanTagMode
--				INTEGER
            extendVlanPortMirroringMode
               INTEGER,
            extendVlanPortMirroringVlanId
               INTEGER,
                                extendVlanPortCommittedMaxNumMacAddresses
                                        Gauge,
             extendVlanPortPVIDTaggingFlag 
               INTEGER,
             extendVlanPortTPIDList                                            
               OCTET STRING (SIZE (8)),
             extendVlanPortDSPbitMode 
               INTEGER
				}

--	extendVlanPortVlanList OBJECT-TYPE
--		SYNTAX	VlanList
--		ACCESS	read-only
--		STATUS	mandatory 
--		DESCRIPTION
--			"The configured set of VLAN for the port. The bit
--			having the value 1 means that the VLAN is supported by
--			this port, the bit having the value 0 means that the
--			VLAN is not supported by this port. This information
--			is another presentation of the information in the table
--			dot1qVlanStaticTable in the object
--			dot1qVlanStaticEgressPorts (or proprietary redefined objects).
--			This object has a meaning for all the ports.
--      Note: in NBE,only the VLANs of Local User VLAN will be in the list.
--			And in first phase, only one VLAN can be listed."
--		::= { extendVlanPortEntry 1 }

	extendVlanPortDefaultPriority OBJECT-TYPE
		SYNTAX	ExtendVlanSystemPriority
		ACCESS	read-write
		STATUS	mandatory
		DESCRIPTION
		"For the frames, received over the bridge port (e.g.ATM 
                 PVC,EFM,..)identified by the dot1dBasePort and to be sent upstream 
                 over the Ethernet interface, this object specifies the Ethernet 
                 priority tag to be set in these frames in case a (port dependent) 
                 default value is to be used.
                 This object is only applicable to UNTAGGED traffic.
             ALCATEL NOTE:
                 ACCESS:     NA       USAGE:      OPT
                 PERSIST:    YES      INSRVMOD:   YES
                 RANGE:      0..7     DEFVALUE:   0[bestEffort]
                 UNITS:      NA       SPARSE:     NA
                 DESCR:      NA"
		::= { extendVlanPortEntry 2 }

	extendVlanPortMaxNumMacAddresses OBJECT-TYPE
		SYNTAX	Gauge
		ACCESS	read-write
		STATUS	mandatory
		DESCRIPTION
         "The uncommitted maximum number of unicast MAC addresses on the
         port, i.e. the maximum for the sum of the dynamic learned and the
         static configured unicast MAC addresses.
	        ALCATEL NOTE:
                 ACCESS:     NA       USAGE:      OPT
                 PERSIST:    YES      INSRVMOD:   YES
                 RANGE:      DEP [For BCM LIM only value between 1 and 16 
                             with step 1 and value between 20 and 64 with 
                             step 4 can be set; for Infineon LT, any value 
                             from 1 to 63 can be set;for IXP LIM any value 
                             from 1 to 256 can be set; for CATAN LIM UNI 
                             ports any value from 1 to 512 can be set; for 
                             CATE LT any value from 1 to 64 can be set, for
                             CATAN NNI port any value from 1 to 3072 can be
                             set; For GPON LT range is from 1..128; For 
                             FPLT-A LT, any value from 1 to 8192 can be set;
                             For FELT-B NNI ports any value from 1 to 65535
                             can be set]
                  DEFVALUE:   1        UNITS:      NA       
                  SPARSE:     NA       DESCR:      NA"
		::= { extendVlanPortEntry 3 }

	extendVlanPortAcceptableFrameTypes OBJECT-TYPE
		SYNTAX	INTEGER {
--				admitAll (1) ,
				admitOnlyVlanTagged (2),
				admitOnlyVlanUntagged (3),
--				admitOnlyDoubleVlanTagged (4),
				admitVlanTaggedAndUntaggedMixture (5)
	            	}
		ACCESS	read-write
		STATUS	mandatory
		DESCRIPTION
			"When admitAll(1), untagged frames or Priority-Tagged 
			frames received on this port will be accepted and assigned 
         to the default VLAN for this port. VLAN-tagged and double VLAN 
         tagged frames (if supported) are accepted too.
			When this is admitOnlyVlanTagged(2) the device will discard 
             untagged frames or Priority-Tagged frames
			received on this port. VLAN-tagged are accepted.
			When this is admitOnlyVlanUntagged(3), the untagged frames or 
			Priority-Tagged frames received on this port will be accepted 
			and assigned to the default VLAN for this port. VLAN-tagged frames 
			are discarded.
			When this is admitOnlyDoubleVlanTagged(4),only frame with double VLAN 
                        tag can be accepted, other frame types will be discarded.
                        When this is admitOnlyVlanUntagged(5), both the untagged 
                        frames/Priority-Tagged frames received on this port will be 
                        accepted Double VLAN-tagged frames will be discarded.
--			This control does not affect VLAN independent BPDU
--			frames, such as GVRP and STP.  It does affect VLAN
--			dependent BPDU frames, such as GMRP.
             ALCATEL NOTE:
                 ACCESS:     NA       USAGE:      OPT
                 PERSIST:    YES      INSRVMOD:   YES
                 RANGE:      2,3,5    DEFVALUE:   3[admitOnlyVlanUntagged]
                 UNITS:      NA       SPARSE:     NA
                 DESCR:      NA"
	        DEFVAL      { admitOnlyVlanUntagged  }
	        ::= { extendVlanPortEntry 4 }

--	extendVlanPortFirstFilterId OBJECT-TYPE
--		SYNTAX	Gauge
--		ACCESS	read-only
--		STATUS	mandatory
--		DESCRIPTION
--			"The first filter ID in the VLAN+MAC filter table. "
--		::= { extendVlanPortEntry 5 }

	extendVlanPortSelfLearnAdminStatus OBJECT-TYPE
		SYNTAX  INTEGER {
				up(1),
				down(2)
				}
		ACCESS  read-write
		STATUS  mandatory
		DESCRIPTION
			"This object specifies the desired administrative state of the
			self learning process of MAC addresses. The up state indicates
			that MAC addresses shall be learned, the down state indicates
			that MAC addresses shall not be learned on that port.
             ALCATEL NOTE:
                 ACCESS:     NA       USAGE:      OPT
                 PERSIST:    YES      INSRVMOD:   YES
                 RANGE:      1,2      DEFVALUE:   1[up]
                 UNITS:      NA       SPARSE:     NA
                 DESCR:      NA"
		::= { extendVlanPortEntry 6 }

--	extend8021XDemoAdminStatus	OBJECT-TYPE
--		SYNTAX  INTEGER {
--				up(1),
--				down(2)
--				}
--		ACCESS  read-write
--		STATUS  mandatory
--		DESCRIPTION
--			"This object specifies the desired administrative state of the
--			use of 802.1X on this port. The up state indicates the
--			protocol will be supported, the down state indicates
--			that the protocol will not be supported.
--			Note: supporting the protocol as a demo in the iSAM results in
--			performing MAC based	authentication on a central place."
--		DEFVAL  { down }
--		::= { extendVlanPortEntry 7 }

	extendVlanPortIfIndex OBJECT-TYPE
		SYNTAX  INTEGER 
		ACCESS  read-only
		STATUS  mandatory
		DESCRIPTION
			"This object returns the IfIndex of a dot1dBasePort
             ALCATEL NOTE:
                 ACCESS:     NA       USAGE:      NA
                 PERSIST:    NO       INSRVMOD:   NO
                 RANGE:      NA       DEFVALUE:   NA
                 UNITS:      NA       SPARSE:     NA
                 DESCR:      NA"
		::= { extendVlanPortEntry 8 }

	extendVlanPortQosProfile OBJECT-TYPE
		SYNTAX  INTEGER
		ACCESS  read-write
		STATUS  mandatory
		DESCRIPTION
			"The QOS profile assigned to a port by QOS management. 
			A value of 0 means no QOS profile is allocated
             ALCATEL NOTE:
                 ACCESS:     NA       USAGE:      OPT
                 PERSIST:    YES      INSRVMOD:   YES
                 RANGE:      NA       DEFVALUE:   0
                 UNITS:      NA       SPARSE:     NA
                 DESCR:      NA"
		DEFVAL { 0 }
		::= { extendVlanPortEntry 9 }

	extendVlanPortPriorityRegenerationProfile OBJECT-TYPE
		SYNTAX  INTEGER
		ACCESS  read-write
		STATUS  mandatory
		DESCRIPTION
			"The Priority regeneration profile assigned to a port. The default
         value is 0, meaning no priority bit regeneration profile is
         applied on the port. DSL interfaces can use profiles 1..10.
         GPON interfaces can use profiles 1..32.
             ALCATEL NOTE:
                 ACCESS:     NA       USAGE:      OPT
                 PERSIST:    YES      INSRVMOD:   YES
                 RANGE:      NA       DEFVALUE:   0 
                 UNITS:      NA       SPARSE:     NA
                 DESCR:      NA"
		DEFVAL { 0 }
		::= { extendVlanPortEntry 10 }

--	extendVlanPortCVlanTagMode OBJECT-TYPE
--		SYNTAX	INTEGER
--				{
--				disabled (1),
--				enabled (2)
--				}
--		ACCESS	read-write
--		STATUS	mandatory
--		DESCRIPTION
--			"If enabled, indicates that the port supports C-VLAN tags."
--		DEFVAL { disabled }
--		::= { extendVlanPortEntry 11 }

--	extendVlanPortSVlanTagMode OBJECT-TYPE
--		SYNTAX	INTEGER
--				{
--				disabled (1),
--				enabled (2)
--				}
--		ACCESS	read-write
--		STATUS	mandatory
--		DESCRIPTION
--			"If enabled, indicates that the port supports S-VLAN tags."
--		DEFVAL { disabled }
--		::= { extendVlanPortEntry 12 }

   extendVlanPortMirroringMode OBJECT-TYPE 
      SYNTAX INTEGER 
      { 
         disabled (1), 
         insertNewEthernetHeader (2),
         insertVlanTagOnly (3),
         overwriteOuterVlanTag (4)
      } 
      ACCESS read-write 
      STATUS mandatory 
      DESCRIPTION 
      "Indicates the flow mirroring mode of the bridgeport. It is disabled by default. Flow mirroring can be enabled in 3 modes: In mode 2, a completely new Ethernet Header is added to the mirrored packets. The VLAN-ID and Dest MAC address are configured in the objects given below this object. In mode 3, only a new VLAN tag is inserted, which is configured in extendVlanPortMirroringVlanId. In mode 4, a the outer VLAN tag is overwitten with the mirror VLAN tag.  Only values 1 and 4 are supported on GLTs.
             ALCATEL NOTE:
                 ACCESS:     NA       USAGE:      OPT
                 PERSIST:    YES      INSRVMOD:   YES
                 RANGE:      1..4       DEFVALUE:   1
                 UNITS:      NA       SPARSE:     NA
                 DESCR:      NA
" 
      DEFVAL { disabled } 
      ::= { extendVlanPortEntry 13 }


   extendVlanPortMirroringVlanId OBJECT-TYPE 
      SYNTAX INTEGER (0..4093) 
      ACCESS read-write 
      STATUS mandatory 
      DESCRIPTION 
      "Indicates the VLAN ID to be inserted into  mirrored packets if bridgeport mirroring is enabled on this bridgeport. 
             ALCATEL NOTE:
                 ACCESS:     NA       USAGE:      OPT
                 PERSIST:    YES      INSRVMOD:   YES
                 RANGE:      0..4093  DEFVALUE:   0
                 UNITS:      NA       SPARSE:     NA
                 DESCR:      NA " 
      DEFVAL { 0 } 
      ::= { extendVlanPortEntry 14 }

        extendVlanPortCommittedMaxNumMacAddresses OBJECT-TYPE
                SYNTAX   Gauge
                ACCESS   read-write
                STATUS   mandatory
                DESCRIPTION
                       "The committed maximum number of unicast MAC addresses on the 
                        port, i.e. the committed maximum for the sum of the dynamic 
                        learned and the static configured unicast MAC addresses. This 
                        value should be equal to or less than the value of 
                        extendVlanPortMaxNumMacAddresses.Default value is 65535, which 
                        means it has the same value as extendVlanPortMaxNumMacAddresses.
                ALCATEL NOTE:
                        ACCESS:     NA       USAGE:      OPT
                        PERSIST:    YES      INSRVMOD:   YES
                        RANGE:      0..128,65535.[For BCM LT, only value between 1 
                                    and 16 with step 1 and value between 20 and 64 
                                    with step 4, or the default value 65535 can be 
                                    set.]    
                        DEFVALUE:   65535    UNITS:      NA       
                        SPARSE:     NA       DESCR:      NA"
                   ::= { extendVlanPortEntry 38 }
                                      
        extendVlanPortPVIDTaggingFlag OBJECT-TYPE
                SYNTAX INTEGER 
                { 
                   onu (1), 
                   olt (2)
                }                 
                ACCESS   read-write
                STATUS   mandatory
                DESCRIPTION
                        "	Indicates the tagging behavior of untagged frames in GPON:
                         When ONU (1)
                             upstream untag frame: PVID is tagged in ONU; downstream: transmission mode of PVID corresponding vlan.port is handled in ONU.
                         When OLT (2)
                             onu forwards the untag frame transparently, the PVID tagging and corresponding transmission mode will be handled in OLT.
                         Default = 1 = ONU.
                        
                ALCATEL NOTE:
                        ACCESS:     NA       USAGE:      OPT
                        PERSIST:    YES      INSRVMOD:   YES
                        RANGE:      1..2     DEFVALUE:   1
                        UNITS:      NA       SPARSE:     NA
                        DESCR:      NA"
                   ::= { extendVlanPortEntry 51 }
        extendVlanPortTPIDList OBJECT-TYPE 
                SYNTAX OCTET STRING (SIZE (8)) 
                ACCESS read-write 
                STATUS mandatory 
                DESCRIPTION 
                        "Indicates the TPID list on this bridgeport.The mapping of the
			                   TPID list is as follows(must be Hex) :
                         Byte 0 - 1:  TPID1 (default value is hex 8100, byte0:00, byte1:81) 
                         Byte 2 - 3:  TPID2 (default value is 0)		 
                         Byte 4 - 7:  not used and set to 0 
                ALCATEL NOTE:
                        ACCESS:     NA       USAGE:      OPT
                        PERSIST:    YES      INSRVMOD:   YES
                        RANGE:      600...ffff    DEFVALUE:   8100
                        UNITS:      NA       SPARSE:     NA
                        DESCR:      NA " 
                DEFVAL { "" } 
                ::= { extendVlanPortEntry 53 }

        extendVlanPortDSPbitMode  OBJECT-TYPE
                SYNTAX INTEGER
                {
                  auto (1),
                  translated (2),
                  transparency (3)
                }
                ACCESS    read-write
                STATUS    mandatory
                DESCRIPTION
                        " This object specifies if the P-bit should be translated or not in downstream.
                        auto : legacy behavior, for DSL, auto means transparency while for GPON, auto means translated.
                        translated : for matched p-bits the inverse translation is performed in downstream; unmatched p-bits are forwarded unchanged in downstream.
                        transparency : all p-bits are forwarded unchanged in downstream.
                        Attribute was first introduced as of ISAM5.5 MIB, with targeted implementation in ISAM5.5.01.
                ALCATEL NOTE:
                        ACCESS:     NA       USAGE:      OPT
                        PERSIST:    YES      INSRVMOD:   YES
                        RANGE:      1,2,3    DEFVALUE:   1 [auto] 
                        UNITS:      NA       SPARSE:     NA
                        DESCR:      NA"
                DEFVAL { auto }
                ::= {extendVlanPortEntry 54 }

-- ========================================================================
-- The Extend Port Table
-- ========================================================================
--
--	extendPortTable OBJECT-TYPE
--		SYNTAX	SEQUENCE OF ExtendPortEntry
--		ACCESS	not-accessible
--		STATUS	mandatory
--		DESCRIPTION
--			"A table containing parameters to be used at the ATM layer
--			of the ATM based ports of the Ethernet-ATM interworking 
--			function. One entry is available per ATM PVC port."
--		::= { plimExtendVlan 6 }

--	extendPortEntry OBJECT-TYPE
--		SYNTAX	ExtendPortEntry
--		ACCESS	not-accessible
--		STATUS	mandatory
--		DESCRIPTION
--			"An entry in the extendPortTable. One entry contains the 
--			ATM parameters for one ATM PVC port."
--		INDEX	{ dot1dBasePort }
--		::= { extendPortTable 1 }

--	ExtendPortEntry ::=
--		SEQUENCE	{
--				extendPortAtmTrafficDescrType
--					OBJECT IDENTIFIER,
--				extendPortAtmTrafficDescrParam1
--					INTEGER (-2147483648..2147483647),
--				extendPortAtmTrafficDescrParam2
--					INTEGER (-2147483648..2147483647),
--				extendPortAtmTrafficDescrParam3
--					INTEGER (-2147483648..2147483647),
--				extendPortAtmTrafficDescrParam4
--					INTEGER (-2147483648..2147483647),
--				extendPortAtmTrafficDescrParam5
--					INTEGER (-2147483648..2147483647),
--				extendPortAtmServiceCategory
--					AtmServiceCategory
--				}

--	extendPortAtmTrafficDescrType OBJECT-TYPE
--		SYNTAX  OBJECT IDENTIFIER
--		ACCESS  read-write
--		STATUS  mandatory
--		DESCRIPTION
--			"This object is similar to an object defined in the ATM-MIB
--			in the ASAM Core. The value of this object identifies the type of ATM 
--			traffic descriptor.
--			The type may indicate no traffic descriptor or
--			traffic descriptor with one or more parameters.
--			These parameters are specified as a parameter
--			vector, in the corresponding instances of the
--			objects:
--				extendPortAtmTrafficDescrParam1
--				extendPortAtmTrafficDescrParam2
--				extendPortAtmTrafficDescrParam3
--				extendPortAtmTrafficDescrParam4
--				extendPortAtmTrafficDescrParam5." 
--		::= { extendPortEntry 1 }

--	extendPortAtmTrafficDescrParam1 OBJECT-TYPE
--		SYNTAX  INTEGER (-2147483648..2147483647)
--		ACCESS  read-write
--		STATUS  mandatory
--		DESCRIPTION
--			"The first parameter of the ATM traffic descriptor
--			used according to the value of atmTrafficDescrType."
--		DEFVAL  { 0 }
--		::= { extendPortEntry 2 }

--	extendPortAtmTrafficDescrParam2 OBJECT-TYPE
--		SYNTAX  INTEGER (-2147483648..2147483647)
--		ACCESS  read-write
--		STATUS  mandatory
--		DESCRIPTION
--			"The second parameter of the ATM traffic descriptor
--			used according to the value of atmTrafficDescrType."
--		DEFVAL  { 0 }
--		::= { extendPortEntry 3 }

--	extendPortAtmTrafficDescrParam3 OBJECT-TYPE
--		SYNTAX  INTEGER (-2147483648..2147483647)
--		ACCESS  read-write
--		STATUS  mandatory
--		DESCRIPTION
--			"The third parameter of the ATM traffic descriptor
--			used according to the value of atmTrafficDescrType."
--		DEFVAL  { 0 }
--		::= { extendPortEntry 4 }

--	extendPortAtmTrafficDescrParam4 OBJECT-TYPE
--		SYNTAX  INTEGER (-2147483648..2147483647)
--		ACCESS  read-write
--		STATUS  mandatory
--		DESCRIPTION
--			"The fourth parameter of the ATM traffic descriptor
--			used according to the value of atmTrafficDescrType."
--		DEFVAL  { 0 }
--		::= { extendPortEntry 5 }

--	extendPortAtmTrafficDescrParam5 OBJECT-TYPE
--		SYNTAX  INTEGER (-2147483648..2147483647)
--		ACCESS  read-write
--		STATUS  mandatory
--		DESCRIPTION
--			"The fifth parameter of the ATM traffic descriptor
--			used according to the value of atmTrafficDescrType."
--		DEFVAL  { 0 }
--		::= { extendPortEntry 6 }

--	extendPortAtmServiceCategory	OBJECT-TYPE
--		SYNTAX	AtmServiceCategory
--		ACCESS	read-write
--		STATUS	mandatory
--		DESCRIPTION
--			"The ATM service category."
--		::= { extendPortEntry 7 }

-- ========================================================================

	extendMaxSupportedBrVlans OBJECT-TYPE
		SYNTAX	Gauge
		ACCESS	read-only
		STATUS	mandatory
		DESCRIPTION
			"This object identifies the maximum number of VLans that can
			be in the mode residentialBridge.
             ALCATEL NOTE:
                 ACCESS:     NA       USAGE:      NA
                 PERSIST:    NO       INSRVMOD:   NO
                 RANGE:      NA       DEFVALUE:   768
                 UNITS:      NA       SPARSE:     NA
                 DESCR:      NA"
		::= { plimExtendVlan 7}

	extendVlanCurrentVlanBridgeList OBJECT-TYPE
		SYNTAX	VlanList
		ACCESS	read-only
		STATUS	mandatory
		DESCRIPTION
			"The VLAN list currently configured with the mode residential 
			Bridge. This is the set of Vlans configured in the 
			extendVlanStaticTable for which the object 
			extendVlanStaticSystemMode has the value residentialBridge. 
			A 1 indicates an entry for this VLAN exists and is 
			configured with the residential bridge mode, a 0 indicates 
			no corresponding entry exists or it is configured in the 
			crossconnect or layer2Terminated mode. 
             ALCATEL NOTE:
                 ACCESS:     NA       USAGE:      NA
                 PERSIST:    NO       INSRVMOD:   NO
                 RANGE:      NA       DEFVALUE:   all '0'
                 UNITS:      NA       SPARSE:     NA
                 DESCR:      NA"
		::= { plimExtendVlan 8}

-- ======================================================================== 

--	extendVlanStaticBrPortsTable OBJECT-TYPE
--		SYNTAX	SEQUENCE OF ExtendVlanStaticBrPortsEntry
--		ACCESS	not-accessible
--		STATUS	mandatory
--		DESCRIPTION
--			"A table that augments the table dot1qVlanStaticTable for 
--			those Vlans that are in (residential) bridge mode with
--			information on the egress ports.
--             ALCATEL NOTE:
--               TABLESIZE:  [depends on the value of 
--             extendMaxSupportedBrVlans*((max bridge ports number of system+32) /(400*8) +1).]
--                 DESCR:   The max bridge ports number of system depends on dot1dBaseNumPorts ."
--	::= { plimExtendVlan 9 }

--	extendVlanStaticBrPortsEntry OBJECT-TYPE
--		SYNTAX	ExtendVlanStaticBrPortsEntry
--		ACCESS	not-accessible
--		STATUS	mandatory
--		DESCRIPTION
--			"An entry in the table extendVlanStaticBrPortsTable. A Vlan
--			in the residentialBridge mode can potentially support all
--			ports of the system. The system can support a large
--			number of ports. In order to improve  management efficiency,
--			the number of ports that can be managed in one object is 
--			limited. The number of ports that can be managed in one object 
--			is presented in the object numPortsInPortList. If the number of 
--			ports supported by the system (inclusive the number of ports for
--			which the port number is reserved for future use) is larger than 
--			the numPortsInPortList, then this total number of ports is split 
--			into sublists.
--			For each Vlan in residentialBridge mode, one entry can exist in
--			this table per such sublist. In case one or more ports of the
--			sublist are associated to the VLAN, then the corresponding
--			entry shall exist. In case none of the ports of the sublist
--			are associated to the VLAN, then the corresponding entry will 
--			not exist."
--		INDEX	{ dot1qVlanIndex, extendVlanStaticBrPortListId }
--		::= { extendVlanStaticBrPortsTable 1 }
--
--	ExtendVlanStaticBrPortsEntry ::=
--		SEQUENCE	{ 
--				extendVlanStaticBrPortListId
--					INTEGER,
--				extendVlanStaticBrEgressPorts
--					PortList
--				}
--
--	extendVlanStaticBrPortListId	OBJECT-TYPE
--		SYNTAX	INTEGER
--		ACCESS	read-only
--		STATUS	mandatory
--		DESCRIPTION
--			"The object identifies the sublist. Index 1 is the first 
--			sublist, index 2 the second sublist, ... The 1st sublist 
--			contains the information about the port 1 up to the port 
--			'numPortsInPortList'. The 2nd sublist contains the 
--			information about the port 'numPortsInPortList + 1' 
--			up to the port '2*numPortsInPortList', etc.
--             ALCATEL NOTE:
--                 ACCESS:     NA       USAGE:      NA
--                 PERSIST:    NO       INSRVMOD:   NO
--                 RANGE:      NA       DEFVALUE:   1
--                 UNITS:      NA       SPARSE:     NA
--                 DESCR:      NA"
--		::= { extendVlanStaticBrPortsEntry 1 }

--	extendVlanStaticBrEgressPorts	OBJECT-TYPE
--		SYNTAX	PortList
--		ACCESS	read-only
--		STATUS	mandatory
--		DESCRIPTION
--			"The list of ports that are egress ports for this Vlan.
--             ALCATEL NOTE:
--                 ACCESS:     NA       USAGE:      NA
--                 PERSIST:    NO       INSRVMOD:   NO
--                 RANGE:      NA       DEFVALUE:   NA
--                 UNITS:      NA       SPARSE:     NA
--                 DESCR:      NA"
--		::= { extendVlanStaticBrPortsEntry 2}


-- ======================================================================== 
-- The Extend VLAN Range
-- ======================================================================== 

--	extendVlanRangeTable OBJECT-TYPE
--		SYNTAX	SEQUENCE OF ExtendVlanRangeEntry
--		ACCESS	not-accessible
--		STATUS	mandatory
--		DESCRIPTION
--			"A table containing VLAN configuration information.
--			Note: in NBE, the table only keeps one entry."
--		::= { plimExtendVlan 10 }

--	extendVlanRangeEntry OBJECT-TYPE
--		SYNTAX	ExtendVlanRangeEntry
--		ACCESS	not-accessible
--		STATUS	mandatory
--		DESCRIPTION
--			"An entry in the extendVlanRangeTable."
--		INDEX	{ extendVlanRangeIndex }
--		::= { extendVlanRangeTable 1 }

--	ExtendVlanRangeEntry ::=
--		SEQUENCE	{ 
--				extendVlanRangeIndex
--					INTEGER,
--				extendLocalUserMinVlanId
--					VlanId,
--				extendLocalUserMaxVlanId
--					VlanId,
--				extendSharingMinVlanId
--					VlanId,
--				extendSharingMaxVlanId
--					VlanId,
--				extendTerminalVlanId
--					VlanId,
--				extendUntaggedMulticastVlanId
--					VlanId,
--				extendIGMPGeneralQueryVlanId
--					VlanId
--				}

--	extendVlanRangeIndex OBJECT-TYPE
--		SYNTAX	INTEGER
--		ACCESS	not-accessible
--		STATUS	mandatory
--		DESCRIPTION
--			"This object identifies index of the entry."
--		::= { extendVlanRangeEntry 1}

--	extendLocalUserMinVlanId OBJECT-TYPE
--		SYNTAX	VlanId
--		ACCESS	read-write
--		STATUS	mandatory
--		DESCRIPTION
--			"This object identifies minimum Vlan Id used for Local User VLANs,
--			which are only used for local ADSL lines."
--		::= { extendVlanRangeEntry 2}

--	extendLocalUserMaxVlanId OBJECT-TYPE
--		SYNTAX	VlanId
--		ACCESS	read-write
--		STATUS	mandatory
--		DESCRIPTION
--			" This object identifies maximum Vlan Id used for Local User VLANs,
--			which are only used for local ADSL lines."
--		::= { extendVlanRangeEntry 3}

--	extendSharingMinVlanId OBJECT-TYPE
--		SYNTAX	VlanId
--		ACCESS	read-write
--		STATUS	mandatory
--		DESCRIPTION
--			"This object identifies minimum Vlan Id used for Sharing VLANs,
--			which include the VLANs for termination and for configured 
--			multicast streams."
--		::= { extendVlanRangeEntry 4 }

--	extendSharingMaxVlanId OBJECT-TYPE
--		SYNTAX	VlanId
--		ACCESS	read-write
--		STATUS	mandatory
--		DESCRIPTION
--			" This object identifies maximum Vlan Id used for Sharing VLANs,
--			which include the VLANs for termination and for configured 
--			multicast streams."
--		::= { extendVlanRangeEntry 5 }

--	extendTerminalVlanId OBJECT-TYPE
--		SYNTAX	VlanId
--		ACCESS	read-write
--		STATUS	mandatory
--		DESCRIPTION
--			"This object identifies Vlan Id used for OAM."
--		::= { extendVlanRangeEntry 6}

--	extendUntaggedMulticastVlanId OBJECT-TYPE
--		SYNTAX	VlanId
--		ACCESS	read-write
--		STATUS	mandatory
--		DESCRIPTION
--			"This object identifies Vlan Id used for untagged multicast stream."
--		::= { extendVlanRangeEntry 7}

--	extendIGMPGeneralQueryVlanId OBJECT-TYPE
--		SYNTAX	VlanId
--		ACCESS	read-write
--		STATUS	mandatory
--		DESCRIPTION
--			"This object identifies Vlan Id used to tag general query of IGMP
--			called by CPU."
--		::= { extendVlanRangeEntry 8}

-- ===============================
-- Multicast related objects
-- ===============================

-- extendMulticast	OBJECT IDENTIFIER ::= {plimExtendVlan 11}

--	extendMulticastCurrentVlanList OBJECT-TYPE
--		SYNTAX	VlanList
--		ACCESS	read-only
--		STATUS	mandatory
--		DESCRIPTION
--			"The current configured VLAN list of Sharing VLANs for multicast in
--			NBE. This is the set of VLANs for which an entry is available in the
--			extendMulticastVlanTable. A 1 indicates an entry for this VLAN exists
--			in the extendMulticastVlanTable, a 0
--			indicates no corresponding entry exists."
--		::= { extendMulticast 1}

-- ==========================================================================
-- The Extend Multicast VLAN Database
-- ==========================================================================

--	extendMulticastVlanTable OBJECT-TYPE
--		SYNTAX	SEQUENCE OF ExtendMulticastVlanEntry
--		ACCESS	not-accessible
--		STATUS	mandatory
--		DESCRIPTION
--			"A table containing configuration information for
--			 VLANs in range of Sharing VLANs configured into the device by
--			IGMP module."
--		::= { extendMulticast 2 }

--	extendMulticastVlanEntry OBJECT-TYPE
--		SYNTAX	ExtendMulticastVlanEntry
--		ACCESS	not-accessible
--		STATUS	mandatory
--		DESCRIPTION
--			"An entry in the extendMulticastVlanTable."
--		INDEX	{ dot1qVlanIndex }
--		::= { extendMulticastVlanTable 1 }

--	ExtendMulticastVlanEntry ::=
--		SEQUENCE	{ 
--				extendMulticastVlanStaticName
--					SnmpAdminString,
--				extendMulticastVlanEgressPorts
--					PortList
--				}

--	extendMulticastVlanStaticName OBJECT-TYPE
--		SYNTAX	SnmpAdminString (SIZE (0..32))
--		ACCESS	read-write
--		STATUS	mandatory
--		DESCRIPTION
--			"An administratively assigned string, which may be used
--			to identify the VLAN."
--		::= { extendMulticastVlanEntry 1 }

--	extendMulticastVlanEgressPorts OBJECT-TYPE
--		SYNTAX	PortList
--		ACCESS	read-only
--		STATUS	mandatory
--		DESCRIPTION
--			"The set of ports which are permanently assigned to the
--			egress list for this VLAN by IGMP module. It has the same
--			meaning as dot1qVlanStaticEgressPorts, but this object is
--			for VLANs used by Configured Multicast Source."
--		::= { extendMulticastVlanEntry 2 }

-- ==========================================================================
-- The Extend Multicast Port Database
-- ==========================================================================

--	extendMulticastPortTable OBJECT-TYPE
--		SYNTAX	SEQUENCE OF ExtendMulticastPortEntry
--		ACCESS	not-accessible
--		STATUS	mandatory
--		DESCRIPTION
--			"A table containing configuration information of Sharing VLANs
--			maintained by IGMP module for each dot1dBasePort."
--		::= { extendMulticast 3 }

--	extendMulticastPortEntry OBJECT-TYPE
--		SYNTAX	ExtendMulticastPortEntry
--		ACCESS	not-accessible
--		STATUS	mandatory
--		DESCRIPTION
--			"An entry in the extendMulticastPortTable."
--		INDEX	{ dot1dBasePort }
--		::= { extendMulticastPortTable 1 }

--	ExtendMulticastPortEntry ::=
--		SEQUENCE	{ 
--				extendMulticastPortVlanList
--					VlanList
--				}

--	extendMulticastPortVlanList OBJECT-TYPE
--		SYNTAX	VlanList
--		ACCESS	read-only
--		STATUS	mandatory 
--		DESCRIPTION
--			"The configured set of VLANs in extendMulticastVlanTable
--			for the port. It has the same meaning as extendVlanPortVlanList,
--			but it is only for Sharing VLANs."
--		::= { extendMulticastPortEntry 1}

-- =======================================================
--  IGMP multicast forwarding table
-- =======================================================
--	extendIGMPMulticastTable OBJECT-TYPE
--		SYNTAX	SEQUENCE OF ExtendIGMPMulticastEntry
--		ACCESS	not-accessible
--		STATUS	mandatory
--		DESCRIPTION
--			"A table containing the forwarding information of
--			the multicast streams controlled by IGMP. "
--		::= { extendMulticast 4}

--	extendIGMPMulticastEntry OBJECT-TYPE
--		SYNTAX	ExtendIGMPMulticastEntry
--		ACCESS	not-accessible
--		STATUS	mandatory
--		DESCRIPTION
--			"An entry in the table extendIGMPMulticastTable. One entry
--			specifies the forwarding information for one multicast stream."
--		INDEX	{ dot1qFdbId, extendIGMPMulticastMacAddress }
--		::= { extendIGMPMulticastTable 1 }

--	ExtendIGMPMulticastEntry::=
--		SEQUENCE	{
--				extendIGMPMulticastMacAddress
--					MacAddress,
--				extendIGMPMulticastEgressPorts
--					PortList,
--				extendIGMPMulticastFilterId
--					Gauge
--				}

--	extendIGMPMulticastMacAddress	OBJECT-TYPE
--		SYNTAX	MacAddress
--		ACCESS	not-accessible
--		STATUS	mandatory
--		DESCRIPTION
--			"The multicast MAC address."
--		::= { extendIGMPMulticastEntry 1}

--	extendIGMPMulticastEgressPorts	OBJECT-TYPE
--		SYNTAX	PortList 
--		ACCESS	read-only
--		STATUS	mandatory
--		DESCRIPTION
--			"The egress port list of one multicast stream."
--		::= { extendIGMPMulticastEntry 2}

--	extendIGMPMulticastFilterId	OBJECT-TYPE
--		SYNTAX	Gauge 
--		ACCESS	read-only
--		STATUS	mandatory
--		DESCRIPTION
--			"The filter ID of this multicast stream."
--		::= { extendIGMPMulticastEntry 3}

-- ==========================================================================
-- The Port - VLAN association table, supports configuration aspects
-- ==========================================================================

	extendPortVlanAssociationTable OBJECT-TYPE
		SYNTAX	SEQUENCE OF ExtendPortVlanAssociationEntry
		ACCESS	not-accessible
		STATUS	mandatory
		DESCRIPTION
			"A virtual Bridge has multiple ports and supports various VLANs. 
			It is possible to associate ports to VLANs. Each VLAN supports its 
			forwarding function between the ports associated to it. It is 
			possible to associate a single port to multiple VLANs. This table 
			is used to configure these port - VLAN associations.
             ALCATEL NOTE:
                 TABLESIZE:  DEP [max nbr of static associations/board * nbr of boards]
                 DESCR:      The max nbr of static associations/board is 576."
		::= { plimExtendVlan 12 }

	extendPortVlanAssociationEntry OBJECT-TYPE
		SYNTAX	ExtendPortVlanAssociationEntry 
		ACCESS	not-accessible
		STATUS	mandatory
		DESCRIPTION
			"A port - VLan association."
		INDEX	{ dot1dBasePort, extendPortVlanVlanIndex }
		::= { extendPortVlanAssociationTable 1 }

	ExtendPortVlanAssociationEntry ::=
		SEQUENCE	{
				extendPortVlanVlanIndex 
					VlanIndex,
				extendPortVlanRowStatus
					RowStatus,
				extendPortVlanQosProfile
					INTEGER,
				extendPortVlanUntagged
					ExtendPortVlanUntagged, 
                                extendPortVlanPbitList
					PriorityBitList,
                                extendPortVlanThisVlanScope
                                        INTEGER,
                                extendPortVlanNetworkVlan
                                        VlanIndex,
                                extendPortVlanIfIndex 
                                        INTEGER,
                                extendPortVlanQosPolicy
                                       INTEGER,
                                extendPortVlanRegeneratedPbit
                                       ExtendVlanSystemPriority,
                                extendPortVlanPriorityRegenerationProfile
                                       INTEGER,
                                extendPortVlanIngressQosTcProfile
                                       INTEGER,
                                extendPortVlanMaxNbrOfPolicy
                                       INTEGER,
                                extendPortVlanMaxNbrOfIpAddresses
                                       INTEGER,
                               extendPortVlanMaxNumMacAddresses
                                       INTEGER,
                               extendPortVlanRateLimitProfileId
                                       INTEGER,
                               extendPortVlanDisablePortAsPkgOverload
                                       INTEGER,
                               extendPortVlanMaxNbrOfIpv6Addresses                                      
                                       INTEGER,
                               extendPortVlanSelfLearnAdminStatus
                                       INTEGER,
                               extendPortVlanDedicatedDsQ
                                       INTEGER,
                               extendPortVlanTunlProtoAwareMinCVLAN
                                       INTEGER,
                               extendPortVlanTunlProtoAwareMaxCVLAN
                                       INTEGER,
                               extendPortVlanTPID                              
                                       INTEGER 
				}

	extendPortVlanVlanIndex OBJECT-TYPE
		SYNTAX	VlanIndex
		ACCESS	read-write
		STATUS	mandatory
		DESCRIPTION
			"This object indicates the VLAN associated to a port.
             ALCATEL NOTE:
                 ACCESS:     NA       USAGE:      NA
                 PERSIST:    YES      INSRVMOD:   NO
                 RANGE:      NA       DEFVALUE:   NA
                 UNITS:      NA       SPARSE:     NA
                 DESCR:      NA"
		::= { extendPortVlanAssociationEntry 1 }

	extendPortVlanRowStatus OBJECT-TYPE
		SYNTAX	RowStatus
		ACCESS	read-write
		STATUS	mandatory
		DESCRIPTION
			"This object indicates the status of this entry.
             ALCATEL NOTE:
                 ACCESS:     NA       USAGE:      MAND
                 PERSIST:    YES      INSRVMOD:   YES
                 RANGE:      1,4,6    DEFVALUE:   NA
                 UNITS:      NA       SPARSE:     NA
                 DESCR:      NA"
		::= { extendPortVlanAssociationEntry 2 }

	extendPortVlanQosProfile OBJECT-TYPE
		SYNTAX  INTEGER
		ACCESS  read-write
		STATUS  mandatory
		DESCRIPTION
			"The QOS profile assigned to a port-VLAN association by QOS
			management. A value of 0 	means no QOS profile is allocated
             ALCATEL NOTE:
                 ACCESS:     NA       USAGE:      OPT
                 PERSIST:    NO       INSRVMOD:   YES
                 RANGE:      NA       DEFVALUE:   0
                 UNITS:      NA       SPARSE:     NA
                 DESCR:      NA"
		DEFVAL { 0 }
 
		::= { extendPortVlanAssociationEntry 3 }
	
	extendPortVlanUntagged OBJECT-TYPE
		SYNTAX  ExtendPortVlanUntagged
		ACCESS  read-write
		STATUS  mandatory
		DESCRIPTION
			"If 1, untagging shall be enabled,if 2, singletagging
             shall be enabled,if 3, priority tagging should be enabled 
             for the VLAN on the port (transmit direction)
             ALCATEL NOTE:
                 ACCESS:     NA       USAGE:      OPT
                 PERSIST:    YES      INSRVMOD:   YES
                 RANGE:      1,2,3    DEFVALUE:   1[untagged]
                 UNITS:      NA       SPARSE:     NA
                 DESCR:      NA"
		DEFVAL { untagged }
		::= { extendPortVlanAssociationEntry 4 }
	
        extendPortVlanPbitList OBJECT-TYPE
        	SYNTAX	PriorityBitList
        	ACCESS	read-write
        	STATUS	mandatory
        	DESCRIPTION
        		"Priority bitmap. In the case of a QoS aware VLAN,
        		a 1 set at a bit position corresponding to a certain
        		priority indicates that this priority is associated
        		with the Vlan Port.
        		For Vlan Ports of VLANs other than QoS aware, this bitmap
        		has no meaning and should be 0.
             ALCATEL NOTE:
                 ACCESS:     NA       USAGE:      OPT
                 PERSIST:    YES      INSRVMOD:   YES
                 RANGE:      NA       DEFVALUE:   0
                 UNITS:      NA       SPARSE:     NA
                 DESCR:      NA"
		DEFVAL { "0" }
		::= { extendPortVlanAssociationEntry 6 }

	extendPortVlanThisVlanScope OBJECT-TYPE
		SYNTAX	INTEGER
				{
                 network (1),
                 local (2)
				}
		ACCESS  read-write
		STATUS  mandatory
		DESCRIPTION
			"Indicating whether the VLAN is scoped as local within a bridge port 
             or as network wide.If 1(network), it means the VLAN-port forwarding 
             interface is attached to a L2 forwarder and the network VLAN has the 
             same VLAN id;if 2(local), it means the VLAN is terminated in the 
             bridge port.
             ALCATEL NOTE:
                 ACCESS:     NA       USAGE:      OPT
                 PERSIST:    YES      INSRVMOD:   YES
                 RANGE:      1,2      DEFVALUE:   1[network]
                 UNITS:      NA       SPARSE:     NA
                 DESCR:      NA"
		DEFVAL { network }
		::= { extendPortVlanAssociationEntry 7 }

	extendPortVlanNetworkVlan OBJECT-TYPE
		SYNTAX	VlanIndex
		ACCESS	read-write
		STATUS	mandatory
		DESCRIPTION
			"Only need to be configured in case of VLAN translation, otherwise it 
             will have the default value none. If configured, it should be 
             configured as a valid network VLAN ID, which means to attach the 
             VLAN-port forwarding interface to a L2 forwarder. It is allowed that 
             the object has the same VLAN ID as the subscriber VLAN --
             extendPortVlanVlanIndex
             ALCATEL NOTE:
                 ACCESS:     NA       USAGE:      NA
                 PERSIST:    YES      INSRVMOD:   NO
                 RANGE:      NA       DEFVALUE:   16777217
                 UNITS:      NA       SPARSE:     NA
                 DESCR:      Default network VLAN of a VLAN-port is 0x01000001 
                             which is interpreted as (0,4097) and means none"
         DEFVAL { 16777217 }
		::= { extendPortVlanAssociationEntry 8 }

	 extendPortVlanIfIndex OBJECT-TYPE
		SYNTAX	INTEGER
		ACCESS	read-only
		STATUS	mandatory
		DESCRIPTION
			"IfIndex of the VLAN-port forwarding interface.
             ALCATEL NOTE:
                 ACCESS:     NA       USAGE:      NA
                 PERSIST:    YES      INSRVMOD:   NO
                 RANGE:      NA       DEFVALUE:   NA
                 UNITS:      NA       SPARSE:     NA
                 DESCR:      NA"
		::= { extendPortVlanAssociationEntry 9 }

	extendPortVlanQosPolicy OBJECT-TYPE
		SYNTAX	INTEGER
				{
                 regeneratedPbit (1),
                 regenerationProfile (2)
				}
		ACCESS  read-write
		STATUS  mandatory
		DESCRIPTION
			"Indicating Qos policy on VLAN-port forwarding interface.There are two 
             options.If 1(regeneratedPbit), it means all untagged and tagged frames 
             received on the VLAN-port forwarding interface be tagged with a fixed 
             priority identified by extendPortVlanRegeneratedPbit;if 
             2(regenerationProfile), it means all tagged frames received on the 
             VLAN-port should be replaced according to Pbit regeneration profile 
             identified by object extendPortVlanPrioritytRegenerationProfile.
             Default value of Qos policy is regenerationProfile.
             ALCATEL NOTE:
                 ACCESS:     NA       USAGE:      OPT
                 PERSIST:    YES      INSRVMOD:   YES
                 RANGE:      1,2      DEFVALUE:   2[regenerationProfile]
                 UNITS:      NA       SPARSE:     NA
                 DESCR:      NA"
		DEFVAL { regenerationProfile }
		::= { extendPortVlanAssociationEntry 10 }

	extendPortVlanRegeneratedPbit OBJECT-TYPE
		SYNTAX  ExtendVlanSystemPriority
		ACCESS  read-write
		STATUS  mandatory
		DESCRIPTION
			"All traffic received on the VLAN-port should be tagged with the fixed 
             priority identified by this object.
             ALCATEL NOTE:
                 ACCESS:     NA       USAGE:      OPT
                 PERSIST:    YES      INSRVMOD:   YES
                 RANGE:      0..7     DEFVALUE:   0
                 UNITS:      NA       SPARSE:     NA
                 DESCR:      NA"
		DEFVAL { 0 }
		::= { extendPortVlanAssociationEntry 11 }

	extendPortVlanPriorityRegenerationProfile OBJECT-TYPE
		SYNTAX  INTEGER
		ACCESS  read-write
		STATUS  mandatory
		DESCRIPTION
			"The Priority regeneration profile assigned to a VLAN-port forwarding 
             interface. 
       The default value is 0, meaning no priority bit regeneration profile
       is applied on the VLAN-port forwarding interface.. 
       DSL interfaces can use profiles 1..10.
       GPON interfaces can use profiles 1..32.

             ALCATEL NOTE:
                 ACCESS:     NA       USAGE:      OPT
                 PERSIST:    YES      INSRVMOD:   YES
                 RANGE:      NA       DEFVALUE:   0 
                 UNITS:      NA       SPARSE:     NA
                 DESCR:      NA"
		DEFVAL { 0 }
		::= { extendPortVlanAssociationEntry 12 }

extendPortVlanIngressQosTcProfile OBJECT-TYPE
      SYNTAX  INTEGER
      ACCESS  read-write
      STATUS  mandatory
      DESCRIPTION
         "It defines a pointer to the Qos Profile that maps pbits to TCs on a VLAN port basis. The QoS Profile exists in the QoS MIB.
          ALCATEL NOTE:
              ACCESS:     NA       USAGE:      OPT
              PERSIST:    YES      INSRVMOD:   YES
              RANGE:               DEFVALUE:   33
              UNITS:      NA       SPARSE:     NA
              DESCR:      NA"
      DEFVAL { 33 }   
      ::= { extendPortVlanAssociationEntry 13 }

extendPortVlanMaxNbrOfPolicy OBJECT-TYPE
      SYNTAX  INTEGER
      ACCESS  read-write
      STATUS  mandatory
      DESCRIPTION
         "It defines the max number of Qos Policy numbers (ACL and CCL) on a VLAN port basis .
          ALCATEL NOTE:
              ACCESS:     NA       USAGE:      OPT
              PERSIST:    YES      INSRVMOD:   YES
              RANGE:      0..8      DEFVALUE:   0
              UNITS:      NA       SPARSE:     NA
              DESCR:      NA"
      DEFVAL { 0 }   
      ::= { extendPortVlanAssociationEntry 14 }

extendPortVlanMaxNbrOfIpAddresses OBJECT-TYPE
      SYNTAX  INTEGER
      ACCESS  read-write
      STATUS  mandatory
      DESCRIPTION
         "It defines the max number of IP address number used in IP antispoofing and/or ARP relay on a VLAN port basis .
          ALCATEL NOTE:
              ACCESS:     NA       USAGE:      OPT
              PERSIST:    YES      INSRVMOD:   YES
              RANGE:               DEFVALUE:   65535
              UNITS:      NA       SPARSE:     NA
              DESCR:      NA"
      DEFVAL { 65535 }   
      ::= { extendPortVlanAssociationEntry 15 }

extendPortVlanMaxNumMacAddresses OBJECT-TYPE
      SYNTAX  INTEGER
      ACCESS  read-write
      STATUS  mandatory
      DESCRIPTION
         "It defines the max number of Mac Address on a VLAN port basis .
          ALCATEL NOTE:
              ACCESS:     NA       USAGE:      OPT
              PERSIST:    YES      INSRVMOD:   YES
              RANGE:      0..65535      DEFVALUE:   65535(not to check max mac on VP)
              UNITS:      NA       SPARSE:     NA
              DESCR:      NA"
      DEFVAL { 65535 }   
      ::= { extendPortVlanAssociationEntry 16 }
      
extendPortVlanRateLimitProfileId OBJECT-TYPE
      SYNTAX  INTEGER
      ACCESS  read-write
      STATUS  mandatory
      DESCRIPTION
         "Indicate the Protocol Rate Limit profile, refer to qosRateLimitProfileTable.
           0 means not associate any profile.
           This attribut is reserved for the future usage. It does not work in project 4.5.01
           default value is 0.
          ALCATEL NOTE:
              ACCESS:     YES      USAGE:      OPT
              PERSIST:    YES      INSRVMOD:   YES
              RANGE:      0..250   DEFVALUE:   0(not associate any profile)
              UNITS:      NA       SPARSE:     NA
              DESCR:      NA"
      DEFVAL { 0 }
      ::= { extendPortVlanAssociationEntry 17 }

extendPortVlanDisablePortAsPkgOverload OBJECT-TYPE
      SYNTAX  INTEGER 
      ACCESS  read-write
      STATUS  mandatory
      DESCRIPTION
         "Indicates whether disable VLAN port when receive protocol packages number exceed the thershold value.
                 0 means no action when overload .
                 1 measn close VLAN port when overload.
          Defaultly, NOT to close VLAN port when protocol packages overload.
          This attribut is reserved for the future usage. It does not work in project 4.5.01
          ALCATEL NOTE:
              ACCESS:     YES      USAGE:      OPT
              PERSIST:    YES      INSRVMOD:   YES
              RANGE:      0..1     DEFVALUE:   0(not to close VP when protocol package overload)
              UNITS:      NA       SPARSE:     NA
              DESCR:      NA"
      DEFVAL { 0 }
      ::= { extendPortVlanAssociationEntry 18 }

extendPortVlanMaxNbrOfIpv6Addresses OBJECT-TYPE
      SYNTAX  INTEGER
      ACCESS  read-write
      STATUS  mandatory
      DESCRIPTION
         "It defines the max number of IPv6 address number used in IP antispoofing and/or ARP relay on a VLAN port basis .
          ALCATEL NOTE:
              ACCESS:     NA       USAGE:      OPT
              PERSIST:    YES      INSRVMOD:   YES
              RANGE:               DEFVALUE:   65535
              UNITS:      NA       SPARSE:     NA
              DESCR:      NA"
      DEFVAL { 65535 }   
      ::= { extendPortVlanAssociationEntry 19 }

extendPortVlanSelfLearnAdminStatus OBJECT-TYPE
	SYNTAX  INTEGER {
			up(1),
			down(2),
         inherit(3)
			}
	ACCESS  read-write
	STATUS  mandatory
	DESCRIPTION
		"This object specifies the desired administrative state of the
		self learning process of MAC addresses. The up state indicates
		that MAC addresses shall be learned, the down state indicates
		that MAC addresses shall not be learned on that port. Inherit 
      indicates to use the bridgePort value.
             ALCATEL NOTE:
                 ACCESS:     NA       USAGE:      OPT
                 PERSIST:    YES      INSRVMOD:   YES
                 RANGE:      1,2,3    DEFVALUE:   3[inherit]
                 UNITS:      NA       SPARSE:     NA
                 DESCR:      NA"
             DEFVAL { 3 }
		::= { extendPortVlanAssociationEntry 20 }

extendPortVlanDedicatedDsQ  OBJECT-TYPE 
   SYNTAX   INTEGER 
         {
            enabled (1),
            disabled (0)
         }
   ACCESS read-write
   STATUS mandatory
   DESCRIPTION
        "When enabled, all the traffic for this VLAN port will use a dedicated per PON special queue in the downstream on the LT. When disabled, all the traffic uses the per UNI/ONT based queues based on traffic-class/pbits. By default, this attribute is disabled. 
ALCATEL NOTE:
                 ACCESS:     NA       USAGE:      NA
                 PERSIST:    YES      INSRVMOD:   NO
                 RANGE:      0..1     DEFVALUE:   0
                 UNITS:      NA       SPARSE:     NA
                 DESCR:      NA "
DEFVAL { 0 }
::= { extendPortVlanAssociationEntry 21 }

extendPortVlanTunlProtoAwareMinCVLAN OBJECT-TYPE
      SYNTAX  INTEGER
      ACCESS  read-write
      STATUS  mandatory
      DESCRIPTION
         "This object allows the operator to configure the lower boundary of CVLAN range for protocol awareness for S-VLAN cross-connect (tunnel).
          ALCATEL NOTE:
              ACCESS:     NA       USAGE:      OPT
              PERSIST:    YES      INSRVMOD:   YES
              RANGE:      1..4095      DEFVALUE: 1
              UNITS:      NA       SPARSE:     NA
              DESCR:      NA "
      DEFVAL { 1 }
      ::= { extendPortVlanAssociationEntry 22 }

extendPortVlanTunlProtoAwareMaxCVLAN OBJECT-TYPE
      SYNTAX  INTEGER
      ACCESS  read-write
      STATUS  mandatory
      DESCRIPTION
         "This object allows the operator to configure the upper boundary of CVLAN range for protocol awareness for S-VLAN cross-connect (tunnel).
          ALCATEL NOTE:
              ACCESS:     NA       USAGE:      OPT
              PERSIST:    YES      INSRVMOD:   YES
              RANGE:      1..4095      DEFVALUE: 4095
              UNITS:      NA       SPARSE:     NA
              DESCR:      NA "
      DEFVAL { 4095 }
      ::= { extendPortVlanAssociationEntry 23 }

extendPortVlanTPID OBJECT-TYPE
      SYNTAX  INTEGER
      ACCESS  read-write
      STATUS  mandatory
      DESCRIPTION
         "This object allows the operator to configure vlan port TPID, must be Hex.
          ALCATEL NOTE:
              ACCESS:     NA       USAGE:      OPT
              PERSIST:    YES      INSRVMOD:   YES
              RANGE:      1536..65535      DEFVALUE: 33024
              UNITS:      NA       SPARSE:     NA
              DESCR:      NA "
      DEFVAL { 33024 }
      ::= { extendPortVlanAssociationEntry 24 }
-- ==========================================================================
-- The port - VLAN association table, sorted differently, just for read purposes
-- ==========================================================================

--   extendVlanPortAssociationTable OBJECT-TYPE
--      SYNTAX   SEQUENCE OF ExtendVlanPortAssociationEntry
--      ACCESS   not-accessible
--      STATUS   mandatory
--      DESCRIPTION
--      "As the table extendPortVlanAssociationTable, this table contains
--      the VLAN-port interface and network VLAN associations. It indicates
--      all the VLAN-port interfaces which are attached to a network VLAN.
--             ALCATEL NOTE:
--                 TABLESIZE:  DEP [depends on the tablesize of
--                             extendPortVlanAssociationTable]
--                 DESCR:      NA "
--      ::= { plimExtendVlan 13 }

--   extendVlanPortAssociationEntry OBJECT-TYPE
--      SYNTAX   ExtendVlanPortAssociationEntry
--      ACCESS   not-accessible
--      STATUS   mandatory
--      DESCRIPTION
--         "A VLAN-port interface attached to a network VLAN."
--      INDEX   { dot1qVlanIndex, extendVlanPortPortId }
--      ::= { extendVlanPortAssociationTable 1 }

--   ExtendVlanPortAssociationEntry ::=
--      SEQUENCE   {
--            extendVlanPortPortId
--               INTEGER,
--                 extendVlanPortSubscriberVlan
--                      VlanIndex
--            }

--   extendVlanPortPortId OBJECT-TYPE
--      SYNTAX   INTEGER
--      ACCESS   read-only
--      STATUS   mandatory
--      DESCRIPTION
--       "Id of a bridge port containing VLAN endpoints (identified by
--      extendVlanPortSubscriberVlan) that are attached to the network VLAN
--     identified by dot1qVlanIndex. As such, extendVlanPortPortId equals a
--       dot1dBasePort.
--             ALCATEL NOTE:
--                 ACCESS:     NA       USAGE:      NA
--                 PERSIST:    NO       INSRVMOD:   NO
--                 RANGE:      NA       DEFVALUE:   NA
--                 UNITS:      NA       SPARSE:     NA
--                 DESCR:      NA"
--      ::= { extendVlanPortAssociationEntry 1 }

--   extendVlanPortSubscriberVlan OBJECT-TYPE
--      SYNTAX   VlanIndex
--      ACCESS   read-only
--      STATUS   mandatory
--      DESCRIPTION
--     "This object indicates the subscriber VLAN associated to bridge port.
--       It corresponds to extendPortVlanVlanIndex.
--             ALCATEL NOTE:
--                 ACCESS:     NA       USAGE:      NA
--                 PERSIST:    NO       INSRVMOD:   NO
--                 RANGE:      NA       DEFVALUE:   NA
--                 UNITS:      NA       SPARSE:     NA
--                 DESCR:      NA"
--      ::= { extendVlanPortAssociationEntry 2 }

-- ==========================================================================
-- The Table to configure VCLs as ports of the Bridge
-- ==========================================================================
--
--	extendVclPortTable OBJECT-TYPE
--		SYNTAX	SEQUENCE OF ExtendVclPortEntry
--		ACCESS	not-accessible
--		STATUS	mandatory
--		DESCRIPTION
--			"A table that contains all the ATM VCLs that are configured as 
--			to be terminated, that contain Ethernet frames, and for which the
--			system has to support bridging functionality. (The encapsulation 
--			technique of the Ethernet frame into ATM, such as VC-Mux or LLC-SNAP,
--			is configured via the ATM MIB.)
--           ALCATEL NOTE:
--             TABLESIZE:  DEP [depends on the value of dot1dBaseNumPorts]
--             DESCR:      NA"
--		::= { plimExtendVlan 14 }
--
--	extendVclPortEntry OBJECT-TYPE
--		SYNTAX	ExtendVclPortEntry 
--		ACCESS	not-accessible
--		STATUS	mandatory
--		DESCRIPTION
--			"An entry in the VCPortTable representing one terminated VCL."
--		INDEX	{ ifIndex, extendVclPortVpi, extendVclPortVci }
--		::= { extendVclPortTable 1 }
--
--	ExtendVclPortEntry ::=
--		SEQUENCE	{
--				extendVclPortVpi
--					AtmVpIdentifier,
--				extendVclPortVci
--					AtmVcIdentifier,
--				extendVclPortDot1dBasePort
--					INTEGER,
--				extendVclPortRowStatus
--					RowStatus,
--				extendVclPortIfIndex
--					INTEGER
--				}
--
--	extendVclPortVpi OBJECT-TYPE
--		SYNTAX	AtmVpIdentifier
--		ACCESS	read-write
--		STATUS	mandatory
--		DESCRIPTION
--			"The VPI identifier of the terminated VCL.
--             ALCATEL NOTE:
--                 ACCESS:     RO       USAGE:      NA
--                 PERSIST:    YES      INSRVMOD:   NO
--                 RANGE:      NA       DEFVALUE:   NA
--                 UNITS:      NA       SPARSE:     NA
--                 DESCR:      NA"
--		::= { extendVclPortEntry 1 }
--
--	extendVclPortVci OBJECT-TYPE
--		SYNTAX	AtmVcIdentifier
--		ACCESS	read-write
--		STATUS	mandatory
--		DESCRIPTION
--			"The VCI identifier of the terminated VCL.
--             ALCATEL NOTE:
--                 ACCESS:     RO       USAGE:      NA
--                 PERSIST:    YES      INSRVMOD:   NO
--                 RANGE:      NA       DEFVALUE:   NA
--                 UNITS:      NA       SPARSE:     NA
--                 DESCR:      NA"
--		::= { extendVclPortEntry 2 }
--
--	extendVclPortDot1dBasePort OBJECT-TYPE
--		SYNTAX	INTEGER (1..65535)
--		ACCESS	read-write
--		STATUS	mandatory
--		DESCRIPTION
--			"The port identifier assigned by the system to this terminated VCL.
--			A port identifier identifies uniquely a port of the VLAN-Bridge
--			within the system.
--             ALCATEL NOTE:
--                 ACCESS:     RO       USAGE:      NA
--                 PERSIST:    YES      INSRVMOD:   NO
--                 RANGE:      NA       DEFVALUE:   NA
--                 UNITS:      NA       SPARSE:     NA
--                 DESCR:      NA"
--		::= { extendVclPortEntry 3 }
--
--	extendVclPortRowStatus OBJECT-TYPE
--		SYNTAX	RowStatus
--		ACCESS	read-write
--		STATUS	mandatory
--		DESCRIPTION
--			"This object indicates the status of this entry.
--             ALCATEL NOTE:
--                 ACCESS:     NA       USAGE:      MAND
--                 PERSIST:    YES      INSRVMOD:   YES
--                 RANGE:      1,4,6    DEFVALUE:   NA
--                 UNITS:      NA       SPARSE:     NA
--                 DESCR:      NA"
--		::= { extendVclPortEntry 4 }
--
--	 extendVclPortIfIndex OBJECT-TYPE
--		SYNTAX	INTEGER
--		ACCESS	read-only
--		STATUS	mandatory
--		DESCRIPTION
--			"IfIndex of the dot1dBasePort
--             ALCATEL NOTE:
--                 ACCESS:     NA       USAGE:      NA
--                 PERSIST:    YES      INSRVMOD:   NO
--                 RANGE:      NA       DEFVALUE:   NA
--                 UNITS:      NA       SPARSE:     NA
--                 DESCR:      NA"
--		::= { extendVclPortEntry 5 }
--
-- ==========================================================================
-- The Table to read out VLAN identifiers based on its name
-- ==========================================================================

	extendVlanNameTable OBJECT-TYPE
		SYNTAX	SEQUENCE OF ExtendVlanNameEntry
		ACCESS	not-accessible
		STATUS	mandatory
		DESCRIPTION
			"A table to translate a VLAN name into a VLANId
             ALCATEL NOTE:
             TABLESIZE:  DEP [depends on the value of dot1qVlanCurrentTable]
             DESCR:      NA"
		::= { plimExtendVlan 15 }

	extendVlanNameEntry OBJECT-TYPE
		SYNTAX	ExtendVlanNameEntry 
		ACCESS	not-accessible
		STATUS	mandatory
		DESCRIPTION
			"One VLAN name - VLAN index relationship."
		INDEX	{ extendVlanNameStaticName, extendVlanNameVlanIndex }
		::= { extendVlanNameTable 1 }

	ExtendVlanNameEntry ::=
		SEQUENCE	{
				extendVlanNameStaticName
               SnmpAdminString (SIZE (0..80)),
				extendVlanNameVlanIndex 
					VlanIndex
				}

	extendVlanNameStaticName OBJECT-TYPE
      SYNTAX   SnmpAdminString (SIZE (0..80))
		ACCESS	read-only
		STATUS	mandatory
		DESCRIPTION
			"An administratively assigned string, which may be used
			to identify the VLAN.
             ALCATEL NOTE:
                 ACCESS:     NA       USAGE:      NA
                 PERSIST:    NO       INSRVMOD:   NO
                 RANGE:      NA       DEFVALUE:   NA
                 UNITS:      NA       SPARSE:     NA
                 DESCR:      NA"
		::= { extendVlanNameEntry 1 }

	extendVlanNameVlanIndex OBJECT-TYPE
		SYNTAX	VlanIndex
		ACCESS	read-only
		STATUS	mandatory
		DESCRIPTION
			"The index of the row in dot1qVlanCurrentTable for the
			VLAN constrained by this entry.
             ALCATEL NOTE:
                 ACCESS:     NA       USAGE:      NA
                 PERSIST:    NO       INSRVMOD:   NO
                 RANGE:      NA       DEFVALUE:   NA
                 UNITS:      NA       SPARSE:     NA
                 DESCR:      NA"
		::= { extendVlanNameEntry 2 }


-- ==========================================================================
-- QoS aware VLAN List, just for read purpose
-- ==========================================================================

	extendVlanCurrentVlanQosAwareList OBJECT-TYPE
		SYNTAX	VlanList
		ACCESS	read-only
		STATUS	mandatory
		DESCRIPTION
			"The list of QoS-aware C-VLANs currently configured. 
			This is the set of C-Vlans configured in the 
			extendVlanStaticTable for which the object 
			extendVlanStaticSystemMode has the value QoS aware. 
			A 1 indicates an entry for this VLAN exists and is 
			configured with the QoS aware mode, a 0 indicates 
			no corresponding entry exists or it is configured in the 
			other mode. 
             ALCATEL NOTE:
                 ACCESS:     NA       USAGE:      NA
                 PERSIST:    NO       INSRVMOD:   NO
                 RANGE:      NA       DEFVALUE:   all '0'    
                 UNITS:      NA       SPARSE:     NA
                 DESCR:      NA"
		::= { plimExtendVlan 16}

--

--   extendCurrentVlanPortTable OBJECT-TYPE
--      SYNTAX   SEQUENCE OF ExtendCurrentVlanPortEntry
--      ACCESS   not-accessible
--      STATUS   mandatory
--      DESCRIPTION
--     "A table containing static and dynamic port configuration information:
--     the table represents the static data until these static data are
--     overruled by dynamic data, typically applied after port authentication
--     using the Radius protocol
--         ALCATEL NOTE:
--             TABLESIZE: DEP [depends on the value of dot1dBaseNumPorts]
--             DESCR:     NA"
--      ::= { plimExtendVlan 19 }

--   extendCurrentVlanPortEntry OBJECT-TYPE
--      SYNTAX   ExtendCurrentVlanPortEntry
--      ACCESS   not-accessible
--      STATUS   mandatory
--      DESCRIPTION
--         "The static and dynamic information for a port."
--      INDEX   { dot1dBasePort }
--      ::= { extendCurrentVlanPortTable 1 }

--   ExtendCurrentVlanPortEntry ::=
--      SEQUENCE   {
--            extendCurrentVlanPortDefaultPriority
--               ExtendVlanSystemPriority,
--            extendCurrentVlanPortQosProfile
--               SnmpAdminString (SIZE (0..32)),
--            extendCurrentDot1qPvid
--               VlanIndex,
--            extendCurrentVlanPortDynamicData
--               INTEGER
--            }

--   extendCurrentVlanPortDefaultPriority OBJECT-TYPE
--      SYNTAX   ExtendVlanSystemPriority
--      ACCESS   read-only
--      STATUS   mandatory
--      DESCRIPTION
--         "Port dynamic or static (if no dynamic)default priority
--             ALCATEL NOTE:
--                 ACCESS:     NA       USAGE:      NA
--                 PERSIST:    NO       INSRVMOD:   NO
--                 RANGE:      0..7     DEFVALUE:   0
--                 UNITS:      NA       SPARSE:     NA
--                 DESCR:      NA"
--      ::= { extendCurrentVlanPortEntry 1 }


--   extendCurrentVlanPortQosProfile OBJECT-TYPE
 --     SYNTAX SnmpAdminString (SIZE (0..32))
 --     ACCESS  read-only
 --     STATUS  mandatory
 --     DESCRIPTION
 --        "The dynamic or static (if no dynamic) QOS profile assigned to a port
--             ALCATEL NOTE:
--                 ACCESS:     NA       USAGE:      NA
--                 PERSIST:    NO       INSRVMOD:   NO
--                 RANGE:      NA       DEFVALUE:   0
--                 UNITS:      NA       SPARSE:     NA
--                 DESCR:      NA"
--      ::= { extendCurrentVlanPortEntry 2 }

--   extendCurrentDot1qPvid OBJECT-TYPE
--      SYNTAX  VlanIndex
--      ACCESS  read-only
--      STATUS  mandatory
--      DESCRIPTION
--         "The dynamic or static (if no dynamic) default VLAN assigned to a
--         port
--             ALCATEL NOTE:
--                 ACCESS:     NA       USAGE:      NA
--                 PERSIST:    NO       INSRVMOD:   NO
--                 RANGE:      NA       DEFVALUE:   16777217
--                 UNITS:      NA       SPARSE:     NA
--                 DESCR:      NA"
--      ::= { extendCurrentVlanPortEntry 3 }

--   extendCurrentVlanPortDynamicData OBJECT-TYPE
--      SYNTAX  INTEGER
--            {
--            true(1),
--            false(2)
--            }

--      ACCESS  read-only
--      STATUS  mandatory
--      DESCRIPTION
--      "If one of the objects in the table entry is dynamic, the value shall
--       be true
--             ALCATEL NOTE:
--                 ACCESS:     NA       USAGE:      NA
--                 PERSIST:    NO       INSRVMOD:   NO
--                 RANGE:      1,2      DEFVALUE:   2[false]
--                 UNITS:      NA       SPARSE:     NA
--                 DESCR:      NA"
--      ::= { extendCurrentVlanPortEntry 4 }

--

--   extendCurrentPortVlanAssociationTable OBJECT-TYPE
--      SYNTAX   SEQUENCE OF ExtendCurrentPortVlanAssociationEntry
--      ACCESS   not-accessible
--      STATUS   mandatory
--      DESCRIPTION
--       "A virtual Bridge has multiple ports and supports various VLANs.
--       It is possible to associate ports to VLANs. Each VLAN supports its
--       forwarding function between the ports associated to it. It is
--       possible to associate a single port to multiple VLANs. This table
--       is used to configure these port - VLAN associations. The table
--       contains dynamic or static (if no dynamic) associations : the table
--       represents the static data until these static data are overruled by
--       dynamic data, typically applied after port authentication using the
--       Radius protocol
--             ALCATEL NOTE:
--                 TABLESIZE:  DEP [For non HYNT, the tablesize is max nbr
--of associations/board * nbr of boards.For HYNT, the tablesize is max nbr
--of associations/board * nbr of boards+5120.]
--                 DESCR:      The max nbr of associations/board is 1080 of
--Intel LT,including the static and dynamic associations.
--The max nbr of associations/board is 768 of Infineon LT, including the
-- static associations"
--      ::= { plimExtendVlan 20 }

--   extendCurrentPortVlanAssociationEntry OBJECT-TYPE
--      SYNTAX   ExtendCurrentPortVlanAssociationEntry
--      ACCESS   not-accessible
--      STATUS   mandatory
--      DESCRIPTION
--         "A port - VLan association."
--      INDEX   { dot1dBasePort, extendCurrentPortVlanVlanIndex }
--      ::= { extendCurrentPortVlanAssociationTable 1 }

--   ExtendCurrentPortVlanAssociationEntry ::=
--      SEQUENCE   {
--            extendCurrentPortVlanVlanIndex
--               VlanIndex,
--            extendCurrentPortVlanQosProfile
--               INTEGER,
--            extendCurrentPortVlanDynamicData
--               INTEGER,
--                 extendCurrentPortVlanIfIndex
--                     INTEGER
--            }

--   extendCurrentPortVlanVlanIndex OBJECT-TYPE
--      SYNTAX   VlanIndex
--      ACCESS   read-only
--      STATUS   mandatory
--      DESCRIPTION
--         "This object indicates the dynamic or static (if no dynamic) VLAN
--         associated to a port.
--             ALCATEL NOTE:
--                 ACCESS:     NA       USAGE:      NA
--                 PERSIST:    NO       INSRVMOD:   NO
--                 RANGE:      NA       DEFVALUE:   NA
--                 UNITS:      NA       SPARSE:     NA
--                 DESCR:      NA"
--      ::= { extendCurrentPortVlanAssociationEntry 1 }

--   extendCurrentPortVlanQosProfile OBJECT-TYPE
--      SYNTAX  INTEGER
--      ACCESS  read-only
--      STATUS  mandatory
--      DESCRIPTION
--         "The QOS profile dynamic or static (if no dynamic) assigned to a
--         port-Vlan association.
--             ALCATEL NOTE:
--                 ACCESS:     NA       USAGE:      NA
--                 PERSIST:    NO       INSRVMOD:   NO
--                 RANGE:      NA       DEFVALUE:   0
--                 UNITS:      NA       SPARSE:     NA
--                 DESCR:      NA"
--      ::= { extendCurrentPortVlanAssociationEntry 2 }

--   extendCurrentPortVlanDynamicData OBJECT-TYPE
--      SYNTAX  INTEGER
--            {
--            true(1),
--            false(2)
--            }

--      ACCESS  read-only
--      STATUS  mandatory
--      DESCRIPTION
--      "If one of the objects in the table entry is dynamic, the value shall
--       be true
--             ALCATEL NOTE:
--                 ACCESS:     NA       USAGE:      NA
--                 PERSIST:    NO       INSRVMOD:   NO
--                 RANGE:      1,2      DEFVALUE:   2[false]
--                 UNITS:      NA       SPARSE:     NA
--                 DESCR:      NA"
--      ::= { extendCurrentPortVlanAssociationEntry 3 }

--    extendCurrentPortVlanIfIndex OBJECT-TYPE
--      SYNTAX   INTEGER
--      ACCESS   read-only
--      STATUS   mandatory
--      DESCRIPTION
--         "IfIndex of the dynamic VLAN-port forwarding interface.
--             ALCATEL NOTE:
--                 ACCESS:     NA       USAGE:      NA
--                 PERSIST:    NO       INSRVMOD:   NO
--                 RANGE:      NA       DEFVALUE:   NA
--                 UNITS:      NA       SPARSE:     NA
--                 DESCR:      NA"
--      ::= { extendCurrentPortVlanAssociationEntry 4 }

--

--   extendVlanCurrentBrPortsTable OBJECT-TYPE
--      SYNTAX   SEQUENCE OF ExtendVlanCurrentBrPortsEntry
--      ACCESS   not-accessible
--      STATUS   mandatory
--      DESCRIPTION
--        "A table that augments the table dot1qVlanStaticTable for
--        those Vlans that are in (residential) bridge mode with
--        information on the egress ports. The table applies on dynamic or
--        static(if no dynamic) data : the table represents the static data
--        until these    static data are overruled by dynamic data, typically
--        applied after port authentication using the Radius protocol
--          ALCATEL NOTE:
--           TABLESIZE:  DEP [depends on the value of extendVlanBrPortsTable]
--            DESCR:      NA"
--
--      ::= { plimExtendVlan 21 }

--   extendVlanCurrentBrPortsEntry OBJECT-TYPE
--      SYNTAX   ExtendVlanCurrentBrPortsEntry
 --     ACCESS   not-accessible
 --     STATUS   mandatory
 --     DESCRIPTION
 --        "An entry in the table extendVlanCurrentBrPortsTable. A Vlan
 --        in the residentialBridge mode can potentially support all
 --        ports of the system. The system can support a large
 --        number of ports. In order to improve  management efficiency,
 --        the number of ports that can be managed in one object is
 --        limited. The number of ports that can be managed in one object
 --        is presented in the object numPortsInPortList. If the number of
 --        ports supported by the system (inclusive the number of ports for
 --        which the port number is reserved for future use) is larger than
 --        the numPortsInPortList, then this total number of ports is split
 --        into sublists.
 --        For each Vlan in residentialBridge mode, one entry can exist in
 --        this table per such sublist. In case one or more ports of the
 --        sublist are associated to the VLAN, then the corresponding
 --        entry shall exist. In case none of the ports of the sublist
 --        are associated to the VLAN, then the corresponding entry will
 --        not exist."
 --     INDEX   { dot1qVlanIndex, extendVlanCurrentBrPortListId }
 --     ::= { extendVlanCurrentBrPortsTable 1 }

--   ExtendVlanCurrentBrPortsEntry ::=
--      SEQUENCE   {
--            extendVlanCurrentBrPortListId
--               INTEGER,
--            extendVlanCurrentBrEgressPorts
--               PortList
--            }

--   extendVlanCurrentBrPortListId   OBJECT-TYPE
--      SYNTAX   INTEGER
--      ACCESS   read-only
--      STATUS   mandatory
--      DESCRIPTION
--         "The object identifies the sublist. Index 1 is the first
--         sublist, index 2 the second sublist, The 1st sublist
--         contains the information about the port 1 up to the port
--         'numPortsInPortList'. The 2nd sublist contains the
--         information about the port 'numPortsInPortList + 1'
--         up to the port '2*numPortsInPortList', etc.
--             ALCATEL NOTE:
--                 ACCESS:     NA       USAGE:      NA
--                 PERSIST:    NO       INSRVMOD:   NO
--                 RANGE:      NA       DEFVALUE:   1
--                 UNITS:      NA       SPARSE:     NA
--                 DESCR:      NA"
--      ::= { extendVlanCurrentBrPortsEntry 1}

--   extendVlanCurrentBrEgressPorts   OBJECT-TYPE
--      SYNTAX   PortList
--      ACCESS   read-only
--      STATUS   mandatory
--      DESCRIPTION
--         "The list of ports that are statically or dynamically associated
--         ports for thisVlan.
--             ALCATEL NOTE:
--                 ACCESS:     NA       USAGE:      NA
--                 PERSIST:    NO       INSRVMOD:   NO
--                 RANGE:      NA       DEFVALUE:   NA
--                 UNITS:      NA       SPARSE:     NA
--                 DESCR:      NA"
--      ::= { extendVlanCurrentBrPortsEntry 2}

--

	extendVlanCurrentVlanlayer2TermList OBJECT-TYPE
		SYNTAX	VlanList
		ACCESS	read-only
		STATUS	mandatory
		DESCRIPTION
			"The VLAN list currently configured with the layer 2 termination. 
			This is the set of Vlans configured in the 
			extendVlanStaticTable for which the object 
			extendVlanStaticSystemMode has the value layer2Terminated. 
			A 1 indicates an entry for this VLAN exists and is 
			configured with the layer2Terminated mode, a 0 indicates 
			no corresponding entry exists or it is configured in the 
			residential bridge or crossconnect mode.
             ALCATEL NOTE:
                 ACCESS:     NA       USAGE:      NA
                 PERSIST:    NO       INSRVMOD:   NO
                 RANGE:      NA       DEFVALUE:   all '0'
                 UNITS:      NA       SPARSE:     NA
                 DESCR:      NA"
		::= { plimExtendVlan 22 }
		
		extendMaxSupportedLayer2TermVlans OBJECT-TYPE
		SYNTAX	Gauge
		ACCESS	read-only
		STATUS	mandatory
		DESCRIPTION
			"This object identifies the maximum number of VLans that can
			be in the mode layer2Terminated.
             ALCATEL NOTE:
                 ACCESS:     NA       USAGE:      NA
                 PERSIST:    NO       INSRVMOD:   NO
                 RANGE:      NA       DEFVALUE:   5372
                 UNITS:      NA       SPARSE:     NA
                 DESCR:      NA"
		::= { plimExtendVlan 23}

-- FTTU Note: The following table is added for FGU4.0:
-- ISAM Note: The table is introduced to ISAM R3.3 for Abstract Low Layer Interface(BDFhw52911)
-- ==========================
-- The Table to configure UNI(User Network Interface) interfaces as ports of the Bridge
-- ==========================

        extendUniPortTable OBJECT-TYPE
                SYNTAX        SEQUENCE OF ExtendUniPortEntry
                ACCESS        not-accessible
                STATUS        mandatory
                DESCRIPTION
                    "A table that contains all the UNIs that are configured to support bridging functionality. The IfIndex is that of the UNI.
             ALCATEL NOTE:
                        TABLESIZE:  DEP [depends on the value of dot1dBaseNumPorts] 
                        DESCR:      NA"
                ::= { plimExtendVlan 25 }

        extendUniPortEntry OBJECT-TYPE
                SYNTAX        ExtendUniPortEntry 
                ACCESS        not-accessible
                STATUS        mandatory
                DESCRIPTION
                        "An entry in the UniPortTable representing one UNI."
                INDEX        { ifIndex }
                ::= { extendUniPortTable 1 }

        ExtendUniPortEntry ::=
                SEQUENCE        {
                    extendUniPortDot1dBasePort
                        INTEGER,
                    extendUniPortRowStatus
                        RowStatus,
                    extendUniPortIfIndex
                        INTEGER
--                  extendUniPortType
--                      INTEGER
                }

        extendUniPortDot1dBasePort OBJECT-TYPE
                SYNTAX        INTEGER (1..2147483647)
                ACCESS        read-only
                STATUS        mandatory
                DESCRIPTION
               "The port identifier assigned by the system to this UNI.
                    A port identifier identifies uniquely a port of the VLAN-Bridge
                    within the system.
                 ALCATEL NOTE:
                        ACCESS:     RO       USAGE:      NA
                        PERSIST:    YES      INSRVMOD:   NO
                        RANGE:      NA       DEFVALUE:   NA
                        UNITS:      NA       SPARSE:     NA
                        DESCR:      NA"
                ::= { extendUniPortEntry 1 }

        extendUniPortRowStatus OBJECT-TYPE
                SYNTAX        RowStatus
                ACCESS        read-write
                STATUS        mandatory
                DESCRIPTION
"This object indicates the status of this entry.
                 ALCATEL NOTE:
                        ACCESS:     NA       USAGE:      MAND
                        PERSIST:    NO       INSRVMOD:   NO
                        RANGE:      1,4,6    DEFVALUE:   NA
                        UNITS:      NA       SPARSE:     NA
                        DESCR:      NA"
                ::= { extendUniPortEntry 2 }

         extendUniPortIfIndex OBJECT-TYPE
                SYNTAX        INTEGER
                ACCESS        read-only
                STATUS        mandatory
                DESCRIPTION
                    "IfIndex of the dot1dBasePort
                 ALCATEL NOTE:
                        ACCESS:     RO       USAGE:      NA
                        PERSIST:    YES      INSRVMOD:   NO
                        RANGE:      NA       DEFVALUE:   NA
                        UNITS:      NA       SPARSE:     NA
                        DESCR:      NA"
                ::= { extendUniPortEntry 3 }

--         extendUniPortType OBJECT-TYPE
--                SYNTAX  INTEGER {
--                      enet(1),
--                      vdsl(2),
--                      voip(3),
--                      moca(4)
--                }
--                ACCESS        read-write
--                STATUS        mandatory
--                DESCRIPTION
--                        "Type of the underlying UniPort"
--                ::= { extendUniPortEntry 4 }



--   extendCurrentVlanPortAssociationTable OBJECT-TYPE
--      SYNTAX   SEQUENCE OF ExtendCurrentVlanPortAssociationEntry
--      ACCESS   not-accessible
--      STATUS   mandatory
--      DESCRIPTION
--        "This table contains dynamic or static (if no dynamic) VLAN-port
--        interface and network VLAN attachments: the table
--        represents the static data until these static data are overruled by
--        dynamic data, typically applied after port authentication using the
--        Radius protocol
--             ALCATEL NOTE:
--             TABLESIZE: DEP [depends on the tablesize of
--extendCurrentPortVlanAssociationTable.]
--                 DESCR:      NA "
--      ::= { plimExtendVlan 26 }

--   extendCurrentVlanPortAssociationEntry OBJECT-TYPE
--      SYNTAX   ExtendCurrentVlanPortAssociationEntry
--      ACCESS   not-accessible
--      STATUS   mandatory
--      DESCRIPTION
--         "A VLAN-port interface and network VLAN attachment."
--      INDEX   { dot1qVlanIndex, extendCurrentVlanPortPortId }
--      ::= { extendCurrentVlanPortAssociationTable 1 }

--   ExtendCurrentVlanPortAssociationEntry ::=
--      SEQUENCE   {
--            extendCurrentVlanPortPortId
--               INTEGER,
--            extendCurrentVlanPortSubscriberVlan
--               VlanIndex,
--            extendCurrentVlanPortDynamicAttach
--               INTEGER
--            }

--   extendCurrentVlanPortPortId OBJECT-TYPE
--      SYNTAX   INTEGER
--      ACCESS   read-only
--      STATUS   mandatory
--      DESCRIPTION
--         "Id of a bridge port containing VLAN endpoints (identified by
--             extendCurrentVlanPortSubscriberVlan) that are attached to
--             the network VLAN identified by dot1qVlanIndex.
--             ALCATEL NOTE:
--                 ACCESS:     NA       USAGE:      NA
--                 PERSIST:    NO       INSRVMOD:   NO
--                 RANGE:      NA       DEFVALUE:   NA
--                 UNITS:      NA       SPARSE:     NA
--                 DESCR:      NA"
--     ::= { extendCurrentVlanPortAssociationEntry 1 }

--  extendCurrentVlanPortSubscriberVlan OBJECT-TYPE
--      SYNTAX   VlanIndex
--      ACCESS   read-only
--      STATUS   mandatory
--      DESCRIPTION
--      "This object indicates the subscriber VLAN associated to bridge port.
--             ALCATEL NOTE:
--                 ACCESS:     NA       USAGE:      NA
--                 PERSIST:    NO       INSRVMOD:   NO
--                 RANGE:      NA       DEFVALUE:   NA
--                 UNITS:      NA       SPARSE:     NA
--                 DESCR:      NA"
--      ::= { extendCurrentVlanPortAssociationEntry 2 }

--   extendCurrentVlanPortDynamicAttach OBJECT-TYPE
--      SYNTAX  INTEGER
--            {
--            true(1),
--            false(2)
--            }
--      ACCESS  read-only
--      STATUS  mandatory
--      DESCRIPTION
--      "If one of the objects in the table entry is dynamic, the value shall
--       be true.
--             ALCATEL NOTE:
--                 ACCESS:     NA       USAGE:      NA
--                 PERSIST:    NO       INSRVMOD:   NO
--                 RANGE:      1,2      DEFVALUE:   2[false]
--                 UNITS:      NA       SPARSE:     NA
--                 DESCR:      NA"
--      ::= { extendCurrentVlanPortAssociationEntry 3 }

-- ==========================================================================
-- The  table will reflect the forwarder interfaces contained in the specified L2 forwarder.
-- ==========================================================================

	extendL2ForwarderContainerTable  OBJECT-TYPE
		SYNTAX	SEQUENCE OF ExtendL2ForwarderContainerEntry
		ACCESS	not-accessible
		STATUS	mandatory
		DESCRIPTION
			" This table is a search table for L2 forwarder interfaces, per FdbId. It contains the same entries as the extendPortVlanAssociationTable, but without attributes and ordered according to the FdbId. .
             ALCATEL NOTE:
                 TABLESIZE:  DEP [depends on the tablesize of
                             extendPortVlanAssociationTable]
                 DESCR:     The L2 forwarder interface is subscriber VLAN.port in this table"

		::= { plimExtendVlan 27 }

	extendL2ForwarderContainerEntry  OBJECT-TYPE
		SYNTAX	ExtendL2ForwarderContainerEntry
		ACCESS	not-accessible
		STATUS	mandatory
		DESCRIPTION
			"A L2 forwarder interface and a L2 forwarder association."
		INDEX	{ dot1qVlanIndex, extendL2ForwarderContainerInterfaceIndex  }
		::= { extendL2ForwarderContainerTable 1 }

	ExtendL2ForwarderContainerEntry ::=
		SEQUENCE	{
			extendL2ForwarderContainerInterfaceIndex
				INTEGER,
			extendL2ForwarderAssociationType
        INTEGER
			}

	extendL2ForwarderContainerInterfaceIndex OBJECT-TYPE
		SYNTAX	INTEGER
		ACCESS	read-only
		STATUS	mandatory
		DESCRIPTION
			"The ifIndex of a L2 forwarder interface.
             ALCATEL NOTE:
                 ACCESS:     NA       USAGE:      NA
                 PERSIST:    NO       INSRVMOD:   NO
                 RANGE:      NA       DEFVALUE:   NA
                 UNITS:      NA       SPARSE:     NA
                 DESCR:      identify a subscriber vlan.port"
		::= { extendL2ForwarderContainerEntry 1 }

extendL2ForwarderAssociationType OBJECT-TYPE
		SYNTAX	INTEGER { static(1),  dynamic(2)	 }
		ACCESS	read-only
		STATUS	mandatory
		DESCRIPTION
			" The type of association is static or dynamic 
             ALCATEL NOTE:
                 ACCESS:     NA       USAGE:      NA
                 PERSIST:    NO       INSRVMOD:   NO
                 RANGE:      NA       DEFVALUE:   NA
                 UNITS:      NA       SPARSE:     NA
                 DESCR:      The type of Association"
		::= { extendL2ForwarderContainerEntry 2 }

-- ==========================================================================
-- Extend Static
-- ==========================================================================

plimExtendStatic	OBJECT IDENTIFIER ::= {plimEthernet 3}

	extendStaticUnicastTable OBJECT-TYPE
		SYNTAX	SEQUENCE OF ExtendStaticUnicastEntry
		ACCESS	not-accessible
		STATUS	mandatory
		DESCRIPTION
			"This table is a proprietary variant on the table 
			dot1qStaticUnicast Table defined in the Q-BRIDGE-MIB.
			It is a table containing filtering information for Unicast
			MAC addresses for each Filtering Database, configured
			into the device by (local or network) management
			specifying the set of ports to which frames received
			from specific ports and containing specific unicast
			destination addresses are allowed to be forwarded. A
			value of zero in this table as the port number from
			which frames with a specific destination address are
			received, is used to specify all ports for which there
			is no specific entry in this table for that particular
			destination address.  Entries are valid for unicast
			addresses only.
			Note: in NBE, only the Local User VLAN can be used as
			index of this table. 
             ALCATEL NOTE:
                 TABLESIZE:  DEP [nbr of unicast addresses/board * nbr of 
                                 boards] "
		::= { plimExtendStatic 1 }

	extendStaticUnicastEntry OBJECT-TYPE
		SYNTAX	ExtendStaticUnicastEntry 
		ACCESS	not-accessible
		STATUS	mandatory
		DESCRIPTION
			"An entry in the table extendStaticUnicastTable. One entry 
			exists in this table for each Unicast MAC address statically 
			configured within a Vlan.
			Filtering information configured into the device by
			(local or network) management specifying the port to 
			which frames received from the Ethernet port and
			containing a specific unicast destination address is
			forwarded."
		INDEX	{ dot1qFdbId, extendStaticUnicastAddress}
		::= { extendStaticUnicastTable 1 }

	ExtendStaticUnicastEntry ::=
		SEQUENCE	{ 
				extendStaticUnicastAddress
					MacAddress,
				extendStaticUnicastAllowedToGoTo
					INTEGER,
				extendStaticUnicastStatus
					INTEGER
				}

	extendStaticUnicastAddress OBJECT-TYPE
		SYNTAX	MacAddress
		ACCESS	not-accessible
		STATUS	mandatory
		DESCRIPTION
			"The destination MAC address in a frame to which this
			entry's filtering information applies. This object must
			take the value of a unicast address.
             ALCATEL NOTE:
                 ACCESS:     NA       USAGE:      NA
                 PERSIST:    YES      INSRVMOD:   NO
                 RANGE:      NA       DEFVALUE:   NA
                 UNITS:      NA       SPARSE:     NA
                 DESCR:      NA"
		::= { extendStaticUnicastEntry 1 }

	extendStaticUnicastAllowedToGoTo	OBJECT-TYPE
		SYNTAX	INTEGER (0..2147483647)
		ACCESS	read-write
		STATUS	mandatory
		DESCRIPTION
			"This object identifies the port number of the ATM PVC port on 
			which a frame received over the Ethernet interface will be sent. 
			It also specifies the port a specific unicast address 
			may be dynamically learnt on. 

			This approach reflects the inability of the system to flood 
			frames to various ports. It therefore is equivalent to the 
			object dot1qStaticUnicastAllowedToGoTo but with the 
			difference it is 1 port in stead of a list.
             ALCATEL NOTE:
                 ACCESS:     NA       USAGE:      MAND
                 PERSIST:    YES      INSRVMOD:   NO
                 RANGE:      NA       DEFVALUE:   NA
                 UNITS:      NA       SPARSE:     NA
                 DESCR:      NA"
		::= { extendStaticUnicastEntry 2}

	extendStaticUnicastStatus OBJECT-TYPE
		SYNTAX	INTEGER {
					other(1),
					invalid(2),
					permanent(3),
					deleteOnReset(4),
					deleteOnTimeout(5)
					}
		ACCESS	read-write
		STATUS	mandatory
		DESCRIPTION
			"This object indicates the status of this entry.
			other(1) - this entry is currently in use but
				the conditions under which it will remain
				so differ from the following values.
			invalid(2) - writing this value to the object
				removes the corresponding entry.
			permanent(3) - this entry is currently in use
				and will remain so after the next reset of
				the bridge.
			deleteOnReset(4) - this entry is currently in
				use and will remain so until the next
				reset of the bridge.
			deleteOnTimeout(5) - this entry is currently in
				use and will remain so until it is aged out.
             ALCATEL NOTE:
                 ACCESS:     NA       USAGE:      MAND
                 PERSIST:    NO       INSRVMOD:   YES
                 RANGE:      NA       DEFVALUE:   permanent
                 UNITS:      NA       SPARSE:     NA
                 DESCR:      NA"
		DEFVAL	{ permanent }
		::= { extendStaticUnicastEntry 3 }

-- ==========================================================================

--	extendStaticMulticastTable OBJECT-TYPE
--		SYNTAX	SEQUENCE OF ExtendStaticMulticastEntry
--		ACCESS	not-accessible
--		STATUS	mandatory
--		DESCRIPTION
--			"This table is a proprietary variant on the table 
--			dot1qStaticMulticast Table defined in the Q-BRIDGE-MIB.
--			It is a table containing filtering information for Multicast
--			and Broadcast MAC addresses for each VLAN, configured
--			into the device by (local or network) management
--			specifying the set of ports to which frames received
--			from specific ports and containing specific Multicast
--			and Broadcast destination addresses are allowed to be
--			forwarded. A value of zero in this table as the port
--			number from which frames with a specific destination
--			address are received, is used to specify all ports for
--			which there is no specific entry in this table for that
--			particular destination address. Entries are valid for
--			Multicast and Broadcast addresses only."
--		::= { plimExtendStatic 2 }

--	extendStaticMulticastEntry OBJECT-TYPE
--		SYNTAX	ExtendStaticMulticastEntry
--		ACCESS	not-accessible
--		STATUS	mandatory
--		DESCRIPTION
--			"An entry in the table extendStaticMulticastTable.
--			Filtering information configured into the device by
--			(local or network) management specifying the set of
--			ports to which frames received from this specific port
--			for this VLAN and containing this Multicast or Broadcast
--			destination address are allowed to be forwarded."
--		INDEX	{ dot1qVlanIndex, extendStaticMulticastAddress}
--		::= { extendStaticMulticastTable 1 }

--	ExtendStaticMulticastEntry ::=
--		SEQUENCE	{
--				extendStaticMulticastAddress
--					MacAddress,
--				extendStaticMulticastStaticEgressPort
--					INTEGER,
--				extendStaticMulticastStatus
--					INTEGER
--				}

--	extendStaticMulticastAddress OBJECT-TYPE
--		SYNTAX	MacAddress
--		ACCESS	not-accessible
--		STATUS	mandatory
--		DESCRIPTION
--			"The destination MAC address in a frame to which this
--			entry's filtering information applies. This object must
--			take the value of a Multicast or Broadcast address."
--		::= { extendStaticMulticastEntry 1 }

--	extendStaticMulticastStaticEgressPort	OBJECT-TYPE
--		SYNTAX	INTEGER (0..65535)
--		ACCESS	read-write
--		STATUS	mandatory
--		DESCRIPTION
--			"This object identifies the ATM PVC port on which a 
--			frame received over the Ethernet interface will be sent.
--			This only applies to ports that are members of the VLAN,
--			defined by extendVlanStaticBrEgressPorts.
--			(This approach reflects the usability of the system to flood 
--			frames to various ports. It therefore is equivalent to the 
--			object dot1qStaticMulticastStaticEgressPorts but with the 
--			difference it is 1 port in stead of a list."
--		::= { extendStaticMulticastEntry 2}

--	extendStaticMulticastStatus OBJECT-TYPE
--		SYNTAX	INTEGER {
--                    other(1),
--                    invalid(2),
--                    permanent(3),
--                    deleteOnReset(4),
--                    deleteOnTimeout(5)
--                }
--		ACCESS	read-write
--		STATUS	mandatory
--		DESCRIPTION
--			"This object indicates the status of this entry.
--			other(1) - this entry is currently in use but
--				the conditions under which it will remain
--				so differ from the following values.
--			invalid(2) - writing this value to the object
--				removes the corresponding entry.
--			permanent(3) - this entry is currently in use
--				and will remain so after the next reset of
--				the bridge.
--			deleteOnReset(4) - this entry is currently in
--				use and will remain so until the next
--				reset of the bridge.
--			deleteOnTimeout(5) - this entry is currently in
--				use and will remain so until it is aged out."
--		DEFVAL	{ permanent }
--		::= { extendStaticMulticastEntry 3 }

-- ==========================================================================

--   extendPortVlanMacTable OBJECT-TYPE
--      SYNTAX   SEQUENCE OF ExtendPortVlanMacEntry
--      ACCESS   not-accessible
--      STATUS   mandatory
--      DESCRIPTION
--           "A table representing the information available in the tables:
--         extendStaticUnicastTable / extendStaticMulticastTable.
--         but represented in another way to give efficient read-access
--         in case the port is known information.
--             ALCATEL NOTE:
--                 TABLESIZE:  DEP [depends on the tablesize of
--                             extendStaticUnicastTable]
--                 DESCR:      NA"
--      ::= { plimExtendStatic 3 }

--   extendPortVlanMacEntry OBJECT-TYPE
--      SYNTAX   ExtendPortVlanMacEntry
--      ACCESS   not-accessible
--      STATUS   mandatory
--      DESCRIPTION
--        "An entry in the table extendPortVlanMacTable. One entry represents
--         the information on the usage of one MAC address within the scope
--         of one Vlan as used on one port."
--      INDEX   { dot1dBasePort,
--             extendPortVlanMacVlanIndex,
--             extendPortVlanMacMacAddress }
--      ::= { extendPortVlanMacTable 1 }

--   ExtendPortVlanMacEntry ::=
--      SEQUENCE {
--         extendPortVlanMacVlanIndex
 --           VlanIndex,
 --        extendPortVlanMacMacAddress
 --           MacAddress
 --           }

 --  extendPortVlanMacVlanIndex   OBJECT-TYPE
 --     SYNTAX   VlanIndex
 --     ACCESS   read-only
 --     STATUS   mandatory
 --     DESCRIPTION
 --        "Identifies a Vlan.
 --            ALCATEL NOTE:
 --                ACCESS:     NA       USAGE:      NA
 --                PERSIST:    NO       INSRVMOD:   NO
 --                RANGE:      NA       DEFVALUE:   NA
 --                UNITS:      NA       SPARSE:     NA
 --                DESCR:      NA"
 --     ::= { extendPortVlanMacEntry 1 }

 --  extendPortVlanMacMacAddress    OBJECT-TYPE
 --     SYNTAX   MacAddress
 --     ACCESS   read-only
 --     STATUS   mandatory
 --     DESCRIPTION
 --        "The destination MAC address in a frame to which this
 --        entry's filtering information applies.  This object can
 --        have the value of a unicast as well as the value of a
 --        multicast address.
 --            ALCATEL NOTE:
 --                ACCESS:     NA       USAGE:      NA
 --                PERSIST:    NO       INSRVMOD:   NO
 --                RANGE:      NA       DEFVALUE:   NA
 --                UNITS:      NA       SPARSE:     NA
 --                DESCR:      NA"
 --     ::= { extendPortVlanMacEntry 2 }


	extendDupMacAlarmTable OBJECT-TYPE
		SYNTAX	SEQUENCE OF ExtendDupMacAlarmEntry 
		ACCESS	not-accessible
		STATUS	mandatory
		DESCRIPTION
	                "A table containing the information for every dupplicate MAC 
                    alarm generated by the system. The entry exists as long as the 
                    alarm is on.the entry is removed when the alarm is off.
                    ALCATEL NOTE:
                    TABLESIZE:  DEP [depends on (max unicast MAC number per LIM)*(num LIM of system)]
                    DESCR:      NA"
		::= { plimExtendStatic 4 }

	extendDupMacAlarmEntry OBJECT-TYPE
		SYNTAX	ExtendDupMacAlarmEntry 
		ACCESS	not-accessible
		STATUS	mandatory
		DESCRIPTION
			"An entry in the table extendDupMacAlarmTable. One entry represents 
			an alarm that is on."
		INDEX   { extendDupMacPortAlarm,
				 extendDupMacFdbId,
				 extendDupMacMacAddress }
		::= { extendDupMacAlarmTable 1 }

	ExtendDupMacAlarmEntry ::=
		SEQUENCE {
			extendDupMacPortAlarm
				INTEGER (1..2147483647),
			extendDupMacFdbId
				Gauge,
			extendDupMacMacAddress
				MacAddress,
			extendDupMacPortAssigned
                            INTEGER (1..2147483647) ,
			extendDupMacSubscriberVlanAlarm
			    VlanIndex,
			extendDupMacSubscriberVlanAssigned
			    VlanIndex
				}

	extendDupMacPortAlarm	OBJECT-TYPE
		SYNTAX	INTEGER (1..2147483647)
		ACCESS	read-only
		STATUS	mandatory
		DESCRIPTION
			"The port identifier of the port on which the self learning of a 
			MAC-address is rejected.
             ALCATEL NOTE:
                 ACCESS:     NA       USAGE:      NA
                 PERSIST:    NO       INSRVMOD:   NO
                 RANGE:      NA       DEFVALUE:   NA
                 UNITS:      NA       SPARSE:     NA
                 DESCR:      NA"
		::= { extendDupMacAlarmEntry 1 }

	extendDupMacFdbId	OBJECT-TYPE
		SYNTAX	Gauge
		ACCESS	read-only
		STATUS	mandatory
		DESCRIPTION
			"The Filtering Database within which the self learning of a 
			MAC-address is rejected.
             ALCATEL NOTE:
                 ACCESS:     NA       USAGE:      NA
                 PERSIST:    NO       INSRVMOD:   NO
                 RANGE:      NA       DEFVALUE:   NA
                 UNITS:      NA       SPARSE:     NA
                 DESCR:      NA"
		::= { extendDupMacAlarmEntry 2 }

	extendDupMacMacAddress	OBJECT-TYPE
		SYNTAX	MacAddress
		ACCESS	read-only
		STATUS	mandatory
		DESCRIPTION
			"The MAC address that could not be learned on the port identified 
			with extendDupMacPortAlarm within the FDB identified by the object 
			extendDupMacFdbId.
             ALCATEL NOTE:
                 ACCESS:     NA       USAGE:      NA
                 PERSIST:    NO       INSRVMOD:   NO
                 RANGE:      NA       DEFVALUE:   NA
                 UNITS:      NA       SPARSE:     NA
                 DESCR:      NA"
		::= { extendDupMacAlarmEntry 3 }

	extendDupMacPortAssigned	OBJECT-TYPE
		SYNTAX	INTEGER (1..2147483647)
		ACCESS	read-only
		STATUS	mandatory
		DESCRIPTION
			"The port identifier of the port on which the MAC address identified
			by the object extendDupMacMacAddress is already learned or 
			statically configured within the FDB identified by the object
			extendDupMacFdbId. Because MAC addresses shall be unique per FDB 
			this gives also the reason why the MAc address could not be learned 
			on the port identified by the object extendDupMacPortAlarm.
             ALCATEL NOTE:
                 ACCESS:     NA       USAGE:      NA
                 PERSIST:    NO       INSRVMOD:   NO
                 RANGE:      NA       DEFVALUE:   NA
                 UNITS:      NA       SPARSE:     NA
                 DESCR:      NA"
		::= { extendDupMacAlarmEntry 4 }

	extendDupMacSubscriberVlanAlarm 	OBJECT-TYPE
		SYNTAX	VlanIndex
		ACCESS	read-only
		STATUS	mandatory
		DESCRIPTION
			" The subscriber vlan which, together with the extendDupMacPortAlarm, identifies the vlan port on which the self learning of a MAC-address is rejected due to MAC-address duplicating with a learned or a static MAC-address in the same forwarder.
             ALCATEL NOTE:
                 ACCESS:     NA       USAGE:      NA
                 PERSIST:    NO       INSRVMOD:   NO
                 RANGE:      NA       DEFVALUE:   NA
                 UNITS:      NA       SPARSE:     NA
                 DESCR:      NA"
		::= { extendDupMacAlarmEntry 5 }

  	extendDupMacSubscriberVlanAssigned	OBJECT-TYPE
		SYNTAX	VlanIndex
		ACCESS	read-only
		STATUS	mandatory
		DESCRIPTION
			" The subscriber vlan which, together with the extendDupMacPortAssigned,identifies the vlan port on which the MAC address identified by the object extendDupMacMacAddress is  already learned or statically configured within the FDB identified by the object extendDupMacFdbId.
             ALCATEL NOTE:
                 ACCESS:     NA       USAGE:      NA
                 PERSIST:    NO       INSRVMOD:   NO
                 RANGE:      NA       DEFVALUE:   NA
                 UNITS:      NA       SPARSE:     NA
                 DESCR:      NA"
		::= { extendDupMacAlarmEntry 6 }

--========================================================================
-- A new tabe set the static unicatst MAC address per user port
--=========================================================================


	extendUserPortStaticUnicastTable OBJECT-TYPE
		SYNTAX	SEQUENCE OF ExtendUserPortStaticUnicastEntry
		ACCESS	not-accessible
		STATUS	mandatory
		DESCRIPTION
			"This table is a proprietary variant on the table
			dot1qStaticUnicast Table defined in the Q-BRIDGE-MIB.
			It is a table containing filtering information for Unicast
			MAC addresses for each subscriber forwarder interfaces, 					configured into the device by (local or network) management.
			 ALCATEL NOTE:
                 TABLESIZE:  DEP [nbr of unicast addresses/board * nbr of
                                 boards]
                 DESCR:      Subscriber forwarder interface refers to subscriber VLAN.Port in this table."

		::= { plimExtendStatic 7 }

	extendUserPortStaticUnicastEntry OBJECT-TYPE
		SYNTAX	ExtendUserPortStaticUnicastEntry
		ACCESS	not-accessible
		STATUS	mandatory
		DESCRIPTION
			" An entry in extenUserPortStaticUnicastTable identifies one
             Unicast MAC address statically configured on a subscriber
             forwarder interface."
		INDEX	{ ifIndex, extendUserPortStaticUnicastAddress }
		::= { extendUserPortStaticUnicastTable 1 }

	ExtendUserPortStaticUnicastEntry ::=
		SEQUENCE	{
				extendUserPortStaticUnicastAddress
					MacAddress,
				extendUserPortStaticUnicastStatus
					INTEGER,
				extendUserPortStaticUnicastFdbId
					Gauge
				}


	extendUserPortStaticUnicastAddress OBJECT-TYPE
		SYNTAX	MacAddress
		ACCESS	not-accessible
		STATUS	mandatory
		DESCRIPTION
			"The source MAC address in a frame from a subscriber forwarder
            interface. This object must take the value of a unicast address.
             ALCATEL NOTE:
                 ACCESS:     NA       USAGE:      NA
                 PERSIST:    YES      INSRVMOD:   NO
                 RANGE:      NA       DEFVALUE:   NA
                 UNITS:      NA       SPARSE:     NA
                 DESCR:      the forwarder interface refers to a vlan.port"
		::= { extendUserPortStaticUnicastEntry 1 }


	extendUserPortStaticUnicastStatus OBJECT-TYPE
		SYNTAX	INTEGER {
					other(1),
					invalid(2),
					permanent(3),
					deleteOnReset(4),
					deleteOnTimeout(5)
					}
		ACCESS	read-write
		STATUS	mandatory
		DESCRIPTION
			"This object indicates the status of this entry.
			other(1) - this entry is currently in use but
				the conditions under which it will remain
				so differ from the following values.
			invalid(2) - writing this value to the object
				removes the corresponding entry.
			permanent(3) - this entry is currently in use
				and will remain so after the next reset of
				the bridge.
			deleteOnReset(4) - this entry is currently in
				use and will remain so until the next
				reset of the bridge.
			deleteOnTimeout(5) - this entry is currently in
				use and will remain so until it is aged out.
             ALCATEL NOTE:
                 ACCESS:     NA       USAGE:      NA
                 PERSIST:    NO       INSRVMOD:   YES
                 RANGE: invalid(2),permanent(3)   DEFVALUE:   permanent
                 UNITS:      NA       SPARSE:     NA
                 DESCR:      NA"
		DEFVAL	{ permanent }
		::= { extendUserPortStaticUnicastEntry 2 }

	extendUserPortStaticUnicastFdbId	OBJECT-TYPE
		SYNTAX	Gauge
		ACCESS	read-only
		STATUS	mandatory
		DESCRIPTION
			"Identifies a L2 forwarder to which the forwarder interface attaches .

             ALCATEL NOTE:
                 ACCESS:     NA       USAGE:      NA
                 PERSIST:    NO       INSRVMOD:   NO
                 RANGE:      NA       DEFVALUE:   NA
                 UNITS:      NA       SPARSE:     NA
                 DESCR:      forwarder interface refers to a vlan.port"
		::= { extendUserPortStaticUnicastEntry 3 }


-- ===================================================================
-- The following group of objects is used to manage the relationship
-- between the ATM Service Category of an ATM VCC over which Ethernet
-- frames are received and the priority to be assigned to the frame
-- when the frame is forwarded.
-- ===================================================================

plimPriorityMapping	OBJECT IDENTIFIER ::= {plimEthernet 4}

--	atmToEthPriorityMapping OBJECT-TYPE
--		SYNTAX	INTEGER {enabled(1),disabled(2)}
--		ACCESS	read-write
--		STATUS	mandatory
--		DESCRIPTION
--			"Object indicating whether the mapping from the ATM Service 
--			Category to the Ethernet priority tag is enabled or disabled."
--		::= { plimPriorityMapping 1 }

--	atmToEthPriorityMappingTable OBJECT-TYPE
--		SYNTAX	SEQUENCE OF AtmToEthPriorityMappingEntry
--		ACCESS	not-accessible
--		STATUS	mandatory
--		DESCRIPTION
--			"A table containing the mapping information from the ATM
--			Service Category to derived information. An entry will 
--			exist for each ATM Service Category supported by the system."
--		::= { plimPriorityMapping 2}

--	atmToEthPriorityMappingEntry OBJECT-TYPE
--		SYNTAX	AtmToEthPriorityMappingEntry
--		ACCESS	not-accessible
--		STATUS	mandatory
--		DESCRIPTION
--			"An entry in the table atmToEthPriorityMappingTable. One entry
--			specifies the information for one ATM Service Category."
--		INDEX	{ atmToEthPrioMapAtmServiceCategory }
--		::= { atmToEthPriorityMappingTable 1 }

--	AtmToEthPriorityMappingEntry ::=
--		SEQUENCE	{
--				atmToEthPrioMapAtmServiceCategory
--					AtmServiceCategory,
--				atmToEthPrioMapEthPriority
--					ExtendVlanSystemPriority
--				}

--	atmToEthPrioMapAtmServiceCategory	OBJECT-TYPE
--		SYNTAX	AtmServiceCategory
--		ACCESS	not-accessible
--		STATUS	mandatory
--		DESCRIPTION
--			"The ATM Service Category."
--		::= { atmToEthPriorityMappingEntry 1}

--	atmToEthPrioMapEthPriority	OBJECT-TYPE
--		SYNTAX	ExtendVlanSystemPriority 
--		ACCESS	read-write
--		STATUS	mandatory
--		DESCRIPTION
--			"The Ethernet priority tag to be set in upstream frames sent
--			over the Ethernet interface."
--		::= { atmToEthPriorityMappingEntry 2}

	priorityMappingSwitch OBJECT-TYPE
		SYNTAX	INTEGER {
					vlanId(1),
					atmServiceCategory(2),
					portDefault(3)
						}
		ACCESS	read-write
		STATUS	mandatory
		DESCRIPTION
			"Object indicating the Ethernet priority tag of the upstream frames
			is mapping from the VLAN Id, or ATM Service Category or port default
			priority.
             ALCATEL NOTE:
                 ACCESS:     NA       USAGE:      NA
                 PERSIST:    YES      INSRVMOD:   YES
                 RANGE:      1,2,3    DEFVALUE:   3[portDefault]
                 UNITS:      NA       SPARSE:     NA
                 DESCR:      NA"
		::= { plimPriorityMapping 3 }

--

	plimL2PriorityRegenerationProfileTable OBJECT-TYPE
		SYNTAX	SEQUENCE OF PlimL2PriorityRegenerationProfileEntry
		ACCESS	not-accessible
		STATUS	mandatory
		DESCRIPTION
			"Priotity bit regeneration profile table (a profile includes both 
			upstream and downstream p bit translation). The first 10 profiles
			are fixed and are not allowed to be modified. First 10 profiles
   can be used on either DSL or GPON interfaces. Last 22 profiles can
   only be used on GPON interfaces.
             ALCATEL NOTE:
                 TABLESIZE:  32
                 DESCR:      "
		::= { plimPriorityMapping 4 }

	plimL2PriorityRegenerationProfileEntry	OBJECT-TYPE
		SYNTAX	PlimL2PriorityRegenerationProfileEntry
		ACCESS	not-accessible
		STATUS	mandatory
		DESCRIPTION
			"One upstream + downstream priority regeneration profile"
		INDEX	{ plimL2PriorityRegenerationProfileId }
		::= { plimL2PriorityRegenerationProfileTable 1 }

	PlimL2PriorityRegenerationProfileEntry	::=
   SEQUENCE	{
      plimL2PriorityRegenerationProfileId   INTEGER,	
      plimL2PriorityRegenerationProfileName SnmpAdminString (SIZE (0..32)),
      plimL2PriorityRegenerationTableUp     INTEGER, 
      plimL2PriorityRegenerationTableDown   INTEGER,
      plimL2PriorityRegenerationRowstatus   RowStatus,  	
      plimL2PriorityRegenerationRefCount    AsamProfileRefCount    
				}

	plimL2PriorityRegenerationProfileId	 OBJECT-TYPE
		SYNTAX	INTEGER
		ACCESS	read-write
		STATUS	mandatory
		DESCRIPTION
			"This is the index of the regeneration profile
             ALCATEL NOTE:
                 ACCESS:     RW       USAGE:      NA
                 PERSIST:    YES      INSRVMOD:   NO
                 RANGE:      NA       DEFVALUE:   NA
                 UNITS:      NA       SPARSE:     NA
                 DESCR:      NA"
		::= { plimL2PriorityRegenerationProfileEntry 1 }

	plimL2PriorityRegenerationProfileName	 OBJECT-TYPE
		SYNTAX	SnmpAdminString (SIZE (0..32))
		ACCESS	read-write
		STATUS	mandatory
		DESCRIPTION
			"This is the name of the regeneration profile
             ALCATEL NOTE:
                 ACCESS:     RW       USAGE:      NA
                 PERSIST:    YES      INSRVMOD:   NO
                 RANGE:      NA       DEFVALUE:   NA
                 UNITS:      NA       SPARSE:     NA
                 DESCR:      NA"
		::= { plimL2PriorityRegenerationProfileEntry 2 }

	plimL2PriorityRegenerationTableUp OBJECT-TYPE
		SYNTAX  INTEGER (0..4294967295)
		ACCESS  read-write
		STATUS  mandatory
		DESCRIPTION
			"The following mapping applies in upstream direction :
       p-bit codepoint 0 corresponds to bit 0-3, codepoint 1 to bit 4-7,
			The mapping goes from 3 bit to 4 bit for implementation convenience.
			As a consequence, The most significant bit of the new p-bit value is
			not used
			Graphical representation of where to find the regenerated priority in 
			the integer of a received .1p priority codepoint :
			Bit31-28 bit27-24 bit23-20 bit19-16 bit15-bit12 bit11-8 bit7-4 bit3-0 
			   CP7      CP6      CP5      CP4      CP3       CP2     CP1     CP0
             ALCATEL NOTE:
                 ACCESS:     RW       USAGE:      NA
                 PERSIST:    YES      INSRVMOD:   NO
                 RANGE:      NA       DEFVALUE:   NA
                 UNITS:      NA       SPARSE:     NA
                 DESCR:      NA"
		::= { plimL2PriorityRegenerationProfileEntry 3 }
	
	plimL2PriorityRegenerationTableDown OBJECT-TYPE
		SYNTAX  INTEGER (0..4294967295)
		ACCESS  read-write
		STATUS  mandatory
		DESCRIPTION
			"The following mapping applies in downstream direction :
			p-bit codepoint 0 corresponds to bit 0-3, codepoint 1 to bit 4-7
			The mapping goes from 3 bit to 4 bit for implementation convenience.
			As a consequence, The most significant bit of the new p-bit value is
			not used
             ALCATEL NOTE:
                 ACCESS:     RW       USAGE:      NA
                 PERSIST:    YES      INSRVMOD:   NO
                 RANGE:      NA       DEFVALUE:   NA
                 UNITS:      NA       SPARSE:     NA
                 DESCR:      NA"
		::= { plimL2PriorityRegenerationProfileEntry 4 }

	 plimL2PriorityRegenerationRowstatus	OBJECT-TYPE
 	   	SYNTAX      	RowStatus
  		ACCESS  		read-write
  	  	STATUS      	mandatory
   		DESCRIPTION
   		"This object indicates the status of this entry.
         ALCATEL NOTE:
             ACCESS:     RW       USAGE:      NA
             PERSIST:    YES      INSRVMOD:   NO
             RANGE:      1,4,6    DEFVALUE:   NA
             UNITS:      NA       SPARSE:     NA
             DESCR:      NA"
  	  	::= { plimL2PriorityRegenerationProfileEntry 5  }

  plimL2PriorityRegenerationRefCount   OBJECT-TYPE
   SYNTAX         AsamProfileRefCount
   ACCESS         read-only
   STATUS         mandatory
   DESCRIPTION
   "This object indicates the number of entries using this
   profile. If the count is not zero, the profile is in use and
   cannot be deleted. If the count is zero, the profile is not
   in use and can be deleted
   ALCATEL NOTE:
        ACCESS:     RO       USAGE:      NA
        PERSIST:    NO       INSRVMOD:   NO
        RANGE:      NA       DEFVALUE:   0
        UNITS:      NA       SPARSE:     NA
        DESCR:      NA"
   ::= { plimL2PriorityRegenerationProfileEntry 6  }

  plimPriorityRegenerationProfileGetNextFree OBJECT-TYPE
	  SYNTAX INTEGER
	  ACCESS read-only
	  STATUS mandatory
	  DESCRIPTION
   "This object contains an appropriate value to be used
   for PlimL2PriorityRegenerationProfileEntry when creating
   entries in the plimL2PriorityRegenerationProfileTable.
   The value 0 indicates that no unassigned entries are available"
  ::= { plimPriorityMapping 5 }

--
-- PriorityRegenerationProfile name mapping table

 plimL2PriorityRegenerationProfileMappingTable OBJECT-TYPE
	SYNTAX	SEQUENCE OF PlimL2PriorityRegenerationProfileMappingEntry
	ACCESS	not-accessible
	STATUS	mandatory
        DESCRIPTION
        "This object contains a table for PriorityRegenerationProfile name to index mapping"
::= { plimPriorityMapping 9 }

plimL2PriorityRegenerationProfileMappingEntry OBJECT-TYPE
        SYNTAX  PlimL2PriorityRegenerationProfileMappingEntry
        ACCESS  not-accessible
        STATUS mandatory
        DESCRIPTION
        " An entry (conceptual row) representing the  PriorityRegenerationProfile Name to index mapping. "
        INDEX   {plimL2PriorityRegenerationProfileMappingName }
        ::= {plimL2PriorityRegenerationProfileMappingTable  1}
       
     PlimL2PriorityRegenerationProfileMappingEntry ::=
         SEQUENCE {
                   plimL2PriorityRegenerationProfileMappingName SnmpAdminString (SIZE (0..32)),
                   plimL2PriorityRegenerationProfileMappingId   INTEGER
                 }
       
plimL2PriorityRegenerationProfileMappingName OBJECT-TYPE
        SYNTAX  SnmpAdminString (SIZE (0..32))
        ACCESS  not-accessible
        STATUS  mandatory
        DESCRIPTION
                "A text string containing the name of this profile"
::= { plimL2PriorityRegenerationProfileMappingEntry 1}
       
plimL2PriorityRegenerationProfileMappingId OBJECT-TYPE
        SYNTAX  INTEGER
        ACCESS  read-only
        STATUS mandatory
        DESCRIPTION
                "This object is the Profile index."
::= { plimL2PriorityRegenerationProfileMappingEntry 2}
       
-- End of PriorityRegenerationProfile name mapping table

--

-- ======================================================= 
-- The following group of objects is used to retrieve the 
-- forwarding entries in forwarding database.
-- =======================================================

extendForwardingInfo	OBJECT IDENTIFIER ::= {plimEthernet 5}

--	extendForwardingRearrangeTime	OBJECT-TYPE
--		SYNTAX	NetworkTimeInSeconds
--		ACCESS	read-only
--		STATUS	mandatory
--		DESCRIPTION
--			"The time in seconds when the last garbage collection of filter
--			table occurs."
--		::= { extendForwardingInfo 1}

--	extendForwardingTable OBJECT-TYPE
--		SYNTAX	SEQUENCE OF ExtendForwardingEntry
--		ACCESS	not-accessible
--		STATUS	mandatory
--		DESCRIPTION
--			"A table containing the forwarding information. An entry will 
--			exist for each filter ID used by the system."
--		::= { extendForwardingInfo 2}

--	extendForwardingEntry OBJECT-TYPE
--		SYNTAX	ExtendForwardingEntry
--		ACCESS	not-accessible
--		STATUS	mandatory
--		DESCRIPTION
--			"An entry in the table extendForwardingTable. One entry
--			specifies the MAC address information of a specified filter Id."
--		INDEX	{ extendForwardingFilterId }
--		::= { extendForwardingTable 1 }

--	ExtendForwardingEntry ::=
--		SEQUENCE	{
--				extendForwardingFilterId
--					Gauge,
--				extendForwardingMacAddress
--					MacAddress
--				}

--	extendForwardingFilterId	OBJECT-TYPE
--		SYNTAX	Gauge
--		ACCESS	not-accessible
--		STATUS	mandatory
--		DESCRIPTION
--			"The filter identifier."
--		::= { extendForwardingEntry 1}

--	extendForwardingMacAddress	OBJECT-TYPE
--		SYNTAX	MacAddress 
--		ACCESS	read-only
--		STATUS	mandatory
--		DESCRIPTION
--			"The learned Mac address in this filter entry."
--		::= { extendForwardingEntry 2}

-- =====================
-- A table to read out the MAC addresses per VLAN and for these to read on 
-- which port they are learned. Note that the table allows that a MAC 
-- address is learned on two ports.
-- =====================

  -- extendTpFdbTable OBJECT-TYPE
  --    SYNTAX   SEQUENCE OF ExtendTpFdbEntry
  --    ACCESS   not-accessible
  --    STATUS   mandatory
  --    DESCRIPTION
  --       "A table that contains information about unicast entries
  --       for which the device has forwarding and/or filtering
  --       information.  This information is used by the
  --       transparent bridging function in determining how to
  --       propagate a received frame.
  --       This table contains as well the static configured as the
  --       dynamically learned MAC addresses
  --           ALCATEL NOTE:
  --               TABLESIZE:  DEP [Table size of extendTpFdbTable is 16384.
 --It is the value of max system mac number including unicast and broadcast
--mac.]
  --                DESCR:      NA"
  --    ::= { extendForwardingInfo 3 }

  -- extendTpFdbEntry OBJECT-TYPE
  --    SYNTAX   ExtendTpFdbEntry
  --    ACCESS   not-accessible
  --    STATUS   mandatory
  --    DESCRIPTION
  --       "Information about a specific unicast MAC address for
  --       which the device has some forwarding and/or filtering
  --       information."
  --    INDEX   { dot1qFdbId, extendTpFdbAddress, extendTpFdbPort }
  --    ::= { extendTpFdbTable 1 }

  -- ExtendTpFdbEntry ::=
  --    SEQUENCE {
  --       extendTpFdbAddress
  --          MacAddress,
  --       extendTpFdbPort
  --          INTEGER,
  --       extendTpFdbStatus
  --          INTEGER,
   --          extendTpFdbvMacAddress
   --             MacAddress
   --            }

   --extendTpFdbAddress OBJECT-TYPE
   --   SYNTAX   MacAddress
   --   ACCESS  read-only
   --   STATUS   mandatory
   --   DESCRIPTION
   --      "A unicast MAC address for which the device has
   --      forwarding and/or filtering information.
   --          ALCATEL NOTE:
   --              ACCESS:     NA       USAGE:      NA
   --              PERSIST:    NO       INSRVMOD:   NO
   --              RANGE:      NA       DEFVALUE:   NA
   --              UNITS:      NA       SPARSE:     NA
   --              DESCR:      NA"
   --   ::= { extendTpFdbEntry 1 }

   --extendTpFdbPort OBJECT-TYPE
   --   SYNTAX   INTEGER (0..65535)
   --   ACCESS   read-only
   --   STATUS   mandatory
   --   DESCRIPTION
   --      "Either the value '0', or the port number of the port on
   --      which a frame having a source address equal to the value
   --      of the corresponding instance of extendTpFdbAddress has
   --      been seen.  A value of '0' indicates that the port
   --      number has not been learned but that the device does
   --      have some forwarding/filtering information about this
   --      address (e.g. in the dot1qStaticUnicastTable).
   --      Implementors are encouraged to assign the port value to
   --      this object whenever it is learned even for addresses
   --      for which the corresponding value of extendTpFdbStatus is
   --      not learned(3).
   --          ALCATEL NOTE:
   --              ACCESS:     NA       USAGE:      NA
   --              PERSIST:    NO       INSRVMOD:   NO
   --              RANGE:      NA       DEFVALUE:   NA
   --              UNITS:      NA       SPARSE:     NA
   --              DESCR:      NA"
   --   ::= { extendTpFdbEntry 2 }

   --extendTpFdbStatus OBJECT-TYPE
   --   SYNTAX   INTEGER {
   --            other(1),
   --            invalid(2),
   --            learned(3),
   --            self(4),
   --            mgmt(5)
   --               }
   --   ACCESS   read-only
   --   STATUS   mandatory
   --   DESCRIPTION
   --      "The status of this entry.  The meanings of the values
   --      are:
   --         other(1) - none of the following.  This may include
   --            the case where some other MIB object (not the
   --            corresponding instance of extendTpFdbPort, nor an
   --            entry in the dot1qStaticUnicastTable) is being
   --            used to determine if and how frames addressed to
   --            the value of the corresponding instance of
     --          extendTpFdbAddress are being forwarded.
     --       invalid(2) - this entry is no longer valid (e.g., it
     --          was learned but has since aged out), but has not
     --          yet been flushed from the table.
     --       learned(3) - the value of the corresponding instance
     --          of extendTpFdbPort was learned and is being used.
     --       self(4) - the value of the corresponding instance of
     --          extendTpFdbAddress represents one of the device's
     --          addresses.  The corresponding instance of
     --          extendTpFdbPort indicates which of the device's
     --          ports has this address.
     --       mgmt(5) - the value of the corresponding instance of
     --          extendTpFdbAddress is also the value of an
     --          existing instance of dot1qStaticAddress.
     --            ALCATEL NOTE:
     --                ACCESS:     NA       USAGE:      NA
     --                PERSIST:    NO       INSRVMOD:   NO
     --                RANGE:      NA       DEFVALUE:   NA
     --                UNITS:      NA       SPARSE:     NA
     --                DESCR:      NA"
     -- ::= { extendTpFdbEntry 3 }

     --    extendTpFdbvMacAddress OBJECT-TYPE
     --           SYNTAX  MacAddress
     --           ACCESS  read-only
     --           STATUS  mandatory
     --           DESCRIPTION
     --                   "A unicast virtual MAC address for which the device has
     --                   forwarding and/or filtering information.
     --      ALCATEL NOTE:
     --            ACCESS:     NA       USAGE:      NA
     --            PERSIST:    NO       INSRVMOD:   NO
     --            RANGE:      NA       DEFVALUE:   NA
     --            UNITS:      NA       SPARSE:     NA
     --            DESCR:      NA"
     --           ::= { extendTpFdbEntry 4 }

-- =====================
-- A table to read out the MAC addresses per Port / VLAN. Note that the 
-- table allows that a MAC address is learned on two ports.
-- =====================

--   extendPortFdbTable OBJECT-TYPE
--      SYNTAX   SEQUENCE OF ExtendPortFdbEntry
--      ACCESS   not-accessible
--      STATUS   mandatory
--      DESCRIPTION
--         "A table that contains information about unicast entries
--         for which the device has forwarding and/or filtering
--         information.  This information is used by the
--         transparent bridging function in determining how to
--         propagate a received frame.
--         This table contains as well the static configured as the
--         dynamically learned MAC addresses
--             ALCATEL NOTE:
--
--                 TABLESIZE:  DEP [depends on the tablesize of
--                                  extendTpFdbTable]
--                 DESCR: This table is obsoleted by
--                       extendBridgePortFdbTable which uses ifIndex as
--                       additional key to access the table to improve CLI
--                       retrieval performance."
--      ::= { extendForwardingInfo 4 }
--
--   extendPortFdbEntry OBJECT-TYPE
--      SYNTAX   ExtendPortFdbEntry
--      ACCESS   not-accessible
--      STATUS   mandatory
--      DESCRIPTION
--         "Information about a specific unicast MAC address for
--         which the device has some forwarding and/or filtering
--         information."
--      INDEX   { dot1dBasePort, extendPortFdbId, extendPortFdbAddress }
--      ::= { extendPortFdbTable 1 }
--
--   ExtendPortFdbEntry ::=
--      SEQUENCE {
--         extendPortFdbId
--            Gauge,
--         extendPortFdbAddress
--            MacAddress,
--         extendPortFdbStatus
--            INTEGER,
--         extendPortFdbvMacAddress
--            MacAddress
--               }
--
--   extendPortFdbId OBJECT-TYPE
--      SYNTAX   Gauge
--      ACCESS   read-only
--      STATUS   mandatory
--      DESCRIPTION
--         "The identity of this Filtering Database.
--             ALCATEL NOTE:
--                 ACCESS:     NA       USAGE:      NA
--                 PERSIST:    NO       INSRVMOD:   NO
--                 RANGE:      NA       DEFVALUE:   NA
--                 UNITS:      NA       SPARSE:     NA
--                 DESCR:      NA"
--      ::= { extendPortFdbEntry 1 }
--
--   extendPortFdbAddress OBJECT-TYPE
--      SYNTAX   MacAddress
--      ACCESS   read-only
--      STATUS   mandatory
--      DESCRIPTION
--         "A unicast MAC address for which the device has
--         forwarding and/or filtering information.
--             ALCATEL NOTE:
--                 ACCESS:     NA       USAGE:      NA
--                 PERSIST:    NO       INSRVMOD:   NO
--                 RANGE:      NA       DEFVALUE:   NA
--                 UNITS:      NA       SPARSE:     NA
--                 DESCR:      NA"
--      ::= { extendPortFdbEntry 2 }
--
--   extendPortFdbStatus OBJECT-TYPE
--      SYNTAX   INTEGER {
--               other(1),
--               invalid(2),
--               learned(3),
--               self(4),
--               mgmt(5)
--                  }
--      ACCESS   read-only
--      STATUS   mandatory
--      DESCRIPTION
--         "The status of this entry.  The meanings of the values
--         are:
--            other(1) - none of the following.  This may include
--               the case where some other MIB object (not the
--               corresponding instance of extendPortFdbPort, nor an
--               entry in the dot1qStaticUnicastTable) is being
--               used to determine if and how frames addressed to
--               the value of the corresponding instance of
--               extendPortFdbAddress are being forwarded.
--            invalid(2) - this entry is no longer valid (e.g., it
--               was learned but has since aged out), but has not
--               yet been flushed from the table.
--            learned(3) - the value of the corresponding instance
--               of extendPortFdbPort was learned and is being used.
--            self(4) - the value of the corresponding instance of
--               extendPortFdbAddress represents one of the device's
--               addresses.  The corresponding instance of
--               extendPortFdbPort indicates which of the device's
--               ports has this address.
--            mgmt(5) - the value of the corresponding instance of
--               extendPortFdbAddress is also the value of an
--               existing instance of dot1qStaticAddress.
--                 ALCATEL NOTE:
--                     ACCESS:     NA       USAGE:      NA
--                     PERSIST:    NO       INSRVMOD:   NO
--                     RANGE:      NA       DEFVALUE:   NA
--                     UNITS:      NA       SPARSE:     NA
--                     DESCR:      NA"
--      ::= { extendPortFdbEntry 3 }

--        extendPortFdbvMacAddress OBJECT-TYPE
--                SYNTAX  MacAddress
--                ACCESS  read-only
--                STATUS  mandatory
--                DESCRIPTION
--                        "A unicast virtual MAC address for which the device has
--                        forwarding and/or filtering information.
--             ALCATEL NOTE:
--                 ACCESS:     NA       USAGE:      NA
--                 PERSIST:    NO       INSRVMOD:   NO
--                 RANGE:      NA       DEFVALUE:   NA
--                 UNITS:      NA       SPARSE:     NA
--                 DESCR:      NA"
--                ::= { extendPortFdbEntry 4 }


-- =====================
-- ANTms41371
-- New Table added (instead of extendPortFdbTable) to improve CLI response
-- time.
-- =====================

--   extendBridgePortFdbTable OBJECT-TYPE
--      SYNTAX	SEQUENCE OF ExtendBridgePortFdbEntry
--      ACCESS	not-accessible
--      STATUS	mandatory
--      DESCRIPTION
--         "A table that contains information about unicast entries
--         for which the device has forwarding and/or filtering
--         information.  This information is used by the
--         transparent bridging function in determining how to
  --       propagate a received frame.
  --       This table contains as well the static configured as the
  --       dynamically learned MAC addresses
  --       ALCATEL NOTE:
  --       TABLESIZE:  DEP [depends on the tablesize of
  --                     extendStaticUnicastTable]
  --       DESCR:      NA"
  --    ::= { extendForwardingInfo 9 }

  -- extendBridgePortFdbEntry OBJECT-TYPE
  --    SYNTAX	ExtendBridgePortFdbEntry
  --    ACCESS	not-accessible
  --    STATUS	mandatory
  --    DESCRIPTION
  --       "Information about a specific unicast MAC address for
  --       which the device has some forwarding and/or filtering
  --       information."
  --    INDEX   { ifIndex, extendBridgePortFdbId,
  --              extendBridgePortFdbAddress }
  --    ::= { extendBridgePortFdbTable 1 }

  -- ExtendBridgePortFdbEntry ::=
  --    SEQUENCE {
  --       extendBridgePortFdbId
  --          Gauge,
  --       extendBridgePortFdbAddress
  --          MacAddress,
  --       extendBridgePortFdbCurrentVlanPortSubscriberVlan
  --          VlanIndex,
  --       extendBridgePortFdbDot1dBasePort
  --          INTEGER,
  --       extendBridgePortFdbStatus
  --          INTEGER,
  --       extendBridgePortFdbvMacAddress
  --          MacAddress
  --    }

  --extendBridgePortFdbId OBJECT-TYPE
  --   SYNTAX	Gauge
  --   ACCESS	read-only
  --    STATUS	mandatory
  --    DESCRIPTION
  --       "The identity of this Filtering Database.
  --       ALCATEL NOTE:
  --       ACCESS:     NA       USAGE:      NA
  --       PERSIST:    NA       INSRVMOD:   NA
  --       RANGE:      NA       DEFVALUE:   NA
  --       UNITS:      NA       SPARSE:     NA
  --       DESCR:      NA"
  --    ::= { extendBridgePortFdbEntry 1 }

  -- extendBridgePortFdbAddress OBJECT-TYPE
  --    SYNTAX	MacAddress
  --    ACCESS	read-only
  --    STATUS	mandatory
  --    DESCRIPTION
  --       "A unicast MAC address for which the device has
  --       forwarding and/or filtering information.
  --       ALCATEL NOTE:
  --       ACCESS:     NA       USAGE:      NA
  --       PERSIST:    NA       INSRVMOD:   NA
  --       RANGE:      NA       DEFVALUE:   NA
   --      UNITS:      NA       SPARSE:     NA
   --      DESCR:      NA"
   --   ::= { extendBridgePortFdbEntry 2 }

   --extendBridgePortFdbCurrentVlanPortSubscriberVlan OBJECT-TYPE
   --   SYNTAX  VlanIndex
   --   ACCESS  read-only
   --   STATUS  mandatory
   --   DESCRIPTION
   --       "This object indicates the subscriber VLAN associated to
   --       bridge port.
   --       ALCATEL NOTE:
   --       ACCESS:     NA       USAGE:      NA
   --       PERSIST:    NA       INSRVMOD:   NA
   --       RANGE:      NA       DEFVALUE:   NA
   --       UNITS:      NA       SPARSE:     NA
   --       DESCR:      NA"
   -- ::= { extendBridgePortFdbEntry 3 }

--extendBridgePortFdbDot1dBasePort OBJECT-TYPE
--     SYNTAX  INTEGER (1..65535)
--     ACCESS  read-only
--     STATUS  mandatory
--     DESCRIPTION
--         "The port number of the port for which this entry
--         contains bridge management information.
--         ALCATEL NOTE:
--         ACCESS:     NA       USAGE:      NA
--         PERSIST:    NA       INSRVMOD:   NA
--         RANGE:      NA       DEFVALUE:   NA
--         UNITS:      NA       SPARSE:     NA
--         DESCR:      NA"
--     ::= { extendBridgePortFdbEntry 4 }

--   extendBridgePortFdbStatus OBJECT-TYPE
--      SYNTAX	INTEGER {
--         other(1),
--         invalid(2),
--         learned(3),
--         self(4),
--         mgmt(5)
--      }
--      ACCESS	read-only
--      STATUS	mandatory
--      DESCRIPTION
--         "The status of this entry.  The meanings of the values are:
--       other(1) - none of the following.  This may include	the case where
--            some other MIB object (not the corresponding instance of
--            extendBridgePortFdbPort, nor an	entry in the
--        dot1qStaticUnicastTable) is being used to determine if and how
--         frames addressed to the value of the corresponding instance of
--            extendBridgePortFdbAddress are being forwarded.
--         invalid(2) - this entry is no longer valid (e.g., it was learned
--           but has since aged out), but has not yet been flushed from the
--            table.
--         learned(3) - the value of the corresponding instance of
--            extendBridgePortFdbPort was learned and is being used.
--         self(4) - the value of the corresponding instance of
--            extendBridgePortFdbAddress represents one of the device's
--            addresses.  The corresponding instance of
--            extendBridgePortFdbPort indicates which of the device's
--            ports has this address.
--         mgmt(5) - the value of the corresponding instance of
--            extendBridgePortFdbAddress is also the value of an
--            existing instance of dot1qStaticAddress.
--         ALCATEL NOTE:
--         ACCESS:     NA       USAGE:      NA
--         PERSIST:    NA       INSRVMOD:   NA
--         RANGE:      NA       DEFVALUE:   NA
--         UNITS:      NA       SPARSE:     NA
--         DESCR:      NA"
--      ::= { extendBridgePortFdbEntry 5 }

--   extendBridgePortFdbvMacAddress OBJECT-TYPE
--      SYNTAX  MacAddress
--      ACCESS  read-only
--      STATUS  mandatory
--      DESCRIPTION
--       "A unicast virtual MAC address for which the device has forwarding
--         and/or filtering information.
--         ALCATEL NOTE:
--         ACCESS:     NA       USAGE:      NA
--         PERSIST:    NA       INSRVMOD:   NA
--         RANGE:      NA       DEFVALUE:   NA
--         UNITS:      NA       SPARSE:     NA
--         DESCR:      NA"
--      ::= { extendBridgePortFdbEntry 6 }


-- =====================
-- A table that allows to remove a self learned MAC address from a port.
-- The concept behind it is that MAC addresses could be learned
-- independently on two ports. The traffic from the second one will be
-- blocked until the MAC address is aged on the first port. The ageing time
-- could be rather big. To overcome this the operator can decide to
-- manually remove the MAC address from the first port.
-- =====================

--   extendRemoveMacTable OBJECT-TYPE
--      SYNTAX   SEQUENCE OF ExtendRemoveMacEntry
--      ACCESS   not-accessible
--      STATUS   mandatory
--      DESCRIPTION
--      "The table allows to remove MAC addresses (that were obtained
--      through the self learning mechanism) from the forwarding database
--      for a specified port. A write action has an immediate effect, it
--      does not have a permanent effect.
--      Note that this table can not be used to delete a Static MAc address.
--             ALCATEL NOTE:
--                 TABLESIZE:  1
--                 DESCR:      NA"
--      ::= { extendForwardingInfo 5 }

--   extendRemoveMacEntry OBJECT-TYPE
--      SYNTAX   ExtendRemoveMacEntry
--      ACCESS   not-accessible
--      STATUS   mandatory
--      DESCRIPTION
--         "The identification of the Port, Forwarding database, from which
--         the Mac address shall be removed."
--      INDEX { dot1dBasePort, extendRemoveMacFdbId, extendRemoveMacAddress}
--      ::= { extendRemoveMacTable 1 }

--   ExtendRemoveMacEntry ::=
--      SEQUENCE   {
--            extendRemoveMacFdbId
--               Gauge,
--            extendRemoveMacAddress
--               MacAddress
--            }

--   extendRemoveMacFdbId   OBJECT-TYPE
--      SYNTAX   Gauge
--      ACCESS   not-accessible
--      STATUS   mandatory
--      DESCRIPTION
--       "The identity of the Filtering Database from which the MAC address
--         is to be removed.
--             ALCATEL NOTE:
--                 ACCESS:     NA       USAGE:      NA
--                 PERSIST:    NO       INSRVMOD:   YES
--                 RANGE:      NA       DEFVALUE:   NA
--                 UNITS:      NA       SPARSE:     NA
--                 DESCR:      NA"
--      ::= { extendRemoveMacEntry 1 }

--   extendRemoveMacAddress OBJECT-TYPE
--      SYNTAX   MacAddress
--      ACCESS   read-write
--      STATUS   mandatory
--      DESCRIPTION
--       "the MAC address to be removed from the filtering database for the
--         specified port (MAC unique within VLAN.)
--             ALCATEL NOTE:
--                 ACCESS:     NA       USAGE:      NA
--                 PERSIST:    NO       INSRVMOD:   YES
--                 RANGE:      NA       DEFVALUE:   NA
--                 UNITS:      NA       SPARSE:     NA
--                 DESCR:      NA"
--      ::= { extendRemoveMacEntry 2 }

-- =====================
-- A table to read out the translation from a subscriber MAC address
-- to a vMAC address
-- =====================

--   extendvMacFdbTable OBJECT-TYPE
--      SYNTAX  SEQUENCE OF ExtendvMacPortFdbEntry
--      ACCESS  not-accessible
--      STATUS  mandatory
--      DESCRIPTION
--      "A table that contains information about unicast entries
--      and virtual MAC address for which the device has forwarding and/or
--      filtering information.
--      A subscriber packet towards the upstream will have the source address
--      of the Ethernet packet changed to a virtual MAC address. A packet
--      destined for a subscriber from the network will have the destination
--      address translated from the virtual MAC to the original subscriber MAC
--      address.
--             ALCATEL NOTE:
--                 TABLESIZE:  DEP [depends on the tablesize of
--                             extendTpFdbTable]
--                 DESCR:      NA"
--::= { extendForwardingInfo 7 }

--   extendvMacPortFdbEntry OBJECT-TYPE
--      SYNTAX  ExtendvMacPortFdbEntry
--      ACCESS  not-accessible
  --    STATUS  mandatory
  --    DESCRIPTION
  --    "Information about a specific unicast MAC address and virtual MAC
  --    address for which the device has some forwarding and/or filtering
  --    information."
  --        INDEX  { dot1dBasePort, extendvMacPortFdbId,extendvMacPortFdbAddress}
--::= { extendvMacFdbTable 1 }

  -- ExtendvMacPortFdbEntry ::=
  --    SEQUENCE {
  --          extendvMacPortFdbId
  --          Gauge,
  --          extendvMacPortFdbAddress
  --          MacAddress,
  --          extendvMacPortFdbvMacAddress
  --          MacAddress
--                                        }

  -- extendvMacPortFdbId OBJECT-TYPE
  --    SYNTAX  Gauge
  --    ACCESS  read-only
  --    STATUS  mandatory
  --    DESCRIPTION
  --    "The identity of this Filtering Database.
  --           ALCATEL NOTE:
  --               ACCESS:     NA       USAGE:      NA
  --               PERSIST:    NO       INSRVMOD:   NO
  --               RANGE:      NA       DEFVALUE:   NA
  --               UNITS:      NA       SPARSE:     NA
  --               DESCR:      NA"
--::= { extendvMacPortFdbEntry 1 }

  -- extendvMacPortFdbAddress OBJECT-TYPE
  --    SYNTAX  MacAddress
  --    ACCESS  read-only
  --    STATUS  mandatory
  --    DESCRIPTION
  --    "A unicast MAC address for which the device has forwarding and/or
  --    filtering information.
  --           ALCATEL NOTE:
  --               ACCESS:     NA       USAGE:      NA
  --               PERSIST:    NO       INSRVMOD:   NO
  --               RANGE:      NA       DEFVALUE:   NA
  --               UNITS:      NA       SPARSE:     NA
  --               DESCR:      NA"
--::= { extendvMacPortFdbEntry 2  }

  -- extendvMacPortFdbvMacAddress OBJECT-TYPE
  --    SYNTAX  MacAddress
  --    ACCESS  read-only
  --    STATUS  mandatory
  --    DESCRIPTION
  --    "A unicast virtual MAC address for which the device has forwarding
  --    and/or filtering information.
  --           ALCATEL NOTE:
  --               ACCESS:     NA       USAGE:      NA
  --               PERSIST:    NO       INSRVMOD:   NO
  --               RANGE:      NA       DEFVALUE:   NA
  --               UNITS:      NA       SPARSE:     NA
  --               DESCR:      NA"
--::= { extendvMacPortFdbEntry 3 }


-- =====================
-- A table to list all unicast MAC address from a user port, which could be
--dynamically learned or statically configured. This table is also used to
--manually delete a dynamically learned MAC address.
-- =====================

	extendUserPortFdbTable OBJECT-TYPE
		SYNTAX	SEQUENCE OF ExtendUserPortFdbEntry
		ACCESS	not-accessible
		STATUS	mandatory
		DESCRIPTION
			"A table that contains unicast MAC address, static and dynamic,
			per user forwarder interface, which could be translated to a vMAC 				address to network.
			And it also allows to remove  MAC addresses, which were obtained
			through the self learning mechanism, from the forwarding database
			on a specified port.
			Note that this table can not be used to delete a static MAc address.             			ALCATEL NOTE:
                 TABLESIZE:  DEP [nbr of unicast addresses/board * nbr of
                                 boards]"
		::= { extendForwardingInfo 10 }

	extendUserPortFdbEntry OBJECT-TYPE
		SYNTAX	ExtendUserPortFdbEntry
		ACCESS	not-accessible
		STATUS	mandatory
		DESCRIPTION
			"An entry of extendUserPortFdbTable, learned or configured on a user forwarder port."
		INDEX	{ ifIndex, extendUserPortFdbUserAddress }
		::= { extendUserPortFdbTable 1 }

	 ExtendUserPortFdbEntry ::=
      SEQUENCE {
         extendUserPortFdbUserAddress
            MacAddress,
         extendUserPortFdbId
            Gauge,
         extendUserPortFdbStatus
            INTEGER,
         extendUserPortFdbvMacAddress
            MacAddress,
         extendUserPortFdbRowStatus
            RowStatus
      }


	  extendUserPortFdbUserAddress OBJECT-TYPE
		SYNTAX	MacAddress
		ACCESS	read-only
		STATUS	mandatory
		DESCRIPTION
			"The source MAC address contained in the frame coming from a user forwarder interface.
             ALCATEL NOTE:
                 ACCESS:     NA       USAGE:      NA
                 PERSIST:    NO       INSRVMOD:   NA
                 RANGE:      NA       DEFVALUE:   NA
                 UNITS:      NA       SPARSE:     NA
                 DESCR:      the user forwarder interface identifies a vlan.port"
		::= { extendUserPortFdbEntry 1 }

   	extendUserPortFdbId OBJECT-TYPE
		SYNTAX	Gauge
		ACCESS	read-only
		STATUS	mandatory
		DESCRIPTION
			"Identifies a L2 forwarder which the user forwarder interface attaches to.
	             ALCATEL NOTE:
                 ACCESS:     NA       USAGE:      NA
                 PERSIST:    NO       INSRVMOD:   NO
                 RANGE:      NA       DEFVALUE:   NA
                 UNITS:      NA       SPARSE:     NA
                 DESCR:      NA"
		::= { extendUserPortFdbEntry 2 }

    extendUserPortFdbStatus OBJECT-TYPE
      SYNTAX	INTEGER {
         other(1),
         invalid(2),
         learned(3),
         self(4),
         mgmt(5)
      }
      ACCESS	read-only
      STATUS	mandatory
      DESCRIPTION
         "The status of this entry.  The meanings of the values are:
         other(1) - none of the following.  This may include	the case where
            some other MIB object is being used to determine if and how
            frames addressed to the value of the corresponding instance of
            extendUserPortFdbUserAddress are being forwarded.
         invalid(2) - this entry is no longer valid (e.g., it was learned
            but has aged out), but has not yet been flushed from the
            table.
         learned(3) - the value of the corresponding instance of
            extendUserPortFdbUserAddress was learned and is being used.
         self(4) - the value of the corresponding instance of
            extendUserPortFdbUserAddress represents one of the device's
            addresses.
         mgmt(5) - the value of the corresponding instance of
            extendUserPortFdbUserAddress is configured manually.
         ALCATEL NOTE:
         ACCESS:     NA       USAGE:      NA
         PERSIST:    NA       INSRVMOD:   NA
         RANGE:      3,5    DEFVALUE:   NA
         UNITS:      NA       SPARSE:     NA
         DESCR:      NA"
      ::= { extendUserPortFdbEntry 3 }

	extendUserPortFdbvMacAddress OBJECT-TYPE
		SYNTAX  MacAddress
		ACCESS  read-only
		STATUS  mandatory
		DESCRIPTION
		"A unicast virtual MAC address to which the extendUserPortFdbUserAddress was translated and the device has forwarding and/or filtering information.
		             ALCATEL NOTE:
		                 ACCESS:     NA       USAGE:      NA
		                 PERSIST:    NO       INSRVMOD:   NO
		                 RANGE:      NA       DEFVALUE:   NA
		                 UNITS:      NA       SPARSE:     NA
		                 DESCR:      NA"
	::= { extendUserPortFdbEntry 4 }


      extendUserPortFdbRowStatus OBJECT-TYPE
		SYNTAX	RowStatus
		ACCESS	read-write
		STATUS	mandatory
		DESCRIPTION
			"The row status of the entry.
             ALCATEL NOTE:
                 ACCESS:     NA       USAGE:      NA
                 PERSIST:    NO       INSRVMOD:   YES
                 RANGE: active(1),destroy(6)  DEFVALUE:   active(1)
                 UNITS:      NA       SPARSE:     NA
                 DESCR:      NA"
        DEFVAL	{ active }
		::= { extendUserPortFdbEntry 5 }


-- =====================
-- A table to read out the MAC addresses per L2 forwarder and get on
-- which port they are learned.
-- =====================
--
-- 	extendForwarderFdbTable OBJECT-TYPE
--		SYNTAX	SEQUENCE OF ExtendForwarderFdbEntry
--		ACCESS	not-accessible
--		STATUS	mandatory
--		DESCRIPTION
--			"A table that contains information about unicast 
--		    MAC	address 	for which the device has forwarding and/or
-- filtering
--			information.  This information is used by the
--			transparent bridging function in determining how to
--			propagate a received frame.
--			Both dynamic and static MAC addresses are covered in this 
--table.
--             ALCATEL NOTE:
--                 TABLESIZE:  DEP [depends on the tablesize of
--		extendUserPortFdbTable]
--DESCR:      NA"
--
--		::= { extendForwardingInfo 11 } 
--		
--	extendForwarderFdbEntry OBJECT-TYPE
--		SYNTAX	ExtendForwarderFdbEntry 
--		ACCESS	not-accessible
--		STATUS	mandatory
--		DESCRIPTION
--			"Information about a specific MAC address for
--			which the device has some forwarding and/or filtering
--			information."
--		INDEX  { dot1qFdbId, extendForwarderFdbNetAddress, e
--xtendForwarderFdbIntf}
--		::= { extendForwarderFdbTable 1 }	
--		
--	 ExtendForwarderFdbEntry ::=
--     SEQUENCE {
--         extendForwarderFdbNetAddress
--            MacAddress,
--         extendForwarderFdbIntf
--            INTEGER,   
--         extendForwarderFdbStatus
--            INTEGER,
--         extendForwarderFdbUserAddress
--            MacAddress
--         }	  
--	  
--	  extendForwarderFdbNetAddress OBJECT-TYPE
--		SYNTAX	MacAddress
--		ACCESS	read-only
--		STATUS	mandatory
--		DESCRIPTION
--			"The MAC address at network side. When vMAC is enabled, it 
--identifies a vMAC address.
--             ALCATEL NOTE:
--                 ACCESS:     NA       USAGE:      NA
--                 PERSIST:    NO       INSRVMOD:   YES
--                 RANGE:      NA       DEFVALUE:   NA
--                 UNITS:      NA       SPARSE:     NA
--                 DESCR:      NA"
--		::= { extendForwarderFdbEntry 1 }   
--		
--	  extendForwarderFdbIntf OBJECT-TYPE
--		SYNTAX	INTEGER 
--		ACCESS	read-only
--		STATUS	mandatory
--		DESCRIPTION
--			"The ifIndex of a forwarder interface where the MAC@ will be 
--forwarded to.
--             ALCATEL NOTE:
--                 ACCESS:     NA       USAGE:      NA
--                 PERSIST:    NO       INSRVMOD:   YES
--                 RANGE:      NA       DEFVALUE:   NA
--                 UNITS:      NA       SPARSE:     NA
--                 DESCR:      the forwarder interface identifies a 
--vlan.port"
--		::= { extendForwarderFdbEntry 2 }
--
--    extendForwarderFdbStatus OBJECT-TYPE
--      SYNTAX	INTEGER {
--         other(1),
--         invalid(2),
--         learned(3),
--         self(4),
--         mgmt(5)
--      }
--      ACCESS	read-only
--      STATUS	mandatory
--      DESCRIPTION
--         "The status of this entry.  The meanings of the values are:
--         other(1) - none of the following.  This may include	the case 
--where
--            some other MIB object is being used to determine if and how
--            frames addressed to the value of the corresponding instance 
--of
--            extendForwarderFdbNetAddress are being forwarded.
--         invalid(2) - this entry is no longer valid (e.g. it was learned
--            but has since aged out), but has not yet been flushed from 
--the
--            table.
--         learned(3) - the value of the corresponding instance of
--            extendForwarderFdbNetAddress was learned and is being used.
--         self(4) - the value of the corresponding instance of
--            extendForwarderFdbNetAddress represents one of the device's
--            addresses.  
--         mgmt(5) - the value of the corresponding instance of
--            extendForwarderFdbNetAddress is manually configured.
--         ALCATEL NOTE:
--         ACCESS:     NA       USAGE:      NA
--         PERSIST:    NA       INSRVMOD:   NA
--         RANGE:      3,5       DEFVALUE:   NA
--         UNITS:      NA       SPARSE:     NA
--         DESCR:      NA"
--      ::= { extendForwarderFdbEntry 3 }
--      
--	extendForwarderFdbUserAddress OBJECT-TYPE
--		SYNTAX  MacAddress
--		ACCESS  read-only
--		STATUS  mandatory
--		DESCRIPTION
--		"the user MAC address, which the extendForwarderFdbNetAddress is 
--translated from when vMAC is enabled. 
--		             ALCATEL NOTE:
--		                 ACCESS:     NA       USAGE:      NA
--		                 PERSIST:    NO       INSRVMOD:   NO
--		                 RANGE:      NA       DEFVALUE:   NA
--		                 UNITS:      NA       SPARSE:     NA
--		                 DESCR:      NA"
--	::= { extendForwarderFdbEntry 4 }


-- =====================
-- A table to read out the MAC addresses per L2 forwarder and get on 
-- which port they are learned. This table is organized per LIM as index. 
-- =====================

   extendBoardForwarderFdbTable OBJECT-TYPE
      SYNTAX	SEQUENCE OF ExtendBoardForwarderFdbEntry
		ACCESS	not-accessible
		STATUS	mandatory
		DESCRIPTION
			"A table that contains information about unicast
         MAC address per LIM for which the device has forwarding and/or filtering
			information.  This information is used by the
			transparent bridging function in determining how to
			propagate a received frame.
			Both dynamic and static MAC addresses are covered in this table.

             ALCATEL NOTE:
                 TABLESIZE:  DEP [depends on the tablesize of
		extendUserPortFdbTable]
DESCR:      NA"

         ::= { extendForwardingInfo 12 } 

   extendBoardForwarderFdbEntry OBJECT-TYPE
      SYNTAX	ExtendBoardForwarderFdbEntry 
		ACCESS	not-accessible
		STATUS	mandatory
		DESCRIPTION
			"Information about a specific MAC address for
			which the device has some forwarding and/or filtering
			information."
      INDEX  { eqptSlotId, dot1qFdbId, extendBoardForwarderFdbNetAddress }
         ::= { extendBoardForwarderFdbTable 1 }	

   ExtendBoardForwarderFdbEntry ::=
      SEQUENCE {
         extendBoardForwarderFdbNetAddress
            MacAddress,
         extendBoardForwarderFdbIntf
            INTEGER,   
         extendBoardForwarderFdbStatus
            INTEGER,
         extendBoardForwarderFdbUserAddress
            MacAddress
         }

   extendBoardForwarderFdbNetAddress OBJECT-TYPE
		SYNTAX	MacAddress
		ACCESS	read-only
		STATUS	mandatory
		DESCRIPTION
			"The MAC address at network side. When vMAC is enabled, it identifies a vMAC address.

             ALCATEL NOTE:
                 ACCESS:     NA       USAGE:      NA
                 PERSIST:    NO       INSRVMOD:   YES
                 RANGE:      NA       DEFVALUE:   NA
                 UNITS:      NA       SPARSE:     NA
                 DESCR:      NA"
          ::= { extendBoardForwarderFdbEntry 1 }   

   extendBoardForwarderFdbIntf OBJECT-TYPE
		SYNTAX	INTEGER
		ACCESS	read-only
		STATUS	mandatory
		DESCRIPTION
			"The ifIndex of a forwarder interface where the MAC@ will be forwarded to.
             ALCATEL NOTE:
                 ACCESS:     NA       USAGE:      NA
                 PERSIST:    NO       INSRVMOD:   YES
                 RANGE:      NA       DEFVALUE:   NA
                 UNITS:      NA       SPARSE:     NA
                 DESCR:      the forwarder interface identifies a vlan.port"
         ::= { extendBoardForwarderFdbEntry 2 }

    extendBoardForwarderFdbStatus OBJECT-TYPE
      SYNTAX	INTEGER {
         other(1),
         invalid(2),
         learned(3),
         self(4),
         mgmt(5)
      }
      ACCESS	read-only
      STATUS	mandatory
      DESCRIPTION
         "The status of this entry.  The meanings of the values are:
         other(1) - none of the following.  This may include	the case where
            some other MIB object is being used to determine if and how
            frames addressed to the value of the corresponding instance of
            extendBoardForwarderFdbNetAddress are being forwarded.
         invalid(2) - this entry is no longer valid (e.g. it was learned
            but has since aged out), but has not yet been flushed from the
            table.
         learned(3) - the value of the corresponding instance of
            extendBoardForwarderFdbNetAddress was learned and is being used.
         self(4) - the value of the corresponding instance of
            extendBoardForwarderFdbNetAddress represents one of the device's
            addresses.
         mgmt(5) - the value of the corresponding instance of
            extendBoardForwarderFdbNetAddress is manually configured.
         ALCATEL NOTE:
         ACCESS:     NA       USAGE:      NA
         PERSIST:    NA       INSRVMOD:   NA
         RANGE:      3,5       DEFVALUE:   NA
         UNITS:      NA       SPARSE:     NA
         DESCR:      NA"
      ::= { extendBoardForwarderFdbEntry 3 }

   extendBoardForwarderFdbUserAddress OBJECT-TYPE
		SYNTAX  MacAddress
		ACCESS  read-only
		STATUS  mandatory
		DESCRIPTION
         "the user MAC address, which the extendBoardForwarderFdbNetAddress 
         is translated from when vMAC is enabled. 
		             ALCATEL NOTE:
		                 ACCESS:     NA       USAGE:      NA
		                 PERSIST:    NO       INSRVMOD:   NO
		                 RANGE:      NA       DEFVALUE:   NA
		                 UNITS:      NA       SPARSE:     NA
		                 DESCR:      NA"
	::= { extendBoardForwarderFdbEntry 4 }


-- =======================================================
-- The monitoring group of objects is used to monitor the 
-- system.
-- =======================================================

extendMonitor	OBJECT IDENTIFIER ::= {plimEthernet 6}

--	extendMonitorForwardingTable OBJECT-TYPE
--		SYNTAX	SEQUENCE OF ExtendMonitorForwardingEntry
--		ACCESS	not-accessible
--		STATUS	mandatory
--		DESCRIPTION
--			"A table containing the monitoring information
--			of the forwarding table. An entry will exist 
--			for each filter ID used by the system."
--		::= { extendMonitor 1}

--	extendMonitorForwardingEntry OBJECT-TYPE
--		SYNTAX	ExtendMonitorForwardingEntry
--		ACCESS	not-accessible
--		STATUS	mandatory
--		DESCRIPTION
--			"An entry in the table extendMonitorForwardingTable. One entry
--			specifies the events of a specified filter Id."
--		INDEX	{ extendForwardingFilterId }
--		::= { extendMonitorForwardingTable 1 }

--	ExtendMonitorForwardingEntry ::=
--		SEQUENCE	{
--				extendMonitorForwardingEvents
--					ExtendInterworkingEvent,
--				extendMonitorForwardingTime
--					NetworkTimeInSeconds
--				}

--	extendMonitorForwardingEvents	OBJECT-TYPE
--		SYNTAX	ExtendInterworkingEvent
--		ACCESS	read-only
--		STATUS	mandatory
--		DESCRIPTION
--			"The events bitmap indicating the last occurred events."
--		::= { extendMonitorForwardingEntry 1}

--	extendMonitorForwardingTime	OBJECT-TYPE
--		SYNTAX	NetworkTimeInSeconds
--		ACCESS	read-only
--		STATUS	mandatory
--		DESCRIPTION
--			"The time in seconds when the events occur."
--		::= { extendMonitorForwardingEntry 2}

	extendMonitorPortTable OBJECT-TYPE
		SYNTAX	SEQUENCE OF ExtendMonitorPortEntry
		ACCESS	not-accessible
		STATUS	mandatory
		DESCRIPTION
			"A table containing the monitoring information
			of the port table. An entry will exist for each ATM port.
             ALCATEL NOTE:
                 TABLESIZE:  DEP [depends on the value of dot1qBaseNumPorts]
                 DESCR:      "
		::= { extendMonitor 2}

	extendMonitorPortEntry OBJECT-TYPE
		SYNTAX	ExtendMonitorPortEntry
		ACCESS	not-accessible
		STATUS	mandatory
		DESCRIPTION
			"An entry in the table extendMonitorPortTable. One entry
			specifies the events of a specified Port."
		INDEX	{ dot1dBasePort }
		::= { extendMonitorPortTable 1 }

	ExtendMonitorPortEntry ::=
		SEQUENCE	{
				extendMonitorPortEvents
					ExtendInterworkingEvent,
				extendMonitorPortTime
					NetworkTimeInSeconds
				}

	extendMonitorPortEvents	OBJECT-TYPE
		SYNTAX	ExtendInterworkingEvent
		ACCESS	read-only
		STATUS	mandatory
		DESCRIPTION
			"The events bitmap indicating the last occurred events.
             ALCATEL NOTE:
                 ACCESS:     NA       USAGE:      NA
                 PERSIST:    NO       INSRVMOD:   NO
                 RANGE:      NA       DEFVALUE:   0
                 UNITS:      NA       SPARSE:     NA
                 DESCR:      NA"
		::= { extendMonitorPortEntry 1}

	extendMonitorPortTime	OBJECT-TYPE
		SYNTAX	NetworkTimeInSeconds
		ACCESS	read-only
		STATUS	mandatory
		DESCRIPTION
			"The time in seconds when the events occur.
             ALCATEL NOTE:
                 ACCESS:     NA       USAGE:      NA
                 PERSIST:    NO       INSRVMOD:   NO
                 RANGE:      NA       DEFVALUE:   0
                 UNITS:      seconds  SPARSE:     NA
                 DESCR:      NA"
		::= { extendMonitorPortEntry 2}

-- ==========================================================================
-- Extensions for VLAN stacking
-- ==========================================================================
vlanStack	OBJECT IDENTIFIER ::= {plimEthernet 7}

	vlanStackEtherType		OBJECT-TYPE
		SYNTAX	INTEGER
		ACCESS	read-write
		STATUS	mandatory
		DESCRIPTION
			"The Ethernet type value for the stacked VLAN tag.
             ALCATEL NOTE:
                 ACCESS:     NA       USAGE:      NA
                 PERSIST:    YES      INSRVMOD:   YES
                 RANGE:      NA       DEFVALUE:   NA
                 UNITS:      NA       SPARSE:     NA
                 DESCR:      NA"
		::= { vlanStack 1}

--	vlanStackMaxVlanId		OBJECT-TYPE
--		::= { vlanStack 2}
--
--	vlanStackMaxSupportedVlans		OBJECT-TYPE
--		::= { vlanStack 3}
--
--	vlanStackVlanConfiguredNumber		OBJECT-TYPE
--		::= { vlanStack 4}

	vlanStackCurrentVlanList OBJECT-TYPE
		SYNTAX	VlanList
		ACCESS	read-only
		STATUS	mandatory
		DESCRIPTION
			"The current configured S-VLAN list in the system. This is
			the set of S-VLANs for which an entry is available in
			the extendVlanStaticTable. A 1 indicates an entry for
			this S-VLAN exists in the dot1qVlanStaticTable, a 0
			indicates no corresponding entry exists.
             ALCATEL NOTE:
                 ACCESS:     NA       USAGE:      NA
                 PERSIST:    NO       INSRVMOD:   NO
                 RANGE:      NA       DEFVALUE:   NA
                 UNITS:      NA       SPARSE:     NA
                 DESCR:      NA"
		::= { vlanStack 5}

	vlanStackCurrentVlanMultiplexList OBJECT-TYPE
		SYNTAX	VlanList
		ACCESS	read-only
		STATUS	mandatory
		DESCRIPTION
			"The S-VLAN termination list currently in the system. This is 
			the set of  S-VLANs configured in the extendVlanStaticTable 
			for which the object extendVlanStaticSystemMode has the value of 
			layer2Terminated. 
			A 1 indicates an entry for this S-VLAN-ID exists and is 
			configured with the layer2Terminated mode, a 0 indicates 
			no corresponding entry exists or it is configured in the 
			other mode.
             ALCATEL NOTE:
                 ACCESS:     NA       USAGE:      NA
                 PERSIST:    NO       INSRVMOD:   NO
                 RANGE:      NA       DEFVALUE:   NA
                 UNITS:      NA       SPARSE:     NA
                 DESCR:      NA"
		::= { vlanStack 6}

	vlanStackCurrentVlanQosAwareList OBJECT-TYPE
		SYNTAX	VlanList
		ACCESS	read-only
		STATUS	mandatory
		DESCRIPTION
			"The QoSaware S-VLAN list currently in the sytem. This is
			the set of S-VLANs configured in the extendVlanStaticTable 
			for which the object extendVlanStaticSystemMode has the value of 
			QoS aware. 
			A 1 indicates an entry for this S-VLAN-ID exists and is 
			configured with the QoS aware mode, a 0 indicates 
			no corresponding entry exists or it is configured in the 
			other mode.
             ALCATEL NOTE:
                 ACCESS:     NA       USAGE:      NA
                 PERSIST:    NO       INSRVMOD:   NO
                 RANGE:      NA       DEFVALUE:   NA
                 UNITS:      NA       SPARSE:     NA
                 DESCR:      NA"
		::= { vlanStack 7}

-- ==========================================================================
-- The Static stacked VLAN Table
-- ==========================================================================
--
--	vlanStackVlanStaticTable OBJECT-TYPE
--		::= { vlanStack 8 }
--
-- ==========================================================================
-- The stacked VLAN Port Table
-- ==========================================================================
--
--	vlanStackVlanPortTable OBJECT-TYPE
--		::= { vlanStack 9 }
--
-- ==========================================================================
-- The stacked Multiplex VLAN Port Table
-- ==========================================================================
--
--	vlanStackMultiplexVlanPortsTable OBJECT-TYPE
--		::= { vlanStack 10 }
--
-- ==========================================================================
-- The stacked QoS aware VLAN Port Table
-- ==========================================================================
--
--	vlanStackQosAwareVlanPortsTable OBJECT-TYPE
--		::= { vlanStack 11 }
--
-- ==========================================================================
-- The stacked QoS aware VLAN Port Table, just for read purpose
-- ==========================================================================
--
--	vlanStackQosAwarePortVlanTable OBJECT-TYPE
--		::= { vlanStack 12 }
--
-- ==========================================================================
-- The Table to read out S-VLAN identifiers based on its name
-- ==========================================================================
--
--	vlanStackVlanNameTable OBJECT-TYPE
--		::= { vlanStack 13 }
--
-- ==========================================================================
-- The Table to read out stacked QoS aware C-VLANs
-- ==========================================================================

	vlanStackCurrentVlanQoSAwareTable OBJECT-TYPE
		SYNTAX	SEQUENCE OF VlanStackCurrentVlanQoSAwareEntry
		ACCESS	not-accessible
		STATUS	mandatory
		DESCRIPTION
			"A table containing the stacked QoS-aware C-VLANs. One entry
			contains a bitlist of all QoS-aware C-VLANs stacked on the
			S-VLAN identified by vlanStackCurrentQoSAwareVlanId. 
			A 1 indicates that the corresponding entry in the
			extendVlanStaticTable has the extendVlanStaticSystemMode =
			qosAware. A 0 indicates that the Vlan doesn't exist or has 
			another mode.
             ALCATEL NOTE:
                 TABLESIZE:  4092
                 DESCR:      NA"
		::= { vlanStack 14 }

	vlanStackCurrentVlanQoSAwareEntry OBJECT-TYPE
		SYNTAX	VlanStackCurrentVlanQoSAwareEntry
		ACCESS	not-accessible
		STATUS	mandatory
		DESCRIPTION
			"An entry in the table vlanStackCurrentVlanQoSAwareTable."
		INDEX	{ dot1qVlanIndex }
		::= { vlanStackCurrentVlanQoSAwareTable 1 }

	VlanStackCurrentVlanQoSAwareEntry ::=
		SEQUENCE	{
				vlanStackCurrentVlanQoSAwareVlanList
					VlanList
				}

	vlanStackCurrentVlanQoSAwareVlanList OBJECT-TYPE
		SYNTAX	VlanList
		ACCESS	read-only
		STATUS	mandatory
		DESCRIPTION
			"The bitlist of QoS-aware C-VLANs.
             ALCATEL NOTE:
                 ACCESS:     NA       USAGE:      NA
                 PERSIST:    NO       INSRVMOD:   NO
                 RANGE:      NA       DEFVALUE:   NA
                 UNITS:      NA       SPARSE:     NA
                 DESCR:      NA"
		::= { vlanStackCurrentVlanQoSAwareEntry 1}

-- ==========================================================================
-- The Table to read out stacked C-VLANs
-- ==========================================================================

	vlanStackCurrentVlanTable OBJECT-TYPE
		SYNTAX	SEQUENCE OF VlanStackCurrentVlanEntry
		ACCESS	not-accessible
		STATUS	mandatory
		DESCRIPTION
			"A table containing the stacked C-VLANs. One entry
			contains a bitlist of all C-VLANs stacked on the
			S-VLAN identified by dot1qVlanIndex. 
			A 1 indicates that there is a corresponding entry in the
			extendVlanStaticTable. A 0 indicates that it does 
			not exist.
             ALCATEL NOTE:
                 TABLESIZE:  4092
                 DESCR:      NA"
		::= { vlanStack 15 }

	vlanStackCurrentVlanEntry OBJECT-TYPE
		SYNTAX	VlanStackCurrentVlanEntry
		ACCESS	not-accessible
		STATUS	mandatory
		DESCRIPTION
			"An entry in the table vlanStackCurrentVlanTable."
		INDEX	{ dot1qVlanIndex }
		::= { vlanStackCurrentVlanTable 1 }

	VlanStackCurrentVlanEntry ::=
		SEQUENCE	{
				vlanStackCurrentVlanVlanList
					VlanList
				}

	vlanStackCurrentVlanVlanList OBJECT-TYPE
		SYNTAX	VlanList
		ACCESS	read-only
		STATUS	mandatory
		DESCRIPTION
			"The bitlist of C-VLANs.
             ALCATEL NOTE:
                 ACCESS:     NA       USAGE:      NA
                 PERSIST:    NO       INSRVMOD:   NO
                 RANGE:      NA       DEFVALUE:   NA
                 UNITS:      NA       SPARSE:     NA
                 DESCR:      NA"
		::= { vlanStackCurrentVlanEntry 1}

-- =====================
--	Dot1v extensions
-- =====================

	extendDot1vProtocol	OBJECT IDENTIFIER ::= { plimEthernet 8 }

	extendDot1vProtocolGroupTable OBJECT-TYPE
		SYNTAX	SEQUENCE OF ExtendDot1vProtocolGroupEntry 
		ACCESS	not-accessible
		STATUS	mandatory
		DESCRIPTION
			"A proprietary dot1vProtocolGroupTable extension containing the
			friendly names for the protocol groups
             ALCATEL NOTE:
                 TABLESIZE:  10
                 DESCR:      NA"
		::= {  extendDot1vProtocol 1 }

	extendDot1vProtocolGroupEntry  OBJECT-TYPE
		SYNTAX	ExtendDot1vProtocolGroupEntry
		ACCESS	not-accessible
		STATUS	mandatory
		DESCRIPTION
			"An entry in the table extendDot1vProtocolGroupTable."
		INDEX	{ dot1vProtocolTemplateFrameType, 
				dot1vProtocolTemplateProtocolValue }
		::= { extendDot1vProtocolGroupTable 1 }

	ExtendDot1vProtocolGroupEntry  ::=
		SEQUENCE	{ 
				extendDot1vProtocolGroupName
					SnmpAdminString (SIZE (0..32))
				}
	
	extendDot1vProtocolGroupName	OBJECT-TYPE
		SYNTAX	SnmpAdminString (SIZE (0..32))
		ACCESS	read-write
		STATUS	mandatory
		DESCRIPTION
			"The friendly name of a protocol group
             ALCATEL NOTE:
                 ACCESS:     NA       USAGE:      NA
                 PERSIST:    YES      INSRVMOD:   YES
                 RANGE:      NA       DEFVALUE:   NULL
                 UNITS:      NA       SPARSE:     NA
                 DESCR:      NA"
		::= { extendDot1vProtocolGroupEntry 1 }

	extendDot1vProtocolPortTable OBJECT-TYPE
		SYNTAX	SEQUENCE OF ExtendDot1vProtocolPortEntry 
		ACCESS	not-accessible
		STATUS	mandatory
		DESCRIPTION
			"A proprietary dot1vProtocolPortTable extension to set the defaut
			priority of a protocol based VLAN
             ALCATEL NOTE:
                 TABLESIZE:  DEP [depends on the size of extendDot1vprotocolGropuTable* dot1dBaseNumPorts]
                 DESCR:      NA"
		::= {  extendDot1vProtocol 2 }

	extendDot1vProtocolPortEntry  OBJECT-TYPE
		SYNTAX	ExtendDot1vProtocolPortEntry
		ACCESS	not-accessible
		STATUS	mandatory
		DESCRIPTION
			"An entry in the table extendDot1vprotocolPortTable."
		INDEX	{ dot1dBasePort, dot1vProtocolPortGroupId }
		::= { extendDot1vProtocolPortTable 1 }

	ExtendDot1vProtocolPortEntry  ::=
		SEQUENCE	{ 
				extendDot1vProtocolPortGroupPriority
					ExtendVlanSystemPriority,
                 extendDot1vProtocolPortGroupVid
                     VlanIndex
				}
	
	extendDot1vProtocolPortGroupPriority	OBJECT-TYPE
		SYNTAX	ExtendVlanSystemPriority
		ACCESS	read-write
		STATUS	mandatory
		DESCRIPTION
			"The default priority of a protocol based VLAN
             ALCATEL NOTE:
                 ACCESS:     NA       USAGE:      NA
                 PERSIST:    YES      INSRVMOD:   YES
                 RANGE:      0..7      DEFVALUE:   NA
                 UNITS:      NA       SPARSE:     NA
                 DESCR:      NA"
		::= { extendDot1vProtocolPortEntry 1 }

	extendDot1vProtocolPortGroupVid	OBJECT-TYPE
		SYNTAX	VlanIndex
		ACCESS	read-write
		STATUS	mandatory
		DESCRIPTION
			"The VID associated with a group of protocols for each port.
             ALCATEL NOTE:
                 ACCESS:     NA       USAGE:      NA
                 PERSIST:    YES      INSRVMOD:   NO
                 RANGE:      NA       DEFVALUE:   NULL
                 UNITS:      NA       SPARSE:     NA
                 DESCR:      NA"
		::= { extendDot1vProtocolPortEntry 2 }


-- =====================
--	Statistics
-- =====================

	extendStatistics	OBJECT IDENTIFIER ::= { plimEthernet 9 }

	extendPortVlanPerfInfoTable	 OBJECT-TYPE
		SYNTAX	SEQUENCE OF ExtendPortVlanPerfInfoEntry
		ACCESS	not-accessible
		STATUS	mandatory
		DESCRIPTION
			"Table of number of previous statistics intervals related to one Vlan
 			on a bridge port.
             ALCATEL NOTE:
                 TABLESIZE:  DEP [depends on the value of 
                                 extendPortVlanAssociationTable]
                 DESCR:      NA"
		::= { extendStatistics 1 }

	extendPortVlanPerfInfoEntry OBJECT-TYPE
		SYNTAX	ExtendPortVlanPerfInfoEntry
		ACCESS	not-accessible
		STATUS	mandatory
		DESCRIPTION
			"Table entry for available statistics intervals for one Vlan on a 
			bridge port."
		INDEX   { dot1dBasePort, extendPortVlanPerfInfoVlanIndex }
		::= { extendPortVlanPerfInfoTable 1 }

	ExtendPortVlanPerfInfoEntry ::=
		SEQUENCE {
				extendPortVlanPerfInfoVlanIndex
					VlanIndex,
				extendPortVlanPerfInfo15MinValidIntervals
					INTEGER,
				extendPortVlanPerfInfo1DayValidIntervals
					INTEGER
				}

	extendPortVlanPerfInfoVlanIndex OBJECT-TYPE
		SYNTAX	VlanIndex
		ACCESS  	not-accessible
		STATUS	mandatory
		DESCRIPTION
			"VLAN ID.
             ALCATEL NOTE:
                 ACCESS:     NA       USAGE:      NA
                 PERSIST:    NO       INSRVMOD:   NO
                 RANGE:      NA       DEFVALUE:   NA
                 UNITS:      NA       SPARSE:     NA
                 DESCR:      NA"
		::= { extendPortVlanPerfInfoEntry 1 }


	extendPortVlanPerfInfo15MinValidIntervals OBJECT-TYPE
		SYNTAX	INTEGER
		ACCESS  	read-only
		STATUS	mandatory
		DESCRIPTION
			"Number of previous 15 minutes intervals
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPerfInfoEntry 2 }

	extendPortVlanPerfInfo1DayValidIntervals OBJECT-TYPE
		SYNTAX	INTEGER
		ACCESS  	read-only
		STATUS	mandatory
		DESCRIPTION
			"Number of previous 1 day intervals
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPerfInfoEntry 3 }

--

	extendPortVlanCurrent15MinIntervalTable	 OBJECT-TYPE
		SYNTAX	SEQUENCE OF ExtendPortVlanCurrent15MinIntervalEntry
		ACCESS	not-accessible
		STATUS	mandatory
		DESCRIPTION
			"15 Minutes current statistics for a VLAN/port	
             ALCATEL NOTE:
                 TABLESIZE:  DEP [depends on the value of 
                                 extendPortVlanAssociationTable]
                 DESCR:      NA"
		::= { extendStatistics 2 }

	extendPortVlanCurrent15MinIntervalEntry OBJECT-TYPE
		SYNTAX	ExtendPortVlanCurrent15MinIntervalEntry
		ACCESS	not-accessible
		STATUS	mandatory
		DESCRIPTION
			"Table entry for the current 15 minutes statistics counters for a 
			VLAN/port."
		INDEX   { dot1dBasePort, extendPortVlanCurrent15MinIntervalVlanIndex }
		::= { extendPortVlanCurrent15MinIntervalTable	 1 }

	 ExtendPortVlanCurrent15MinIntervalEntry ::=
		SEQUENCE {
				extendPortVlanCurrent15MinIntervalVlanIndex
					VlanIndex,
				extendPortVlanCurrent15MinTimeElapsed
					INTEGER, 
				extendPortVlanCurrent15MinTimeMeasured
					INTEGER,
				extendPortVlanCurrent15MinUpFwdFrameCounter
					 OCTET STRING (SIZE (8)),
				extendPortVlanCurrent15MinUpFwdByteCounter
					 OCTET STRING (SIZE (8)),
				extendPortVlanCurrent15MinDnFwdFrameCounter
					 OCTET STRING (SIZE (8)),
				extendPortVlanCurrent15MinDnFwdByteCounter
					 OCTET STRING (SIZE (8)),
				extendPortVlanCurrent15MinUpDiscFrameCounter
					 OCTET STRING (SIZE (8)),
				extendPortVlanCurrent15MinUpDiscByteCounter
					 OCTET STRING (SIZE (8)),
				extendPortVlanCurrent15MinDnDiscFrameCounter
					 OCTET STRING (SIZE (8)),
				extendPortVlanCurrent15MinDnDiscByteCounter
					 OCTET STRING (SIZE (8))
			}

	extendPortVlanCurrent15MinIntervalVlanIndex OBJECT-TYPE
		SYNTAX	VlanIndex
		ACCESS  	not-accessible
		STATUS	mandatory
		DESCRIPTION
			"VLAN ID. on which the counters apply
             ALCATEL NOTE:
                 ACCESS:     NA       USAGE:      NA
                 PERSIST:    NO       INSRVMOD:   NO
                 RANGE:      NA       DEFVALUE:   NA
                 UNITS:      NA       SPARSE:     NA
                 DESCR:      NA"
		::= { extendPortVlanCurrent15MinIntervalEntry 1 }
	
	extendPortVlanCurrent15MinTimeElapsed OBJECT-TYPE
		SYNTAX	INTEGER
		ACCESS  	read-only
		STATUS	mandatory
		DESCRIPTION
			"Elapsed time in interval (seconds)
            ALCATEL NOTE:
                ACCESS:     NA       USAGE:      NA
                PERSIST:    NO       INSRVMOD:   NO
                RANGE:      NA       DEFVALUE:   NA
                UNITS:      seconds  SPARSE:     NA
                DESCR:      NA"
		::= { extendPortVlanCurrent15MinIntervalEntry 2 }

	extendPortVlanCurrent15MinTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
		::= { extendPortVlanCurrent15MinIntervalEntry 3 }


	 extendPortVlanCurrent15MinUpFwdFrameCounter OBJECT-TYPE
		SYNTAX	OCTET STRING (SIZE (8))
--		the first octet contains the most significant byte
		ACCESS  	read-only
		STATUS	mandatory
		DESCRIPTION
			"All forwarded frames in upstream direction per VLAN on a bridge port 
			in current 15 min interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 4 }


	extendPortVlanCurrent15MinUpFwdByteCounter OBJECT-TYPE
		SYNTAX	OCTET STRING (SIZE (8))
		ACCESS  	read-only
		STATUS	mandatory
		DESCRIPTION
			"All forwarded bytes in upstream direction per VLAN on a bridge port
 			in current 15 min interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 5 }

	extendPortVlanCurrent15MinDnFwdFrameCounter OBJECT-TYPE
		SYNTAX	OCTET STRING (SIZE (8))
		ACCESS  	read-only
		STATUS	mandatory
		DESCRIPTION
			"All forwarded frames in downstream direction per VLAN on a bridge
			port in current 15 min interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 6 }

	extendPortVlanCurrent15MinDnFwdByteCounter OBJECT-TYPE
		SYNTAX	OCTET STRING (SIZE (8))
		ACCESS  	read-only
		STATUS	mandatory
		DESCRIPTION
			"All forwarded  bytes in downstream direction per VLAN on a bridge 
			port in current 15 min interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 7 }

	extendPortVlanCurrent15MinUpDiscFrameCounter OBJECT-TYPE
		SYNTAX	OCTET STRING (SIZE (8))
		ACCESS  	read-only
		STATUS	mandatory
		DESCRIPTION
			"All discarded frames in upstream direction per VLAN on a bridge 
			port in current 15 min interval.Counted : discards by buffer 
			acceptance or policing
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 8 }

	extendPortVlanCurrent15MinUpDiscByteCounter OBJECT-TYPE
		SYNTAX	OCTET STRING (SIZE (8))
		ACCESS  	read-only
		STATUS	mandatory
		DESCRIPTION
			"All discarded bytes in upstream direction per VLAN on a bridge 
			port in current 15 min interval.Counted : discards by buffer 
			acceptance or policing
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 9 }

	extendPortVlanCurrent15MinDnDiscFrameCounter OBJECT-TYPE
		SYNTAX	OCTET STRING (SIZE (8))
		ACCESS  	read-only
		STATUS	mandatory
		DESCRIPTION
			"All discarded frames in downstream direction per VLAN on a bridge 
			port in current 15 min interval. Counted : discards by buffer 
			acceptance or policing
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 10 }

	extendPortVlanCurrent15MinDnDiscByteCounter OBJECT-TYPE
		SYNTAX	OCTET STRING (SIZE (8))
		ACCESS  	read-only
		STATUS	mandatory
		DESCRIPTION
			"All discarded bytes in downstream direction per VLAN on a bridge 
			port in current 15 min interval. Counted : discards by buffer 
			acceptance or policing
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 11 }

--   
	
	extendPortVlanCurrent1DayIntervalTable	 OBJECT-TYPE
		SYNTAX	SEQUENCE OF ExtendPortVlanCurrent1DayIntervalEntry
		ACCESS	not-accessible
		STATUS	mandatory
		DESCRIPTION
			"1 Day current statistics for a VLAN/port
             ALCATEL NOTE:
                 TABLESIZE:  DEP [depending on the value of 
                                 extendPortVlanAssociationTable]
                 DESCR:      NA"
		::= { extendStatistics 3 }

	extendPortVlanCurrent1DayIntervalEntry OBJECT-TYPE
		SYNTAX	ExtendPortVlanCurrent1DayIntervalEntry
		ACCESS	not-accessible
		STATUS	mandatory
		DESCRIPTION
			"Table entry for the current 1 day statistics counters per VLAN/port."
		INDEX   { dot1dBasePort, extendPortVlanCurrent1DayIntervalVlanIndex }
		::= { extendPortVlanCurrent1DayIntervalTable	 1 }

	 ExtendPortVlanCurrent1DayIntervalEntry ::=
		SEQUENCE {
				extendPortVlanCurrent1DayIntervalVlanIndex
					VlanIndex,
				extendPortVlanCurrent1DayTimeElapsed
					INTEGER, 
				extendPortVlanCurrent1DayTimeMeasured
					INTEGER,
				extendPortVlanCurrent1DayUpFwdFrameCounter
					OCTET STRING (SIZE (8)),
				extendPortVlanCurrent1DayUpFwdByteCounter
					OCTET STRING (SIZE (8)),
				extendPortVlanCurrent1DayDnFwdFrameCounter
					OCTET STRING (SIZE (8)),
				extendPortVlanCurrent1DayDnFwdByteCounter
					OCTET STRING (SIZE (8)),
				extendPortVlanCurrent1DayUpDiscFrameCounter
					OCTET STRING (SIZE (8)),
				extendPortVlanCurrent1DayUpDiscByteCounter
					OCTET STRING (SIZE (8)),
				extendPortVlanCurrent1DayDnDiscFrameCounter
					OCTET STRING (SIZE (8)),
				extendPortVlanCurrent1DayDnDiscByteCounter
					OCTET STRING (SIZE (8))
							}

	extendPortVlanCurrent1DayIntervalVlanIndex  OBJECT-TYPE
		SYNTAX	VlanIndex
		ACCESS  	not-accessible
		STATUS	mandatory
		DESCRIPTION
			"VLAN ID. of the VLAN on which the counters apply
             ALCATEL NOTE:
                 ACCESS:     NA       USAGE:      NA
                 PERSIST:    NO       INSRVMOD:   NO
                 RANGE:      NA       DEFVALUE:   NA
                 UNITS:      NA       SPARSE:     NA
                 DESCR:      NA"
		::= { extendPortVlanCurrent1DayIntervalEntry 1 }
	
	extendPortVlanCurrent1DayTimeElapsed OBJECT-TYPE
		SYNTAX	INTEGER
		ACCESS  	read-only
		STATUS	mandatory
		DESCRIPTION
			"Elapsed time in interval (seconds)
             ALCATEL NOTE:
                 ACCESS:     NA       USAGE:      NA
                 PERSIST:    NO       INSRVMOD:   NO
                 RANGE:      NA       DEFVALUE:   NA
                 UNITS:      seconds  SPARSE:     NA
                                 DESCR:      NA"
		::= { extendPortVlanCurrent1DayIntervalEntry 2 }

	extendPortVlanCurrent1DayTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
		::= { extendPortVlanCurrent1DayIntervalEntry 3 }


	 extendPortVlanCurrent1DayUpFwdFrameCounter OBJECT-TYPE
		SYNTAX	OCTET STRING (SIZE (8))
--		the first octet contains the most significant byte
		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 4 }


	extendPortVlanCurrent1DayUpFwdByteCounter OBJECT-TYPE
		SYNTAX	OCTET STRING (SIZE (8))
		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 5 }

	extendPortVlanCurrent1DayDnFwdFrameCounter OBJECT-TYPE
		SYNTAX	OCTET STRING (SIZE (8))
		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 6 }

	extendPortVlanCurrent1DayDnFwdByteCounter OBJECT-TYPE
		SYNTAX	OCTET STRING (SIZE (8))
		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 7 }

	extendPortVlanCurrent1DayUpDiscFrameCounter OBJECT-TYPE
		SYNTAX	OCTET STRING (SIZE (8))
		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 8 }

	extendPortVlanCurrent1DayUpDiscByteCounter OBJECT-TYPE
		SYNTAX	OCTET STRING (SIZE (8))
		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 9 }

	extendPortVlanCurrent1DayDnDiscFrameCounter OBJECT-TYPE
		SYNTAX	OCTET STRING (SIZE (8))
		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 10 }

	extendPortVlanCurrent1DayDnDiscByteCounter OBJECT-TYPE
		SYNTAX	OCTET STRING (SIZE (8))
		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 11 }

	

--

	extendPortVlanPrevious15MinIntervalTable	 OBJECT-TYPE
		SYNTAX	SEQUENCE OF ExtendPortVlanPrevious15MinIntervalEntry
		ACCESS	not-accessible
		STATUS	mandatory
		DESCRIPTION
			"15 Minutes previous statistics counters for VLAN/port
             ALCATEL NOTE:
                 TABLESIZE:  DEP [depending on the value of 
                                 extendPortVlanAssociationTable]
                 DESCR:      NA"
		::= { extendStatistics 4 }

	extendPortVlanPrevious15MinIntervalEntry OBJECT-TYPE
		SYNTAX	ExtendPortVlanPrevious15MinIntervalEntry
		ACCESS	not-accessible
		STATUS	mandatory
		DESCRIPTION
			"Table entry for the previous 15 minutes statistics counters per 
			VLAN/port."
      INDEX   { dot1dBasePort,
            extendPortVlanPrevious15MinIntervalVlanIndex,
				extendPortVlanPrevious15MinIntervalNumber }
		::= { extendPortVlanPrevious15MinIntervalTable	 1 }

	 ExtendPortVlanPrevious15MinIntervalEntry ::=
		SEQUENCE {
				extendPortVlanPrevious15MinIntervalVlanIndex
					VlanIndex,
				extendPortVlanPrevious15MinIntervalNumber
					INTEGER,
				extendPortVlanPrevious15MinTimeMeasured
					INTEGER,
				extendPortVlanPrevious15MinUpFwdFrameCounter
					OCTET STRING (SIZE (8)),
				extendPortVlanPrevious15MinUpFwdByteCounter
					OCTET STRING (SIZE (8)),
				extendPortVlanPrevious15MinDnFwdFrameCounter
					OCTET STRING (SIZE (8)),
				extendPortVlanPrevious15MinDnFwdByteCounter
					OCTET STRING (SIZE (8)),
				extendPortVlanPrevious15MinUpDiscFrameCounter
					OCTET STRING (SIZE (8)),
				extendPortVlanPrevious15MinUpDiscByteCounter
					OCTET STRING (SIZE (8)),
				extendPortVlanPrevious15MinDnDiscFrameCounter
					OCTET STRING (SIZE (8)),
				extendPortVlanPrevious15MinDnDiscByteCounter
					OCTET STRING (SIZE (8))
			}

	extendPortVlanPrevious15MinIntervalVlanIndex OBJECT-TYPE 
		SYNTAX	VlanIndex
		ACCESS  	not-accessible
		STATUS	mandatory
		DESCRIPTION
			"VLAN ID. on which the counters apply
             ALCATEL NOTE:
                 ACCESS:     NA       USAGE:      NA
                 PERSIST:    NO       INSRVMOD:   NO
                 RANGE:      NA       DEFVALUE:   NA
                 UNITS:      NA       SPARSE:     NA
                 DESCR:      NA"
		::= { extendPortVlanPrevious15MinIntervalEntry 1 }
	
	extendPortVlanPrevious15MinIntervalNumber OBJECT-TYPE
		SYNTAX	INTEGER
		ACCESS  	not-accessible
		STATUS	mandatory
		DESCRIPTION
			"Previous interval reference
             ALCATEL NOTE:
                 ACCESS:     NA       USAGE:      NA
                 PERSIST:    NO       INSRVMOD:   NO
                 RANGE:      NA       DEFVALUE:   NA
                 UNITS:      NA       SPARSE:     NA
                 DESCR:      NA"
		::= { extendPortVlanPrevious15MinIntervalEntry 2 }

	extendPortVlanPrevious15MinTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
		::= { extendPortVlanPrevious15MinIntervalEntry 3 }


	 extendPortVlanPrevious15MinUpFwdFrameCounter OBJECT-TYPE
		SYNTAX	OCTET STRING (SIZE (8))
--		the first octet contains the most significant byte
		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 4 }


	extendPortVlanPrevious15MinUpFwdByteCounter OBJECT-TYPE
		SYNTAX	OCTET STRING (SIZE (8))
		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 5 }

	extendPortVlanPrevious15MinDnFwdFrameCounter OBJECT-TYPE
		SYNTAX	OCTET STRING (SIZE (8))
		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 6 }

	extendPortVlanPrevious15MinDnFwdByteCounter OBJECT-TYPE
		SYNTAX	OCTET STRING (SIZE (8))
		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 7 }

	extendPortVlanPrevious15MinUpDiscFrameCounter OBJECT-TYPE
		SYNTAX	OCTET STRING (SIZE (8))
		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 8 }

	extendPortVlanPrevious15MinUpDiscByteCounter OBJECT-TYPE
		SYNTAX	OCTET STRING (SIZE (8))
		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 9 }

	extendPortVlanPrevious15MinDnDiscFrameCounter OBJECT-TYPE
		SYNTAX	OCTET STRING (SIZE (8))
		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 10 }

	extendPortVlanPrevious15MinDnDiscByteCounter OBJECT-TYPE
		SYNTAX	OCTET STRING (SIZE (8))
		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 11 }

--

	extendPortVlanPrevious1DayIntervalTable	 OBJECT-TYPE
		SYNTAX	SEQUENCE OF ExtendPortVlanPrevious1DayIntervalEntry
		ACCESS	not-accessible
		STATUS	mandatory
		DESCRIPTION
			"1 Day previous statistics for VLAN/port
             ALCATEL NOTE:
                 TABLESIZE:  DEP [depending on the value of 
                                 extendPortVlanAssociationTable]
                 DESCR:      NA"
		::= { extendStatistics 5 }

	extendPortVlanPrevious1DayIntervalEntry OBJECT-TYPE
		SYNTAX	ExtendPortVlanPrevious1DayIntervalEntry
		ACCESS	not-accessible
		STATUS	mandatory
		DESCRIPTION
			"Table entry for the previous 1 day statistics counters."
		INDEX	{ dot1dBasePort, extendPortVlanPrevious1DayIntervalVlanIndex, 
				extendPortVlanPrevious1DayIntervalNumber
				}
		::= { extendPortVlanPrevious1DayIntervalTable	 1 }

	 ExtendPortVlanPrevious1DayIntervalEntry ::=
		SEQUENCE {
				extendPortVlanPrevious1DayIntervalVlanIndex
					VlanIndex,
				extendPortVlanPrevious1DayIntervalNumber
					INTEGER,
				extendPortVlanPrevious1DayTimeMeasured
					INTEGER,
				extendPortVlanPrevious1DayUpFwdFrameCounter
					OCTET STRING (SIZE (8)),
				extendPortVlanPrevious1DayUpFwdByteCounter
					OCTET STRING (SIZE (8)),
				extendPortVlanPrevious1DayDnFwdFrameCounter
					OCTET STRING (SIZE (8)),
				extendPortVlanPrevious1DayDnFwdByteCounter
					OCTET STRING (SIZE (8)),
				extendPortVlanPrevious1DayUpDiscFrameCounter
					OCTET STRING (SIZE (8)),
				extendPortVlanPrevious1DayUpDiscByteCounter
					OCTET STRING (SIZE (8)),
				extendPortVlanPrevious1DayDnDiscFrameCounter
					OCTET STRING (SIZE (8)),
				extendPortVlanPrevious1DayDnDiscByteCounter
					OCTET STRING (SIZE (8))
				

			}

	extendPortVlanPrevious1DayIntervalVlanIndex  OBJECT-TYPE
		SYNTAX	VlanIndex
		ACCESS  	not-accessible
		STATUS	mandatory
		DESCRIPTION
			"VLAN ID. on which the counters apply
             ALCATEL NOTE:
                 ACCESS:     NA       USAGE:      NA
                 PERSIST:    NO       INSRVMOD:   NO
                 RANGE:      NA       DEFVALUE:   NA
                 UNITS:      NA       SPARSE:     NA
                 DESCR:      NA"
		::= { extendPortVlanPrevious1DayIntervalEntry 1 }
	
	extendPortVlanPrevious1DayIntervalNumber OBJECT-TYPE
		SYNTAX	INTEGER
		ACCESS  	not-accessible
		STATUS	mandatory
		DESCRIPTION
			"Previous interval reference
             ALCATEL NOTE:
                 ACCESS:     NA       USAGE:      NA
                 PERSIST:    NO       INSRVMOD:   NO
                 RANGE:      NA       DEFVALUE:   NA
                 UNITS:      NA       SPARSE:     NA
                 DESCR:      NA"
		::= { extendPortVlanPrevious1DayIntervalEntry 2 }


	extendPortVlanPrevious1DayTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
		::= { extendPortVlanPrevious1DayIntervalEntry 3 }


	 extendPortVlanPrevious1DayUpFwdFrameCounter OBJECT-TYPE
		SYNTAX	OCTET STRING (SIZE (8))
--		the first octet contains the most significant byte
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 4 }


	extendPortVlanPrevious1DayUpFwdByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 5 }

	extendPortVlanPrevious1DayDnFwdFrameCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 6 }

	extendPortVlanPrevious1DayDnFwdByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 7 }

	extendPortVlanPrevious1DayUpDiscFrameCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 8 }

	extendPortVlanPrevious1DayUpDiscByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 9 }

	extendPortVlanPrevious1DayDnDiscFrameCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 10 }

	extendPortVlanPrevious1DayDnDiscByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 11 }

	
--
--


	extendPortTotalPerfInfoTable	 OBJECT-TYPE
		SYNTAX	SEQUENCE OF ExtendPortTotalPerfInfoEntry
		ACCESS	not-accessible
		STATUS	mandatory
		DESCRIPTION
			"Table of number of previous statistics intervals for the traffic on a
 			bridgeport (PortTotal = all traffic on a port, including PPPoE relayed
 			and PPPoE terminated traffic) per bridge port
             ALCATEL NOTE:
                 TABLESIZE:  DEP [depending on the value of 
                             dot1dBaseNumPorts.]
                 DESCR:      NA"
		::= { extendStatistics 6 }

	extendPortTotalPerfInfoEntry OBJECT-TYPE
		SYNTAX	ExtendPortTotalPerfInfoEntry
		ACCESS	not-accessible
		STATUS	mandatory
		DESCRIPTION
			"Table entry of extendportTotalPerfInfoTable"
		INDEX   { dot1dBasePort }
		::= { extendPortTotalPerfInfoTable 1 }

	ExtendPortTotalPerfInfoEntry ::=
		SEQUENCE	{
				extendPortTotalPerfInfo15MinValidIntervals
					INTEGER,
				extendPortTotalPerfInfo1DayValidIntervals
					INTEGER
				}

	
	extendPortTotalPerfInfo15MinValidIntervals OBJECT-TYPE
		SYNTAX	INTEGER
		ACCESS  	read-only
		STATUS	mandatory
		DESCRIPTION
			"Number of previous 15 minutes intervals
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPerfInfoEntry 1 }

	extendPortTotalPerfInfo1DayValidIntervals OBJECT-TYPE
		SYNTAX	INTEGER
		ACCESS  	read-only
		STATUS	mandatory
		DESCRIPTION
			"Number of previous 1 day intervals
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPerfInfoEntry 2 }

--

	extendPortTotalCurrent15MinIntervalTable	 OBJECT-TYPE
		SYNTAX	SEQUENCE OF ExtendPortTotalCurrent15MinIntervalEntry
		ACCESS	not-accessible
		STATUS	mandatory
		DESCRIPTION
			"15 Minutes current statistics for PortTotal (= all traffic on a port, 
			Including PPPoE relayed and PPPoE terminated traffic) 
             ALCATEL NOTE:
                 TABLESIZE:  DEP [depending on the value of 
                             dot1dBaseNumPorts.]
                 DESCR:      NA"
		::= { extendStatistics 7 }

	extendPortTotalCurrent15MinIntervalEntry OBJECT-TYPE
		SYNTAX	ExtendPortTotalCurrent15MinIntervalEntry
		ACCESS	not-accessible
		STATUS	mandatory
		DESCRIPTION
			"Table entry for the current 15 minutes statistics counters."
		INDEX   { dot1dBasePort }
		::= { extendPortTotalCurrent15MinIntervalTable 1 }

	 ExtendPortTotalCurrent15MinIntervalEntry ::=
		SEQUENCE {
				extendPortTotalCurrent15MinTimeElapsed
					INTEGER, 
				extendPortTotalCurrent15MinTimeMeasured
					INTEGER,
				extendPortTotalCurrent15MinUpFwdFrameCounter
					OCTET STRING (SIZE (8)),
				extendPortTotalCurrent15MinUpFwdByteCounter
					OCTET STRING (SIZE (8)),
				extendPortTotalCurrent15MinDnFwdFrameCounter
					OCTET STRING (SIZE (8)),
				extendPortTotalCurrent15MinDnFwdByteCounter
					OCTET STRING (SIZE (8)),
				extendPortTotalCurrent15MinUpDiscFrameCounter
					OCTET STRING (SIZE (8)),
				extendPortTotalCurrent15MinUpDiscByteCounter
					OCTET STRING (SIZE (8)),
				extendPortTotalCurrent15MinDnDiscFrameCounter
					OCTET STRING (SIZE (8)),
				extendPortTotalCurrent15MinDnDiscByteCounter
					OCTET STRING (SIZE (8))
			}

		
	extendPortTotalCurrent15MinTimeElapsed OBJECT-TYPE
		SYNTAX	INTEGER
		ACCESS  	read-only
		STATUS	mandatory
		DESCRIPTION
			"Elapsed time in interval (seconds)
             ALCATEL NOTE:
                 ACCESS:     NA       USAGE:      NA
                 PERSIST:    NO       INSRVMOD:   NO
                 RANGE:      NA       DEFVALUE:   0
                 UNITS:      seconds  SPARSE:     NA
                 DESCR:      NA"
		::= { extendPortTotalCurrent15MinIntervalEntry 1 }

	extendPortTotalCurrent15MinTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   0
                 UNITS:      seconds  SPARSE:     NA
                 DESCR:      NA"
		::= { extendPortTotalCurrent15MinIntervalEntry 2 }

	 extendPortTotalCurrent15MinUpFwdFrameCounter OBJECT-TYPE
		SYNTAX	OCTET STRING (SIZE (8))
--		the first octet contains the most significant byte
		ACCESS  	read-only
		STATUS	mandatory
		DESCRIPTION
			"Total forwarded frames per port in upstream direction (current 
			15 min. interval)
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 3 }


	extendPortTotalCurrent15MinUpFwdByteCounter OBJECT-TYPE
		SYNTAX	OCTET STRING (SIZE (8))
		ACCESS  	read-only
		STATUS	mandatory
		DESCRIPTION
			"Total forwarded bytes per port in upstream direction (current 
			15 min. interval)
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 4 }

	extendPortTotalCurrent15MinDnFwdFrameCounter OBJECT-TYPE
		SYNTAX	OCTET STRING (SIZE (8))
		ACCESS  	read-only
		STATUS	mandatory
		DESCRIPTION
			"Total forwarded frames per port in downstream direction (current 
			15 min. interval)
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 5 }

	extendPortTotalCurrent15MinDnFwdByteCounter OBJECT-TYPE
		SYNTAX	OCTET STRING (SIZE (8))
		ACCESS  	read-only
		STATUS	mandatory
		DESCRIPTION
			"Total forwarded bytes per port in downstream direction (current 
			15 min. interval)
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 6 }

	extendPortTotalCurrent15MinUpDiscFrameCounter OBJECT-TYPE
		SYNTAX	OCTET STRING (SIZE (8))
		ACCESS  	read-only
		STATUS	mandatory
		DESCRIPTION
			"Total discarded frames per port in upstream direction (current 
			15 min interval). Counted : discards by buffer acceptance or 
			policing.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 7 }

	extendPortTotalCurrent15MinUpDiscByteCounter OBJECT-TYPE
		SYNTAX	OCTET STRING (SIZE (8))
		ACCESS  	read-only
		STATUS	mandatory
		DESCRIPTION
			"Total discarded bytes per port in upstream direction (current 
			15 min. interval). Counted : discards by buffer acceptance or 
			policing.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 8 }

	extendPortTotalCurrent15MinDnDiscFrameCounter OBJECT-TYPE
		SYNTAX	OCTET STRING (SIZE (8))
		ACCESS  	read-only
		STATUS	mandatory
		DESCRIPTION
			"Total discarded frames per port in downstream direction (current 
			15 min. interval). Counted : discards by buffer acceptance or 
			policing.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 9 }

	extendPortTotalCurrent15MinDnDiscByteCounter OBJECT-TYPE
		SYNTAX	OCTET STRING (SIZE (8))
		ACCESS  	read-only
		STATUS	mandatory
		DESCRIPTION
			"Total discarded bytes per port in downstream direction (current 
			15 min. interval). Counted : discards by buffer acceptance or 
			policing.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 10 }


--   
	
	extendPortTotalCurrent1DayIntervalTable	 OBJECT-TYPE
		SYNTAX	SEQUENCE OF ExtendPortTotalCurrent1DayIntervalEntry
		ACCESS	not-accessible
		STATUS	mandatory
		DESCRIPTION
			"1 Day current statistics for PortTotal (= all traffic on a port, 
	I		including PPPoE relayed and PPPoE terminated traffic) 
             ALCATEL NOTE:
                 TABLESIZE:  DEP [depending on the value of 
                             dot1dBaseNumPorts.]
                 DESCR:      NA"
		::= { extendStatistics 8 }

	extendPortTotalCurrent1DayIntervalEntry OBJECT-TYPE
		SYNTAX	ExtendPortTotalCurrent1DayIntervalEntry
		ACCESS	not-accessible
		STATUS	mandatory
		DESCRIPTION
			"Table entry for the current 1 day statistics counters for PortTotal."
		INDEX   { dot1dBasePort }
		::= { extendPortTotalCurrent1DayIntervalTable	 1 }

	 ExtendPortTotalCurrent1DayIntervalEntry ::=
		SEQUENCE {
				extendPortTotalCurrent1DayTimeElapsed
					INTEGER, 
				extendPortTotalCurrent1DayTimeMeasured
					INTEGER,
				extendPortTotalCurrent1DayUpFwdFrameCounter
					OCTET STRING (SIZE (8)),
				extendPortTotalCurrent1DayUpFwdByteCounter
					OCTET STRING (SIZE (8)),
				extendPortTotalCurrent1DayDnFwdFrameCounter
					OCTET STRING (SIZE (8)),
				extendPortTotalCurrent1DayDnFwdByteCounter
					OCTET STRING (SIZE (8)),
				extendPortTotalCurrent1DayUpDiscFrameCounter
					OCTET STRING (SIZE (8)),
				extendPortTotalCurrent1DayUpDiscByteCounter
					OCTET STRING (SIZE (8)),
				extendPortTotalCurrent1DayDnDiscFrameCounter
					OCTET STRING (SIZE (8)),
				extendPortTotalCurrent1DayDnDiscByteCounter
					OCTET STRING (SIZE (8))
			}

		
	extendPortTotalCurrent1DayTimeElapsed OBJECT-TYPE
		SYNTAX	INTEGER
		ACCESS  	read-only
		STATUS	mandatory
		DESCRIPTION
			"Elapsed time in interval (seconds)
             ALCATEL NOTE:
                 ACCESS:     NA       USAGE:      NA
                 PERSIST:    NO       INSRVMOD:   NO
                 RANGE:      NA       DEFVALUE:   0
                 UNITS:      seconds  SPARSE:     NA
                 DESCR:      NA"
		::= { extendPortTotalCurrent1DayIntervalEntry 1 }

	extendPortTotalCurrent1DayTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   0
                 UNITS:      seconds  SPARSE:     NA
                 DESCR:      NA"
		::= { extendPortTotalCurrent1DayIntervalEntry 2 }

	 extendPortTotalCurrent1DayUpFwdFrameCounter OBJECT-TYPE
		SYNTAX	OCTET STRING (SIZE (8))
--		the first octet contains the most significant byte
		ACCESS  	read-only
		STATUS	mandatory
		DESCRIPTION
			"Definition as for current corresponding 15 min. counters but per 
			day.
             ALCATEL NOTE:
                 ACCESS:     NA       USAGE:      NA
                 PERSIST:    NO       INSRVMOD:   YES
                 RANGE:      NA       DEFVALUE:   NA
                 UNITS:      NA       SPARSE:     NA
                 DESCR:      NA"
		::= { extendPortTotalCurrent1DayIntervalEntry 3 }


	extendPortTotalCurrent1DayUpFwdByteCounter OBJECT-TYPE
		SYNTAX	OCTET STRING (SIZE (8))
		ACCESS  	read-only
		STATUS	mandatory
		DESCRIPTION
			"Definition as for current corresponding 15 min. counters but per 
			day.
              ALCATEL NOTE:
                  ACCESS:     NA       USAGE:      NA
                  PERSIST:    NO       INSRVMOD:   NO
                  RANGE:      NA       DEFVALUE:   0
                  UNITS:      NA       SPARSE:     NA
                  DESCR:      NA"
		::= { extendPortTotalCurrent1DayIntervalEntry 4 }

	extendPortTotalCurrent1DayDnFwdFrameCounter OBJECT-TYPE
		SYNTAX	OCTET STRING (SIZE (8))
		ACCESS  	read-only
		STATUS	mandatory
		DESCRIPTION
			"Definition as for current corresponding 15 min. counters but per 
			day.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent1DayIntervalEntry 5 }

	extendPortTotalCurrent1DayDnFwdByteCounter OBJECT-TYPE
		SYNTAX	OCTET STRING (SIZE (8))
		ACCESS  	read-only
		STATUS	mandatory
		DESCRIPTION
			"Definition as for current corresponding 15 min. counters but per 
			day.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent1DayIntervalEntry 6 }

	extendPortTotalCurrent1DayUpDiscFrameCounter OBJECT-TYPE
		SYNTAX	OCTET STRING (SIZE (8))
		ACCESS  	read-only
		STATUS	mandatory
		DESCRIPTION
			"Definition as for current corresponding 15 min. counters but per 
			day.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent1DayIntervalEntry 7 }

	extendPortTotalCurrent1DayUpDiscByteCounter OBJECT-TYPE
		SYNTAX	OCTET STRING (SIZE (8))
		ACCESS  	read-only
		STATUS	mandatory
		DESCRIPTION
			"Definition as for current corresponding 15 min. counters but per 
			day.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent1DayIntervalEntry 8 }

	extendPortTotalCurrent1DayDnDiscFrameCounter OBJECT-TYPE
		SYNTAX	OCTET STRING (SIZE (8))
		ACCESS  	read-only
		STATUS	mandatory
		DESCRIPTION
			"Definition as for current corresponding 15 min. counters but per 
			day.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent1DayIntervalEntry 9 }

	extendPortTotalCurrent1DayDnDiscByteCounter OBJECT-TYPE
		SYNTAX	OCTET STRING (SIZE (8))
		ACCESS  	read-only
		STATUS	mandatory
		DESCRIPTION
			"Definition as for current corresponding 15 min. counters but per 
			day.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent1DayIntervalEntry 10 }

	--

	extendPortTotalPrevious15MinIntervalTable	 OBJECT-TYPE
		SYNTAX	SEQUENCE OF ExtendPortTotalPrevious15MinIntervalEntry
		ACCESS	not-accessible
		STATUS	mandatory
		DESCRIPTION
			"15 Minutes previous statistics for PortTotal(= all traffic on a port,
 			Including PPPoE relayed and PPPoE terminated traffic) 
             ALCATEL NOTE:
                 TABLESIZE:  DEP [depending on the value of 
                             dot1dBaseNumPorts.]
                 DESCR:      NA"
		::= { extendStatistics 9 }

	extendPortTotalPrevious15MinIntervalEntry OBJECT-TYPE
		SYNTAX	ExtendPortTotalPrevious15MinIntervalEntry
		ACCESS	not-accessible
		STATUS	mandatory
		DESCRIPTION
			"Table entry for the previous 15 minutes statistics counters."
		INDEX   { dot1dBasePort,	extendPortTotalPrevious15MinIntervalNumber }
		::= { extendPortTotalPrevious15MinIntervalTable	 1 }

	 ExtendPortTotalPrevious15MinIntervalEntry ::=
		SEQUENCE {
				extendPortTotalPrevious15MinIntervalNumber
					INTEGER,
				extendPortTotalPrevious15MinTimeMeasured
					INTEGER,
				extendPortTotalPrevious15MinUpFwdFrameCounter
					OCTET STRING (SIZE (8)),
				extendPortTotalPrevious15MinUpFwdByteCounter
					OCTET STRING (SIZE (8)),
				extendPortTotalPrevious15MinDnFwdFrameCounter
					OCTET STRING (SIZE (8)),
				extendPortTotalPrevious15MinDnFwdByteCounter
					OCTET STRING (SIZE (8)),
				extendPortTotalPrevious15MinUpDiscFrameCounter
					OCTET STRING (SIZE (8)),
				extendPortTotalPrevious15MinUpDiscByteCounter
					OCTET STRING (SIZE (8)),
				extendPortTotalPrevious15MinDnDiscFrameCounter
					OCTET STRING (SIZE (8)),
				extendPortTotalPrevious15MinDnDiscByteCounter
					OCTET STRING (SIZE (8))
			}

	extendPortTotalPrevious15MinIntervalNumber OBJECT-TYPE
		SYNTAX	INTEGER
		ACCESS  	not-accessible
		STATUS	mandatory
		DESCRIPTION
			"Previous interval reference
             ALCATEL NOTE:
                 ACCESS:     NA       USAGE:      NA
                 PERSIST:    NO       INSRVMOD:   NO
                 RANGE:      NA       DEFVALUE:   NA
                 UNITS:      NA       SPARSE:     NA
                 DESCR:      NA"
		::= { extendPortTotalPrevious15MinIntervalEntry 1 }

	extendPortTotalPrevious15MinTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
		::= { extendPortTotalPrevious15MinIntervalEntry 2 }


	 extendPortTotalPrevious15MinUpFwdFrameCounter OBJECT-TYPE
		SYNTAX	OCTET STRING (SIZE (8))
--		the first octet contains the most significant byte
		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   NA
                 UNITS:      seconds  SPARSE:     NA
                 DESCR:      NA"
		::= { extendPortTotalPrevious15MinIntervalEntry 3 }


	extendPortTotalPrevious15MinUpFwdByteCounter OBJECT-TYPE
		SYNTAX	OCTET STRING (SIZE (8))
		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious15MinIntervalEntry 4 }

	extendPortTotalPrevious15MinDnFwdFrameCounter OBJECT-TYPE
		SYNTAX	OCTET STRING (SIZE (8))
		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious15MinIntervalEntry 5 }

	extendPortTotalPrevious15MinDnFwdByteCounter OBJECT-TYPE
		SYNTAX	OCTET STRING (SIZE (8))
		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious15MinIntervalEntry 6 }

	extendPortTotalPrevious15MinUpDiscFrameCounter OBJECT-TYPE
		SYNTAX	OCTET STRING (SIZE (8))
		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious15MinIntervalEntry 7 }

	extendPortTotalPrevious15MinUpDiscByteCounter OBJECT-TYPE
		SYNTAX	OCTET STRING (SIZE (8))
		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious15MinIntervalEntry 8 }

	extendPortTotalPrevious15MinDnDiscFrameCounter OBJECT-TYPE
		SYNTAX	OCTET STRING (SIZE (8))
		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious15MinIntervalEntry 9 }

	extendPortTotalPrevious15MinDnDiscByteCounter OBJECT-TYPE
		SYNTAX	OCTET STRING (SIZE (8))
		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious15MinIntervalEntry 10 }

--

	extendPortTotalPrevious1DayIntervalTable	 OBJECT-TYPE
		SYNTAX	SEQUENCE OF ExtendPortTotalPrevious1DayIntervalEntry
		ACCESS	not-accessible
		STATUS	mandatory
		DESCRIPTION
			"1 Day previous statistics for PortTotal (= all traffic on a port,
			Including PPPoE relayed and PPPoE terminated traffic)
             ALCATEL NOTE:
                 TABLESIZE:  DEP [depending on the value of 
                             dot1dBaseNumPorts.]
                 DESCR:      NA"
		::= { extendStatistics 10 }

	extendPortTotalPrevious1DayIntervalEntry OBJECT-TYPE
		SYNTAX	ExtendPortTotalPrevious1DayIntervalEntry
		ACCESS	not-accessible
		STATUS	mandatory
		DESCRIPTION
			"Table entry for the previous 1 day statistics counters."
		INDEX   { dot1dBasePort, extendPortTotalPrevious1DayIntervalNumber }
		::= { extendPortTotalPrevious1DayIntervalTable	 1 }

	 ExtendPortTotalPrevious1DayIntervalEntry ::=
		SEQUENCE {
				extendPortTotalPrevious1DayIntervalNumber
					INTEGER,
				extendPortTotalPrevious1DayTimeMeasured
					INTEGER,
				extendPortTotalPrevious1DayUpFwdFrameCounter
					OCTET STRING (SIZE (8)),
				extendPortTotalPrevious1DayUpFwdByteCounter
					OCTET STRING (SIZE (8)),
				extendPortTotalPrevious1DayDnFwdFrameCounter
					OCTET STRING (SIZE (8)),
				extendPortTotalPrevious1DayDnFwdByteCounter
					OCTET STRING (SIZE (8)),
				extendPortTotalPrevious1DayUpDiscFrameCounter
					OCTET STRING (SIZE (8)),
				extendPortTotalPrevious1DayUpDiscByteCounter
					OCTET STRING (SIZE (8)),
				extendPortTotalPrevious1DayDnDiscFrameCounter
					OCTET STRING (SIZE (8)),
				extendPortTotalPrevious1DayDnDiscByteCounter
					OCTET STRING (SIZE (8))
			}

	extendPortTotalPrevious1DayIntervalNumber OBJECT-TYPE
		SYNTAX	INTEGER
		ACCESS  	not-accessible
		STATUS	mandatory
		DESCRIPTION
			"Previous interval reference
             ALCATEL NOTE:
                 ACCESS:     NA       USAGE:      NA
                 PERSIST:    NO       INSRVMOD:   NO
                 RANGE:      NA       DEFVALUE:   NA
                 UNITS:      NA       SPARSE:     NA
                 DESCR:      NA"
		::= { extendPortTotalPrevious1DayIntervalEntry 1 }
	
	extendPortTotalPrevious1DayTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   0
                 UNITS:      seconds  SPARSE:     NA
                 DESCR:      NA"
		::= { extendPortTotalPrevious1DayIntervalEntry 2 }

	 extendPortTotalPrevious1DayUpFwdFrameCounter OBJECT-TYPE
		SYNTAX	OCTET STRING (SIZE (8))
--		the first octet contains the most significant byte
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious1DayIntervalEntry 3 }

	extendPortTotalPrevious1DayUpFwdByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   YES
                 RANGE:      NA       DEFVALUE:   NA
                 UNITS:      NA       SPARSE:     NA
                 DESCR:      NA"
		::= { extendPortTotalPrevious1DayIntervalEntry 4 }

	extendPortTotalPrevious1DayDnFwdFrameCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious1DayIntervalEntry 5 }

	extendPortTotalPrevious1DayDnFwdByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious1DayIntervalEntry 6 }

	extendPortTotalPrevious1DayUpDiscFrameCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"

		::= { extendPortTotalPrevious1DayIntervalEntry 7 }

	extendPortTotalPrevious1DayUpDiscByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious1DayIntervalEntry 8 }

	extendPortTotalPrevious1DayDnDiscFrameCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious1DayIntervalEntry 9 }

	extendPortTotalPrevious1DayDnDiscByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious1DayIntervalEntry 10 }

extendPortVlanTroubleShootingSummaryTable    OBJECT-TYPE
      SYNTAX   SEQUENCE OF ExtendPortVlanTroubleShootingSummaryEntry    
      ACCESS   not-accessible
      STATUS   mandatory
      DESCRIPTION
         "Troubleshooting vlanport summary counters table. An entry exists for each static vlanport on boards that support vlanport troubleshooting. 
             ALCATEL NOTE:
                 TABLESIZE:  DEP [depending on the size of 
                             extendPortVlanAssociationTable.]
                 DESCR:      NA"
      ::= { extendStatistics 13 }

   extendPortVlanTroubleShootingSummaryEntry OBJECT-TYPE
      SYNTAX   ExtendPortVlanTroubleShootingSummaryEntry
      ACCESS   not-accessible
      STATUS   mandatory
      DESCRIPTION
         "Table entry for the troubleshooting summary counters. 
The ifIndex equals the extendPortVlanIfIndex. All counters show the value since the last counter reset."
      INDEX   { ifIndex }
      ::= { extendPortVlanTroubleShootingSummaryTable    1 }

    ExtendPortVlanTroubleShootingSummaryEntry::=
      SEQUENCE {
            extendPortVlanUpFwdFrameCounter
               Counter,
            extendPortVlanUpDiscFrameCounter
               Counter,
            extendPortVlanDnFwdFrameCounter
               Counter,
            extendPortVlanDnDiscFrameCounter
               Counter,
	    extendPortVlanUpBcastFwdFrameCounter
               INTEGER,
            extendPortVlanUpUcastFwdFrameCounter
               INTEGER,
            extendPortVlanDnBcastFwdFrameCounter
               INTEGER,
            extendPortVlanDnUcastFwdFrameCounter
               INTEGER
                }

extendPortVlanUpFwdFrameCounter OBJECT-TYPE
      SYNTAX   Counter
      ACCESS     read-only
      STATUS   mandatory
      DESCRIPTION
         "The number of frames received from the user side that are successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 1 }

extendPortVlanUpDiscFrameCounter OBJECT-TYPE
      SYNTAX   Counter
      ACCESS     read-only
      STATUS   mandatory
      DESCRIPTION
         "The number of frames received from the user side that are discarded for any reason related to the vlanport checks, including policing.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 2 }

extendPortVlanDnFwdFrameCounter OBJECT-TYPE
      SYNTAX   Counter
      ACCESS     read-only
      STATUS   mandatory
      DESCRIPTION
         "The number of frames received from the network side that are successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 3 }

extendPortVlanDnDiscFrameCounter OBJECT-TYPE
      SYNTAX   Counter
      ACCESS     read-only
      STATUS   mandatory
      DESCRIPTION
         "The number of frames received from the network side that are discarded.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 4 }
extendPortVlanUpBcastFwdFrameCounter OBJECT-TYPE
      SYNTAX   INTEGER (-1..2147483647)
      ACCESS     read-only
      STATUS   mandatory
      DESCRIPTION
         "The number of broadcast frames received from the user side that are successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 5 }

 extendPortVlanUpUcastFwdFrameCounter OBJECT-TYPE
      SYNTAX   INTEGER (-1..2147483647)
      ACCESS   read-only
      STATUS   mandatory
      DESCRIPTION
         "The number of unicast frames received from the user side that are successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 6 }

extendPortVlanDnBcastFwdFrameCounter OBJECT-TYPE
      SYNTAX   INTEGER (-1..2147483647)
      ACCESS     read-only
      STATUS   mandatory
      DESCRIPTION
         "The number of broadcast frames received from the network side that are successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 7 }

extendPortVlanDnUcastFwdFrameCounter OBJECT-TYPE
      SYNTAX   INTEGER (-1..2147483647)
      ACCESS     read-only
      STATUS   mandatory
      DESCRIPTION
         "The number of unicast frames received from the network side that are successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 8 }

extendPortVlanTroubleShootingExtensiveTable    OBJECT-TYPE
      SYNTAX   SEQUENCE OF ExtendPortVlanTroubleShootingExtensiveEntry    
      ACCESS   not-accessible
      STATUS   mandatory
      DESCRIPTION
         "Troubleshooting vlanport extensive counters table.
An entry exists for each static vlanport on each line in the TroubleShootingObservationTable which table defined in troubleshooting MIB.
             ALCATEL NOTE:
                 TABLESIZE:  DEP [(the value of 
                             Max static vlanport per line) *(the max lim number of the system).]
                 DESCR:      NA"
      ::= { extendStatistics 14 }

   extendPortVlanTroubleShootingExtensiveEntry OBJECT-TYPE
      SYNTAX   ExtendPortVlanTroubleShootingExtensiveEntry
      ACCESS   not-accessible
      STATUS   mandatory
      DESCRIPTION
         "Table entry for the troubleshooting detail counters.
The ifIndex equals the extendPortVlanIfIndex. All counters show the value since the last counter reset."
      INDEX   { ifIndex }
      ::= { extendPortVlanTroubleShootingExtensiveTable    1 }

    ExtendPortVlanTroubleShootingExtensiveEntry::=
      SEQUENCE {
            extendPortVlanUpInvDaSaDiscFrameCounter
               Counter,
            extendPortVlanUpMacPortLimitExcDiscFrameCounter
               Counter,
            extendPortVlanUpMacFdbLimitExcDiscFrameCounter
               Counter,
            extendPortVlanUpInvProtDiscFrameCounter
               Counter,
            extendPortVlanUpIPSpoofingDiscFrameCounter
               Counter,
            extendPortVlanUpAclDiscFrameCounter
               Counter,
            extendPortVlanUpPolicerDiscFrameCounter
               Counter,
            extendPortVlanUpQueueDiscFrameCounter
               Counter,            
            extendPortVlanDnMultiFwdFrameCounter
               Counter,
            extendPortVlanDnNonMultiFwdFrameCounter
               Counter,
            extendPortVlanDnMultiDiscFrameCounter
               Counter,
            extendPortVlanDnNonMultiDiscFrameCounter
               Counter,
            extendPortVlanDnAclDiscFrameCounter
               Counter,
            extendPortVlanDnPolicerDiscFrameCounter
               Counter,
            extendPortVlanDnQueueDiscFrameCounter
               Counter,
            extendPortVlanUpIPv6SpoofingDiscFrameCounter
               Counter,
            extendPortVlanUpTpidDiscFrameCounter                       
               INTEGER         
                }

extendPortVlanUpInvDaSaDiscFrameCounter OBJECT-TYPE
      SYNTAX   Counter
      ACCESS     read-only
      STATUS   mandatory
      DESCRIPTION
         "The number of frames received from the user side which have an invalid destination or source MAC address. It applies to L2 and L3 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 1 }

extendPortVlanUpMacPortLimitExcDiscFrameCounter OBJECT-TYPE
      SYNTAX   Counter
      ACCESS     read-only
      STATUS   mandatory
      DESCRIPTION
         " The number of frames received from the user side that are discarded because the maximum number of MAC addresses per port is exceeded or because MAC learning is disabled on the port. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 2 }

extendPortVlanUpMacFdbLimitExcDiscFrameCounter OBJECT-TYPE
      SYNTAX   Counter
      ACCESS     read-only
      STATUS   mandatory
      DESCRIPTION
         "The number of frames received from the user side that are discarded because the max mac number of FDB is reached. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 3 }

extendPortVlanUpInvProtDiscFrameCounter OBJECT-TYPE
      SYNTAX   Counter
      ACCESS     read-only
      STATUS   mandatory
      DESCRIPTION
         "The number of frames received from the user side with an invalid protocol. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 4 }

extendPortVlanUpIPSpoofingDiscFrameCounter OBJECT-TYPE
      SYNTAX   Counter
      ACCESS     read-only
      STATUS   mandatory
      DESCRIPTION
         "The number of frames received from the user side with an IPv4 address not matching the assigned IP address. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 5 }

extendPortVlanUpAclDiscFrameCounter OBJECT-TYPE
      SYNTAX   Counter
      ACCESS     read-only
      STATUS   mandatory
      DESCRIPTION
         "The number of frames received from the user side that are discarded by an Acess Control List. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 6 }

extendPortVlanUpPolicerDiscFrameCounter OBJECT-TYPE
      SYNTAX   Counter
      ACCESS     read-only
      STATUS   mandatory
      DESCRIPTION
         " The number of frames received from the user side that are discarded due to policing. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 7 }

extendPortVlanUpQueueDiscFrameCounter OBJECT-TYPE
      SYNTAX   Counter
      ACCESS     read-only
      STATUS   mandatory
      DESCRIPTION
         " The number of frames received from the user side that are discarded due to the uplink queues overflow. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 8 }

extendPortVlanDnMultiFwdFrameCounter OBJECT-TYPE
      SYNTAX   Counter
      ACCESS     read-only
      STATUS   mandatory
      DESCRIPTION
         " The number of multicast frames received from the network side and successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 9 }

extendPortVlanDnNonMultiFwdFrameCounter OBJECT-TYPE
      SYNTAX   Counter
      ACCESS     read-only
      STATUS   mandatory
      DESCRIPTION
         " The number of unicast and broadcast frames received from the network side and successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 10 }

extendPortVlanDnMultiDiscFrameCounter OBJECT-TYPE
      SYNTAX   Counter
      ACCESS     read-only
      STATUS   mandatory
      DESCRIPTION
         "The discarded number of multicast frames received from the network side.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 11 }

extendPortVlanDnNonMultiDiscFrameCounter OBJECT-TYPE
      SYNTAX   Counter
      ACCESS     read-only
      STATUS   mandatory
      DESCRIPTION
         "The number of unicast and broadcast frames received from the network side.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 12 }

extendPortVlanDnAclDiscFrameCounter OBJECT-TYPE
      SYNTAX   Counter
      ACCESS     read-only
      STATUS   mandatory
      DESCRIPTION
         " The number of frames received from the network side that are discarded by an Access Control List. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 13 }

extendPortVlanDnPolicerDiscFrameCounter OBJECT-TYPE
      SYNTAX   Counter
      ACCESS     read-only
      STATUS   mandatory
      DESCRIPTION
         " The number of frames received from the network side that is discarded due to policing. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 14 }

extendPortVlanDnQueueDiscFrameCounter OBJECT-TYPE
      SYNTAX   Counter
      ACCESS     read-only
      STATUS   mandatory
      DESCRIPTION
         "The number of frames received from the network side, forwarded to the Vlan Port and then discarded because of queue overflow. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 15 }

extendPortVlanUpIPv6SpoofingDiscFrameCounter OBJECT-TYPE
      SYNTAX   Counter
      ACCESS   read-only
      STATUS   mandatory
      DESCRIPTION
         "The number of frames received from the user side with an IPv6 address not matching the assigned IP address. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 16 }
extendPortVlanUpTpidDiscFrameCounter  OBJECT-TYPE
      SYNTAX   INTEGER
      ACCESS   read-only
      STATUS   mandatory
      DESCRIPTION
         "The number of frames received from the user side with TPID not matching the assigned TPID. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 17 }

    extendPortVlanDot1pTrafficCounterTable    OBJECT-TYPE
      SYNTAX   SEQUENCE OF ExtendPortVlanDot1pTrafficCounterEntry    
      ACCESS   not-accessible
      STATUS   mandatory
      DESCRIPTION
         "Vlanport p-bit traffic counters table.
An entry exists for each traffic flow identified by a p-bit value or range on one vlanport.
             
                 TABLESIZE:  DEP [(the value of 
                             Max p-bit traffic counter pair per line) * (the max line number of FD L3 lim) * (the max lim number of the system).]
                 DESCR:      NA"
      ::= { extendStatistics 15 }

   extendPortVlanDot1pTrafficCounterEntry OBJECT-TYPE
      SYNTAX   ExtendPortVlanDot1pTrafficCounterEntry
      ACCESS   not-accessible
      STATUS   mandatory
      DESCRIPTION
         "Table entry for the p-bit traffic counters.
The ifIndex equals the extendPortVlanIfIndex. All counters show the value since the last system reset."
      INDEX   { ifIndex,extendPortVlanDot1pMinValue, extendPortVlanDot1pMaxValue  }
      ::= { extendPortVlanDot1pTrafficCounterTable    1 }

    ExtendPortVlanDot1pTrafficCounterEntry::=
      SEQUENCE {
            extendPortVlanDot1pMinValue
INTEGER,
            extendPortVlanDot1pMaxValue
INTEGER,
            extendPortVlanDot1pTrafficUpFwdByteCounter
               OCTET STRING (SIZE (8)),
            extendPortVlanDot1pTrafficDnFwdByteCounter
               OCTET STRING (SIZE (8)),
            extendPortVlanDot1pTrafficCounterRowStatus
               RowStatus
                }

   extendPortVlanDot1pMinValue OBJECT-TYPE
      SYNTAX   INTEGER(0..7)
      ACCESS     not-accessible
      STATUS   mandatory
      DESCRIPTION
         "The minimum value in specified p-bit range.
             ALCATEL NOTE:
                 ACCESS:     NA       USAGE:      NA
                 PERSIST:    YES       INSRVMOD:   NO
                 RANGE:      0..7     DEFVALUE:   NA
                 UNITS:      NA  SPARSE:     NA
                 DESCR:      NA"
      ::= { extendPortVlanDot1pTrafficCounterEntry 1 }

extendPortVlanDot1pMaxValue OBJECT-TYPE
      SYNTAX   INTEGER(0..7)
      ACCESS     not-accessible
      STATUS   mandatory
      DESCRIPTION
         "The maximum value in specified p-bit range.
             ALCATEL NOTE:
                 ACCESS:     NA       USAGE:      NA
                 PERSIST:    YES       INSRVMOD:   NO
                 RANGE:      0..7     DEFVALUE:   NA
                 UNITS:      NA  SPARSE:     NA
                 DESCR:      NA"
      ::= { extendPortVlanDot1pTrafficCounterEntry 2 }

extendPortVlanDot1pTrafficUpFwdByteCounter OBJECT-TYPE
      SYNTAX   OCTET STRING (SIZE (8))
      ACCESS     read-only
      STATUS   mandatory
      DESCRIPTION
         "All forwarded  bytes in upstream direction per VLAN on a bridge 
         port with traffic flow indentification in specified p-bit range.
             ALCATEL NOTE:
                 ACCESS:     NA       USAGE:      NA
                 PERSIST:    NO      INSRVMOD:   NO
                 RANGE:      NA       DEFVALUE:   NA
                 UNITS:      bytes    SPARSE:     NA
                 DESCR:      NA"
      ::= { extendPortVlanDot1pTrafficCounterEntry 3 }

extendPortVlanDot1pTrafficDnFwdByteCounter OBJECT-TYPE
      SYNTAX   OCTET STRING  (SIZE (8))
      ACCESS     read-only
      STATUS   mandatory
      DESCRIPTION
         "All forwarded  bytes in downstream direction per VLAN on a bridge 
         port with traffic flow indentification in specified p-bit range.
             ALCATEL NOTE:
                 ACCESS:     NA       USAGE:      NA
                 PERSIST:    NO       INSRVMOD:   NO
                 RANGE:      NA       DEFVALUE:   NA
                 UNITS:      bytes    SPARSE:     NA
                 DESCR:      NA"
      ::= { extendPortVlanDot1pTrafficCounterEntry 4 }

extendPortVlanDot1pTrafficCounterRowStatus OBJECT-TYPE
    SYNTAX      RowStatus
    ACCESS  	   read-write
    STATUS      mandatory
    DESCRIPTION
        "This object indicates the status of this entry.
        ALCATEL NOTE:
            ACCESS:     RO       USAGE:      NA
            PERSIST:    YES      INSRVMOD:   NO
            RANGE:      1,4,6        DEFVALUE:  NA 
            UNITS:      NA       SPARSE:     NA
            DESCR:      NA " 
    ::= { extendPortVlanDot1pTrafficCounterEntry 5 }
    
extendUniTroubleShootingSummaryTable    OBJECT-TYPE
      SYNTAX   SEQUENCE OF ExtendUniTroubleShootingSummaryEntry    
      ACCESS   not-accessible
      STATUS   mandatory
      DESCRIPTION
         "Troubleshooting uni summary counters table. An entry exists to support line level troubleshooting. 
             ALCATEL NOTE:
                 TABLESIZE:  DEP [ the max uni number of the system ]
                 DESCR:      NA"
      ::= { extendStatistics 16 }

   extendUniTroubleShootingSummaryEntry OBJECT-TYPE
      SYNTAX   ExtendUniTroubleShootingSummaryEntry
      ACCESS   not-accessible
      STATUS   mandatory
      DESCRIPTION
         "Table entry for the line level troubleshooting summary counters. 
The ifIndex is from InterfaceIndex,used to index uni interface. All counters show the value since the last counter reset."
      INDEX   { ifIndex }
      ::= { extendUniTroubleShootingSummaryTable    1 }

    ExtendUniTroubleShootingSummaryEntry::=
      SEQUENCE {
            extendUniUpIpv4SpoofingDiscFrameCounter
               Counter
                }

extendUniUpIpv4SpoofingDiscFrameCounter OBJECT-TYPE
      SYNTAX   Counter
      ACCESS   read-only
      STATUS   mandatory
      DESCRIPTION
         "The number of frames received from the uni that are discard for ipv4-antispoofing.
             ALCATEL NOTE:
                 ACCESS:     NA       USAGE:      NA
                 PERSIST:    NO       INSRVMOD:   NO
                 RANGE:      NA       DEFVALUE:   NA
                 UNITS:      frames   SPARSE:     NA
                 DESCR:      NA"
      ::= { extendUniTroubleShootingSummaryEntry 1 }

extendPortTotalAccumulativeTable OBJECT-TYPE
      SYNTAX   SEQUENCE OF ExtendPortTotalAccumulativeEntry
      ACCESS   not-accessible
      STATUS   mandatory
      DESCRIPTION
        "This table counts all data traffic (not including packets handled in protocol plane) over bridge ports since LT starts up. Each entry records counters for one bridge port.
             ALCATEL NOTE:
                 TABLESIZE:  DEP [depending on the value of dot1dBaseNumPorts.]
                 DESCR:      NA"
      ::= { extendStatistics 17 }

extendPortTotalAccumulativeEntry OBJECT-TYPE
      SYNTAX   ExtendPortTotalAccumulativeEntry
      ACCESS   not-accessible
      STATUS   mandatory
      DESCRIPTION
         "Table entry for the statistics counters of one birdge port."
      INDEX   { ifIndex }
      ::= { extendPortTotalAccumulativeTable 1 }
      
ExtendPortTotalAccumulativeEntry::=
   SEQUENCE {
            extendPortTotalUpFwdFrameCounter 
               OCTET STRING (SIZE (8)),
            extendPortTotalUpFwdByteCounter
               OCTET STRING (SIZE (8)),
            extendPortTotalDnFwdFrameCounter
               OCTET STRING (SIZE (8)),
            extendPortTotalDnFwdByteCounter
               OCTET STRING (SIZE (8)),
            extendPortTotalUpDiscFrameCounter
               OCTET STRING (SIZE (8)),
            extendPortTotalUpDiscByteCounter
               OCTET STRING (SIZE (8)),
            extendPortTotalDnDiscFrameCounter
               OCTET STRING (SIZE (8)),
            extendPortTotalDnDiscByteCounter
               OCTET STRING (SIZE (8))
            }


extendPortTotalUpFwdFrameCounter OBJECT-TYPE
      SYNTAX   OCTET STRING (SIZE (8))
--      the first octet contains the most significant byte
      ACCESS     read-only
      STATUS   mandatory
      DESCRIPTION
         "Total forwarded data frames per bridge port in upstream direction since LT starts up.
             ALCATEL NOTE:
                 ACCESS:     NA       USAGE:      NA
                 PERSIST:    NO       INSRVMOD:   NO
                 RANGE:      NA       DEFVALUE:   0
                 UNITS:      NA       SPARSE:     NA
                 DESCR:      NA"
      ::= { extendPortTotalAccumulativeEntry 1 }

extendPortTotalUpFwdByteCounter OBJECT-TYPE
      SYNTAX   OCTET STRING (SIZE (8))
      ACCESS     read-only
      STATUS   mandatory
      DESCRIPTION
         "Total forwarded data bytes per bridge port in upstream direction since LT starts up.
             ALCATEL NOTE:
                 ACCESS:     NA       USAGE:      NA
                 PERSIST:    NO       INSRVMOD:   NO
                 RANGE:      NA       DEFVALUE:   0
                 UNITS:      NA       SPARSE:     NA
                 DESCR:      NA"
      ::= { extendPortTotalAccumulativeEntry 2 }

extendPortTotalDnFwdFrameCounter OBJECT-TYPE
      SYNTAX   OCTET STRING (SIZE (8))
      ACCESS     read-only
      STATUS   mandatory
      DESCRIPTION
         "Total forwarded data frames per brdige port in downstream direction since LT starts up.
             ALCATEL NOTE:
                 ACCESS:     NA       USAGE:      NA
                 PERSIST:    NO       INSRVMOD:   NO
                 RANGE:      NA       DEFVALUE:   0
                 UNITS:      NA       SPARSE:     NA
                 DESCR:      NA"
      ::= { extendPortTotalAccumulativeEntry 3 }

extendPortTotalDnFwdByteCounter OBJECT-TYPE
      SYNTAX   OCTET STRING (SIZE (8))
      ACCESS     read-only
      STATUS   mandatory
      DESCRIPTION
         "Total forwarded data bytes per bridge port in downstream direction since LT starts up.
             ALCATEL NOTE:
                 ACCESS:     NA       USAGE:      NA
                 PERSIST:    NO       INSRVMOD:   NO
                 RANGE:      NA       DEFVALUE:   0
                 UNITS:      NA       SPARSE:     NA
                 DESCR:      NA"
      ::= { extendPortTotalAccumulativeEntry 4 }

extendPortTotalUpDiscFrameCounter OBJECT-TYPE
      SYNTAX   OCTET STRING (SIZE (8))
      ACCESS     read-only
      STATUS   mandatory
      DESCRIPTION
         "Total discarded data frames per bridge port in upstream direction since LT starts up. 
             ALCATEL NOTE:
                 ACCESS:     NA       USAGE:      NA
                 PERSIST:    NO       INSRVMOD:   NO
                 RANGE:      NA       DEFVALUE:   0
                 UNITS:      NA       SPARSE:     NA
                 DESCR:      NA"
      ::= { extendPortTotalAccumulativeEntry 5 }

extendPortTotalUpDiscByteCounter OBJECT-TYPE
      SYNTAX   OCTET STRING (SIZE (8))
      ACCESS     read-only
      STATUS   mandatory
      DESCRIPTION
         "Total discarded data bytes per bridge port in upstream direction since LT starts up.
             ALCATEL NOTE:
                 ACCESS:     NA       USAGE:      NA
                 PERSIST:    NO       INSRVMOD:   NO
                 RANGE:      NA       DEFVALUE:   0
                 UNITS:      NA       SPARSE:     NA
                 DESCR:      NA"
      ::= { extendPortTotalAccumulativeEntry 6 }

extendPortTotalDnDiscFrameCounter OBJECT-TYPE
      SYNTAX   OCTET STRING (SIZE (8))
      ACCESS     read-only
      STATUS   mandatory
      DESCRIPTION
         "Total discarded data frames per bridge port in downstream direction since LT starts up.
             ALCATEL NOTE:
                 ACCESS:     NA       USAGE:      NA
                 PERSIST:    NO       INSRVMOD:   NO
                 RANGE:      NA       DEFVALUE:   0
                 UNITS:      NA       SPARSE:     NA
                 DESCR:      NA"
      ::= { extendPortTotalAccumulativeEntry 7 }

extendPortTotalDnDiscByteCounter OBJECT-TYPE
      SYNTAX   OCTET STRING (SIZE (8))
      ACCESS     read-only
      STATUS   mandatory
      DESCRIPTION
         "Total discarded data bytes per bridge port in downstream direction since LT starts up.
             ALCATEL NOTE:
                 ACCESS:     NA       USAGE:      NA
                 PERSIST:    NO       INSRVMOD:   NO
                 RANGE:      NA       DEFVALUE:   0
                 UNITS:      NA       SPARSE:     NA
                 DESCR:      NA"
      ::= { extendPortTotalAccumulativeEntry 8 }

-- =================================================================================================================
--
-- The table contains OLT-side rolling frame counters per PBit value AND per VLAN.
--
-- Rows in this table are created/deleted as a result of the creation/deletion of associated
-- rows in troubleShootingPbitObservationTable in the TROUBLESHOOTING-MIB.
-- As of ISAM5.0.01, the ifIndex value in this table only represents a VLAN (which is associated to the
-- bridge port ifindex from the above mentioned row in troubleShootingPbitObservationTable).
-- 
-- This table also contains an index for individulal PBit value (i.e. extendPortVlanPbitTroubleshootPriority),
-- so that manager can retrieve counters per PBit valuesper per VLAN port.
--
-- This table is SUPPORTED as of ISAM5.0.01
--
-- =================================================================================================================

   extendPortVlanPbitTroubleshootTable    OBJECT-TYPE
      SYNTAX   SEQUENCE OF ExtendPortVlanPbitTroubleshootEntry
      ACCESS   not-accessible
      STATUS   mandatory
      DESCRIPTION
         " OLT-side PBit troubleshoot counters for a vlan port.
             ALCATEL NOTE:
                 TABLESIZE:  DEP [8 per LT card]
                 DESCR:      NA"
      ::= { extendStatistics 18  }

   extendPortVlanPbitTroubleshootEntry OBJECT-TYPE
      SYNTAX   ExtendPortVlanPbitTroubleshootEntry
      ACCESS   not-accessible
      STATUS   mandatory
      DESCRIPTION
         "Table entry for OLT-side PBit troubleshoot counters for vlan port."
      INDEX   { ifIndex, extendPortVlanPbitTroubleshootPriority  }
      ::= { extendPortVlanPbitTroubleshootTable    1 }

    ExtendPortVlanPbitTroubleshootEntry ::=
      SEQUENCE {

            extendPortVlanPbitTroubleshootPriority
               ExtendVlanSystemPriority, 
            extendPortVlanPbitTroubleshootUpFwdFrameCounter
               OCTET STRING,
            extendPortVlanPbitTroubleshootDownFwdFrameCounter
               OCTET STRING,
            extendPortVlanPbitTroubleshootUpDropFrameCounter
               OCTET STRING,
            extendPortVlanPbitTroubleshootDownDropFrameCounter
               OCTET STRING }

    extendPortVlanPbitTroubleshootPriority OBJECT-TYPE
      SYNTAX   ExtendVlanSystemPriority
      ACCESS     read-only
      STATUS   mandatory
      DESCRIPTION
         " This index represents the PBit value associated with the counter
             ALCATEL NOTE:
                 ACCESS:     NA       USAGE:      NA
                 PERSIST:    NO       INSRVMOD:   NO
                 RANGE:      0..7       DEFVALUE:  NA
                 UNITS:      NA       SPARSE:     NA
                 DESCR:      NA "
      ::= { extendPortVlanPbitTroubleshootEntry 1 }
   
   extendPortVlanPbitTroubleshootUpFwdFrameCounter OBJECT-TYPE
      SYNTAX   OCTET STRING (SIZE (8))
      ACCESS     read-only
      STATUS   mandatory
      DESCRIPTION
         " 64-bit counter equivalent for number of upstream forwarded frames.
             ALCATEL NOTE:
                 ACCESS:     NA       USAGE:      NA
                 PERSIST:    NO       INSRVMOD:   NO
                 RANGE:      NA     DEFVALUE:   0
                 UNITS:      NA       SPARSE:     NA
                 DESCR:      NA"
      ::= { extendPortVlanPbitTroubleshootEntry 2 }


   extendPortVlanPbitTroubleshootDownFwdFrameCounter OBJECT-TYPE
      SYNTAX   OCTET STRING (SIZE (8))
      ACCESS     read-only
      STATUS   mandatory
      DESCRIPTION
         " 64-bit counter equivalentfor number of downstream forwarded frames.
             ALCATEL NOTE:
                 ACCESS:     NA       USAGE:      NA
                 PERSIST:    NO       INSRVMOD:   NO
                 RANGE:      NA     DEFVALUE:   0
                 UNITS:      NA       SPARSE:     NA
                 DESCR:      NA"
      ::= { extendPortVlanPbitTroubleshootEntry 3 }


  extendPortVlanPbitTroubleshootUpDropFrameCounter OBJECT-TYPE
      SYNTAX   OCTET STRING (SIZE (8))
      ACCESS     read-only
      STATUS   mandatory
      DESCRIPTION
         " 64-bit counter equivalent for number of upstream dropped frames.
             ALCATEL NOTE:
                 ACCESS:     NA       USAGE:      NA
                 PERSIST:    NO       INSRVMOD:   NO
                 RANGE:      NA     DEFVALUE:   0
                 UNITS:      NA       SPARSE:     NA
                 DESCR:      NA"
      ::= { extendPortVlanPbitTroubleshootEntry 4 }


   extendPortVlanPbitTroubleshootDownDropFrameCounter OBJECT-TYPE
      SYNTAX   OCTET STRING (SIZE (8))
      ACCESS     read-only
      STATUS   mandatory
      DESCRIPTION
         " 64-bit counter equivalent for number of downstream dropped frames.
             ALCATEL NOTE:
                 ACCESS:     NA       USAGE:      NA
                 PERSIST:    NO       INSRVMOD:   NO
                 RANGE:      NA     DEFVALUE:   0
                 UNITS:      NA       SPARSE:     NA
                 DESCR:      NA"
      ::= { extendPortVlanPbitTroubleshootEntry 5 }


-- ========================================================
--     vMAC Address Format. The 48 bit MAC address is defined 
--     in accordance with the VLAN MIB of type MacAddress.
-- ========================================================

systemVMacAddressFormat        OBJECT IDENTIFIER ::= { plimEthernet 11 }

--   extendVMacSizeofvMacId OBJECT-TYPE
--   ::= { systemVMacAddressFormat 1 }

--   extendVMacSizeofPortId OBJECT-TYPE
--   ::= { systemVMacAddressFormat 2 }

--   extendVMacSizeofSlotId OBJECT-TYPE
--   ::= { systemVMacAddressFormat 3 }

--   extendVMacSizeofRackId OBJECT-TYPE
--   ::= { systemVMacAddressFormat 4 }

--   extendVMacSizeofDSLAMId OBJECT-TYPE
--   ::= { systemVMacAddressFormat 5 }

extendVMacValueofDSLAMId OBJECT-TYPE
SYNTAX  INTEGER
ACCESS  read-write
STATUS  mandatory
DESCRIPTION
      "The object specifies the value of the DSLAM Id. This value 
      must be unique DSLAM Id within an EMAN connected to the same IP edges. 
      When the value is 0, it implies that the object has not been 
      set yet and vMAC could not be enabled on any VLAN. The value
      0 cannot be configured; it is a factory default value only.
      For CFM, this field must be configured to ensure the uniqueness 
      of the MP MAC address across the network with multiple DSLAMs.
ALCATEL NOTE:
ACCESS:     RW       USAGE:      OPT
PERSIST:    YES      INSRVMOD:   YES
            RANGE:   0..524287   DEFVALUE:   0
UNITS:      NA       SPARSE:     NA
DESCR:      NA"
             DEFVAL { 0 }
::= { systemVMacAddressFormat 6 }

--   extendVMacSizeofvMacSignature OBJECT-TYPE
--   ::= { systemVMacAddressFormat 7 }

--   extendVMacValueofvMacSignature OBJECT-TYPE
--   ::= { systemVMacAddressFormat 8 }


-- ========================================================
--     extend VLAN TPID table.
-- ========================================================
extendVlanTpidTable OBJECT-TYPE
		SYNTAX	SEQUENCE OF ExtendVlanTpidEntry
		ACCESS	not-accessible
		STATUS	mandatory
		DESCRIPTION
			"A table that contains system TPID value"
		::= { vlanStack 16 }

extendVlanTpidEntry OBJECT-TYPE
		SYNTAX	ExtendVlanTpidEntry
		ACCESS	not-accessible
		STATUS	mandatory
		DESCRIPTION
			"An entry of systemTpidTable."
		INDEX	{ extendVlanTpidIndex }
		::= { extendVlanTpidTable 1 }

ExtendVlanTpidEntry ::=
      SEQUENCE {
         extendVlanTpidIndex
            INTEGER,
         extendVlanTpidValue
            INTEGER,
         extendVlanTpidRowStatus
            RowStatus
      }
      
extendVlanTpidIndex OBJECT-TYPE
		SYNTAX	INTEGER(1..4)
		ACCESS	not-accessible
		STATUS	mandatory
		DESCRIPTION
			"The system TPID index."
		::= { extendVlanTpidEntry 1 }
		
extendVlanTpidValue OBJECT-TYPE
		SYNTAX	INTEGER
		ACCESS	read-write
		STATUS	mandatory
		DESCRIPTION
			"The system TPID value, must be Hex.
             ALCATEL NOTE:
                 ACCESS:     NA       USAGE:      NA
                 PERSIST:    NO       INSRVMOD:   NA
                 RANGE:      1536..65535       DEFVALUE:   NA
                 UNITS:      NA       SPARSE:     NA
                 DESCR:      system TPID value"
		::= { extendVlanTpidEntry 2 }

extendVlanTpidRowStatus OBJECT-TYPE
		SYNTAX	RowStatus
		ACCESS	read-write
		STATUS	mandatory
		DESCRIPTION
			"The row status of the entry.
             ALCATEL NOTE:
                 ACCESS:     NA       USAGE:      NA
                 PERSIST:    NO       INSRVMOD:   YES
                 RANGE: active(1),createAndGo(4), destroy(6)  DEFVALUE:   active(1)
                 UNITS:      NA       SPARSE:     NA
                 DESCR:      NA"
        DEFVAL	{ active }
		::= { extendVlanTpidEntry 3 }

END
