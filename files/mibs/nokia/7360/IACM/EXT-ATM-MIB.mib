--  ATM Extension MIB
-- ===========================================================================
--  This specification is published by Alcatel under Non-Disclosure
--  Agreement(s) (NDA) with specific parties and has to be considered as
--  Confidential Information as defined in such NDA.
--  Alcatel reserves the right to revise this document for any reason,
--  including but not limited to conformity with standards promulgated by
--  various agencies, utilisation of advances in the state of the technical
--  areas, or the reflection of changes in the design of any equipment,
--  techniques, or procedures described or referred to herein.
--  The product specifications and other technical or performance information
--  contained herein are subject to change without notice.
--  Updates of this document will be issued under the above NDA's.
--  Alcatel makes no representation or warranty, expressed or implied, with
--  respect to the sufficiency, accuracy, or utility of any information or
--  opinion contained herein. Alcatel expressly advises that any use of for 
--  any purpose or reliance upon this technical reference is at the risk of
--  the user and that Alcatel shall not be liable for any damage or injury
--  incurred by any person arising out of the sufficiency, accuracy, or
--  utility of any information or opinion contained herein.
--  This document is not to be construed as a suggestion to any manufacturer
--  to modify or change any of its products, nor does this document represent
--  any commitment by Alcatel to sell or purchase any product.
--  Nothing contained herein shall be construed as conferring by implication,
--  estoppel, or otherwise any license or right under any patent, whether or
--  not the use of any information herein necessarily employs an invention of
--  any existing or later issued patent.
--  Alcatel reserves the right not to offer any or all of these products and
--  to withdraw any or all of them at any future time.
--  Copyright (C) 2003-2007, Alcatel. All Rights Reserved.
-- ===========================================================================



--  MODULE-IDENTITY
--  LAST-UPDATED "20070501000000Z"
--  ORGANIZATION "Alcatel"
--  CONTACT-INFO
--
--          "Email:  asam.mibsupport@alcatel.be"
--
--  DESCRIPTION  
--    This MIB Module defines extended configuration, fault, and
--    performance management objects for ATM Services in ISAM.
--    It works in conjunction with the following MIBs:
--       [1] ATM-MIB  : IETF RFC-2515 MIB adapted by Alcatel
--
--  REVISION "20110717000000Z"
--  DESCRIPTION
--        "Version: 3EC15357EAAA_E4.2.0.0.1
--         Editor:  Sun Baoping
--         Changes: asamAtmVclStatTable is added for ALU01300397.
--
--  REVISION "20101101000000Z"
--  DESCRIPTION
--        "Version: 3EC15357EAAA_E4.2.0.0.0
--         Editor:  Sun Baoping
--         Changes: encapsulation type 'none' added for asamAtmVclEncapsType for ALU00123662
--
--
--  REVISION "20090401000000Z"
--  DESCRIPTION
--        "Version: 3EC15357EAAA_E4.0.0.1.1
--         Editor:  Dongxing A ZHOU
--         Changes: ALCATEL NOTE added for asamAtmVclEncapsType
--
--  REVISION "20070501000000Z"
--  DESCRIPTION
--        "Version: 3EC15357EAAA_E3.4.0.0.1
--         Editor: Larry Boone
--         Changes:  rename the autoDetectIpPpp code point to
--                   autoDetectIpoePpp (BDFhw46950)"
--
--  REVISION "20070326000000Z"
--  DESCRIPTION
--        "Version: 3EC15357EAAA_E3.4.0.0.0
--         Editor:  Larry Boone
--         Changes:  add the autoDetectIpPpp code point to the
--                   asamAtmVclEncapsAutodetect enum (BDFhw46950)"
--  
--  REVISION "20060605000000Z"
--  DESCRIPTION
--        "Version: 3EC15357EAAA_E3.2.0.0.0
--         Editor: Rommy VOLDERS
--         Changes:  Open SNMP feature ISAM R3.2"
--
--  REVISION "20060123000000Z"
--  DESCRIPTION
--        "Version: 3EC15357EAAA_E2.0.0.2.1
--         Editor: Bart Bogaert
--         Changes:  Implemented BDFhw70643: strict syntax checks (smilint)"
--
--  REVISION "20030325000000Z"
--  DESCRIPTION
--        "Version: 3EC15357EAAA_E1.0.0.1.1
--         Editor: Peter Van Mele
--         Changes:  Introduction of VCL interface index: Mapping tables"
--
--  REVISION "20030228000000Z"
--  DESCRIPTION
--        "Version: 3EC15357EAAA_E1.0.0.1.0
--         Editor: Peter Van Mele
--         Changes:  introduction of f5 loopback test"
--
--  REVISION "20021222000000Z"
--  DESCRIPTION
--        "Version: 3EC15357EAAA_E1.0.0.0.0
--         Editor: Yingzhong Miao 
--         Changes:  based on 3EC15357AAAA for ISAM R1.0"
-- ============================================================================

EXT-ATM-MIB DEFINITIONS ::= BEGIN


IMPORTS

    OBJECT-TYPE
        FROM RFC-1212
    Counter
        FROM RFC1155-SMI
    asam
        FROM SYSTEM-MIB
--    atmTrafficDescrParamIndex 
--        FROM ATM-MIB
-- ,atmVplVpi, 
atmVclVpi, atmVclVci
        FROM ATM-MIB
RowStatus
-- , TruthValue
        FROM SNMPv2-TC
     ifIndex,
     InterfaceIndex
        FROM ITF-MIB
  AtmVpIdentifier, AtmVcIdentifier
       FROM ATM-TC-MIB
    -- AsamNextProfileIndex, AsamMaxProfileIndex, AsamProfileIndex,
    -- AsamProfilePointer, AsamProfileName, AsamProfileScope, AsamProfileRefCount
    --     FROM ASAM-TC-MIB
;
  
-- ===========================================================================

-- Textual Conventions
-- ===================

-- Loopback direction type
-- =======================
-- Indicates the loopback direction.
-- o networkSide : loopback is on network side
-- This means traffic received from the internal switch by the ATM interface is
-- looped to the internal switch, traffic received from the line is discarded
-- o userSide    : loopback is on user side
-- This means traffic received from the line by the ATM interface is
-- looped to the line, traffic received from the internal switch is discarded
-- AsamAtmLoopbackDirectionType ::= INTEGER {
--                      networkSide         (1),
--                      userSide            (2)}

-- F4/F5 loopback direction
-- ========================
--  The requested direction, in which F4F5 loopback cells has to be generated.
--  The notion used here is relative to underlaying ATM interface.
--  This means for ATM interface on LT 'incoming' means towards network side
--  and 'outgoing' means towards user side. For ATM interface on NT 'incoming'
--  means towards user side and 'outgoing' means towards network side. 
--  It is valid only for segment loopbacking, in which case it takes either
--  'incoming' or 'outgoing'. In case of E2E loopbacking, its 'outgoing'.
  AsamAtmF4F5LoopbackDirection ::= INTEGER {
             incoming(1), 
             outgoing(2)
              }
                                                
-- Loopback span
-- =============
   AsamAtmLoopbackSpan ::= INTEGER {
              e2e(1),   -- for end to end loopbacking
              seg(2)    -- for segment loopbacking
            }

-- Loopback Location Identifier (LLID)
-- ===================================
--  The 16 byte LLID to identify the loopback location. Its valid only 
--  for segment loopbacking, in which case it identifies the loopback 
--  location code of the point, where the cell has to be loopbacked.
--  For end to end loopback, set LLID to all 1's.
   AsamAtmLoopbackLLID ::= OCTET STRING (SIZE(16))


asamExtAtmMIB OBJECT IDENTIFIER ::= { asam 4 }

asamExtAtmMIBObjects OBJECT IDENTIFIER ::= { asamExtAtmMIB 1 }

--
-- The following object may be used in conjunction with
-- the asamAtmCacProfileTable for the creation of
-- new table entries.
--

-- asamAtmCacProfileIndexNext OBJECT-TYPE
--     ::= { asamExtAtmMIBObjects 29 }

-- asamAtmCacProfileMaxIndex OBJECT-TYPE
--     ::= { asamExtAtmMIBObjects 30 }

-- asamAtmCacProfileTable OBJECT-TYPE
--     ::= { asamExtAtmMIBObjects 31 }

-- asamAtmAccessProfileIndexNext OBJECT-TYPE
--     ::= { asamExtAtmMIBObjects 32 }
-- 
-- asamAtmAccessProfileMaxIndex OBJECT-TYPE
--     ::= { asamExtAtmMIBObjects 33 }

-- asamAtmAccessProfileTable OBJECT-TYPE
--     ::= { asamExtAtmMIBObjects 34 }
--
-- asamAtmCdvtProfileIndexNext OBJECT-TYPE
--     ::= { asamExtAtmMIBObjects 35 }
-- 
-- asamAtmCdvtProfileMaxIndex OBJECT-TYPE
--     ::= { asamExtAtmMIBObjects 36 }

-- asamAtmCdvtProfileTable OBJECT-TYPE
--     ::= { asamExtAtmMIBObjects 37 }
--

-- ==================================================================

-- Extensions to the ATM interface configuration Table
-- ===================================================

asamAtmInterfaceConfigTable OBJECT-TYPE
    SYNTAX  SEQUENCE OF AsamAtmInterfaceConfigEntry
    ACCESS  not-accessible
    STATUS  mandatory
    DESCRIPTION
           "This table contains ATM interface configuration parameters,
            one entry per ATM interface. This table is an extended part
            of 'atmInterfaceConfTable' in the ATM_MIB."
    ::= { asamExtAtmMIBObjects 38 }

asamAtmInterfaceConfigEntry OBJECT-TYPE
    SYNTAX  AsamAtmInterfaceConfigEntry
    ACCESS  not-accessible
    STATUS  mandatory
    DESCRIPTION
           "This list contains ATM interface configuration information,
            Each ATM interface automatically has an entry in this table
            associated with it."
    INDEX   { ifIndex }
    ::= { asamAtmInterfaceConfigTable 1 }

AsamAtmInterfaceConfigEntry ::=
    SEQUENCE {
        asamAtmInterfaceType
            INTEGER,
 
--        asamAtmCacProfileIndexIncoming
--            AsamProfilePointer,
--             
--         asamAtmCacProfileIndexOutgoing
--             AsamProfilePointer,
-- 
--         asamAtmAccessProfileIndex
--             AsamProfilePointer,
-- 
--         asamAtmCdvtProfileIndex
--             AsamProfilePointer,
-- 
--         asamAtmNgcrAdminWeight
--             INTEGER,
-- 
-- 	       asamAtmSignVpi
--             AtmVpIdentifier,
-- 
-- 	       asamAtmSignVci
--             AtmVcIdentifier,
-- 
--         asamAtmGlobalLoopbackConfigured
--             TruthValue,
-- 
--         asamAtmGlobalLoopbackDirection
--             AsamAtmLoopbackDirectionType,
--             
--         asamAtmIlmiVpi
--             AtmVpIdentifier,
-- 
-- 	       asamAtmIlmiVci
--             AtmVcIdentifier,
--          asamAtmInterfaceCrossConnectedPVpcs
--	     INTEGER,
--
--         asamAtmInterfaceCrossConnectedPVccs
--             INTEGER,
--
--         asamAtmInterfaceNonCrossConnectedPVpcs
--             INTEGER,

           asamAtmInterfaceNonCrossConnectedPVccs
               INTEGER

         }

asamAtmInterfaceType OBJECT-TYPE
    SYNTAX  INTEGER {
              ns (1),  -- Not Specified
              nt (2),  -- Network Termination
              aai (3), -- Access to Access Interface
              uai (4), -- User to Access Interface
              isi (5), -- Internal Server Interface
              asi (6)  -- External Server Interface
            }
    ACCESS  read-write
    STATUS  mandatory
    DESCRIPTION
           "The value of this object determines the type of ATM interface.
Only uai (4) is supported."
    ::= { asamAtmInterfaceConfigEntry 1 }

-- asamAtmCacProfileIndexIncoming OBJECT-TYPE
--     ::= { asamAtmInterfaceConfigEntry 2 }
-- 
-- asamAtmCacProfileIndexOutgoing OBJECT-TYPE
--     ::= { asamAtmInterfaceConfigEntry 3}
-- 
-- asamAtmAccessProfileIndex OBJECT-TYPE
--     ::= { asamAtmInterfaceConfigEntry 4}
-- 
-- asamAtmCdvtProfileIndex OBJECT-TYPE
--     ::= { asamAtmInterfaceConfigEntry 5}
-- 
-- asamAtmNgcrAdminWeight  OBJECT-TYPE
--     ::= { asamAtmInterfaceConfigEntry 6}
-- 
-- asamAtmSignVpi  OBJECT-TYPE
--     ::= { asamAtmInterfaceConfigEntry 7}
--
-- asamAtmSignVci  OBJECT-TYPE
--     ::= { asamAtmInterfaceConfigEntry 8}
-- 
-- asamAtmGlobalLoopbackConfigured OBJECT-TYPE
--     ::= { asamAtmInterfaceConfigEntry 9}
-- 
-- asamAtmGlobalLoopbackDirection OBJECT-TYPE
--     ::= { asamAtmInterfaceConfigEntry 10 }
--
-- asamAtmIlmiVpi  OBJECT-TYPE
--     ::= { asamAtmInterfaceConfigEntry 11}
-- 
-- asamAtmIlmiVci  OBJECT-TYPE
--     ::= { asamAtmInterfaceConfigEntry 12}

-- asamAtmInterfaceCrossConnectedPVpcs  OBJECT-TYPE
--     ::= { asamAtmInterfaceConfigEntry 13}
--
-- asamAtmInterfaceCrossConnectedPVccs  OBJECT-TYPE
--     ::= { asamAtmInterfaceConfigEntry 14}
--
-- asamAtmInterfaceNonCrossConnectedPVpcs  OBJECT-TYPE
--     ::= { asamAtmInterfaceConfigEntry 15}

asamAtmInterfaceNonCrossConnectedPVccs  OBJECT-TYPE
    SYNTAX  INTEGER (0..65535)
    ACCESS  read-only
    STATUS  mandatory
    DESCRIPTION
        "The value of this object determines the number of Vcttp connections
         on this ATM interface (only PVC)."
    ::= { asamAtmInterfaceConfigEntry 16}


-- asamAtmExtTrafficDescrTypes OBJECT IDENTIFIER ::= {asamExtAtmMIBObjects 39 }
-- 

-- asamAtmTrafficDescrParamMaxIndex OBJECT-TYPE
--     ::= { asamExtAtmMIBObjects 45 }
-- 
-- 
-- asamAtmTrafficDescrParamTable OBJECT-TYPE
--     ::= { asamExtAtmMIBObjects 13 }
--

-- ==================================================================

-- ATM TC Adaptor Protocol Monitoring Current Data Table

asamAtmTcProtoCurrentTable OBJECT-TYPE
    SYNTAX  SEQUENCE OF AsamAtmTcProtoCurrentEntry
    ACCESS  not-accessible
    STATUS  mandatory
    DESCRIPTION
           "The ATM TC Adaptor Protocol Monitoring Current Data Table."
    ::= { asamExtAtmMIBObjects 14 }

asamAtmTcProtoCurrentEntry OBJECT-TYPE
    SYNTAX  AsamAtmTcProtoCurrentEntry
    ACCESS  not-accessible
    STATUS  mandatory
    DESCRIPTION
        "An entry in the ATM TC Adaptor Protocol Monitoring Current Data Table,
         each ATM interface automatically has an entry in this table
         associated with it."
    INDEX   { ifIndex }
    ::= { asamAtmTcProtoCurrentTable  1 }

AsamAtmTcProtoCurrentEntry ::=
    SEQUENCE {
        asamAtmNearEndCurrentOCDs
            Counter,
            
        asamAtmNearEndCurrentDHECVs
            Counter,
            
        asamAtmFarEndCurrentOCDs
            Counter,
            
        asamAtmFarEndCurrentDHECVs
Counter,

        asamAtmNearEndCurrentOCDs1Day
            Counter,
            
        asamAtmNearEndCurrentDHECVs1Day
            Counter,
            
        asamAtmFarEndCurrentOCDs1Day
            Counter,
            
        asamAtmFarEndCurrentDHECVs1Day
            Counter
        }

asamAtmNearEndCurrentOCDs OBJECT-TYPE
    SYNTAX  Counter
    ACCESS  read-only
    STATUS  mandatory
    DESCRIPTION
            " The number of Out of Cell Delinations anomalies which 
              occurred for incoming cells on an ATM interface
              since the start of this current 15 minute interval.
              An Out of Cell Delineation anomaly occurs when
              there are 7 consecutive ATM cells received which
              contain HEC errors."
    ::= { asamAtmTcProtoCurrentEntry 1 }

asamAtmNearEndCurrentDHECVs OBJECT-TYPE
    SYNTAX  Counter
    ACCESS  read-only
    STATUS  mandatory
    DESCRIPTION
            "The number of ATM cells discarded on this interface,
             due to a HEC error, since the start of this 
             current 15 minute interval."
    ::= { asamAtmTcProtoCurrentEntry 2 }
    
asamAtmFarEndCurrentOCDs OBJECT-TYPE
    SYNTAX  Counter
    ACCESS  read-only
    STATUS  mandatory
    DESCRIPTION
            " The number of Out of Cell Delinations anomalies which 
              occurred for incoming cells on the far end ATM 
              interface connected to this ATM interface since
              the start of this current 15 minute interval.
              The far end ATM interface does only exist when the
              ATM interface is situated on top of the ADSL physical
              medium.
              An Out of Cell Delineation anomaly occurs when
              there are 7 consecutive ATM cells received which
              contain HEC errors."
    ::= { asamAtmTcProtoCurrentEntry 3 }

asamAtmFarEndCurrentDHECVs OBJECT-TYPE
    SYNTAX  Counter
    ACCESS  read-only
    STATUS  mandatory
    DESCRIPTION
            "The number of ATM cells discarded on the far end ATM interface
              connnected to this ATM interface,
              due to a HEC error, since the start of this 
              current 15 minute interval.
              The far end ATM interface does only exist when the ATM
              interface is situated on top of the ADSL physical
              medium."
::= { asamAtmTcProtoCurrentEntry 4 }

asamAtmNearEndCurrentOCDs1Day OBJECT-TYPE
    SYNTAX  Counter
    ACCESS  read-only
    STATUS  mandatory
    DESCRIPTION
            " The number of Out of Cell Delinations anomalies which 
              occurred for incoming cells on an ATM interface
              since the start of this current 24 hour interval.
              An Out of Cell Delineation anomaly occurs when
              there are 7 consecutive ATM cells received which
              contain HEC errors."
    ::= { asamAtmTcProtoCurrentEntry 5 }

asamAtmNearEndCurrentDHECVs1Day OBJECT-TYPE
    SYNTAX  Counter
    ACCESS  read-only
    STATUS  mandatory
    DESCRIPTION
            "The number of ATM cells discarded on this interface,
             due to a HEC error, since the start of this 
             current 24 hour interval."
    ::= { asamAtmTcProtoCurrentEntry 6 }
    
asamAtmFarEndCurrentOCDs1Day OBJECT-TYPE
    SYNTAX  Counter
    ACCESS  read-only
    STATUS  mandatory
    DESCRIPTION
            " The number of Out of Cell Delinations anomalies which 
              occurred for incoming cells on the far end ATM 
              interface connected to this ATM interface since
              the start of this current 24 hour interval.
              The far end ATM interface does only exist when the
              ATM interface is situated on top of the ADSL physical
              medium.
              An Out of Cell Delineation anomaly occurs when
              there are 7 consecutive ATM cells received which
              contain HEC errors."
    ::= { asamAtmTcProtoCurrentEntry 7 }

asamAtmFarEndCurrentDHECVs1Day OBJECT-TYPE
    SYNTAX  Counter
    ACCESS  read-only
    STATUS  mandatory
    DESCRIPTION
            "The number of ATM cells discarded on the far end ATM interface
              connnected to this ATM interface,
              due to a HEC error, since the start of this 
              current 24 hour interval.
              The far end ATM interface does only exist when the ATM
              interface is situated on top of the ADSL physical
              medium."
    ::= { asamAtmTcProtoCurrentEntry 8 }

-- ==================================================================

-- ATM TC Adapter Protocol Performance Table 

asamAtmTcPerfTable OBJECT-TYPE
SYNTAX SEQUENCE OF AsamAtmTcPerfEntry
    ACCESS  not-accessible
    STATUS  mandatory
    DESCRIPTION
           "The ATM TC Adaptor Protocol Performance Table.
            This table maintains per interface the number of valid
performance intervals."
    ::= { asamExtAtmMIBObjects 15 }

asamAtmTcPerfEntry OBJECT-TYPE
    SYNTAX  AsamAtmTcPerfEntry
    ACCESS  not-accessible
    STATUS  mandatory
    DESCRIPTION
           "An entry in the ATM TC Adaptor Protocol Performance Table,
            each ATM interface automatically has an entry associated with it."
    INDEX   { ifIndex }
    ::= { asamAtmTcPerfTable  1 }

AsamAtmTcPerfEntry ::=
    SEQUENCE {
        asamAtmTcValidIntervals
INTEGER,
        asamAtmTcValidIntervals1Day
INTEGER
        } 

asamAtmTcValidIntervals OBJECT-TYPE
    SYNTAX  INTEGER
    ACCESS  read-only
    STATUS  mandatory
    DESCRIPTION
            "The number of previous intervals for which valid data has been
            stored. An ATM device must support n intervals. The value of n
            is 192. The value of this object will be n unless the device was
            brought online within the last nx15 minutes, in which case the
            value will be the number of complete 15 minute intervals the 
            device has been online."
::= { asamAtmTcPerfEntry 1 }

asamAtmTcValidIntervals1Day OBJECT-TYPE
    SYNTAX  INTEGER
    ACCESS  read-only
    STATUS  mandatory
    DESCRIPTION
            "The number of previous intervals for which valid data has been
            stored. An ATM device must support n intervals. The value of n
            is 2. The value of this object will be n unless the device was
            brought online within the last nx24 hours, in which case the
            value will be the number of complete 24 hours intervals the 
            device has been online."
    ::= { asamAtmTcPerfEntry 2 }

-- =====================================================================

-- ATM TC Adaptor Protocol Monitoring 15 Minute Interval Data Table

asamAtmTcProtoIntervalTable OBJECT-TYPE
    SYNTAX  SEQUENCE OF AsamAtmTcProtoIntervalEntry
    ACCESS  not-accessible
    STATUS  mandatory
    DESCRIPTION
           "The ATM TC Adaptor Protocol Monitoring Interval Data Table.
            This table maintains per interface statistics
            for the previous 15 minute intervals."
    ::= { asamExtAtmMIBObjects 16 }

asamAtmTcProtoIntervalEntry OBJECT-TYPE
    SYNTAX  AsamAtmTcProtoIntervalEntry
    ACCESS  not-accessible
    STATUS  mandatory
    DESCRIPTION
           "An entry in the ATM TC Adaptor Protocol Monitoring Interval Data
            Table, each ATM interface automatically has an entry in this table
            associated with it."
    INDEX   { ifIndex, asamAtmIntervalNumber }
    ::= { asamAtmTcProtoIntervalTable  1 }

AsamAtmTcProtoIntervalEntry ::=
    SEQUENCE {
        asamAtmIntervalNumber
            INTEGER,
            
        asamAtmNearEndIntervalOCDs
            Counter,
            
        asamAtmNearEndIntervalDHECVs
            Counter,
            
        asamAtmFarEndIntervalOCDs
            Counter,
            
        asamAtmFarEndIntervalDHECVs
            Counter
        }
        
asamAtmIntervalNumber OBJECT-TYPE
    SYNTAX  INTEGER 
    ACCESS  not-accessible
    STATUS  mandatory
    DESCRIPTION
           "A number between 1 and n, which identifies the
            interval for which the set of statistics is available.
            An ATM device support n intervals. The value of n is 192.
            The interval identified by 1 is the most recently
            completed 15 minute interval,
            and the interval identified
            by n is the interval immediately preceding the
            one identified by n-1."
    ::= { asamAtmTcProtoIntervalEntry  1 }

asamAtmNearEndIntervalOCDs OBJECT-TYPE
    SYNTAX  Counter
    ACCESS  read-only
    STATUS  mandatory
    DESCRIPTION
            " The number of Out of Cell Delinations anomalies which 
              occurred for incoming cells on an ATM interface
              in a particular 15 minute interval."
    ::= { asamAtmTcProtoIntervalEntry 2 }

asamAtmNearEndIntervalDHECVs OBJECT-TYPE
    SYNTAX  Counter
    ACCESS  read-only
    STATUS  mandatory
    DESCRIPTION
            "The number of ATM cells discarded on this interface,
             due to a HEC error, in a particular 15 minute
             interval."
    ::= { asamAtmTcProtoIntervalEntry 3 }
    
asamAtmFarEndIntervalOCDs OBJECT-TYPE
    SYNTAX  Counter
    ACCESS  read-only
    STATUS  mandatory
    DESCRIPTION     
            " The number of Out of Cell Delinations anomalies which 
              occurred for incoming cells on the far end ATM 
              interface connected to this ATM interface in a particular
              15 minute interval.
              The far end ATM interface does only exist when the
              ATM interface is situated on top of the ADSL physical
              medium.
              An Out of Cell Delineation anomaly occurs when
              there are 7 consecutive ATM cells received which
              contain HEC errors."
    ::= { asamAtmTcProtoIntervalEntry 4 }

asamAtmFarEndIntervalDHECVs OBJECT-TYPE
    SYNTAX  Counter
    ACCESS  read-only
    STATUS  mandatory
    DESCRIPTION
            "The number of ATM cells discarded on the far end ATM interface
             connnected to this ATM interface,
             due to a HEC error, in a particular 15 minute interval.
             The far end ATM interface does only exist when the ATM
             interface is situated on top of the ADSL physical
             medium."
::= { asamAtmTcProtoIntervalEntry 5 }
-- ==================================================================

-- ATM TC Adaptor Protocol Monitoring 24 hour Interval Data Table

asamAtmTcProtoInterval1DayTable OBJECT-TYPE
    SYNTAX  SEQUENCE OF AsamAtmTcProtoInterval1DayEntry
    ACCESS  not-accessible
    STATUS  mandatory
    DESCRIPTION
           "The ATM TC Adaptor Protocol Monitoring Interval Data Table.
            This table maintains per interface statistics
            for the previous 24 hour intervals."
    ::= { asamExtAtmMIBObjects 74}

asamAtmTcProtoInterval1DayEntry OBJECT-TYPE
    SYNTAX  AsamAtmTcProtoInterval1DayEntry
    ACCESS  not-accessible
    STATUS  mandatory
    DESCRIPTION
           "An entry in the ATM TC Adaptor Protocol Monitoring Interval Data
            Table, each ATM interface automatically has an entry in this table
            associated with it."
    INDEX   { ifIndex, asamAtmIntervalNumber1Day }
    ::= { asamAtmTcProtoInterval1DayTable  1 }

AsamAtmTcProtoInterval1DayEntry ::=
    SEQUENCE {
        asamAtmIntervalNumber1Day
            INTEGER,
            
        asamAtmNearEndIntervalOCDs1Day
            Counter,
            
        asamAtmNearEndIntervalDHECVs1Day
            Counter,
            
        asamAtmFarEndIntervalOCDs1Day
            Counter,
            
        asamAtmFarEndIntervalDHECVs1Day
            Counter
        }
        
asamAtmIntervalNumber1Day OBJECT-TYPE
    SYNTAX  INTEGER 
    ACCESS  not-accessible
    STATUS  mandatory
    DESCRIPTION
           "A number between 1 and n, which identifies the
            interval for which the set of statistics is available.
            An ATM device must support n intervals. The value of n is 2, 
            The interval identified by 1 is the most recently
            completed 24 hour interval,
            and the interval identified
            by n is the interval immediately preceding the
            one identified by n-1."
    ::= { asamAtmTcProtoInterval1DayEntry  1 }

asamAtmNearEndIntervalOCDs1Day OBJECT-TYPE
    SYNTAX  Counter
    ACCESS  read-only
    STATUS  mandatory
    DESCRIPTION
            " The number of Out of Cell Delinations anomalies which 
              occurred for incoming cells on an ATM interface
              in a particular 24 hour interval."
    ::= { asamAtmTcProtoInterval1DayEntry 2 }

asamAtmNearEndIntervalDHECVs1Day OBJECT-TYPE
    SYNTAX  Counter
    ACCESS  read-only
    STATUS  mandatory
    DESCRIPTION
            "The number of ATM cells discarded on this interface,
             due to a HEC error, in a particular 24 hour
             interval."
    ::= { asamAtmTcProtoInterval1DayEntry 3 }
    
asamAtmFarEndIntervalOCDs1Day OBJECT-TYPE
    SYNTAX  Counter
    ACCESS  read-only
    STATUS  mandatory
    DESCRIPTION     
            " The number of Out of Cell Delinations anomalies which 
              occurred for incoming cells on the far end ATM 
              interface connected to this ATM interface in a particular
              24 hour interval.
              The far end ATM interface does only exist when the
              ATM interface is situated on top of the ADSL physical
              medium.
              An Out of Cell Delineation anomaly occurs when
              there are 7 consecutive ATM cells received which
              contain HEC errors."
    ::= { asamAtmTcProtoInterval1DayEntry 4 }

asamAtmFarEndIntervalDHECVs1Day OBJECT-TYPE
    SYNTAX  Counter
    ACCESS  read-only
    STATUS  mandatory
    DESCRIPTION
            "The number of ATM cells discarded on the far end ATM interface
             connnected to this ATM interface,
             due to a HEC error, in a particular 24 hour interval.
             The far end ATM interface does only exist when the ATM
             interface is situated on top of the ADSL physical
             medium."
     ::= { asamAtmTcProtoInterval1DayEntry 5 }

-- asamAtmDs3PlcpCurrentTable OBJECT-TYPE
--     ::= { asamExtAtmMIBObjects 17 }
-- 

-- asamAtmDs3PlcpIntervalTable OBJECT-TYPE
--     ::= { asamExtAtmMIBObjects 18 }
--

-- asamAtmLoopbackVplTable OBJECT-TYPE
--     ::= { asamExtAtmMIBObjects 20 }
-- 

-- asamAtmLoopbackVclTable OBJECT-TYPE
--     ::= { asamExtAtmMIBObjects 21 }
-- 

-- asamAtmVplStatTable   OBJECT-TYPE
-- ::= { asamExtAtmMIBObjects 40 }
-- 

-- ASAM ATM VCL Statistics Table
-- =============================

 asamAtmVclStatTable   OBJECT-TYPE
     SYNTAX  SEQUENCE OF AsamAtmVclStatEntry
     ACCESS  not-accessible
     STATUS  mandatory
     DESCRIPTION
         "This table has been introduced to allow the Manager to start and stop
         monitoring on a need basis, by creating/deleting entry in this table."
 ::= { asamExtAtmMIBObjects 22 }

 asamAtmVclStatEntry    OBJECT-TYPE
     SYNTAX  AsamAtmVclStatEntry
     ACCESS  not-accessible
     STATUS  mandatory
     DESCRIPTION
         "Each entry in this table corresponds to perf monitoring on a specific
         VCL."
 INDEX { ifIndex, atmVclVpi, atmVclVci }
 ::= { asamAtmVclStatTable 1 }

 AsamAtmVclStatEntry ::=
 SEQUENCE {
--   asamAtmVclStatRowStatus  RowStatus,    
     asamAtmVclStatUsDiscards   Counter,
     asamAtmVclStatDsDiscards   Counter,
     asamAtmVclStatReset        INTEGER
 }

-- asamAtmVclStatRowStatus OBJECT-TYPE
--    SYNTAX  RowStatus
--    ACCESS  read-write
--    STATUS  mandatory
--    DESCRIPTION
--        "The Manager is allowed to perform only 'createAndGo' and 'destroy'
--        operations on this object. In response to 'createAndGo' operation,
--        Agent will check the conditions (listed in the note given with
--        definition of atmVclStatEntry) and if satisfied, creates an entry in
--        this table, set asamAtmVclStatRowStatus to Active, creates
--        an entry in atmVclStatTable and starts monitoring.
--        In response to 'destroy' operation on a specific entry in this
--        table, Agent deletes the entry from this table and also the
--        corresponding entry from atmVclStatTable, and stops monitoring. 
--            ALCATEL NOTE:
--              SUPPORT :       YES
--              PERSIST :       YES
--              INSRVMOD:       YES
--              RANGE:          1..6
--              DEFVALUE:       NA
--              UNITS:          NA "
--::= { asamAtmVclStatEntry 1 }

 asamAtmVclStatUsDiscards OBJECT-TYPE
     SYNTAX  Counter
     ACCESS  read-only
     STATUS  mandatory
     DESCRIPTION
         "The total number of ATM cells that are
         discarded in the upstream direction
         ALCATEL NOTE:
            ACCESS:      NA           USAGE:       NA
            PERSIST:     NO           INSRVMOD:    NO
            RANGE:       NA           DEFVALUE:    NA
            UNITS:       NA           SPARSE:      NA
            DESCR:       NA
"

 ::= { asamAtmVclStatEntry 2 }


 asamAtmVclStatDsDiscards  OBJECT-TYPE
     SYNTAX  Counter
     ACCESS  read-only
     STATUS  mandatory
     DESCRIPTION
         "The total number of ATM cells that are
         discarded in the downstream direction
         ALCATEL NOTE:
            ACCESS:      NA           USAGE:       NA
            PERSIST:     NO           INSRVMOD:    NO
            RANGE:       NA           DEFVALUE:    NA
            UNITS:       NA           SPARSE:      NA
            DESCR:       NA
"

 ::= { asamAtmVclStatEntry 3 }

 asamAtmVclStatReset  OBJECT-TYPE
     SYNTAX  INTEGER { 
                       reset(1) 
                      }
     ACCESS  read-write
     STATUS  mandatory
     DESCRIPTION
         "All the counters of an VCL can be reset
         using this variable. 1 means to reset the counters.

 ALCATEL NOTE:
            ACCESS:      NA           USAGE:       MAND
            PERSIST:     NO           INSRVMOD:    NO
            RANGE:       1            DEFVALUE:    NA
            UNITS:       NA           SPARSE:      NA
            DESCR:       NA"

 ::= { asamAtmVclStatEntry 4 }


-- ASAM ATM VPL loopback test table
-- ================================

-- asamAtmVpLoopbackTestTable OBJECT-TYPE
--     SYNTAX  SEQUENCE OF AsamAtmVpLoopbackTestEntry
--     ACCESS  not-accessible
--     STATUS  mandatory
--     DESCRIPTION
--         "This table contains all parameters needed to run loopback test on a
--         VP. The logic of acquiring and starting a loopback test on a specific
--         VPL is kept centrally with atmfM4VpTestTable.   
--         atmfM4VpTestTable is used in way similar to the ifTestTable in RFC2233. 
--         This is achieved by making atmfM4VpTestType 
--         (which is a OBJECT-IDENTIFIER) of atmfM4VpTestTable point to
--         an (virtual) entry in this table.
--         For the procedure to be followed for acquiring, refer to the definition
--         of ifTestTable. After acquiring the permission, in order to start a
--         loopback test, Manager has to send a set-request on atmfM4VpTestType
--         specifying an object identifier as value, which refers to an entry in
--         asamAtmVpLoopbackTestTable.
--         For example; in order to start a loopback test with below details
--         ifIndex=a, VplVpi=b, asamAtmVpLoopbackSpan=c,
--         asamAtmVpLoopbackLLIDRequested=d and asamAtmVpLoopbackDirection=e,
--         below set request has to be sent.
--         set-request(atmfM4VpTestType.a.b.atmfM4VpTestObject, <OID of 
--         AsamAtmVpLoopbackVplVpiRequested>.b.c.d.e)
-- 
--         This table is a VIRTUAL table (an Alcatel proprietary concept),
--         meaning entries in it donot need to be created/deleted by Manager
--         explicitly and hence, all its objects are kept not-accessible."
-- ::= { asamExtAtmMIBObjects 23 }
--
-- asamAtmVpLoopbackTestEntry    OBJECT-TYPE
--     SYNTAX  AsamAtmVpLoopbackTestEntry
--     ACCESS  not-accessible
--     STATUS  mandatory
--     DESCRIPTION
--         "Each entry in this table corresponds to one instance of loopback test."
--     INDEX { asamAtmVpLoopbackVplVpiRequested,
--             asamAtmVpLoopbackSpan,
--             asamAtmVpLoopbackLLIDRequested,
--             asamAtmVpLoopbackDirection }
-- ::= { asamAtmVpLoopbackTestTable 1 }
-- 
-- AsamAtmVpLoopbackTestEntry ::=
-- SEQUENCE {
--     asamAtmVpLoopbackVplVpiRequested  AtmVpIdentifier,
--     asamAtmVpLoopbackSpan             AsamAtmLoopbackSpan,
--     asamAtmVpLoopbackLLIDRequested    AsamAtmLoopbackLLID,
--     asamAtmVpLoopbackDirection        AsamAtmF4F5LoopbackDirection
-- }
-- 
-- asamAtmVpLoopbackVplVpiRequested OBJECT-TYPE
--     SYNTAX  AtmVpIdentifier
--     ACCESS  not-accessible
--     STATUS  mandatory
--     DESCRIPTION
--        "The VPI value of the VPL. Note that the VPI=0 is not used
--         for a VPL not associated with a VCL."
--     ::= { asamAtmVpLoopbackTestEntry 1 }
-- 
-- asamAtmVpLoopbackSpan OBJECT-TYPE
--     SYNTAX  AsamAtmLoopbackSpan
--     ACCESS  not-accessible
--     STATUS  mandatory
--     DESCRIPTION
--        "The requested loopback span"
--     ::= { asamAtmVpLoopbackTestEntry 2 }
-- 
-- asamAtmVpLoopbackLLIDRequested OBJECT-TYPE
--     SYNTAX  AsamAtmLoopbackLLID
--     ACCESS  not-accessible
--     STATUS  mandatory
--     DESCRIPTION
--        "The requested LLID"
--     ::= { asamAtmVpLoopbackTestEntry 3 }
-- 
-- asamAtmVpLoopbackDirection OBJECT-TYPE
--     SYNTAX  AsamAtmF4F5LoopbackDirection
--     ACCESS  not-accessible
--     STATUS  mandatory
--     DESCRIPTION
--        "The requested loopback direction."
--     ::= { asamAtmVpLoopbackTestEntry 4 }


-- ASAM ATM VPL loopback test result table
-- =======================================

-- asamAtmVpLoopbackTestResultTable OBJECT-TYPE
--     SYNTAX  SEQUENCE OF AsamAtmVpLoopbackTestResultEntry
--     ACCESS  not-accessible
--     STATUS  mandatory
--     DESCRIPTION
--         "After completion of loopback testing, Agent logs test result data,
--         which is specific to ATM into this VIRTUAL table (apart from this ,
--         Agent logs the overall outcome of the test, success/failure into
--         the atmfM4VpResult of atmfM4VpTestTable).
--         atmfM4VpTestTable is used in way similar to the ifTestTable in RFC2233.
--         The logic of getting the info about completion of a particular test
--         (for more details, refer to definition of ifTestTable in RFC2233) and
--         retrieving the test result is kept centrally with atmfM4VpTestTable.
--         This is achieved by making atmfM4VpTestCode 
--         (which is a OBJECT-IDENTIFIER) of atmfM4VpTestTable to point to 
--         an (virtual) entry in this table.
--         When Manager comes to know about the test completion, it can retrieve
--         the result by sending a get-request on atmfM4VpTestCode.
--         For example; in order to retrieve the result of a test ran on a VPL,
--         which corresponds to an ATM i/f with ifIndex=a,
--         get-request(atmfM4VpTestCode.a.f.atmfM4VpTestObject) has to be sent.
--         In response, Agent sends get-response(<OID of 
--         AsamAtmVpLoopbackVplVpiResult>.f.g.h),
--         where f, g and h are the values of atmVplVpi,
--         asamAtmVpLoopbackRoundTripDelay and asamAtmVpLoopbackLLIDResult.
--
--         This table is a VIRTUAL table."
-- ::= { asamExtAtmMIBObjects 24 }
--
-- asamAtmVpLoopbackTestResultEntry    OBJECT-TYPE
--     SYNTAX  AsamAtmVpLoopbackTestResultEntry
--     ACCESS  not-accessible
--     STATUS  mandatory
--     DESCRIPTION
--         "Each entry in this table corresponds to one instance of loopback test."
--     INDEX { asamAtmVpLoopbackVplVpiResult,
--             asamAtmVpLoopbackRoundTripDelay,
--             asamAtmVpLoopbackLLIDResult}
-- ::= { asamAtmVpLoopbackTestResultTable 1 }
-- 
-- AsamAtmVpLoopbackTestResultEntry ::=
-- SEQUENCE {
--     asamAtmVpLoopbackVplVpiResult     AtmVpIdentifier,
--     asamAtmVpLoopbackRoundTripDelay   INTEGER,
--     asamAtmVpLoopbackLLIDResult       AsamAtmLoopbackLLID
-- }
-- 
-- asamAtmVpLoopbackVplVpiResult OBJECT-TYPE
--     SYNTAX  AtmVpIdentifier
--     ACCESS  not-accessible
--     STATUS  mandatory
--     DESCRIPTION
--        "The VPI value of the VPL. Note that the VPI=0 is not used
--         for a VPL not associated with a VCL."
--     ::= { asamAtmVpLoopbackTestResultEntry 1 }
-- 
-- asamAtmVpLoopbackRoundTripDelay OBJECT-TYPE
--     SYNTAX  INTEGER (0..5000000)
--     ACCESS  not-accessible
--     STATUS  mandatory
--     DESCRIPTION
--        "Round trip delay of the loopback cell"
--     ::= { asamAtmVpLoopbackTestResultEntry 3 }
-- 
-- asamAtmVpLoopbackLLIDResult OBJECT-TYPE
--     SYNTAX  AsamAtmLoopbackLLID
--     ACCESS  not-accessible
--     STATUS  mandatory
--     DESCRIPTION
--        "Gives the location the cells were looped back"
--     ::= { asamAtmVpLoopbackTestResultEntry 4 }


-- ASAM ATM VC loopback test table
-- ===============================

 asamAtmVcLoopbackTestTable OBJECT-TYPE
     SYNTAX  SEQUENCE OF AsamAtmVcLoopbackTestEntry
     ACCESS  not-accessible
     STATUS  mandatory
     DESCRIPTION
         "The description for this table goes in same line with that of
         asamAtmVpLoopbackTestTable."
 ::= { asamExtAtmMIBObjects 25 }
 
 asamAtmVcLoopbackTestEntry    OBJECT-TYPE
     SYNTAX  AsamAtmVcLoopbackTestEntry
     ACCESS  not-accessible
     STATUS  mandatory
     DESCRIPTION
         "Each entry in this table corresponds to one instance of loopback test."
     INDEX { asamAtmVcLoopbackVclVpiRequested,
             asamAtmVcLoopbackVclVciRequested,
             asamAtmVcLoopbackSpan,
             asamAtmVcLoopbackLLIDRequested,
             asamAtmVcLoopbackDirection}
 ::= { asamAtmVcLoopbackTestTable 1 }

 AsamAtmVcLoopbackTestEntry ::=
 SEQUENCE {
     asamAtmVcLoopbackVclVpiRequested  AtmVpIdentifier,
     asamAtmVcLoopbackVclVciRequested  AtmVcIdentifier,
     asamAtmVcLoopbackSpan             AsamAtmLoopbackSpan,
     asamAtmVcLoopbackLLIDRequested    AsamAtmLoopbackLLID,
     asamAtmVcLoopbackDirection        AsamAtmF4F5LoopbackDirection
 }
 
 asamAtmVcLoopbackVclVpiRequested OBJECT-TYPE
     SYNTAX  AtmVpIdentifier
     ACCESS  not-accessible
     STATUS  mandatory
     DESCRIPTION
        "The VPI value of the VCL."
     ::= { asamAtmVcLoopbackTestEntry 1 }
 
 asamAtmVcLoopbackVclVciRequested OBJECT-TYPE
     SYNTAX  AtmVcIdentifier
     ACCESS  not-accessible
     STATUS  mandatory
     DESCRIPTION
        "The VCI value of the VCL."
     ::= { asamAtmVcLoopbackTestEntry 2 }
 
 asamAtmVcLoopbackSpan OBJECT-TYPE
     SYNTAX  AsamAtmLoopbackSpan
     ACCESS  not-accessible
     STATUS  mandatory
     DESCRIPTION
        "The requested loopback span
        ALCATEL NOTE:
         ACCESS:        NA
         USAGE:         NA
         PERSIST:  	NO
         INSRVMOD: 	NO
         RANGE:         NA
         DEFVALUE: 	NA
         UNITS:	        NA
         SPARSE:	NA
         DESCR:	Only e2e is supported in ISAM."
     ::= { asamAtmVcLoopbackTestEntry 3 }
 
 asamAtmVcLoopbackLLIDRequested OBJECT-TYPE
     SYNTAX  AsamAtmLoopbackLLID
     ACCESS  not-accessible
     STATUS  mandatory
     DESCRIPTION
        "The requested LLID"
     ::= { asamAtmVcLoopbackTestEntry 4 }
 
 asamAtmVcLoopbackDirection OBJECT-TYPE
     SYNTAX  AsamAtmF4F5LoopbackDirection
     ACCESS  not-accessible
     STATUS  mandatory
     DESCRIPTION
        "The requested loopback direction.
        ALCATEL NOTE:
         ACCESS:        NA
         USAGE:         NA
         PERSIST:  	NO
         INSRVMOD: 	NO
         RANGE:         NA
         DEFVALUE: 	NA
         UNITS:	        NA
         SPARSE:	NA
         DESCR:	Only outgoing is supported in ISAM."
     ::= { asamAtmVcLoopbackTestEntry 5 }


-- ASAM ATM VCL loopback test result table
-- =======================================

 asamAtmVcLoopbackTestResultTable OBJECT-TYPE
     SYNTAX  SEQUENCE OF AsamAtmVcLoopbackTestResultEntry
     ACCESS  not-accessible
     STATUS  mandatory
     DESCRIPTION
         "After completion of loopback testing, Agent logs test result data,
         which is specific to ATM into this VIRTUAL table (apart from this ,
         Agent logs the overall outcome of the test, success/failure into
         the atmfM4VcResult of atmfM4VcTestTable).
         atmfM4VcTestTable is used in way similar to the ifTestTable in RFC2233.
         The logic of getting the info about completion of a particular test
         (for more details, refer to definition of ifTestTable in RFC2233) and
         retrieving the test result is kept centrally with atmfM4VcTestTable.
         This is achieved by making atmfM4VcTestCode 
         (which is a OBJECT-IDENTIFIER) of atmfM4VcTestTable to point to 
         an (virtual) entry in this table.
         When Manager comes to know about the test completion, it can retrieve
         the result by sending a get-request on atmfM4VcTestCode.
         For example; in order to retrieve the result of a test ran on a VPL,
         which corresponds to an ATM i/f with ifIndex=a,
         get-request(atmfM4VpTestCode.a.f.atmfM4VcTestObject) has to be sent.
         In response, Agent sends get-response(<OID of 
         AsamAtmVcLoopbackVplVpiResult>.f.g.h),
         where f, g, h, i are the values of atmVclVpi, atmVclVci
         asamAtmVpLoopbackRoundTripDelay and asamAtmVpLoopbackLLIDResult.
 
         This table is a VIRTUAL table."
 ::= { asamExtAtmMIBObjects 41 }
 
 asamAtmVcLoopbackTestResultEntry    OBJECT-TYPE
     SYNTAX  AsamAtmVcLoopbackTestResultEntry
     ACCESS  not-accessible
     STATUS  mandatory
     DESCRIPTION
         "Each entry in this table corresponds to one instance of loopback test."
     INDEX { asamAtmVcLoopbackVclVpiResult,
             asamAtmVcLoopbackVclVciResult,
             asamAtmVcLoopbackRoundTripDelay,
             asamAtmVcLoopbackLLIDResult}
 ::= { asamAtmVcLoopbackTestResultTable 1 }
 
 AsamAtmVcLoopbackTestResultEntry ::=
 SEQUENCE {
     asamAtmVcLoopbackVclVpiResult     AtmVpIdentifier,
     asamAtmVcLoopbackVclVciResult     AtmVcIdentifier,
     asamAtmVcLoopbackRoundTripDelay   INTEGER,
     asamAtmVcLoopbackLLIDResult       AsamAtmLoopbackLLID
 }
 
 asamAtmVcLoopbackVclVpiResult OBJECT-TYPE
     SYNTAX  AtmVpIdentifier
     ACCESS  not-accessible
     STATUS  mandatory
     DESCRIPTION
        "The VPI value of the VCL."
     ::= { asamAtmVcLoopbackTestResultEntry 1 }
 
 asamAtmVcLoopbackVclVciResult OBJECT-TYPE
     SYNTAX  AtmVcIdentifier
     ACCESS  not-accessible
     STATUS  mandatory
     DESCRIPTION
        "The VCI value of the VCL."
     ::= { asamAtmVcLoopbackTestResultEntry 2 }
 
 asamAtmVcLoopbackRoundTripDelay OBJECT-TYPE
     SYNTAX  INTEGER (0..5000000)
     ACCESS  not-accessible
     STATUS  mandatory
     DESCRIPTION
        "Round trip delay of the loopback cell"
     ::= { asamAtmVcLoopbackTestResultEntry 3 }
 
 asamAtmVcLoopbackLLIDResult OBJECT-TYPE
     SYNTAX  AsamAtmLoopbackLLID
     ACCESS  not-accessible
     STATUS  mandatory
     DESCRIPTION
        "Gives the location the cells were looped back"
     ::= { asamAtmVcLoopbackTestResultEntry 4 }


-- asamAtmInterfacePMTable OBJECT-TYPE
-- ::= { asamExtAtmMIBObjects 27 }
--

-- asamAtmInterfaceTCTable OBJECT-TYPE
-- ::= { asamExtAtmMIBObjects 28 }

-- asamAtmIsiTable OBJECT-TYPE
-- ::= {asamExtAtmMIBObjects 42}

-- asamAtmVplRootListTable OBJECT-TYPE
-- ::= {asamExtAtmMIBObjects 43}

-- asamAtmVclRootListTable OBJECT-TYPE
-- ::= {asamExtAtmMIBObjects 44}

-- asamAtmAsiTable OBJECT-TYPE
-- ::= {asamExtAtmMIBObjects 46}

-- ASAM ATM VCL TO IF index VCL MAPPING TABLE
-- ==========================================

asamAtmVclToIfVclMappingTable  OBJECT-TYPE
    SYNTAX  SEQUENCE OF AsamAtmVclToIfVclMappingTableEntry
    ACCESS  not-accessible
    STATUS  mandatory
    DESCRIPTION
           "This table is a mapping table between the ATM VCL (keys: atm
            interface, vpi and vci) and the associated ATM VCL If index."
    ::= { asamExtAtmMIBObjects 72 }

asamAtmVclToIfVclMappingTableEntry OBJECT-TYPE
    SYNTAX  AsamAtmVclToIfVclMappingTableEntry
    ACCESS  not-accessible
    STATUS  mandatory
    DESCRIPTION
           "This list contains the mapping between the ATM VCL specific data 
            and the associated ATM VCL If index.
            Each ATM VCL automatically has an entry in this table
            associated with it.
            There is only partial compliance with the lexicographical ordering, as the 
            atmVclVpi and atmVclVci combination are ordered in the order of their creation."
    INDEX   { ifIndex,  atmVclVpi, atmVclVci }
    ::= { asamAtmVclToIfVclMappingTable 1 }

AsamAtmVclToIfVclMappingTableEntry ::=
    SEQUENCE {
                  atmVclIfIndex    InterfaceIndex
             }

atmVclIfIndex OBJECT-TYPE
    SYNTAX      InterfaceIndex
    ACCESS      read-only
    STATUS      mandatory
    DESCRIPTION "This is the unique IfIndex associated with a VCL"
    ::= { asamAtmVclToIfVclMappingTableEntry 1 }

-- ASAM If index VCL TO VCL MAPPING TABLE
-- ======================================


asamAtmIfVclToVclMappingTable  OBJECT-TYPE
    SYNTAX  SEQUENCE OF AsamAtmIfVclToVclMappingTableEntry
    ACCESS  not-accessible
    STATUS  mandatory
    DESCRIPTION
           "This table is a mapping table between the If index of an ATM VCL 
            and the associated ATM VCL data (atm interface index, vpi and vci)."
    ::= { asamExtAtmMIBObjects 73 }

asamAtmIfVclToVclMappingTableEntry OBJECT-TYPE
    SYNTAX  AsamAtmIfVclToVclMappingTableEntry
    ACCESS  not-accessible
    STATUS  mandatory
    DESCRIPTION
           "This list contains the mapping between the If index of an ATM VCL 
            and the associated ATM VCL specific data 
            (ATM interface, vpi and vci).
            Each ATM VCL automatically has an entry in this table
            associated with it."
    INDEX   { ifIndex }
    ::= { asamAtmIfVclToVclMappingTable 1 }

AsamAtmIfVclToVclMappingTableEntry ::=
    SEQUENCE {
         atmVCLMapAtmIfIndex    InterfaceIndex,
         atmVclMapVpi           AtmVpIdentifier, 
         atmVclMapVci           AtmVcIdentifier
             }

atmVCLMapAtmIfIndex OBJECT-TYPE
    SYNTAX      InterfaceIndex
    ACCESS      read-only
    STATUS      mandatory
    DESCRIPTION "This is the unique IfIndex of the ATM interface on on which the
                 VCL is created.
                 Note: Every VCL also has a unique IfIndex."
    ::= { asamAtmIfVclToVclMappingTableEntry 1 }

atmVclMapVpi OBJECT-TYPE
    SYNTAX  AtmVpIdentifier
    ACCESS  read-only
    STATUS  mandatory
    DESCRIPTION
           "The VPI value of the VCL."
    ::= { asamAtmIfVclToVclMappingTableEntry  2 }

atmVclMapVci OBJECT-TYPE
    SYNTAX  AtmVcIdentifier
    ACCESS  read-only
    STATUS  mandatory
    DESCRIPTION
           "The VCI value of the VCL.
            The maximum VCI value cannot
            exceed the value allowable by the atmInterfaceMaxVciBits."
    ::= { asamAtmIfVclToVclMappingTableEntry  3 }

asamAtmVclTable OBJECT-TYPE
    SYNTAX  SEQUENCE OF AsamAtmVclEntry
    ACCESS  not-accessible
    STATUS  mandatory
    DESCRIPTION
           "The table as atmVclTable's extension to configure encapsulation type 
and auto-detection."
    ::= { asamExtAtmMIBObjects 75}

asamAtmVclEntry OBJECT-TYPE
    SYNTAX  AsamAtmVclEntry
    ACCESS  not-accessible
    STATUS  mandatory
    DESCRIPTION
           "Whenever an entry is created in the atmVclTable, a corresponding entry
will be created by the system (automatically) in this table."
    INDEX   {
                 ifIndex,
                 atmVclVpi,
                 atmVclVci
               }
    ::= { asamAtmVclTable  1 }

AsamAtmVclEntry ::=
    SEQUENCE {
        asamAtmVclEncapsType
              INTEGER,
        asamAtmVclEncapsAutodetect
              INTEGER
    }

asamAtmVclEncapsType OBJECT-TYPE
    SYNTAX  INTEGER {
                 llcSnapBridged(1),
                 llcSnapRouted(2),
                 llcNlpid(3),
                 vcMuxBridged(4),
                 vcMuxRouted(5),
                 vcMuxPppoa(6),
                 other(7),
                 unknown(8),
                 none(9)
               }
    ACCESS  read-write
    STATUS  mandatory
    DESCRIPTION
           "An instance of this object only exists when the
            local VCL end-point is also the VCC end-point,
            and AAL5 is in use.
            It specifies the type of data encapsulation used over
            the AAL5 SSCS layer.
		llcSnapBridged (RFC2684) can be used for IPoE and PPPoE,
		llcSnapRouted (RFC2684) can be used for IPoA,
		llcNlpid (RFC2364) can be used for PPPoA,
		vcMuxBridged can be used for IPoE and PPPoE,
		vcMuxRouted can be used for IPoA,
		vcMuxPppoa can be used for PPPoA.
                none can be used for ServiceMPLS
	    When the value of asamAtmVclEncapsAutodetect is disabled,
            this object must be configured by operator explicitly when
            creating the VCL. When the value of asamAtmVclEncapsAutodetect is
            different from disabled, this object is read only and will
            indicate the actual encapsulation type.
            Once a VCL has been created with asamAtmVclEncapsAutodetect put to
            disabled, this object cannot be modified anymore.
    ALCATEL NOTE: other(7) is not supported from R2.1
                  unknown(8) is a readonly value which indicate the EncapType 
                  is unknown when the value of asamAtmVclEncapsAutodetect is 
                  different from disabled."
       DEFVAL  { llcSnapBridged }
       ::= { asamAtmVclEntry  1 }

asamAtmVclEncapsAutodetect OBJECT-TYPE
SYNTAX  INTEGER {
             disabled(1),
             autoDetectIp(2),
             autoDetectPpp(3),
             autoDetectPppoa(4),
             autoDetectIpoePpp(5)
}
    ACCESS  read-write
    STATUS  mandatory
    DESCRIPTION
            "This object will be used to enable/disable auto detection,
            If enabled, asamAtmVclEncapsType will be read-only and 
              it will indicate the actual encapsulation type.
            If disabled, PVC encapsulation type object will be configurable. 
              autoDetectIp is used for auto-detection between RFC2684 
              LLC-SNAP and VC-MUX, both bridged and routed.
            autoDetectPpp is used for auto-detection between RFC2684 
              LLC-SNAP bridged, VC-MUX bridged, RFC2364 LLC-NLPID and
              VC-MUX-PPPoA.
            autoDetectPppoa is used for auto-detection between VC-MUX-PPPoA
              and LLC-NLPID.
            autoDetectIpoePpp is used for auto-detection between RFC 2364 PPPoA
              LLC/NLPID, RFC 2364 PPPoA VC-MUX, RFC 2684 Bridged LLC/SNAP, and RFC
              2684 VC-MUX.
            Once a VCL has been created, this object cannot be modified anymore."
    DEFVAL  { disabled }
    ::= { asamAtmVclEntry  2 }

END
