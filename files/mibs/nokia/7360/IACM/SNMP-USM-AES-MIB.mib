-- ALCATEL rfc3826 MIB
-- ===========================================================================
-- The following MIB module definition was extracted from rfc3826
-- and modified to reflect Alcatel's implementation.
--
         -- Postal: Alcatel Bell Telephone
         -- Francis Wellesplein 1
         -- 2018 Antwerpen
         -- BELGIUM

-- ===========================================================================
--  HISTORY:
--
--  date: 09/12/2014
--  editor: Dharmaraj Gurusamy
--  Version: 3FE21961EAAA_5.2.0.0
--  Changes:
--      * ALU00125044 : Stronger encryption for SNMPV3
-- ===========================================================================

SNMP-USM-AES-MIB DEFINITIONS ::= BEGIN
    IMPORTS
--	MODULE-IDENTITY, OBJECT-IDENTITY,
--	snmpModules FROM SNMPv2-SMI  [RFC2578]
	snmpModules       FROM RFC1155-SMI
	snmpPrivProtocols FROM SNMP-FRAMEWORK-MIB; -- [RFC3411]

snmpUsmAesMIB OBJECT IDENTIFIER ::= { snmpModules 20 }

usmAesCfb128Protocol OBJECT IDENTIFIER ::= { snmpPrivProtocols 4 }
--    STATUS        mandatory
--    DESCRIPTION  "The CFB128-AES-128 Privacy Protocol."
--    REFERENCE    "- Specification for the ADVANCED ENCRYPTION
--                    STANDARD. Federal Information Processing
--                    Standard (FIPS) Publication 197.
--                    (November 2001).
--
--                  - Dworkin, M., NIST Recommendation for Block
--                    Cipher Modes of Operation, Methods and
--                    Techniques. NIST Special Publication 800-38A
--                    (December 2001).
--                 "

END
