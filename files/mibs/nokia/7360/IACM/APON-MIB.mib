APON-MIB DEFINITIONS ::= BEGIN

-- =============================================================================
--  This specification is published by Alcatel under Non-Disclosure
--  Agreement(s) (NDA) with specific parties and has to be considered as
--  Confidential Information as defined in such NDA.
--  Alcatel reserves the right to revise this document for any reason,
--  including but not limited to conformity with standards promulgated by
--  various agencies, utilisation of advances in the state of the technical
--  areas, or the reflection of changes in the design of any equipment,
--  techniques, or procedures described or referred to herein.
--  The product specifications and other technical or performance information
--  contained herein are subject to change without notice.
--  Updates of this document will be issued under the above NDA's.
--  Alcatel makes no representation or warranty, expressed or implied, with
--  respect to the sufficiency, accuracy, or utility of any information or
--  opinion contained herein. Alcatel expressly advises that any use of for 
--  any purpose or reliance upon this technical reference is at the risk of
--  the user and that Alcatel shall not be liable for any damage or injury
--  incurred by any person arising out of the sufficiency, accuracy, or
--  utility of any information or opinion contained herein.
--  This document is not to be construed as a suggestion to any manufacturer
--  to modify or change any of its products, nor does this document represent
--  any commitment by Alcatel to sell or purchase any product.
--  Nothing contained herein shall be construed as conferring by implication,
--  estoppel, or otherwise any license or right under any patent, whether or
--  not the use of any information herein necessarily employs an invention of
--  any existing or later issued patent.
--  Alcatel reserves the right not to offer any or all of these products and
--  to withdraw any or all of them at any future time.
--  Copyright (C) 2003, Alcatel. All Rights Reserved.
-- =============================================================================
--
--  MODULE-IDENTITY
--  LAST-UPDATED  Oct 4, 2016
--  ORGANIZATION "Alcatel"
--  CONTACT-INFO
--
--          Email:  asam.mibsupport@alcatel-lucent.com
--
--  DESCRIPTION "This vendor specific MIB is defined to manage 
--               the PON and ONT aspects of the Alcatel-Lucent ISAM/FTTU converged platform. " 
--  
--  REVISION 
--  DESCRIPTION
--        "Version: 3HH-08248-EFAA-PBZZA

--         Editor: Li Chengbing
--         Changes:  See below "
--  
--
-- =============================================================================
-- 
--
--
--  APON MIB HISTORY
--
--
-- Li Ya - 12/12/16:
-- For ISAM5.6.01
--
--  ALU02283589 - MII Universal BB Service: Location Config Data - OLT part
--	Added gponGISInfoGroup  OBJECT IDENTIFIER ::= { apon 33 }
--	Added gponOltGISInfoTable to the new gponGISInfoGroup.
--              - gponOltGISLng
--              - gponOltGISLat
--              - gponOltGISElev
--              - gponOltGISHrzErr
--              - gponOltGISAltErr
--              - gponOltGISAreaCode
--              - gponOltGISTimeStamp
--              - gponOltGISDigest

--  Added gponOntGISInfoTable to bponOntGroup:
--              - gponOntGISIndex
--              - gponOntGISMode
--              - gponOntGISLng
--              - gponOntGISLat
--              - gponOntGISElev
--              - gponOntGISHrzErr
--              - gponOntGISAltErr
--              - gponOntGISAreaCode
--              - gponOntGISTimeStamp
--              - gponOntGISDigest
--              - gponOntGISCheck 
--
--
-- Anitha K  10/5/16:
-- For ISAM5.6
--
-- For RCR:ALU02266265 - MIB Readiness for ALU01192932
-- Added following attributes to gponVideoAniTable
--              gponVideoAniSignalLevelMinDbm
--              gponVideoAniSignalLevelMaxDbm
--
-- Added following attributes to gponVideoAniOpInfoTable
--              gponVideoAniOpInfoOpticalSignalLevelDbm
--
-- For gponVideoAniUpperOpticalThreshold attribute in gponVideoAniTable, changed
-- default as follows:
--                 Prior to ISAM5.6 - Default = +25 = +2.5 dBm = (Coded in 2's
--                                        compliment as 0x19 for OMCI messaging)
--                 As of ISAM5.6 - Default = +10 = +1.0 dBm =  (Coded in 2's
--                                        compliment as 0x0A for OMCI messaging)
--
-- sanjeevg - 10/04/16:
-- For ISAM5.6
-- 
--   ALU01192930 - Global SSNAP Modification
--      Added the following attribute in gponUriProfileTable
--      gponUriProfileVersionNbr
--
--      Updated the description of gponUriProfileAddress
--      removed description that implies modification is not permitted
--
--
--
-- Zhang Tinghui - 6/28/16:
-- For ISAM5.5
-- 
-- ALU02238420 - MIB description BponOntPlanCardType not updated
--
-- Per Ronny KUPERS
-- modify the description of bponOntPlanCardType attribute in bponOntPlanCardTable and bponOntActualCardType attribute in bponOntActualCardTable
-- 24 = Ethernet ( Old value : 10/100 Base-T, Prior to ISAM5.2) (prior to and since FGU4.0)
--
-- Koen Decroix - 09/06/2016
-- ALU02221429 - Update the description of bponOntVoipCapability indicating that types
-- 0 and 2 are supported.

-- For RCR:ALU01856435
-- Added the following 2 attributes in bponOntTable
-- bponOntRateLimitUpstreamDhcp
-- bponOntRateLimitUpstreamArp
--
-- ALU022199997 - Voip: Mark all MEGACO and legacy related attributes as not relevant 
--               for NG-PON2:
-- Update the description of the following entries:
--    bponPotsPortVoipServiceIndex
--    bponPotsPortTerminationId
--    bponPotsPortDscpSetting
--    bponPotsPortSipMsgTimeoutTCAThreshold
--    bponPotsPortBearerPktLossTCAThreshold
--    bponPotsPortJitterTCAThreshold
--    bponPotsPortMgcConfigPointer
--    bponPotsPortVeipPointer
--
-- Update the description of the bponOntVoipCapability indicating that only standard mode 
-- is supported.
--
-- Update the description of bponOntPlanCardType indicating that as of ISAM5.4.01 
-- types 24 (i.e., 10/100 Ethernet) and 32 (i.e., POTS) are supported.
--
-- Update the description of bponOntActualCardType indicating that as of ISAM5.4.01
-- types 24 (i.e., 10/100 Ethernet) and 32 (i.e., POTS) are supported.
-- 
--
-- Guo Erjun - 17/05/16
-- For ISAM5.5.01
--
-- ALU02143020 - Flush MAC in LT FDB automatically when ONT is rebooted/power-cycled or 
--               when a UNI goes down 
--
--  Per Guo Erjun
--  Added following attribute to bponOntTable: 
--  bponOntFlushMACMode
--
-- Bao Kun - 5/23/16:
-- For ISAM5.5
--
--  ALU02143023 - CLI ONT Index Lookup Using SN
--
--      Per Bao Kun:
--      Added the following table:
--              bponOntIndexMappingTable
--
-- Koen Decroix - 02/05/2016
-- ALU02205114 - SIP Voice Support on FWLT-A (OLT part)
-- For ISAM5.4.01
-- Update table descriptions to indicate NG-PON2 support
-- bponPotsPortTable
-- gponPotsDialTestTable
-- gponPotsCallHistTable
-- gponPotsSipDialTestTable
-- gponPotsMltTestTable
-- gponPotsPortOpstatTable
-- gponPotsVoipOpstatTable
-- gponPotsCallCntlCurrentIntervalTable
-- gponPotsCallCntlIntervalTable
-- gponPotsRtpCurrentIntervalTable
-- gponPotsRtpIntervalTable
-- bponPotsPortProfileStatusTable
-- gponAuthSecurityProfileTable
-- gponAuthSecurityProfileMappingTable
-- gponSecureUriProfileTable
-- gponSecureUriProfileMappingTable
-- gponRtpProfileTable
-- gponRtpProfileMappingTable
-- gponVoipMediaProfileTable
-- gponVoipMediaProfileMappingTable
-- gponTonePatternProfileMappingTable
-- gponTonePatternProfileTable
-- gponToneSequenceProfileTable
-- gponToneSequenceProfileMappingTable
-- gponToneEventProfileTable
-- gponToneEventProfileMappingTable
-- gponRingPatternProfileTable
-- gponRingPatternProfileMappingTable
-- gponRingSequenceProfileTable
-- gponRingSequenceProfileMappingTable
-- gponRingEventProfileTable
-- gponRingEventProfileMappingTable
-- gponVoiceServiceProfileTable
-- gponVoiceServiceProfileMappingTable
-- gponSipMsgProfileTable
-- gponSipMsgProfileMappingTable
-- gponNetDialPlanProfileTable
-- gponNetDialPlanProfileMappingTable
-- gponVoipAppServProfileTable
-- gponVoipAppServProfileMappingTable
-- gponVoipFeatAccessCodeProfileTable
-- gponVoipFeatAccessCodeProfileMappingTable
-- gponUriProfileTable
-- gponUriProfileMappingTable
-- gponVoipServiceOpInfoTable
-- gponVoipServiceOntsideGemCurrentIntervalTable
-- gponVoipServiceOntsideGemIntervalTable
-- gponVoipServiceOltsideGemCurrentIntervalTable
-- gponVoipServiceOltsideGemIntervalTable
-- gponOntIpHostTable
-- gponOntIpHostOpInfoTable
-- gponOntIpHostPingTestTable
-- gponIpHostCurrentIntervalTable
-- gponIpHostIntervalTable
-- gponOntVoipConfigTable
-- gponOntVoipConfigOpInfoTable
-- gponOntSipConfigTable
-- gponOntSipConfigOpInfoTable
-- gponOntSipCurrentIntervalTable
-- gponOntSipIntervalTable
-- gponOntSipCallInitCurrentIntervalTable
-- gponOntSipCallInitIntervalTable
--
--
-- Xu Xinde - 01/13/16:
-- For ISAM5.4.01
-- ALU02124533 - FWLT-A LOID ONU authentication
-- For bponOntLogicalAuthID and bponOntLogicalAuthPassword attribute in bponOntTable, modify descriptions to point out that from ISAM5.4.01, only MIB is ready. From ISAM5.5, LOID Auth is supported for NG-PON2
-- For bponPonDiscovOntLogicalAuthId attribute in bponPonDiscovOntTable, modify descriptions to point out that from ISAM5.4.01, only MIB is ready. From ISAM5.5, LOID Auth is supported for NG-PON2

-- Chen Xinfei - 12/11/15:
-- For ISAM5.4.01
-- ALU02086825 - GPON/NGPON2 NNI extensions - Inc.1
-- Added following attributes to bponOntPlanCardTable
-- bponOntPlanCardNoMulticastControl
--
--
-- Li Chengbing - 9/21/15:
-- For ISAM5.4
--
-- ALU01959379 - Support of AIS on ONT UNI (OLT part)
--
-- Per Zhu Cuiping
-- Add bponLanEtherPortShutdownAIS in bponLanEtherPortTable
--
--
--
-- Tinghui Zhang - 6/19/15:
-- For ISAM5.3.01
--
--  ALU02060085 - Individual HGU configuration via OLT without TR69 ACS via SNMP/OMCI
--        Alarms (OLT part)
--
--  Per Tinghui Zhang:
--  Added the following table:
--     gponHGUTR069CustomizedAlarmTable 
--
--
--
-- John Boyle - 5/21/15:
-- For ISAM5.3
--
-- ALU01986788 - Completion of PON Utilization and Threshold (FWLT-A Part)
--
-- 	For gponOltSideOntUtilPmIntervalEntry definition in gponOltSideOntUtilPmIntervalTable,
--	clarified the following:
-- 		Third index pmIntervalNum range is 1..288
--
--	For following 'upstream oriented' attributes:
--		>> gponOltSidePonUtilRxPmCurrentIntervalTotalUtil 
--		>> gponOltSidePonUtilRxPmCurrentIntervalTotalBytes
--		>> gponOltSidePonUtilRxPmCurrentIntervalTotalPackets
--		>> gponOltSidePonUtilRxPmIntervalTotalUtil
--		>> gponOltSidePonUtilRxPmIntervalTotalBytes
--		>> gponOltSidePonUtilRxPmIntervalTotalPackets
--		>> gponOltSideOntUtilPmCurrentIntervalRxUcastBytes
--		>> gponOltSideOntUtilPmCurrentIntervalRxUcastPackets
--		>> gponOltSideOntUtilPmIntervalRxUcastBytes
--		>> gponOltSideOntUtilPmIntervalRxUcastPackets
--		>> gponOltSideOntUtilBulkPmIntervalRxUcastBytes
--		>> gponOltSideOntUtilBulkPmIntervalRxUcastPackets
--			>>>> changed descriptions FROM >> TO for either or both of the following:
--				FROM: (unicast + multicast + broadcast)
--				TO:   (on unicast GEM ports)
--				FROM: downstream
--				TO:   upstream
--
--
--
-- John Boyle - 5/20/15:
-- (per Erjun Guo)
--
-- FR ALU02054751 - Unable to associate RSSI profile ranging from 1 to 20 on GPON/NGPON2 ONT ANI 
--
--	For gponOntAniRSSIProfileId attribute in gponOntAniTable, changed range as follows:           
--		Prior to ISAM5.3, the range of profile is 0 and 21..200.
--	        As of ISAM5.3, the range of profile is 0..200.
--
--
--
-- John Boyle - 5/5/15:
--
-- Carried forward from ISAM5.2
-- ALU01848928 - PON Utilization & Thresholds
--
--	For gponSysOltSidePonUtilHighThresholdLevelDown SCALAR attribute, changed the commentary 
--	regarding the measurement:
--		FROM >> total downstream non-multicast (i.e. unicast + broadcast) traffic.
--		TO >>  total downstream traffic
--
--
-- ALU01862953 - NGPON2 TWDM LT first 4-port version (FWLT-A)
--
--	For gponOntSwDownldStatusTable, change the up-front commentary regarding support timeframe;
--		FROM >> For NG-PON2 - NOT SUPPORTED as of ISAM5.2
--		TO >> NG-PON2 - SUPPORTED as of ISAM5.3 (CfgFile1 and CfgFile2 are NOT SUPPORTED as of ISAM5.2)
--
--  
--
-- John Boyle - 4/27/15:
-- For ISAM5.3
--
--  ALU02047957 - Individual HGU configuration via OLT without TR69 ACS via SNMP/OMCI
--		  Provisioning (OLT part)
--
--	Per Tinghui Zhang:
--	For following attributes in gponHGUTR069LKeyProvisionTable, changed max size
--	FROM (SIZE(0..256)) TO (SIZE(0..255))
--		gponHGUTR069LKeyProvisionParamName
--		gponHGUTR069LKeyProvisionParamValue
--
--
-- John Boyle - 4/21/15:
-- For ISAM5.3
--
-- ALU02025800 - Allow GPON ONUs to range in the presence of Alien ONUs
--
--	Per Li Jian
--	Added following SCALAR:	gponOltRangeMode  { gponOltGroup 48 } 
--
--
--
-- John Boyle - 4/16/15:
-- For ISAM5.3
--
--  ALU02047957 - Individual HGU configuration via OLT without TR69 ACS via SNMP/OMCI
--		  Provisioning (OLT part)
--
--	Per Tinghui Zhang:
--	Added the following tables:
--		gponHGUTR069SKeyProvisionTable
--		gponHGUTR069LKeyProvisionTable
--
--
--
--  For SCALAR: gponOltPowerBurstDetectMode,
--  Changed applicability, such that for NG-PON2 it is NOT SUPPORTED.
--
--
-- John Boyle - 3/19/15:
-- For ISAM5.2
--
--  For SCALAR: gponOltPowerBurstDetectMode,
--  Changed applicability, such that for NG-PON2 it is NOT SUPPORTED.
--	For GPON - SUPPORTED as of ISAM4.0.10
--	For XG-PON1 - SUPPORTED as of ISAM4.6.02
--	For NG-PON2 - NOT SUPPORTED as of ISAM5.2 
--
--
--  Deleted following SCALAR: gponOltRangeMode  { gponOltGroup 48 }  
--  Because it is only applicable as of ISAM5.3
--
--
--
-- John Boyle - 3/17/15:
-- For ISAM5.2
--
--  RCR ALU01893430 - Detection of ALIEN ONU on GPON 
--
--	Added following SCALAR:	gponOltRangeMode  { gponOltGroup 48 }  
--
--
--
-- John Boyle - 3/5/15:
-- For ISAM5.2
--
-- ALU01862953 - NGPON2 TWDM LT first 4-port version (FWLT-A)
--
-- For bponPonStatsBerTable and bponPonStatsBerResetTable,
-- noted that entire tables are NOT SUPPORTED for NG-PON2.
--
--	For GPON - SUPPORTED as of ISAM4.0.10 (for PONs)
--	For XG-PON1 - SUPPORTED as of ISAM4.6.02
--	For NG-PON2 - NOT SUPPORTED as of ISAM5.2
-- 
-- 
--
--
-- John Boyle - 2/25/15:
-- For ISAM5.2
--
-- ALU01862953 - NGPON2 TWDM LT first 4-port version (FWLT-A)
--
-- 	Since NG-PON2 has capability to operate at multiple wavelengths, removed legacy commentary
--	that implied merely 1310 and 1490 nm wavelengths (i.e. the GPON wavelengths). Following
--	attributes have updated commentary:
--		gponOntAniLowerOpticalThreshold
--		gponOntAniUpperOpticalThreshold
--		gponOntAniOpInfoOpticalSignalLevel
--		gponOntOpticSupDailyOntsideRxOpticalSignalLevel
--		gponOntOpticSupDailyOltsideTxOpticalSignalLevel
--		gponPonOltsideOpInfoTxOpticalSignalLevel
--		gponPonOltsideOpTxLowerThreshold
--		gponPonOltsideOpTxUpperThreshold
--		gponOntAniTxLowerOpticalThreshold
--		gponOntAniTxUpperOpticalThreshold
--		gponOntAniOpInfoTxOpticalSignalLevel
--		gponOntOltsideOpInfoRxOpticalSignalLevel
--		gponOntOpticSupDailyOntsideTxOpticalSignalLevel
--		gponOntOpticSupDailyOltsideRxOpticalSignalLevel
--
--
--
-- Karel Meijfroidt - 2/24/15:
-- For ISAM5.2
--
-- ALU02052944 - Issue with gponPonOltsideOpInfoSpecialFeatures for NGPON2
--
--      Extended the MIB description of the gponPonOltsideOpInfoSpecialFeatures
--      with the values that can be retrieved from XFP's
--
--
--
-- John Boyle - 2/15/15:
-- For ISAM5.2
--
-- ALU01885465 - OMCI Pre-Configuration download for Residential Gateway
--
--	For following SCALARs and attributes in following tables, updated all descriptions
--	to convey that above feature is NOT SUPPORTED for NG-PON as of ISAM5.2:
--
-- 		Following attributes in bponOntTable:
--			bponOntPlannedCfgFile1	
--			bponOntDownloadCfgFile1	
--			bponOntPlannedCfgFile2	
--			bponOntDownloadCfgFile2	
--			bponOntCfgFile1Active	
--			bponOntCfgFile1Passive	
--			bponOntCfgFile2Active	
--			bponOntCfgFile2Passive
--
--		gponOntSwVerCtlTable 
--		gponOntSwVerCtlIndexNext
--		gponOntSwVerCtlReferencedRow
--		gponOntSwVerCtlRefOntTable
--		gponOntSwVerInfoTable
--		gponOntSwVerDeleteCmd
--		gponOntSwVerDeleteCmdStatus
--		gponOntSwDownldStatusTable
--		gponPonOntSwDownldStatusTable
--
--
-- ALU01862953 - NGPON2 TWDM LT first 4-port version (FWLT-A)
--
--	For bponOntFecUpstreamInd attribute in bponOntTable,
--	updated differing defaults as follows:
--		 For GPON:	Default = 2 = Disable
--		 For XG-PON1:	Default = 2 = Disable
--		 For NG-PON2: 	Default = 1 = Enable
--		
--
--
--
--
-- John Boyle - 2/10/15:
-- For ISAM5.2
--
-- ALU01986788 - Completion of PON Utilization and Threshold (FWLT-A Part)
--
--	Commitment of this RCR was recently changed FROM Release 5.1.01 TO Release 5.3,
--	For all affected attributes, changed commentary as follows:
--		FROM: For NG-PON2 - SUPPORTED as of ISAM5.2.01 (for channel pairs)
--		TO: For NG-PON2 - NOT SUPPORTED as of ISAM5.2.01 (for channel pairs)
--
--
--
-- John Boyle - 1/29/15:
-- For ISAM5.2
--
-- RCR ALU01848928 - PON Utilization & Thresholds
--
--	For following attributes, changed lower end of range FROM 1 TO 0:
--	- gponSysOltSidePonUtilDbaCongestionThreshold SCALAR
--	- gponOltSidePonUtilDbaCongestionThreshold attribute in gponOltSidePonUtilTCAThresholdTable
--
-- John Boyle - 1/15/15:
-- For ISAM5.2
--
-- RCR ALU01848928 - PON Utilization & Thresholds
--
--	For all "utilization percentage" attributes in the following tables,
--	clarified the traffic composition of the denominators:
--		> gponOltSidePonUtilTxPmCurrentIntervalTable  
--		> gponOltSidePonUtilTxPmIntervalTable 
--		> gponOltSidePonUtilTxOntPmCurrentIntervalTable 
--		> gponOltSidePonUtilTxOntPmIntervalTable
--
-- John Boyle - 1/14/15:
-- For ISAM5.2
--
-- RCR ALU01848928 - PON Utilization & Thresholds
--
--	For the following attributes:
--		> gponOltSidePonUtilTxPmCurrentIntervalUcastUtil 
--		> gponOltSidePonUtilTxPmCurrentIntervalBcastUtil 
--		> gponOltSidePonUtilTxPmIntervalUcastUtil 
--		> gponOltSidePonUtilTxPmIntervalBcastUtil 
--		> gponOltSidePonUtilTxOntPmCurrentIntervalUtil 
--		> gponOltSidePonUtilTxOntPmIntervalUtil
--
--	Increased their upper range FROM 10000 (100.00%) TO 100000 (1000.00%),
--	And noted the following as the reason for this oddity:
--		The utilization percentage can exceed 100% because the denominator is the non-multicast BW of the PON
--		(calculated as the max PON BW less that reserved for multicast in the QOS cac-profile), 
--		yet the unicast (and broadcast) traffic can use the BW reserved for multicast if it is available. 
-- 
--
--
-- John Boyle - 12/18/14:
-- For ISAM5.2
--
-- ALU01961528 - OLT configuration for ONT policer
--
--	Added bponOntTcPoliceMode attribute to bponOntTable
--
--
-- John Boyle - 12/12/14:
-- For ISAM5.2
--
-- Undid everything I had previously done below 3 days ago on 12/9/14.  
--	GPON-MIB PON Utilization SCALARs are again shared by PONs (in R5.2) and channel-pairs (in R5.2.01)
--	Made this fact clear in description portions of the various SCALAR attributes.
--
--
-- John Boyle - 12/9/14:
-- For ISAM5.2
--
-- ALU01986788 - Completion of PON Utilization and Threshold (FWLT-A Part)
--
--	For gponOltSidePonUtilHighTCAEnable attribute in gponOltSidePonUtilThresholdTable, modified as follows:
--		This attribute is used choose whether/how TCA alarms are enabled for this PON/channel-pair.
--		A value of 1 means that TCA alarms are enabled for this PON/channel pair.
--	        A value of 2 means that TCA alarms are disabled for this PON/channel-pair.
--		A value of 3 means - INHERIT - Inherits the system-wide TCA setting for the BW Utilization TCAs.  
--			As of ISAM5.2, the value 3 is SUPPORTED for PONs.
--			As of ISAM5.2.01, the value 3 is NOT SUPPORTED for channel-pairs.
--
--		Default = 3 INHERIT (for PONs)
--		Default = 2 DISABLED (for channel-pairs) 
--
--		For GPON - SUPPORTED as of ISAM5.2	
--		For XG-PON1 - NOT SUPPORTED as of ISAM4.6.02	
--		For NG-PON2 - SUPPORTED as of ISAM5.2.01 (see above exceptions between PONs and channel-pairs)
--
--	For following SCALARs, noted For NG-PON2 - NOT SUPPORTED as of ISAM5.2.01 (for channel pairs)
--		gponSysOltSidePonUtilPmCollectInd {gponOltGroup 17}
--		gponSysOltSidePonUtilHighTcaEnable {gponOltGroup 18}
--		gponSysOltSidePonUtilHighThresholdLevelDown {gponOltGroup 19}
--		gponSysOltSidePonUtilHighThresholdLevelUp {gponOltGroup 20}
--		gponSysOltSidePonMcastUtilHighThresholdLevelDown {gponOltGroup 21}
--		gponSysOltSidePonUtilHighThresholdDBACongestionUp {gponOltGroup 22}
--		gponSysOltSidePonUtilNumTcIntervals {gponOltGroup 23}
--		gponSysOltSidePonUtilHighThresholdTxUcastDroppedPackets	{gponOltGroup 24}
--		gponSysOltSidePonUtilHighThresholdRxUcastDroppedPackets	{gponOltGroup 25}
--		gponSysOltSidePonUtilHighThresholdTxMcastDroppedPackets	{gponOltGroup 26}
--		gponSysOltSidePonUtilHighThresholdTxBcastDroppedPackets {gponOltGroup 27}
--		gponSysOltSidePonUtilMediumThresholdLevelDown {gponOltGroup 28}
--		gponSysOltSidePonUtilMediumThresholdLevelUp {gponOltGroup 29}
--	    	gponSysOltSidePonMcastUtilMediumThresholdLevelDown  {gponOltGroup 30}	
--	    	gponSysOltSidePonUtilMediumThresholdDBACongestionUp   {gponOltGroup 31}
--		gponSysOltSidePonUtilMediumThresholdTxUcastDroppedPackets {gponOltGroup 32}
--		gponSysOltSidePonUtilMediumThresholdRxUcastDroppedPackets {gponOltGroup 33}
--		gponSysOltSidePonUtilMediumThresholdTxMcastDroppedPackets {gponOltGroup 34}
--		gponSysOltSidePonUtilMediumThresholdTxBcastDroppedPackets {gponOltGroup 35}
--		gponSysOltSidePonUtilLowThresholdLevelDown {gponOltGroup 36}
--		gponSysOltSidePonUtilLowThresholdLevelUp {gponOltGroup 37}
--	    	gponSysOltSidePonMcastUtilLowThresholdLevelDown {gponOltGroup 38}
--	    	gponSysOltSidePonUtilLowThresholdDBACongestionUp  {gponOltGroup 39}
--		gponSysOltSidePonUtilLowThresholdTxUcastDroppedPackets	{gponOltGroup 40}
--		gponSysOltSidePonUtilLowThresholdRxUcastDroppedPackets	{gponOltGroup 41}
--		gponSysOltSidePonUtilLowThresholdTxMcastDroppedPackets	{gponOltGroup 42}
--		gponSysOltSidePonUtilLowThresholdTxBcastDroppedPackets {gponOltGroup 43}
--		gponSysOltSidePonUtilDbaCongestionThreshold {gponOltGroup 44}
--		gponSysOltSidePonUtilNumDbaTcIntervals {gponOltGroup 45}
--		gponSysOltsidePonUtilOntDetailSelector {gponOltGroup 46}
--
--
--
-- John Boyle - 12/4/14:
-- For ISAM5.2
--
-- For gponPonTrafficTcaInterval SCALAR attribute, changed to say following:
--	For NG-PON2 - NOT SUPPORTED as of ISAM5.2 (for channel pairs)  
--	Instead added counterpart SCALAR in ng-pon2 MIB (for channel-pairs)
--
-- For gponOltSidePonUtilHighTCAEnable attribute gponOltSidePonUtilTCAThresholdTable
--	Changed from NOT SUPPORTED to following:
--		For GPON - SUPPORTED as of ISAM5.2	
--		For XG-PON1 - NOT SUPPORTED as of ISAM4.6.02	
--		For NG-PON2 - SUPPORTED as of ISAM5.2.01 
--
-- For following attributes, clarified their descriptions as follows:
--	The percentage of actual congestion within a DBA grant window wherein
--	the system declares a congested window. NOTE: This window is NOT the	
--	same as the 5-minute PM/TCA periods.
--		gponOltSidePonUtilDbaCongestionThreshold
--		gponSysOltSidePonUtilDbaCongestionThreshold
--
-- For following TCA attributes, clarified their percentage meanings as follows:
--	This percentage is in relationship to the 5-minute PM/TCA interval.
--		gponOltSidePonUtilHighThresholdDBACongestionUp
--		gponOltSidePonUtilMediumThresholdDBACongestionUp
--		gponOltSidePonUtilLowThresholdDBACongestionUp
--		gponSysOltSidePonUtilHighThresholdDBACongestionUp
--		gponSysOltSidePonUtilMediumThresholdDBACongestionUp
--		gponSysOltSidePonUtilLowThresholdDBACongestionUp
--
--
-- John Boyle - 11/7/14:
-- For ISAM5.2
--
-- ALU01862953 - NGPON2 TWDM LT first 4-port version (FWLT-A)
--
--	For following tables and SCALARs, clarified their application 
--	and release SUPPORT requirements for PONs (for GPON) and 
--	channel-pairs (for NG-PON2).
--  
--	For tables that have PON ifIndexes (for GPON), clarified that the 
--	same OID can represent a channel-pair (for NG-PON2).
--
--	For PM tables that are instantiated via a 'collect indicator',
--	clarified when the collect indicator is in this GPON MIB (for PONs) or
--	in NG-PON2 MIB (for channel-pairs).
--
--	******** TABLES **************
--		bponPonDiscovOntTable
--		bponPonStatsBerTable
--		bponPonStatsBerResetTable
--		gponPonAggGemCurrentIntervalTable
--		gponPonAggGemIntervalTable
--		gponPonAggGemTCAThresholdIndex
--		gponPonOltsideOpInfoIndex
--		gponPonOltsideFecCurrentIntervalTable
--		gponPonOltsidePhyCurrentIntervalTable
--		gponPonOltsideXgTcCurrentIntervalTable
--		gponPonOltsideXgTcIntervalTable
--		gponOltSidePonUtilTCAThresholdTable
--		gponOltSidePonUtilStatsResetTable
--		gponMulticastServiceOltsideGemCurrentIntervalPonTable
--		gponMulticastServiceOltsideGemIntervalPonTable
--		gponOltsidePonPortTroubleshootCounterTable
--		gponOltSidePonUtilPmCurrentIntervalTable
--		gponOltSidePonUtilPmIntervalTable
--		gponOltSidePonUtilTxOntPmCurrentIntervalTable
--		gponOltSidePonUtilTxOntPmIntervalTable
--		gponOltSidePonUtilRxOntPmCurrentIntervalTable
--		gponOltSidePonUtilRxOntPmIntervalTable
--		gponOltSideOntUtilPmCurrentIntervalTable
--		gponOltSideOntUtilPmIntervalTable
--		gponOltSideOntUtilBulkPmIntervalTable
--
--	******** SCALARS **************
--		gponPonTrafficTcaInterval {gponOltGroup 15}
--		gponSysOltSidePonUtilPmCollectInd {gponOltGroup 17}
--		gponSysOltSidePonUtilHighTcaEnable {gponOltGroup 18}
--		gponSysOltSidePonUtilHighThresholdLevelDown {gponOltGroup 19}
--		gponSysOltSidePonUtilHighThresholdLevelUp {gponOltGroup 20}
--		gponSysOltSidePonMcastUtilHighThresholdLevelDown {gponOltGroup 21}
--		gponSysOltSidePonUtilHighThresholdDBACongestionUp {gponOltGroup 22}
--		gponSysOltSidePonUtilNumTcIntervals {gponOltGroup 23}
--		gponSysOltSidePonUtilHighThresholdTxUcastDroppedPackets	{gponOltGroup 24}
--		gponSysOltSidePonUtilHighThresholdRxUcastDroppedPackets	{gponOltGroup 25}
--		gponSysOltSidePonUtilHighThresholdTxMcastDroppedPackets	{gponOltGroup 26}
--		gponSysOltSidePonUtilHighThresholdTxBcastDroppedPackets {gponOltGroup 27}
--		gponSysOltSidePonUtilMediumThresholdLevelDown {gponOltGroup 28}
--		gponSysOltSidePonUtilMediumThresholdLevelUp {gponOltGroup 29}
--	    	gponSysOltSidePonMcastUtilMediumThresholdLevelDown  {gponOltGroup 30}	
--	    	gponSysOltSidePonUtilMediumThresholdDBACongestionUp   {gponOltGroup 31}
--		gponSysOltSidePonUtilMediumThresholdTxUcastDroppedPackets	{gponOltGroup 32}
--		gponSysOltSidePonUtilMediumThresholdRxUcastDroppedPackets	{gponOltGroup 33}
--		gponSysOltSidePonUtilMediumThresholdTxMcastDroppedPackets	{gponOltGroup 34}
--		gponSysOltSidePonUtilMediumThresholdTxBcastDroppedPackets {gponOltGroup 35}
--		gponSysOltSidePonUtilLowThresholdLevelDown {gponOltGroup 36}
--		gponSysOltSidePonUtilLowThresholdLevelUp {gponOltGroup 37}
--	    	gponSysOltSidePonMcastUtilLowThresholdLevelDown {gponOltGroup 38}
--	    	gponSysOltSidePonUtilLowThresholdDBACongestionUp  {gponOltGroup 39}
--		gponSysOltSidePonUtilLowThresholdTxUcastDroppedPackets	{gponOltGroup 40}
--		gponSysOltSidePonUtilLowThresholdRxUcastDroppedPackets	{gponOltGroup 41}
--		gponSysOltSidePonUtilLowThresholdTxMcastDroppedPackets	{gponOltGroup 42}
--		gponSysOltSidePonUtilLowThresholdTxBcastDroppedPackets {gponOltGroup 43}
--		gponSysOltSidePonUtilDbaCongestionThreshold	{gponOltGroup 44}
--		gponSysOltSidePonUtilNumDbaTcIntervals	{gponOltGroup 45}
--		gponSysOltsidePonUtilOntDetailSelector	{gponOltGroup 46}
--
-- 
--	For following tables, indicated in intro description that these tables are
--	collected on a 5-minute PM cycle:
--		gponOltSidePonUtilPmCurrentIntervalTable
--		gponOltSidePonUtilPmIntervalTable
--		gponOltSidePonUtilTxOntPmCurrentIntervalTable
--		gponOltSidePonUtilTxOntPmIntervalTable
--		gponOltSidePonUtilRxOntPmCurrentIntervalTable
--		gponOltSidePonUtilRxOntPmIntervalTable
--		gponOltSideOntUtilPmCurrentIntervalTable
--		gponOltSideOntUtilPmIntervalTable
--		gponOltSideOntUtilBulkPmIntervalTable
--
--
--
-- John Boyle - 11/3/14:
-- For ISAM5.2
--
-- ALU01862953 - NGPON2 TWDM LT first 4-port version (FWLT-A)
--
-- 	For gponPonOntSwDownldStatusTable, changed to say following:
--		For NG-PON2 - NOT SUPPORTED as of ISAM5.2
--  
-- *********************************************
--
--
-- John Boyle - 10/22/14:
-- For ISAM5.2
--
-- ALU01917971 - Selective Behavior for ONT Service Continuity Relative to SW Planning
--
--	Added following system SCALAR:
--		ponSysOntSwVerMismatchTrafficBlockSelector {gponOltGroup 47}
--
--
-- ALU01862953 - NGPON2 TWDM LT first 4-port version (FWLT-A)
--
-- 	In intro description of gponOntOltsideAggGemTCAThresholdTable, 
-- 	changed as follows (difference being that table is NOT SUPPORTED for XG-PON1):
--
--		For GPON - SUPPORTED as of ISAM4.0.10
--		For XG-PON1 - NOT SUPPORTED as of ISAM4.6.02
--		For NG-PON2 - SUPPORTED as of ISAM5.2 
-- 
--
--
-- John Boyle - 10/6/14:
-- For ISAM5.2
--
-- ALU01862953 - NGPON2 TWDM LT first 4-port version (FWLT-A)
--
--	In order to correct my own typo, changed the following attributes in the following tables
--	to say SUPPORTED as follows:
--	
--		bponOntOntsideXgTcPmNumPMIntervals in bponOntTable:
--			For GPON - NOT SUPPORTED as of ISAM4.6 
--			For XG-PON1 - SUPPORTED as of ISAM4.6.02 
--			For NG-PON2 - SUPPORTED as of ISAM5.2 
--		bponOntOltsideXgTcPmNumPMIntervals in bponOntTable:
--			For GPON - NOT SUPPORTED as of ISAM4.6 
--			For XG-PON1 - SUPPORTED as of ISAM4.6.02 
--			For NG-PON2 - SUPPORTED as of ISAM5.2 
--		bponPonConfigOltsideXgTcPmNumPMIntervals
--			For GPON - NOT SUPPORTED as of ISAM4.6
--			For XG-PON1 - SUPPORTED as of ISAM4.6.02
--			For NG-PON2 - NOT SUPPORTED as of ISAM5.2 
--				(similar attribute SUPPORTED in ng2ChanPairConfigTable of NG-PON2 MIB)
--
--
--
-- John Boyle - 9/30/14:
-- For ISAM5.2
-- (Carried forward from ISAM5.1.01)
--
-- RCR ALU02014776 - Add new values to VOIP Voice Server Status in OLT
--
--	Added following codepoint to gponPotsVoipOpstatVoiceServerStatus attribute
--	in gponPotsVoipOpstatTable:
--		15 = Disabled by Switch
--
--
-- John Boyle - 9/17/14:
-- For ISAM5.2
--
-- ALU01862953 - NGPON2 TWDM LT first 4-port version (FWLT-A)
--
--	For bponOntAesMode attribute in bponOntTable, noted the following qualification applies to NGPON2 as well:
--		NOTE: When the type of PON for this ONT is XGPON or NGPON2 (determined from LT card type), then the setting
--		of this attribute only applies to downstream traffic associated with bi-directionl GEM ports.
--		For XGPON and NGPON2, the setting for upstream traffic is determined from bponOntUpEncryptMode attribute.
--		Also, for XGPON and NGPON2 modes, modification is SUPPORTED but only if ONT is Admin Down.
--
-- 
--
-- ALU01862953 - NGPON2 TWDM LT first 4-port version (FWLT-A)
--
-- John Boyle - 9/5/14:
-- For ISAM5.2
--
-- ALU01862953 - NGPON2 TWDM LT first 4-port version (FWLT-A)
--
--	For bponOntSubscriberLocId attribute in bponOntTable, mentioned following: 
--		As of ISAM5.2, the SIZE of this attribute was expanded from 
--		12 bytes to 36 bytes, in order to also accommodate the 
--		36 byte Registration ID for NG-PON2 as defined in G989.3
--
--	For following attributes, mentioned that For NG-PON2 - NOT SUPPORTED as of ISAM5.2
--		 bponOntLogicalAuthID attribute in bponOntTable
--		 bponOntLogicalAuthPassword attribute in bponOntTable
--
--	For bponPonDiscovOntSubsLocId attribute in bponPonDiscovOntTable, mentioned the following:
--		As of ISAM5.2, the SIZE of this attribute was expanded from 
--		10 bytes to 36 bytes, in order to also accommodate the 
--		36 byte Registration ID for NG-PON2 as defined in G989.3
--
--	For following attributes, mentioned that For NG-PON2 - NOT SUPPORTED as of ISAM5.2
--		bponPonDiscovOntLogicalAuthID attribute in bponPonDiscovOntTable
--
--	For gponOltSlidInterpretationMode SCALAR, mentioned that attribute is also
--	relevant for NG-PON2 Registration ID 
--
--
--
-- John Boyle - 8/15/14:
-- For ISAM5.2
--
-- ALU01885465 - OMCI Pre-Configuration download for Residential Gateway
-- (per recommendations for Qiang HE)
--
--	Mentioned that status Bit 18 = 'DELAYACTIVATE activity is Pending' is NOT SUPPORTED - always 0, 
--	for following attributes in following tables:
--		In gponOntSwDownldStatusTable:
--			gponOntCfgFile1DownldStatus
--			gponOntCfgFile2DownldStatus
--		In gponPonOntSwDownldStatusTable:
--			gponPonOntCfgFile1DownldStatus
--			gponPonOntCfgFile2DownldStatus
--
-- RCR ALU01848928 - PON Utilization & Thresholds
--
--	For gponOltSidePonUtilStatsResetTrigger attribute in gponOltSidePonUtilStatsResetTable, added the following:
--		 The only valid SET for this attribute is the value = 1 (meaning to trigger the reset action).
--		 For GET, GET-NEXT, the agent can return value 0 (which is meaningless, since this attribute is 
--		 really intended to be a trigger, and manager obtains no useful information from a GET).
--		 Default = 0
--
--
--
-- John Boyle - 8/14/14:
-- For ISAM5.2
--
-- RCR ALU01885465 - OMCI Pre-Configuration download for Residential Gateway
-- (per recommendations for Qiang HE)
--
--	Everywhere, changed partial name sections of all relevant attributes (see 8/1/14 history):
--		FROM: PrimaryCfgFile    TO: CfgFile1
--		FROM: SecondaryCfgFile	TO: CfgFile2
--
--	Added status Bit 19 = 'Download Activity is Pending' to following attributes in following tables:
--		In gponOntSwDownldStatusTable:
--			gponOntSwDownldStatus
--			gponOntCfgFile1DownldStatus
--			gponOntCfgFile2DownldStatus
--		In gponPonOntSwDownldStatusTable:
--			gponPonOntSwDownldStatus
--			gponPonOntCfgFile1DownldStatus
--			gponPonOntCfgFile2DownldStatus
--
-- John Boyle - 8/1/14:
-- For ISAM5.2
--
-- RCR ALU01885465 - OMCI Pre-Configuration download for Residential Gateway
-- (per recommendations for Qiang HE)
--
--	Added following attributes to bponOntTable:
--		bponOntPlannedPrimaryCfgFile	
--		bponOntDownloadPrimaryCfgFile	
--		bponOntPlannedSecondaryCfgFile	
--		bponOntDownloadSecondaryCfgFile	
--		bponOntPrimaryCfgFileActive	
--		bponOntPrimaryCfgFilePassive	
--		bponOntSecondaryCfgFileActive	
--		bponOntSecondaryCfgFilePassive
--
--	Added following attributes to gponOntSwVerCtlTable:
--		gponOntSwVerCtlPlannedPrimaryCfgfile
--		gponOntSwVerCtlDownloadPrimaryCfgfile
--		gponOntSwVerCtlPlannedSecondaryCfgfile
--		gponOntSwVerCtlDownloadSecondaryCfgfile
--
--	Added following attributes to gponOntSwDownldStatusTable:
--		gponOntPriCfgDownldStatus
--		gponOntSecCfgDownldStatus
--
--	Added following attributes to gponPonOntSwDownldStatusTable:
--		gponPonOntPriCfgDownldStatus
--		gponPonOntSecCfgDownldStatus
--
--	For following tables/SCALARs, mentioned that as of ISAM5.2 they apply for
--	primary and secondary config files:
--		gponOntSwVerInfoTable
--		gponOntSwVerDeleteCmd
--		gponOntSwVerDeleteCmdStatus
--
--
--
-- John Boyle - 7/30/14:
-- For ISAM5.2
--
-- RCR ALU01976945 - PON-ID Maintenance for GPON
-- (per recommendations for TU Ming)
--
--	Added following attributes to bponPonConfigTable:
--		bponPonConfigPonIdInterval	
--		bponPonConfigPonIdOdnClass	
--		bponPonConfigPonIdIdentifier	
--
--
-- John Boyle - 7/24/14:
-- For ISAM5.2
--
--  RCR ALU01893430 - Detection of ALIEN ONU on GPON 
--  (per recommendations from Yao Liqiang)
--
--	Added following attributes to bponPonConfigTable:
--		bponPonConfigAlienTestCmd
--		bponPonConfigBkgdAlienTestCmd	
--		bponPonConfigBkgdAlienTestInterval	
--
--
--
-- John Boyle - 6/30/14:
-- (Carried forward from ISAM5.1.01)
--
--  RCR ALU01962351: Adding VOIP Line Status support (OLT part) 
--
--	Added following attribute to gponPotsVoipOpstatTable:
--		- gponPotsVoipOpstatVoiceLineStatus
--
--
-- John Boyle - 6/24/14:
-- For ISAM5.2
--
--  (Carried forward from ISAM5.1)
--  RCR ALU01951611 : G.988 OMCIv2 provision H.248 MG domain name per ONT
--
--	This FR/RCR was not included in ISAM5.1 roadmap. So commented out
--	gponOntMgcConfigMessageIdStr attribute in gponOntMgcConfigTable as NOT SUPPORTED.
--
--
-- ALU01848928 - PON Utilization & Thresholds
--
--	Renamed a SCALAR
--		FROM:	bponSysOltsidePonUtilOntDetailSelector
--		TO:	gponSysOltsidePonUtilOntDetailSelector
--
--
--
-- John Boyle - 6/10/14:
-- For ISAM5.2
--
-- ALU01848928 - PON Utilization & Thresholds
--
--	Added following SCALARS to delineate PON ifindex and ONT if Index
--		 ponIfIndex and ontIfIndex
--	Modified following tables to utilize these indexes:
--		 gponOltSideOntUtilPmCurrentIntervalTable
--		 gponOltSideOntUtilPmIntervalTable
--		 gponOltSideOntUtilBulkPmCurrentIntervalTabl
--	Added following attribute to bponOntTable:
--		 bponOntOltsidePonUtilPmNumPMIntervals
--
--
-- ALU01926856 - N:P OMCI Management Model for CMCC
--
--	For bponOntVlanBridgeMappingMode attribute in bponOntTable:
--		Removed the superflous language regarding 'limit functionity'
--		for N:p and N:MP modes.
--
--
-- John Boyle - 6/6/14:
-- For ISAM5.2
--
--
-- ALU01848928 - PON Utilization & Thresholds
--
-- In both gponOltSideOntUtilPmCurrentIntervalTable and gponOltSideOntUtilPmIntervalTable:
--	Added another ifIndex as an index to table indexes, with following comment:
-- 		First ifIndex is the ifIndex of either a PON or a channel-pair
-- 		Second ifIndex is the ifIndex of the ONT
--	NOTE:  This was done for read efficiency, since for NG-PON2, the ifindex of the ONT
--		is not structured to contain the associated channel pair.
--
--	Added bponPonConfigPonUtilOntBulkDetailSelector attribute to bponPonConfigTable
--
--	Added gponOltSideOntUtilBulkPmIntervalTable
--
--
-- Carried forward from ISAM5.1.01 (per Li Ya a and Li Chengbing)
--
-- ALU01926856 - N:P OMCI Management Model for CMCC 
--
--		For bponOntVlanBridgeMappingMode attribute in bponOntTable, added mode 0x06
--		and expounded on mode 0x07 as follows:
--
--       	0x05 - 1:MP map-filtering (SUPPORTED as of ISAM4.4).
--
--
--		0x06 - limited N:P bridge filtering (SUPPORTED as of ISAM5.1.01). 
--				In this mode, the different data flows identified by 
--				VLAN ids from users must correspond to different outer
--				VLAN id in outer VLAN tag in frames on ONT aggregated
--				interfaces.
--
--    		0x07 - limited N:MP bridge-map-filtering (SUPPORTED as of ISAM4.4).
--				In this mode, the  VLAN  id in the outermost VLAN tag 
--				egressing from the ONU for different data flows in one 
--				ONU can not be same. It means the different data flows 
--				from users can not be aggregated into same VLAN id in the ONU.
--       	Default = 0x05 = 1:MP
--
--		For GPON - SUPPORTED as of ISAM4.4 (modes 5 and 7) 
--		For GPON - SUPPORTED as of ISAM5.1.0 (modes 5, 6 and 7)   
--		For XG-PON1 - SUPPORTED as of ISAM4.6.02 (modes 5 and 7) 
--		For NG-PON2 - SUPPORTED as of ISAM5.2 (modes 5 and 7)
--
--
--
-- John Boyle - 6/2/14:
-- For ISAM5.2
--
-- ALU01848928 - PON Utilization & Thresholds
--
--	In gponOltSidePonUtilTable, did following to following attributes:
--		gponOltSidePonUtilRxPmCurrentIntervalUcastUtil >> commented out of MIB

--		gponOltSidePonUtilRxPmCurrentIntervalUcastBytes >> commented out of MIB
--		gponOltSidePonUtilRxPmCurrentIntervalUcastDropBytes >> renamed to following:
--				gponOltSidePonUtilRxPmCurrentIntervalTotalDropBytes

--		gponOltSidePonUtilRxPmCurrentIntervalUcastPackets >> commented out of MIB
--		gponOltSidePonUtilRxPmCurrentIntervalUcastDropPackets >> renamed to following:
--				gponOltSidePonUtilRxPmCurrentIntervalTotalDropPackets
--
--	In gponOltSidePonUtilTable added following:
--		gponOltSidePonUtilTxPmCurrentIntervalTotalDropBytes
--		gponOltSidePonUtilTxPmCurrentIntervalTotalDropPackets
--
--
--	In gponOltSidePonUtilPmIntervalTable, did following to following attributes:
--		gponOltSidePonUtilRxPmIntervalUcastUtil >> commented out of MIB
--
--		gponOltSidePonUtilRxPmIntervalUcastBytes >> commented out of MIB
--		gponOltSidePonUtilRxPmIntervalUcastDropBytes >> renamed to following:
--				gponOltSidePonUtilRxPmIntervalTotalDropBytes
--
--		gponOltSidePonUtilRxPmIntervalUcastPackets >> commented out of MIB
--		gponOltSidePonUtilRxPmIntervalUcastDropPackets >> renamed to following:
--				gponOltSidePonUtilRxPmIntervalTotalDropPackets
--
--	In gponOltSidePonUtilPmIntervalTable added following:
--		gponOltSidePonUtilTxPmIntervalTotalDropBytes
--		gponOltSidePonUtilTxPmIntervalTotalDropPackets
--
--
--	In gponOltSidePonUtilTCAThresholdTable, did following to following attributes:
--		gponOltSidePonUtilHighThresholdRxUcastDroppedPackets >> renamed to following:				
--				gponOltSidePonUtilLowThresholdRxTotalDroppedPackets
--		gponOltSidePonUtilMediumThresholdRxUcastDroppedPackets >> renamed to following:				
--				gponOltSidePonUtilMediumThresholdRxTotalDroppedPackets
--		gponOltSidePonUtilLowThresholdRxUcastDroppedPackets >> renamed to following:				
--				gponOltSidePonUtilLowThresholdRxTotalDroppedPackets
--
--	Renamed following SCALARs:
--
--		FROM >> gponSysOltSidePonUtilHighThresholdRxUcastDroppedPackets
--		TO >> gponSysOltSidePonUtilHighThresholdRxTotalDroppedPackets
--
--		FROM >> gponSysOltSidePonUtilMediumThresholdRxUcastDroppedPackets
--		TO >> gponSysOltSidePonUtilMediumThresholdRxTotalDroppedPackets
--
--		FROM >> gponSysOltSidePonUtilLowThresholdRxUcastDroppedPackets
--		TO >> gponSysOltSidePonUtilLowThresholdRxTotalDroppedPackets		
--
--
-- John Boyle - 5/28/14:
-- For ISAM5.2
--
--	(Carried forward from ISAM5.1) - (per Yao Liquiang and Tao Shanxue):
--
--  RCR ALU01951611 : G.988 OMCIv2 provision H.248 MG domain name per ONT
--
--	Added gponOntMgcConfigMessageIdStr to gponOntMgcConfigTable 
--
--
-- ALU01848928 - PON Utilization & Thresholds
--
--	For bponPonConfigPonUtilOntDetailSelector attribute in bponPonConfigTable:
--		Added codepoint 3 = Inherit from System level SCALAR, 
--		and made it the DEFAULT.
--
--	Added following System SCALAR: 
--		bponSysOltsidePonUtilOntDetailSelector { gponOltGroup 46 }
--		
--
--
-- John Boyle - 5/23/14:
-- For ISAM5.2
--
-- ALU01862953 - NGPON2 TWDM LT first 4-port version (FWLT-A)
--
--	Deleted support for Card Type 49 (10 Gigabit Ethernet) to attributes in following tables:
--		bponOntPlanCardTable
--		bponOntActualCardTable
--	This card type is supported internally via OMCI, but is not explicitly
--	exposed in MIB.  The real 10gigE card is planned using the existing 24 = 10/100 Base-T
--	card type selection (which effectively handles all OMCI Ethernet card types). 

--
-- John Boyle - 5/19/14:
-- For ISAM5.2
--
-- ALU01848928 - PON Utilization & Thresholds
--
--	Added following attributes to bponPonConfigTable:
--		bponPonConfigPonUtilOntDetailSelector
--	Added following attributes to gponOltSidePonUtilTCAThresholdTable
--		gponOltSidePonUtilDbaCongestionThreshold
--		gponOltSidePonNumDbaTcIntervals
--	Added following system SCALARS:
--		gponSysOltSidePonUtilDbaCongestionThreshold {gponOltGroup 44}
--		gponSysOltSidePonUtilNumDbaTcIntervals {gponOltGroup 45}
--	Changed all read-only PON utilization 'percentage' attributes to say following:
--		 Range is 0..10000, represented in percentage as 0.00 to 100.00	
--
--
-- ALU01862953 - NGPON2 TWDM LT first 4-port version (FWLT-A)
--
--	Added support for Card Type 49 (10 Gigabit Ethernet) to attributes in following tables:
--		bponOntPlanCardTable
--		bponOntActualCardTable

--	For bponLanEtherPortAutoDetectConfig attribute of bponLanEtherPortTable, added support
--	for following codepoint:
--		5 (MIB Value) = 10GigFD (new starting ISAM5.2)
--		OMCI Translation = 5 = RATE - 10Gig & DUPLEXITY - Full Duplex only
--
--	For bponLanEtherPortOpstatConfigIndicator attribute of bponLanEtherPortOpstatTable, 
--	added support for following codepoint:
--		4 = 10GigE (full duplex) - SUPPORTED as of ISAM5.2
--
--				
--
--
-- John Boyle - 5/13/14:
-- For ISAM5.2
--
-- ALU01848928 - PON Utilization & Thresholds
--
--	This time, I actually added following table:
--		gponOltSidePonUtilStatsResetTable
--	Added a new Group - gponIndexes	OBJECT IDENTIFIER ::= { apon 100 }
--	Defined following new OIDs under this group:
--		- pmIntervalNum
--		- ontRank
--	Re-indexed following tables to remove index from the table entry
--		gponOltSideOntUtilPmCurrentIntervalTable
--		gponOltSideOntUtilPmIntervalTable
--
--
-- John Boyle - 5/6/14:
-- For ISAM5.2
-- 
-- ALU01862953 - NGPON2 TWDM LT first 4-port version (FWLT-A)
--
--	Added following attributes to bponOntTable:
--		bponOntNg2PreferredChanPair
--		bponOntNg2ActualChanPair
--
--	For every table and/or attribute in this MIB, tried to distinguish applicability
--	and support level for GPON, XG-PON1 and NG-PON2 type boards.
--
--	ASssorted commentary to distinguish fact that for NG-PON2, only Ethernet UNI is
--	(derived from ONT Card Type 24 - 10/000 Ethernet)
--
-- 	For bponOntOpInfoPloamCurrStatus attribute of bponOntOpInfoTable, added following
-- 	codepoint:
--		 28 = Loss of OMCI channel (LOOC) - added as of ISAM5.2 for NG-PON2 
--
-- ALU01848928 - PON Utilization & Thresholds
--
--	Added following attributes to bponPonConfigTable
--	 	bponPonConfigPonUtilPmCollectInd 
--   		bponPonConfigPonUtilNumPmIntervals 
--
--	Added following tables:
--		gponOltSidePonUtilPmCurrentIntervalTable
--		gponOltSidePonUtilPmIntervalTable
--		gponOltSidePonUtilTxOntPmCurrentIntervalTable
--		gponOltSidePonUtilTxOntPmIntervalTable
--		gponOltSidePonUtilRxOntPmCurrentIntervalTable
--		gponOltSidePonUtilRxOntPmIntervalTable
--		gponOltSideOntUtilPmCurrentIntervalTable
--		gponOltSideOntUtilPmIntervalTabl
--		gponOltSidePonUtilTCAThresholdTable
--		gponOltSidePonUtilStatsResetTable
--
--	Added following system SCALARS:
--		gponSysOltSidePonUtilPmCollectInd {gponOltGroup 17}
--		gponSysOltSidePonUtilHighTcaEnable {gponOltGroup 18}
--		gponSysOltSidePonUtilHighThresholdLevelDown {gponOltGroup 19}
--		gponSysOltSidePonUtilHighThresholdLevelUp {gponOltGroup 20}
--		gponSysOltSidePonMcastUtilHighThresholdLevelDown {gponOltGroup 21}
--		gponSysOltSidePonUtilHighThresholdDBACongestionUp {gponOltGroup 22}
--		gponSysOltSidePonUtilNumTcIntervals {gponOltGroup 23}
--		gponSysOltSidePonUtilHighThresholdTxUcastDroppedPackets	{gponOltGroup 24}
--		gponSysOltSidePonUtilHighThresholdRxUcastDroppedPackets	{gponOltGroup 25}
--		gponSysOltSidePonUtilHighThresholdTxMcastDroppedPackets	{gponOltGroup 26}
--		gponSysOltSidePonUtilHighThresholdTxBcastDroppedPackets {gponOltGroup 27}
--		gponSysOltSidePonUtilMediumThresholdLevelDown {gponOltGroup 28}
--		gponSysOltSidePonUtilMediumThresholdLevelUp {gponOltGroup 29}
--	    	gponSysOltSidePonMcastUtilMediumThresholdLevelDown  {gponOltGroup 30}	
--	    	gponSysOltSidePonUtilMediumThresholdDBACongestionUp   {gponOltGroup 31}
--		gponSysOltSidePonUtilMediumThresholdTxUcastDroppedPackets	{gponOltGroup 32}
--		gponSysOltSidePonUtilMediumThresholdRxUcastDroppedPackets	{gponOltGroup 33}
--		gponSysOltSidePonUtilMediumThresholdTxMcastDroppedPackets	{gponOltGroup 34}
--		gponSysOltSidePonUtilMediumThresholdTxBcastDroppedPackets {gponOltGroup 35}
--		gponSysOltSidePonUtilLowThresholdLevelDown {gponOltGroup 36}
--		gponSysOltSidePonUtilLowThresholdLevelUp {gponOltGroup 37}
--	    	gponSysOltSidePonMcastUtilLowThresholdLevelDown {gponOltGroup 38}
--	    	gponSysOltSidePonUtilLowThresholdDBACongestionUp  {gponOltGroup 39}
--		gponSysOltSidePonUtilLowThresholdTxUcastDroppedPackets	{gponOltGroup 40}
--		gponSysOltSidePonUtilLowThresholdRxUcastDroppedPackets	{gponOltGroup 41}
--		gponSysOltSidePonUtilLowThresholdTxMcastDroppedPackets	{gponOltGroup 42}
--		gponSysOltSidePonUtilLowThresholdTxBcastDroppedPackets {gponOltGroup 43}

--
--
-- John Boyle - 1/28/14:
-- For ISAM5.1:
-- (Carried forward from ISAM5.0)
--
-- ALU01946081 - 'gponUniGemPmTable' is not supported on HPNA, MoCA - NOT Ok
--
-- 	In intro section to following tables:
--		gponUniGemPmTable
--		gponUniOntsideGemCurrentIntervalTable 
--		gponUniOntsideGemIntervalTable 
--		gponUniOltsideGemCurrentIntervalTable 
--		gponUniOltsideGemIntervalTable
-- 
-- 	Made following statements:
--  		Prior to ISAM5.0, this table was only SUPPORTED for following:
--  		Ethernet and XDSL UNI types
--
-- 		As of ISAM5.0, this table is SUPPORTED for following:
-- 		Ethernet, XDSL,HPNA, MOCA and VEIP UNI types.
--
--
-- John Boyle - 1/21/14:
-- For ISAM5.1
--	(Carried forward from ISAM5.0):
--
-- ALU01896795 - 7342 Gap: OLT Support for Verizon SIPPING mode VoIP
--
--	For gponVoipServiceIpsecEnable attribute in gponVoipServiceTable, amended as follows:
--	As of ISAM5.0, this attribute is SUPPORTED, but only relevant for SIPPING and FTP config methods.
--
--
-- John Boyle - 1/13/14:
-- For ISAM5.1:
--
--  RCR ALU01873708 - Configurable behavior for Ethernet port on PONLOS
--
--	Added bponLanEtherPortGwayPonLossBehaveMode attribute to bponLanEtherPortTable	
--	Added gponVeipPortGwayPonLossBehaveMode attribute to gponVeipPortTable
--
--
--  RCR ALU01900262 - [TdE only] virtual Residential Gateway - ISAM core0 changes
--
--	In gponProfileGroup, added the following:
--		- gponOpenFlowProfileTable
--		- gponOpenFlowProfileMappingTable
--		- gponOpenFlowProfileIndexNext 	SCALAR
--		- gponOpenFlowProfileMaxIndex	SCALAR
--
--	In gponServicesGroup, added gponOpenFlowServiceTable 
--
--	For bponOntIPHCCapability attribute in bponOntTable, mentioned following:  
--		As of ISAM5.1, this attribute must be set to 'enable IPHC' in order to 
--		configue Open Flow service using gponIpHostTable.
--
--	In gponOntIpHostTable, added the following:
-- 	VALIDATION:  As of ISAM5.1, must SUPPORT up to 2 rows in this table for same ONT in following manner:
--	  	1 row for standard VoIP, (use the same ifIndex as the Virtual UNI in IFM MIB).
--	  	1 row for other L3 service (use the same ifIndex that corresponds to a VLAN.PORT in the IFM MIB).
--	 	NOTE:  As of ISAM5.1, the only such dual IP stack ONT built by ALU is one that supports only 
--	         	Standard VoIP AND Open Flow Service.
--
-- John Boyle - 1/9/14:
-- For ISAM5.0:
--
--  RCR ALU01928607 - SIP registration status for POTS line to be available at OLT via MIB/ CLI/ AMS 
--
--	Changed targeted release in following comment to intro section of gponPotsVoipOpstatTable:
-- 		As of targeted release ISAM5.1, this table must also be SUPPORTED for legacy Voip.
--
--
-- John Boyle - 1/8/14:
-- For ISAM4.6:
--
--  (Carried forward from ISAM4.6)
--  ALU00333231 - Extra parameters in GPON MIB
--
--	Marked following tables as NOT SUPPORTED (since RCR was descoped long in the past):
--		- gponPonSummaryInfoTable
--		- gponOntSummaryInfoTable 
--
-- John Boyle - 1/7/14:
-- For ISAM5.0:
--
--  RCR ALU01874046 - 64bit rolling counter for Total/Multicast/Broadcast 
--  (per recommendations from Yao Liqiang)
--
--	For following attributes in following tables:
--	changed SYNTAX from INTEGER to OCTET STRING (SIZE (8), and also changed units FROM from kbps TO bps:
--
--		In gponOntOntsidePonAggEtherCurrentIntervalTable:
--			- gponOntOntsidePonAggEtherCurrentIntervalTxRate 
--			- gponOntOntsidePonAggEtherCurrentIntervalRxRate 
--		In gponOntOntsidePonAggEtherIntervalTable:
--			- gponOntOntsidePonAggEtherIntervalTxRate 
--			- gponOntOntsidePonAggEtherIntervalRxRate
--
--
-- John Boyle - 11/12/13:
-- For ISAM5.0:
--
--  RCR ALU01928607 - SIP registration status for POTS line to be available at OLT via MIB/ CLI/ AMS 
--
--	Added following comment to intro section of gponPotsVoipOpstatTable:
-- 		As of targeted release ISAM5.0.01, this table must also be SUPPORTED for legacy Voip.
-- 		(i.e. auto creation/deletion of rows in concert with creation/deletion of associated
--		 POTS ports).
--
--
--
-- John Boyle - 11/8/13:
-- For ISAM5.0:
--
--  RCR ALU01874046 - 64bit rolling counter for Total/Multicast/Broadcast 
--  (per recommendations from Yao Liqiang)
--
--	For following attributes in following tables, changed the units FROM bps TO kbps:
--
--		In gponOntOntsidePonAggEtherCurrentIntervalTable:
--			- gponOntOntsidePonAggEtherCurrentIntervalTxRate 
--			- gponOntOntsidePonAggEtherCurrentIntervalRxRate 
--		In gponOntOntsidePonAggEtherIntervalTable:
--			- gponOntOntsidePonAggEtherIntervalTxRate 
--			- gponOntOntsidePonAggEtherIntervalRxRate 
--
--
-- John Boyle - 10/31/13:
-- For ISAM5.0:
--
-- ALU01858660 - Decouple ONT Software Planning and Activation
--
--
--	Edited description commentary to following attributes, to account for special meaning, handling,
--	and extra input validation checks associated with new special string value - DELAYACTIVATE:
--		bponOntSwPlannedVersion attribute in bponOntTable
--		bponOntSwDownloadVersion attribute in bponOntTable
--		bponOntAutoSwPlannedVersion attribute in bponOntTable
--		gponOntSwVerCtlPlannedSwVersion attribute in gponOntSwVerCtlTable
--		gponOntSwVerCtlDownloadSwVersion attribute in gponOntSwVerCtlTable
--
--
-- Carried forward the following change from ISAM4.6.02:
--
--  ALU00858939 : XGPON FGXT-A Standard G.987x Compliant 
--
--	For following 2 attributes in bponOntTable:
--		bponOntUpEncryptMode
--		bponOntTodControl	
--	Commented as follows: 	Due to recent PLM decisions, attribute is NOT SUPPORTED 
--				and there are no plans for future support.
--
-- John Boyle - 9/20/13:
-- For ISAM5.0:
--
-- ALU01858660 - Decouple ONT Software Planning and Activation
--
--	Edited description commentary to following attributes, to account for special meaning/handling
--	associated with new special string value - DELAYACTIVATE:
--		bponOntSwPlannedVersion attribute in bponOntTable
--		bponOntSwDownloadVersion attribute in bponOntTable
--		bponOntAutoSwPlannedVersion attribute in bponOntTable
--		gponOntSwVerCtlPlannedSwVersion attribute in gponOntSwVerCtlTable
--	For following download status attributes: 
--		gponOntSwDownldStatus attribute in gponOntSwDownldStatusTable
--		gponPonOntSwDownldStatus attribute in gponPonOntSwDownldStatus
--			added meaning/support for following; 	
--			Bit 18 ON = DELAYACTIVATE activity is Pending.
--		
--
--
--
-- John Boyle - 9/18/13:
-- For ISAM5.0:
--
-- ALU00372328 - 7342 Feature Gap: MoCA Support
--
--	For bponOntPlanCardType attribute in bponOntPlanCardTable, corrected typo to clarify that MoCA type
--	is SUPPORTED as of ISAM5.0.
--
-- ALU01631410 - Support Ping from ONT
--
--	In intro section of gponOntIpHostPingTestTable, clarified the options for ifIndex as follows:
--
--  	Rows are created/deleted by the manager.  Rows may also be deleted
--  	automatically by the system for various reasons (e.g. if row existence exceeds
--  	a system timer).
--
-- 	NOTE: This table is indexed using ifIindex.  The ifIndex can only be the same as associated with rows
-- 	in gponVoipServiceTable or gponOntIpHostTable.
--
-- 	For cases where bponOntVoipCapability attribute in bponOntTable indicates either legacy VoIP or Standard VoIP
-- 	(regardless of the setting of bponOntIPHCCapability attribute in bponOntTable), the format of the 
-- 	related ifIndex in this table uses the same Virtual UNI Index as that used on the related VoIP row in either
-- 	gponVoipServiceTable or gponOntIpHostTable.
--
-- 	Otherwise, for cases where bponOntIPHCCapability attribute in bponOntTable indicates IPHC is ENABLED,
-- 	the format of the related ifIndex in this table uses the same VLAN.PORT ifIndex as that used on the related
-- 	IP Host row in the gponOntIpHostTable.
--
-- ALU01407694 - Support POTS related VOIP PM feature in VEIP mode (OLT)
--
--	For gponPotsRtpCurrentIntervalPacketLoss attribute in gponPotsRtpCurrentIntervalTable:
--		Changed upper end range to say - The value 0 indicates no packet loss scaling linearly
--		  	to 0xFFFF FFFF to indicate 100 percent packet loss.
--		Changed NOT SUPPORTED clause to instead say -  SUPPORTED as of ISAM4.5.02, since some ONTs may 
--			actually calculate the loss fraction on a current interval basis
--
--	For gponPotsRtpIntervalPacketLoss attribute in gponPotsRtpIntervalTable:
--		Changed upper end range to say - The value 0 indicates no packet loss scaling linearly
--		  	to 0xFFFF FFFF to indicate 100 percent packet loss.
--		Changed NOT SUPPORTED clause to instead say -  SUPPORTED as of ISAM4.5.02.
--		 
--
--
-- John Boyle - 9/5/13:
-- For ISAM5.0:
--
--	Changed doc identifier version:
-- 	 	FROM:  3HH-08248-DHAA-PBZZA  
--	 	TO:  3HH-08248-EAAA-PBZZA
--
-- John Boyle - 8/27/13:
-- For ISAM5.0:
--
-- ALU01896795 - 7342 Gap: OLT Support for Verizon SIPPING mode VoIP
--
--	For gponVoipServiceIpsecEnable attribute in gponVoipServiceTable,
--		 mentioned that Modification is NOT permitted.
--	For gponVoipServiceSecondaryNetGwyIpAddr attribute in gponVoipServiceTable,
--		 mentioned that Modification is NOT permitted. "
--	For gponVoipServiceConfigMethod in gponVoipServiceTable,
--		mentioned the following:
--			As of ISAM4.6.01, Modification between method 1 and 3 is permitted.
--			As of ISAM5.0, codepoint 2 (SIPPING Server Method)  is SUPPORTED,
--			but Modification FROM or TO Sipping method 2 is NOT permitted.
--	For gponVoipServiceSecretId attribute in gponVoipServiceTable,
--		 mentioned that Modification is NOT permitted.
--	For gponVoipServiceSecretK attribute in gponVoipServiceTable,
--		 mentioned that Modification is NOT permitted.
--
--
-- John Boyle - 8/22/13:
-- For ISAM5.0, carried forward the following changes to ISAM4.6.01 MIB.:
--
--  ALU00858939 : XGPON FGXT-A Standard G.987x Compliant 
--
--	For bponPonConfigFecDownstreamInd attribute in bponPonConfigTable:
--		For GPON and X-GPON situations, described the differences regarding
--		default values and modification limitations.
--
--	For following attributes in PonStatsBerTable:
--		bponPonStatsBerUpstream
--		bponPonStatsBerDownstream
--			Described the differences in effective SUPPORT between GPON and X-GPON.
--			(i.e. X-GPON always returns 0 value).
--
--	For bponPonStatsBerResetTrigger attribute in bponPonStatsBerResetTable,
--		Mentioned that for X-GPON (as of ISAM4.6.01), this attribute can be SET, 
--		but setting the trigger is effectively a NO-OP since the relevant counts are always 0
--
--
-- John Boyle - 8/1/13:
-- For ISAM5.0:
--
-- ALU01896795 - 7342 Gap: OLT Support for Verizon SIPPING mode VoIP
--
--	Made following changes to following attributes in gponVoipServiceTable:
--	- For gponVoipServiceClientIdentifier:
--		Noted as of ISAM5.0, in-service modification of this attribute is SUPPORTED.
--	- For gponVoipServiceSecretID, noted following:
--		As of ISAM5.0, this attribute is SUPPORTED (because SIPPING config method is SUPPORTED)
--	- For gponVoipServiceSecretK, noted following:
--		As of ISAM5.0, this attribute is SUPPORTED (because SIPPING config method is SUPPORTED)
--	- For gponVoipServiceConfigMethod, noted following:
--		As of ISAM5.0, codepoint 2 (SIPPING Server Method)  is SUPPORTED
--	- For gponVoipServiceSippingAuthUsername, noted following:
--		As of ISAM5.0, this attribute is SUPPORTED (because SIPPING config method is SUPPORTED)
--		As of ISAM5.0, in-service modification of this attribute is SUPPORTED.
--	- For gponVoipServiceSippingAuthPassword, noted following:
--		As of ISAM5.0, this attribute is SUPPORTED (because SIPPING config method is SUPPORTED)
--		As of ISAM5.0, in-service modification of this attribute is SUPPORTED.
--	- For gponVoipServiceSippingAuthRealm, noted following:
--		As of ISAM5.0, this attribute is SUPPORTED (because SIPPING config method is SUPPORTED)
--		As of ISAM5.0, in-service modification of this attribute is SUPPORTED.
--	- For gponVoipServiceIpsecEnable, noted following:
--		As of ISAM5.0, this attribute is SUPPORTED
--	- For gponVoipServiceSippingServerAddress, noted following:	  
--		As of ISAM5.0, this attribute is SUPPORTED (along with in-service modification).  But unlike FTTU, this attribute points to a row 
--		in the gponUriProfileTable.
--
--	Made following changes to following attributes in gponVoipOpInfoTable:
--		- Added gponVoipServiceOpInfoProfileDownloadStatus
--
--	Added bponPotsPortProfileStatusTable. Ported the table from FTTU MIB (but recognized that
--		JBoyle had an OID clash between the FTTU and ISAM GPON MIBs for this table). So JBoyle did following: 
--		FTTU had this table at  { bponPotsGroup 8 }
--		For ISAM5.0, JBoyle moved it to { bponPotsGroup 15 }
--
--
-- ALU01848928 - 7342 Feature Gap: PON Utilization Threshold
-- ALU01848930 - 7342 Feature Gap: Multicast Utilization Threshold
-- 		REMOVED all attributes/tables associated with above RCRs (because PLM has moved them into a ISAM5.1+ release,
--		where a database migration is permitted).  The feature is being worked with FTTU4.9+ with Verizon, and it may
--		well take on different characteristics than what was in this MIB (prior to this deletion). Following was deleted:
--
--		Deleted following attributes from bponPonConfigTable:
--			bponPonConfigPonMcastUtilPmCollectInd 
--      			bponPonConfigPonMcastUtilizationNumPmIntervals  
--      			bponPonConfigPonUtilPmCollectInd  
--      			bponPonConfigPonUtilizationNumPmIntervals 
--			bponPonConfigPonBcastUtilPmCollectInd   
--       			bponPonConfigPonBcastUtilizationNumPmIntervals 
--		Deleted following tables:
--			gponOltSidePonMcastUtilTCAThresholdTable
--			gponOltSidePonMcastUtilPmCurrentIntervalTable
--			gponOltSidePonMcastUtilPmIntervalTable
--			gponOltSidePonUtilTCAThresholdTable
--			gponOltSidePonUtilPmCurrentIntervalTable
--			gponOltSidePonUtilPmIntervalTable
--			gponOltSidePonUtilTxOntPmIntervalTable
--			gponOltSidePonUtilRxOntPmIntervalTable
--			gponOltSidePonBcastUtilTCAThresholdTable
--			gponOltSidePonBcastUtilPmCurrentIntervalTable
--			gponOltSidePonBcastUtilPmIntervalTable 
--		Deleted following SCALARs:
--			gponSysOltSidePonMcastUtilPmCollectInd
--			gponSysOltSidePonMcastUtilHighTcaEnable
--			gponSysOltSidePonMcastUtilHighThresholdLevelDown
--			gponSysOltSidePonMcastUtilNumTcIntervals
--			gponSysOltSidePonUtilPmCollectInd
--			gponSysOltSidePonUtilHighTcaEnable
--			gponSysOltSidePonUtilHighThresholdLevelDown
--			gponSysOltSidePonUtilHighThresholdLevelUp
--			gponSysOltSidePonUtilNumTcIntervals
--			gponSysOltSidePonBcastUtilPmCollectInd
--			gponSysOltSidePonBcastUtilHighTcaEnable
--			gponSysOltSidePonBcastUtilHighThresholdLevelDown
--			gponSysOltSidePonBcastUtilNumTcIntervals
--
		
--
-- John Boyle - 7/22/13:
-- For ISAM5.0:
--
-- ALU01631410 - Support Ping from ONT
--
--	In gponOntIpHostPingTestTable:
--		Deleted following attribute:
--			gponOntIpHostPingTestAddressPinged	OCTET STRING
--		Added following attributes: 
--			gponOntIpHostPingTestPingedIpAddressType	InetAddressType
--			ponOntIpHostPingTestPingedIpAddress	InetAddress
--
-- John Boyle - 7/5/13:
-- For ISAM5.0:
--
--
-- ALU01848928 - 7342 Feature Gap: PON Utilization Threshold
--
--	Added following attributes to bponPonConfigTable:
--		bponPonConfigPonBcastUtilPmCollectInd
--      		bponPonConfigPonBcastUtilizationNumPmIntervals
--
--	Added following tables:
--		gponOltSidePonBcastUtilTCAThresholdTable
--		gponOltSidePonBcastUtilPmCurrentIntervalTable
--		gponOltSidePonBcastUtilPmIntervalTable
--
--	Added following SCALARs under gponOltGroup OID:
--		gponSysOltSidePonBcastUtilPmCollectInd
--		gponSysOltSidePonBcastUtilHighTcaEnable
--		gponSysOltSidePonBcastUtilHighThresholdLevelDown
--		gponSysOltSidePonBcastUtilNumTcIntervals
--
-- ALU01631410 - Support Ping from ONT
--
--	Addded following attributes to IMPORTS section:
--		InetAddressType, InetAddress FROM INET-ADDRESS-MIB
--
--	For gponOntIpHostPingTestTable:
--		Revamped and reordered every attribute in table, 
--		to hopefully be MIB-ready when IPv6 ping is also supported.
--
--		
--
-- John Boyle - 6/28/13:
-- For ISAM5.0:
--
-- ALU01631410 - Support Ping from ONT
--
--	Noted that gponOntIpHostPingTestTable is SUPPORTED as of ISAM5.0.
--	Updated all attributes and added introductory text to describe intended usage.
--	Also added the following attributes to this table:
--		gponOntIpHostPingTestNetworkAddress
--		gponOntIpHostPingTestRowStatus
--
--
-- John Boyle - 6/20/13:
-- For ISAM5.0:
--
-- ALU01848928 - 7342 Feature Gap: PON Utilization Threshold
--
--	Added following attributes to bponPonConfigTable:
--        		bponPonConfigPonUtilPmCollectInd
--       		bponPonConfigPonUtilizationNumPmIntervals
--
--	Added following tables:
--		gponOltSidePonUtilTCAThresholdTable
--		gponOltSidePonUtilPmCurrentIntervalTable
--		gponOltSidePonUtilPmIntervalTable
--		gponOltSidePonUtilTxOntPmIntervalTable
--		gponOltSidePonUtilRxOntPmIntervalTable
--
--	Added following SCALARs under gponOltGroup OID:
--		gponSysOltSidePonUtilPmCollectInd
--		gponSysOltSidePonUtilHighTcaEnable
--		gponSysOltSidePonUtilHighThresholdLevelDown
--		gponSysOltSidePonUtilHighThresholdLevelUp
--		gponSysOltSidePonUtilNumTcIntervals
--
-- ALU01848930 - 7342 Feature Gap: Multicast Utilization Threshold
--
--	Added following attributes to bponPonConfigTable:
--		bponPonConfigPonMcastUtilPmCollectInd
--      		bponPonConfigPonMcastUtilizationNumPmIntervals
--
--	Added following tables:
--		gponOltSidePonMcastUtilTCAThresholdTable
--		gponOltSidePonMcastUtilPmCurrentIntervalTable
--		gponOltSidePonMcastUtilPmIntervalTable
--
--	Added following SCALARs under gponOltGroup OID:
--		gponSysOltSidePonMcastUtilPmCollectInd
--		gponSysOltSidePonMcastUtilHighTcaEnable
--		gponSysOltSidePonMcastUtilHighThresholdLevelDown
--		gponSysOltSidePonMcastUtilNumTcIntervals
--
-- ALU01856409 - 7342 Feature Gap: OLT Support for B-0404G-B
--	For following attributes in following tables, changed to indicate SUPPORTED:
--		gponCesServicePWCurrentIntervalTable
--			gponCesServicePWCurrentIntervalTransmitPkts
--			gponCesServicePWCurrentIntervalMisorderPktsDropped
--		gponCesServicePWIntervalTable
--			gponCesServicePWIntervalTransmitPkts
--			gponCesServicePWIntervalMisorderPktsDropped 
--
--
--  ALU00372328 - 7342 Feature Gap: MoCA Support
--	For following attributes in following tables, added support for ONT MoCA linecard (Type 46):
--		bponOntPlanCardType attribute in bponOntPlanCardTable
--		bponOntActualCardType attribute in bponOntActualCardTable
--	For following tables, mentioned that they are applicable for following UNI types: Ethernet, XDSL, HPNA and MoCA
--		gponEtherTrafficCurrentIntervalTable
--		gponEtherTrafficIntervalTable
--		gponUniGemPmTable
--		gponUniOntsideGemCurrentIntervalTable
--		gponUniOntsideGemIntervalTable
--		gponUniOltsideGemCurrentIntervalTable
--		gponUniOltsideGemIntervalTable
--
--
--  RCR ALU01874046 - 64bit rolling counter for Total/Multicast/Broadcast 
--  (per recommendations from Yao Liqiang)
--
--	Added following counter attributes to gponOntOntsidePonAggEtherCurrentIntervalTable:
--		- gponOntOntsidePonAggEtherCurrentIntervalTxFramesUnicast 
--		- gponOntOntsidePonAggEtherCurrentIntervalRxFramesUnicast 
--		- gponOntOntsidePonAggEtherCurrentIntervalTxFramesMulticast 
--		- gponOntOntsidePonAggEtherCurrentIntervalRxFramesMulticast 
--		- gponOntOntsidePonAggEtherCurrentIntervalTxFramesBroadcast 
--		- gponOntOntsidePonAggEtherCurrentIntervalRxFramesBroadcast 
--		- gponOntOntsidePonAggEtherCurrentIntervalTxFrames 
--		- gponOntOntsidePonAggEtherCurrentIntervalRxFrames 
--		- gponOntOntsidePonAggEtherCurrentIntervalTxBytes 
--		- gponOntOntsidePonAggEtherCurrentIntervalRxBytes 
--		- gponOntOntsidePonAggEtherCurrentIntervalTxRate 
--		- gponOntOntsidePonAggEtherCurrentIntervalRxRate 
--
--	Added following counter attributes to gponOntOntsidePonAggEtherIntervalTable:
--		- gponOntOntsidePonAggEtherntervalTxFramesUnicast 
--		- gponOntOntsidePonAggEtherIntervalRxFramesUnicast 
--		- gponOntOntsidePonAggEtherntervalTxFramesMulticast 
--		- gponOntOntsidePonAggEtherIntervalRxFramesMulticast 
--		- gponOntOntsidePonAggEtherIntervalTxFramesBroadcast 
--		- gponOntOntsidePonAggEtherIntervalRxFramesBroadcast 
--		- gponOntOntsidePonAggEtherIntervalTxFrames 
--		- gponOntOntsidePonAggEtherIntervalRxFrames 
--		- gponOntOntsidePonAggEtherIntervalTxBytes 
--		- gponOntOntsidePonAggEtherIntervalRxBytes 
--		- gponOntOntsidePonAggEtherIntervalTxRate 
--		- gponOntOntsidePonAggEtherIntervalRxRate 
--
--	Added following tables to bponOntGroup(indexed primarily by ONT):
--		- gponOntOntsidePonAggEtherTable
--
--
--
-- John Boyle - 5/21/13:
-- For ISAM4.6:
--
-- ALU01865135 = MIB Readiness for ALU01192933 : 7342 Feature Gap: OLT Support CES provisioning for SAToP (targeted for ISAM4.6.01)
--
--	Due to CLI inability to deal with compound fields in single attribute, for following attributes in gponCesServiceTable:
--		gponCesServiceRtpPayloadType
--		gponCesServiceRtpSyncSource
--		gponCesServiceRtpExpectedPayloadType
--		gponCesServiceRtpExpectedSyncSource
--	Split them into the following 8 attributes (and changed their SYNTAX from OCTET String to INTEGER):
--		gponCesServiceRtpPtypePayloadChannel
--		gponCesServiceRtpPtypeSignalChannel
--		gponCesServiceRtpSyncSourcePayloadChannel	
--		gponCesServiceRtpSyncSourceSignalChannel
--		gponCesServiceRtpExpectedPtypePayloadChannel
--		gponCesServiceRtpExpectedPtypeSignalChannel
--		gponCesServiceRtpExpectedSyncSourcePayloadChannel	
--		gponCesServiceRtpExpectedSyncSourceSignalChannel
--
--
-- ALU01857121 = MIB Readiness for ALU00858939 : XGPON FGXT-A Standard G.987x Compliant (targeted for ISAM4.6.01)
--
-- 	For bponPonConfigXgTag attribute in bponPonConfigTable, added following validation
--		VALIDATION:  Other than the value 'all zeroes', the value of this attribute must be UNIQUE among all PONs on the shelf.
--
--
--
-- John Boyle - 5/3/13:
-- For ISAM4.6:
--
-- ALU01865135 = MIB Readiness for ALU01192933 : 7342 Feature Gap: OLT Support CES provisioning for SAToP (targeted for ISAM4.6.01)
--
--	For gponCesServiceTransmitCircuitId attribute in gponCesServiceTable, changed comments as follows:
--
--		  NOTE: For L2, the payload ECID part cannot be 0. Other than the zero value for the signalling ECID part, all
--		  ECID parts (payload and signalling) must be unique across all Transmit ECID parts across all CES 
--		  Services within a single ONT. 
--
--		  NOTE: For L2, any edit of this parameter is service-affecting.
--
--		  For L2, No Default - must be provided by operator.
--		  For L3, Default = all zeroes (since attribute is irrelevant)
--
--
-- John Boyle - 5/2/13:
-- For ISAM4.6:
--
-- ALU01865991 - OLT: XML Over OMCI for NAR
--
--	For gponVoipServiceForceOmciXmlDownload attribute to gponVoipServiceTable, changed comments as follows:
--
--		 The only valid SET (other than row creation) for this attribute is the value = 1 (meaning a trigger to force unconditional download).
--		 For GET, the agent can return value 0 (which is meaningless, since this attribute is really intended to 
--			be a trigger, and manager obtains no useful information from a GET).
--		 For row creation, the only legitimate value is 0. 
--		 Default = 0 
--
-- ALU01865135 = MIB Readiness for ALU01192933 : 7342 Feature Gap: OLT Support CES provisioning for SAToP (targeted for ISAM4.6.01)
--
--	For gponCesServiceTcpUdpPortNum attribute in gponCesServiceTable, changed comments as follows:
--		VALIDATION:  For L3, CES IP services that share the same source IP address
--				(i.e. same row in IpHostConfigTable) must have different source UDP port numbers.
--		If L2, Default = 2142 (and attribute is irrelavant)
--		If L3, No Default - must be provided by operator.
--
--	For gponCesServiceFarEndIpInfo attribute in gponCesServiceTable, cahnaged comments as follows:
--		If L2, Default = null string (and attribute is irrelavant)
--		If L3, No Default - must be provided by operator.
--
--  ALU01857121 = MIB Readiness for ALU00858939 : XGPON FGXT-A Standard G.987x Compliant (targeted for ISAM4.6.01)
--
--	For bponPonConfigDsMulticastEncryptInd attribute in bponponConfigTable, added following comment:
--		Modification SUPPORTED
--
--
-- John Boyle - 4/12/13:
-- For ISAM4.6:
--
--  ALU01857121 = MIB Readiness for ALU00858939 : XGPON FGXT-A Standard G.987x Compliant (targeted for ISAM4.6.01)
--
-- 	For bponOntTodControl attribute in bponOntTable:
--		Changed functional meaning back to enable/disable option.  The actual update interval will not be provisionable
--		individually on an ONT basis.  The update interval will be deduced internally by OLT for the whole shelf.  Will
--		require experimentation, but goal in ISAM4.6.0x timeframe is '1 minute'.  This time may become operator provisionable
--		in the future (e.g. a SCALAR for the whole shelf), but this would need to be in ISAM4.7 timeframe and would require
--		specific RCR.
--
--
-- John Boyle - 4/11/13:
-- For ISAM4.6:
--
-- ALU01857121 = MIB Readiness for ALU00858939 : XGPON FGXT-A Standard G.987x Compliant (targeted for ISAM4.6.01)
--
-- For following attributes in bponOntTable made the following comment regarding expected SUPPORT (pushed out from ISAM4.6.01):
-- 	bponOntUpEncryptMode
--	bponOntTodControl	
--		Introduced in ISAM4.6 MIB
--		Expectation is that as of ISAM4.6.02, attribute is SUPPORTED (only for XGPON).
--
--	Also for bponOntTodControl attribute, changed its intended functional meaning with following comments (to convey an update interval):
--		Expectation is that in addition to allowing a 'disable option', this parameter will also function as an interval timer for how often the OLT
--		initiates ToD updates.  So even though not finalized, manager should consider following representation when implemented.
--
--		Range is value 0, and 10..86400
--		Units are seconds
--		
--		Value 0 means  = Do Not use OMCI mechanisms.
--		 
--		Default = 0
--
-- John Boyle - 3/29/13:
-- For ISAM4.6:
--
-- ALU01865991 - OLT: XML Over OMCI for NAR
--
--	Added gponVoipServiceForceOmciXmlDownload attribute to gponVoipServiceTable.
--
--
-- John Boyle - 3/22/13:
-- For ISAM4.6:
--
-- (Per recommendations of Liya Ma)
-- ALU01871121 - MIB Readiness for ALU01868338 : Support RF programmable Filter Options for I-241W-T
--	For bponOntVideoRfFilter attribute in bponOntTable, added following:
--		Following text added to ISAM4.6 MIB:
--		As of ISAM4.6.01, new codepoint 3 = (Low Band 2 (639 MHz)) must be SUPPORTED, 
--		and meaning of codepoint 1 is clarified to mean (Low Band 1 (431 MHz)).
--
--
-- John Boyle - 03/13/13:
-- For ISAM4.6
--
-- ALU01857121 = MIB Readiness for ALU00858939 : XGPON FGXT-A Standard G.987x Compliant (targeted for ISAM4.6.01)
--
--		Clarification of previous statement in this history section. 
--		Should insted be: Following tables are SUPPORTED as of ISAM4.6.01:
--			gponOntOntsideXgTcIntervalTable
--			gponOntOltsideXgTcIntervalTable
--			gponPonOltsideXgTcIntervalTable
--
-- RCR ALU01186229 - CHN GPON OLT PM counter - phase 1
--
-- 	In order to align with what had already been checked in MIB, changed name of following attribute:
-- 		FROM 	bponPonConfigTrafficThresholdDown 
-- 		TO 	bponPonConfigTrafficThresholdDn
--	
--
-- John Boyle - 03/12/13:
-- For ISAM4.6:
--
-- ALU01857121 = MIB Readiness for ALU00858939 : XGPON FGXT-A Standard G.987x Compliant (targeted for ISAM4.6.01)
--
--	Added following attributes to gponPonOltsideFecCurrentIntervalTable (and adjusted OIDs to better align with ONT-level counterparts):
--		gponPonOltsideFecCurrentIntervalCorrectedBytes
--		gponPonOltsideFecCurrentIntervalCorrectedCodeWords
--	Added following attributes to gponPonOltsideFecIntervalTable  (and adjusted OIDs to better align with ONT-level counterparts):
--		gponPonOltsideFecIntervalCorrectedBytes
--		gponPonOltsideFecIntervalCorrectedCodeWords
--
--	For following historical PM tables, noted that As of ISAM4.6, they are NOT SUPPORTED:
--		gponOntFecIntervalTable
--		gponOntOltsideFecIntervalTable
--		gponOntOltsidePhyIntervalTable
--		gponOntOntsideXgTcIntervalTable
--		gponOntOltsideXgTcIntervalTable
--		gponPonOltsideFecIntervalTable
--		gponPonOltsidePhyIntervalTable
--		gponPonOltsideXgTcIntervalTable	
--
--
-- John Boyle - 3/5/13:
-- For ISAM4.6:
--
-- (Per recommendations of Yin Qin)
-- RCR ALU01849935 - DSCP to pbit alignment for PPPoE frames on GPON LT
--	For bponOntDscpToPriorityAlignOLTMode attribute to bponOntTable,
--	removed implications that attribute setting forced ONT to perform specific actions.
--	This attribute only controls OLT behavior - not ONT behavior.
--
--
-- John Boyle - 03/1/13:
-- For ISAM4.6:
--
-- For bponOntRebootCmd attribute in bponOntTable, made following updates and description changes:
--	As of ISAM4.6, commented out rebootPassiveImage(2) enumeration option.
--	It is NOT an option.
--	Only commandable option is rebootActiveImage(1).
--
-- (Per recommendations of Li Jian D)
-- RCR ALU01808212 - SN bundle with LOID/SLID 
--	For gponOltSnAutoBundleTimer SCALAR attribute, changed the range:
--		FROM  1..48 (hours)
--		TO  1..72 (hours)
--
-- ALU01323051 - GPON  OLT support loop inspection and alarm function
--	In intro section and various attributes of gponOntLoopDetectTable, updated to clearly state
-- 	table was added to ISAM4.5 MIB (and as of ISAM4.6, attributes are SUPPORTED).
--
--
-- John Boyle - 02/28/13:
-- For ISAM4.6:
--
-- ALU01857121 = MIB Readiness for ALU00858939 : XGPON FGXT-A Standard G.987x Compliant (targeted for ISAM4.6.01)
--
--	In  bponOntTable, made following changes:
--		Commented out compilation existence of bponOntXgRegisterId attribute in bponOntTable (left in text as a memento).
--	In bponPonConfigTable, made following changes:
--		For bponPonConfigAuthMethod attribute, removed codepoint 6 option
--		Added bponPonConfigXgId attribute to bponPonConfigTable
--
--
-- ALU01813365 - FX GPON: ONU RSSI Support for CHT
-- (Changes proposed by Yao Liqiang)
--
-- In order to be consistent with what was actually done in ISAM4.5.02 GPON MIB,:
-- 	Added following type reference to IMPORTS section - FROM ASAM-TC-MIB:
--		AsamProfileIndexOrZero
-- 	For gponOntAniRSSIProfileId attribute to gponOntAniTable,
--		changed SYNTAX from INTEGER to AsamProfileIndexOrZero
--
--
-- John Boyle - 02/21/13:
-- For ISAM4.6:
--
-- ALU01865135 = MIB Readiness for ALU01192933 : 7342 Feature Gap: OLT Support CES provisioning for SAToP (targeted for ISAM4.6.01)
--
--	Added the following attributes to gponCesServiceTable:
--		gponCesServiceUnderlyingTransportInd
--		gponCesServiceTcpUdpPortNum
--		gponCesServiceDscpSetting
--		gponCesServiceFarEndIpInfo
--		gponCesServiceRtpClockReference
--		gponCesServiceRtpTimeStampMode
--		gponCesServiceRtpPayloadType
--		gponCesServiceRtpSyncSource
--		gponCesServiceRtpExpectedPayloadType
--		gponCesServiceRtpExpectedSyncSource
--	For all pre-ISAM4.6 existing attributes in gponCesServiceTable, clarified whether attribute is relevant in following situations:
--		1) only for L2 service
--		2) for both L2 and L3 service
--		3) only for L3 service
--
--	Added following commentary to bponOntIPHCCapability attribute of bponOntTable:
--		As of ISAM4.4, this attribute must be set to 'enable IPHC' in order to configue SNMP agent service using gponIpHostTable.
--		As of ISAM4.6.01, this attribute must be set to 'enable IPHC' in order to configue L3 CES pseudowire service using gponIpHostTable.
--
--	In up-front commentary of gponOntIpHostTable, added the following:
-- 		As of ISAM4.6.01, the VLAN.PORT style usage is also relevant for L3 CES psuedowire service 
--		(since an IpHost instance is necessary for such service).
-- 		For such L3 CES service, this association is inferred between gponCesServiceVlanPointer attribute in 
--		gponCesServiceTable and VLAN.PORT ifIndex style usage in this gponOntIpHostTable.
--
-- 		VALIDATION:  As of ISAM4.6.01, ALU is building an ONT that supports L3 CES pseudowire service.  This ONT does NOT support VoIP service of
--		of any type and does NOT support ONT SNMP agent service that uses an IpHost entry in this table.  So in the real world (so far), it is still
-- 		only necessary to support a single IpHost entry for a single ONT.  And it is also NOT necessary to support legacy VoIP along with
-- 		L3 CES pseudowire service in the same ONT.  But in theory, an ONT could support 'multiple IpHost instances' along with legacy VoIP, etc...
--		In order to step gradually:
--			As of ISAM4.6.01 sill can only configure a single entry in IpHost table for a single ONT.
--			As of ISAM4.6.01 cannot configure both legacy VoIP and any gponOntIpHostTable entry for the same ONT.
-- 
--	Noted that: As of ISAM4.6.01, following tables are relevant for both L2 and L3 CES pseudowire service:
--		gponCesServicePWCurrentIntervalTable		
--		gponCesServicePWIntervalTable
--	Noted that: As of ISAM4.6.01, following tables are NOT supported for L3 CES pseudowire service:
--		gponCesServiceOntsideGemCurrentIntervalTable
--		gponCesServiceOntsideGemIntervalTable
--		gponCesServiceOltsideGemCurrentIntervalTable
--		gponCesServiceOltsideGemIntervalTable
--
--
--
--
-- John Boyle - 02/13/13:
-- For ISAM4.6:
--
-- ALU01857121 = MIB Readiness for ALU00858939 : XGPON FGXT-A Standard G.987x Compliant (targeted for ISAM4.6.01)
--
--	For bponOntAesMode attribute in bponOntTable, noted the following qualification:
--		NOTE: When the type of PON for this ONT is XGPON (determined from LT card type), then the setting
--		of this attribute only applies to downstream traffic associated with bi-directionl GEM ports.
--		For XGPON, the setting for upstream traffic is determined from bponOntUpEncryptMode attribute.
--		Also, for XGPON mode, modification is SUPPORTED but only if ONT is Admin Down.
--
--	Added following attributes to bponOntTable:
--		bponOntUpEncryptMode
--		bponOntTodControl	
--		bponOntXgRegisterId
--		bponOntOltsideUpFecPmCollectInd
--		bponOntOltsideUpFecPmNumPMIntervals
--		bponOntOltsidePhyPmCollectInd
--		bponOntOltsidePhyPmNumPMIntervals
--		bponOntOntsideXgTcPmCollectInd
--		bponOntOntsideXgTcPmNumPMIntervals
--
--	For gponOntFecIntervalTable, noted that as of ISAM4.6.01, this table is SUPPORTED (for XGPON only).
--
--	Added following tables (indexed primarily by ONT):
--		gponOntOltsideFecCurrentIntervalTable
--		gponOntOltsideFecIntervalTable
--		gponOntOltsidePhyCurrentIntervalTable
--		gponOntOltsidePhyIntervalTable
--		gponOntOntsideXgTcCurrentIntervalTable
--		gponOntOntsideXgTcIntervalTable
--		gponOntOltsideXgTcCurrentIntervalTable
--		gponOntOltsideXgTcIntervalTable
--
--	For bponPonConfigAuthMethod attribute in bponPonConfigTable, added following codepoint (and NOTE): 
--		6 = XGPON Registration ID authentication - means that if XGPON registration ID for a particular ONT is non-zero, then that registration
--		ID is used for that particular ONT.  But if registration ID for a particular ONT is all zeroes, then the system uses SN only
--		authentication (as used with option 1). Introduced in ISAM4.6 for mib-readiness.  SUPPORTED as of ISAM4.6.01 (only for XGPON).
--
--	Added following attributes to gponPonConfigTable:
--		bponPonConfigXgTag
--		bponPonConfigDsMulticastEncryptInd
--		bponPonConfigOltsideUpFecPmCollectInd
--		bponPonConfigOltsideUpFecPmNumPMIntervals
--		bponPonConfigOltsidePhyPmCollectInd
--		bponPonConfigOltsidePhyPmNumPMIntervals
--		bponPonConfigOltsideXgTcPmCollectInd
--		bponPonConfigOltsideXgTcPmNumPMInterval
--
--	Added following tables (indexed primarily by PON):
--		gponPonOltsideFecCurrentIntervalTable
--		gponPonOltsideFecIntervalTable
--		gponPonOltsidePhyCurrentIntervalTable
--		gponPonOltsidePhyIntervalTable
--		gponPonOltsideXgTcCurrentIntervalTable
--		gponPonOltsideXgTcIntervalTable
--
--
--
-- John Boyle - 02/8/13:
-- For ISAM4.6:
--
-- (Per recommendations of Li Jian D)
-- RCR ALU01808212 - SN bundle with LOID/SLID 
--	For bponOntSnBundleStatus attribute in bponOntTable, changed codepoints to say following:
--		0 = Idle: the SN currently is NOT bundled.
--		1 = Bundling: only applicable for auto-bundle mode.
--		      Applies to situations where auto-bundle timer is being restored (e.g. due to system reboot).
--		2 = Bundled: the SN currently is bundled.
--
--
-- John Boyle - 01/29/13:
-- For ISAM4.6:
--
-- (Per recommendations of Yin Qin)
-- RCR ALU01849935 - DSCP to pbit alignment for PPPoE frames on GPON LT
--	Added bponOntDscpToPriorityAlignOLTMode attribute to bponOntTable as OID { bponOntEntry 92 }
--
-- (Per recommendations of Li Jian D)
-- RCR ALU01808212 - SN bundle with LOID/SLID 
--	Added following attributes to bponOntTable:
--		bponOntSnBundleControl as OID { bponOntEntry 93 }
--		bponOntSnBundleStatus as OID { bponOntEntry 94 }
--	Added new SCALAR gponOltSnAutoBundleTimer as OID { gponOltGroup 16 }
--	For bponPonDiscovOntDisableIndicator attribute in bponPonDiscovOntTable,
--		added support for following string: SNBUNDLE - meaning ONT failed to bundle SN with LOID/SLID. 
--
--
-- John Boyle - 01/23/13:
-- For ISAM4.6:
--
-- RCR ALU00398914 - 7342 Feature Gap: Configurable RF Timer
--	For bponVideoPortServiceTimer attribute in bponVideoPortTable:
--		Extended existing FTTU range to include value -1 (meaing do not care, and do not send OMCI)
--		Made Default = -1
--
-- For bponOntLogicalAuthID and bponOntLogicalAuthPassword attributes (in bponOntTable), updated notes as follows:
--	    It is relevant only when bponPonConfigAuthMethod is set to one of following
--	         	2 = CT proprietary logical authentication (LOID) only
--		3 = CT proprietary LOID precedence mix authentication
--		4 = LoidStd - means 988 standard LOID only 
--		5 = LoidPreStd - 988 standard LOID precedence mix
--
--	
--
-- John Boyle - 01/21/13 : (for YAO Liqiang, YIN Qin F and, YI XIAO)  
-- For ISAM4.6:
--
--	RCR ALU01186229 - CHN GPON OLT PM counter - phase 1
-- 	Added following PON port traffic threshold to bponPonConfigTable 
-- 		- bponPonConfigTrafficThresholdUp 
-- 		- bponPonConfigTrafficThresholdDn 
-- 	Added following PON traffic TCA interval to gponOltGroup 
-- 		- gponPonTrafficTcaInterval 
--
--
--
-- John Boyle - 01/07/13 : (for YAO Liqiang, YIN Qin F and, Xiangdong WANG )  
-- For ISAM4.6:
--
--	RCR ALU01186229 - CHN GPON OLT PM counter - phase 1
--	Added following 64-bit counter attributes to gponOltsidePonPortTroubleshootCounterTable:
--		- gponOltsidePonPortDnEthernetFrames
--		- gponOltsidePonPortUpEthernetFrames
--		- gponOltsidePonPortDnEthernetOctets
--		- gponOltsidePonPortUpEthernetOctets
--		- gponOltsidePonPortDnCRCErrorFrames
--		- gponOltsidePonPortUpCRCErrorFrames
--		- gponOltsidePonPortDnCRCErrorFrames
--		- gponOltsidePonPortUpCRCErrorFrames
--		- gponOltsidePonPortUpMcastFrames
--
-- On 11/22/12, backfilled following that was added previously:
-- Shanxue Tao - 9/13/2012
-- For ISAM45
--
-- ALU01821538: MIB readiness for ALU01805130 - G.988 amd1 compliant ONU LOID authentication
--
--      Added following value to bponPonConfigAuthMethod attribute in bponPonConfigTable:
--              4 = LoidStd
--              5 = LoidPreStd
--
--
-- John Boyle - 10/30/2012
-- For ISAM4.5 - carried forward from ISAM4.4.02e
--
-- ALU01830348 (Emergency Fix) - License Control over ONU IOP
--
-- 	Added gponOltIOPOntControlMode SCALAR at { gponOltGroup 14 } OID.
--
--
-- John Boyle - 9/28/2012
-- For ISAM4.5
--
-- 	For codepoint 4 in gponVoipServiceConfigMethod attribute in gponVoipServiceTable, changed to say following:
--		4 = As of ISAM4.4.02, the description for this attribute says following:
--			OMCI FTP Complete (NOTE: This method describes the results of the OMCI FTP download,
--                           	system will auto change it to 4 after OMCI FTP success, this value is using in
--                             	system, user can not get the value (OMCI FTP Complete), if the value is OMCI FTP 
--                             	Complete, the system will auto change it to 3 to show for the user).
--		      As of ISAM4.5, implementation remains the same as previous ISAM release.
--
--	For gponOntAniLowerOpticalThreshold and gponOntAniUpperOpticalThreshold attributes in gponOntAniTable,
--		corrected an upper range typo as follows:
--		FROM: 	From this GPON MIB perspective, valid values are -127.0 dBm to +0.1 dBm (in 0.5 dB increments). 
--			This is represented by the INTEGER range: -254 to +1  -  with interger value +1 meaning use ONT internal policy.
--		TO: 	From this GPON MIB perspective, valid values are -127.0 dBm to +0.0 dBm (in 0.5 dB increments) along with a special value. 
--			This is represented by the INTEGER range: -254 to +1  -  with interger value +1 meaning use ONT internal policy. 
--
--
-- John Boyle - 9/24/2012
-- For ISAM4.5
--
-- ALU01813365 - FX GPON: ONU RSSI Support for CHT
-- (Changes proposed by Yao Liqiang)
--
--	Added gponOntAniRSSIProfileId attribute to gponOntAniTable
--
--
-- Shanxue Tao - 9/13/2012
-- For ISAM45
--
-- ALU01821538: MIB readiness for ALU01805130 - G.988 amd1 compliant ONU LOID authentication
--
--      Added following value to bponPonConfigAuthMethod attribute in bponPonConfigTable:
--              4 = LoidStd
--              5 = LoidPreStd
--
--
-- John Boyle - 9/10/2012
-- For ISAM4.5
--
-- Shifted following attributes to following OIDs
--	bponOntOntsidePonAggEtherPmCollectInd  FROM { bponOntEntry 91} TO { bponOntEntry 90 }
--	bponOntOntsidePonAggEtherPmNumPMIntervals  FROM { bponOntEntry 92} TO { bponOntEntry 91 }
--
-- For codepoint 4 in gponVoipServiceConfigMethod attribute in gponVoipServiceTable, changed to say following:
--		4 = As of ISAM4.4.02, the description for this attribute said following:
--			OMCI FTP Complete (NOTE: This method describes the results of the OMCI FTP download,
--                           	system will auto change it to 4 after OMCI FTP success, this value is using in
--                           	system, user can not get the vlaue (OMCI FTP Complete), if the vlaue is OMCI FTP 
--                             	Complete, the system will auto change it to 3 to show for the user).
--		      As of ISAM4.5, this codepoint value is RESERVED and agent should never return such value in a GET message.
--
--
-- John Boyle - 9/7/2012
-- For ISAM4.5
--
-- ALU01813692 - MIB readiness for ALU01407694 - Support POTS related VOIP PM feature in VEIP mode (OLT)
-- 	For all affected tables/attributes, changed target implementation support to ISAM release 4.5.02.
--
-- For all RCRs (mib ready, whatever, too many to count) that caused introduction of ...Counter64 attributes, added following description
-- statement to their existing 32-bit counterpart attribute:
--		 As of ISAM4.5, the plan is to effectively DEPRECATE this attribute.  Manager should instead use equivalent 
--		 64-bit counter attribute ...Counter64.
--
--
-- John Boyle - 9/4/2012
-- For ISAM4.5
--
-- ALU01813692 - MIB readiness for ALU01407694 - Support POTS related VOIP PM feature in VEIP mode (OLT)
--	For gponPotsCallCntlIntervalTable and gponPotsRtpIntervalTable, added following statement:
--	As of targeted release ISAM4.5.01, this table must be SUPPORTED for Veip-style Voip.
--
-- ALU01816285 - MIB Readiness for ALU01813827 - GPON UNI Octet PM counter improvements - OLT side
-- ALU01817359 - MIB Readiness for ALU01805906 - STC KPI: 64-bit counter requirement - OLT part
-- ALU01814561 - GPON UNI Packet PM counter improvements - OLT side
--	For all newly added Performance Monitor attributes of the variety  ...Counter64, updated the descriptions to say following:
--		 Introduced for readiness in ISAM 4.5 MIB.  Plan to support 32-bit counts in this attribute with ISAM4.5
--		 with target implementation of 64-bit counts in ISAM4.5.01.
--
-- John Boyle - 8/31/2012
-- For ISAM4.5
--
-- For conglomeration of mib-ready RCRs, tried to better pinpoint the expected target release for actual implementation.
-- So I also expect to get badly burned by the shifting winds of this wildfire.
--
-- ALU01813692 - MIB readiness for ALU01407694-Support POTS related VOIP PM feature in VEIP mode (OLT)
--	For affected tables (attributes), mentioned that targeted release for implementation is ISAM4.5.01.
--
-- 	Added following paragraph to intro section of bponPotsPortTable:
-- 	VALIDATION:  As of ISAM4.3,  bponOntVoipCapability attribute was extended to also support what is
-- 	known as Veip-style VOIP.  POTS ports (as represented in this table) are also relevant for provisioning
-- 	when mode is Veip-style VOIP, but only a subset of table attributes are relevant for this mode. Hopefully,
-- 	the specific relevance is indicated within the individual attribute descriptions within.
--
-- ALU01323051 - CM/CT/CU require GPON  OLT can support loop inspection and alarm function
--	In intro section of gponOntLoopDetectTable, updated to say following:
-- 	This is a new table added to ISAM4.5 MIB (targeted implementation release is ISAM4.6).
--
-- RCR ALU01624656 - Mixture of ONU authentification of LOID and SN at same GPON port
--	For bponOntLogicalAuthID and bponOntLogicalAuthPassword attributes in bponOntTable, updated to 
--	say the following:
--	    It is relevant only when bponPonConfigAuthMethod is set to one of following:
--         		2 = logical authentication
--		3 = LOID precedence mix authentication
--
-- John Boyle - 8/30/2012
-- For ISAM4.5
--
-- ALU01814561 - GPON UNI Packet PM counter improvements - OLT side
--	Added following attributes to gponEtherTrafficCurrentIntervalTable:
--		gponEtherTrafficCurrentIntervalTxPacketsCounter64
--		gponEtherTrafficCurrentIntervalRxPacketsCounter64
--	Added following attributes to gponEtherTrafficIntervalTable:
--		gponEtherTrafficIntervalTxPacketsCounter64
--		gponEtherTrafficIntervalRxPacketsCounter64
--
-- ALU01186229 - CHN GPON OLT PM counter - phase 1
--    	Deleted following attributes from gponOltsidePonPortTroubleshootCounterTable as the scope and timeframe
--    	of the RCR has changed:
--		- gponOltsidePonPortDnEthernetFrames
--          		- gponOltsidePonPortUpEthernetFrames
--           		- gponOltsidePonPortDnEthernetOctets
--            	- gponOltsidePonPortUpEthernetOctets
--
-- RCR ALU01430222 - GPON: Enhanced Downstream Frame Handling - MIB Support
--	Removed bponOntDownstreamTagMode attribute from bponOntTable, as scope and timeframe 
--    	of the RCR has changed.	
--
--
--
-- John Boyle - 8/27/2012
-- For ISAM4.5
--
-- ALU01816285 - MIB Readiness for ALU01813827 - GPON UNI Octet PM counter improvements - OLT side
-- 	- Already done in prior updates to this MIB - see ALU01813827 in prior History Remarks below.
--
-- ALU01817359 - MIB Readiness for ALU01805906 - STC KPI: 64-bit counter requirement - OLT part
-- 	- Already done in prior updates to this MIB - see ALU01805906 in prior History Remarks below.
--
-- ALU01817609 - MIB Readiness for ALU00123633 - Subtending Interface on GPON LT (NNI)
-- 	- Already done in prior updates to this MIB - see ALU00123633 in prior History Remarks below.
--
-- ALU01758061 - GPON ONU: GPON Error PM counter - OLT part 
--    Added new Tables:
--        - gponOntOntsidePonAggEtherCurrentIntervalTable
--        - gponOntOntsidePonAggEtherIntervalTable
--
--    Added the following attributes to bponOntTable:
--        - bponOntOntsidePonAggEtherPmCollectInd 
--        - bponOntOntsidePonAggEtherPmNumPMIntervals
--
--
-- ALU01186229 - CHN GPON OLT PM counter - phase 1
--    Deleted following attributes from gponOltsidePonPortTroubleshootCounterTable as the scope
--    of the RCR has changed:
--        - gponOltsidePonPortDnJabbers       
--        - gponOltsidePonPortUpJabbers
--    
-- ALU01747919 - CHN GPON ONU PM counter - OLT part
--    The scope of the RCR changed resulting in the updates below.
--    Deleted the following attributes from bponOntTable:
--	  - bponOntOntsidePonPortPmCollectInd
--	  - bponOntOntsidePonPortPmNumPMIntervals
--    Deleted following tables:
--	  - gponOntOntsidePonPortPmCurrentIntervalTable
--	  - gponOntOntsidePonPortPmIntervalTable
--    Deleted the following attributes from gponEtherTrafficCurrentIntervalTable:
--	  - gponEtherTrafficCurrentIntervalTxJabbers
--	  - gponEtherTrafficCurrentIntervalRxJabbers 
--    Deleted the following attributes from gponEtherTrafficIntervalTable:
--	  - gponEtherTrafficIntervalTxJabbers
--	  - gponEtherTrafficIntervalRxJabbers 
-- 
--
-- 
-- John Boyle - 8/24/2012
-- For ISAM4.5
--
-- RCR ALU01624656 - Mixture of ONU authentification of LOID and SN at same GPON port
--
-- 	For bponPonConfigAuthMethod attribute in bponPonConfigTable, noted that following codepoint is SUPPORTED as of ISAM4.5.
--			3 = LOID precedence mix authentication (SUPPORTED as of ISAM4.5)
--
-- John Boyle - 8/23/2012
-- For ISAM4.5
--
-- ALU01813692 - MIB readiness for ALU01407694-Support POTS related VOIP PM feature in VEIP mode (OLT)
--
--	Updated all of following for MIB-readiness in ISAM4.5, for implementation beyond ISAM4.5:
--		 - For bponPotsPortCallHistCollectInd attribute in bponPotsPortTable, made following comment:
--			As of future release beyond ISAM4.5, enable/disable must also be SUPPORTED for Veip-style VoIP.
--			And also made similar timeframe SUPPORT comment in intro section of following related tables: 
--				- gponPotsCallHistTable
--		 - For bponPotsPortRtpPmCollectInd and bponPotsPortRtpNumPMIntervals attributes in bponPotsPortTable, 
--		   made following comment:
--			As of future release beyond ISAM4.5, enable/disable must also be SUPPORTED for Veip-style VoIP.
--			And also made similar timeframe SUPPORT comment in intro section of following related tables:
--				- gponPotsRtpCurrentIntervalTable and gponPotsRtpIntervalTable
--		 - In intro section of gponPotsVoipOpstatTable, added following comment:
-- 			As of future release beyond ISAM4.5, this table must also be SUPPORTED for Veip-style Voip.
-- 			(i.e. auto creation/deletion of rows in concert with creation/deletion of associated POTS ports).
--		 - For bponPotsPortCallCntlPmCollectInd and bponPotsPortCallCntlNumPMIntervals attributes in bponPotsPortTable,
--		   made following comment:
--			As of future release beyond ISAM4.5, must also be SUPPORTED for Veip-style VoIP.
--			And also made similar timeframe SUPPORT comment in intro section of following related tables:
--				- gponPotsCallCntlCurrentIntervalTable and gponPotsCallCntlIntervalTable
--
-- FR ALU01811373 - Issue when trying to change ifAdminStatus & bponPonConfigAuthMethod in the same PDU
--
--         	Added following statement to bponPonConfigAuthMethod attribute in bponPonConfigTable:
--		Modification is SUPPORTED, but only if PON port is Admin DOWN.
--
--	
-- ALU00123633 - Subtending Interface on GPON LT
--	Added following attributes to 	bponOntPlanCardTable
--		bponOntPlanCardConnectNodeType
--		bponOntPlanCardTransparentMode
--
--
-- ALU01323051 - CM/CT/CU require GPON  OLT can support loop inspection and alarm function
--	Added gponOntLoopDetectTable
--
--
-- ALU01805906 - STC KPI: 64-bit counter requirement - OLT part
--	Added following attributes to gponOntOntsideAggGemCurrentIntervalTable:
--		gponOntOntsideAggGemCurrentIntervalReceiveBlocksCounter64
--		gponOntOntsideAggGemCurrentIntervalTransmitBlocksCounter64
--	Added following attributes to gponOntOntsideAggGemIntervalTable:
--		gponOntOntsideAggGemIntervalReceiveBlocksCounter64
--		gponOntOntsideAggGemIntervalTransmitBlocksCounter64
--	Added following attributes to gponOntOltsideODAggGemCurrentIntervalTable:
--		gponOntOltsideODAggGemCurrentIntervalReceiveBlocksCounter64
--		gponOntOltsideODAggGemCurrentIntervalTransmitBlocksCounter64	
--	Added following attributes to gponOntOltsideODAggGemIntervalTable:
--		gponOntOltsideODAggGemIntervalReceiveBlocksCounter64
--		gponOntOltsideODAggGemIntervalTransmitBlocksCounter64	
--
--
-- ALU01813827 - GPON UNI Octet PM counter improvements - OLT side
--	Added following attributes to gponEtherTrafficCurrentIntervalTable
--		gponEtherTrafficCurrentIntervalTxBytesCounter64
--		gponEtherTrafficCurrentIntervalRxBytesCounter64
--	Added following attributes to gponEtherTrafficIntervalTable
--		gponEtherTrafficIntervalTxBytesCounter64
--		gponEtherTrafficIntervalRxBytesCounter64
--
--
--
-- John Boyle - 6/26/2012
-- For ISAM4.4.02
--
-- ALU01798237 - Deletion of SIP / MGC configuration possible even when associated with POTS port
--
-- 	In intro descriptions of gponOntMgcConfigTable and gponOntSipConfigTable, modified VALIDATION rule
--	back to original statements to say following:
-- 		VALIDATION:  A row cannot be deleted if has an associated POTS port.
--
-- John Boyle - 6/25/2012
-- For ISAM4.4.02
--
-- ALU01792234 - FR - Fail to Authenticate with LOID Precedence Mixed Mode Under Same PON
--
--	Added following codepoint to bponPonConfigAuthMethod attribute in bponPonConfigTable:
--		3 = LOID precedence mix authentication
--
-- John Boyle - 6/21/2012
-- For ISAM4.4.02
--
-- ALU01798237 - Deletion of SIP / MGC configuration possible even when associated with POTS port
--
-- 	In intro descriptions of gponOntMgcConfigTable and gponOntSipConfigTable, modified VALIDATION rule to say following:
-- 		VALIDATION:  A row cannot be deleted if has an associated POTS port that is Admin UP.
--
-- ALU01438625 - SFU/MDU Voice XML File Downloading over OMCI
--
-- 	In gponVoipServiceTable, deleted following codepoint from gponVoipServiceConfigMethod attribute:
--		4 = OMCI FTP Complete.  
--
-- John Boyle - 6/8/2012
-- For ISAM4.4.02
--
-- ALU01438625 - SFU/MDU Voice XML File Downloading over OMCI
--
-- 	In gponVoipServiceTable, added following codepoints to gponVoipServiceConfigMethod attribute:
--		3 = OMCI FTP (NOTE: With this setting, OLT fetches configuration file from external FTP server
--		      and pushes file to ONT using the OMCI channel.
--		      This codepoint value was introduced in ISAM4.4.02.
--		4 = OMCI FTP Complete.  This codepoint value is used only in conjunction with setting 3 above (i.e. OMCI FTP).
--		      It is used to convey that necessary OMCI FTP method download activity is completed.
--		      This value is set internally by OLT and is read-only. 
--		      This value CANNOT be SET by manager, and such attempt should be rejected by OLT.
--		      This codepoint value was introduced in ISAM4.4.02.
--
--
--
-- John Boyle - 4/12/2012
-- For ISAM4:
--
-- ALU01780585 - Background Rogue ONT test should be disabled by default
--
--	For bponPonConfigRogueTestEnableDisableCmd attribute in bponPonConfigTable, changed DEFAULT description:
--		  Default = 2 (as of ISAM4.0.10) - Disable
--		  Default = 3 (in ISAM4.2.33) - Enable
--		  Default = 2 (as of ISAM4.4) - Disable
--
--	For bponPonConfigBkgdRogueTestEnableDisableCmd attribute in bponPonConfigTable, changed DEFAULT description:
--               	Default = 1 (in ISAM4.2.33) - Enable
--	   	Default = 2 (as of ISAM4.4) - Disable
--
-- John Boyle - 3/16/2012
-- For ISAM4:
--
-- For following tables, removed implication that they are ONLY relevant for 'standard VoIP' configuration. 
-- Intention is that they are potentially relevant whenever associated row in gponOntIpHostTable is configured.
--	- gponOntIpHostOpInfoTable
--	- gponIpHostCurrentIntervalTable
--	- gponIpHostIntervalTable
--
-- ALU01186229 -CHN GPON OLT PM counter - phase 1
-- 	Added following attributes to gponOltsidePonPortTroubleshootCounterTable:
--		- gponOltsidePonPortDnEthernetFrames
--          		- gponOltsidePonPortUpEthernetFrames
--           		- gponOltsidePonPortDnEthernetOctets
--            	- gponOltsidePonPortUpEthernetOctets
--            	- gponOltsidePonPortDnJabbers       
--            	- gponOltsidePonPortUpJabbers
--
-- ALU01747919-CHN GPON ONU PM counter - OLT part
--	Added following attributes to bponOntTable:
--		- bponOntOntsidePonPortPmCollectInd
--		- bponOntOntsidePonPortPmNumPMIntervals
--	Added following tables:
--		- gponOntOntsidePonPortPmCurrentIntervalTable
--		- gponOntOntsidePonPortPmIntervalTable
--	Added following attributes to gponEtherTrafficCurrentIntervalTable:
--		- gponEtherTrafficCurrentIntervalTxJabbers
--		- gponEtherTrafficCurrentIntervalRxJabbers 
--	Added following attributes to gponEtherTrafficIntervalTable:
--		- gponEtherTrafficIntervalTxJabbers
--		- gponEtherTrafficIntervalRxJabbers 
--
--
--
-- John Boyle - 2/29/2012
-- For ISAM4.4
--
-- RCR ALU00719164 - OMCI extension: ME for remote MDU mgmt - OLT part
--
--	Updated introductory text of gponOntIpHostTable to account for following:
-- Prior to ISAM4.4, this table was only used for standard VoIP service. For standard VoIP service, rows in this table use the same ifIndex as the 
-- Virtual UNI that is auto-created in the IFM MIB (stemming from appropriate setting of bponOntVoipCapability attribute in bponOntTable).
--
-- As of ISAM4.4, if bponOntIPHCCapability attribute in bponOntTable is set to SUPPORTED then rows in this table
-- can also use the same ifIndex that corresponds to a VLAN.PORT in the IFM MIB.  As of ISAM4.4, the only relevant usage in this manner
-- is for ONT SNMP agent service that uses IP service explicitly configured via this MIB,  Such association is conveyed via corresponding
-- ifIndex value in gponSnmpIpServiceIPHC attribute in gponSnmpIpServiceTable.
--
-- VALIDATION:  As of ISAM4.4, a specific ONT can have at most a single row represented in this table.  Thus, for a specific ONT there
--	can be no conflict regarding the usage format of the ifIndex.
--
-- VALIDATION:  Regarding VoIP for a specific ONT, creation of a row in this table must be MUTUALLY EXCLUSIVE
-- 	with creation of a row in gponOntVoipServiceTable that would use same ifIndex in Interface MIB 
--	(i.e. either legacy Voip or standard Voip - but not both). 
--
-- VALIDATION:  As of ISAM4.4, for a specific ONT, cannot configure both legacy VoIP service and SNMP agent service that uses IP service 
--	explicitly configured in this MIB.
--
-- 	For gponOntIpHostVlanPointer attribute in gponOntIpHostTable, updated description with following:	
--		 When ifIndex format for table row represents Virtual UNI, then no default is permitted. Legitimate value 
--		 must be supplied by manager.
--		 When ifIndex format for table row represents VLAN.PORT, then default is 0.  
--
-- 	For gponSnmpIpServiceIPHC attribute in gponSnmpIpServiceTable, touched up description as follows:
--		This attribute was introduced with ISAM4.4.
--
--                   	When non-zero, this attribute must point to an appropriate row in gponOntIpHostTable. This would
--	     	be the situation when ONT SNMP agent uses IP service explicitly configured via this MIB.  When used
--	     	in this manner, the ifIndex format must be the appropriate VLAN.PORT ifIndex (for the corresponding row
--	     	in gponOntIpHostTable).
--
--                   	Zero means ONT SNMP agent uses IP service configured internally via VEIP mechanisms.
--                   
--                   	Default = 0 = SNMP over VEIP.
--
--		Modification is SUPPORTED.
--
--
-- John Boyle - 2/21/2012
-- For ISAM4.4
--
-- 	RCR ALU01430222 - GPON: Enhanced Downstream Frame Handling - MIB Support
--		Added bponOntDownstreamTagMode attribute to bponOntTable.	
--
-- John Boyle - 2/4/2012
-- For ISAM4.4
--
-- Carried forward following update from ISAM4.3.02:
-- 	RCR ALU01571622 - Support 24 POTS lines per POTS slot in FX/FD Platform.
--
--		Made statement 'As of ISAM4.3.02, the range is increased to 0..24' for following attributes in following tables:
--			- bponOntPlanCardNumPotsPorts attribute in bponOntPlanCardTable
--			- bponOntActualCardNumPotsPorts attribute in bponOntActualCardTable
--
-- John Boyle - 1/20/2012
-- For ISAM4.4
--
-- RCR ALU00123609 - PON Redundancy For GPON Linecards
--	For gponPonProtectTable, noted that as of ISAM4.4 this table in NOT SUPPORTED.  All PON protection
--	functionality is henceforth subsumed by new mechanisms incorportated into EQIPMENT MIB.
--
-- John Boyle - 1/19/2012
-- For ISAM4.4
--
-- RCR ALU01284906 - ME Extension for PoE Management.
--	Commented out bponLanEtherPortPowerPairPinoutControl attribute in bponLanEtherPortTable, and mentioned 
--	that as of ISAM4.4 attribute is NOT SUPPORTED.
--
-- John Boyle - 1/13/2012
-- For ISAM4.4
--
--  ALU01192818 - HPNA ONT Support
-- 	For hpnaPortSpIndex attribute in hpnaPortTable, changed ACCESS method FROM not-accessible TO read-only.
--
--
-- John Boyle - 1/10/2012
-- For ISAM4.4
--
--  ALU01192818 - HPNA ONT Support
--	Started with hpnaPortTable from FTTU-HPNA-MIB, adapted the attributes to fit the ISAM style of provisioning (which included commenting out 
--	many of the attributes), and merged the resultant table into this GPON-MIB.
--
-- Zhang Tinghui - 12/14/2011
-- For ISAM4.4
-- RCR ALU00719164 - OMCI extension: ME for remote MDU mgmt - OLT part
--      Added bponOntIPHCCapability in bponOntTable
--      Added new table gponSnmpIpServiceTable
--
--
--
-- John Boyle - 11/18/2011
-- For ISAM4.4
--
-- RCR ALU01324314 - Rogue ONT Detection Enhancements
--	- For bponPonConfigBkgdRogueTestInterval attribute in bponConfigTable, changed the lower bound
--	  from 15 minutes to 60 minutes
--
-- Carried forward following from ISAM4.3.01:
-- RCR ALU01582530 - Decouple GPON ONU SW Version Control on OLT.
--
--	For following attributes in following tables:
--		- bponOntSwPlannedVersion attribute in bponOntTable
--		- gponOntSwVerCtlPlannedSwVersion attribute in gponOntSwVerCtlTable
--	Updated and added new following text to descriptions:
--
--		  The special string value UNPLANNED means that any download and activation processing 
--		  associated with this attribute is inhibited.  UNPLANNED also means that the OLT will not provision this
--		  ONT via OMCI with relevant information from the OLT MIB.
--
--		  As of ISAM4.3.01, the special string value DISABLED means that any download and activation processing
--		  associated with this attribute is inhibited.  However, unlike UNPLANNED string, the DISABLED string
--		  means that the OLT will provision this ONT via OMCI with relevant information from the OLT MIB.
--
-- John Boyle - 11/11/2011
-- For ISAM4.4
--
-- RCR ALU01284906 - ME Extension for PoE Management.
-- 	Added following attributes to bponLanEtherPortTable:
--		- bponLanEtherPortPowerControl
--		- bponLanEtherPortPowerPairPinoutControl
--		- bponLanEtherPortPseClassControl
--	Added following attributes to bponLanEtherPortOpstatTable:
--		- bponLanEtherPortOpstatPoECapabilities
--		- bponLanEtherPortOpstatPowerPairPinoutActual	
--		- bponLanEtherPortOpstatPowerDetectionStatus
--		- bponLanEtherPortOpstatPowerClassStatus
--
-- RCR ALU01186193 - GPON Support new ME 'ONU capability'  from CTC GPON2.0 spec - OLT part
--	Added following attributes to bponOntTable:
--		- bponOntCtcSpecVersion
--  		- bponOntCtcOntType
--		- bponOntCtcTxPowerControl
--
--
-- John Boyle - 10/24/2011
--
-- For ISAM4.4
-- RCR ALU01322604 - VEIP and VEIP associated TR069MgtServer 
--	Deleted gponTR069ServerAssoUni attribute from gponTR069ServerTable
--
--
-- For ISAM4.4
--
-- RCR ALU01324314 - Rogue ONT Detection Enhancements
--
--     	 	- In bponPonConfigTable, added following attribute:
--			- bponPonConfigBkgdStuckLaserTestCmd
--
-- Wei Yanqin - 10/21/2011
-- For ISAM 4.4
-- RCR ALU01263602 FX GPON:CVLAN translation
--      Added a new attribute bponOntVlanTranslateMode to bponOntTable.
--
--
-- Sun Baoping - 10/21/2011
-- For ISAM4.4
-- RCR ALU01322604 - VEIP and VEIP associated TR069MgtServer 
--	Added new table gponTR069ServerTable
--
--
-- MA Liya - 10/14/2011
-- For ISAM 4.4
--
-- RCR ALU01186189 - N:MP OMCI mgt model support without GEM port sharing cross UNI (Phase1) - OLT part
--      		-  Added a new attribute bponOntVlanBridgeMappingMode to bponOntTable.
--
--
-- John Boyle - 10/13/2011
-- For ISAM4.4
--
-- RCR ALU01324314 - Rogue ONT Detection Enhancements
--	
--     	 	- In bponPonConfigTable, added following attributes:
--			- bponPonConfigBkgdRogueTestEnableDisableCmd
--			- bponPonConfigBkgdRogueTestInterval
--		- For bponPonConfigRogueTestEnableDisableCmd attribute in bponPonConfigTable:
--			- Added new codepoint to initiate PON Rogue Pattern Test, and made it the new default.
--
-- RCR ALU01192818 - Support HPNA ONT
--
-- 		- Mentioned support for Card Type 192 (HPNA) in following attributes of following tables:
-- 			- bponOntPlanCardType attribute in bponOntPlanCardTable
--			- bponOntPlanCardNumNonPotsPorts in bponOntPlanCardTable
--			- bponOntPlanCardNumPotsPorts in bponOntPlanCardTable
-- 			- bponOntActualCardType attribute in bponOntActualCardTable
--
-- John Boyle - 4/29/2011
-- For ISAM4.3
--
-- 	Baselined previous E3P2 changes to proper E3P1 MIB.
--
-- Guan Yue - 4/29/2011
-- For ISAM4.3.02
-- RCR ALU01006981 - CTC V2.0 GPON LOID+Password ONT registration
--	Added following attributes to bponOntTable
--		- bponOntLogicalAuthID
--		- bponOntLogicalAuthPassword
--	Added following attributes to bponPonConfigTable
--		- bponPonConfigAuthMethod
--	Added following attributes to bponPonDiscovOntTable
--		- bponPonDiscovOntLogicalAuthId
--
-- John Boyle - 4/22/2011
-- For ISAM4.3
--
-- RCR ALU00946602 - PON 40km ranging window & ONT differential
--	In order to be in alignment with FTTU feature parity, made following updates:
--		- For bponOntOpInfoPloamCurrStatus attribute in bponOntOpInfoTable, added following codepoints:
--		 	25 = ONT Power Up Error (ONTPWRERR)
--		 	26 = Rogue ONT Disabled (ROGUEONTDIS)
--		 	27  = Differential Reach Exceeded (DIFREACH)
--		 	28 thru 32 = Undefined - Not Supported
--		- For bponPonDiscovOntDisableIndicator attribute in bponPonDiscovOntTable, added following codepoint:
--			DIFREACH - meaning ONT has been deactivated because its location on the PON has exceeded its
--			differential reach capability.
--			
--
-- John Boyle - 3/24/2011
-- For ISAM4.3
--
--	Carried forward from ISAM4.2.20:
--	Per official-agreement between Mike Shaffer (PLM) and development organization:
--	For following tables, noted that they are NOT SUPPORTED as of ISAM4.2.02:
--		- gponPotsCallCntlIntervalTable
--		- gponPotsRtpIntervalTable
--		- gponIpHostIntervalTable
--		- gponOntSipIntervalTable
--		- gponOntSipCallInitIntervalTable
--		- gponOntMgcIntervalTable
--		- gponOntFecIntervalTable
--		- gponOntEquipExtenTable
--		- gponOntEquipExtenInfoTable
--
-- John Boyle - 3/16/2011
-- For ISAM4.3:
--
-- 	Updated intro section of gponOntIpHostPingTestTable to say following:
-- 		It is NOT SUPPORTED yet for any targeted ISAM release. 
--
-- John Boyle - 3/16/2011
-- For ISAM4.3
--
--  Following FR changes carried forward from ISAM4.2:
--
--  FR_IR ALU01155045 - Modification of Gateway softswitch vendor possible even if POTS port is associated to Voip
--
-- 	Removed 'modification qualifier' statement from following attributes in following tables:
--		- In gponOntMgcConfigTable:
--			gponOntMgcConfigTerminationIdBase	
--			gponOntMgcConfigSoftswitchVendor
--		- In gponOntSipConfigTable:
--			gponOntSipConfigSoftswitchVendor
--		
--
--  FR_IR ALU01155046 - Modification of some IP host parameters possible even though VoIP UNI is not admin OOS
--
-- 	Removed 'modification qualifier' statement from following attributes in gponOntIpHostTable, and mentioned
--	that edit may be service-affecting:
--		gponOntIpHostDhcpInd	
--		gponOntIpHostRespondToPingsInd	
--		gponOntIpHostRespondToTraceRouteInd
--		gponOntIpHostOntIdentifier	
--		gponOntIpHostIpAddress	
--		gponOntIpHostSubnetMask	
--		gponOntIpHostDefaultGateway
--		gponOntIpHostPrimaryDns	
--		gponOntIpHostSecondaryDns
--		gponOntIpHostDhcpDscpSetting
--
--
-- John Boyle - 3/1/2011
-- For ISAM4.3
-- RCR ALU00123839 - Embedded OTDR on GPON LT
--	- For gponPonOltsideOpInfoSpecialFeatures in gponPonOltsideOpInfoTable (ALU00123839):
--	  Changed codepoints to reflect following:
--                   20H : Default
--                   21H : Supports 2500BASE-X 
--                   22H : 10/100BASE FX/LX with PHY/SGMII
--                   23H : 10/100/1000BASE-T Electrical with PHY/SGMII and without LOS
--                   24H : 10/100/1000BASE-T with PHY/SGMII and with LOS
--                   25H : Ethernet to E1/T1 
--                   26H : GPON OLT
--                   27H : GPON OTDR capable 
--
--
-- John Boyle - 2/17/2011
-- For ISAM4.3
--
--	For bponPonConfigReach attribute in bponPonConfigTable:
--		- Mentioned that attribute is only applicable for GPON.
--		- And noted following: As of ISAM4.3, this attribute is SUPPORTED
--		  (with same allowed value constraints as FTTU4.7.4).
--
--
-- John Boyle - 2/4/2011
-- For ISAM4.3
--
-- RCR ALU00946602 - PON 40km ranging window & ONT differential
--	Uncommented following attribute, and noted that it must be SUPPORTED as of ISAM4.3:
--		- bponPonConfigReach attribute in bponPonConfigTable
--
-- In a few places throughout commentary sections of MIB, changed following TYPO:
--	Changed FROM gponIpHostConfigTable TO gponIpHostConfigTable
--
--
-- John Boyle - 1/31/2011
-- For ISAM4.3
--
-- RCR ALU00755077 - Dual SIP Stack/ client supporting - OLT impact
--	- Added gponPotsPortOpstatTable
--
--
-- John Boyle - 12/8/2010
-- For ISAM4.3
--
-- RCR ALU00755077 - Dual SIP Stack/ client supporting - OLT impact 
--
--	- In intro descriptions of gponVoipServiceTable and gponOntIpHostTable, clarified that MUTUAL EXCLUSIVITY
--	  (from a VoIP service perspective) means that rows cannot exist that would represent the same ifIndex in the IFM MIB.
--
--	- For bponOntVoipCapability attribute in bponOntTable, added new codepoint = 3 = VEIP-style VoIP.
--
--	- Added SpIndexOrZero as a new type definition that extends the SpIndex definition to also include the value 0 (for cases where
-- 	  a null pointer must also be considered). 
--
--	- Added bponPotsPortVeipPointer attribute to bponPotsPortTable (using SpIndexOrZero syntax as mentioned above).
--	  Also added some validation statements regarding when it can be set to a non-zero value.
--
--	- For all attributes in bponPotsPortTable, made comments regarding relevance for ISAM4.3 including relevance/non-relevance for 
--	  situation when bponOntVoipCapability attribute is set to VEIP-style VoIP.
--
--	- For following attributes in tables (which effectively control whether various POTS line tests can be initiated), indicated whether 
--	  test can be executed if bponOntVoipCapability attribute is set to VEIP-style VoIP:
--		- gponPotsMltTestCmd in gponPotsMltTestTable (SUPPORTED if VEIP-style VoIP).
--		- gponPotsSipDialTestCmd in gponPotsSipDialTestTable (NOT SUPPORTED if VEIP-style VoIP).
--		- gponPotsDialTestCmd in gponPotsDialTestTable (NOT SUPPORTED if VEIP-style VoIP).
--
-- John Boyle - 12/8/2010 - 
-- 	Merged following changes from Katrien (from 7/28/2010) into into newest 12/8/2010 MIB (based on ISAM4.2.20 - 10/18/2010)
-- Katrien SCHARRE - 7/28/2010
-- For ISAM4.3:
--
-- RCR ALU00123839 - Embedded OTDR on GPON LT
--	- Added gponPonOltsideOpInfoSpecialFeatures in gponPonOltsideOpInfoTable. (ALU00123839)
--
--
--
-- John Boyle - 10/18/2010
-- For ISAM4.2
--
--	- Added bponPotsPortFileNamePart attribute to bponPotsPortTable
--
--
-- John Boyle - 10/12/2010
-- For ISAM4.2
--
--  ALU00820181 - GPON MIB Has Clashing OIDs
--	Due to FTTU4.7.x and ISAM4.2.x release concurrency, and cross-fertilization of RCRs, I let a GPON MIB
--	OID clash slip through the cracks.  So had to make following changes:
--		For following attributes in bponPonConfigTable, moved their OIDs as follows:
--			bponPonConfigMcastGemPmCollectInd  - FROM 27 TO 28
--        			bponPonConfigMcastGemPmNumPMIntervals  - FROM 28 TO 29
--
--  Noted that following tables/attributes are SUPPORTED as of ISAM4.2.02 (instead of ISAM4.2):
--
--	- In bponPotsPortTable
--		- bponPotsPortImpedance
--	- In bponOntTable:
--		- bponOntFecPmCollectInd	
--		- bponOntFecPmNumPMIntervals
--	- gponOntFecCurrentIntervalTable
--	- gponOntFecIntervalTable
--
--
-- John Boyle - 9/24/2010
-- For ISAM4.2
--
-- Added InterfaceIndexOrZero definition to IMPORTS section - FROM ITF-MIB
-- Then changed the SYNTAX of the following attributes in bponPotsPortTable, to use this new convention:
--	bponPotsPortMgcConfigPointer
--	bponPotsPortSipConfigPointer
--
-- In bponPotsPortTable, made following changes:
--	- Commented out bponPotsPortSipUserPassPointer (NOT SUPPORTED)
--	- Added following attributes:
--		bponPotsPortSipValidScheme
--		bponPotsPortSipUsername	
--		bponPotsPortSipPassword	
--		bponPotsPortSipRealm	
--	
--
--
-- John Boyle - 9/22/2010
-- For ISAM4.2
--
-- 	- Deleted bponOntRealIfIndex attribute to bponOntTable - since the FR ALU00184026 was rejected
--		in favor of another RCR that is targeted beyond ISAM4.2.30 (will deal with it then..).
--
-- 	- In gponVeipPortTable, fixed some typos in descriptions of following attributes:
--		- gponVeipPortEtherTrafficPmCollectInd
--		- gponVeipPortEtherTrafficNumPMIntervals
--
-- John Boyle - 9/17/2010
-- For ISAM4.2
--
--  ALU00184026 - Additon of real ifIndex to GPON MIB
--	- Added bponOntRealIfIndex attribute to bponOntTable
--
--  ALU00333231 - Extra parameters in GPON MIB
--	- Added following tables/attributes to ISAM4.2 MIB, even though they are not supported until ISAM4.2.30:
--		- Added gponPonSummaryInfoTable
--		- Added gponOntSummaryInfoTable
--
-- In gponOntVoipConfigTable, added following validation statement:
-- 	VALIDATION: A row cannot be deleted if a corresponding row in gponOntMgcConfigTable or
--	gponOntSipConfigTable is provisioned for this ONT.
-- For gponOntVoipConfigSecureUriPointer attribute in gponOntVoipConfigTable, changed description to say following:
--		 Value 0 (meaning none specified) is permitted.  
--		 This attribute is only relevant if VoipConfigMethod is NOT via OMCI.
--		 If ConfigMethod is via OMCI, then this pointer must be 0.
-- For gponOntVoipConfigRetrieveProfileCmd attribute in gponOntVoipConfigTable, added following clarification:
--		 This command attribute is only relevant if VoipConfigMethod is NOT via OMCI.
-- In gponOntIpHostTable, extended the the deletion validation statement in table intro description to say following:
--	VALIDATION:  A row cannot be deleted if there exists a corresponding row
--	in  gponOntMgcConfigTable or gponOntSipConfigTable or gponOntVoipConfigTable.
--	NOTE: corresponding means that they share the same Ip Host ifIndex.
-- In gponOntMgcConfigTable and gponOntSipConfigTable, added following validation statement:
-- 	VALIDATION:  A row cannot be deleted if has an associated POTS port.
--
--
-- John Boyle - 9/13/2010
-- For ISAM4.2
--
--	Added following VALIDATION statement is description section of bponPotsPortTable:
-- 		VALIDATION: Beginning with ISAM4.2.02, for a specific ONT, a POTS port
-- 		can be associated with one of the following 3 Voip agent types: legacy, standard MGC,
-- 		or standard SIP.  The legacy versus standard style decision is controlled via the
-- 		bponOntVoipCapability attribute in bponOntVoipTable.  The standard MGC versus 
-- 		standard SIP decision is controlled via mutually exclusive pointers in the 
-- 		bponPotsPortMgcConfigPointer and bponPotsPortSipConfigPointer attributes of this table.
-- 		Once the OLT has sufficient information to clearly know the VoIP agent type selection, it
-- 		should reject SET commands on POTS port attributes that are irrelevant for the known VoIP agent type. 
--
--
-- John Boyle - 9/8/2010
-- For ISAM4.2
--
--	For gponRingSequenceProfilePattern2Pointer through gponRingSequenceProfilePattern5Pointer attributes
--	in gponRingSequenceProfileTable, added following notes:
--		 Default = 0 (null pointer).
--		 VALIDATION:  Once a null value has been established for a pointer, all subsequent
--			pattern pointers in this table must also be null.
--
-- John Boyle - 9/8/2010
-- For ISAM4.2
--
--	For gponToneSequenceProfilePattern2Pointer through gponToneSequenceProfilePattern8Pointer attributes
--	in gponToneSequenceProfileTable, added following notes:
--		 Default = 0 (null pointer).
--		 VALIDATION:  Once a null value has been established for a pointer, all subsequent
--			pattern pointers in this table must also be null.
--
-- John Boyle - 8/31/2010
-- For ISAM4.2
--
--	- For ALU00500716 - Support of Missing OMCIv1 Attributes: 
--  		- Added gponOntEquipExtenTable
--		- Added gponOntEquipExtenInfoTable
--
--	- For bponOntFecPmCollectInd attribute in bponOntTable, changed default to 2 = Disabled.
--
--	- For bponOntVoipCapability attribute in gponOntTable, extended codepoints to reflect following:  
--		0 = ONT should NOT support VoIP (default).
--		1 = ONT should support VoIP (only legacy mode using gponVoipServiceTable)
--		2 = ONT should support Voip (only standard mode using gponOntIpHostTable)
--	- In gponVoipServiceTable and gponIpHostTable, updated description regarding mutual exclusivity
--	  of the 2 tables in relation to setting of bponOntVoipCapability attribute.
--
--	- In bponPonConfigMcastGemPmNumPMIntervals attribute of bponPonConfigTable, corrected
--	  the table reference in the commentary.
--
--
-- John Boyle - 8/23/2010
-- For ISAM4.2
--
--  	- Eliminated the bponOntVoipStyle attribute from bponOntTable. Determination of legacy versus standard VoIP will
--	now be determined based on which table is first created:  gponVoipServiceTable or gponIpHostTable.
--	- Updated all other description sections of MIB that referenced this eliminated attribute, and tried to convey
--	the new approach.
--
--	- Added validation statements to gponOntMgcConfigTable and gponOntSipConfigTable that mentioning that rows 
--	cannot be created unless they agree with signalling method chosen in gponOntVoipConfigSignallingProtocol
--	attribute of gponOntVoipConfigTable.
--
-- John Boyle - 8/13/2010
-- For ISAM4.2
--
--	Added following attributes to gponEtherTrafficCurrentIntervalTable
--		- gponEtherTrafficCurrentIntervalRxPackets
--		- gponEtherTrafficCurrentIntervalTxPackets
--	Added following attributes to gponEtherTrafficIntervalTable
--		- gponEtherTrafficIntervalRxPackets
--		- gponEtherTrafficIntervalTxPackets
--
--
-- John Boyle - 8/13/2010
-- For ISAM4.2
--
--	In following attributes, corrected typo:  from PMCA to PCMA
--		- gponPotsVoipOpstatCodecUsed attribute in gponPotsVoipOpstatTable
--		- gponVoipMediaProfileCodec1stOrder attribute in gponVoipMediaProfiletable
--
--	In bponOntPlanCardTable and bponOntActualCardTable, annotated various attributes to convey notion
--		that card type 48 (VEIP) is NOT SUPPORTED until ISAM4.2.02.
--
--	Noted that gponVeipPortTable is NOT SUPPORTED until ISAM4.2.02, and also added following attributes
--		- gponVeipPortEtherTrafficPmCollectInd
--		- gponVeipPortEtherTrafficNumPMIntervals
--
--
-- John Boyle - 7/23/2010
-- For ISAM4.2
--
--  Added following VALIDATION RULE for bponPotsPortVoipMediaPointer attribute in bponPotsPortTable:
--
--		 RULE1: OLT will REJECT any provisioning which would cause ALL of following to be
--			 TRUE for 2 or more POTs ports::
--		 1) POTS ports are on same ONT.
--		 2) POTS ports are associated with same SIP agent or same MGC agent
--		 3) POTS ports are In-Service (i.e. bponPotsPortAdminState = unlocked).
--		 4) POTS ports point to different Media Profiles (i.e. value of this pointer attribute is NOT identical).
--
-- For a number of attributes in gponOntIpHostTable, made following notation regarding modification permission:
--   		  - Modification is SUPPORTED  - but only if associated IP Host UNI is Admin OOS. 
--
--
--
-- John Boyle - 7/16/2010
-- For ISAM4.2
--
--	- Did my best to note which tables were introduced in ISAM4.2, but NOT SUPPORTED until ISAM4.2.02.
--
-- John Boyle - 7/13/2010
-- For ISAM4.2
--
--	- RCR ALU00505245 - Add Missing OMCIv1 PM Support to OLT
--		- Added following new PM tables:
--			- gponOntFecCurrentIntervalTable 
--			- gponOntFecIntervalTable 
--		- Added following new attributes to bponOntTable:
--			- bponOntFecPmCollectInd	
--			- bponOntFecPmNumPMIntervals
--
--	- Corrected various comments to now reflect the following:
--		- bponPotsPortCustomerInfo - SUPPORTED
--		- bponPotsPortOperState - SUPPORTED
--
-- John Boyle - 7/2/2010
-- For ISAM4.2
--
--	- BDFam59279 carried froward from FGU4.7.04.  Added many more Ethernet PM attributes to following tables:
--		- gponEtherTrafficCurrentIntervalTable
--		- gponEtherTrafficIntervalTable
--
--	- Added following validation to up-front description in gponOntIpHostTable
-- 		VALIDATION:  A row cannot be deleted if there exists a corresponding row
--		in either gponOntMgcConfigTable or gponOntSipConfigTable.
--		NOTE: corresponding means that they share the same Ip Host ifIndex.
--
-- John Boyle - 6/28/2010
-- For ISAM4.2
--
-- 	For ISAM R4.2 RCR ANTmt80984:PT Counters and Statistics (done by ALIL).
-- 	Original changes done by Sankar Ramachandran
-- 	The following table is removed because GEM port level counters are descoped from this RCR:
--		- gponOltsidePonGemPortTroubleshootCounterTable
--
--
-- John Boyle - 6/25/2010
-- For ISAM4.2
--
--	- New direction from PLM is to support both old proprietary OMCI VoIP and new standard OMCI VoIP
--	  in same release.  This means both old and new provisioning methods (via this MIB)
--	  must be supported.  In order to accomplish this, made following changes:
--		- Added back the gponVoipServiceTable as being SUPPORTED (with attribute specific notes regarding ISAM4.2).
--		- Added back the gponVoipServiceOpInfoTable as being SUPPORTED (with attribute specific notes regarding ISAM4.2).
--		- Added back the gponVoipServiceOntsideGemCurrentIntervalTable as being SUPPORTED
--		    (with attribute specific notes regarding ISAM4.2).
--		- Added back the gponVoipServiceOntsideGemIntervalTable as being SUPPORTED
--		    (with attribute specific notes regarding ISAM4.2).
--		- Added back the gponVoipServiceOltsideGemCurrentIntervalTable as being SUPPORTED
--		    (with attribute specific notes regarding ISAM4.2).
--		- Added back the gponVoipServiceOltsideGemIntervalTable as being SUPPORTED
--		    (with attribute specific notes regarding ISAM4.2).
--		- Added bponOntVoipStyle attribute to bponOntTable.
--		- Added following validation statement to intro section of gponVoipServiceTable:
--			- VALIDATION:  A row can only be created if bponOntVoipStyle = 1 (Legacy style).
--		- Added following validation statement to intro sections of following tables:
--			- VALIDATION:  A row can only be created if bponOntVoipStyle = 2 (Standard style).
--				- gponOntIpHostTable
--				- gponOntVoipConfigTable
--				- gponOntMgcConfigTable
--				- gponOntSipConfigTable
--		- For all attributes in bponPotsPortTable, made distinctions which attributes are relevant depending on 
--			whether bponOntVoipStyle setting is Legacy mode or Standard mode.
--		- For gponPotsVoipOpstatTable, noted in table description that auto-creation only occurs
--			if bponOntVoipStyle = 2 (Standard style).
--		- For all of the profile tables that are only used if bponOntVoipStyle = 2 (Standard style), made following notes:
-- 			- This table was first introduced with ISAM4.2 MIB.
--			- It is only SUPPORTED beginning with ISAM4.2.02 release.
--
--
-- John Boyle - 6/17/2010
-- For ISAM4.2
--
--	- Added gponOntMgcConfigTcpUdpPortNum attribute to gponOntMgcConfigTable.
--	- For gponOntSipConfigTcpUdpPortNum attribute in gponOntSipConfigTable,
--		changed range to 5000..6000.
--
-- John Boyle - 6/16/2010
-- For ISAM4.2
--
--	- For gponOntIpHostSubnetMask attribute in gponOntIpHostTable, changed valaditions to following:
--		  VALIDATION:  The OLT should enforce following rules:
--		  1) Non-contiguoius 1's are NOT permitted.
--		  2) If there are any 1's at all, they must begin at the leftmost (i.e. most-significant) bit.	
--
--	- Added following PM tables and associated enable/disable attributes as appropriate:
--		- gponIpHostCurrentIntervalTable
--		- gponIpHostIntervalTable
--			- gponOntIpHostPmCollectInd (added to gponOntIpHostTable)
--			- gponOntIpHostNumPMIntervals (added to gponOntIpHostTable)
--
--	- Added gponOntMgcConfigMessageId attribute to gponOntMgcConfigTable.
--
--
-- John Boyle - 6/11/2010
-- For ISAM4.2
--
--	Carried forward following changes made to ISAM4.0.10 MIB:
--	- In gponVoipServiceTable, noted changes to following attributes:
--		- gponVoipServiceGwySigPort - (marked as NOT SUPPORTED for ISAM4.0.10).
--		- gponVoipServiceSecretId - (marked as NOT SUPPORTED for ISAM4.0.10).
--		- gponVoipServiceSecretK - (marked as NOT SUPPORTED for ISAM4.0.10).
--		- gponVoipServiceSippingServerIpAddr - (marked as NOT SUPPORTED for ISAM4.0.10).
--		- gponVoipServiceSippingAuthUsername - (marked as NOT SUPPORTED for ISAM4.0.10).
--		- gponVoipServiceSippingAuthPassword - (marked as NOT SUPPORTED for ISAM4.0.10).
--		- gponVoipServiceSippingAuthRealm - (marked as NOT SUPPORTED for ISAM4.0.10).
--		- gponVoipServiceIpsecEnable - (marked as NOT SUPPORTED for ISAM4.0.10).
--		- gponVoipServiceSippingServerAddress - (marked as NOT SUPPORTED for ISAM4.0.10).
--		- gponVoipServiceSecondaryNetGwyIpAddr - (marked as NOT SUPPORTED for ISAM4.0.10).
--
--	- Noted that following profile table and associated scalars are NOT SUPPORTED for ISAM4.0.10:
--		- gponLargeStringProfileTable
--		- gponLargeStringProfileIndexNext
--		- gponLargeStringProfileMaxIndex
--
--	In gponVoiceServiceProfileTable, made changes to following attributes:
--		- gponVoiceServiceProfilePstnProtocolVariant - updated to add supported country codes.
--		- gponVoiceServiceProfileNetSpecificExtensionsPointer - added this attribute to allow specification
--		  of pointer to a fully-qualified file path/name.
--
-- John Boyle - 5/27/2010
-- For ISAM4.2
--
--	RCR ANTmt81009 - Motive Managed ONTs
--	- Added gponVeipGroup     OBJECT IDENTIFIER ::= { apon 30 }
--	- In bponOntPlanCardTable, updated following attributes:
--		- bponOntPlanCardType - added support for card type 48 = Virtual Ethernet Interface Point (VEIP).
--		- bponOntPlanCardNumNonPotsPorts - added support for VEIP UNis.
--		- bponOntPlanCardNumPotsPorts - added mention regarding VEIP UNIs.
--	- In bponOntActualCardTable, updated following attributes:
--		- bponOntActualCardType - added support for card type 48 = Virtual Ethernet Interface Point (VEIP).
--	- Added gponVeipPortTable.
--
--
--	- For OISGv2 VoIP, added following PM tables and associated enable/disable attributes as appropriate:
--		- gponPotsCallCntlCurrentIntervalTable
--		- gponPotsCallCntlIntervalTable
--			- bponPotsPortCallCntlPmCollectInd (added to bponPotsPortTable)
--			- bponPotsPortCallCntlNumPMIntervals (added to bponPotsPortTable)
--		- gponPotsRtpCurrentIntervalTable
--		- gponPotsRtpIntervalTable
--			- bponPotsPortRtpPmCollectInd (added to bponPotsPortTable)
--			- bponPotsPortRtpNumPMIntervals (added to bponPotsPortTable)
--		- gponSipCurrentIntervalTable
--		- gponSipIntervalTable
--			- gponSipAgentPmCollectInd (added to gponSipConfigTable)
--			- gponSipAgentNumPMIntervals (added to gponSipConfigTable)
--		- gponSipCallInitCurrentIntervalTable
--		- gponSipCallInitIntervalTable
--			- gponSipAgentCallInitPmCollectInd (added to gponSipConfigTable)
--			- gponSipAgentCallInitNumPMIntervals (added to gponSipConfigTable)
--		- gponMgcCurrentIntervalTable
--		- gponMgcIntervalTable
--			- gponMgcConfigPmCollectInd (added to gponMgcConfigTable)
--			- gponMgcConfigNumPMIntervals (added to gponMgcConfigTable)
--
--	- For bponPotsPortImpedance attribute in bponPotsPortTable, changed Default to 255.
--
--	- Changed name of attribute:
--		-  FROM gponOltPonGemPortUnDiscFrameCounter
--		-  TO gponOltPonGemPortUpDiscFrameCounter
--
--
-- John Boyle - 5/20/2010
-- For ISAM4.2
--
--	- Added following attributes to gponVoipFeatAccessCodeProfileTable:
--		- gponVoipFeatAccessCodeProfileUnattendedCallTransfer
--		- gponVoipFeatAccessCodeProfileAttendedCallTransfer
--
-- John Boyle - 5/19/2010
-- For ISAM4.2
--
--	- Marked following tables and attributes as NOT SUPPORTED:
--		- gponTextMsgProfileTable
--		- gponTextMsgProfileIndexNext and gponTextMsgProfileMaxIndex.
--	- Marked all attributes that point to gponTextMsgProfileTable as NOT SUPPORTED.
--	- Marked following tables and attributes as NOT SUPPORTED:
--		- gponSipMsgProfileTable
--		- gponSipMsgProfileIndexNext and gponSipMsgProfileMaxIndex.
--	- Marked all attributes that point to gponSipMsgProfileTable as NOT SUPPORTED.
--	- Added following tables to provide reverse mapping from profile Name to profile Number:
--		- gponAuthSecurityProfileMappingTable
--		- gponSecureUriProfileMappingTable
--		- gponRtpProfileMappingTable
--		- gponVoipMediaProfileMappingTable
--		- gponToneEventProfileMappingTable
--		- gponRingPatternProfileMappingTable
--		- gponRingSequenceProfileMappingTable
--		- gponRingEventProfileMappingTable
--		- gponVoiceServiceProfileMappingTable
--		- gponNetDialPlanProfileMappingTable
--		- gponVoipAppServProfileMappingTable
--		- gponVoipFeatAccessCodeProfileMappingTable
--		- gponSipMsgProfileMappingTable
--		- gponTextMsgProfileMappingTable
--	- For the ProfileName attribute in all of the above mentioned profiles, added following constraints:
--	     	- Must be supplied by management system.
--	     	- Cannot be null.
--	     	- Must be unique accross other profile names within this profile table.
--
-- 	For ISAM R4.2 RCR ANTmt80984:PT Counters and Statistics (done by ALIL).
-- 	Original changes done by Sankar Ramachandran
-- 	The following tables are added;
--		- gponOltsidePonPortTroubleshootCounterTable
--		- gponOltsidePonGemPortTroubleshootCounterTable
--
--
-- John Boyle - 5/4/2010
-- For ISAM4.2
--
--	- In gponVoipMediaProfileTable, made following changes to folllowing attributes:
--		- gponVoipMediaProfileFaxMode - added T.38 option.
--		- gponVoipMediaProfileCodec1stOrder - noted that all values are SUPPORTED.
--		- gponVoipMediaProfileOobDtmf  - Noted that 1 = Enabled is the default.
--		- For all codec attributes (2nd, 3rd, and 4th orders) - removed the NOT SUPPORTED comments
--		  (because let's assume everything is SUPPORTED).
--
--	- In gponVoiceServiceProfileTable, made following changes to folllowing attributes:
--		- gponVoiceServiceProfileAnnounceType - clarified that  value 255 = Not Applicable (default) - 
--		  amd means none specified and ONT can choose its own behavior.
--		- gponVoiceServiceProfileDtmfDigitLevels - limited the range to -25dBm TO -3dBm, and value 0.
--
--	
--
-- John Boyle - 4/30/2010
-- For ISAM4.2
--
--	- For ISAM R4.2 RCR ANTmt80966 (Porting FT features from R4.7.04 to R4.2):
--	- Merged the following RCRs (MIB changes) from ALIL organization.  These features 
--	  were part of FTTU4.7.4, and are merged into the ISAM4.2 baseline.
--
-- 	- Original additions done by Sengottuvelan Srirangan - 5/11/2009
--
-- ANTmt80966(ANTmt54885 - Multicast Gem Port PM:)
--
--        - In bponOntTable, added bponOntOntsideMcastGemPmCollectInd,
--       bponOntOntsideMcastGemPmNumPMIntervals attributes.
--
--          - In bponPonConfigTable, added bponPonConfigMcastGemPmCollectInd,
--       bponPonConfigMcastGemPmNumPMIntervals attributes.
--
--          - Added the following tables.
--       - gponMulticastServiceOntsideGemCurrentIntervalTable
--       - gponMulticastServiceOntsideGemIntervalTable
--       - gponMulticastServiceOltsideGemCurrentIntervalTable
--       - gponMulticastServiceOltsideGemIntervalTable
--
-- ANTmt80975(ANTmt61713 - Both ALCL and YP serial numbers in RI:)
--
--    - In bponOntTable, added bponOntYPSerialNumber attribute.
--
-- ANTmt80975(BDFam52745 - SLID availability while ONT is on PON:)
--
--    - In bponOntTable, added bponOntSLIDAvailability attribute.
--
--
-- John Boyle - 4/27/2010
-- For ISAM4.2
--
--	- Added bponPotsPortSipVoicemailUriPointer attribute to bponPotsPortTable (and reordered the OID numbers
--	  that follow this added attribute).
--
-- John Boyle - 4/26/2010
-- For ISAM4.2
--
--	- For following attributes in bponPotsPort, changed range FROM  0..86400  TO  0..60:
--		- bponPotsPortSipReleaseTimer
--		- bponPotsPortSipRohTimer
--	- Added following table to provide reverse mapping from profile Name to profile Number:
--		- gponUriProfileMappingTable
--	- Added gponOntSipConfigOpInfoTable.
--	- Added gponOntSipConfigTcpUdpPortNum attribute to gponOntSipConfigTable.
--
-- John Boyle - 4/22/2010
-- For ISAM4.2
--
--	- For every tone event in gponToneEventProfileTable, added a constraint that ToneSequence pointer and
--	  alternative tone file pointer cannot both be non-zero.
--	- Added following tables to provide reverse mapping from profile Name to profile Number:
--		- gponTonePatternProfileMappingTable
--		- gponToneSequenceProfileMappingTable
--	- Changed some notes (and syntax) to gponVoiceServiceProfilePstnProtocolVariant attribute in
--		 gponVoiceServiceProfileTable.
--	- Changed some notes to gponOntMgcConfigSoftswitchVendor attribute in gponOntMgcConfigTable.
--	- Changed some notes to gponOntSipConfigSoftswitchVendor attribute in gponOntSipConfigTable.
--	- For SCALAR gponUriProfileMaxIndex - increased max number of Uri profiles from 50 to 100.
--
-- John Boyle - 4/13/2010
-- For ISAM4.2
--
--	- Added gponPotsVoipOpstatTable
--
--	- In gponRtpProfileTable, made following updates:
--		Expanded options for following attributes:
--			- gponRtpProfilePiggybackEventsInd
--			- gponRtpProfileToneEventsInd
--			- gponRtpProfileDtmfEventsInd
--			- gponRtpProfileCasEventsInd
--		Put ranges in for following attributes:
--			-gponRtpProfileLocalPortMin
--			-gponRtpProfileLocalPortMax
--
--	- For following attributes in gponNetDialPlanProfileTable, mentioned that 
--	  OLT should only accept input on 1000 millisecond (i.e. 1 second) boundaries.
--		- gponNetDialPlanProfileCriticalDialTimeout
--		- gponNetDialPlanProfilePartialDialTimeout
--
--	- Made following changes to attributes in gponTonePatternProfileTable;
--		- Tightened individual pattern frequencies (1 through 4) range to 0..4000 Hz.
--		- Tightened modulation frequency range to 0..2000 Hz.
--		- Changed scheme for modulation power to align with scheme for individual frequency powers;
--		  i.e. Range is -25.5 dBm TO  0.0 dBm0 (where 0 represents 0x00 dBm0 and 0xFF represents -25.5 dBm0). 
--
--
-- John Boyle - 4/10/2010
-- For ISAM4.2
--
--	- In gponToneEventProfileTable:
--		- Added appropriate attributes for User Defined Tones 1 through 4.
--		- Made extensive notations to indicate that profile attributes are modifiable,
--	  	  as long as the profile is unassociated.
--
-- John Boyle - 4/9/2010
-- For ISAM4.2
--
--	- Added bponOntVoipCapability attribute to the bponOntTable.  This was carried forward from ISAM4.0.10.
--	  Mentioned that for ISAM4.2, this determines whether or not IP Host UNI is auto-created in IFM MIB.
--
--	- Noted that gponLargeStringProfileTable is NOT SUPPORTED for ISAM4.2.
--
--	- For SCALAR gponTonePatternProfileMaxIndex - increased max number of TonePattern profiles from 20 to 50.
--	- For SCALAR gponToneSequenceProfileMaxIndex - increased max number of ToneSequence profiles from 20 to 50.
--	- For SCALAR gponToneEventProfileMaxIndex - decreased max number of ToneEvent profiles from 20 to 5.
--	- For SCALAR gponRingEventProfileMaxIndex - decreased max number of RingEvent profiles from 20 to 5.
--	- For SCALAR gponVoipMediaProfileMaxIndex - decreased max number of VoipMedia profiles from 20 to 10.
--	- For SCALAR gponRtpProfileMaxIndex - decreased max number of Rtp profiles from 20 to 10.
--	- For SCALAR gponVoiceServiceProfileMaxIndex - decreased max number of VoiceService profiles from 20 to 10.
--
-- John Boyle - 4/7/2010
-- For ISAM4.2
--
--	- For bponPotsPortImpedance attribute in bponPotsPortTable, made following notations:
--		- Noted as of ISAM4.2, attribute is SUPPORTED.
--		- Extended enumerations to include value 256 (the default) - which means unspecified,
--		  and implies that OLT does NOT send such value to ONT via OMCI.
--
-- John Boyle - 4/6/2010
-- For ISAM4.2
--
--	- For SCALAR gponSecureUriProfileMaxIndex - increased max number of SecureUri profiles from 20 to 50.
--	- For SCALAR gponUriProfileMaxIndex - increased max number of Uri profiles from 20 to 50.
--
-- 	- In gponOntMgcConfigTable, made following changes to following attributes:
--		- gponOntMgcConfigPrimaryMgcAddress - Noted that value 0 is not permitted (must point to 
--			existing profile).  No default - must be provided by manager.
--		- gponOntMgcConfigSecondaryMgcAddress - Noted that value 0 is not permitted (must point to 
--			existing profile).  No default - must be provided by manager.  It is permitted to point
--			to same UriProfile as used for gponOntMgcConfigPrimaryMgcAddress.
--		- gponOntMgcConfigMaxRetryAttempts - increased upper range fromn 10 to 20.
--		- gponOntMgcConfigMessageFormat - noted options are limited to text long and text short.
--
--	- In bponPotsPortTable, noted following attributes are NOT SUPPORTED for ISAM4.2:
--		- bponPotsPortSipMsgTimeoutTCAThreshold
--		- bponPotsPortBearerPktLossTCAThreshold
--		- bponPotsPortJitterTCAThreshold
--
--
-- John Boyle - 3/29/2010
-- For ISAM4.2
--
--
--	- Changed OID number of following group:
--		- FROM	gponVoipGroup  OBJECT IDENTIFIER ::= { apon 30 }
--		- TO	gponVoipGroup  OBJECT IDENTIFIER ::= { apon 31 }	
--
-- John Boyle - 3/22/2010
-- For ISAM4.2
--
--
--	- For gponOntVoipConfigSignallingProtocol attribute in gponOntVoipConfigTable:
--		- Removed the distinction between SIP thin and SIP thick. Removed MGCP.  Now only SIP and H248.
--	- For gponOntVoipConfigOpInfoAvailSigProtocols attribute in gponOntVoipConfigOpInfoTable:
--		- Removed the distinction between SIP thin and SIP thick - now just 1 bit for SIP (period).
--
-- 	- In gponOntMgcConfigTable, added some ranges for following attributes:
--		- gponOntMgcConfigMaxRetryTime
--		- gponOntMgcConfigMaxRetryAttempts
--		- gponOntMgcConfigServiceChangeDelay
--	- For gponOntMgcConfigSoftswitchVendor attribute in gponOntMgcConfigTable,
--		invented some alphabetic codes to convey legacy H248 modes of operation.
--	- For gponOntSipConfigSoftswitchVendor attribute in gponOntSipConfigTable,
--		invented some alphabetic codes to convey legacy SIP modes of operation.
--
-- John Boyle - 3/19/2010
-- For ISAM4.2
--
-- 	- In gponOntMgcConfigTable, changed notes to indicate Modification is permitted for following attributes:
--		- gponOntMgcConfigPrimaryMgcAddress
--		- gponOntMgcConfigSecondaryMgcAddress
--
--
-- John Boyle - 3/18/2010
-- For ISAM4.2
--
--  	- In a few more places, changed term FROM NetworkAddress TO SecureUri where the new gponSecureUriProfileTable
--	  was referenced.
--
-- 	Following changes were brought forward from ISAM4.0.10 changes:
--	- For gponPonOntSwDownldStatus attribute in gponPonOntSwDownldStatusTable, increased size to 512 octets,
--		in order to handle 128 ONTs per PON.
--	- For gponOntSwVerCtlRefOntIndex attribute in gponOntSwVerCtlRefOntTable, increased upper range to 8192,
--		in order to handle more potential ONTs per OLT.
--	- For gponOntSwVerCtlNumOntsReferenced attribute in gponOntSwVerCtlTable, increased upper range to 8192,
--		in order to handle more potential ONTs per OLT.
--
-- John Boyle - 3/17/2010
-- For ISAM4.2
--
--    For RCR ANTmt80991 - OMCI Implementer's Guide v2 - OLT
--
--	- NOTED following tables are NOT SUPPORTED for ISAM4.2:
--		- gponVoipServiceTable
--		- gponVoipServiceOpInfoTable
--		- gponVoipServiceOntsideGemCurrentIntervalTable
--		- gponVoipServiceOntsideGemIntervalTable
--		- gponVoipServiceOltsideGemCurrentIntervalTable
--		- gponVoipServiceOltsideGemIntervalTable
--		- gponOltPeriodInfoTable
--		- gponOltPeriodInfoLastAccessTime
--	- Really deleted gponDscpPbitMapProfileTable (which I said I did in previous version, but actually forgot
--		to remove it from the MIB).
--	- In bponPotsPortTable, noted following attributes are NOT SUPPORTED for ISAM4.2:
--		- bponPotsPortVoipServiceIndex
--		- bponPotsPortTerminationId
--		- bponPotsPortDscpSetting
--
--
-- John Boyle - 3/16/2010
-- For ISAM4.2
--
--    For RCR ANTmt80991 - OMCI Implementer's Guide v2 - OLT
--
--	- Added gponUriProfileTable along with following attribute that go with profiles:
--		gponUriProfileIndexNext and gponUriProfileMaxIndex.
--	- Added gponTextMsgProfileTable along with following attribute that go with profiles:
--		gponTextMsgProfileIndexNext and gponTextMsgProfileMaxIndex.
--	- Changed name of gponNetworkAddressProfileTable TO  gponSecureUriProfileTable.
--	- Changed descriptions in all relevant pointer attributes to mention reference proper profile table.
--	- For bponPotsPortSipUserPartAorPointer attribute in bponPotsPortTable, 
--		changed SYNTAX to DisplayString.
--
--
-- John Boyle - 3/15/2010
-- For ISAM4.2
--
--    For RCR ANTmt80991 - OMCI Implementer's Guide v2 - OLT
--
--	- Deleted bponOntNumIpHosts attribute from bponOntTable.
-- 	- For gponOntVoipConfigTable, changed meaning of ifIndex
-- 	  FROM index of ONT TO index of IP Host UNI.
-- 	- For gponOntVoipConfigOpInfoTable, changed meaning of IfIndex (see above), 
--	  and changed auto-creation trigger such that that auto creation/deletion is tied
--	  to create/delete of IP Host UNI.
--
--	- Added gponOntIpHostPingTestTable
--
--	- Added back following tables (at back of MIB) - for compilation purposes.  Plan 
-- 	  to DELETE them at first opportunity - as they are not used in ISAM4.2 - but they 
--	  are still used for ISAM4.0.10.
--		gponVoipServiceTable
--		gponVoipServiceOpInfoTable
--		gponVoipServiceOntsideGemCurrentIntervalTable
--		gponVoipServiceOntsideGemIntervalTable
--		gponVoipServiceOltsideGemCurrentIntervalTable
--		gponVoipServiceOltsideGemIntervalTable
--		gponOltPeriodInfoTable
--		gponOltPeriodInfoLastAccessTime
--
-- John Boyle - 3/11/2010
-- For ISAM4.2
--
--    For RCR ANTmt80991 - OMCI Implementer's Guide v2 - OLT:
--
--	- Added bponOntNumIpHosts attribute to bponOntTable
--	- Added gponOntIpHostTable
--	- Added gponOntIpHostOpInfoTable
--	- Added gponAuthSecurityProfileTable along with following attribute that go with profiles:
--		gponAuthSecurityProfileIndexNext and gponAuthSecurityProfileMaxIndex.
--	- Added gponNetworkAddressProfileTable along with following attribute that go with profiles:
--		gponNetworkAddressProfileIndexNext and gponNetworkAddressProfileMaxIndex.
--	- Added gponOntVoipConfigTable
--	- Added gponOntVoipConfigOpInfoTable
--	- Added gponOntMgcConfigTable
--	- Added gponRtpProfileTable along with following attribute that go with profiles:
--		gponRtpProfileIndexNext and gponRtpProfileMaxIndex.
--	- Added gponVoipMediaProfileTable along with following attribute that go with profiles:
--		gponVoipMediaProfileIndexNext and gponVoipMediaProfileMaxIndex.
--	- Added gponTonePatternProfileTable along with following attribute that go with profiles:
--		gponTonePatternProfileIndexNext and gponTonePatternProfileMaxIndex.
--	- Added gponToneSequenceProfileTable along with following attribute that go with profiles:
--		gponToneSequenceProfileIndexNext and gponToneSequenceProfileMaxIndex.
--	- Added gponToneEventProfileTable along with following attribute that go with profiles:
--		gponToneEventProfileIndexNext and gponToneEventProfileMaxIndex.
--	- Added gponRingPatternProfileTable along with following attribute that go with profiles:
--		gponRingPatternProfileIndexNext and gponRingPatternProfileMaxIndex.
--	- Added gponRingSequenceProfileTable along with following attribute that go with profiles:
--		gponRingSequenceProfileIndexNext and gponRingSequenceProfileMaxIndex.
--	- Added gponRingEventProfileTable along with following attribute that go with profiles:
--		gponEventProfileIndexNext and gponRingEventProfileMaxIndex.
--	- Added gponVoiceServiceProfileTable along with following attribute that go with profiles:
--		gponVoiceServiceProfileIndexNext and gponVoiceServiceProfileMaxIndex.
--	- Added following attributes to bponPotsPortTable:
--		- bponPotsPortMgcConfigPointer
--		- bponPotsPortSipAgentConfigPointer
--		- bponPotsPortVoipMediaPointer
--		- bponPotsPortSipUserPartAorPointer	
--		- bponPotsPortSipDisplayName	
--		- bponPotsPortSipUserPassPointer		
--		- bponPotsPortSipVoicemailUriPointer	
--		- bponPotsPortSipVoicemailExpireTime	
--		- bponPotsPortSipNetDialPlanPointer	
--		- bponPotsPortSipAppServicesPointer	
--		- bponPotsPortSipFeatAccessCodePointer		
--		- bponPotsPortSipReleaseTimer	
--		- bponPotsPortSipRohTimer		
--	- Added gponSipMsgProfileTable along with following attribute that go with profiles:
--		gponSipMsgProfileIndexNext and gponSipMsgProfileMaxIndex.
--	- Added gponOntSipConfigTable
--	- Added gponNetDialPlanProfileTable along with following attribute that go with profiles:
--		gponNetDialPlanProfileIndexNext and gponNetDialPlanProfileMaxIndex.
--	- Added gponVoipAppServProfileTable along with following attribute that go with profiles:
--		gponVoipAppServProfileIndexNext and gponVoipAppServProfileMaxIndex.
--	- Added gponVoipFeatAccessCodeProfileTable along with following attribute that go with profiles:
--		gponVoipFeatAccessCodeProfileIndexNext and gponVoipFeatAccessCodeProfileMaxIndex.
--
--
--	Deleted the following tables which were not used for ISAM4.2
--		bponLanOntMacBrdgTable
--		bponLanMacBrdgServProfTable
--		gponBwProfileTable
--		gponPQProfileTable
--		gponDscpPbitMapProfileTable
--		gponPbitXlProfileTable
--		gponHsiServiceTable
--		gponVoipServiceTable
--		gponVoipServiceOpInfoTable
--		gponHsiServiceOntsideGemCurrentIntervalTable
--		gponHsiServiceOntsideGemIntervalTable
--		gponVoipServiceOntsideGemCurrentIntervalTable
--		gponVoipServiceOntsideGemIntervalTable
--		gponHsiServiceOltsideGemCurrentIntervalTable
--		gponHsiServiceOltsideGemIntervalTable
--		gponVoipServiceOltsideGemCurrentIntervalTable
--		gponVoipServiceOltsideGemIntervalTable
--		gponServiceFlowTable
--		gponServiceFlowOntsideGemCurrentIntervalTable
--		gponServiceFlowOntsideGemIntervalTable
--		gponServiceFlowOltsideGemCurrentIntervalTable
--		gponServiceFlowOltsideGemIntervalTable
--		gponServicePortalTable
--		gponOltPeriodInfoTable
--		gponOltPeriodInfoLastAccessTime
--
--
-- John Boyle - 2/23/2010
-- For ISAM4.0.10:
--
--	Changed FROM ontIndex TO OntIndex.
--
-- John Boyle - 2/23/2010
-- For ISAM4.0.10:
--
--	- Added ifIndex to IMPORTS section (FROM ITF-MIB).
--	- Added following new type definition convention:
--		ontIndex (used specifically as an index for creation of rows in bponOntTable).
--	- For gponVoipServiceUniIndex attribute in gponVoipServiceTable, clarified the
--		composition of the index (i.e. VoIP UNI ifIndex with slot/port = 15/15).
--		Also made same clarification in other relevant gponVoipService tables.
--
-- John Boyle - 2/17/2010
-- For ISAM4.0.10:
--
--	For gponVoipServiceAdminState and gponVoipServiceOperState attributes in gponVoipServiceTable,
--	added following NOTES:
--		 NOTE: VoIP has a logical UNI represented in Interface MIB (and has
--		 a Admin/Oper State attributes in that MIB that control/represent the logical UNI-aspect of VoIP).
--		 The Admin/Oper State attributes (in this GPON MIB) control/represent the service-aspect
--		 of the VoIP service.
--
-- John Boyle - 2/17/2010
-- For ISAM4.0.10:
--
--	For gponVoipServiceAdminState and gponVoipServiceOperState attributes in gponVoipServiceTable,
--	NOTED that neither attribute is supported for ISAM4.0.10.
--
--
-- John Boyle - 2/3/2010
-- For ISAM4.0.10:
--
--	For gponVoipServiceAdminState and gponVoipServiceOperState attributes in gponVoipServiceTable,
--	added following NOTES:
--		  NOTE: Even though VoIP has a logical UNI represented in Interface MIB,
--		  manager must recognize that these attributes actually control/represent 
--		  Admin State / Oper State of the VoIP service.
--	For  bponOntPoliceMode attribute in bponOntTable, added following qualifications:
--		 - For ISAM4.0.10, only certain ONTs support this feature (e.g. ETSI MDUs), and only
--		   for following UNI types: XDSL and Ethernet.
--		 - Modification is SUPPORTED, but only if no XDSL or Ethernet UNIs
--		   have been auto-created for this ONT.
--
-- John Boyle - 2/1/2010
-- For ISAM4.0.10:
--
--  	Added following to IMPORTS section:
-- 		VlanIndex FROM Q-BRIDGE-MIB 
-- 	In gponVoipServiceTable
--		- deleted gponVoipServiceSvlan attribute
--		- deleted gponVoipServiceCvlan attribute
--		- added gponVoipServiceVlanPointer (as VlanIndex)
--
-- 	In gponCesServiceTable
--		- deleted gponCesServiceSvlan attribute
--		- deleted gponCesServiceCvlan attribute
--		- added gponCesServiceVlanPointer (as VlanIndex)
--
-- 	For bponCesPortStructureInd attribute in bponCesPortTable, changed description to mention following:
-- 		 Modification is PERMITTED - but only if NO pseudowire service is defined on this CES port.
--
-- John Boyle - 2/1/2010
-- For ISAM4.0.10:
--
-- 	In gponVoipServiceTable:
--		- deleted gponVoipServiceVlan1Index attribute.
--		- added gponVoipServiceSvlan attribute
--		- added gponVoipServiceCvlan attribute
--
-- 	In gponCesServiceTable:
--		- deleted gponCesServiceVlan1Index attribute.
--		- added gponCesServiceSvlan attribute
--		- added gponCesServiceCvlan attribute
--
-- John Boyle - 12/21/2009
-- For ISAM4.0.10:
--
-- 	For asam profile names and conventions:
--		- deleted them as explicit type definitions.
--		- moved them to IMPORTS section as being derived from ASAM-TC-MIB.
-- 
--
-- John Boyle - 12/1/2009
-- For ISAM4.0.10:
--
-- 	In order to align with 4.0.10 feature agreements, marked the following 4.7 tables and/or parameters as 
-- 	NOT SUPPORTED for ISAM4.0.10:
--		- bponVideoPortServiceTimer attribute in bponVideoPortTable.
--		- gponOntPingTestTable (entire table).
--		- gponOltPeriodInfoTable (entire table).
--		- gponOltPeriodInfoLastAccessTime (SCALAR)
--
-- John Boyle - 11/12/2009
-- For ISAM4.0.10:
--
--	In bponOntTable, made following attribute changes:
--		- bponOntPoliceMode - changed its OID from 70 to 74 (because parallel table changes are being made
--		  in 4.7.4 release - so trying to avoid future OID clash if 4.7.4 features get carried forward into 4.0.10.
--		- added bponOntAesMode attribute at OID 75.
--	In gponVoipServiceTable, made following attribute changes:
--		- gponVoipServiceAesEnableInd - NOTED this attribute is NOT SUPPORTED for ISAM4.0.10
--	In gponCesServiceTable, made following attribute changes:
--		- gponCesServiceAesEnableInd - NOTED this attribute is NOT SUPPORTED for ISAM4.0.10
--
-- John Boyle - 10/30/2009
-- For ISAM4.0.10:
--
--	In bponOntTable, made following attribute changes:
--		- bponOntAdminState - marked as NOT SUPPORTED
--
--	In bponLanEtherPortTable, made following attribute changes:
--		- bponLanEtherPortAdminState - marked as NOT SUPPORTED
--		- bponLanEtherPortOperState - marked as NOT SUPPORTED
--
--	In bponCesPortTable, made following attribute changes:
--		- bponCesPortAdminState - marked as NOT SUPPORTED
--		- bponCesPortOperState - marked as NOT SUPPORTED
--
-- John Boyle - 10/28/2009
-- For ISAM4.0.10:
--
--	In bponOntTable, made following attribute changes:
--		- bponOntPolice Mode - added this attribute
--
--	In bponOntActualCardTable, made following attribute changes:
--		- bponOntActualCardNumPorts - marked as NOT SUPPORTED
--		- bponOntActualCardNumNonPotsPorts - added this attribute
--		- bponOntActualCardNumPotsPorts - added this attribute
--
--	In bponPotsPortTable, made following attribute changes:
--		- bponPotsPortVoipServiceIndex - noted that default = 1.
--
--
-- John Boyle - 10/22/2009
-- For ISAM4.0.10:
--
-- >>> For the most part, the following note differences between ISAM 4.0.10 and previous FGU4.7.x
--
--  >> Noted that the following tables are NOT SUPPORTED:
--	- gponBwProfileTable
--	- gponPQProfileTable
--	- gponDscpPbitMapProfileTable
--	- gponPbitXlProfileTable
--	- gponHsiServiceTable
--	- gponHsiServiceOntsideGemCurrentIntervalTable
--	- gponHsiServiceOntsideGemIntervalTable
--	- gponHsiServiceOltsideGemCurrentIntervalTable
--	- gponHsiServiceOltsideGemIntervalTable
--	- gponServiceFlowTable
--	- gponServiceFlowOntsideGemCurrentIntervalTable
--	- gponServiceFlowOntsideGemIntervalTable
--	- gponServiceFlowOltsideGemCurrentIntervalTable
--	- gponServiceFlowOltsideGemIntervalTable
--	- gponServicePortalTable
--
--  >> Added the following tables:
--	- gponUniGemPmTable
--	- gponUniOntsideGemCurrentIntervalTable
--	- gponUniOntsideGemIntervalTable
--	- gponUniOltsideGemCurrentIntervalTable
--	- gponUniOltsideGemIntervalTable
--
--
--  >> For bponOntTable, noted following differences for following attributes:
--	- bponOntTrafficManageOption - NOT SUPPORTED
-- 	- bponOntVpVcCrossConnectOption - NOT SUPPORTED
--	- bponOntActualNumSlots - extended upper-end range to 16.
--	- bponOntSchedulerProfile - NOT SUPPORTED
--	- bponOntDownstreamRateLimitOption - NOT SUPPORTED
--	- bponOntStaticMcastVlanXlateInd - NOT SUPPORTED
--
--  >> For bponOntPlanCardTable, noted following differences for following attributes:
--	- bponOntPlanCardType - constrained supported card types (i.e. no MoCA or VDSL1).
--	- bponOntPlanCardNumNonPotsPorts - added this attribute.
--	- bponOntPlanCardNumPotsPorts - added this attribute.
--
--  >> For bponOntActualCardTable, noted following differences for following attributes:
--	- bponOntPActualCardType - constrained supported card types (i.e. no MoCA or VDSL1).
--
--  >> For bponPonConfigTable, noted following differences for following attributes:
--	- bponPonConfigUpProvCIR - NOT SUPPORTED
--	- bponPonConfigUpProvAIR - NOT SUPPORTED
--	- bponPonConfigDownProvCIR - NOT SUPPORTED
--	- bponPonConfigDownProvAIR - NOT SUPPORTED
--	- bponPonConfigGuarUpBwRemaining - NOT SUPPORTED
--	- bponPonConfigGuarDownBwRemaining - NOT SUPPORTED
--
--  >> For bponPonDiscovOntTable, noted following differences for following attributes:
--	- bponPonDiscovOntNum - extended upper-end range to 128.
--
--  >> For bponPotsPortTable, noted following differences for following attributes:
--	- bponPotsPortRowStatus - NOT SUPPORTED
--
--  >> For bponLanEtherPortTable, noted following differences for following attributes:
--	- bponLanEtherPortRowStatus - NOT SUPPORTED
--	- bponLanEtherPortMaxFrameSize - NOT SUPPORTED
--	- bponLanEtherPortDteOrDceInd - NOT SUPPORTED
--	- bponLanEtherPortCustVlan - NOT SUPPORTED
--	- bponLanEtherPortQosProfile - NOT SUPPORTED
--	- bponLanEtherPortDscpPbitMapProfile - NOT SUPPORTED
--
--  >> For bponCesPortTable, noted following differences for following attributes:
--	- bponCesPortRowStatus - NOT SUPPORTED
--
--  >> For bponVideoPortTable, noted following differences for following attributes:
--	- bponVideoPortRowStatus - NOT SUPPORTED
--
--  >> For gponVoipServiceTable, noted following differences for following attributes:
--	- gponVoipServiceUpBwProfile - NOT SUPPORTED
--	- gponVoipServiceDownBwProfile - NOT SUPPORTED
--	- gponVoipServicePQProfile - NOT SUPPORTED
--	- gponVoipServiceGwyOption - noted that only SIP1 and SIP 2 options are supported.
--	- gponVoipServiceVlanId - NOT SUPPORTED
--	- gponVoipServiceCustomerId - NOT SUPPORTED
--	- gponVoipServiceConfigMethod - noted that only supported option is FTP Server
--	- gponVoipServiceSourceVlanId - NOT SUPPORTED
--	- gponVoipServiceDsRateSchedProfile - NOT SUPPORTED
--	- gponVoipServiceVlan1Index - added this attribute (to reference VLAN in L2 subsystem)
--
--  >> For gponCesServiceTable, noted following differences for following attributes:
--	- gponCesServiceUpBwProfile - NOT SUPPORTED
--	- gponCesServiceDownBwProfile - NOT SUPPORTED
--	- gponCesServicePQProfile - NOT SUPPORTED
--	- gponCesServiceVlanId - NOT SUPPORTED
--	- gponCesServiceSourceVlanId - NOT SUPPORTED
--	- gponCesServiceDsRateSchedProfile - NOT SUPPORTED
--	- gponCesServiceVlan1Index - added this attribute (to reference VLAN in L2 subsystem)
--
--
-- John Boyle - 6/3/2008
-- For FGU4.7:
--
-- BDFam46121 - Ability to Ping from ONT:
--
--	- For gponOntPingTestExplicitIpAddress attribute in gponOntPingTestTable, clarified that
--	  this attribute only has relevance if gponOntPingTestMode = 0 = explicit IP address.
--
--
-- John Boyle - 5/28/2008
-- For FGU4.7:
--
-- BDFam32547 - 5 Minute Performance Data:
--
--	- Deleted following attributes from gponOltPeriodInfoTable (since they were added to System MIB):
--		- gponOltPeriodInfoNtaObcCpuUtil	
--		- gponOltPeriodInfoNtaLanxCpuUtil	
--		- gponOltPeriodInfoNtbObcCpuUtil	
--		- gponOltPeriodInfoNtbLanxCpuUtil	
--
--
-- John Boyle - 5/27/2008
-- For FGU4.7:
--
-- BDFam46121 - Ability to Ping from ONT:
--
--	- For gponOntPingTestNumberToAttempt attribute in gponOntPingTestTable, specified that there is 
--	  No Default - value must be specified by manager.
--
-- ANTms79887 - PON Feeder Protection:
--
-- 	- For gponPonProtectRowStatus attribute in gponPonProtectTable, added following RULE:
--	  RULE 1 - Cannot create a protection group on an LT card that doesn't support PON protection.
--
-- John Boyle - 5/21/2008
-- For FGU4.7:
--
-- BDFam46121 - Ability to Ping from ONT:
--
--	- Added gponOntPingTestTable.
--
--
-- John Boyle - 5/8/2008
-- For FGU4.7:
--
-- ANTms79887 - PON Feeder Protection:
--
--	- Added gponPonProtectTable.
--
-- John Boyle - 4/24/2008
-- For FGU4.7:
--
-- BDFam32547 - 5 Minute Performance Data:
--
--	- Added gponOltPeriodInfoTable 
--	- Added gponOltPeriodInfoLastAccessTime (SCALAR)
--
--
-- John Boyle - 4/22/2008
-- For FGU4.7:
--
-- BDFam39976 - Verizon Video Requirements:
--
--	- In bponVideoPortTable, added bponVideoPortServiceTimer attribute.  
--
--
-- John Boyle - 4/6/2008
-- For FGU4.6.4:
--
-- BDFam46207 - Multicast Translation in Different VLANs:
--
--	- In bponOntTable, added bponOntStaticMcastVlanXlateInd attribute.  Noted that as of FGU4.6.4, this
--	  special translation indicator only applies to RIP packets.
--
-- ANTmt41157 - OLT Voice Mode Parameter
--
--	- For gponVoipServiceGwyOption attribute in gponVoipServiceTable, noted that expanded enumerations
-- 	  are effective as of FGU 4.6.4.
--
-- John Boyle - 3/5/2008
-- For FGU4.6.4:
--
-- ANTmt41157 - OLT Voice Mode Parameter
--
-- Made following changes to following attributes in gponVoipServiceTable
--	- For gponVoipServiceGwyOption, added following enumerations:
--		6 = PPPoE SIP 1
--		7 = PPPoE SIP 2
--		8 = Future 1
--		9 = Future 2
--	- For gponVoipServiceClientIdentifier, added following rule:
--		  RULE: If gponVoipServiceConfigMethod = 2 = SIPPING Server AND 
--		  gponVoipServiceGwyOption is NOT a PPPoE variety (6, 7), then
--		  this attribute cannot be null (i.e. it must be SET by the manager).
--	- For gponVoipServiceConfigMethod, added following note:
--		  NOTE: If gponVoipServiceGwyOption is a PPPoE variety (6, 7), then
--		  this attribute is not relevant (can be set to any value).
--	- For gponVoipServiceSippingAuthUsername, added notes regarding usage for either
--		 authentication with the SIPPING Server OR for PPPoE authentication.
--	- For gponVoipServiceSippingAuthPassword, added notes regarding usage for either
--		 authentication with the SIPPING Server OR for PPPoE authentication.
--	- For gponVoipServiceSippingAuthRealm, added notes regarding usage for either
--		 authentication with the SIPPING Server OR for the PPPoE access concentrator name.
--
-- BDFam46431 - Enable Tx/Rx gain control on POTS UNI
--
--	In bponPotsPortTable, noted that the following attributes are SUPPORTED as of FGU4.6.4, but are
--	only relevant for a Cambridge ONT (i.e. Vendor ID = CIGG):
--		- bponPotsPortRxGain
--		- bponPotsPortTxGain
--
-- BDFam46434 - EnergiMidt network deployment specifics
--
--	Added bponOntVideoRfFilter attribute to bponOntTable.  Noted the following:
--		  NOTE: This attribute is only relevant for a Cambridge ONT (i.e. Vendor ID = CIGG).
--		  This attribute is only relevant if an RF Video port has been provisioned for a Cambridge ONT.
--
--
-- John Boyle - 12/1/2008
-- For FGU4.6:
--
-- For bponOntRebootCmd attribute in bponOntTable, added the following clarifying notes:
--		 Option 2 was never implemented as intended. 
--		 Setting it will result in same behavior as Option 1.
--		 It is recommended that a manager only use Option 1.
--		 
--		 For the majority of cases, the planned version is equal to 
--		 the active version, so setting this attribute will result in a pure reboot.
--		 In rare cases, the ONT may have an error condition where the planned
--		 version is stuck on the passive version (e.g. after a previous activation
--		 failure).  In such a case, setting this attribute will trigger the ONT to 
--		 attempt to activate the passive version.
--
-- For gponOntSwDownldStatus attribute in gponOntSwDownldStatusTable and 
-- gponPonOntSwDownldStatus attribute in  gponPonOntSwDownldStatusTable, 
-- added following clarification regarding Bit number positioning:
--           		 In following descriptions, Bit 1 position is defined as the high-order left-most 
--		 and Bit 32 position is defined as the low-order, right-most. 
--
--
-- John Boyle - 11/24/2008
-- For FGU4.6:
--
-- WPRas09091 - FLOWSVCMIS alarm on creation of 2nd FLOW
--
--	- In gponServiceFlowTable, added following rule to gponServiceFlowAniSideVlan attribute:
--		  RULE1: 
--		  If  'mode'  of the associated S-VLAN is 'CVLANLEARN', then the following 
--		  UNI-side/ANI-side VID specifications should be REJECTED:
--			1) UNI-side 4096 with ANI-side 4096
--			2) UNI-side 0xFFFF with ANI-side 4096
--
--	- In gponServiceFlowTable, added following rules to gponServiceFlowVlanId attribute:
--		 RULE2: OLT will REJECT flow creation attempt that would cause ALL of following to be
--		 	TRUE for 2 or more flows:
--		 1) Flows are on the same UNI.
--		 2) 'mode'  of the associated S-VLAN (for flows) is NOT 'CVLANLEARN'. 
--		 3) Flows have the same S-VLAN value.
--		 4) Flows reference PQ profiles that have 1 or more overlapping PBits specified (i.e. a PBit clash).
--
--		 RULE3: OLT will REJECT flow creation attempt that would cause ALL of following to be 
--		 	TRUE for 2 or more flows:
--		 1) Flows are on the same UNI.
--		 2) 'mode'  of the associated S-VLAN (for flows) is 'CVLANLEARN'. 
--		 3) Flows have the same S-VLAN value.
--		 4) Flows reference PQ profiles that have 1 or more overlapping PBits specified (i.e. a PBit clash).
--		 5) Flow would effectively have the same ANI-side VLAN value (see descriptions above for 
--		     gponServiceFlowAniSideVlan attribute).
--
--
--
-- John Boyle - 11/11/2008
-- For FGU4.6:
--
-- 	- Indicated that gponOntSwVerInfoSwVersionCrc attribute in gponOntSwVerInfoTable is NOT SUPPORTED.
--
--
-- John Boyle - 10/30/2008
-- For FGU4.6:
--
-- BDFam44032 - SVLAN NR on Portal w BW
--
-- 	- In gponServicePortalVlanId attribute of gponServicePortalTable, removed the following validation statement
-- 	  from description: 
--		- If gponServicePortalUpBwProfile is non-null, then this attribute cannot be 0.
--
-- John Boyle - 10/17/2008
-- For FGU4.6:
--
--  For gponOntSwDownldStatus attribute and gponPonOntSwDownldStatus attributes (in their respective tables),
--  corrected erroneous descriptive references for Bits 3 and 4. Now says these bits only have relevance when Bit 2
--  is set (it used to refer to Bit 15 - which was erroneous).
--
-- John Boyle - 10/7/2008
-- For FGU4.6:
--
-- BDFam43531 - MIB/OMCI support for ETSI MDU Policing
--
--	- Added following attribute to gponServiceFlowTable:
--		- gponServiceFlowOntTrafDescriptMode. 
-- 		  NOTED: As of FGU4.6, attribute is NOT SUPPORTED. Was only introduced in FGU4.6 to
--		  to avoid off-line migration impacts beyond FGU4.6.
--
--
-- John Boyle - 10/6/2008
-- For FGU4.6:
--
-- BDFam43310 -  Retrieve serialNo. of optics on GLT card:
--
--	- Added following attributes to gponPonOltsideOpInfoTable:
--		- gponPonOltsideOpInfoVendorName
--		- gponPonOltsideOpInfoPartNumber
--		- gponPonOltsideOpInfoSerialNumber	
--		- gponPonOltsideOpInfoMfgDateCode
--
-- For gponServiceFlowPortalNumber attribute in gponServiceFlowPortalTable:
--	- Increased range FROM 1..50 TO 1..64.
--
--
-- John Boyle - 10/2/2008
-- For FGU4.6:
--
-- BDFam43086 (FR) Vbrick: VoIP SRCVLANID=4095 not working:
--
--	- For gponVoipServiceSourceVlanId attribute in gponVoipServiceTable,
--		changed range FROM 0...4095 TO 0...4094.
--
-- John Boyle - 10/1/2008
-- For FGU4.6:
--
-- BDFam42123 - NE Support for LRM
--
--	- In gponOntSwVerCtlTable, made following changes;
--		- Deleted gponOntSwVerCtlAdminStateAttribute
--		- Added gponOntSwVerCtlPlannedSwVersionConf
--		- Added gponOntSwVerCtlPreviousPlannedSwVersion
--		- Added gponOntSwVerCtlPlannedSwVersionRevertCmd
--
--	- For gponOntSwDownldStatus attribute in gponOntSwDownldStatusTable and 
--	  	gponPonOntSwDownldStatus attribute in gponPonOntSwDownldStatusTable, 
--		changed defaults and re-ordered all bits by squeezing in following new bit definitions:
--		 Bit 2 ON =  ONT is INACTIVE (mirrors INACT alarm condition, although OLT may be supressing
--			      an actual INACT alarm ). 
--		 Bit 3 ON =  Last known Planned Software Version was NOT OK (i.e. Planned did not equal
--			      Active).  This bit only has relevance when Bit 15 is ON (i.e. when ONT is inactive).
--		 Bit 4 ON =  Last known Download Software Version was NOT OK (i.e. Download did not equal
--			      Active or Passive).  This bit only has relevance when Bit 15 is ON (i.e. when ONT is inactive).
--
--
-- John Boyle - 9/29/2008
-- For FGU4.6:
--
-- BDFam42123 - NE Support for LRM
--
--	- Added following attributes to gponOntSwVerCtlTable:
--		- gponOntSwVerCtlAdminState
--		- gponOntSwVerCtlNumOntsReferenced
--	- Added gponOntSwVerCtlReferencedRow SCALAR
--	- Added the gponOntSwVerCtlRefOntTable
--	- For gponOntSwDownldStatus attribute in gponOntSwDownldStatusTable and 
--	  	gponPonOntSwDownldStatus attribute in gponPonOntSwDownldStatusTable, 
--		added following bit definition:
--		  - Bit 15 ON =  Entry match found in ONT Software Version Control Table, but entry is locked.
--		    (mirrors SWVERCTLLOCK alarm introduced in FGU4.6).
--
-- John Boyle - 9/11/2008
-- For FGU4.6:
--
--  For gponServicePortalAggUpDT attribute in gponServicePortalTable:
--  	- Extended the range to include 0, and made statement that value 0 is used for case where
--	  gponServicePortalUpBwProfile attribute is null, and no flows are assigned to this portal.
--
-- Added the gponOntSwVerCtlIndexNext attribute as a SCALAR to be used in conjunction with
--	  the gponOntSwVerCtlTable.  Allows agent to guide manager regarding appropriate choice of 
--	  index for adding a table row.
--
-- For following 'scope' attributes in following profiles, noted that default setting should be 1 = local:
--	- gponBwProfileScope in gponBwProfile
--	- gponPQProfileScope in gponPQProfile
--	- gponPwrShedProfileScope in gponPwrShedProfile
--	- gponCesMaintProfileScope in gponCesMaintProfile
--	- gponDscpPbitMapProfileScope in gponDscpPbitMapProfile
--	- gponLargeStringProfileScope in gponLargeStringProfile
--	- gponPbitXlProfileScope in gponPbitXlProfile
--
--
-- John Boyle - 8/26/2008
-- For FGU4.6:
--
-- For following attributes in following tables, clarified (hopefully) the meaning and usage of terms 'null' and 'non-null'
-- with respect to profile pointers, restrictions associated with creation/modification, and default specification:
-- 	- gponServiceFlowUpBwProfile and gponServiceFlowDownBwProfile attributes in gponServiceFlowTable.
-- 	- gponServicePortalUpBwProfile and gponServicePortalDownBwProfile attributes in gponServicePortalTable.
--
-- John Boyle - 8/26/2008
-- For FGU4.6:
--
-- BDFam42123 - NE Support for LRM
--
--  	-  Added gponOntSwGroup as oid {apon 26}
--	-  Added the gponOntSwVerCtlTable under new oid {apon 26}
--	-  Added  following attributes in bponOntTable:
--		- bponOntPlannedVariant
--		- bponOntAutoSwPlannedVersion
--		- bponOntAutoSwDownloadVersion
--	-  For following attributes in bponOntTable, noted meaning and implication
--	   of special value AUTO along with relationship to associated attributes in
--	   gponOntSwVerCtlTable:
--		- bponOntSwPlannedVersion
--		- bponOntSwDownloadVersion
--	- Added gponOntSwVerInfoTable
--	- Added gponOntSwVerDeleteCmd as a SCALAR
--	- Added gponOntSwVerDeleteCmdStatus as a SCALAR
-- 	- Added following tables (for status-oriented collection of ONT software download status):
--		- gponOntSwDownldStatusTable
--		- gponPonOntSwDownldStatusTable
--
-- BDFam42680 - Descope of RCR ANTmt00304
-- 	- Made following changes to following attributes in gponVoipServiceTable:
--		- gponVoipServiceVlanId - Removed all reference notes to gponVoipServiceSignalVlanId
--		  attribute (along with behavioral implications).
--		- gponVoipServiceSignalVlanId - Noted attribute is NOT SUPPORTED.
--
--
-- John Boyle - 7/30/2008
-- For FGU4.6: 
--
-- For following attributes in gponVoipServiceTable, added the following NOTE:
--		NOTE: The following attributes are tightly related:
--		gponVoipServiceConfigFileName, gponVoipServiceFtpAuthUsername,
--		and gponVoipServiceFtpAuthUsername.  From and OMCI standpoint,
--		all 3 must be sent to the ONT in that order. This applies to initial VoIP
--		Client creation, and subsequently if any one or more of these attributes
--		are edited.
--
--
-- John Boyle - 7/24/2008
-- For FGU4.6: 
--
-- For  gponVoipServicePQProfile attribute in gponVoipServiceTable, removed validation
--	regarding no more than 2 queues (GEM ports).  There are still limitations,
--	but mentioned in context of other attributes (e.g. gponVoipServiceSignalVlanId).
--	Changed description to say following: 		 
--		 For all ONTs (other that older M300),  the referenced PQ Profile should
--		 specify exactly 2 queues (GEM ports).  But the OLT will will not
--		 enforce this check.  If the particular ONT does not support the 
--		 the number of specified queues (GEM ports) for this VoIP service,
--		 it will reject via OMCI and OLT will raise a 'service mismatch alarm'.
--
-- John Boyle - 7/24/2008
-- For FGU4.6: 
--
-- In gponVoipServiceTable, updated constraints and validations in following attributes:
--	- gponVoipServicePQProfile
--	- gponVoipServiceVlanId
--	- gponVoipServiceSignalVlanId
-- These overall additional constraints are the following:
--	- VoIP PQ Profile CANNOT specify more than 2 queues (GEM ports)
--	- If signalling VLAN is same as bearer VLAN, it's the same as pre-4.6
--	  behavior (i.e. like a single S-VLAN).
--	- If signalling VLAN and bearer VLAN are different (other than 4096 value),
--	  then associated PQ Profile must specify exactly 2 queues (GEM ports).
--
--
-- John Boyle - 7/24/2008
-- For FGU4.6: 
--
-- For gponServicePortalUpBwProfile attribute in gponServicePortalTable:
--	- Further constrained so that it is NOT permitted to modify from 
--	  null to non-null or from non-null to null.  Formerly said that this 
--	  restriction was only applicable if portal had an associated flow.
--	  Now we prohibit such modification regardless if portal has an
--	  associated flow.
--
-- John Boyle - 7/9/2008
-- For FGU4.6: 
--
-- For gponServicePortalAdminState attribute in gponServicePortalTable:
--	- Removed TBD regarding whether supported (it is SUPPORTED for FGU4.6)
-- For gponServicePortalOperState attribute in gponServicePortalTable:
--	- Removed TBD regarding whether supported (it is SUPPORTED for FGU4.6)
-- For gponServicePortalVlanId attribute in gponServicePortalTable:
--	- Removed the NOT SUPPORTED comment.
--	- Added value 0 to the valid range.
--	- Added constraints regarding what values are VALID in relation to gponServicePortalUpBwProfile.
-- For gponServiceFlowVlanId attribute in gponServiceFlowVlanId, added following constraint: 	
--	- If gponServicePortalVlanId attribute (in associated Portal) is not 0,
--	  then this attribute must be equal to value in gponServicePortalVlanId.
--
--
-- John Boyle - 7/8/2008
-- For FGU4.6: 
--
-- For gponOntOpticSupDailyTime attribute in gponOntOpticSupDailyTable:
--	- corrected the OID name to properly match the table name (wouldn't compile otherwise).
--
--
-- John Boyle - 6/30/2008
-- For FGU4.6: 
--
-- BDFam39015 - Additional RSSI Capibilities
--	- In gponOntOpticSupDailyTable, made following changes:
--		- Noted that data for only a single day is stored.
--		- Added gponOntOpticSupDailyTime attribute (i.e. timestamp).
--
-- John Boyle - 6/25/2008
-- For FGU4.6: 
--
-- BDFam40872 - ONT Power Burst
--	- Added gponOltPowerBurstDetectMode scalar.
--	- For bponPonDiscovOntDisableIndicator in bponPonDiscovOntTable, added a new 
--	  possible text string so the set is as follows:		
--		  DISABLED - meaning ONT has been told via a PLOAM message to turn off it's laser.
--		  PWRERR - meaning extraneous power bursts have been detected for this ONT.
--		  'null string' (i.e. no text) - meaning none of the above are true.
--
--
-- John Boyle - 6/24/2008
-- For FGU4.6: 
--
-- BDFam31073 - Per Service Throughput Rate Limiting
--	- For gponOltVoipDownstreamSchedMode attribute, specified that 1 = PON-based
--	  setting is only applicable for GLT4 cards.  Such setting is ignored for GLT2 cards,
--	  which will always work as pre-4.6 'ONT-based'. 
--	- For following profile pointer attributes, specified that they must be set to 1 (i.e. the default)
--	  if they are not being used:
--		 bponOntSchedulerProfile in bponOntTable
--		 gponHsiServiceDsRateSchedProfile in gponHsiServiceTable
--		 gponCesServiceDsRateSchedProfile in gponCesServiceTable
--		 gponVoipServiceDsRateSchedProfile in gponVoipServiceTable
--		 gponServicePortalDsRateSchedProfile in gponPortalServicetable
--
--
-- John Boyle - 6/17/2008
-- For FGU4.6: 
--
-- Carried forward following RCR that was introduced in FGU4.5.6:
-- ANTmt02051 - TdE  Wholesale Video Via Residential Bridging
--	- For gponHsiServiceNetworkVlan attribute in gponHsiServiceTable,
--	  qualified that the uniqueness constraint only applies
--	  if the 'tagging mode'  of the associated S-VLAN is NOT 'stacked'.
--
-- John Boyle - 6/17/2008
-- For FGU4.6: 
--
-- BDFam39015 - Additional RSSI Capibilities
--	- Added gponOntOpticSupDailyTable
--	- Added bponOntOpticalSupDailyCollectInd attribute to bponOntTable
--	- Added bponOntOpticalSupDailyNumIntervals attribute to bponOntTable
--
-- For gponOltVoipDownstreamSchedMode scalar, clarified the meaning of the enumeration choices.
--
-- For bponPonConfigDownProvAIR attribute in bponPonConfigTable, marked as NOT SUPPORTED as of FGU4.6.
--
-- John Boyle - 6/12/2008
-- For FGU4.6: 
--
-- For gponOltVoipDownstreamSchedMode scalar, further restricted modification possibility as follows:
--		 -  Modification permitted only if NO Voip services exist (in entire system).
--		
--
-- John Boyle - 6/10/2008
-- For FGU4.6: 
--
-- BDFam40009 - RTRV Booked and In-Use PON Bandwidth
--	Added following attributes to bponPonConfigTable:
--		- bponPonConfigUpProvCIR			
--		- bponPonConfigUpProvAIR			
--		- bponPonConfigDownProvCIR			
--		- bponPonConfigDownProvAIR			
--		- bponPonConfigGuarUpBwRemaining		
--		- bponPonConfigGuarDownBwRemaining
--
-- For gponOltVoipDownstreamSchedMode scalar, updated modification restrictions to add following:
--	This parameter CANNOT be modified if there is a VoIP service provisioned on an ONT
--	 for which the bponOntDownstreamRateLimitOption is set to per-service-based.
--	
--
-- John Boyle - 6/5/2008
-- For FGU4.6: 
--
-- For gponVoipServiceSignalVlanId attribute in gponVoipServiceTable, noted that modification is NOT permitted.
-- For bponOntDownstreamRateLimitOption attribute in bponOntTable, changed to note that
--	 modification is NOT permitted.
--
-- John Boyle - 6/4/2008
-- For FGU4.6: 
--
--
-- ANTmt0304 - Separate VLAN for Signalling and Data
-- 	- For gponVoipServiceVlanId attribute in gponVoipServiceTable, added following NOTE: 
--		 Prior to FGU4.6, this S-VLAN carried all traffic associated with the 
--		 VoIP Client (i.e. signalling, bearer, and all else).  As of FGU4.6, user
--		 can designate this S-VLAN to only carry bearer traffic.  This is done
--		 by setting gponVoipServiceSignalVlanId to a value other than 4096.
--	- Added gponVoipServiceSignalVlanId attribute to gponVoipServiceTable.
--
-- For bponLanEtherPortCustVlan attribute in bponLanEtherPortTable, increased upper range
-- 	from 4094 to 4095.
-- For gponServicePortalNumber attribute in gponServicePortalTable, increased upper range
--	from 50 to 64.
--
-- For following attributes in following tables, revamped all rules regarding usage and combinations of null
-- and non-null Bandwidth Profile pointers for flows associated with portals:
--	gponServiceFlowUpBwProfile in gponServiceFlowTable
-- 	gponServiceFlowDownBwProfile in gponServiceFlowTable
--	gponServicePortalUpBwProfile in gponServicePortalTable
-- 	gponServicePortalDownBwProfile in gponServicePortalTable
--
-- In case we decide to support 'GEM PMs' for Flows - added the following attributes/tables:
--	- Added gponServiceFlowGemPmCollectInd attribute to gponServiceFlowTable
--	- Added gponServiceFlowGemPmNumPMIntervals attribute to gponServiceFlowTable
--	- Created gponServiceFlowOntsideGemCurrentIntervalTable
--	- Created gponServiceFlowOntsideGemIntervalTable
--	- Created gponServiceFlowOltsideGemCurrentIntervalTable
--	- Created gponServiceFlowOltsideGemIntervalTable
--
-- 
--
-- John Boyle - 5/30/2008
-- For FGU4.6: 
--
-- BDFam38773 - SIP Security and Config Enhancements
--	- Added following attributes to gponVoipServiceTable:
--		- gponVoipServiceFtpAuthUsername
--		- gponVoipServiceFtpAuthPassword
--
--
-- John Boyle - 5/28/2008
-- For FGU4.6: 
--
-- 	- For bponOntDownstreamRateLimitOption attribute in gponOntTable, added more VALIDATION
-- 	  qualifiers regarding setting/modifying.
--	- Constrained the profile pointer range to 1..32 for following attributes:
--		 gponHsiServiceDsRateSchedProfile.
--		 gponCesServiceDsRateSchedProfile.
--		 gponVoipServiceDsRateSchedProfile. 
--		 gponServicePortalDsRateSchedProfile. 
--	- For gponOltVoipDownstreamSchedMode attribute, made following changes:
--		- Changed enumeration meanings, and changed default to ONT-based.
--		- Reworded the constraits associated with modification.
--	- For bponOntEtherPortToPortEnableInd attribute in bponOntTable, added following
--	  constraints:
--		 - Modification NOT SUPPORTED.
--		 - RULE: If selection = 1 (i.e. Enabled), then OLT must prohibit creation of any 
--		   	HSI Service or Service Flow on any Ethernet port other than Port 1. 
--
--
--
-- John Boyle - 5/22/2008
-- For FGU4.6: 
--
-- 	- For gponServiceFlowUpBwProfile attribute in gponServiceFlowTable, removed the VALIDATION
-- 	  regarding DT parameters when multiple flows (having their own specified BW profiles) point to the
--	  the same portal.
--	- Added gponServicePortalAggUpDT to gponServicePortalTable
-- 
--
-- John Boyle - 5/22/2008
-- For FGU4.6: 
--
-- BDFam31073 - Per Service Throughput Rate Limiting
--	- Added the gponOltVoipDownstreamSchedMode as a system-wide
--	  scalar attribute.
--	- In bponOntTable:
--		- Added bponOntDownstreamRateLimitOption attribute.
--		- For bponOntSchedulerProfile attribute, made note that 
--		    this attribute is IGNORED (not relevant) if
--		    bponOntDownstreamRateLimitOption attribute is NOT set to
--		    0 = ONT-based.
--	- In gponHsiServiceTable:
--		- Added gponHsiServiceDsRateSchedProfile. Made note that 
--		    this attribute is IGNORED (not relevant) if
--		    bponOntDownstreamRateLimitOption attribute is NOT set to
--		    1 = Service-based.
--	- In gponCesServiceTable:
--		- Added gponCesServiceDsRateSchedProfile. Made note that 
--		    this attribute is IGNORED (not relevant) if
--		    bponOntDownstreamRateLimitOption attribute is NOT set to
--		    1 = Service-based.
--	- In gponVoipServiceTable:
--		- Added gponVoipServiceDsRateSchedProfile. Made note that 
--		    this attribute is IGNORED (not relevant) if either of the following:
--			- gponOltVoipDownstreamSchedMode scalar attribute is NOT
--			  set to 1 = ONT-based.
--		    	- bponOntDownstreamRateLimitOption attribute is NOT set to
--		    	  1 = Service-based.
--	- In gponServicePortalTable:
--		- Added gponServicePortalDsRateSchedProfile. Made note that 
--		    this attribute is IGNORED (not relevant) if
--		    bponOntDownstreamRateLimitOption attribute is NOT set to
--		    1 = Service-based.
--
--
-- ANTms83109 - Per Service IP Anti-Spoofing
--	- Added gponHsiServiceMaxIpAddresses to gponHsiServiceTable
--
--
--
-- John Boyle - 5/14/2008
-- For FGU4.6: 
--
--
-- BDFam37203 - Business Service Requirements
-- 	- Added following tables:
--		- gponPbitXlProfileTable 
--		- gponServiceFlowTable
--		- gponServicePortalTable
--
-- ANTms71536 - Reporting the distance between OLT & ONT
--	- Added bponOntOpInfoDistance attribute to the
--	  bponOntOpInfoTable
--
-- ANTms83109 - Per Service IP Anti-Spoofing
--	- Added gponHsiServiceIpAntispoofInd attribute to gponHsiServiceTable
--
-- BDFam40516 - Port 2 Port Communication on Mult-Ethernet Port ONTs
-- 	- For bponOntEtherPortToPortEnableInd attribute in bponOntTable,
--	  changed from NOT SUPPORTED to SUPPORTED (for FGU4.6).
--
--
-- John Boyle - 3/24/2008
-- For FGU4.5.5: 
--
-- BDFam39962 - New Data Items to Support EMS/ONT Interaction
-- 	- Added following attributes to gponVoipServiceOpInfoTable: 
--		- gponVoipServiceOpInfoActualConfigFileVersion	
--		- gponVoipServiceOpInfoVoipSwVersion
--
-- John Boyle - 3/18/2008
-- For FGU4.5.5: 
--
-- BDFam39910 - Modify behavior/TL1 For Auto-Negotiation
-- 	- For bponLanEtherPortAutoDetectConfig attribute in bponLanEtherPortTable: 
--	  	Changed it all again to accommodate latest proposal that retains old 
--		meanings as well as new meanings (for backward compatibility). 
--
-- John Boyle - 3/13/2008
-- For FGU4.5.5: 
--
-- For the following OLT-side optics measurement attributes, added another special codepoint to distinguish
-- INVALID and NOT SUPPORTED. And changed the default to INVALID.
--
--	- gponOntOltsideOpInfoRxOpticalSignalLevel attribute in gponOntOltsideOpInfoTable
--	- gponPonOltsideOpInfoTxOpticalSignalLevel attribute in gponPonOltsideOpInfoTable	
--	- gponPonOltsideOpInfoTemp attribute in gponPonOltsideOpInfoTable
--	- gponPonOltsideOpInfoVoltage attribute in gponPonOltsideOpInfoTable
--	- gponPonOltsideOpInfoBiasCurrent attribute in gponPonOltsideOpInfoTable
--
--
-- John Boyle - 3/12/2008
-- For FGU4.5.5: 
--
-- For gponOntAniOpInfoLaserBiasCurrent attribute in gponOntAniOpInfoTable, changed the range:
--	- FROM :   	-65536 ... +65538
--	- TO:   		0  ... +131074
-- Reason is because the measurement from OMCI is actually a 16 bit unsigned integer
-- (with resolution of 2uA). 
--
--
-- John Boyle - 3/11/2008
-- For FGU4.5.5: 
--
-- BDFam33193 - Enable/Disable Ethernet port-to-port Traffic
--	- In bponOntTable, marked bponOntEtherPortToPortEnableInd attribute as NOT SUPPORTED
--	  as of FGU4.5.5 - since it was forwarded for implementation in 4.6 (we'll just see about that).
--
--
-- John Boyle - 3/4/2008
-- For FGU4.5.5: 
--
-- In gponOntAniOpInfoTable, tweaked all attributes to indicate that they are SUPPORTED for FGU4.5.5, and made
-- all the the descriptions look similar).
--
--
-- John Boyle - 3/3/2008
-- For FGU4.5.5: 
--
-- Made the following changes to the gponOntAniOpInfoTable:
--   	 - For gponOntAniOpInfoOpticalSignalLevel, extended range to account for situation where attribute is not
--	   supported by the ONT.
--	 - Added the following attributes:
--		- gponOntAniOpInfoPowerFeedVoltage (SUPPORTED for FGU4.5.5)
--		- gponOntAniOpInfoTxOpticalSignalLevel  (SUPPORTED for FGU4.5.5)
--		- gponOntAniOpInfoLaserBiasCurrent (SUPPORTED for FGU4.5.5)
--		- gponOntAniOpInfoTemperature (SUPPORTED for FGU4.5.5)
--
-- In gponPonOltsideOpInfoTable, noted the following attributes are SUPPORTED
-- for FGU4.5.5 release:
--	gponPonOltsideOpInfoTemp	
--	gponPonOltsideOpInfoVoltage
--	gponPonOltsideOpInfoBiasCurrent
--	
--
--
--
-- John Boyle - 2/19/2008
-- For FGU4.5.5: 
--
-- BDFam35047 - DBA Algorithm Improvement
--
-- Added the following attribute to the gponBwProfileTable:
--	gponBwProfileAIR	
--
-- In gponPonOltsideOpInfoTable, noted the following attributes are NOT SUPPORTED
-- yet for any release:
--	gponPonOltsideOpInfoTemp	
--	gponPonOltsideOpInfoVoltage
--	gponPonOltsideOpInfoBiasCurrent
--
--
-- John Boyle - 2/11/2008
-- For FGU4.5.5: 
--
-- BDFhw07099 - RSSI: Measure Optic Levels on OLT/ONT
--
-- Added the following attributes to the gponPonOltsideOpInfoTable:
--	gponPonOltsideOpInfoTemp	
--	gponPonOltsideOpInfoVoltage
--	gponPonOltsideOpInfoBiasCurrent
--
--
-- John Boyle - 2/11/2008
-- For FGU4.5.5: 
--
--  For gponOntOltsideOpInfoRxOpticalSignalLevel attribute in gponOntOltsideOpInfoTable: 
--	Added the special value 65535 to indicate condition where value is UNKNOWN
--	(e.g. because capability is not supported).  Made this special value the default.
--
--  For gponPonOltsideOpInfoTxOpticalSignalLevel attribute in gponPonOltsideOpInfoTable: 
--	Added the special value 65535 to indicate condition where value is UNKNOWN
--	(e.g. because capability is not supported).  Made this special value the default.
--
--
-- John Boyle - 2/11/2008
-- For FGU4.5.5: 
--
-- Carried forward the following modification from FGU4.4.13:
-- BDFam36650 - Autonegotiation on the ONT Etherent Ports
-- 	- For bponLanEtherPortAutoDetectConfig attribute in bponLanEtherPortTable: 
--	  	Completely changed description to add new codepoints and change the
--		meaning of some of the old codepoints.  Left in old and new meaning 
--		juxtapositions for historical clarity.
--
-- Carried forward the following modification from FGU4.4.13:
-- ANTms76279 - Increase Traffic Profiles
--	- For gponBwProfileMaxIndex attribute, noted that for FGU4.4.13 the maximum
--		number of bandwidth profiles increased to 250.
--
-- BDFam33193 - Enable/Disable Ethernet port-to-port Traffic
--	- In bponOntTable, added the bponOntEtherPortToPortEnableInd attribute.
--
-- BDFam35581 - Secondary Softswitch IP Address
--	- In gponVoipServiceTable, added gponVoipServiceSecondaryNetGwyIpAddr attribute.
--
-- BDFhw07099 - RSSI: Measure Optic Levels on OLT/ONT
--	- Added the gponOntOltsideOpInfoTable
--	- Added the gponPonOltsideOpInfoTable
--
-- In the following tables for the following attributes, noted that ONT card type = 42 = VDLS1/POTS combo
-- is NOT SUPPORTED as of FGU4.5.5:
--		- bponOntPlanCardType attribute in bponOntPlanCardTable
--		- bponOntActualCardType attribute in bponOntActualCardTable
--
--
-- John Boyle - 12/11/2007
-- Made the following modifications for FGU4.5.5:
--
-- For BDFam34329 (Support FGO4.3 on FGU4.5.10):
--	Added enumeration in following attributes in following tables to support new ONT card type = 35 = xDSL (VDSL2) only:
--		- bponOntPlanCardType attribute in bponOntPlanCardTable
--		- bponOntActualCardType attribute in bponOntActualCardTable
--
-- For bponLanEtherPortMaxFrameSize attribute in bponLanEtherPortTable, mentioned that manages (TL1 and EMS) should
-- NOT SET this attribute, and are discouraged from using a GET on it.  It has been removed from TL1 and AMS screens as of
-- FGU4.5.5.  Attribute will eventually be NOT SUPPORTED, but not just yet.  OLT defaults to 2000.
--
-- John Boyle - 11/13/2007
-- Made the following modifications for FGU4.5:
--
-- For BDFam36757 (fault report):
--  	For bponPotsPortTerminationId attribute in bponPotsPortTable, updated the comments to reflect that when relevant 
--	and required (i.e. only for H248 mode), the first character must be alphabetic.
--
--
-- John Boyle - 10/29/2007
-- Made the following modifications for FGU4.5:
--
-- For BDFam36579 (fault report):
--  	For bponPotsPortTerminationId attribute in bponPotsPortTable, changed the comments to reflect that this 
--	attribute is only relevant and required when associated VoIP Client is in H248 mode of operation (i.e. not SIP).  
--	Also noted that uniqueness and other validation rules are only relevant when in H248 mode (i.e. rules do not
--	apply for SIP mode).
--
-- John Boyle - 10/22/2007
-- Made the following modifications for FGU4.5:
--
-- For attribute bponOntSwPlannedVersion in bponOntTable, changed the default value to the string UNPLANNED, 
--   and clarified that such a value is used to inhibit any download and activation processing associated with this attribute.
--
-- John Boyle - 10/11/2007
-- Made the following modifications for FGU4.5:
--
-- For attribute bponOntSwDownloadVersion in bponOntTable, changed the default value to the string DISABLED, 
--   and clarified that such a value is used to inhibit any download processing associated with this attribute.
--
-- Made comment changes to following attributes in following tables to indicate that FTP Server may still be accessed
--  for POTS analog data set information, even when VoipConfigurationMethod is set to SIPPING Server:
--       In gponVoipServiceTable
--	 - gponVoipServiceConfigFileName  - removed note that indicated relevant only if config mode is FTP server
--	 - gponVoipServiceFtpServerIpAddr -  removed note that indicated relevant only if config mode is FTP server
-- 	 - gponVoipServiceConfigMethod - for SIPPING Server option, added note that clarified that FTP server may still
--		accessed for POTS line info even though primary VoIP information is obtained from SIPPING Server.
--       In gponVoipServiceOpInfoTable
--	 - gponVoipServiceOpInfoFtpServerIpAddr - removed note that indicated relevant only if config mode is FTP server
--	 - gponVoipServiceOpInfoActualConfigFileName - removed note that indicated relevant only if config mode is FTP server
--
-- John Boyle - 10/5/2007
-- Made the following modifications for FGU4.5:
--
-- Commented that the following attributes in the following tables are NOT SUPPORTED for FGU4.5:
--      	In gponPotsDialTestTable:
--        		gponPotsDialTestDialtoneFrequency1	
--		gponPotsDialTestDialtoneFrequency2	
--		gponPotsDialTestDialtoneFrequency3	
--		gponPotsDialTestDialtonePowerThreshold
--		gponPotsDialTestIdleChannelPowerThreshold
--		gponPotsDialTestDialtonePowerResult	
--		gponPotsDialTestIdleChannelPowerResult
--		gponPotsDialTestDialtonePowerMeasure
--		gponPotsDialTestIdleChannelPowerMeasure
--      	In gponPotsSipDialTestTable:
-- 		gponPotsSipDialTestPingResult
--
-- John Boyle - 10/4/2007
-- Made the following modifications for FGU4.5:
--
--	ANTms47735 - SW Download Improvements
--	 -  In bponOntTable, added bponOntSwDownloadVersion attribute.
--	 -  In bponOntTable, modified the comments associated with the behavior for bponOntSwPlannedVersion attribute.
--	 -  For gponOltOntSwDownloadBehavior SCALER, indicated that as of FGU4.5 this attribute is NOT SUPPORTED.
--
-- John Boyle - 9/12/2007
-- Made the following modifications for FGU4.5:
--
--	- For gponCesServicePayloadSize attribute in gponCesServiceTable, corrected comment to again say
--	  the MODIFICATION NOT PERMITTED for this attribute.
--		
--
-- John Boyle - 9/12/2007
-- Made the following modifications for FGU4.5:
--
--	- In gponCesServiceTable, removed the MODIFICATION NOT PERMITTED comment for both
--	  the following attributes (instead now says modification is service-affecting):
--		gponCesServicePayloadEncapDelay
--		gponCesServicePayloadSize
--
--
--
-- John Boyle - 8/23/2007
-- Made the following modifications for FGU4.5:
--
--	- In gponPotsMltTestTable, for both the following attributes made the following changes:
--		gponPotsMltTestRingEquivMinThreshold 
--		gponPotsMltTestRingEquivMaxThreshold 
--	 Changed the units resolution from 0.1 REN to 0.01 REN.
--	 Extended the SYNTAX range from 0..70 to 0..700.
--
--
-- John Boyle - 7/2/2007
-- Made the following modifications for FGU4.5:
--
-- BDFam32513 (Automatic Layer 3 Ping):
--	- In gponPotsSipDialTestTable, made following changes:
--		- For gponPotsSipDialTestSummaryResult attribute, clarified that this represents
--		  the result of the draw-break portion of the test.
-- 		-  Added gponPotsSipDialTestPingResult attribute to represent the result of the
--		   automatic ping portion of the test.
--
--
-- John Boyle - 6/15/2007
-- Made the following modifications for FGU4.5:
--
-- BDFam32510 (Programmable GR-909 Thresholds):
--	- Added gponPotsMltTestTable (used for all subsequent POTS line MLT testing)
--	- In bponPotsPortTable, made note that the following attributes are NOT SUPPORTED
--	  starting with FGU4.5:
--		- bponPotsPortMltTestCmd
--		- bponPotsPortMltTestResult
--
-- BDFam32506 (Perform Line Test even if Line Busy)
--     - For the gponPotsMltTestTable (used for all subsequent POTS line MLT testing), made sure it contains
--	 a force/deny option (gponPotsMltTestMode attribute).  
--     - For gponPotsSipDialTestMode attribute in gponPotsSipDialTestTable, noted that 'force mode' is 
--	NOT SUPPORTED as of FGU4.3.
--     - For gponPotsDialTestMode attribute in gponPotsDialTestTable, noted that 'force mode' is 
--	NOT SUPPORTED as of FGU4.3.
--
-- BDFam32512 (PBDT Statistics in a Class 5 Environment)
--     - In gponPotsDialTestTable, made the following changes:
--	- gponPotsDialTestMakeResult - extended codes to account for reported measurements.
--	- gponPotsDialTestBreakResult - extended codes to account for reported measurements.
--	- Added gponPotsDialTestTimeToMakeMeasure attribute
--	- Added gponPotsDialTestTimeToBreakMeasure attribute
--	- Added gponPotsDialTestDialtoneFrequency1
--	- Added gponPotsDialTestDialtoneFrequency2
--	- Added gponPotsDialTestDialtoneFrequency3
--	- Added gponPotsDialTestDialtonePowerThreshold attribute
--	- Added gponPotsDialTestIdleChannelPowerThreshold attribute
--	- Added gponPotsDialTestDialtonePowerResult attribute
--	- Added gponPotsDialTestIdleChannelPowerResult attribute
--	- Added gponPotsDialTestDialtonePowerMeasure attribute
--	- Added gponPotsDialTestIdleChannelPowerMeasure attribute
--
-- BDFam32517 (PBDT Delay Reporting)
--     - This attribute already exists in the MIB since FGU4.3 (and is implemented):
--	- gponPotsSipDialTestDelayMeasure attribute in gponPotsSipDialTestTable
--
--
-- John Boyle - 6/11/2007
-- Made the following modifications for FGU4.4.10:
-- 	- Mentioned that the gponOltSlidInterpretationMode attribute in scaler section of the MIB is
--              SUPPORTED for FGU4.4.10
--	- For the following attributes, mentioned that management applications should use setting of  
--	  gponOltSlidInterpretationMode attribute to determine ASCII or hex display format:
--		- bponOntSubscriberLocId in bponOntTable
--		- bponPonDiscovOntSubsLocId in bponPonDiscovOntTable
--
-- John Boyle - 6/7/2007
-- Made the following modifications for FGU4.4 - carried forward to FGU4.4.10:
--
-- BDFam32812 - HEX SLID for TdE:
--   Changed SYNTAX from DisplayString to OCTET STRING for following attributes:
--	- bponOntSubscriberLocId in bponOntTable
--	- bponPonDiscovOntSubsLocId in bponPonDiscovOntTable
--
-- John Boyle - 5/24/2007
-- Made the following modifications for FGU4.4:
--
-- CR (33200) - Global DSCP to PBit:
-- For bponLanEtherPortDscpPbitMapProfile attribute in bponLanEtherPorttable:
--	- Mentioned that Value 0 implies internal pointer to auto-created DSCP-to-PBit Profile
--	  Number 51 defined in GPON MIB (which is used for system-wide mapping).
--	- Mentioned that pointer range is restricted to 0 - 50.
-- For gponDscpPbitMapProfileTable, mentioned the following restrictions:
-- 	- Rows are created by the operator, except for profile Number 51,
-- 	  which is auto-created by the system.
-- 	- Profile cannot be deleted if associated with a service. 
-- 	- Other than Profile Number 51, a profile cannot be modified at all.  
-- 	- Profile Number 51 cannot be created or deleted by the operator.
-- 	- Profile Number 51 is the only profile that can be edited by the operator.
--
--
-- John Boyle - 5/12/2007
-- Made the following modifications for FGU4.4:
--
-- BDFam32843 (GPON MIB Default Value Change):
-- For bponOntCraftEnableInd attribute in bponOntTable, changed default to disabled (instead of enabled).
--
--
-- John Boyle - 5/8/2007
-- Made the following modifications for FGU4.4.10:
--
-- BDFam31071 - Ethertype/VLAN Translation Enhancement:
-- 	For gponHsiServiceVlanId attribute in gponHsiServiceTable, updated validation rules to account 
-- 	for new Ethertype/VLAN Translation mode.
--
--
-- John Boyle - 5/3/2007
-- Made the following modifications for FGU4.4.10:
--
-- BDFam31071 - Ethertype/VLAN Translation Enhancement:
-- 	In gponHsiServiceTable, updated validation rules for the following attributes to account for new
-- 	Ethertype/VLAN Translation mode:
--		- gponHsiServiceEthertype
--		- gponHsiServiceUniSideVlan
--		- gponHsiServiceNetworkSideVlan
--
-- BDFhw80639 - ONT Craft Configurable JPC - For bponOntCraftEnableInd attribute in bponOntTable,
--	 noted that this attribute is SUPPORTED for FGU4.4.10.
--
--
-- John Boyle - 4/13/2007
-- Made the following modifications for FGU4.4:
--
-- For bponOntBerInterval attribute in bponOntTable, wrote the following
-- constraint into the comment section:
--	Starting with FGU4.4, the allowable range is constrained
--	to (8000..100000).
--
--
-- John Boyle - 4/12/2007
-- Made the following modifications for FGU4.4:
--
-- BDFam29055 (Reconfigurable Management VLANs):
-- 	- For gponHsiServiceVlan attribute in gponHsiServicetable, changed valid range from 2..4090 to 2..4094.
--	- For gponVoipServiceVlan attribute in gponVoipServicetable, changed valid range from 2..4090 to 2..4094.
-- For bponOntCraftEnableInd attribute in bponOntTable, changed default to enabled (instead of disabled).
--
--
-- John Boyle - 4/5/2007
-- Made the following modifications for FGU4.4:
--
-- To accommodate BDFam31800 (which says MIB ready for BDFhw80639):
--	 - Added bponOntCraftEnableInd attribute to bponOntTable.
--
-- John Boyle - 4/3/2007
-- Made the following modifications for FGU4.4:
--
-- Added the gponLargeStringProfileTable (along with standard 'profile objects').  This profile was
--	created so that common large string network addresses can be pointed to from multiple
--	entities.
-- For gponVoipServiceSippingServerAddress attribute in gponVoipServiceTable, changed the syntax
--	and commentary so that this attribute now represents a pointer to an entry in the newly
--	created gponLargeStringProfileTable.
--
-- John Boyle - 3/28/2007
-- Made the following modifications for FGU4.4:
--
-- For gponVideoAniAgcSetting attribute in gponVideoAniTable, changed default from 0 to 20 
--	(which represents 2.0dB).  NOTE: This change was actually delivered with FGU4.3.6 release
--	for Verizon - but it is being documented in this MIB version (for completeness). 
--	
--
-- John Boyle - 3/26/2007
-- Made the following modifications for FGU4.4:
--
-- In gponPwrShedProfileTable, limited the high-end of the range for each power shed timer
--	to 28800 seconds (i.e. 8 hours).
--
-- John Boyle - 3/8/2007
-- Made the following modifications for FGU4.4:
--
-- In gponVoipServiceTable, made modifications to following attributes:
--	- Changed gponVoipServiceSippingServerIpAddr to NOT SUPPORTED.
--	- Added gponVoipServiceSippingServerAddress.
--	- Added following validation note to gponVoipServiceClientIdentifier:
--		NOTE:  The ONT also uses this field when acquiring a SIPPING Server.
--		Therefore, if gponVoipServiceConfigMethod = 2 = SIPPING Server, then
--		this attribute cannot be null (i.e. it must be SET by the manager).
--
-- For gponVideoAniAgcModePlanned attribute in gponVideoAniTable, noted that option for 
--	'optical AGC mode' is NOT SUPPPORTED as of FGU4.4.
--
-- John Boyle - 3/1/2007
-- Made the following modifications for FGU4.4:
--
-- For bponOntEnableDisableCmd attribute in bponOntTable, added 0 back as a legal enumeration (and the 
--	default), but changed its meaning to be 0 = let system decide. 
-- For bponPonConfigRogueTestEnableDisableCmd in bponPonConfigTable, removed the 0 = Not Issued enumeration,
--	noted that DEFAULT is 2 = DISABLED. 
--
-- John Boyle - 2/28/2007
-- Made the following modifications for FGU4.4:
--
-- For bponOntEnableDisableCmd attribute in bponOntTable, changed comment to mention that attribute
--	is modifiable even if ONT is Admin UP, and also, that the change will be applied to the ONT 
--	even if the ONT is Admin DOWN.
--
-- John Boyle - 2/28/2007
-- Made the following modifications for FGU4.4:
--
-- For bponOntEnableDisableCmd attribute in bponOntTable, removed the 0 = Not Issued enumeration,
--	noted that DEFAULT is 2 = ENABLED, and mentioned that attribute is modifiable even if ONT
--	is Admin DOWN.
--
-- John Boyle - 2/27/2007
-- Made the following modifications for FGU4.4:
--
-- For bponPonStatsBerRangedInd attribute in bponPonStatsBerTable, extended the 
--	enumerations to now include all the following:
--		  0 = Not Ranged (and Not DISABLED)
--		  1 = Ranged
--		  2 = manually-DISABLED (by the operator)
-- 		  3 = auto-DISABLED (by the OLT)
--
-- John Boyle - 2/22/2007
-- Made the following modifications for FGU4.4:

-- For bponLanEtherPortDscpPbitMapProfile attribute in bponLanEtherPortTable, redefined
--	the interpretation of a 0 value pointer to mean use the system-wide mapping
--	specifed in the QoS MIB.
--
-- John Boyle - 2/20/2007
-- Made the following modifications for FGU4.3.5
--
-- For gponCesServicePayloadEncapDelay attribute in gponCesServicetable:
--	- For NxDS0 with DS1 CAS -> extended options to allow 16 (2 ms) or 24 (3 ms)
-- For gponCesServicePayloadEncapDelay attribute in gponCesServicetable and 
--       gponCesMaintProfileJitterBufferMaxDepth attribute in gponCesMaintProfiletable,
--       added following VALIDITY RULE:
--		  Max Jitter Delay in msec > 1.5 * (payload length in frames) * 0.125
--
-- John Boyle - 2/13/2007
-- Made the following modifications for FGU4.4:
--
--   (ANTms14159) - ROGUE ONT DEFENSE (more functionality)
-- 	- Added bponPonConfigRogueTestEnableDisableCmd to bponPonConfigTable
--	- Added bponPonDiscovOntDisableIndicator to bponPonDiscovOntTable
--	- For bponOntEnableDisableCmd in bponOntTable, made note that zero value is 
--	  only relevant at row creation, and that attribute must be PERSISTED by OLT.
--
--   (BDFam29274) - DATA STORAGE ON ONT (more functionality)
--  	- For bponOntForceDataStoreCmd attribute in bponOntTable, changed to note that
--	  attribute has only a single valid value (for the command).  GPON agent will
--	  use internal mechanism to ensure single command results in single execution.
--	- Added the gponOntDataStoreInfoTable (used to acquire time of last dump from ONT
--	  along with other status of the operation).
--
--   For gponDscpPbitMapProfileMapping attribute in gponDscpPbitMapProfileTable, added the 
--	following VALIDATION RULE (to limit usage of ONT filter resources): 
--		The OLT must ensure that there is no more than
--		8 contiguous DSCP-number zones of translation (where the 
--		associated P-Bit changes between the zones).

--
-- John Boyle - 2/1/2007
-- Made the following modifications for FGU4.4:
--
--  For gponDscpPbitMapProfileMapping attribute in gponDscpPbitMapProfileTable,
--	changed the default mapping.
--
--   (ANTms14159) - ROGUE ONT DEFENSE
--	-  Added bponOntEnableDisableCmd to bponOntTable
--
--   (BDFam29274) - DATA STORAGE ON ONT
--	-  Added bponOntForceDataStoreCmd to bponOntTable
--
-- John Boyle - 1/24/2007
-- Made the following modifications for FGU4.3.5
--
-- For gponPotsSipDialTestDelayMeasure attribute in gponPotsSipDialTestTable, changed units of measure
--	from milliseconds to tenths of seconds.
--
-- John Boyle - 1/18/2007
-- Made the following modifications for FGU4.4
--
--   (BDFhw81200) - CONFIGURABLE ONT POWER DOWN PROFILES 
--	- Noted that the following are SUPPORTED for FGU4.4:
--		bponOntPwrShedProfile attribute in gponOntTable
--		bponPotsPortPwrShedOverride attribute in bponPotsPortTable
--		bponLanEtherPortPwrShedOverride attribute in bponLanEtherPortTable
--	- Added bponCesPortPwrShedOverride attribute to bponCesPortTable
--	- Added bponVideoPortPwrShedOverride attribute to bponVideoPortTable
--	- Added gponPwrShedProfileCesClassTime attribute to gponPwrShedProfileTable
--	- Added the gponOntPwrShedInfoTable
--
--  (BDFam27553) - VLAN STACKING FOR VOICE
--	- Noted that the following are SUPPORTED for FGU4.4:
--		gponVoipServiceSourceVlanId attribute in gponVoipServiceTable
--
--  (BDFam29776) - G-BRICK MANAGEMENT
--	- Added new card type = 60 = Ethernet/POTS combo to following:
--		bponOntPlanCardType attribute in bponOntPlanCardTable
--		bponOntActualCardType attribute in bponOntActualCardTable
--
--   (BDFam29056) - OLT/ONT DYNAMIC UNI PARAMETERS and (BDFam26556) - PER UNI DSCP
--	- For HSI Service, VoIP Service and CES Service:  NOTED that Up and Down Bandwidth
--		Profile references can be modified (without having to ADMIN DOWN the service).
--	- Added gponDscpPbitMapProfileTable
--	- Added bponLanEtherPortDscpPbitMapProfile attribute to bponLanEtherPortTable. NOTED 
--		that DSCP-to-Pbit mapping profile reference can be modified (without having to
--		ADMIN DOWN the UNI).
--
--   (BDFam29093) - MDU/OLT V-BRICK REQUIREMENTS
--  	- For bponOntPlanCardSelfTstCmd attribute in bponOntPlanCardTable, noted that test command should
--  		be supported by integrated VDSL2/POTS combo card types as well as all plugable card types.
--
--   (BDFhw30061) - VOIP TCAs and ALARMS
--	- Added the following attributes to bponPotsPortTable:
--		- bponPotsPortSipMsgTimeoutTCAThreshold	
--		- bponPotsPortBearerPktLossTCAThreshold	
--		- bponPotsPortJitterTCAThreshold	
--
--
-- John Boyle - 1/17/2007
-- Made the following modifications for FGU4.3.5
--
--  	- For gponPotsSipDialTestPhoneNumber attribute in gponPotsSipDialTestTable, noted that attribute
--  		cannot be null when test is invoked (and must be at least one character when test is invoked).
--		Also specified the characters which are valid.
--	- For gponPotsSipDialTestDelayMeasure attribute, noted that delay is measured from time INVITE
--		message is sent until time bearer packets are first received.
--	- For bponOntPlanCardType attribute in bponOntPlanCardTable and
--		for bponOntActualCardType attribute in bponOntActualCardTable,
--		changed to note that 41 = xDSL(VDSL2)/POTS combo card type is supported
--		(starting with FGU4.4) instead of (starting with FGU4.3.5).
--
-- John Boyle - 1/10/2007
-- Made the following modifications for FGU4.3.5
--
--	- Added new NOTES and VALIDITY RULES in the comment sections of the 
--	  following CES attributes:
--		- gponCesServiceDs0TimeslotMap
--		- gponCesServiceTransmitCircuitId
--		- gponCesServiceExpectedCircuitId
--
-- John Boyle - 1/8/2007
-- Made the following modifications for FGU4.3.5
--
--	- For gponPotsSipDialTestCmd attribute in gponPotsSipDialTestTable,
--	  corrected an erroneous comment that referred to non-existent attributes.
--
--
-- John Boyle - 1/5/2007
-- Made the following modifications for FGU4.3.5
--
--	- Added the gponPotsSipDialTestTable 
--		(for SIP environment make-break dialtone test per POTS port).
--
--
-- John Boyle - 12/31/2006
-- Made the following modifications for FGU4.3.5:
--
--	- For gponPotsCallHistAvgMos attribute in gponPotsCallHistTable,  
--	  	reduced upper range from 500 to 50 (with units being tenths).
--	- For gponCesServiceRtpEnable attribute in gponCesServiceTable,
--		noted that RTP must be enabled if timing mode is differential.
--
--
-- John Boyle - 11/21/2006
-- Made the following modifications for FGU4.3.5:
--
--	- In gponPotsCallHistTable, changed maximum number of calls per POTS line 
--	  from 8 to 32, and re-introduced support for the following new attributes per call:
-- 		gponPotsCallHistRtpPeakJitter
--		gponPotsCallHistAvgJitterBufferDepth
--		gponPotsCallHistRtcpXrParticipation	
--		gponPotsCallHistAvgMos		
--		gponPotsCallHistPeakRoundtripDelay	
--		gponPotsCallHistAvgRoundtripDelay	
--
-- John Boyle - 11/16/2006
-- Made the following modifications for FGU4.3.5:
--
--	- Mentioned that modification is NOT PERMITTED for following attributes:
--		- bponCesPortStructureInd   in bponCesPortTable
--
--		- gponCesServiceSignalling   in   gponCesServiceTable
--		- gponCesServicePayloadSize   in   gponCesServiceTable	
--		- gponCesServicePayloadEncapDelay   in   gponCesServiceTable
--
--	- Mentioned that the following attributes must be unique for different CES Services
--	  within a single ONT:
--		- gponCesServiceTransmitCircuitId
--		- gponCesServiceExpectedCircuitId
--
--	- For the bponCesPortCesLoopConfig attribute in bponCesPortTable, mentioned that
--	  the CES UNI must be Admin In-Service in order to actually implement a requested loopback.
--
--
-- John Boyle - 11/9/2006
-- Made the following modifications for FGU4.3:
--
--	- For bponCesPortFraming attribute in bponCesPortTable, made following note:
--		If line is set to Structured, then this attribute can NOT be set to Unframed.
--
-- John Boyle - 11/3/2006
-- Made the following modifications for FGU4.3:
--
--	- In gponVoipServiceTable, DELETED the gponVoipServiceConfigDataTlsEnable attribute.
--
-- John Boyle - 10/31/2006
-- Made the following modifications for FGU4.3:
--
--	- In gponPotsCallHistTable, noted that the gponPotsCallHistRtpPeakJitter attribute is 
--		NOT SUPPORTED for FGU4.3.
-- 
--
-- John Boyle - 10/30/2006
-- Made the following modifications for FGU4.3:
--
--
--	- In bponOntTable, noted following attributes are NOT SUPPORTED for FGU4.3:
--		- bponOntPingRespondInd
--		- bponOntTracerouteRespondInd
--
--	- In gponPotsCallHistTable, noted that the last 5 attributes in table are NOT SUPPORTED
--		for FGU4.3, and that support is needed for 8 calls per POTS line (instead of 32).
--
--
-- John Boyle - 10/24/2006
-- Made the following modifications for FGU4.3:
--
--
--	- For bponCesPortFraming attribute in bponCesPortTable,
--		changed DEFAULT from ESF to Unframed (because the
--		default for the line is Unstructured, and Resolute only supports
--		Unframed with Unstructured).
--
--
-- John Boyle - 10/19/2006
-- Made the following modifications for FGU4.3:
--
--	- For following attributes in gponCesServiceTable, noted that editing is permitted
--	  and is service-affecting:
--		- gponCesServiceDs0TimeslotMap
--		- gponCesServiceRtpEnableInd
--	- For gponCesServiceTimingMode attribute in gponCesServicetable,
--		changed DEFAULT from differential to adaptive (because GB
--		doesn't support differential until sometime in 2007).
--
-- John Boyle - 10/12/2006
-- Made the following modifications for FGU4.3:
--
--	- For gponCesServicePayloadEncapDelay attribute in gponCesServiceTable,
--		clarified that valid values are limited to 8, 16, 24, 32 and 64.
--	- In gponCesServicePWIntervalTable, changed name of attribute 
--		FROM gponHsiServicePWIntervalNumber TO gponCesServicePWIntervalNumber
--
--
-- John Boyle - 10/10/2006
-- Made the following modifications for FGU4.3:
--
--	- Added following attributes to bponOntTable:
--		- bponOntPingRespondInd
--		- bponOntTracerouteRespondInd
--
--	- Added the following attribute to gponVoipServiceTable
--		- gponVoipServiceConfigDataTlsEnable
--
--	- For gponPotsDialTestNoMakeThresholdTimer and gponPotsDialTestNoBreakThresholdTimer
--		attributes in gponPotsDialTestTable, changed the SYNTAX so that 0 is a discrete
--		valid value outside the continuous valid range.
--		
--
-- John Boyle - 10/9/2006
-- Made the following modifications for FGU4.3:
--
--	- In gponCesServiceOpInfoTable, included gponCesServiceOpInfoServiceNumber
--		as an index to the table (this was a typo that was recently caught in review).
--		
-- John Boyle - 10/9/2006
-- Made the following modifications for FGU4.3:
--
--	- In gponCesServiceOpInfoTable, included gponCesServiceOpInfoServiceNumber
--		as an index to the table (this was a typo that was recently caught in review).
--
-- John Boyle - 10/4/2006
-- Made the following modifications for FGU4.3
--
--	- Added the gponCesServiceRtpEnableInd attribute to the gponCesServiceTable.
--
-- John Boyle - 10/3/2006
-- Made the following modifications for FGU4.3
--
--	- For bponPotsPortCustomerInfo attribute in bponPotsPortTable, changed max size of
--		octet string from 32 to 80.
--	- For gponHsiServiceLabel attribute in gponHsiServiceTable, changed max size of
--		octet string from 20 to 80.
--	- For gponVoipServiceLabel attribute in gponVoipServiceTable, changed max size of
--		octet string from 20 to 80.
--	- Added the bponLanEtherPortLabel attribute to the bponLanEtherPortTable
--	- Added the bponPonConfigLabel attribute to the bponPonConfigTable
--
--	- In gponPotsCallHistTable, changed maximum number of calls per POTS line 
--	  from 8 to 32, and added the following new attributes per call:
-- 		gponPotsCallHistRtpPeakJitter
--		gponPotsCallHistAvgJitterBufferDepth
--		gponPotsCallHistRtcpXrParticipation	
--		gponPotsCallHistAvgMos		
--		gponPotsCallHistPeakRoundtripDelay	
--		gponPotsCallHistAvgRoundtripDelay	
--
--
-- John Boyle - 10/2/2006
-- Made the following modifications for FGU4.3
--
--	- For gponPotsDialTestMode attribute in gponPotsDialtable, noted that
--		forced mode option is NOT SUPPORTED.
--	- For gponPotsDialTestToneOrPulse attribute in gponPotsDialtable, noted that
--		pulse dialing option is NOT SUPPORTED.
--
-- John Boyle - 9/29/2006
-- Made the following modifications for FGU4.3
--
--	- Changed and clarified the ranges and defaults for the following 1490 measurement attributes:
--		- gponOntAniLowerOpticalThreshold attribute in gponOntAniTable
--		- gponOntAniUpperOpticalThreshold attribute in gponOntAniTable
--		- gponOntAniOpInfoOpticalSignalLevel attribute in gponOntAniOpInfoTable
--
--
-- John Boyle - 9/29/2006
-- Made the following modifications for FGU4.3
--
--	- For gponCesServiceOpInfoReceiveCircuitId attribute in gponCesServiceOpInfotable, noted
--		that this attribute is NOT SUPPORTED by Resolute chip for FGU4.3.
--	- Added following attributes to gponVoipServiceTable:
--		gponVoipServiceConfigMethod
--		gponVoipServiceSippingServerIpAddr
--		gponVoipServiceSippingAuthUsername
--		gponVoipServiceSippingAuthPassword
--		gponVoipServiceSippingAuthRealm
--		gponVoipServiceIpsecEnable
--
--
-- John Boyle - 9/21/2006
-- Made the following modifications for FGU4.3
--
--  	- For bponCesPortTCAThresholdTable and gponCesServicePwTCAThresholdTable,
--		made note in the table intro section that the entire tables are 
--		NOT SUPPORTED for FGU4.3 (i.e. nor CES/Pseudowire TCAs for FGU4.3).
--	- In gponPotsDialTestTable, changed the range for all the timers to extend to 0.0.
--	- For bponOntSchedulerProfile attribute in bponOntTable, changed default from 0 to 1
--		(and clarified that attribute must point to an existing profile).
--
-- John Boyle - 9/19/2006
-- Made the following modifications for FGU4.3
--
--  	- In bponCesPortTCAThresholdTable, made note that TCAs for Bursty Error Seconds (BES)
--		and Controlled Slip Seconds (CSS) are NOT SUPPORTED for FGU4.3.
--	- Added the gponCesServicePwTCAThresholdTable.
--
--
-- John Boyle - 9/15/2006
-- Made the following modifications for FGU4.3
--
--  	- Fixed capitalization type - changed FROM gponPotsDialtestEntry TO GponPotsDialtestEntry.
-- 	- For gponVoipServiceSourceVlanId attribute in gponVoipServiceTable, noted that this attribute is 
--		NOT SUPPORTED for FGU4.3.
--	- For bponOntPlanCardCardConfig attribute in bponOntPlanCardTable, clarified that this attribute is
--		relevant for FGU4.3 (specifically to configure a DS1/E1 card as either DS1 or E1).
--	- In gponPotsDialTestTable, changed the defaults for the 4 timers to 0.0 (meaning that the ONT
--		should use its own internal default timer values).
--	- For gponHsiServiceNetworkSideVlanID attribute, specified that Network-side can only be FFFF
--		if UNI-side is FFFF.
--	- For bponOntSchedulerProfile attribute in bponOntTable, specified that the default is 0. 
--	- For gponOntNtpServer1IpAddr, gponOntNtpServer2IpAddr, and gponOntNtpServer3IpAddr
--		attributes in gponOntNtptable, removed the validation statement that restricted input
--		of multicast IP address range (because such addresses are allowed if operational mode
--		is either Multicast or Broadcast).
-- 	- For gponOntNtpKeyIdentifier attribute, changed SYNTAX from OCTET STRING to INTEGER, and 
--		limited the range from 0 to 65535.
--	- For bponCesPortAdminState attribute in bponCesPortTable, noted that ONT uses the unlocked
--		setting as a trigger mechanism to update the Resolute hardware.
--	- In bponCesPortTable and gponCesServiceTable, noted in some of the attributes that any edit 
--		will be service-affecting.
--
--
-- John Boyle - 9/12/2006
-- Made the following modifications for FGU4.3
--
--  	- For bponCesPortLineLength attribute in bponCesPortTable, noted that 0dB option is
--		NOT SUPPORTED for FGU4.3.
--	- For L-BitReceivePolicy attribute of PseudowireMaintProfile, noted that option to repeat
--		last received packet is NOT SUPPORTED for FGU4.3.
--	- Added the gponOntNtpTable
--
--
-- John Boyle - 9/8/2006
-- Made the following modifications for FGU4.3
--
--  	- Within gponHsiServiceTable, modified some of the validation comments associated with
--		the Ethertype and Network-side VLAN attributes.
--
--	- Provided ranges for the following attributes:
--		- gponVoipServiceSourceVlanId
--		- gponCesServiceSourceVlanId
--		- gponHsiServiceUniSideVlan
--		- gponVoipServiceNetworkSideVlan
--
--	- Added gponCesServiceLoopback attribute to gponCesServiceTable
--		(noted that it is NOT SUPPORTED for FGU4.3).
--
--	- Added the gponPotsDialTestTable (for make-break dialtone test per POTS port).
--
--
-- John Boyle - 8/30/2006
-- Made the following modifications for FGU4.3
--
--  	- Added a comment that gponVdsl2Group would be reserved by oid {apon 25}
--
--	- Added the following new tables for reading 1490 optical signal level, and setting 
--	  associated High/Low alarm thresholds:
--		- gponOntAniTable
--		- gponOntAniOpInfoTable
--
--	- To improve readability (and hopefully get-next discovery performance), removed
--	  following tables from the MIB (which relate to older BPON ATM-centric system):
--		- bponPonVpiTable
--		- bponPotsVclTable
--		- bponLanVclTable
--		- bponCesVclTable
--		- bponCesProfileTable
--		- oNUAtmVclTable
--		- oNUAtmVcCrossConnectTable
--		- bponAtmAal1ProfileTable
--		- bponAtmAal1IntervalTable
--		- bponAtmAal2CPSIntervalTable
--		
--
--
-- John Boyle - 8/22/2006
-- Made the following modifications for FGU4.3
--
--  	- For bponCesPortLineLength attribute in bponCesPortTable, extended the code-points
--	  relevant for DS1.
--
--	- In bponOntTable, added the bponOntSchedulerProfile attribute (as a pointer to
--	  Scheduler Profile in QOS MIB).
--
--
-- John Boyle - 8/21/2006
-- Made the following modifications for FGU4.3
--
--  	- For MissingPackets count attribute in gponCesServicePWCurrentIntervalTable and
--	  gponCesServicePWIntervalTable, removed the NOT SUPPORTED comment (because
--	  we found out that this count is SUPPORTED by Resolute chip).
--
-- John Boyle - 8/17/2006
-- Made the following modifications for FGU4.3
--
--  	- For gponHsiServiceTable, added following attributes (for Ethertype Map and VLAN Translation):
--		- gponHsiServiceEthertype	
--		- gponHsiServiceUniSideVlan
--		- gponHsiServiceNetworkSideVlan
--
--	- For ONT self-test, Card self-test and POTS MLT test - created new code-points
--		to handle the the cases where OLT doesn't issue the test command
--		to the ONT.
--
--	- For Voip Service, added a VLAN ID attribute that the ONT should use to tag upstream
--		bearer and signalling packets.
--
--	- Added the gponOltOntSwDownloadBehavior scaler to the OLT group.
--	  This defines (for the entire shelf) how ONT software download is handled
--	   (i.e. auto-activate after download or DO NOT auto-activate after download.
--
--	- Made some changes to bponCesPortTable attributes (to handle Resolute's 
--		capabilities regarding pseudowire).
--	- Added the bponCesPortNumPMIntervals attribute to the bponCesPortTable.
--		
--	- Made note that the bponCesPortIntervalTable is supported for FGU4.3.
--	- Added the bponCesPortCurrentIntervalTable (for current counts).
--	- Added the gponCesPortTCAThresholdTable (for TCAs).
--
--	- Added the gponCesServiceTable
--
--	- Added the gponCesMaintProfileTable (along with the scalers for IndexNext and 
--		MaxIndex).
--
--	- Added the gponCesServicePWCurrentIntervalTable
--	- Added the gponCesServicePWIntervalTable
--	- Added the gponCesServiceOntsideGemCurrentIntervalTable
--	- Added the gponCesServiceOntsideGemIntervalTable
--	- Added the gponCesServiceOltsideGemCurrentIntervalTable
--	- Added the gponCesServiceOltsideGemIntervalTable
--
--	- Added the gponCesServiceOpInfoTable
--
--
-- John Boyle - 7/18/2006
-- Made the following modifications for FGU4.2
--
--  	- For bponPotsPortMltTestResult attribute in bponPotsPortTable, changed the 
--		description to indicate the correct bitmap settings for the drop test results.
--
-- John Boyle - 7/12/2006
-- Made the following modifications for FGU4.2
--
--  	- For bponOntBerInterval attribute in bponOntTable, changed the 
--		default from 1000 to 8000.
--
-- John Boyle - 6/29/2006
-- Made the following modifications for FGU4.2
--
--  	- For the 'Threshold' textual convention type, redefined the range to be
--		as follows:  Threshold ::= INTEGER (0..4294967295).
--
--	- For all TCA Threshold setting attributes in all TCA tables, changed the SYNTAX
--		from 'Counter' to 'Threshold'.
--
-- John Boyle - 6/22/2006
-- Made the following modifications for FGU4.2
--
--  	- In gponHsiServiceOntsideGemCurrentIntervalTable:
--		- Indicated that gponHsiServiceOntsideGemCurrentIntervalValidInd
--		  attribute is NOT SUPPORTED.
--		- Removed the NOT SUPPORTED comment from the 
--		  gponHsiServiceOntsideGemCurrentIntervalLostFragsDown attribute.
--
--	- For gponHsiServiceVlanId attribute in gponHsiServiceTable, changed valid
--		range FROM 1..4093       TO 2..4090
--
--	- For gponVoipServiceVlanId attribute in gponVoipServiceTable, changed valid
--		range FROM 1..4093       TO 2..4090
--
-- John Boyle - 6/19/2006
-- Made the following modifications for FGU4.2
--
--  	- For the gponPotsCallHistRtpAvgJitter attribute in bponPotsCallHistTable, 
--	  changed description to indicate that this measurement is Average Jitter
--	  instead of Average Jitter Buffer Depth.
--
-- John Boyle - 6/16/2006
-- Made the following modifications for FGU4.2
--
--  	- In bponEtherPortTable, added the following code-points to the
--	  bponEtherPortAutoDetectConfig attribute:
--		3 = GigE (full duplex)
--		19 = GigE (half duplex)
--		32 = GigE Auto-sense
--
--  	- In bponEtherPortOpstatTable, added the following code-points to the
--	  bponEtherPortOpstatConfigIndicator attribute:
--		3 = GigE (full duplex)
--		19 = GigE (half duplex)
--
--
-- John Boyle - 6/13/2006
-- Made the following modifications for FGU4.2
--
--  	- In gponEtherTrafficTCAThresholdTable, changed following
--	  from read-only to read-write:
--		- gponEtherTrafficTCAThresholdDroppedFramesUp
--		- gponEtherTrafficTCAThresholdDroppedBytesUp
--		- gponEtherTrafficTCAThresholdDroppedFramesDown
--
--  	- In gponEtherTrafficTables (current, interval and TCA), noted that
--		all attributes regarding DroppedBytesUp are NOT SUPPORTED
--
-- John Boyle - 6/8/2006
-- Made the following modifications for FGU4.2
--
--  	- Made following changes in gponPotsCallHistTable:
--		- Changed name of attribute FROM gponPotsCallHistRtpPeakJitter
--		  TO gponPotsCallHistRtpAvgJitter, and modified description.
--		- For gponPotsCallHistRtcpParticipation attribute, changed SYNTAX
--		  from Boolean to INTEGER, and added a code for NOT SUPPORTED.
--
-- John Boyle - 6/7/2006
-- Made the following modifications for FGU4.2
--
--  	- For bponOntNormalPotsPowerHoldTimer attribute of bponOntTable.
--		made note that this is NOT SUPPORTED as of FGU4.2.
--
--	- For all Current and Interval PM tables, made note that as of FGU4.2
--		the Valid Indicator attribute is NOT SUPPORTED.
--
--	- For various OLT-Side, GEM-related Current and Interval PM Tables:
--		noted that Lost Fragments Down counter is NOT SUPPORTED.
--
-- John Boyle - 6/1/2006
-- Made the following modifications for FGU4.2
--
--	- Made note that gponOltUpgradePotsPowerHoldTimer scaler
--		is NOT SUPPORTED (might come back later or be deleted for good).
--	- Made note that gponOltUpgradePotsPowerHoldTimerWindow scaler
--		is NOT SUPPORTED (might come back later or be deleted for good).
--	- Made note that bponOntNormalPotsPowerHoldTimer attribute of bponOntTable
--		is NOT SUPPORTED (might come back later or be deleted for good).
--	- Added the bponPotsPortVoltageHoldoverTimer attribute to bponPotsPortTable.
--
--	- In order to support ONT remote debugging capability, added the following
--		attributes to the bponOntTable:
--			- bponOntDebugClientIpAddress
--			- bponOntDebugClientIpPort
-- 
--
-- John Boyle - 5/30/2006
-- Made the following modifications for FGU4.2
--
--	- For all TCA threshold attributes (in all TCA tables), changed the following:
--		- Changed SYNTAX from INTEGER to Counter
--		- A value of 4294967295 means that this threshold is disabled.
--		- The Default = 4294967295.
--
--	- Noted that the gponLanEtherTCAThresholdTable is NOT SUPPORTED
--		as of FGU4.2.
--
-- John Boyle - 5/26/2006
-- Made the following modifications for FGU4.2
--
--	- Made notes that TCAs are supported for FGU4.2 
--
--
-- John Boyle - 5/24/2006
-- Made the following modifications for FGU4.2
--
-- 	- Added the bponPotsPortCallHistCollectInd attribute to the
--		bponPotsPortTable
--	- Added new card type (i.e.MoCA = 46) to the description clauses
--		of bponOntPlanCardTable and bponOntActualCardTable
--	- Added the bponOntNormalPotsPowerHoldTimer attribute to the
--		bponOntTable
--
--	- Added gponOltGroup  OBJECT IDENTIFIER ::= { apon 24 }
--	- Added the gponOltUpgradePotsPowerHoldTimer as a scaler
--		attribute under the new gponOltGroup.
--	- Added the gponOltUpgradePotsPowerHoldTimerWindow as a scaler
--		attribute under the new gponOltGroup.
--
-- 	- Changed various comments and description to indicate that the following
--		features are Not Supported as of FGU4.2:
--			- Power Shed Profiles
--			- TCAs
--
-- John Boyle - 5/22/2006
-- Made the following modifications for FGU4.2
--
-- 	- Added the gponPotsCallHistTable (for call history per POTS line)
--	- Added the bponPonConfigRamanReductionInd attribute to the 
--		bponPonConfigTable
--
-- John Boyle - 5/19/2006
-- Made following modifications for FGU4.2:
--
--	- Added the following attributes to the gponVoipServiceTable (for DHCP Option 90):
--		- gponVoipServiceSecretId
--		- gponVoipServiceSecretK
--
--	- Changed from single UNI index to OntIndex/SpIndex for following tables:
--		- gponEtherTrafficCurrentIntervalTable
--		- gponEtherTrafficIntervalTable
--		- gponEtherTrafficTCAThresholdTable
--
--	- Changed PmCollectIndicator default from disabled to enabled for following:
--		- bponOntOntsideAggGemPmCollectInd
--		- bponOntOltsideAggGemPmCollectInd
--		- bponPonConfigAggGemPmCollectInd
--
-- John Boyle - 5/15/2006
-- Made following modifications for FGU4.2:
--
--	- Added the gponPwrShedProfileTable
--	- Added the gponPwrShedProfileIndexNext scaler
--	- Added the gponPwrShedProfileMaxIndex scaler
--
--	- Added bponOntPwrShedProfile attribute to bponOntTable
--
--	- Added bponPotsPortPwrShedOverride attribute to bponPotsPortTable
--	- Added bponLanEtherPortPwrShedOverride attribute to bponLanEtherPortTable
--	
--
--
--
--
-- John Boyle - 5/11/2006
-- Made following modifications for FGU4.2:
--
--	- Made changes such that all PMs are effectively 'on-demand'
--		(i.e. added a 'PM Collect Indicator' associated with
--		every PM table). 
--
--	- Added gponEthernetGroup  OBJECT IDENTIFIER ::= { apon 22 }
--		for generic Ethernet traffic counters
--	- Added gponEtherTrafficCurrentIntervalTable
--	- Added gponEtherTrafficIntervalTable
--	- Added gponEtherTrafficTCAThresholdTable
--
--
-- John Boyle - 5/4/2006
-- Made following modifications for FGU4.2:
--
--
--	- Changed name of  gponHsiServiceGemCurrentIntervalTable
--		to gponHsiServiceOntsideGemCurrentIntervalTable
--	- Changed name of  gponHsiServiceGemIntervalTable
--		to gponHsiServiceOntsideGemIntervalTable
--	- Added the gponHsiServiceOltsideGemCurrentIntervalTable
--	- Added the gponHsiServiceOltsideGemIntervalTable
--
--	- Changed name of  gponVoipServiceGemCurrentIntervalTable
--		to gponVoipServiceOntsideGemCurrentIntervalTable
--	- Changed name of  gponVoipServiceGemIntervalTable
--		to gponVoipServiceOntsideGemIntervalTable
--	- Added the gponVoipServiceOltsideGemCurrentIntervalTable
--	- Added the gponVoipServiceOltsideGemIntervalTable
--
--	- Added TransmitFrags and BadHeaders attributes to 
--		gponOntOntsideAggGemCurrentIntervalTable and
--		gponOntOntsideAggGemIntervalTable
--	- Added BadHeadersDown TCA threshold attribute to 
--		gponOntOntsideAggGemTCAThresholdTable
--
--	- Changed name of gponOntOltsideAggGemCurrentIntervalTable
--		to gponOntOltsideODAggGemCurrentIntervalTable and
--		added a TransmitFrags attribute.
--	- Changed name of gponOntOltsideAggGemIntervalTable
--		to gponOntOltsideODAggGemIntervalTable and
--		added a TransmitFrags attribute.
--
--	- Changed contents of gponOntOltsideAggGemCurrentIntervalTable
--	- Changed contents of gponOntOltsideAggGemIntervalTable
--	- Changed contents of gponOntOltsideAggGemTCAThresholdTable
--
--	- Added gponPonAggGemCurrentIntervalTable
--	- Added gponPonAggGemIntervalTable
--	- Added gponPonAggGemTCAThresholdTable
--
--
-- John Boyle - 4/7/2006
-- Made following modifications for FGU4.2:
--
--	- Added following attributes to bponOntTable
--		- bponOntOntsideAggGemPmCollectInd
--		- bponOntOntsideAggGemNumPMIntervals
--		- bponOntOltsideAggGemPmCollectInd
--		- bponOntOltsideAggGemNumPMIntervals
--
--	- Added the gponOntOntsideAggGemCurrentIntervalTable
--	- Added the gponOntOntsideAggGemIntervalTable
--	- Added the gponOntOltsideAggGemCurrentIntervalTable
--	- Added the gponOntOltsideAggGemIntervalTable
--	- Added the gponOntOntsideAggGemTCAThresholdTable
--	- Added the gponOntOltsideAggGemTCAThresholdTable
--
--	- Added the gponLanEtherCurrentIntervalTable
--	- Added the gponLanEtherTCAThresholdTable
--
--	- Added following attributes to gponHsiServiceTable
--		- gponHsiServiceGemPmCollectInd
--		- gponHsiServiceGemPmNumPMIntervals
--	- Added the gponHsiServiceGemCurrentIntervalTable
--	- Added the gponHsiServiceGemIntervalTable
--
--	- Added following attributes to gponVoipServiceTable
--		- gponVoipServiceGemPmCollectInd
--		- gponVoipServiceGemPmNumPMIntervals
--	- Added the gponVoipServiceGemCurrentIntervalTable
--	- Added the gponVoipServiceGemIntervalTable
--	
--
-- John Boyle - 3/29/2006
-- Made following modifications for FGU4.1:
--
--	- For bponOntSerialNumber attribute (in bponOntTable), corrected note to say this
--		attribute cannot be edited unless ONT Admin State is set to locked.
--	- For bponOntAdminState attribute (in bponOntTable), corrected note to say this
--		attribute cannot be set to unlocked if ONT Serial Number is set to
--		the 'bogus' Serial Number.
--
-- John Boyle - 3/23/2006
-- Made following modifications for FGU4.1:
--
--	- Within gponVoipServiceTable, made note that the OLT should prohibit entry of
--		well-known IP addresses for the following attributes:
--			gponVoipServiceNetGwyIpAddr
--			gponVoipServiceDefaultNextHopAddr
--			gponVoipServiceClientIpAddr
--			gponVoipServiceFtpServerIpAddr
--
--	- For bponOntSerialNumber attribute (in bponOntTable), made note that this
--		attribute cannot be edited unless ONT Admin State is set to unlocked.
--	- For bponOntAdminState attribute (in bponOntTable), made note that this
--		attribute cannot be set to locked if ONT Serial Number is set to
--		the 'bogus' Serial Number.
--
-- John Boyle - 3/2/2006
-- Made following modifications for FGU4.1:
--
--	- For bponOntVendorProductCode attribute (in bponOntTable), made note that this
--		attribute is supported for FGU4.1 (and that ONT populates OMCI field
--		with Manufacturing Revision - as obtained from Remote Inventory).
--	- For gponVideoAniOpInfoRfPowerLevel attribute (in gponVideoAniOpInfoTable), 
--		changed the units from dbuW to dbuV.
--
-- John Boyle - 2/28/2006
-- Made following modifications for FGU4.1:
--
--	- For PloamCurrStatus attribute (in bponOntOpInfoTable), redefined the
--		bitmap numbers to better align with numbers in the Alarm Definition Spec.
--		
--
--
-- John Boyle - 2/23/2006
-- Made following modifications for FGU4.1:
--
--	- Deleted the bponOntPloamCurrStatus attribute from the bponOntTable (was
--		moved to a newly created bponOntOpInfoTable).
--	- Created the bponOntOpInfoTable (to include PloamCurrStatus attribute).
--	- For gponBwProfileDT attribute in gponBwProfileTable, clarified that units are
--		actually 125 microseconds (instead of .125 microseconds).
--
--
-- John Boyle - 2/16/2006
-- Made following modifications for FGU4.1:
--
--	- For bponPotsPortVoipServiceIndex in bponPotsPortTable, changed the
--		SYNTAX from ifIndex to INTEGER (since this pointer is not really the ifIndex
--		of the VoIP Client, but rather the Service Number).
--	- For gponVoipServiceOpInfoActualConfigFileName attribute in gponVoipServiceOpInfoTable,
--		changed ACCESS from read-write to read-only (since all attributes in this
--		must be read-only).
--
-- John Boyle - 2/9/2006
-- Made following modifications for FGU4.1:
--
--	- For the bponOntSerialNumber attribute (in the bponOntTable), added the following 
--		comment: Prior to FGU4.1, the OLT would only overwrite the provisioned
--		Serial Number (with the acquired Serial Number) if the provisioned 
--		Serial Number was 'bogus' (and the provisioned SLID matches the
--		acquired SLID).  Starting with FGU4.1, the OLT will overwrite any 
--		provisioned Serial Number (with the acquired Serial Number) if the
--		provisioned SLID matches the acquired SLID).  OLT will also overwrite
--		 any provisioned Serial Number (with acquired Serial Number) if 
--		 provisioned SLID matches acquired Serial Number (when an actual
--		 SLID message is not received). 
--	- For ANI Index in gponVideoAniTable and gponVideoAniOpInfoTable, changed the
--		SYNTAX from ifIndex to INTEGER (since ANI is not really an ifIndex).
--	- For gponVoipServiceClientIdentifier attribute (in gponVoipServiceTable), clarified 
--		that the default value is the null value.
--	- For gponHsiServiceCustomerId attribute (in gponHsiServiceTable) and 
--		gponVoipServiceCustomerId attribute (in gponVoipServiceTable), increased
--		size of both attributes from 32 bytes to 64 bytes.
--	- Added bponPonConfigClosestOntDistance attribute to bponPonConfigtable (used 
--		for OLT determination of equalization delay).
--	- Added gponBwProfileDT attribute to gponBwProfileTable (used by OLT to compute
--		upstream granting behavior).
--	- For bponOntSubscriberLocId attribute (in bponOntTable), increased size of attribute
--		from 10 bytes to 12 bytes (for cases when OLT wants to compare provisioned
--		SLID with acquired Serial Number).
--	- For gponVoipServiceConfigFileName attribute (in gponVoipServiceTable) noted that this
--		attribute now takes on the characteristic of being the Planned VoIP Configuration
--		File Name, and that it can be edited by the manager.
--	- Added gponVoipServiceOpInfoActualConfigFileName attribute to the gponVoipServiceOpInfoTable
--		(used for obtaining the actual VoIP Config file name being used by the ONT).
--
--
--
-- John Boyle - 1/27/2006
-- Made following modifications for FGU4.1, which is based on
-- FGU4.0:
--
--	- Brought back the bponVideoPortTable, and noted that it is applicable for
--		for FGU4.1.  Also added following attribute to this table:
--		bponVideoPortPowerControl.
--	- Added the gponVideoAniTable
--	- Added the gponVideoAniOpInfoTable
--	- For bponOntPlanCardType attribute (in bponOntPlanCardTable), noted that
--		Type 38 = Video is relevant for FGU4.1.
--	- For bponOntActualCardType attribute (in bponOntActualCardTable), noted that
--		Type 38 = Video is relevant for FGU4.1.
--	- Added gponVoipServiceClientIdentifier attribute to the gponVoipServiceTable
--		(used by ONT to construct DHCP Option 61 field).
--	- For gponVoipServiceDscpSetting attribute (in gponVoipServicetable), changed
--		description to note that this is the DSCP setting to be used for 
--		signalling and management packets (not bearer packets).  Also changed
--		the default from 46 (Expedited Forwarding) to 24 (Class Selector 3).
--	- Added the bponPotsPortDscpSetting attribute to the bponPotsPortTable (used to
--		establish the DSCP value to tag bearer packets for a specific POTS port).
--	- For gponVoipServiceGwyOption attribute (in gponVoipServicetable), extended the
--		enumeration list to include SIP 1 (compatible with Broadsoft softswitch) 
--		and SIP 2 (compatible with Nortel softswitch).
--	- Added the gponHsiServiceCustomerId attribute to the gponHsiServiceTable (used 
--		by OLT DHCP relay function to construct DHCP Option 82 field).
--	- Added the gponVoipServiceCustomerId attribute to the gponVoipServiceTable (used 
--		by OLT DHCP relay function to construct DHCP Option 82 field).
--	- Added the bponOntPloamCurrStatus attribute to the bponOntTable (used to view
--		PLOAM alarms/conditions that may be masked due to alarm hierarchy).
-- 
--
--
--
-- John Boyle - 9/28/2005
-- Made following changes:
--	- In bponLanEtherPortTable, changed the OID for 
--	  bponLanEtherPortNumPM Intervals from 25 to 23
--	  (to make it match with FGU2.6.1) - and renumbered subsequent
--	  OIDs in the table.  Same attribute must have same OID across
--	  GPON releases.
--
-- John Boyle - 9/14/2005
-- Made following changes:
--	- For gponVoipServiceTable, changed default values for following
--		- gponVoipServiceGwySigPort (to 2944).
--		- gponVoipServiceDscpSetting (to 1011100).
--
--
-- John Boyle - 8/25/2005
-- Made following changes:
--	- For bponOntCountryCode attribute in bponOntTable, made note
--	  that this attribute in not supported for FGU4.0.
--	- For gponVoipServiceGwySigEncoding attribute in gponVoipServiceTable, 
--	  made note that the default value is the only supported value for FGU4.0.
--	- For gponVoipServiceGwySigProtocol attribute in gponVoipServiceTable, 
--	  made note that the default value is the only supported value for FGU4.0.
--	
--
--
-- John Boyle - 8/25/2005
-- Made following changes:
--	Since downstream FEC is enabled/disabled on a PON basis
--	(instead of on an ONT basis), did the following:
--		- Deleted bponOntFecDownstreamInd attribute from the bponOntTable
--		 (and renumbered subsequent OIDs).
--		- Added bponPonConfigFecDownstreamInd attribute to the bponPonConfigTable
--
--
-- John Boyle - 8/17/2005
-- Made following changes:
--	- Deleted Max Number MAC Addresses attribute from bponLanEtherPortTable.
--
--
--
-- John Boyle - 8/17/2005
-- Made following changes:
--	- Deleted Max Number MAC Addresses attribute from bponLanEtherPortTable.
--
--
-- John Boyle - 8/12/2005
-- Made following changes:
--	- Moved attributes for QOS Profile Pointer and Max Number MAC Addresses
--	  	from gponHsiServiceTable to bponLanEtherPortTable.  This change
--		resulted from decision to equate one ONT UNI port with one OLT
--		bridge port.  Formerly, it had been one Service equates to one 
--		bridge port.
--	- Added 50 byte gponVoipServiceConfigFileName attribute to the
--		 gponVoipServicetable.
--
--
-- John Boyle - 7/27/2005
-- Made following changes:
--	- For gponVoipServiceDscpSetting attribute in the gponVoipServiceTable:
--	  	changed the default value from 0 to 48 (i.e. binary setting for
--		Expedited Forwarding is 110000).
--
--
-- John Boyle - 7/21/2005
-- Made following changes:
--	- In both the gponHsiServiceTable and gponVoipServiceTable:
--	  	changed the description of the ServiceVlanID attribute
--		to specify the range as 1 - 4093.
--
--
-- John Boyle - 6/30/2005
-- Made following changes:
--	- For specific manually provisioned attributes in 
--	  the gponVoipServiceTable, made comment clarifications
--	  for those that are overridden by the ONT when DHCP enable
--	  option is in effect.
--
-- John Boyle - 6/20/2005
-- Made following changes:
--	- Added the gponVoipServiceOpInfoTable (used to obtain
--	  actual Voip information directly from the ONT). 
--
--
-- John Boyle - 6/16/2005
-- Made following changes:
--	- For bponPonStatsBerTable made following changes:
--		- For bponPonStatsBerUpstream, changed SYNTAX
--		  from INTEGER to Counter.
--		- For bponPonStatsBerDownstream, changed SYNTAX
--		  from INTEGER to Counter.
--
--
--
-- John Boyle - 6/16/2005
-- Made following changes:
--	- For gponHsiServiceTable and gponVoipServiceTable
--		- Made note that Up and Down Bandwidth Profile
--		  associations can be modified.
--	- In gponBwProfileTable, commented the following:
--		- Both CIR and EIR can have 0 as a value.
--		- CIR must be less than or equal to EIR.
--
--
-- John Boyle - 6/9/2005
-- Made following changes:
--	- Added following attributes to bponPonConfigTable
--		- bponPonConfigSigFailThreshold
--		- bponPonConfigSigDegradeThreshold
--
--
-- John Boyle - 6/8/2005
-- Made following changes:
--	- Added bponPonStatsBerTable
--	- Added bponPonStatsBerResetTable
--	- Deleted bponOntMulticastGemPort attribute
--		from bponOntTable
--	- Added bponPonMulticastGemPort attribute
--		to bponPonTable
--	- Added gponVoipServiceRtpBasePort attribute
--		to gponVoipServiceTable
--
--
-- John Boyle - 6/1/2005
-- Made following changes:
--	- Added gponHsiServiceMaxNumMacAddr
--	   attribute to gponHsiServiceTable.
--
--
-- John Boyle - 5/25/2005
-- Made following changes:
--	- Added gponVoipServiceClientSubnetMask
--	   attribute to gponVoipServiceTable.
--	- In gponVoipServiceTable, changed name of
--	    gponVoipServiceNetGwayNextHop to
--	    gponVoipServiceDefaultNextHop
--
--
-- John Boyle - 5/19/2005
-- Made following changes:
--	- Deleted License Group
--	- Clarified usage of Downstream BW Profile
--	- For VoIP Service, removed language about it
--	   being a UNI or being slotted.
--	- Added the bponLanEtherPortNumPMIntervals
--	   attribute to the bponLanEtherPortTable.
--	- Clarified that Profile Tables cannot be editied.
--	- For Service Tables, clarified that only simple
--	   attributes can be modified (i.e. Admin State and Label).
--	- Added bponPotsPortTerminationId attribute to
--	   bponPotsPortTable.
--	- Added bponOntMulticastGemPort attribute to
--	   bponOntTable
--	- Added a bunch of attributes to gponVoipServiceTable
--
--
-- John Boyle - 4/15/2005
-- Made following changes:
--	- Added AdminStatus and OperStatus to both the HSI
--	   Service Table and VoIP Service Table.
--	- Added Current Status bitmap to POTS port table.
--
--
-- John Boyle - 4/11/2005
-- Made following changes after initial MIB review:
-- 	- Better clarification of attribute applicability
--	  (e.g. BPON, GPON, Prior to FGU4.0, etc.)
--	- Marked a few more attributes as 'Not Supported'.
--	- Added an Admin State attribute to ONT Table.
--	- Added an Equip ID attribute to ONT Actual Card Table.
--	- Obseleted Row Status in PON Table.
--	- Added Current Status bitmap to Ethernet port table.
--	- Added QOS Profile Pointer attribute to HSI Service Table.
--	- Deleted the License Table from this MIB
--
--
-- John Boyle - 4/8/2005
-- Made following modifications for FGU4.0, which is a major
-- change from BPON to GPON (and ATM to GEM):
--
-- Added 3 new gpon groups (starting at OID 20 in the 
-- overall apon MIB)-> Profiles, Services and License.
--
-- Added the following new tables and scalers (in gpon groups)
--  that will be used starting with FGU4.0:
--	1) gponBwProfileTable
--	2) gponBwProfileIndexNext
--	3) gponBwProfileMaxIndex
--	4) gponPQProfileTable
--	5) gponPQProfileIndexNext
--	6) gponPQProfileMaxIndex
--	7) gponHsiServiceTable
--	8) gponVoipServiceTable
--
-- Made note that following BPON tables are re-used for
-- GPON.  Added attributes as necessary.  Noted which
-- attributes are BPON only, GPON only or both:
--	1) bponOntTable
--	2) bponOntPlanCardTable
--	3) bponOntActualCardTable
--	4) bponPonConfigTable
--	5) bponPonDiscovOntTable
--	6) bponPotsPortTable
--	7) bponLanEtherPortTable
--
-- Made note that the following BPON tables will not be used
-- for GPON:
--	1) bponPonVpiTable
--	2) bponPotsVclTable
--	3) bponLanOntMacBrdgTable
--	4) bponLanVclTable
--	5) bponLanIntervalTable
--	6) bponLanMacBrdgServProfTable
--	7) bponCesPortTable
--	8) bponCesVclTable
--	9) bponCesIntervalTable
--	10) bponVideoPortTable
--	11) oNUAtmVclTable
--	12) oNUAtmVcCrossConnectTable
--	13) bponAtmAal1IntervalTable
--	14) bponAtmAal2IntervalTable
--
--
-- John Boyle - 3/1/2005
-- Made following modifications for FGU2.6:
--	- Indicated that Structured/Fractional DS1
--	  and E1 is supported.
--	- For bponOntVoiceSignalOption attribute in 
--	  bponOntTable -> added support for following:
--		- GR303-H248
--		- V5.x-H248
--		- Softswitch-H248
--
--
-- John Boyle - 11/29/2004
-- Made following modifications for FGU2.5:
--	- In the bponPotsPortTable, made note that the following
--	  attributes are neither implemented nor supported:
--		- bponPotsPortSignallingCode
--		- bponPotsPortRobbedBitSig
--		- bponPotsPortCid
--
--
-- John Boyle - 10/13/2004
-- Made following modifications for FGU2.5:
--	- Added the bponLanEtherPortOpstatTable. Contains
--	  Ethernet attributes that must be retrieved directly from
--	  ONT via OMCI messages.
-- 	- Deleted the following attributes from the bponLanEtherPortTable,
--	  renumbered the OIDs, and added them to the new 
--	  bponLanEtherPortOpstatTable:
--		- ConfigIndicator
--		- LinkStatus
--	- Added an Upstream Traffic Descriptor index attribute to the 
--	   following Interwork VCL Tables: 
--		- bponPotsVclTable
--		- bponLanVclTable
--		- bponCesVclTable
--	- For the bponPotsVclTable, added commentary that rows
--	  are created by operator (instead of automatically).
--
-- John Boyle - 9/30/2004
-- Made following modifications for FGU2.5:
--	- Added an Operational State attribute to POTS Port
--	   table.
-- 	- Added comments to Operational State atributes for
--	  port related services (e.g. POTS, Ethernet, CES and 
--	  Video). Indicated that Oper State is related to ability of
--	  port to perform its function (e.g. presence/absence of
--	  Service Affecting alarms).
--
--
-- John Boyle - 9/28/2004
-- Made following modifications for FGU2.5:
-- 	- Added comments to various attributes to mention that
--	  following features descoped for FGU2.5:
--		- 802.1P
--		- Structured/Fractional DS1
--	- For Voice Signalling Option in bontTable, combined H248
--	  and MEGACO as same option, and added MGCP as new
--	  option.
--
--
-- John Boyle - 9/20/2004
-- Made following modifications for FGU2.5:
-- 	- For bponOntCountryCode attribute in bponOntTable, 
--	  added Great Britain = 44 as a supported value.
--
--
-- John Boyle - 9/9/2004
-- Made following modifications for FGU2.5:
-- 	- For bponOntCountryCode attribute in bponOntTable, 
--	  changed coding semantics to reflect ITU E.164 instead of
--	  ITU T.35.
--	- Changed semantics for Admin State and Operational State
--	  in both oNUAtmVclTable and oNUAtmVcCrossConnectTable.
--	  Made them consistent with other Admin/Oper state codings
--	  in rest of the APON MIB.
--
--
-- John Boyle - 9/8/2004
-- Made following modifications for FGU2.5:
-- 	- Removed Admin State and Oper State from BponOnt Table.
--	- Made a few notes regarding attributes that are
--	   'Not Supported' for initial FGU2.5.
--	- Made a few notes for various tables regarding whether they
--	   are created dynamically (create-and-go) or statically (i.e.
--	   automatically by OLT) - this is trying to document behavior
--	   that is special for the initial FGU2.5 release.
--	  
--
-- John Boyle - 8/27/2004
-- Made following modifications for FGU2.5:
-- 	- Split ONT card tables into 2 tables: Planned and
--	  Actual.
--	- Changed Country Code assignments to refer to ITU T.35. 
--	- A few other changes stemming from review comments.
--
--	- Created the following tables, which are essentially the same
--	  as old apon Tables - but their prefix has been changed from 
--	  apon to bpon - and their OIDs have been changed to move
--	  them into the appropriate bpon group:
--		1) bponPonConfigGroup
--		2) bponPonDiscovOntTable
--		3) bponLanMacBrdgServProfTable
--		4) bponAtmAal1ProfileTable
--		5) bponCesProfileTable
--
--
-- John Boyle - 7/28/2004
-- Made following modifications for FGU2.5:
-- 	- Clarified the meaning of SpIndex in various tables
--	- Introduced a few new attributes in bponOntTable
--	  (for new OMCI Proprietary message and ONT Type).
--	- A few other changes stemming from review comments
--
-- John Boyle - 5/28/2004
-- Made following modifications for FGU2.5, which was effectively
-- a complete MIB re-write:
--
-- Added 8 new bpon groups (starting at OID 10 in the 
-- overall apon MIB).
--
-- Deleted the following tables (from apon groups) which will
-- no longer be used starting with FGU2.5:
--	1) aponOntEquipTable
--	2) aponPotsVciInterwkTable
--	3) aponPotsMltTable
--	4) aponLanVciInterwkTable
--	5) aponLanServiceProfileTable
--	6) aponLanMacBrdgConfDataTable
--	7) aponLanIntervalTable
--	8) aponAtmAal1IntervalTable
--	9) aponAtmAal2IntervalTable
--	10) aponDs1VciInterwkTable
--	11) aponDs1IntervalTable
--
-- Added the following new tables (in bpon groups) that will
-- be used starting with FGU2.5:
--	1) bponOntTable
--	2) bponOntCardTable
--	3) bponPonVpiTable
--	4) bponPotsPortTable
--	5) bponPotsVclTable
--	6) bponLanOntMacBrdgTable
--	7) bponLanEtherPortTable
--	8) bponLanVclTable
--	9) bponLanEtherIntervalTable
--	10) bponCesPortTable
--	11) bponCesVclTable
--	12) bponCesIntervalTable
--	13) bponVideoPortTable
--	14) oNUAtmVclTable
--	15) oNUAtmVcCrossConnectTable
--	16) bponAtmAal1IntervalTable
--	17) bponAtmAal2IntervalTable
--
--


IMPORTS 
	OBJECT-TYPE
		FROM RFC-1212
	ifIndex , InterfaceIndexOrZero
		FROM ITF-MIB
	RowStatus, MacAddress
            		FROM SNMPv2-TC
	DisplayString 
		FROM RFC1213-MIB
	Counter, TimeTicks,  IpAddress,  Gauge
		FROM RFC1155-SMI
	VlanIndex
        		FROM Q-BRIDGE-MIB 
	asam 
		FROM SYSTEM-MIB
	InetAddressType, InetAddress
		FROM INET-ADDRESS-MIB
	AsamProfileName, AsamNextProfileIndex, AsamProfileScope, 
	AsamProfileRefCount, AsamProfilePointer, AsamProfileIndex,
	AsamProfileIndexOrZero, AsamMaxProfileIndex 
		FROM ASAM-TC-MIB; 


--
-- Attach APON-MIB under 35th branch of asam.
--

apon OBJECT IDENTIFIER ::= { asam 35 }

-- Decompose APON Managed Objects into 14 Groups.
-- The first 6 groups (prefaced with apon) carried us
-- through FGU2.1.  For FGU2.5 we re-wrote many tables
-- and changed the interface strategy.  Therefore 8 new
-- groups were created (similar to the old groups), but
-- they will be prefaced as bpon instead of apon. FGU2.5
-- (and maybe beyond) will use all bpon groups (and
-- possibly some tables in the old apon groups.  Hopefully
-- this will be apparent from the embedded comments.
--

aponOntGroup  OBJECT IDENTIFIER ::= { apon 1 }

aponPonGroup  OBJECT IDENTIFIER ::= { apon 2 }

aponPotsGroup  OBJECT IDENTIFIER ::= { apon 3 }

aponLanGroup  OBJECT IDENTIFIER ::= { apon 4 }

aponAtmGroup  OBJECT IDENTIFIER ::= { apon 5 }

aponDs1Group  OBJECT IDENTIFIER ::= { apon 6 }

-- The 8 new bpon groups (starting at OID 10 in the 
-- overall apon MIB).

bponOntGroup  OBJECT IDENTIFIER ::= { apon 10 }

bponPonGroup  OBJECT IDENTIFIER ::= { apon 11 }

bponPotsGroup  OBJECT IDENTIFIER ::= { apon 12 }

bponLanGroup  OBJECT IDENTIFIER ::= { apon 13 }

bponCesGroup  OBJECT IDENTIFIER ::= { apon 14 }

bponVideoGroup  OBJECT IDENTIFIER ::= { apon 15 }

bponAtmGroup  OBJECT IDENTIFIER ::= { apon 16 }

-- bponVdslGroup  OBJECT IDENTIFIER ::= { apon 17 }



-- New gpon groups (starting at OID 20 in the 
-- overall apon MIB).

gponProfilesGroup  OBJECT IDENTIFIER ::= { apon 20 }

gponServicesGroup  OBJECT IDENTIFIER ::= { apon 21 }

gponEthernetGroup  OBJECT IDENTIFIER ::= { apon 22 }

-- gponMocaGroup	 OBJECT IDENTIFIER ::= { apon 23 }

gponOltGroup  OBJECT IDENTIFIER ::= { apon 24 }

-- gponVdsl2Group	 OBJECT IDENTIFIER ::= { apon 25 }

gponOntSwGroup  OBJECT IDENTIFIER ::= { apon 26 }

gponOntIpGroup  OBJECT IDENTIFIER ::= { apon 27 }

gponGenericUniGroup  OBJECT IDENTIFIER ::= { apon 28 }

hpnaMIB     OBJECT IDENTIFIER ::= { apon 29 }

gponVeipGroup     OBJECT IDENTIFIER ::= { apon 30 }

gponVoipGroup  OBJECT IDENTIFIER ::= { apon 31 }

-- gatmMIB  OBJECT IDENTIFIER ::= { apon 32 }

gponGISInfoGroup  OBJECT IDENTIFIER ::= { apon 33 }


-- New epon groups (starting at OID 50 in the 
-- overall apon MIB).

-- eponGroup	 OBJECT IDENTIFIER ::= { apon 50 }
--
-- ngpon2Group	 OBJECT IDENTIFIER ::= { apon 60 }

gponIndexes	OBJECT IDENTIFIER ::= { apon 100 }


--
-- A few Textual Conventions
--


IfIndex ::= INTEGER (1..2147483647)


-- index DEFINITIONS for some PON Utilization tables (to reduce number of OIDs)

pmIntervalNum	OBJECT-TYPE
	SYNTAX INTEGER(1..288)
	ACCESS	read-only
	STATUS mandatory
	DESCRIPTION	"PM Interval Number"
	::= {gponIndexes 1}

ontRank	OBJECT-TYPE
	SYNTAX INTEGER(1..5)
	ACCESS	read-only
	STATUS mandatory
	DESCRIPTION	"ONT traffic utilization ranking on PON"
	::= {gponIndexes 2}

ponIfIndex	OBJECT-TYPE
	SYNTAX IfIndex
	ACCESS	read-only
	STATUS mandatory
	DESCRIPTION	"PON interface index"
	::= {gponIndexes 3}

ontIfIndex	OBJECT-TYPE
	SYNTAX IfIndex
	ACCESS	read-only
	STATUS mandatory
	DESCRIPTION	"ONT interface index"
	::= {gponIndexes 4}


-- OntIndex is the index of the bponOntTable.
-- its format is identical to that of an ONT ifIndex,
-- but its value is not guaranteed to be the same
-- because the ONT ifIndex is undefined at the time
-- an entry in this table is being created.
-- The coding semantics are defined in relevant PBZZA spec.

OntIndex ::= INTEGER (1..2147483647)


-- SpIndex is a FTTU definition that allows
-- indexing deeper into the ONT. As a minimum, it
-- contains the slot and port within an ONT. The
-- coding semantics of the 32 bit integer are defined
-- in the relevant GPON MIB PBZZA Interface Spec.

SpIndex ::= INTEGER (1..2147483647)

-- SpIndexOrZero is a definition that extends the SpIndex
-- definition to also include the value 0 (for cases where
-- a null pointer must also be considered).

SpIndexOrZero ::= INTEGER (0..2147483647)


Threshold ::= INTEGER (0..4294967295)

-- Administrative State -> 0 = unlock, 1 = lock

AdminState ::= INTEGER (0..1)

-- 0 equals FALSE and 1 equals TRUE

Boolean ::= INTEGER (0..1)

-- Operational State -> 0 = enabled, 1 = disabled,
--		2 = unknown

OperState ::= INTEGER (0..2)

ONUServiceType ::= INTEGER 
                         {
                          pots (1),
                          lan (2),
                          ces (3),
                          atm  (4)
                         }

-- PlannedRateUp mode
PlannedRateUp ::= INTEGER 
                         {
                          nominalLineRate (0),      -- nominal line rate (default)
                          twoDotFiveGbps (1),       -- 2.5 GBits/sec
                          tenGbps (2)               -- 10 GBits/sec                         
                         }
-- ActualRateUp mode
ActualRateUp ::= INTEGER 
                         {
                          unknown (0),              -- ONT is not activated yet (default)
                          twoDotFiveGbps (1),       -- 2.5 GBits/sec
                          tenGbps (2),              -- 10 GBits/sec
                          oneDotTwentyFiveGbps (3)  -- 1.25 GBits/sec                          
                         }

-- *********************************************
--
-- BPON ONT TABLE
--
-- This is a new table beginning with FGU2.5. It is
-- used instead of the old aponOntEquipTable. 
-- Rows are created automatically by OLT - 64 rows after
-- LT card is created. 
--
-- For FGU4.0, this table is being re-used.  Comments are 
-- made regarding whether attribute is relevant to BPON,
-- GPON or both, etc.  NOTE: For GPON, these rows are not
-- automatically created by the OLT - instead they are 
-- created as a result of operator provisioning action.
--
-- For ISAM4.0.10, this table is being re-used.
--
--
-- This table is applicable for GPON, XG-PON1 and NG-PON2 
-- Noted which attributes are relevant for each flavor of each.
-- 
-- *********************************************

bponOntTable  OBJECT-TYPE
	SYNTAX SEQUENCE OF BponOntEntry
	ACCESS	not-accessible
	STATUS	mandatory
	::= { bponOntGroup 1 }

bponOntEntry  OBJECT-TYPE
	SYNTAX 	BponOntEntry
	ACCESS	not-accessible
	STATUS	mandatory
	INDEX	{ bponOntIndex }
	::= { bponOntTable 1 }

BponOntEntry ::= SEQUENCE {
	bponOntIndex				OntIndex,
	bponOntRowStatus			RowStatus,
	bponOntVendorId			OCTET STRING,
	bponOntVersionNumber		OCTET STRING,
	bponOntSerialNumber		OCTET STRING,
	bponOntTrafficManageOption		INTEGER,
	bponOntVpVcCrossConnectOption	INTEGER,
	bponOntBatteryBackup		Boolean,
	bponOntSwActiveVersion		DisplayString,
	bponOntSwPassiveVersion		DisplayString,
	bponOntSwPlannedVersion		DisplayString,
	bponOntAllocatedUpstreamBw	INTEGER,
	bponOntOmciVpi			INTEGER,
	bponOntOmciVci			INTEGER,
	bponOntPlanNumSlots		INTEGER,
	bponOntActualNumSlots		INTEGER,
	bponOntRebootCmd			INTEGER,
	bponOntBerInterval			INTEGER,
	bponOntSelfTstCmd			INTEGER,
	bponOntSubscriberLocId		OCTET STRING,
	bponOntProvVersion			OCTET STRING,
	bponOntMaxBwUp			INTEGER,
	bponOntMaxBwDown		INTEGER,
	bponOntSubscriberId1		OCTET STRING,
	bponOntSubscriberId2		OCTET STRING,
	bponOntEquipId			OCTET STRING,
	bponOntOmccVersion		INTEGER,
	bponOntVendorProductCode		OCTET STRING,
	bponOntSecurityCapability		INTEGER,
	bponOntSecurityMode 			INTEGER,
	bponOntCountryCode		INTEGER,
	bponOntNetworkCode		INTEGER,
	bponOntVoiceSignalOption		INTEGER,
	bponOnt802Dot1PEnableOption		INTEGER,
	bponOntType			INTEGER,
	bponOntPassThrough		OCTET STRING,
	bponOntFecUpstreamInd		INTEGER,
	bponOntNumTconts			INTEGER,
	bponOntNumTrafficScheds			INTEGER,
	bponOntNumPriorityQueues		INTEGER,
	bponOntAdminState			AdminState,
	bponOntOntsideAggGemPmCollectInd			INTEGER,
	bponOntOntsideAggGemPmNumPMIntervals		INTEGER,
	bponOntOltsideODAggGemPmCollectInd		INTEGER,
	bponOntOltsideODAggGemPmNumPMIntervals		INTEGER,
	bponOntOltsideAggGemPmCollectInd		INTEGER,
	bponOntOltsideAggGemPmNumPMIntervals		INTEGER,
	bponOntPwrShedProfile			AsamProfilePointer,
	bponOntNormalPotsPowerHoldTimer		INTEGER,
	bponOntDebugClientIpAddress		IpAddress,
	bponOntDebugClientIpPort		INTEGER,
	bponOntSchedulerProfile		AsamProfilePointer,
	bponOntPingRespondInd		INTEGER,
	bponOntTracerouteRespondInd		INTEGER,
	bponOntEnableDisableCmd		INTEGER,
	bponOntForceDataStoreCmd		INTEGER,
	bponOntCraftEnableInd		INTEGER,
	bponOntSwDownloadVersion		DisplayString,
	bponOntEtherPortToPortEnableInd	INTEGER,
	bponOntDownstreamRateLimitOption	INTEGER,
	bponOntOpticalSupDailyCollectInd	INTEGER,
	bponOntOpticalSupDailyNumIntervals	INTEGER,
	bponOntPlannedVariant		DisplayString,
	bponOntAutoSwPlannedVersion	DisplayString,
	bponOntAutoSwDownloadVersion	DisplayString,
	bponOntVideoRfFilter		INTEGER,
	bponOntStaticMcastVlanXlateInd	INTEGER,
        bponOntYPSerialNumber      OCTET STRING,
        bponOntSLIDAvailability    INTEGER,
        bponOntOntsideMcastGemPmCollectInd INTEGER,
        bponOntOntsideMcastGemPmNumPMIntervals    INTEGER,
	bponOntPoliceMode		INTEGER,
	bponOntAesMode			INTEGER,
	bponOntVoipCapability		INTEGER,
	bponOntFecPmCollectInd		INTEGER,
	bponOntFecPmNumPMIntervals		INTEGER,
	bponOntLogicalAuthID		DisplayString,       
	bponOntLogicalAuthPassword  		DisplayString,
	bponOntVlanBridgeMappingMode  	INTEGER,
	bponOntVlanTranslateMode		INTEGER,
	bponOntCtcSpecVersion		INTEGER,
  	bponOntCtcOntType			INTEGER,
	bponOntCtcTxPowerControl		INTEGER,
	bponOntIPHCCapability		INTEGER,
        bponOntOntsidePonAggEtherPmCollectInd   INTEGER,
        bponOntOntsidePonAggEtherPmNumPMIntervals INTEGER,
	bponOntDscpToPriorityAlignOLTMode	INTEGER,
	bponOntSnBundleControl		INTEGER,
	bponOntSnBundleStatus		INTEGER,
	bponOntUpEncryptMode		INTEGER,
	bponOntTodControl			INTEGER,
	bponOntOltsideUpFecPmCollectInd	INTEGER,
	bponOntOltsideUpFecPmNumPMIntervals	INTEGER,
	bponOntOltsidePhyPmCollectInd	INTEGER,
	bponOntOltsidePhyPmNumPMIntervals	INTEGER,
	bponOntOntsideXgTcPmCollectInd	INTEGER,
	bponOntOntsideXgTcPmNumPMIntervals	INTEGER,
	bponOntOltsideXgTcPmCollectInd	INTEGER,
	bponOntOltsideXgTcPmNumPMIntervals	INTEGER,
	bponOntOltsidePonUtilPmNumPMIntervals	INTEGER,
	bponOntNg2PreferredChanPair	InterfaceIndexOrZero,
	bponOntNg2ActualChanPair	InterfaceIndexOrZero,
	bponOntPlannedCfgFile1	DisplayString,
	bponOntDownloadCfgFile1	DisplayString,
	bponOntPlannedCfgFile2	DisplayString,
	bponOntDownloadCfgFile2	DisplayString,
	bponOntCfgFile1Active	DisplayString,
	bponOntCfgFile1Passive	DisplayString,
	bponOntCfgFile2Active	DisplayString,
	bponOntCfgFile2Passive	DisplayString,
	bponOntTcPoliceMode	INTEGER,
	bponOntRateLimitUpstreamDhcp INTEGER,
	bponOntRateLimitUpstreamArp INTEGER,
	bponOntFlushMACMode     INTEGER,
	bponOntPlannedRateUp	PlannedRateUp,
	bponOntActualRateUp		ActualRateUp
}

bponOntIndex  OBJECT-TYPE
	SYNTAX 	OntIndex
	ACCESS	read-only
	STATUS	mandatory
	DESCRIPTION 
		"Each row is indexed by the OntIndex.

		Applicable for GPON. 
		 
		Statically defined prior to FGU4.0.
		Non-statically defined starting with FGU4.0.

		For GPON - SUPPORTED as of ISAM4.0.10 - changed syntax from IfIndex to OntIndex.
		For XG-PON1 - SUPPORTED as of ISAM4.6.02
		For NG-PON2 - SUPPORTED as of ISAM5.2 "
	::= { bponOntEntry 1 }


bponOntRowStatus  OBJECT-TYPE
	SYNTAX 	RowStatus
	ACCESS	read-write
	STATUS	mandatory
	DESCRIPTION 
		"Applicable for both BPON and GPON.

		 Prior to FGU4.0 ->All rows initially created
		 'notInService' when a PLT 
		 card is planned, and RW attributes can be 
		 pre-provisioned.  Manager 
		 sets to 'active', when ONT is actually 
		 provisioned, and to 'notInService' when ONT is
		 de-provisioned.

		 Since FGU4.0 --> All rows instantiated using 'create-and-go' to
		 provision an ONT. Set to 'destroy' to delete
		 an ONT. 

		For GPON - SUPPORTED as of ISAM4.0.10
		For XG-PON1 - SUPPORTED as of ISAM4.6.02
		For NG-PON2 - SUPPORTED as of ISAM5.2 "
	::= { bponOntEntry 2 }

bponOntVendorId  OBJECT-TYPE
	SYNTAX 	OCTET STRING (SIZE(0..4))
	ACCESS	read-only
	STATUS	mandatory
	DESCRIPTION 
		"This represents the Vendor ID field in the
		 remote inventory of the ONT - it is reported
		 by the ONT via the OMCI channel.  
		 Default - all ASCII spaces.

		Applicable for both BPON and GPON.

		For GPON - SUPPORTED as of ISAM4.0.10
		For XG-PON1 - SUPPORTED as of ISAM4.6.02
		For NG-PON2 - SUPPORTED as of ISAM5.2 "
	::= { bponOntEntry 3 }


bponOntVersionNumber  OBJECT-TYPE
	SYNTAX 	OCTET STRING (SIZE(0..14))
	ACCESS	read-only
	STATUS	mandatory
	DESCRIPTION 
		"Version Number of the ONT. Cannot be created by
		 operator - read from ONT remote inventory.
		 Default - all ASCII spaces.

		Applicable for both BPON and GPON.

		For GPON - SUPPORTED as of ISAM4.0.10
		For XG-PON1 - SUPPORTED as of ISAM4.6.02
		For NG-PON2 - SUPPORTED as of ISAM5.2 "
	::= { bponOntEntry 4 }


bponOntSerialNumber  OBJECT-TYPE
	SYNTAX 	OCTET STRING (SIZE(0..8))
	ACCESS	read-write
	STATUS	mandatory
	DESCRIPTION 
		"Represents the provisioned Serial Number
		 of the ONT.  This can either be the 'bogus'
		 Serial Number, or the Serial Number that 
		 actually gets transmitted in 983.1 PLOAM
		 message (when ranging an ONT). From a display
		 standpoint, it should be interpreted as 
		 follows: 1st 4 bytes are ASCII Vendor ID, and
		 2nd 4 bytes are a 32 bit number (which gets
		 displayed as 8 ASCII characters.  Can be set by
		 operator during pre-provisioning, and is also
		 changeable.
		 Default - 1st 4 bytes = ASCII spaces
		         - 2nd 4 bytes = 32 binary ones.

		 Prior to FGU4.1, the OLT would only overwrite the provisioned
		 Serial Number (with the acquired Serial Number) if the provisioned 
		 Serial Number was 'bogus' (and the provisioned SLID matches the
		 acquired SLID).  Starting with FGU4.1, the OLT will overwrite any 
		 provisioned Serial Number (with the acquired Serial Number) if the
		 provisioned SLID matches the acquired SLID). OLT will also overwrite
		 any provisioned Serial Number (with acquired Serial Number) if 
		 provisioned SLID matches acquired Serial Number (when an actual
		 SLID message is not received). 

		 Serial Number can only be edited if ONT Admin State is locked.

		Applicable for both BPON and GPON.

		For GPON - SUPPORTED as of ISAM4.0.10
		For XG-PON1 - SUPPORTED as of ISAM4.6.02
		For NG-PON2 - SUPPORTED as of ISAM5.2 "
	::= { bponOntEntry 5 }

bponOntTrafficManageOption  OBJECT-TYPE
	SYNTAX 	INTEGER 
	ACCESS	read-only
	STATUS	mandatory
	DESCRIPTION 
		"ONT Upstream traffics policing option.
		 priorityControlled (0),
		 cellRate(1)
		 Cannot be created by operator - read from ONT
		 remote inventory.

		Applicable for both BPON and GPON.
		 Prior to FGU4.0  --> Default = 1
		 For FGU4.0  --> Default = 0

		For GPON - NOT SUPPORTED as of ISAM4.0.10
		For XG-PON1 - NOT SUPPORTED as of ISAM4.6.02
		For NG-PON2 - NOT SUPPORTED as of ISAM5.2 "
	::= { bponOntEntry 6 }


bponOntVpVcCrossConnectOption  OBJECT-TYPE
	SYNTAX 	INTEGER 
	ACCESS	read-only
	STATUS	mandatory
	DESCRIPTION 
		"Whether ONT implements ATM cross connect
		 functionality.
		 0 = Neither VP or VC modelled
		 1 = VP modelled
		 2 = VC modelled
		 Cannot be created by operator - read from ONT
		 via OMCI.
		 Default = 0

		 Applicable for both BPON and GPON.

		For GPON - NOT SUPPORTED as of ISAM4.0.10
		For XG-PON1 - NOT SUPPORTED as of ISAM4.6.02
		For NG-PON2 - NOT SUPPORTED as of ISAM5.2 "
	::= { bponOntEntry 7 }

bponOntBatteryBackup  OBJECT-TYPE
	SYNTAX 	Boolean
	ACCESS	read-write
	STATUS	mandatory
	DESCRIPTION 
		"Whether the ONT is equipped with battery
		 backup. Modification is 
		 permitted even after ONT activation.
		 Default = 0 = False

		 Applicable for both BPON and GPON.

		For GPON - SUPPORTED as of ISAM4.0.10
		For XG-PON1 - SUPPORTED as of ISAM4.6.02
		For NG-PON2 - SUPPORTED as of ISAM5.2 "
	::= { bponOntEntry 8 }


bponOntSwActiveVersion  OBJECT-TYPE
	SYNTAX 	DisplayString
	ACCESS	read-only
	STATUS	mandatory
	DESCRIPTION 
		"The active software version in the ONT.
		 Cannot be created by operator - read from ONT.
		 Default = all spaces

		 Applicable for both BPON and GPON.

		For GPON - SUPPORTED as of ISAM4.0.10
		For XG-PON1 - SUPPORTED as of ISAM4.6.02
		For NG-PON2 - SUPPORTED as of ISAM5.2 "
	::= { bponOntEntry 9 }


bponOntSwPassiveVersion  OBJECT-TYPE
	SYNTAX 	DisplayString
	ACCESS	read-only
	STATUS	mandatory
	DESCRIPTION 
		"The passive software version in the ONT.
		 Cannot be created by operator - read from ONT.
		 Default = all spaces


		 Applicable for both BPON and GPON.

		For GPON - SUPPORTED as of ISAM4.0.10
		For XG-PON1 - SUPPORTED as of ISAM4.6.02
		For NG-PON2 - SUPPORTED as of ISAM5.2 "
	::= { bponOntEntry 10 }

bponOntSwPlannedVersion  OBJECT-TYPE
	SYNTAX 	DisplayString
	ACCESS	read-write
	STATUS	mandatory
	DESCRIPTION 
		" As of FGU4.5, this attribute takes on a new meaning. SET of this attribute
		  will cause the OLT to make every attempt to ensure that this version becomes 
		  the active image on the ONT.

		  The special string value UNPLANNED means that any download and activation processing 
		  associated with this attribute is inhibited.  UNPLANNED also means that the OLT will NOT provision this
		  ONT via OMCI with relevant information from the OLT MIB.

		  Modification is permitted even after ONT activation.

		  Default = string value UNPLANNED

		  This new meaning of UNPLANNED is applicable as of FGU4.5 is only applicable for GPON.

		  As of FGU4.6, when this attribute is set to special value AUTO, and this ONT's hardware
		  version (i.e. Version Number) and planned variant have a match in the gponOntSwVerCtlTable,
		  then the gponOntSwVerCtlPlannedSwVersion attribute (in that table) is used in place
		  of this attribute.

		For ISAM4.0.10 - stays the same as latest FGU4.x.

		As of ISAM4.3.01, the special string value DISABLED means that any download and activation processing
		associated with this attribute is inhibited.  However, unlike UNPLANNED string, the DISABLED string
		means that the OLT will provision this ONT via OMCI with relevant information from the OLT MIB.

		As of ISAM5.0, the special string value DELAYACTIVATE means that following the next ONT Out-of-Service (OOS)
		to In-Service (IS) transition, the OLT will activate the software version implied in bponOntSwDownloadVersion
		attribute.  Following completion of delayed activation logic, the OLT will replace this bponOntSwPlannedVersion 
		attribute with value implied in bponOntSwDownloadVersion attribute.

		As of ISAM5.0:
		RULE:  The following combination of values are prohibited:
			 bponOntSwPlannedVersion = DELAYACTIVATE
			 bponOntSwDownloadVersion = DISABLED

		For XG-PON1 - SUPPORTED as did GPON at ISAM4.6.02
		For NG-PON2 - SUPPORTED as GPON at ISAM5.2 "
	::= { bponOntEntry 11 }


bponOntAllocatedUpstreamBw  OBJECT-TYPE
	SYNTAX 	INTEGER 
	ACCESS	read-only
	STATUS	mandatory
	DESCRIPTION 
		"The upstream bandwidth currently allocated 
		 to this ONT (in Cells Per Second).  The total
		 aggregated upstream bandwidth for all active
		 ONTs cannot exceed 343414 Cells Per Second.
		 Cannot be created by operator - updated by
		 OLT as services are provisioned on ONT.
		 Default = 0

		 Applicable prior to FGU4.0.
		 Since FGU4.0 -> Not Supported.

		For GPON - NOT SUPPORTED as of ISAM4.0.10
		For XG-PON1 - NOT SUPPORTED as of ISAM4.6.02
		For NG-PON2 - NOT SUPPORTED as of ISAM5.2 "
	::= { bponOntEntry 12 }

bponOntOmciVpi  OBJECT-TYPE
	SYNTAX 	INTEGER (0..4095)
	ACCESS	read-write
	STATUS	mandatory
	DESCRIPTION 
		"The VPI assigned to the OMCI channel for this ONT.
		 It is statically determined based on
		 the ONT position on the PON  (i.e. Range is 1 - 32.
		 ONT 1 gets VPI 1, ONT 2 gets VPI 2, ... ONT 32 gets
		 VPI 32). Cannot be created by operator - statically
		 predetermined by system.
		 Range: 0 to 4095
		 Default = 0

		 Applicable prior to FGU4.0.
		 Since FGU4.0 -> Not Supported.

		For GPON - NOT SUPPORTED as of ISAM4.0.10
		For XG-PON1 - NOT SUPPORTED as of ISAM4.6.02
		For NG-PON2 - NOT SUPPORTED as of ISAM5.2 "
	::= { bponOntEntry 13 }

bponOntOmciVci  OBJECT-TYPE
	SYNTAX 	INTEGER 
	ACCESS	read-write
	STATUS	mandatory
	DESCRIPTION 
		"The VCI assigned for the OMCI channel for this
		 ONT. Statically determined(e.g. always value 32)
		 for Release 1. Cannot be created by
		 operator - statically predetermined by system.
		 Range: 32 to 255
		 Default = 32

		 Applicable prior to FGU4.0.
		 Since FGU4.0 -> Not Supported.

		For GPON - NOT SUPPORTED as of ISAM4.0.10
		For XG-PON1 - NOT SUPPORTED as of ISAM4.6.02
		For NG-PON2 - NOT SUPPORTED as of ISAM5.2 "
	::= { bponOntEntry 14 }

bponOntPlanNumSlots  OBJECT-TYPE
	SYNTAX 	INTEGER 
	ACCESS	read-write
	STATUS	mandatory
	DESCRIPTION 
		"This represents the number of slots that
	 	operator plans/expects in the ONT.
	 	Range: 1 to 15
	 	Default = 4

		Applicable only for BPON

		Prior to FGU4.0, agent will automatically populate this
		attribute based on choice of ONT Type. 

		For FGU4.0 -> Not Supported

		For GPON - NOT SUPPORTED as of ISAM4.0.10
		For XG-PON1 - NOT SUPPORTED as of ISAM4.6.02
		For NG-PON2 -  NOT SUPPORTED as of ISAM5.2 "
	::= { bponOntEntry 15 }

bponOntActualNumSlots  OBJECT-TYPE
	SYNTAX 	INTEGER 
	ACCESS	read-only
	STATUS	mandatory
	DESCRIPTION 
		"This represents the actual number of slots that
		 the ONT contains - discovered via OMCI.
		 Range: 0 to 16
 		 Default = 0 meaning actual number not yet 
   		 discovered

		 Applicable for both BPON and GPON.

		For ISAM4.0.10 - stays the same as latest FGU4.x (except upper-end
		range is extended to 16).
		For XG-PON1 - SUPPORTED as did GPON at ISAM4.6.02
		For NG-PON2 - SUPPORTED as GPON at ISAM5.2 "
	::= { bponOntEntry 16 }


bponOntRebootCmd  OBJECT-TYPE
	SYNTAX 	INTEGER {
		rebootActiveImage(1),
--		rebootPassiveImage(2),
		rebootViaPloam(3)
	}
	ACCESS	read-write
	STATUS	mandatory
	DESCRIPTION 
		"Manager sets this attribute to command
		 different types of ONT reboot.

		 Option 1 means that the ONT reboots with 
		 currently Active Software Image.  From an
		 OMCI standpoint, this is accomplished via
		 the Reboot Action on the ONT BPON ME.

		 Option 2 was never implemented as intended. 
		 Setting it will result in same behavior as Option 1.
		 It is recommended that a manager only use Option 1.
		 
		 Option 3 means OLT sends a proprietary PLOAM message to ONT 
		 to trigger ONT reboot.

		 
		 For the majority of cases, the planned version is equal to 
		 the active version, so setting this attribute will result in a pure reboot.
		 In rare cases, the ONT may have an error condition where the planned
		 version is stuck on the passive version (e.g. after a previous activation
		 failure).  In such a case, setting option 1 will trigger the ONT to 
		 attempt to activate the passive version.
                 In some cases, ONT's OMCI task crashed, setting this option 3 will reboot the ONT 
		 through a proprietary PLOAM message.


		 Applicable for both BPON and GPON.

		For ISAM4.0.10 - stays the same as latest FGU4.x.

		As of ISAM4.6, commented out rebootPassiveImage(2) enumeration option.
		It is NOT an option.
		Only commandable option is rebootActiveImage(1).

                As of ISAM5.4.01,add a new option 3.
                option 3 was first introduced as of ISAM5.4.01 MIB, 
                with targeted implementation in ISAM5.5.01.

		For XG-PON1 - SUPPORTED as did GPON at ISAM4.6.02
		For NG-PON2 - SUPPORTED as GPON at ISAM5.2 "
	::= { bponOntEntry 17 }



bponOntBerInterval  OBJECT-TYPE
	SYNTAX 	INTEGER (656..100000)
	ACCESS	read-write
	STATUS	mandatory
	DESCRIPTION 
		"Defines the accumulation interval (expressed in
		 number of downstream frames) for the ONU to use
		 for BER calculations. Modification permitted even
		 after row becomes 'active'.

		 Starting with FGU4.4, the allowable range is constrained
		 to (8000..100000).

		 Default = 8000 

		 Applicable for both BPON and GPON.

		For ISAM4.0.10 - stays the same as latest FGU4.x
		For XG-PON1 - NOT SUPPORTED
		For NG-PON2 - NOT SUPPORTED "
	::= { bponOntEntry 18 }


bponOntSelfTstCmd  OBJECT-TYPE
	SYNTAX 	INTEGER 
	ACCESS	read-write
	STATUS	mandatory
	DESCRIPTION 
		"Manager is only permitted to SET this attribute
		 to 1, indicating desire to execute ONT self-test.
		 Thereafter, manager issues SNMP GET to determine
		 status/result of the self-test. Agent changes
		 attribute value accordingly as follows:
		 0 - this is the initial default value, meaning no
		      self-test has been executed since ONT first
		      initialized.
		 1 - Only value settable by manager (to initiate test)
		 2 - meaning self-test is in progress.
		 3 - meaning self-test failed because ONT failed
		       to respond within reasonable time period.
		 4 - meaning self-test failed because ONT
		       indicated it could not complete the test.
		 5 - meaning self-test failed because ONT
		       indicated failure.
		 6 - meaning self-test passed because ONT
		       indicated it passed.
		 7 - meaning OLT didn't issue the self-test command.

		 Applicable for both BPON and GPON.  

		 Default = 0


		For GPON - SUPPORTED as of ISAM4.0.10
		For XG-PON1 - SUPPORTED as of ISAM4.6.02
		For NG-PON2 - SUPPORTED as of ISAM5.2 "
	::= { bponOntEntry 19 }


bponOntSubscriberLocId  OBJECT-TYPE
	SYNTAX 	OCTET STRING (SIZE(0..36))
	ACCESS	read-write
	STATUS	mandatory
	DESCRIPTION 
		"Subscriber Location ID (SLID) of the ONT. 
		 Contains the binary representation of the SLID,
		 which could consist of ASCII characters and/or
		 non-ASCII octets. Management applications
		 (e.g. EMS, TL1 interface) should use the setting of
		 gponOltSlidInterpretationMode attribute in this MIB 
		 to interpret whether ASCII or hex display format.
		 Default -  the ASCII word 'WILDCARD' in
		 uppercase, followed by 4 octets of zeroes - 
		 meaning SLID processing is turned off for this ONT.

		 For FGU4.1, this field was increased from 10 bytes to 
		 12 bytes (for cases when OLT wants to compare 
		 provisioned SLID with acquired Serial Number).

		 For FGU4.4, the SYNTAX was changed from DisplayString
		 to OCTET STRING to expand the representation format.

		As of ISAM5.2, the SIZE of this attribute was expanded from 
		12 bytes to 36 bytes, in order to also accommodate the 
		36 byte Registration ID for NG-PON2 as defined in G989.3


		For GPON - SUPPORTED as of ISAM4.0.10 (12 byte SLID)
		For XG-PON1 - SUPPORTED as of ISAM4.6.02 (12 byte SLID)
		For NG-PON2 - SUPPORTED as of ISAM5.2 (36 byte REGISTRATION ID) "
	::= { bponOntEntry 20 }


bponOntProvVersion  OBJECT-TYPE
	SYNTAX 	OCTET STRING (SIZE(0..14))
	ACCESS	read-write
	STATUS	mandatory
	DESCRIPTION 
		"The provisioned Version Number of the ONT. 
		 Version field is used to ensure provisioned
		 ONT Type is compatible with Version reported
		 by the ONT.  Otherwise, OLT raises ONT Equipment
		 Type Mismatch alarm. 
		 Default - one single asterisk * - this is the
		 wildcard value meang that version mismatch
		 alarm will not be raised for this ONT. 

		 Applicable for both BPON and GPON.


		For GPON - SUPPORTED as of ISAM4.0.10
		For XG-PON1 - SUPPORTED as of ISAM4.6.02
		For NG-PON2 - SUPPORTED as of ISAM5.2 "
	::= { bponOntEntry 21 }

bponOntMaxBwUp  OBJECT-TYPE
	SYNTAX 	INTEGER
	ACCESS	read-write
	STATUS	mandatory
	DESCRIPTION 
		"Maximum Bandwidth Upstream.  This
		  represents the maximum bandwidth
		  (in Cells Per Second), that this specific
		  ONT will ever be permitted in the upstream
		  direction.  Used in CAC calculations.

		 Units are in Cells Per Second (CPS).
		 Range is -1 to 341433 (i.e -1 to the max cells
		 per second permitted by OATD in upstream
		 direction). -1 means that this parameter is 
		 ignored by CAC.

		 The provisioned value would obviously be
		 lower than this max value, to accommodate
		 all ONTs on a PON, and to take into account
		 the limitations of a particular ONT, and the type
		 of PLT card (i.e. IQ or HCL).
	
		 Default = -1 (meaning CAC disabled)

		 Applicable prior to FGU4.0.
		 Since FGU4.0 --> Not Supported.

		For GPON - NOT SUPPORTED as of ISAM4.0.10
		For XG-PON1 - NOT SUPPORTED as of ISAM4.6.02
		For NG-PON2 - NOT SUPPORTED as of ISAM5.2 "
	::= { bponOntEntry 22 }

bponOntMaxBwDown  OBJECT-TYPE
	SYNTAX 	INTEGER
	ACCESS	read-write
	STATUS	mandatory
	DESCRIPTION 
		"Maximum Bandwidth Downstream.  This
		  represents the maximum bandwidth
		  (in Cells Per Second), that this specific
		  ONT will ever be permitted in the downstream
		  direction.  Used in CAC calculations.

		 Units are in Cells Per Second (CPS).
		 Range is -1 to 1415094  (i.e - to about 600 Mbps).
		 600 Mbps is max downstream bandwidth
		 allowed for individual HCL-based LT card).
		 -1 means that this parameter is ignored by CAC.

		 The provisioned value would obviously be
		 lower than this max value, to accommodate
		 all ONTs on a PON, and to take into account
		 the limitations of a particular ONT, and the type
		 of PLT card (i.e. IQ or HCL).
	
		 Default = -1 (meaning CAC disabled)

		 Applicable prior to FGU4.0.
		 Since FGU4.0 --> Not Supported.

		For GPON - NOT SUPPORTED as of ISAM4.0.10
		For XG-PON1 - NOT SUPPORTED as of ISAM4.6.02
		For NG-PON2 - NOT SUPPORTED as of ISAM5.2 "
	::= { bponOntEntry 23 }

bponOntSubscriberId1  OBJECT-TYPE
	SYNTAX 	OCTET STRING (SIZE(0..64))
	ACCESS	read-write
	STATUS	mandatory
	DESCRIPTION 
		"This is the 1st 64 byte free-form textual field that the
		  operator can use to associate with the ONT. 
		 Default - null string. 

		 Applicable for both BPON and GPON.

		For GPON - SUPPORTED as of ISAM4.0.10
		For XG-PON1 - SUPPORTED as of ISAM4.6.02
		For NG-PON2 - SUPPORTED as of ISAM5.2 "
	::= { bponOntEntry 24 }

bponOntSubscriberId2  OBJECT-TYPE
	SYNTAX 	OCTET STRING (SIZE(0..64))
	ACCESS	read-write
	STATUS	mandatory
	DESCRIPTION 
		"This is the 2nd 64 byte free-form textual field that the
		  operator can use to associate with the ONT. 
		 Default - null string. 

		 Applicable for both BPON and GPON.

		For GPON - SUPPORTED as of ISAM4.0.10
		For XG-PON1 - SUPPORTED as of ISAM4.6.02
		For NG-PON2 - SUPPORTED as of ISAM5.2 "
	::= { bponOntEntry 25 }

bponOntEquipId  OBJECT-TYPE
	SYNTAX 	OCTET STRING (SIZE(0..20))
	ACCESS	read-only
	STATUS	mandatory
	DESCRIPTION 
		"Used to represent specific type of ONT. In North
		 America, this may be CLEI code.
		 Default = null string

		 Applicable for both BPON and GPON.

		For GPON - SUPPORTED as of ISAM4.0.10
		For XG-PON1 - SUPPORTED as of ISAM4.6.02
		For NG-PON2 - SUPPORTED as of ISAM5.2 "
	::= { bponOntEntry 26 }


bponOntOmccVersion  OBJECT-TYPE
	SYNTAX 	INTEGER
	ACCESS	read-only
	STATUS	mandatory
	DESCRIPTION 
		"Represents the OMCI version supported by the ONT.
		 Default = 0


		 Applicable for both BPON and GPON.
		 Prior to FGU4.0 -> Not Supported
		 Since FGU4.0 -> Not Supported.

		For GPON - NOT SUPPORTED as of ISAM4.0.10
		For XG-PON1 - NOT SUPPORTED as of ISAM4.6.02
		For NG-PON2 - NOT SUPPORTED as of ISAM5.2 "
	::= { bponOntEntry 27 }


bponOntVendorProductCode  OBJECT-TYPE
	SYNTAX 	OCTET STRING (SIZE(0..2))
	ACCESS	read-only
	STATUS	mandatory
	DESCRIPTION 
		"Represents Vendor specific product code.
		 Default = null string.


		 Applicable for GPON.
		 Prior to FGU4.1 -> Not Supported
		 Since FGU4.1 -> The OLT should obtain this attribute from
			the ONT (using OMCI).  The ONT populates this
			OMCI attribute with the Manufacturing Revision (as
			obtained from its Remote Inventroy).

		For GPON - SUPPORTED as of ISAM4.0.10
		For XG-PON1 - SUPPORTED as of ISAM4.6.02
		For NG-PON2 - SUPPORTED as of ISAM5.2 "
	::= { bponOntEntry 28 }


bponOntSecurityCapability  OBJECT-TYPE
	SYNTAX 	INTEGER
	ACCESS	read-only
	STATUS	mandatory
	DESCRIPTION 
		"Represents the advanced security modes supported
		 by the ONT.
		 0 = No extra security features supported.
		 1 = AES Encryption of Downstream payload supported.

		 Applicable for both BPON and GPON.
		 Prior to FGU4.0 -> Not Supported
		 Since FGU4.0 -> Not Supported.

		For GPON - NOT SUPPORTED as of ISAM4.0.10
		For XG-PON1 - NOT SUPPORTED as of ISAM4.6.02
		For NG-PON2 - NOT SUPPORTED as of ISAM5.2 "
	::= { bponOntEntry 29 }


bponOntSecurityMode  OBJECT-TYPE
	SYNTAX 	INTEGER
	ACCESS	read-write
	STATUS	mandatory
	DESCRIPTION 
		"Used to select the advanced security mode for
		 the ONT.
		 0 = Churning will be used.
		 1 = AES Encryption will be used.
 		All secure VPs or GEM ports in an ONT must use same
		 Security Mode at any one time.

		 Applicable for both BPON and GPON.
		 Prior to FGU4.0 -> Not Supported
		 Since FGU4.0 -> Not Supported.

		For GPON - NOT SUPPORTED as of ISAM4.0.10
		For XG-PON1 - NOT SUPPORTED as of ISAM4.6.02
		For NG-PON2 - NOT SUPPORTED as of ISAM5.2 "
	::= { bponOntEntry 30 }


bponOntCountryCode  OBJECT-TYPE
	SYNTAX 	INTEGER
	ACCESS	read-write
	STATUS	mandatory
	DESCRIPTION 
		"Used to inform the ONT what country code to 
		 assume - for Voice function specifics. These country
		 codes are per ITU E.164 spec.  Some of the relevant codes
		 are as follows (but E.164 should be used as official values):
		 1 = United States
		 33 = France
		 34 = Spain
		 44 = Great Britian
		 61 = Australia
		 64 = New Zealand

 		Default = 1 = United States 

		 Applicable prior to FGU4.0.
		 Since FGU4.0 -> Not Supported.

		For GPON - NOT SUPPORTED as of ISAM4.0.10
		For XG-PON1 - NOT SUPPORTED as of ISAM4.6.02
		For NG-PON2 - NOT SUPPORTED as of ISAM5.2 "
	::= { bponOntEntry 33 }


bponOntNetworkCode  OBJECT-TYPE
	SYNTAX 	INTEGER
	ACCESS	read-write
	STATUS	mandatory
	DESCRIPTION 
		"Used to inform the ONT what carrier network
		 (within a country) to assume - for Voice function
		 specifics.
		 0 = Don't Care

 		Default = 0

		 Applicable for both BPON and GPON.
		 Prior to FGU4.0 -> Not Supported
		 Since FGU4.0 -> Not Supported.

		For GPON - NOT SUPPORTED as of ISAM4.0.10
		For XG-PON1 - NOT SUPPORTED as of ISAM4.6.02
		For NG-PON2 - NOT SUPPORTED as of ISAM5.2 "
	::= { bponOntEntry 34 }


bponOntVoiceSignalOption  OBJECT-TYPE
	SYNTAX 	INTEGER
	ACCESS	read-write
	STATUS	mandatory
	DESCRIPTION 
		"Used to inform the ONT what voice signalling
		 option to assume - for Voice function specifics.
		0 = CAS
		1 = CCS (V5.1)
		2 = CCS (V5.2)
		3 = GR303-H248
		4 = V5.x-H248
		5 = Softswitch-H248

		Applicable only for BPON.

 		Prior to FGU4.0 -> Default = 0 
		Since FGU4.0 -> Not Supported.

		For GPON - NOT SUPPORTED as of ISAM4.0.10
		For XG-PON1 - NOT SUPPORTED as of ISAM4.6.02
		For NG-PON2 - NOT SUPPORTED as of ISAM5.2 "
	::= { bponOntEntry 35 }


bponOnt802Dot1PEnableOption  OBJECT-TYPE
	SYNTAX 	INTEGER
	ACCESS	read-write
	STATUS	mandatory
	DESCRIPTION 
		"Used to inform the ONT whether 802.1P
		 special traffic handling is enabled.
		0 = Not enabled
		1 = Enabled

		 Applicable for both BPON and GPON.

		 Prior to FGU4.0 -> Not Supported
		 Since FGU4.0 -> Not Supported.

		For GPON - NOT SUPPORTED as of ISAM4.0.10
		For XG-PON1 - NOT SUPPORTED as of ISAM4.6.02
		For NG-PON2 - NOT SUPPORTED as of ISAM5.2 "
	::= { bponOntEntry 36 }

bponOntType  OBJECT-TYPE
	SYNTAX 	INTEGER
	ACCESS	read-write
	STATUS	obsolete
	DESCRIPTION 
		"Used to select the type of ONT that will be
		  provisioned.  For FGU2.6, the OLT only 
		  supports a fixed number of types - and all 
		  subsequent provisioning (e.g. OMCI card types,
		  slot numbers, numbers of ports, etc) assumes a fixed
		  configuration based on this type.  

		Prior to FGU4.0 -> the following ONT types are supported:
		1 = HONT(either 1st or 2nd generation)
		5 = BONT
		9 = MDU

		Default = 1 =  HONT

		Since FGU4.0 -> Not Supported 

		For GPON - NOT SUPPORTED as of ISAM4.0.10
		For XG-PON1 - NOT SUPPORTED as of ISAM4.6.02
		For NG-PON2 - NOT SUPPORTED as of ISAM5.2 "
	::= { bponOntEntry 37 }

bponOntPassThrough  OBJECT-TYPE
	SYNTAX 	OCTET STRING (SIZE(0..8))
	ACCESS	read-only
	STATUS	mandatory
	DESCRIPTION 
		"This is a special 4-byte field that is used to pass
		  coded information directly from the EMS to the
		  the ONT (with minimal OLT processing).  The intent
		  is that the OLT just captures the information - and then
		  passes it to the ONT using a specific 4-byte field in
		  the Alcatel Vendor Specific OMCI message called ONT
		  Generic.

		  Default = null string.

		 Prior to FGU4.0 -> Not Supported
		 Since FGU4.0 -> Not Supported.

		For GPON - NOT SUPPORTED as of ISAM4.0.10
		For XG-PON1 - NOT SUPPORTED as of ISAM4.6.02
		For NG-PON2 - NOT SUPPORTED as of ISAM5.2 "
	::= { bponOntEntry 38 }

bponOntFecUpstreamInd  OBJECT-TYPE
	SYNTAX 	INTEGER {
		enable(1),
		disable(2)
	}
	ACCESS	read-write
	STATUS	mandatory
	DESCRIPTION 
		" Used to Enable/Disable use of FEC in Upstream direction
		  for this specific ONT.

		 For GPON:	Default = 2 = Disable
		 For XG-PON1:	Default = 2 = Disable
		 For NG-PON2: 	Default = 1 = Enable

		For GPON - SUPPORTED as of ISAM4.0.10
		For XG-PON1 - SUPPORTED as of ISAM4.6.02
		For NG-PON2 - SUPPORTED as of ISAM5.2 "
	::= { bponOntEntry 39 }



bponOntNumTconts  OBJECT-TYPE
	SYNTAX 	INTEGER
	ACCESS	read-only
	STATUS	mandatory
	DESCRIPTION 
		" The number of T-CONTS supported by this ONT.
		 Default = 0 

		 Applicable only for GPON.

		For GPON - SUPPORTED as of ISAM4.0.10
		For XG-PON1 - SUPPORTED as of ISAM4.6.02
		For NG-PON2 - SUPPORTED as of ISAM5.2 "
	::= { bponOntEntry 40 }

bponOntNumTrafficScheds  OBJECT-TYPE
	SYNTAX 	INTEGER
	ACCESS	read-only
	STATUS	mandatory
	DESCRIPTION 
		" The number of Traffic Schedulers supported by this ONT.
		 Default = 0 

		 Applicable only for GPON.

		For GPON - SUPPORTED as of ISAM4.0.10
		For XG-PON1 - SUPPORTED as of ISAM4.6.02
		For NG-PON2 - SUPPORTED as of ISAM5.2 "
	::= { bponOntEntry 41 }

bponOntNumPriorityQueues  OBJECT-TYPE
	SYNTAX 	INTEGER
	ACCESS	read-only
	STATUS	mandatory
	DESCRIPTION 
		" The number of upstream Priority Queues supported by this ONT.
		 Default = 0 

		 Applicable only for GPON.

		For GPON - SUPPORTED as of ISAM4.0.10
		For XG-PON1 - SUPPORTED as of ISAM4.6.02
		For NG-PON2 - SUPPORTED as of ISAM5.2 "
	::= { bponOntEntry 42 }

bponOntAdminState  OBJECT-TYPE
	SYNTAX 	AdminState
	ACCESS	read-write
	STATUS	mandatory
	DESCRIPTION 
		"The Admin State of the ONT.
		 Default = 0 = unlocked 

		Applicable only for GPON.
		Prior to FGU4.0 --> The Admin State attribute in the 
		Interface MIB was used instead (since ONTs were
		created statically).
		Since FGU4.0--> ONTs are created non-statically in
		the Interface MIB.  Therefore we use this Admin State
		attribute instead of counterpart in Interface MIB.

		NOTE:  ONT Admin State cannot be set to unlocked if
		provisioned Serial Number is set to 'bogus' Serial Number.

		For GPON - NOT SUPPORTED as of ISAM4.0.10
		For XG-PON1 - NOT SUPPORTED as of ISAM4.6.02
		For NG-PON2 - NOT SUPPORTED as of ISAM5.2 "
	::= { bponOntEntry 43 }


bponOntOntsideAggGemPmCollectInd  OBJECT-TYPE
	SYNTAX 	INTEGER
	ACCESS	read-write
	STATUS	mandatory
	DESCRIPTION 
		" This indicates whether ONT-side aggregate
		   GEM Port Performance Monitors should be collected for this ONT.
	
		  1 = PM collection enabled
		  2 = PM collection disabled

		 Default = 1 = enabled.

		For GPON - SUPPORTED as of ISAM4.0.10
		For XG-PON1 - SUPPORTED as of ISAM4.6.02
		For NG-PON2 - SUPPORTED as of ISAM5.2 "
	::= { bponOntEntry 44 }


bponOntOntsideAggGemPmNumPMIntervals  OBJECT-TYPE
	SYNTAX 	INTEGER
	ACCESS	read-only
	STATUS	mandatory
	DESCRIPTION 
		" Indicates the number of rows currently present
		  in the gponOntOntsideAggGemIntervalTable.  This
		  is for convenience of the EMS, so that it can
		 quickly determine how many rows should be 
		 uploaded. 
		For GPON - SUPPORTED as of ISAM4.0.10
		For XG-PON1 - SUPPORTED as of ISAM4.6.02
		For NG-PON2 - SUPPORTED as of ISAM5.2 "
	::= { bponOntEntry 45 }


bponOntOltsideODAggGemPmCollectInd  OBJECT-TYPE
	SYNTAX 	INTEGER
	ACCESS	read-write
	STATUS	mandatory
	DESCRIPTION 
		" This indicates whether OLT-side On-Demand aggregate
		   GEM Port Performance Monitors should be collected for this ONT.
	
		  1 = PM collection enabled
		  2 = PM collection disabled

		 Default = 2 = disabled.

		For GPON - SUPPORTED as of ISAM4.0.10
		For XG-PON1 - SUPPORTED as of ISAM4.6.02
		For NG-PON2 - SUPPORTED as of ISAM5.2 "
	::= { bponOntEntry 46 }


bponOntOltsideODAggGemPmNumPMIntervals  OBJECT-TYPE
	SYNTAX 	INTEGER
	ACCESS	read-only
	STATUS	mandatory
	DESCRIPTION 
		" Indicates the number of rows currently present
		  in the gponOntOltsideODAggGemIntervalTable.  This
		  is for convenience of the EMS, so that it can
		 quickly determine how many rows should be 
		 uploaded. 

		For GPON - SUPPORTED as of ISAM4.0.10
		For XG-PON1 - SUPPORTED as of ISAM4.6.02
		For NG-PON2 - SUPPORTED as of ISAM5.2 "
	::= { bponOntEntry 47 }

bponOntOltsideAggGemPmCollectInd  OBJECT-TYPE
	SYNTAX 	INTEGER
	ACCESS	read-write
	STATUS	mandatory
	DESCRIPTION 
		" This indicates whether OLT-side aggregate
		   GEM Port Performance Monitors should be collected for this ONT.
	
		  1 = PM collection enabled
		  2 = PM collection disabled

		 Default = 1 = enabled

		For GPON - SUPPORTED as of ISAM4.0.10
		For XG-PON1 - SUPPORTED as of ISAM4.6.02
		For NG-PON2 - SUPPORTED as of ISAM5.2 "
	::= { bponOntEntry 48 }


bponOntOltsideAggGemPmNumPMIntervals  OBJECT-TYPE
	SYNTAX 	INTEGER
	ACCESS	read-only
	STATUS	mandatory
	DESCRIPTION 
		" Indicates the number of rows currently present
		  in the gponOntOltsideAggGemIntervalTable.  This
		  is for convenience of the EMS, so that it can
		 quickly determine how many rows should be 
		 uploaded.

		For GPON - SUPPORTED as of ISAM4.0.10
		For XG-PON1 - SUPPORTED as of ISAM4.6.02
		For NG-PON2 - SUPPORTED as of ISAM5.2 "
	::= { bponOntEntry 49 }


bponOntPwrShedProfile OBJECT-TYPE
	SYNTAX	AsamProfilePointer
	ACCESS read-write
	STATUS	mandatory
	DESCRIPTION
		" The value of this object identifies the row in the GPON
          		 Power Shed Profile Table that applies for this ONT.

		 The value 0 means that power shedding is not specified for this ONT.

		 Modification is permitted.
		 Default = 0 = meaning no shedding specified. 

		 Supported as of FGU4.4

		For GPON - SUPPORTED as of ISAM4.0.10
		For XG-PON1 - SUPPORTED as of ISAM4.6.02
		For NG-PON2 - SUPPORTED as of ISAM5.2 "
	::= { bponOntEntry 50 }

bponOntNormalPotsPowerHoldTimer  OBJECT-TYPE
	SYNTAX 	INTEGER
	ACCESS	read-write
	STATUS	mandatory
	DESCRIPTION 
		" Used to specify the normal situation timer the the ONT uses
		  to hold up POTS line power after losing communication with the OLT.

		  Range is 0 - 1440 in minutes (i.e. up to 24 hours).

		  Default = 5 minutes

		  NOT SUPPORTED as of FGU4.2

		For GPON - NOT SUPPORTED as of ISAM4.0.10
		For XG-PON1 - NOT SUPPORTED as of ISAM4.6.02
		For NG-PON2 - NOT SUPPORTED as of ISAM5.2 "
	::= { bponOntEntry 51 }

bponOntDebugClientIpAddress  OBJECT-TYPE
	SYNTAX 	IpAddress
	ACCESS	read-write
	STATUS	mandatory
	DESCRIPTION 
		" Specifies the IP address of a management system or other client machine
		   that can connect through the OLT's management system VLAN to this ONT
		   for initiating ping, traceroute or other debug commands on the ONT.  The OLT
		   may limit the number of ONTs that can simultaneously be managed in this manner.
		   A value of 0.0.0.0 (Default) indicates the ONT is not in debug mode.

		  Default = 0.0.0.0 (meaning this ONT is NOT in debug mode)

		  VALIDATION:  The OLT should prohibit entry of the 
		  following range of IP addresses:
		  224.0.0.0 to 239.255.255.255   (multicast)
    		  127.0.0.0 to 127.255.255.255   (loopback) 

		For GPON - SUPPORTED as of ISAM4.0.10
		For XG-PON1 - SUPPORTED as of ISAM4.6.02
		For NG-PON2 - SUPPORTED as of ISAM5.2 "
	::= { bponOntEntry 52 }

bponOntDebugClientIpPort  OBJECT-TYPE
	SYNTAX 	INTEGER
	ACCESS	read-only
	STATUS	mandatory
	DESCRIPTION 
		" Specifies the destination IP port that a client should use for connecting to the OLT/ONT
		   when the bponOntDebugClientIpAddress is specified.  That is, after writing its IP address,
		   the client should read this attribute to determine what destination IP port to use to
		   communicate with this ONT.

		    Default = 0 

		  NOTE: This attribute value only has legitimacy when the bponOntDebugClientIpAddress
		             attribute (above) is set to something other than 0.0.0.0 

		For GPON - SUPPORTED as of ISAM4.0.10
		For XG-PON1 - SUPPORTED as of ISAM4.6.02
		For NG-PON2 - SUPPORTED as of ISAM5.2 "
	::= { bponOntEntry 53 }


bponOntSchedulerProfile OBJECT-TYPE
	SYNTAX	AsamProfilePointer
	ACCESS read-write
	STATUS	mandatory
	DESCRIPTION
		" This object is used to reference the appropriate Profile
		 qosSubscriberSchedulerProfileTable (in the QOS MIB) -> for
		 ONT-based downstream rate limiting.

		 Must reference an existing profile.

		 Modification is permitted.
		 Default = 1 (which is the default profile delivered with the system). 

		 NOTE: This attribute must be set to 1 (i.e. the default) if bponOntDownstreamRateLimitOption
		 attribute is NOT set to 0 = ONT-based.

		Applicable only for GPON.

		For GPON - NOT SUPPORTED as of ISAM4.0.10
		For XG-PON1 - NOT SUPPORTED as of ISAM4.6.02
		For NG-PON2 - NOT SUPPORTED as of ISAM5.2 "
	::= { bponOntEntry 54 }


bponOntPingRespondInd  OBJECT-TYPE
	SYNTAX 	INTEGER
	ACCESS	read-write
	STATUS	mandatory
	DESCRIPTION 
		" This indicates whether or not ONT should respond to PING messages.
	
		  0 = PING Response Disabled
		  1 = PING Response Enabled

		 Default = 0 = Disabled.

		 NOT SUPPORTED for FGU4.3.

		For GPON - NOT SUPPORTED as of ISAM4.0.10
		For XG-PON1 - NOT SUPPORTED as of ISAM4.6.02
		For NG-PON2 - NOT SUPPORTED as of ISAM5.2 "
	::= { bponOntEntry 55 }

bponOntTracerouteRespondInd  OBJECT-TYPE
	SYNTAX 	INTEGER
	ACCESS	read-write
	STATUS	mandatory
	DESCRIPTION 
		" This indicates whether or not ONT should respond to Traceroute messages.
	
		  0 = Traceroute Response Disabled
		  1 = Traceroute Response Enabled

		 Default = 0 = Disabled.

		 NOT SUPPORTED for FGU4.3.

		For GPON - NOT SUPPORTED as of ISAM4.0.10
		For XG-PON1 - NOT SUPPORTED as of ISAM4.6.02
		For NG-PON2 - NOT SUPPORTED as of ISAM5.2 "
	::= { bponOntEntry 56 }

bponOntEnableDisableCmd  OBJECT-TYPE
	SYNTAX 	INTEGER 
	ACCESS	read-write
	STATUS	mandatory
	DESCRIPTION 
		" This attribute allows the manager to manually enable or disable
		   an ONT (used for rogue ONT action and diagnosis).  Also allows
		   option to let the system decide auto-decide.

		   NOTE: The OLT must PERSIST this attribute, because it is not persisted 
		   by the GLOB across an LT reset.
		    
		   Attribute values are as follows:
			0 - auto - let the system decide
			1 - force disable - operator-commanded disable
			2 - force enable - operator-commanded enable

		   NOTE:  Attribute can be modified even if ONT is Admin UP, and also, the
		   change will be applied to the ONT even if the ONT is Admin DOWN.

		   Default = 0

		For GPON - SUPPORTED as of ISAM4.0.10
		For XG-PON1 - SUPPORTED as of ISAM4.6.02
		For NG-PON2 - SUPPORTED as of ISAM5.2 "
	::= { bponOntEntry 57 }

bponOntForceDataStoreCmd  OBJECT-TYPE
	SYNTAX 	INTEGER 
	ACCESS	read-write
	STATUS	mandatory
	DESCRIPTION 
		" This attribute allows the manager to force the ONT to
		   transfer appropriate data from volatile storage to non-volatile
		   storage. The only valid value is 1.
		   After the manager sets the value to 1, the OLT issues
		   the appropriate OMCI message to the ONT.  
		    
		   Attribute values are as follows:
		   1 - Force Data Storage on ONT

		 The GPON agent uses internal mechanisms to keep track
		 that a single command is implemented a single time.

		For GPON - SUPPORTED as of ISAM4.0.10
		For XG-PON1 - SUPPORTED as of ISAM4.6.02
		For NG-PON2 - SUPPORTED as of ISAM5.2 "
	::= { bponOntEntry 58 }

bponOntCraftEnableInd  OBJECT-TYPE
	SYNTAX 	INTEGER
	ACCESS	read-write
	STATUS	mandatory
	DESCRIPTION 
		" This indicates whether or not the ONT supports usage of craft port functionality.
	
		  0 = Craft function Enabled
		  1 = Craft function Disabled

		 Default = 1 = Disabled.

		 SUPPORTED for FGU4.4.10

		For GPON - NOT SUPPORTED as of ISAM4.0.10
		For XG-PON1 - NOT SUPPORTED as of ISAM4.6.02
		For NG-PON2 - NOT SUPPORTED as of ISAM5.2 "
	::= { bponOntEntry 59 }

bponOntSwDownloadVersion  OBJECT-TYPE
	SYNTAX 	DisplayString
	ACCESS	read-write
	STATUS	mandatory
	DESCRIPTION 
		" As of ISAM4.0.10, SET of this attribute causes the OLT to ensure that this image version
		  is present in ONT's passive or active image.  If not already present
		  in either passive or active, OLT will download this image to passive - and
		  go no further (i.e. it won't auto-activate this version).  This attribute is used
		  to 'download only' an image. Modification is permitted even after ONT activation.

		  The special string value DISABLED means that any download processing associated
		  with this attribute is inhibited.

		  Default = string value DISABLED

		 Applicable only for GPON.

		  As of FGU4.6, when this attribute is set to special value AUTO, and this ONT's hardware
		  version (i.e. Version Number) and planned variant have a match in the gponOntSwVerCtlTable,
		  then the gponOntSwVerCtlDownloadSwVersion attribute (in that table) is used in place
		  of this attribute.

		As of ISAM5.0, if bponOntSwPlannedVersion = DELAYACTIVATE and the ONT does an OOS-to-IS transition,
		the OLT will auto-activate the image version implied in this bponOntSwDownloadVersion attribute.

		As of ISAM5.0:
		RULE:  The following combination of values are prohibited:
			 bponOntSwPlannedVersion = DELAYACTIVATE
			 bponOntSwDownloadVersion = DISABLED 


		For GPON - SUPPORTED as of ISAM4.0.10
		For XG-PON1 - SUPPORTED as did GPON at ISAM4.6.02
		For NG-PON2 - SUPPORTED as GPON at ISAM5.2 "
	::= { bponOntEntry 60 }

bponOntEtherPortToPortEnableInd  OBJECT-TYPE
	SYNTAX 	INTEGER
	ACCESS	read-write
	STATUS	mandatory
	DESCRIPTION 
		" This indicates whether or not the ONT should allow port-to-port traffic
		   exchange between Ethernet UNIs on the same ONT.
	
		  0 = Port-to-port traffic exchage Disabled
		  1 = Port-to-port traffic exchage Enabled

		 Default = 0 = Disabled.

		 Modification NOT SUPPORTED.
		 RULE: If selection = 1 (i.e. Enabled), then OLT must prohibit creation of any 
		            HSI Service or Service Flow on any Ethernet port other than Port 1. 

		 SUPPORTED as of FGU4.6

		For GPON - SUPPORTED as of ISAM4.0.10
		For XG-PON1 - SUPPORTED as did GPON at ISAM4.6.02
		For NG-PON2 - SUPPORTED as GPON at ISAM5.2 "
	::= { bponOntEntry 61 }

bponOntDownstreamRateLimitOption  OBJECT-TYPE
	SYNTAX 	INTEGER
	ACCESS	read-write
	STATUS	mandatory
	DESCRIPTION 
		" Indicates the type of downstream rate-limiting choice for this ONT.
	
		  0 = ONT-based
		  1 = Service-based

		 Default = 0 = ONT-based.

		 SUPPORTED as of FGU4.6

		 Modification NOT permitted.

		For GPON - NOT SUPPORTED as of ISAM4.0.10
		For XG-PON1 - NOT SUPPORTED as of ISAM4.6.02
		For NG-PON2 - NOT SUPPORTED as of ISAM5.2 "
	::= { bponOntEntry 62 }

bponOntOpticalSupDailyCollectInd  OBJECT-TYPE
	SYNTAX 	INTEGER
	ACCESS	read-write
	STATUS	mandatory
	DESCRIPTION 
		" This indicates whether daily optical supervision measurements
		   should be collected for this ONT.
	
		  1 = Collection enabled
		  2 = Collection disabled

		 Default = 2 = disabled.

		For GPON - SUPPORTED as of ISAM4.0.10
		For XG-PON1 - SUPPORTED as did GPON at ISAM4.6.02
		For NG-PON2 - SUPPORTED as GPON at ISAM5.2 "
	::= { bponOntEntry 63 }


bponOntOpticalSupDailyNumIntervals  OBJECT-TYPE
	SYNTAX 	INTEGER
	ACCESS	read-only
	STATUS	mandatory
	DESCRIPTION 
		" Indicates the number of rows currently present
		  in the gponOntOpticSupDailyTable.  This
		  is for convenience of the EMS, so that it can
		 quickly determine how many rows should be 
		 uploaded.

		For GPON - SUPPORTED as of ISAM4.0.10
		For XG-PON1 - SUPPORTED as did GPON at ISAM4.6.02
		For NG-PON2 - SUPPORTED as GPON at ISAM5.2 "
	::= { bponOntEntry 64 }

bponOntPlannedVariant 	OBJECT-TYPE 
	SYNTAX 	DisplayString
	ACCESS	read-write
	STATUS	mandatory
	DESCRIPTION 
		" This attribute is operator specified free-form displayable text field.
		  This attribute has same connotation as bponOntSwVerCtlPlannedVariant attribute in 
		  bponOntSwVerCtlTable (where it represents a key in that table along with 
		  bponOntSwVerCtlHwVersion attribute).

		  See descriptions in bponOntSwPlannedVersion and bponOntSwDownloadVersion
		  attributes regarding how this attribute plays a role when either of those attributes
		  are set to special value AUTO.

		  Modification is permitted. 

		  Maximum of 80 displayable characters.

		  Default = null string.
		For GPON - SUPPORTED as of ISAM4.0.10
		For XG-PON1 - SUPPORTED as did GPON at ISAM4.6.02
		For NG-PON2 - SUPPORTED as GPON at ISAM5.2 "
	::= { bponOntEntry 65 }

bponOntAutoSwPlannedVersion  OBJECT-TYPE
	SYNTAX 	DisplayString
	ACCESS	read-only
	STATUS	mandatory
	DESCRIPTION 
		" If this ONT has a matching row in the gponOntSwVerCtlTable, this attribute contains
		  the same string value contained in the gponOntSwVerCtlPlannedSwVersion attribute
		  in that matching row.

		  If there is no matching row in the table, this attribute contains the null string value.

		For ISAM4.0.10 - stays the same as latest FGU4.x

		As of ISAM5.0, this attribute value could say DELAYACTIVATE if that is what is contained in the 
		gponOntSwVerCtlPlannedSwVersion attribut in that matching row.  But once the delay activation logic
		has completed, this attribute value will reflect the actual intended Planned Version. 

		For GPON - SUPPORTED as of ISAM4.0.10
		For XG-PON1 - SUPPORTED as did GPON at ISAM4.6.02
		For NG-PON2 - SUPPORTED as GPON at ISAM5.2 "
	::= { bponOntEntry 66 }

bponOntAutoSwDownloadVersion  OBJECT-TYPE
	SYNTAX 	DisplayString
	ACCESS	read-only
	STATUS	mandatory
	DESCRIPTION 
		" If this ONT has a matching row in the gponOntSwVerCtlTable, this attribute contains
		  the same string value contained in the gponOntSwVerCtlDownloadSwVersion attribute of
		  in that matching row.

		  If there is no matching row in the table, this attribute contains the null string value.

		For GPON - SUPPORTED as of ISAM4.0.10
		For XG-PON1 - SUPPORTED as did GPON at ISAM4.6.02
		For NG-PON2 - SUPPORTED as GPON at ISAM5.2 "
	::= { bponOntEntry 67 }

bponOntVideoRfFilter  OBJECT-TYPE
	SYNTAX 	INTEGER
	ACCESS	read-write
	STATUS	mandatory
	DESCRIPTION 
		" Controls filter settings for RF Video.  

		  NOTE: This attribute is only relevant for the Cambridge ONT (i.e. Vendor ID = CIGG).
		  This attribute is only relevant if an RF Video port has been provisioned for a Cambridge ONT.
	
		  0 = Pass Nothing
		  1 = Pass only Low Band 1 (431 MHz)
		  2 = Pass Low and High Band
		  3 = Pass only Low Band 2 (639 MHz)

		 Default = 2 = Pass Low and High Band.

		 SUPPORTED as of FGU4.6.4

		 Modification is permitted.

		For ISAM4.0.10 - stays the same as latest FGU4.x

		Following text added to ISAM4.6 MIB:
		As of ISAM4.6.01, new codepoint 3 = (Low Band 2 (639 MHz)) must be SUPPORTED, 
		and meaning of codepoint 1 is clarified to mean (Low Band 1 (431 MHz)). 

		For GPON - SUPPORTED as of ISAM4.0.10
		For XG-PON1 - SUPPORTED as did GPON at ISAM4.6.02
		For NG-PON2 - SUPPORTED as GPON at ISAM5.2 "
	::= { bponOntEntry 68 }

bponOntStaticMcastVlanXlateInd  OBJECT-TYPE
	SYNTAX 	INTEGER
	ACCESS	read-write
	STATUS	mandatory
	DESCRIPTION 
		" This indicates whether or not the ONT should perform special VLAN translation
		   actions for static multicast.

		   NOTE: As of FGU4.6.4, this special translation processing only applies to 
			RIP packets.
	
		  0 = Disabled (special VLAN translation Disabled)
		  1 = Enabled (special VLAN translation Enabled)

		 Default = 0 = Disabled.

		 Modification is permitted.

		 SUPPORTED as of FGU4.6.4

		For ISAM4.0.10, this attribute is NOT SUPPORTED.

		For GPON - NOT SUPPORTED as of ISAM4.0.10
		For XG-PON1 - NOT SUPPORTED as of ISAM4.6.02
		For NG-PON2 - NOT SUPPORTED as of ISAM5.2 "
	::= { bponOntEntry 69 }

bponOntYPSerialNumber  OBJECT-TYPE
   SYNTAX   OCTET STRING (SIZE(0..12))
   ACCESS   read-only
   STATUS   mandatory
   DESCRIPTION
      "Represents the YP Serial Number of the ONT.  The YP serial number
       contains the manufacturing dates for the ONT.  For ONT that do not support
       this attribute the value shall be 0.

	For ISAM4.2, attribute is SUPPORTED (merged from FGU4.7.4).


		For GPON - SUPPORTED as of ISAM4.2
		For XG-PON1 - SUPPORTED as did GPON at ISAM4.6.02
		For NG-PON2 - SUPPORTED as GPON at ISAM5.2 " 
   ::= { bponOntEntry 70 }

bponOntSLIDAvailability  OBJECT-TYPE
   SYNTAX   INTEGER
   ACCESS   read-write
   STATUS   mandatory
   DESCRIPTION
      "This attribute defines whether the ONT SLID visibility is enabled or disabled
       while Connected to PON.  This attribute is also used to enable Telnet and HTTP
       interface on the ONT local interface.

       0 = Disabled.
       1 = Enabled SLID ON
       2 = Enabled ALL (SLID, HTTP, Telnet)

       Default = 0 = Disabled

	Modification is permitted.

	For ISAM4.2, attribute is SUPPORTED (merged from FGU4.7.4).

		For GPON - SUPPORTED as of ISAM4.2
		For XG-PON1 - SUPPORTED as did GPON at ISAM4.6.02
		For NG-PON2 - SUPPORTED as GPON at ISAM5.2 " 
   ::= { bponOntEntry 71 }

bponOntOntsideMcastGemPmCollectInd  OBJECT-TYPE
   SYNTAX   INTEGER
   ACCESS   read-write
   STATUS   mandatory
   DESCRIPTION
      " This indicates whether OLT-side Multicast Port Performance Monitors should be collected for this ONT.

        1 = PM collection enabled
        2 = PM collection disabled

       Default = 2 = disabled.

	For ISAM4.2, attribute is SUPPORTED (merged from FGU4.7.4).

		For GPON - SUPPORTED as of ISAM4.2
		For XG-PON1 - SUPPORTED as did GPON at ISAM4.6.02
		For NG-PON2 - SUPPORTED as GPON at ISAM5.2 " 
   ::= { bponOntEntry 72 }


bponOntOntsideMcastGemPmNumPMIntervals  OBJECT-TYPE
   SYNTAX   INTEGER
   ACCESS   read-only
   STATUS   mandatory
   DESCRIPTION
      " Indicates the number of rows currently present
        in the gponMulticastServiceOntsideGemIntervalTable.  This
        is for convenience of the EMS, so that it can
       quickly determine how many rows should be
       uploaded. 

	For ISAM4.2, attribute is SUPPORTED (merged from FGU4.7.4).

		For GPON - SUPPORTED as of ISAM4.2
		For XG-PON1 - SUPPORTED as did GPON at ISAM4.6.02
		For NG-PON2 - SUPPORTED as GPON at ISAM5.2 " 
   ::= { bponOntEntry 73 }

bponOntPoliceMode  OBJECT-TYPE
	SYNTAX 	INTEGER
	ACCESS	read-write
	STATUS	mandatory
	DESCRIPTION 
		" This attribute was first introduced with ISAM4.0.10.

		Used to designate whether OMCI policing parameters
		are sent directly to the ONT (for remote enforcement) or held at OLT (for 
		local enforcement). The policing characteristics regard upstream rate-limiting
		per VLAN).  For ISAM4.0.10, only certain ONTs support this feature (e.g. ETSI MDUs),
		and only for following UNI types: XDSL and Ethernet.

 		 0 = Local at OLT (meaning no OMCI sent to ONT)
  		 1 = Remote at ONT (meaning OMCI is sent to ONT)
   
 		 Default = 0 = Local at OLT

		 Modification is SUPPORTED, but only if no XDSL or Ethernet UNIs
		 have been auto-created for this ONT.

		For GPON - SUPPORTED as of ISAM4.0.10
		For XG-PON1 - SUPPORTED as did GPON at ISAM4.6.02
		For NG-PON2 - SUPPORTED as GPON at ISAM5.2 "  
	::= { bponOntEntry 74 }

bponOntAesMode  OBJECT-TYPE
	SYNTAX 	INTEGER
	ACCESS	read-write
	STATUS	mandatory
	DESCRIPTION 
		" This attribute was first introduced with ISAM4.0.10.

		Used to designate whether AES should be enabled/disabled for all bi-directional
		GEM ports associated with this ONT.  NOTE: this setting excludes the GEM ports 
		associated with dynamic multicast and incidental broadcast.

 		 0 = AES Disabled
  		 1 = AES Enabled
   
 		 Default = 0 = Disabled

		 Modification is SUPPORTED.

		 NOTE: When the type of PON for this ONT is XGPON or NGPON2 (determined from LT card type), then the setting
			of this attribute only applies to downstream traffic associated with bi-directionl GEM ports.
			For XGPON and NGPON2, the setting for upstream traffic is determined from bponOntUpEncryptMode attribute.

			Also, for XGPON and NGPON2 modes, modification is SUPPORTED but only if ONT is Admin Down.

		For GPON - SUPPORTED as of ISAM4..0.10
		For XG-PON1 - SUPPORTED as of ISAM4.6.02
		For NG-PON2 - SUPPORTED as GPON at ISAM5.2 " 

	::= { bponOntEntry 75 }

bponOntVoipCapability  OBJECT-TYPE
	SYNTAX 	INTEGER
	ACCESS	read-write
	STATUS	mandatory
	DESCRIPTION 
		" This attribute was first introduced with ISAM4.0.10.

		Used to designate whether or not this ONT should support VoIP (i.e.whether or not a 
		VoIP UNI or IP Host UNI interface is auto-created in the IFM MIB).  Also, if VoIP is supported,
		used to designate the allowable method of configuration (i.e. legacy or standard style).

		0 = ONT should NOT support VoIP (default).
		1 = ONT should support VoIP (only legacy mode using gponVoipServiceTable)
		2 = ONT should support Voip (only standard mode using gponOntIpHostTable)
		3 = ONT should support VEIP-style Voip. This means association of POTs ports with VEIP interface. 
		      Physical aspects of POTS port managed via this GPON MIB.  But VoIP service aspects managed
		      outside of OMCI (e.g. via TR69) via the VEIP interface associated with POTS port.

		Modification is NOT permitted.

		For ISAM4.2, this attribute continues to be SUPPORTED, but clarified codepoint 1
		to restrict only legacy mode using gponVoipServiceTable.
		For ISAM4.2.02, this attribute continues to be SUPPORTED, but added codepoint 2
		to restrict only standard mode using gponOntIpHostTable.
		For ISAM4.3, this attribute continues to be SUPPORTED, but added codepoint 3
		to restrict only VEIP-style whereby POTS port is associated to VEIP interface. 

		For GPON - SUPPORTED as of ISAM4.0.10
		For XG-PON1 - SUPPORTED as of ISAM4.6.02
		For NG-PON2 - As of ISAM5.4.01, the supported values are 0 and 2. "
	::= { bponOntEntry 76 }



bponOntFecPmCollectInd  OBJECT-TYPE
	SYNTAX 	INTEGER
	ACCESS	read-write
	STATUS	mandatory
	DESCRIPTION 
		" This indicates whether downstream FEC Performance Monitors should be collected for this ONT (at ONT-side).
	
		  1 = PM collection enabled
		  2 = PM collection disabled

		 Default = 2 = disabled

		For ISAM4.2.02, attribute is SUPPORTED 


		For GPON - SUPPORTED as of ISAM4.2.02
		For XG-PON1 - SUPPORTED as of ISAM4.6.02
		For NG-PON2 - SUPPORTED as GPON at ISAM5.2 " 
	::= { bponOntEntry 78 }


bponOntFecPmNumPMIntervals  OBJECT-TYPE
	SYNTAX 	INTEGER
	ACCESS	read-only
	STATUS	mandatory
	DESCRIPTION 
		" Indicates the number of rows currently present
		  in the gponOntFecIntervalTable.  This
		  is for convenience of the EMS, so that it can
		 quickly determine how many rows should be 
		 uploaded.

		As of ISAM4.2.02,  attribute will always be zero, since associated history table is NOT SUPPORTED.

		For GPON - SUPPORTED as of ISAM4.2.02 (attribute will always be 
				zero, since associated history table is NOT SUPPORTED.
		For XG-PON1 - SUPPORTED same as GPON at ISAM4.6.02
		For NG-PON2 - SUPPORTED same as GPON at ISAM5.2 " 
	::= { bponOntEntry 79 }

bponOntLogicalAuthID  OBJECT-TYPE
	SYNTAX 	DisplayString (SIZE(0..24))
	ACCESS	read-write
	STATUS	mandatory
	DESCRIPTION 
	  " This object is used to specify a Logical ID (LOID) for the ONT.

	    It is relevant only when bponPonConfigAuthMethod is set to one of following
	         	2 = CT proprietary logical authentication (LOID) only
		3 = CT proprietary LOID precedence mix authentication
		4 = LoidStd - means 988 standard LOID only 
		5 = LoidPreStd - 988 standard LOID precedence mix

	  Duplicate LOIDs for ONTs on the same PON are not allowed.
	  LOID can only be edited if ONT Admin State is locked.
	  
	    Default = null string.

		For GPON - SUPPORTED as of ISAM4.5 
		For XG-PON1 - SUPPORTED as of ISAM4.6.02
		For NG-PON2 - NOT SUPPORTED as of ISAM5.2, start to support from ISAM5.5. Only MIB is ready in ISAM5.4.01 " 
	::= { bponOntEntry 82 }

bponOntLogicalAuthPassword  OBJECT-TYPE  
	SYNTAX 	DisplayString (SIZE(0..12))
	ACCESS	read-write
	STATUS	mandatory
	DESCRIPTION 
	  " This object is used to specify a password for the ONT. 

	    It is relevant only when bponPonConfigAuthMethod is set to one of following:
	         	2 = CT proprietary logical authentication (LOID) only
		3 = CT proprietary LOID precedence mix authentication
		4 = LoidStd - means 988 standard LOID only 
		5 = LoidPreStd - 988 standard LOID precedence mix

	    If the password is configured to null,
	    the password will NOT be checked during logical authentication.
	    Otherwise, the password must be checked.
	    
	      Default = null string.

		For GPON - SUPPORTED as of ISAM4.5 
		For XG-PON1 - SUPPORTED as of ISAM4.6.02
		For NG-PON2 - NOT SUPPORTED as of ISAM5.2, start to support from ISAM5.5. Only MIB is ready in ISAM5.4.01 " 
	::= { bponOntEntry 83 }

bponOntVlanBridgeMappingMode OBJECT-TYPE
	SYNTAX    INTEGER
    	ACCESS    read-write
    	STATUS    mandatory
    	DESCRIPTION 
     	 " This attribute was introduced in ISAM4.4.
	This attribute is used to configure ONU VLAN bridge mapping mode. 

       		0x05 - 1:MP map-filtering (SUPPORTED as of ISAM4.4).

		0x06 - N:P bridge filtering (SUPPORTED as of ISAM5.1.01). 

      		0x07 - N:MP bridge-map-filtering (SUPPORTED as of ISAM4.4).


       	Default = 0x05 = 1:MP

		For GPON - SUPPORTED as of ISAM4.4 (modes 5 and 7) 
		For GPON - SUPPORTED as of ISAM5.1.0 (modes 5, 6 and 7)   
		For XG-PON1 - SUPPORTED as of ISAM4.6.02 (modes 5 and 7) 
		For NG-PON2 - SUPPORTED same as of ISAM5.2 (modes 5 and 7)  " 
::= { bponOntEntry 84 }


bponOntVlanTranslateMode  OBJECT-TYPE 
        SYNTAX  INTEGER
        ACCESS  read-write 
        STATUS  mandatory 
        DESCRIPTION 
	" This attribute was introduced in ISAM4.4
          	At this time it is used to indicate whether CVLAN translation (excluding configured multicast traffic) should be performed
	remote (in ONT) or local (in OLT).

            0 - CVLAN translation should be performed remote in ONT (SUPPORTED as of ISAM4.4)
            1 - CVLAN translation should be performed local in OLT (SUPPORTED as of ISAM4.4)

            Default = 0 = Remote "
        ::= { bponOntEntry 85 } 

bponOntCtcSpecVersion OBJECT-TYPE
        SYNTAX  INTEGER
        ACCESS  read-only
        STATUS  mandatory
        DESCRIPTION
                " This attribute is China Telecom (CTC) customer specific.
	     Indicates the CTC spec version supported by the ONT.
	     Maps to a GET of CTC proprietary OMCI attribute (i.e. CTC Spec Version of ONU Capability ME).

		  0 = CTC Version 2.0
		  1 - 255 = Other than CTC Version 2.0 (yet reported by ONT)

		  256 = UNKNOWN - (because OLT has not communicated with ONT for OMCI discovery purposes),
			or because ONT does NOT support GET of this attribute.

		  Default = 256 = UNKNOWN

		For GPON - SUPPORTED as of ISAM4.4 
		For XG-PON1 - SUPPORTED as of ISAM4.6.02
		For NG-PON2 - SUPPORTED same as of ISAM5.2 " 
        ::= { bponOntEntry 86  }

bponOntCtcOntType OBJECT-TYPE
        SYNTAX  INTEGER
        ACCESS  read-only
        STATUS  mandatory
        DESCRIPTION
                " This attribute is China Telecom (CTC) customer specific.
	     Indicates the CTC ONT Type.
	     Maps to a GET of CTC proprietary OMCI attribute (i.e. ONU Type of ONU Capability ME).

         		0 = SFU
         		1 = HGU
         		2 = SBU
         		3 = CBU
         		4 = MDU
        		5 = MTU
		6 - 255 = Other CTC Type (yet reported by ONT)
 
		256 = UNKNOWN - (because OLT has not communicated  with ONT for OMCI discovery purposes),
			or because ONT does NOT support GET of this attribute.

		Default = 256 = UNKNOWN

		For GPON - SUPPORTED as of ISAM4.4 
		For XG-PON1 - SUPPORTED as of ISAM4.6.02
		For NG-PON2 - SUPPORTED same as of ISAM5.2 " 
        ::= { bponOntEntry 87  }

bponOntCtcTxPowerControl OBJECT-TYPE
        SYNTAX  INTEGER
        ACCESS  read-only
        STATUS  mandatory
        DESCRIPTION
                "  This attribute is China Telecom (CTC) customer specific.
	     Indicates whether power supply of ONT transmitter can be independently controlled.
	     Maps to a GET of CTC proprietary OMCI attribute (i.e. ONU TX Power Supply Control of ONU Capability ME).

        		0 = Not Supported
         		1 = Only supporting Tx control
         		2 = Tx and Rx power supplies can be controlled independently 
		3 - 255 = Other (yet reported by ONT)
 
  		256 = UNKNOWN - (because OLT has not communicated  with ONT for OMCI discovery purposes),
			or because ONT does NOT support GET of this attribute.

		Default = 256 = UNKNOWN


		For GPON - SUPPORTED as of ISAM4.4 
		For XG-PON1 - SUPPORTED as of ISAM4.6.02
		For NG-PON2 - SUPPORTED same as of ISAM5.2 " 
        ::= { bponOntEntry 88  }

bponOntIPHCCapability  OBJECT-TYPE
        SYNTAX  INTEGER
        ACCESS  read-write
        STATUS  mandatory
        DESCRIPTION
                " This attribute was first introduced with ISAM4.4.

                Used to designate whether or not this ONT should support IPHC (i.e.whether or not a
                IP Host UNI interface is auto-created in the IFM MIB).  

                0 = ONT should NOT support IPHC (default).
                1 = ONT should enable support of IPHC

                Modification is NOT permitted.

	As of ISAM4.4, this attribute must be set to 'enable IPHC' in order to configue SNMP agent service using gponIpHostTable.
	As of ISAM4.6.01, this attribute must be set to 'enable IPHC' in order to configue L3 CES pseudowire service using gponIpHostTable.


		For GPON - SUPPORTED as of ISAM4.4 (see above for restrictions)
		For XG-PON1 - SUPPORTED as of ISAM4.6.02
		For NG-PON2 - As of ISAM5.2, only SUPPORTED value is 0. " 

        ::= { bponOntEntry 89 }


bponOntOntsidePonAggEtherPmCollectInd  OBJECT-TYPE
	SYNTAX 	INTEGER
	ACCESS	read-write
	STATUS	mandatory
	DESCRIPTION 
		" This indicates whether ONT-side PON aggregate
		  Ethernet traffic Performance Monitors should be collected for this ONT.
	
		  1 = PM collection enabled
		  2 = PM collection disabled

		 Default = 2 = disabled.


		For GPON - SUPPORTED as of ISAM4.5 
		For XG-PON1 - SUPPORTED as of ISAM4.6.02
		For NG-PON2 - SUPPORTED same as of ISAM5.2 " 
	::= { bponOntEntry 90 }

bponOntOntsidePonAggEtherPmNumPMIntervals  OBJECT-TYPE
	SYNTAX 	INTEGER
	ACCESS	read-only
	STATUS	mandatory
	DESCRIPTION 
		" Indicates the number of rows currently present
		  in the gponOntOntsidePonAggEtherIntervalTable.  This
		  is for convenience of the EMS, so that it can
		  quickly determine how many rows should be 
		  uploaded.

		For GPON - SUPPORTED as of ISAM4.5 
		For XG-PON1 - SUPPORTED as of ISAM4.6.02
		For NG-PON2 - SUPPORTED same as of ISAM5.2 " 
	::= { bponOntEntry 91 }

bponOntDscpToPriorityAlignOLTMode  OBJECT-TYPE 
        SYNTAX  INTEGER
        ACCESS  read-write 
        STATUS  mandatory 
        DESCRIPTION 
	" Used to indicate whether DSCP-to-Priority alignment behavior should be performed at OLT or NOT.
            	
	0 = FALSE - meaning DSCP-to-Priority alignment should NOT be performed at OLT (already SUPPORTED since R4.0.10)
	1 = TRUE - meaning DSCP-to-Priority alignment should be performed at OLT (SUPPORTED as of ISAM4.6)
            
	Default = 0 = False

		For GPON - SUPPORTED as of ISAM4.5 
		For XG-PON1 - SUPPORTED as of ISAM4.6.02
		For NG-PON2 - SUPPORTED same as of ISAM5.2 " 
        ::= { bponOntEntry 92 }


bponOntSnBundleControl  OBJECT-TYPE
	SYNTAX 	INTEGER
	ACCESS	read-write
	STATUS	mandatory
	DESCRIPTION
		" Used to enable/disable Serial Number (SN) bundling behavior associated with SLID/LOID.
		0 = UnBundle: No bundle behavior for SN with LOID/SLID.  Same as behavior prior to bundle feature introduction.
		1 = Bundle: Manual bundling of SN with LOID/SLID.
		2 = AutoBundle: Automatically bundle the SN with LOID/SLID when a NEW SN is learned (after a timer associated 
				with SnAutoBundleTimer attribute)
		
		Default = 0 = Unbundle
		
		For GPON - SUPPORTED as of ISAM4.6 
		For XG-PON1 - SUPPORTED as of ISAM4.6.02
		For NG-PON2 - SUPPORTED same as of ISAM5.2 " 
        ::= { bponOntEntry 93 } 


bponOntSnBundleStatus OBJECT-TYPE
	SYNTAX 	INTEGER
	ACCESS	read-only
	STATUS	mandatory
	DESCRIPTION
		" Used to retrieve SN with SLID/LOID bundling status
		0 = Idle: the SN currently is NOT bundled.
		1 = Bundling: only applicable for auto-bundle mode.
		      Applies to situations where auto-bundle timer is being restored (e.g. due to system reboot).
		2 = Bundled: the SN currently is bundled.

		Default = 0 = Idle
		
		For GPON - SUPPORTED as of ISAM4.6 
		For XG-PON1 - SUPPORTED as of ISAM4.6.02
		For NG-PON2 - SUPPORTED same as of ISAM5.2 " 
        ::= { bponOntEntry 94 } 


bponOntUpEncryptMode	OBJECT-TYPE
	SYNTAX 	INTEGER
	ACCESS	read-write
	STATUS	mandatory
	DESCRIPTION 
		" Used to designate whether AES should be enabled/disabled for all upstream traffic on
		GEM ports associated with this ONT. 

 		 0 = AES Disabled
  		 1 = AES Enabled
   
 		 Default = 0 = Disabled

		Modification is SUPPORTED, but only if ONT is Admin Down.

		Introduced in ISAM4.6 MIB
		Due to recent PLM decisions, attribute is NOT SUPPORTED and there are no plans for future support.

		For GPON - NOT SUPPORTED as of ISAM4.6 
		For XG-PON1 - NOT SUPPORTED as of ISAM4.6.02
		For NG-PON2 - NOT SUPPORTED same as of ISAM5.2 " 
	::= { bponOntEntry 95 }

bponOntTodControl		OBJECT-TYPE
	SYNTAX 	INTEGER
	ACCESS	read-write
	STATUS	mandatory
	DESCRIPTION 
		" Used to designate whether standard OMCI mechanisms should used to synchronize ONT Time of Day
		   with OLT Time of Day.

 		 0 = No (do NOT use OMCI mechanisms)
  		 1 = Yes (do use OMCI mechanisms)
   
 		 Default = 0 = No


		Modification is SUPPORTED, but only if ONT is Admin Down.

		Introduced in ISAM4.6 MIB
		Due to recent PLM decisions, attribute is NOT SUPPORTED and there are no plans for future support.


		For GPON - NOT SUPPORTED as of ISAM4.6 
		For XG-PON1 - NOT SUPPORTED as of ISAM4.6.02
		For NG-PON2 - NOT SUPPORTED same as of ISAM5.2 " 
	::= { bponOntEntry 96 }



bponOntOltsideUpFecPmCollectInd  OBJECT-TYPE
	SYNTAX 	INTEGER
	ACCESS	read-write
	STATUS	mandatory
	DESCRIPTION 
		" This indicates whether upstream FEC Performance Monitors should be collected for this ONT (at OLT-side).
	
		  1 = PM collection enabled
		  2 = PM collection disabled

		 Default = 2 = disabled

		Introduced in ISAM4.6 MIB

		For GPON - NOT SUPPORTED as of ISAM4.6 
		For XG-PON1 - SUPPORTED as of ISAM4.6.02
		For NG-PON2 - SUPPORTED same as of ISAM5.2 " 
	::= { bponOntEntry 98 }

bponOntOltsideUpFecPmNumPMIntervals  OBJECT-TYPE
	SYNTAX 	INTEGER
	ACCESS	read-only
	STATUS	mandatory
	DESCRIPTION 
		" Indicates the number of rows currently present
		  in the gponOntOltsideFecIntervalTable.  This
		  is for convenience of the EMS, so that it can
		 quickly determine how many rows should be 
		 uploaded.

		Introduced in ISAM4.6 MIB


		For GPON - NOT SUPPORTED as of ISAM4.6 
		For XG-PON1 - NOT SUPPORTED as of ISAM4.6.02 attribute will always be zero, 
			since associated history table is NOT SUPPORTED.
		For NG-PON2 - NOT SUPPORTED as of ISAM5.2 attribute will always be zero, 
			since associated history table is NOT SUPPORTED." 
	::= { bponOntEntry 99 }

bponOntOltsidePhyPmCollectInd  OBJECT-TYPE
	SYNTAX 	INTEGER
	ACCESS	read-write
	STATUS	mandatory
	DESCRIPTION 
		" This indicates whether Physical Layer Performance Monitors should be collected for this ONT (at OLT-side).
	
		  1 = PM collection enabled
		  2 = PM collection disabled

		 Default = 2 = disabled

		Introduced in ISAM4.6 MIB

		For GPON - NOT SUPPORTED as of ISAM4.6 
		For XG-PON1 - SUPPORTED as of ISAM4.6.02
		For NG-PON2 - SUPPORTED same as of ISAM5.2 " 
	::= { bponOntEntry 100 }


bponOntOltsidePhyPmNumPMIntervals  OBJECT-TYPE
	SYNTAX 	INTEGER
	ACCESS	read-only
	STATUS	mandatory
	DESCRIPTION 
		" Indicates the number of rows currently present
		  in the gponOntOltsidePhyIntervalTable.  This
		  is for convenience of the EMS, so that it can
		 quickly determine how many rows should be 
		 uploaded.

		Introduced in ISAM4.6 MIB


		For GPON - NOT SUPPORTED as of ISAM4.6 
		For XG-PON1 - NOT SUPPORTED as of ISAM4.6.02 attribute will always be zero, 
			since associated history table is NOT SUPPORTED.
		For NG-PON2 - NOT SUPPORTED as of ISAM5.2 attribute will always be zero, 
			since associated history table is NOT SUPPORTED." 
	::= { bponOntEntry 101 }

bponOntOntsideXgTcPmCollectInd  OBJECT-TYPE
	SYNTAX 	INTEGER
	ACCESS	read-write
	STATUS	mandatory
	DESCRIPTION 
		" This indicates whether XGPON Transmission Convergence Performance Monitors should be collected for this ONT (at ONT-side).
	
		  1 = PM collection enabled
		  2 = PM collection disabled

		 Default = 2 = disabled

		Introduced in ISAM4.6 MIB

		For GPON - NOT SUPPORTED as of ISAM4.6 
		For XG-PON1 - SUPPORTED as of ISAM4.6.02
		For NG-PON2 - SUPPORTED same as of ISAM5.2 " 
	::= { bponOntEntry 102 }


bponOntOntsideXgTcPmNumPMIntervals  OBJECT-TYPE
	SYNTAX 	INTEGER
	ACCESS	read-only
	STATUS	mandatory
	DESCRIPTION 
		" Indicates the number of rows currently present
		  in the gponOntOntsideXgTcIntervalTable.  This
		  is for convenience of the EMS, so that it can
		 quickly determine how many rows should be 
		 uploaded.

		Introduced in ISAM4.6 MIB

		For GPON - NOT SUPPORTED as of ISAM4.6 
		For XG-PON1 - SUPPORTED as of ISAM4.6.02 
		For NG-PON2 - SUPPORTED as of ISAM5.2 " 
	::= { bponOntEntry 103 }

bponOntOltsideXgTcPmCollectInd  OBJECT-TYPE
	SYNTAX 	INTEGER
	ACCESS	read-write
	STATUS	mandatory
	DESCRIPTION 
		" This indicates whether XGPON Transmission Convergence Performance 
		  Monitors should be collected for this ONT (at OLT-side).
	
		  1 = PM collection enabled
		  2 = PM collection disabled

		 Default = 2 = disabled

		Introduced in ISAM4.6 MIB

		For GPON - NOT SUPPORTED as of ISAM4.6 
		For XG-PON1 - SUPPORTED as of ISAM4.6.02
		For NG-PON2 - SUPPORTED same as of ISAM5.2 " 
	::= { bponOntEntry 104 }


bponOntOltsideXgTcPmNumPMIntervals  OBJECT-TYPE
	SYNTAX 	INTEGER
	ACCESS	read-only
	STATUS	mandatory
	DESCRIPTION 
		" Indicates the number of rows currently present
		  in the gponOntOltsideXgTcIntervalTable.  This
		  is for convenience of the EMS, so that it can
		 quickly determine how many rows should be 
		 uploaded.

		Introduced in ISAM4.6 MIB

		For GPON - NOT SUPPORTED as of ISAM4.6 
		For XG-PON1 - SUPPORTED as of ISAM4.6.02 
		For NG-PON2 - SUPPORTED as of ISAM5.2 " 
	::= { bponOntEntry 105 }

bponOntOltsidePonUtilPmNumPMIntervals  OBJECT-TYPE
	SYNTAX 	INTEGER
	ACCESS	read-only
	STATUS	mandatory
	DESCRIPTION 
		" Indicates the number of rows currently present
		  in the following tables (for this ONT):

		- gponOltSideOntUtilPmCurrentIntervalTable
		- gponOltSideOntUtilPmIntervalTable
		- gponOltSideOntUtilBulkPmCurrentIntervalTable
	
		  This is for convenience of the EMS, so that it can
		  quickly determine how many rows should be 
		  uploaded.

		For GPON - SUPPORTED as of ISAM5.2 
		For XG-PON1 - NOT SUPPORTED as of ISAM4.6.02
		For NG-PON2 - SUPPORTED same as of ISAM5.2.01 " 
	::= { bponOntEntry 106 }


bponOntNg2PreferredChanPair  OBJECT-TYPE
	SYNTAX 	InterfaceIndexOrZero
	ACCESS	read-write
	STATUS	mandatory
	DESCRIPTION 
		" This attribute is used to specify the ifIndex
		  of the preferred channel pair (for this ONT).

		  This attribute is relevant only for NG-PON

		Introduced in ISAM5.2 MIB

		For GPON - NOT SUPPORTED as of ISAM5.2 (default = 0) 
		For XG-PON1 - NOT SUPPORTED as of ISAM4.6.02 (default = 0)
		For NG-PON2 - SUPPORTED as of ISAM5.2 (no default - mandatory) " 
	::= { bponOntEntry 108 }

bponOntNg2ActualChanPair  OBJECT-TYPE
	SYNTAX 	InterfaceIndexOrZero
	ACCESS	read-only
	STATUS	mandatory
	DESCRIPTION 
		" This attribute contains the ifIndex
		  of the actual channel pair (for this ONT).

		  This attribute is relevant only for NG-PON

		Introduced in ISAM5.2 MIB

		For GPON - NOT SUPPORTED as of ISAM5.2 (default = 0) 
		For XG-PON1 - NOT SUPPORTED as of ISAM4.6.02 (default = 0)
		For NG-PON2 - SUPPORTED as of ISAM5.2 (default = 0) " 
	::= { bponOntEntry 109 }


bponOntPlannedCfgFile1  OBJECT-TYPE
	SYNTAX 	DisplayString
	ACCESS	read-write
	STATUS	mandatory
	DESCRIPTION 
		"Indicates the planned CfgFile1 version.  SET of this attribute will cause OLT to attempt 
		 to ensure this version become the active one on ONT.

		 Special value DISABLED means OLT will ignore this attribute.

		 Special value AUTO means OLT will use the respective version defined in gponOntSwVerCtlTable

		 Default = DISABLED

 		 Introduced in ISAM5.2 MIB

		For GPON - SUPPORTED as of ISAM5.2 
		For XG-PON1 - NOT SUPPORTED as of ISAM4.6.02 
		For NG-PON2 - NOT SUPPORTED as of ISAM5.2 "
	::= { bponOntEntry 110 }


bponOntDownloadCfgFile1  OBJECT-TYPE
	SYNTAX 	DisplayString
	ACCESS	read-write
	STATUS	mandatory
	DESCRIPTION 
		"Indicates the CfgFile1 file version to be downloaded. SET of this attribute causes the OLT 
		 to ensure that this file version is present in ONT's passive or active image.  If not already present
		 in either passive or active, OLT will download this image to passive - and
		 go no further (i.e. it won't auto-activate this version).  This attribute is used
		 to 'download only' a file. Modification is permitted even after ONT activation.
	  
		 Special value DISABLED means OLT will ignore this attribute.

		 Special value AUTO means OLT will use the respective version defined in gponOntSwVerCtlTable

		 Default = DISABLED

 		 Introduced in ISAM5.2 MIB

		For GPON - SUPPORTED as of ISAM5.2 
		For XG-PON1 - NOT SUPPORTED as of ISAM4.6.02 
		For NG-PON2 - NOT SUPPORTED as of ISAM5.2 "
	::= { bponOntEntry 111 }

bponOntPlannedCfgFile2  OBJECT-TYPE
	SYNTAX 	DisplayString
	ACCESS	read-write
	STATUS	mandatory
	DESCRIPTION 
		"Indicates the planned CfgFile2 version.  SET of this attribute will cause OLT to attempt 
		 to ensure this version become the active one on ONT.

		 Special value DISABLED means OLT will ignore this attribute.

		 Special value AUTO means OLT will use the respective version defined in gponOntSwVerCtlTable

		 Default = DISABLED

 		 Introduced in ISAM5.2 MIB

		For GPON - SUPPORTED as of ISAM5.2 
		For XG-PON1 - NOT SUPPORTED as of ISAM4.6.02 
		For NG-PON2 - NOT SUPPORTED as of ISAM5.2 "
	::= { bponOntEntry 112 }


bponOntDownloadCfgFile2  OBJECT-TYPE
	SYNTAX 	DisplayString
	ACCESS	read-write
	STATUS	mandatory
	DESCRIPTION 
		"Indicates the CfgFile2 version to be downloaded. SET of this attribute causes the OLT 
		 to ensure that this file version is present in ONT's passive or active image.  If not already present
		 in either passive or active, OLT will download this image to passive - and
		 go no further (i.e. it won't auto-activate this version).  This attribute is used
		 to 'download only' a file. Modification is permitted even after ONT activation.
	  
		 Special value DISABLED means OLT will ignore this attribute.

		 Special value AUTO means OLT will use the respective version defined in gponOntSwVerCtlTable

		 Default = DISABLED

 		 Introduced in ISAM5.2 MIB

		For GPON - SUPPORTED as of ISAM5.2 
		For XG-PON1 - NOT SUPPORTED as of ISAM4.6.02 
		For NG-PON2 - NOT SUPPORTED as of ISAM5.2 "
	::= { bponOntEntry 113 }


bponOntCfgFile1Active  OBJECT-TYPE
	SYNTAX 	DisplayString
	ACCESS	read-only
	STATUS	mandatory
	DESCRIPTION 
		"Indicates the active version of CfgFile1 in ONT. 
		 If file not used or supported, this attribute remains null string.

		 Default = null string

 		 Introduced in ISAM5.2 MIB

		For GPON - SUPPORTED as of ISAM5.2 
		For XG-PON1 - NOT SUPPORTED as of ISAM4.6.02 
		For NG-PON2 - NOT SUPPORTED as of ISAM5.2 "
	::= { bponOntEntry 114 }


bponOntCfgFile1Passive  OBJECT-TYPE
	SYNTAX 	DisplayString
	ACCESS	read-only
	STATUS	mandatory
	DESCRIPTION 
		"Indicates the passive version of CfgFile1 in ONT. 
		 If file not used or supported, this attribute remains null string.

		 Default = null string

 		 Introduced in ISAM5.2 MIB

		For GPON - SUPPORTED as of ISAM5.2 
		For XG-PON1 - NOT SUPPORTED as of ISAM4.6.02 
		For NG-PON2 - NOT SUPPORTED as of ISAM5.2 "
	::= { bponOntEntry 115 }

bponOntCfgFile2Active  OBJECT-TYPE
	SYNTAX 	DisplayString
	ACCESS	read-only
	STATUS	mandatory
	DESCRIPTION 
		"Indicates the active version of CfgFile2 in ONT. 
		 If file not used or supported, this attribute remains null string.

		 Default = null string

 		 Introduced in ISAM5.2 MIB

		For GPON - SUPPORTED as of ISAM5.2 
		For XG-PON1 - NOT SUPPORTED as of ISAM4.6.02 
		For NG-PON2 - NOT SUPPORTED as of ISAM5.2 "
	::= { bponOntEntry 116 }


bponOntCfgFile2Passive  OBJECT-TYPE
	SYNTAX 	DisplayString
	ACCESS	read-only
	STATUS	mandatory
	DESCRIPTION 
		"Indicates the passive version of CfgFile2 in ONT. 
		 If file not used or supported, this attribute remains null string.

		 Default = null string

 		 Introduced in ISAM5.2 MIB

		For GPON - SUPPORTED as of ISAM5.2 
		For XG-PON1 - NOT SUPPORTED as of ISAM4.6.02 
		For NG-PON2 - NOT SUPPORTED as of ISAM5.2 "
	::= { bponOntEntry 117 }


bponOntTcPoliceMode OBJECT-TYPE
         SYNTAX    INTEGER
         ACCESS    read-write
         STATUS    mandatory
         DESCRIPTION 
                   " Used to designate whether OMCI policing parameters
                   are sent directly to the ONT (for remote enforcement) or held at OLT (for 
                   local enforcement). The policing characteristics regard upstream rate-limiting
                   per gemport). 
 
                   0 = Local at OLT (meaning no OMCI sent to ONT)
                   1 = Remote at ONT (meaning OMCI is sent to ONT)
   
                    Default = 0 = Local at OLT
 
                   Modification is SUPPORTED, but only if no XDSL or Ethernet UNIs
                   have been auto-created for this ONT and admin-status of this ONT is down.

  		For GPON - SUPPORTED as of ISAM5.2.01 
		For XG-PON1 - NOT SUPPORTED as of ISAM4.6.02 
		For NG-PON2 - SUPPORTED as of ISAM5.2.01 "
         ::= { bponOntEntry 118 }

bponOntRateLimitUpstreamDhcp OBJECT-TYPE
        SYNTAX  INTEGER
        ACCESS  read-write
        STATUS  mandatory
        DESCRIPTION
                " Indicates the upstream rate-limit of DHCP packet per UNI of this ONT.

                  0 = rate limiting of DHCP disabled
                  1-16 = Packets per Second limit

                 Default = 10 .
             For GPON - SUPPORTED as of ISAM5.5
             For XG-PON1 - NOT SUPPORTED as of ISAM5.5
             For NG-PON2 - SUPPORTED as of ISAM5.5

             Modification permitted.   "
        DEFVAL  { 10 }
        ::= { bponOntEntry 119 }

bponOntRateLimitUpstreamArp OBJECT-TYPE
        SYNTAX  INTEGER
        ACCESS  read-write
        STATUS  mandatory
        DESCRIPTION
                " Indicates the upstream rate-limit of ARP packet per UNI of this ONT.

                  0 = rate limiting of ARP disabled
                  1-16 = Packets per Second limit

                 Default = 10 .

                For GPON - SUPPORTED as of ISAM5.5
                For XG-PON1 - NOT SUPPORTED as of ISAM5.5
                For NG-PON2 - SUPPORTED as of ISAM5.5

                 Modification permitted.   "
        DEFVAL  { 10 }
        ::= { bponOntEntry 120 }

bponOntFlushMACMode OBJECT-TYPE 
        SYNTAX INTEGER 
        ACCESS read-write 
        STATUS mandatory 
        DESCRIPTION 
            "Indicates whether the MAC address could be automatically flushed 
             when a specific UNI goes down. 

            0 = the MAC will not be flushed when UNIs go down 
            1 = the MAC will be flushed when UNIs go down 

            Default = 0 

            Introduced in ISAM5.5 MIB, with targeted implementation in ISAM5.5.01 
        For GPON - SUPPORTED as of ISAM5.5.01 
        For XG-PON1 - not SUPPORTED as of ISAM5.5.01 
        For NG-PON2 - SUPPORTED as of ISAM5.5.01" 

        DEFVAL  { 0 }
        ::= { bponOntEntry 121 }

bponOntPlannedRateUp  OBJECT-TYPE
	SYNTAX 	PlannedRateUp
	ACCESS	read-write
	STATUS	mandatory
	DESCRIPTION 
	" This object represents the ONT upstream rate as planned by the operator.
	
        0 = from channel pair (default)
        1 = 2.5 (in GBits/sec)
        2 = 10 (in GBits/sec)

	The default '0' value means that the planned ONT upstream rate is
	- '2.5' when channel speed is set to '10 down/2.5 up'
	- '10' when channel speed is set to '10 down/10 up'
	When channel speed is '10 down/dual-rate up', value '0' is not allowed.

	Applicable only for XGS-PON "
	::= { bponOntEntry 122 }


bponOntActualRateUp  OBJECT-TYPE
SYNTAX 	ActualRateUp
		ACCESS	read-only
		STATUS	mandatory
		DESCRIPTION 
			"This object represents the actual ONT upstream rate as detected during ONT activation.

             Supported values (see also ActualRateUp) :
   			  unknown              (0) : the ONT is not yet activated (default)
   			  twoDotFiveGbps       (1) : the actual upstream rate of the ONT is 2.5Gpbs, applicable for NG-PON2/XG-PON ONTs
   			  tenGbps              (2) : the actual upstream rate of the ONT is 10Gpbs, applicable for NG-PON2/XGS-PON ONTs
   			  oneDotTwentyFiveGbps (3) : the actual upstream rate of the ONT is 1.25Gpbs, applicable for GPON ONTs

			SUPPORTED as of ISAM5.5.01."
		::= { bponOntEntry 123 }

	
-- *********************************************
--
-- BPON ONT PLANNED CARD TABLE
--
-- This is a new table beginning with FGU2.5. For initial 2.6, rows
-- are statically created by OLT - based on ONT Type (i.e. number and types
-- of cards are known in advance by OLT based on Planned ONT Type). 
--
-- For FGU4.0, this table is being re-used.  Comments are 
-- made regarding whether attribute is relevant to BPON,
-- GPON or both, etc.  NOTE: For GPON, these rows are not
-- automatically created by the OLT - instead they are 
-- created as a result of operator provisioning action.
--
-- For ISAM4.0.10, this table is being re-used. 
-- Noted which attributes are relevant for ISAM4.0.10.
-- 
-- *********************************************

bponOntPlanCardTable  OBJECT-TYPE
	SYNTAX SEQUENCE OF BponOntPlanCardEntry
	ACCESS	not-accessible
	STATUS	mandatory
	::= { bponOntGroup 2 }

bponOntPlanCardEntry  OBJECT-TYPE
	SYNTAX 	BponOntPlanCardEntry
	ACCESS	not-accessible
	STATUS	mandatory
	INDEX	{ bponOntPlanCardOntIndex,
		  bponOntPlanCardSpIndex }
	::= { bponOntPlanCardTable 1 }

BponOntPlanCardEntry ::= SEQUENCE {
	bponOntPlanCardOntIndex				IfIndex,
	bponOntPlanCardSpIndex				SpIndex,
	bponOntPlanCardRowStatus			RowStatus,
	bponOntPlanCardType			INTEGER,
	bponOntPlanCardNumPorts			INTEGER,
	bponOntPlanCardAdminState			AdminState,
	bponOntPlanCardBridgeOrRouter			INTEGER,
	bponOntPlanCardCardConfig			INTEGER,
	bponOntPlanCardSelfTstCmd			INTEGER,
	bponOntPlanCardNumNonPotsPorts			INTEGER,
	bponOntPlanCardNumPotsPorts			INTEGER,
	bponOntPlanCardConnectNodeType			INTEGER,
	bponOntPlanCardTransparentMode			INTEGER,
        bponOntPlanCardNoMulticastControl		INTEGER
}

bponOntPlanCardOntIndex  OBJECT-TYPE
	SYNTAX 	IfIndex
	ACCESS	read-only
	STATUS	mandatory
	DESCRIPTION 
		"Each row is indexed by the ifIndex of the ONT.

		Applicable for both BPON and GPON.

		For GPON - SUPPORTED as of ISAM4.0.10 
		For XG-PON1 - SUPPORTED as of ISAM4.6.02
		For NG-PON2 - SUPPORTED as of ISAM5.2 " 
	::= { bponOntPlanCardEntry 1 }

bponOntPlanCardSpIndex  OBJECT-TYPE
	SYNTAX 	SpIndex
	ACCESS	read-only
	STATUS	mandatory
	DESCRIPTION 
		"Each row is also indexed by a number that
		 contains the slot number within the ONT. 

		Applicable for both BPON and GPON.

		For GPON - SUPPORTED as of ISAM4.0.10 
		For XG-PON1 - SUPPORTED as of ISAM4.6.02
		For NG-PON2 - SUPPORTED as of ISAM5.2 "
	::= { bponOntPlanCardEntry 2 }


bponOntPlanCardRowStatus  OBJECT-TYPE
	SYNTAX 	RowStatus
	ACCESS	read-write
	STATUS	mandatory
	DESCRIPTION 
		" Applicable for both BPON and GPON.
		
		 Prior to FGU4.0 --> All rows initially created 'notInService'. 
		 The numberrows created is based on ONT Type.
		 Manager sets to 'active' when card is planned,
		 and to 'notInService' when card is un-planned. 

		 Since FGU4.0 --> All rows instantiated using 'create-and-go' to
		 provision a card. Set to 'destroy' to delete
		 a card.

		For GPON - SUPPORTED as of ISAM4.0.10 
		For XG-PON1 - SUPPORTED as of ISAM4.6.02
		For NG-PON2 - SUPPORTED as of ISAM5.2 "
	::= { bponOntPlanCardEntry 3 }



bponOntPlanCardType  OBJECT-TYPE
	SYNTAX 	INTEGER
	ACCESS	read-write
	STATUS	mandatory
	DESCRIPTION 
		"Represents the planned type of Linecard 
		 in the Holder, per Table 9.1.5-1 of 984.4.  
		 Values supported are as follows:

		 0 = Unplanned (only prior to FGU4.0)
		 16 = Configurable DS1/E1(starting again with FGU4.3)
		 24 = Ethernet ( Old value : 10/100 Base-T, Prior to ISAM5.2) (prior to and since FGU4.0)
		 32 = POTS (prior to and since FGU4.0)
		 35 = xDSL(VDSL2) only (since FGU4.5.5)
		 38 = Video (prior to FGU4.0, and since FGU4.1)
		 41 = xDSL(VDSL2)/POTS combo (starting with FGU4.4)
		 42 = VDSL/POTS combo  (NOT SUPPORTED as of FGU4.5.5)
		 46 = MoCA (since FGU4.2).  SUPPORTED starting with ISAM5.0
		 48 = Virtual Ethernet Interface Point (SUPPORTED starting with ISAM4.2.02)
		 60 = Ethernet/POTS combo (since FGU4.4)
          		192 = HPNA (since FGU4.7.4).  SUPPORTED starting with ISAM4.4.

		Applicable for both BPON and GPON.

		Prior to FGU4.0--> this is automatically filled in
		by OLT - based on ONT type.

		Since FGU4.0--> this is set by manager.

		For ISAM4.0.10 - stays the same as latest FGU4.x, except only
		following types supported: 16, 24, 32, 35, 38, 41 and 60

		For ISAM4.2, supported types stay same as ISAM4.0.10.
		Added type 48 (VEIP) to ISAM4.2 MIB, but type is only SUPPORTED beginning with ISAM4.2.02.

		For ISAM4.4, added SUPPORT for type 192 (HPNA) 

		For ISAM5.0, added SUPPORT for type 46 (MoCA)

		For GPON - SUPPORTED as of ISAM4.0.10 
		For XG-PON1 - SUPPORTED as GPON as of ISAM4.6.02 (no MoCA, no 10 Gig Ethernet)
		For NG-PON2 - SUPPORTED as of ISAM5.4.01 (but ONLY for Type 24 = 10/100 Ethernet, and Type 32 = POTS) "
	::= { bponOntPlanCardEntry 4 }


bponOntPlanCardNumPorts  OBJECT-TYPE
	SYNTAX 	INTEGER
	ACCESS	read-write
	STATUS	mandatory
	DESCRIPTION 
		" This represents the number of ports that
 		operator plans/expects on the ONT card.
 		Range: 1 to 15.
		
		For BPON, this is automatically filled in
		by OLT based on ONT Type.

		 Default = 4 

		Applicable for BPON only.

		For FGU4.0 --> Not Supported

		For GPON - NOT SUPPORTED as of ISAM4.0.10 
		For XG-PON1 - NOT SUPPORTED as of ISAM4.6.02
		For NG-PON2 - NOT SUPPORTED as of ISAM5.2 "
	::= { bponOntPlanCardEntry 5 }

bponOntPlanCardAdminState  OBJECT-TYPE
	SYNTAX 	AdminState
	ACCESS	read-write
	STATUS	mandatory
	DESCRIPTION 
		"Used to unlock and lock the functions performed
		  by the Subscriber Line Card.  When set to 'lock',
 		  all user traffic to and from this SLC is blocked and
		  alarms for the SLC and associated entities are no
		  longer generated.

		  Applicable for both BPON and GPON.
		  Default = 0 = unlocked

		For GPON - SUPPORTED as of ISAM4.0.10 
		For XG-PON1 - SUPPORTED as of ISAM4.6.02
		For NG-PON2 - SUPPORTED as of ISAM5.2 "
	::= { bponOntPlanCardEntry 6 }


bponOntPlanCardBridgeOrRouter  OBJECT-TYPE
	SYNTAX 	INTEGER
	ACCESS	read-write
	STATUS	mandatory
	DESCRIPTION 
		" For Ethernet cards, indicates whether Ethernet interface
		  is bridged or derived from an IP router function.
		 Meanings are as follows:

		 0 = Bridged
		 1 = IP Router
		 2 = Both Bridged and IP Router

		For FGU2.6, only 0 = Bridged is supported for Ethernet card.

		For all other cards, value = 255 = not relevant.

		Applicable only for BPON.
		For FGU4.0-> Not Supported.

		For GPON - NOT SUPPORTED as of ISAM4.0.10 
		For XG-PON1 - NOT SUPPORTED as of ISAM4.6.02
		For NG-PON2 - NOT SUPPORTED as of ISAM5.2 "
	::= { bponOntPlanCardEntry 7 }

bponOntPlanCardCardConfig  OBJECT-TYPE
	SYNTAX 	INTEGER
	ACCESS	read-write
	STATUS	mandatory
	DESCRIPTION 
		"For configurable cards (e.g. DS1/E1 card for FGU4.3), 
		  this attribute is used to select the appropriate 
		  configuration. 
		  Meanings are as follows for DS1/E1 card (i.e. Type 16):

		 0 = DS1
		 1 = E1		 

		For all other cards, value = 255 = not relevant.
		For GPON - SUPPORTED as of ISAM4.0.10 
		For XG-PON1 - SUPPORTED as of ISAM4.6.02
		For NG-PON2 - SUPPORTED as of ISAM5.2 "
	::= { bponOntPlanCardEntry 8 }

bponOntPlanCardSelfTstCmd  OBJECT-TYPE
	SYNTAX 	INTEGER 
	ACCESS	read-write
	STATUS	mandatory
	DESCRIPTION 
		"Manager is only permitted to SET this attribute
		 to 1, indicating desire to execute linecard self-test.
		 Thereafter, manager issues SNMP GET to determine
		 status/result of the self-test. Agent changes
		 attribute value accordingly as follows:
		 0 - this is the initial default value, meaning no
		      self-test has been executed on this card 
		      since ONT first initialized.
		 1 - Only value settable by manager (to initiate test)
		 2 - meaning self-test is in progress.
		 3 - meaning self-test failed because ONT failed
		       to respond within reasonable time period.
		 4 - meaning self-test failed because ONT
		       indicated it could not complete the test.
		 5 - meaning self-test failed because ONT
		       indicated failure.
		 6 - meaning self-test passed because ONT
		       indicated it passed.
		 7 - meaning OLT didn't issue the self-test command.

		 Default = 0

		Prior to FGU4.0 --> not supported 
		Since FGU4.0 --> is supported for plugable VDSL1/POTS combo
		card types and integrated VDSL2/POTS combo card types.

		For ISAM4.0.10 - stays the same as latest FGU4.x
		For GPON - SUPPORTED as of ISAM4.0.10 (for plugable cards)
		For XG-PON1 - SUPPORTED as GPON as of ISAM4.6.02 (for plugable cards)
		For NG-PON2 - NOT SUPPORTED as of ISAM5.2 (no plugable cards). "
	::= { bponOntPlanCardEntry 9 }

bponOntPlanCardNumNonPotsPorts  OBJECT-TYPE
	SYNTAX 	INTEGER
	ACCESS	read-write
	STATUS	mandatory
	DESCRIPTION 
		" Prior to ISAM 4.0.10 -> NOT SUPPORTED.

		For ISAM4.0.10, this attribute is SUPPORTED.
		Range is 0 - 16.

		For POTS-only card type (32), this attribute must be set to 0.
		For all card types (other than POTS-only), this attribute cannot be set to 0.
		No default - must be supplied by operator.
		For ISAM4.0.10, this attribute determines the number of  non-POTS UNI rows
		that are auto-created by the agent.
		This attribute causes auto-creation of rows for the following UNI-types,
		for the following card-types:
		 16 = Configurable DS1/E1 -> CES UNIs
		 24 = Ethernet (10/100 Base-T) -> Ethernet UNIs
		 32 = POTS -> no auto-creation
		 35 = xDSL(VDSL2) only -> XDSL UNIs
		 38 = Video -> Video UNI
		 46 = MoCA -> MoCA UNIs (SUPPORTED beginning with ISAM5.0)
		 48 = VEIP -> VEIP UNIs (SUPPORTED beginning with ISAM4.2.02)
		 41 = xDSL(VDSL2)/POTS combo -> XDSL UNIs only
		 60 = Ethernet/POTS combo -> Ethernet UNIs only
		 192 = HPNA -> HPNA UNIs only
		
		Modification NOT permitted.
		For ISAM5.4, modification is permitted for the CDE Key of 
		MODIFY_NBR_OF_PORTS_ON_ONTCARD_ALLOWED for Telus.

		For ISAM4.2, stays same as ISAM4.0.10.
		Added mention of support for type 48 = VEIP (beginning with ISAM4.2.02).

		For ISAM4.4, added mention of support for type 192 (HPNA) 

		For ISAM5.0, added mention of support for type 46 (MoCA) 

		For GPON - SUPPORTED (as above)
		For XG-PON1 - SUPPORTED as of ISAM4.6.02
		For NG-PON2 - SUPPORTED as of ISAM5.2 (only for Ethernet UNI card types) "
	::= { bponOntPlanCardEntry 10 }

bponOntPlanCardNumPotsPorts  OBJECT-TYPE
	SYNTAX 	INTEGER
	ACCESS	read-write
	STATUS	mandatory
	DESCRIPTION 
		" This attribute was added for ISAM4.0.10.
		   For ISAM4.2, stays the same as ISAM4.0.10 but added mention of type 48 = VEIP.
		   Range is 0 - 16.

		As of ISAM4.3.02, the range is increased to 0..24.

		 For ISAM4.4, added mention of type 192 = HPNA.


		For cards that have no POTS ports (16, 24, 35, 38, 46, 48, 192), this attribute must be set to 0.
		For all card types that do have POTS ports (32, 41, 60) this attribute cannot be set to 0.

		No default - must be supplied by operator.
		For ISAM4.0.10, this attribute determines the number of  POTS UNI rows
		that are auto-created by the agent.
		This attribute causes auto-creation of rows for the following UNI-types,
		for the following card-types:
		 16 = Configurable DS1/E1 -> no auto-creation
		 24 = Ethernet (10/100 Base-T) -> no auto-creation
		 32 = POTS -> POTS UNIs only
		 35 = xDSL(VDSL2) only -> no auto-creation
		 38 = Video -> no auto-creation
		 41 = xDSL(VDSL2)/POTS combo -> POTS UNIs only
		 46 = MoCA -> no auto-creation
		 48 = VEIP -> no auto-creation
		 60 = Ethernet/POTS combo -> POTS UNIs only
		 192 = HPNA -> no auto-creation
		
		Modification NOT permitted.
		For ISAM5.4, modification is permitted for the CDE Key of 
		MODIFY_NBR_OF_PORTS_ON_ONTCARD_ALLOWED for Telus.

		For GPON - SUPPORTED (as above) as of ISAM4.0.10
		For XG-PON1 - SUPPORTED as of ISAM4.6.02
		For NG-PON2 - SUPPORTED as of ISAM5.2 (only for Ethernet UNI card types) "
	::= { bponOntPlanCardEntry 11 }

bponOntPlanCardConnectNodeType  OBJECT-TYPE
	SYNTAX 	INTEGER
	ACCESS	read-write
	STATUS	mandatory
	DESCRIPTION 
		" Represents the type for all interfaces supported for this ONT linecard.

		Values supported are as follows:
			1 = UNI interface (DEFAULT)
			2 = Subtending interface (sometimes referred to as NNI)
		

		For initial implementation (post ISAM4.5), it is expected that OLT will enforce following validations:
		VALIDATION:  Subtending NNI type is an option ONLY for following card-types:
		 		24 = Ethernet (10/100 Base-T) -> Ethernet UNIs
		 		48 = VEIP -> VEIP UNIs
		VALIDATION:  Subtending NNI type is an option only for shelf LT types that support such.
		VALIDATION:  Subtending NNI type CANNOT be selected if bponOntVlanBridgeMappingMode is N:MP.
		
		Modification NOT permitted.

		Attribute was first introduced as of ISAM4.5 MIB, with targeted implementation in ISAM4.5.01.
		For GPON - SUPPORTED as of ISAM4.5.01
		For XG-PON1 - SUPPORTED as of ISAM4.6.02
		For NG-PON2 - SUPPORTED (only for value 1 = UNI interface).  "
	::= { bponOntPlanCardEntry 12 }

bponOntPlanCardTransparentMode  OBJECT-TYPE
	SYNTAX 	INTEGER
	ACCESS	read-write
	STATUS	mandatory
	DESCRIPTION 
		" Represents if interfaces on ONT linecard enable/disable transparent forwarding.

		Values supported are as follows:
			1 = Disable (DEFAULT)
			2 = Enable
		
		Value only has relevance if selected value of bponOntPlanCardConnectNodeType
		 attribute  (above) = Subtending (NNI).
		
		Modification NOT permitted.

		Attribute was first introduced as of ISAM4.5 MIB, with targeted implementation in ISAM4.5.01.

		For GPON - SUPPORTED as of ISAM4.5.01
		For XG-PON1 - SUPPORTED as of ISAM4.6.02
		For NG-PON2 - SUPPORTED (only for value 1 = Disable).  "
	::= { bponOntPlanCardEntry 13 }

bponOntPlanCardNoMulticastControl  OBJECT-TYPE
	SYNTAX	INTEGER
	ACCESS	read-write
	STATUS	mandatory
	DESCRIPTION 
		"This attribute is used to control whether multicast related OMCI messages(mainly multicast operation,
profile and multicast subscriber configure info) should be sent to ONU or not.
		If it is enabled, it means OLT will not control the multicast behavior on ONT, so multicast related OMCI messages will not be sent to ONU.
		Values supported are as follows:  	
			1--- Disable (DEFAULT)
			2--- Enable

		Value only has relevance if selected value of bponOntPlanCardConnectNodeType attribute  (above) = Subtending (NNI) and selected value of bponOntPlanCardTransparentMode attribute (above) = Enable . 
		
		Modification NOT permitted.

		Attribute was first introduced as of ISAM5.4 MIB, with targeted implementation in ISAM5.4.01.

		For GPON - SUPPORTED as of ISAM5.4.01
		For XG-PON1 - NOTSUPPORTED
		For NG-PON2 - SUPPORTED as of ISAM5.4.01."
	::= { bponOntPlanCardEntry 14 }
-- *********************************************
--
-- BPON ONT ACTUAL CARD TABLE
--
-- This is a new table beginning with FGU2.5. Rows
-- are automatically created by agent when ONT is
-- actually ranged - and actual card configuration
-- is discovered by the OLT via OMCI.
--
-- For FGU4.0, this table is being re-used.  Comments are 
-- made regarding whether attribute is relevant to BPON,
-- GPON or both, etc.  
-- 
-- For ISAM4.0.10, this table is being re-used. 
-- Noted which attributes are relevant for ISAM4.0.10.
--
-- *********************************************

bponOntActualCardTable  OBJECT-TYPE
	SYNTAX SEQUENCE OF BponOntActualCardEntry
	ACCESS	not-accessible
	STATUS	mandatory
	::= { bponOntGroup 3 }

bponOntActualCardEntry  OBJECT-TYPE
	SYNTAX 	BponOntActualCardEntry
	ACCESS	not-accessible
	STATUS	mandatory
	INDEX	{ bponOntActualCardOntIndex,
		  bponOntActualCardSpIndex }
	::= { bponOntActualCardTable 1 }

BponOntActualCardEntry ::= SEQUENCE {
	bponOntActualCardOntIndex				IfIndex,
	bponOntActualCardSpIndex				SpIndex,
	bponOntActualCardType		INTEGER,
	bponOntActualCardIntegConfig			INTEGER,
	bponOntActualCardNumPorts			INTEGER,
	bponOntActualCardSerialNumber			OCTET STRING,
	bponOntActualCardVersion				OCTET STRING,
	bponOntActualCardVendorId			OCTET STRING,
	bponOntActualCardOperState			OperState,
	bponOntActualCardEquipId			OCTET STRING,
	bponOntActualCardNumNonPotsPorts			INTEGER,
	bponOntActualCardNumPotsPorts			INTEGER
}

bponOntActualCardOntIndex  OBJECT-TYPE
	SYNTAX 	IfIndex
	ACCESS	read-only
	STATUS	mandatory
	DESCRIPTION 
		"Each row is indexed by the ifIndex of the ONT. 

		Applicable for both BPON and GPON.

		For GPON - SUPPORTED as of ISAM4.0.10
		For XG-PON1 - SUPPORTED as of ISAM4.6.02
		For NG-PON2 - SUPPORTED as of ISAM5.2  "
	::= { bponOntActualCardEntry 1 }

bponOntActualCardSpIndex  OBJECT-TYPE
	SYNTAX 	SpIndex
	ACCESS	read-only
	STATUS	mandatory
	DESCRIPTION 
		"Each row is also indexed by a number that
		 contains the slot number within the ONT.

		Applicable for both BPON and GPON.

		For GPON - SUPPORTED as of ISAM4.0.10
		For XG-PON1 - SUPPORTED as of ISAM4.6.02
		For NG-PON2 - SUPPORTED as of ISAM5.2  "
	::= { bponOntActualCardEntry 2 }


bponOntActualCardType  OBJECT-TYPE
	SYNTAX 	INTEGER
	ACCESS	read-only
	STATUS	mandatory
	DESCRIPTION 
		"Represents the actual type of Linecard 
		 in the Holder, per Table 9.1.5 of 984.4.  
		 Values supported are as follows:

		 0 = Empty - no linecard in slot (prior to and since FGU4.0)
		 16 = Configurable DS1/E1(starting again with FGU4.3)
		 24 = Ethernet ( Old value : 10/100 Base-T, Prior to ISAM5.2) (prior to and since FGU4.0)
		 32 = POTS (prior to and since FGU4.0)
		 35 = xDSL(VDSL2) only (since FGU4.5.5)
		 38 = Video (prior to FGU4.0, and since FGU4.1)
		 41 = xDSL(VDSL2)/POTS combo (starting with FGU4.4)
		 42 = VDSL/POTS combo  (NOT SUPPORTED as of FGU4.5.5)
		 46 = MoCA (since FGU4.2) (SUPPORTED as of ISAM5.0)
		 48 = VEIP (starting with ISAM4.2.02)
		 60 = Ethernet/POTS combo (since FGU4.4)
		 192 = HPNA (SUPPORTED as of ISAM4.4)
		 255 = Unknown - slot not empty, but card type is unrecognizable
		            (prior to and since FGU4.0)

		Applicable for both BPON and GPON.

		For ISAM4.0.10 - stays the same as latest FGU4.x, except only
		following types supported: 0, 16, 24, 32, 35, 38, 41, 60 and 255.

		For ISAM4.2 - stays same as ISAM4.0.10.
		Added mention of support for type 48 = VEIP (beginning with ISAM4.2.02).

		For ISAM4.4, added mention of support for 192 = HPNA.

		For ISAM5.0, added mention of support for 46 = MoCA 

		For GPON - SUPPORTED as of ISAM4.0.10
		For XG-PON1 - SUPPORTED as of ISAM4.6.02
		For NG-PON2 - SUPPORTED as of ISAM5.4.01 (only for Ethernet Card types and POTS)  "
	::= { bponOntActualCardEntry 3 }


bponOntActualCardIntegConfig  OBJECT-TYPE
	SYNTAX 	INTEGER
	ACCESS	read-only
	STATUS	mandatory
	DESCRIPTION 
		"This reflects how the ONT considers to
		 model its subscriber interfaces as follows:

		 0 = Non-Integrated
		 1 = Integrated
		 2 = Unknown

		Applicable for both BPON and GPON.


		For GPON - SUPPORTED as of ISAM4.0.10
		For XG-PON1 - SUPPORTED as of ISAM4.6.02
		For NG-PON2 - SUPPORTED as of ISAM5.2  "
	::= { bponOntActualCardEntry 4 }



bponOntActualCardNumPorts  OBJECT-TYPE
	SYNTAX 	INTEGER
	ACCESS	read-only
	STATUS	mandatory
	DESCRIPTION 
		" This represents the actual number of ports that
		 the ONT card contains - discovered via OMCI.
 		Range: 0 to 15
		 Default = 0 meaning actual number not yet 
   		discovered.

		Applicable for both BPON and GPON.

		For ISAM4.0.10 - this attribute is NOT SUPPORTED. 

		For GPON - NOT SUPPORTED as of ISAM4.0.10
		For XG-PON1 - NOT SUPPORTED as of ISAM4.6.02
		For NG-PON2 - NOT SUPPORTED as of ISAM5.2 "
	::= { bponOntActualCardEntry 5 }



bponOntActualCardSerialNumber  OBJECT-TYPE
	SYNTAX 	OCTET STRING (SIZE(0..8))
	ACCESS	read-only
	STATUS	mandatory
	DESCRIPTION 
		"Represents the Serial Number of the Subscriber
		 Line Card.  For cards with Integrated Interfaces.
		 this should be same as the ONT Serial Number.
		 This is discovered from the ONT.
		 Default = null string

		Applicable for both BPON and GPON.

		For GPON - SUPPORTED as of ISAM4.0.10
		For XG-PON1 - SUPPORTED as of ISAM4.6.02
		For NG-PON2 - SUPPORTED as of ISAM5.2 "
	::= { bponOntActualCardEntry 6 }


bponOntActualCardVersion  OBJECT-TYPE
	SYNTAX 	OCTET STRING (SIZE(0..14))
	ACCESS	read-only
	STATUS	mandatory
	DESCRIPTION 
		"Represents the Version of the Subscriber
		 Line Card.  For cards with Integrated Interfaces.
		 this should be same as the ONT Version.
		 This is discovered from the ONT.
		 Default = null string

		Applicable for both BPON and GPON.

		For GPON - SUPPORTED as of ISAM4.0.10
		For XG-PON1 - SUPPORTED as of ISAM4.6.02
		For NG-PON2 - SUPPORTED as of ISAM5.2 "
	::= { bponOntActualCardEntry 7 }


bponOntActualCardVendorId  OBJECT-TYPE
	SYNTAX 	OCTET STRING (SIZE(0..4))
	ACCESS	read-only
	STATUS	mandatory
	DESCRIPTION 
		"Represents the Vendor ID of the Subscriber
		 Line Card.  For cards with Integrated Interfaces.
		 this should be same as the ONT Version.
		 This is discovered from the ONT.
		 Default = null string

		Applicable for both BPON and GPON.

		For GPON - SUPPORTED as of ISAM4.0.10
		For XG-PON1 - SUPPORTED as of ISAM4.6.02
		For NG-PON2 - SUPPORTED as of ISAM5.2 "
	::= { bponOntActualCardEntry 8 }

bponOntActualCardOperState  OBJECT-TYPE
	SYNTAX 	OperState
	ACCESS	read-only
	STATUS	mandatory
	DESCRIPTION 
		"Indicates whether or not card is capable of performing its
		  task. Valid values are Enabled and Disabled
		  Default = 0 = Enabled 

		 Prior to FGU4.0--> Not Supported
		 Since FGU4.0--> is supported

		For GPON - SUPPORTED as of ISAM4.0.10
		For XG-PON1 - SUPPORTED as of ISAM4.6.02
		For NG-PON2 - SUPPORTED as of ISAM5.2 "
	::= { bponOntActualCardEntry 9 }

bponOntActualCardEquipId  OBJECT-TYPE
	SYNTAX 	OCTET STRING (SIZE(0..20))
	ACCESS	read-only
	STATUS	mandatory
	DESCRIPTION 
		"Used to represent specific type of card. In North
		 America, this may be CLEI code.
		 Default = null string

		 Applicable for both BPON and GPON.

		Prior to FGU4.0--> Not Supported
		Since FGU4.0--> is supported.

		For GPON - SUPPORTED as of ISAM4.0.10
		For XG-PON1 - SUPPORTED as of ISAM4.6.02
		For NG-PON2 - SUPPORTED as of ISAM5.2 "
	::= { bponOntActualCardEntry 10 }


bponOntActualCardNumNonPotsPorts  OBJECT-TYPE
	SYNTAX 	INTEGER
	ACCESS	read-only
	STATUS	mandatory
	DESCRIPTION 
		" This represents the actual number of non-POTS ports that
		 the ONT card contains - discovered via OMCI.
 		 Range: 0 to 16

		 Default = 0 meaning either actual number not yet 
   		 discovered.or card actually has 0 non-POTs ports.
		 NOTE: Meaning is discernable because if card has not yet
		 been discovered, both bponOntActualCardNumNonPotsPorts
		 and bponOntActualCardNumPotsPorts attributes will be 0.  They both
		 cannot be 0 if card has been discovered. 

		For GPON - SUPPORTED as of ISAM4.0.10
		For XG-PON1 - SUPPORTED as of ISAM4.6.02
		For NG-PON2 - SUPPORTED as of ISAM5.2 (only for Type 24 Ethernet Card UNIs) "
	::= { bponOntActualCardEntry 11 }

bponOntActualCardNumPotsPorts  OBJECT-TYPE
	SYNTAX 	INTEGER
	ACCESS	read-only
	STATUS	mandatory
	DESCRIPTION 
		" This represents the actual number of POTS ports that
		 the ONT card contains - discovered via OMCI.
 		 Range: 0 to 16

		 As of ISAM4.3.02, the range is increased to 0..24.

		 Default = 0 meaning either actual number not yet 
   		 discovered.or card actually has 0 POTs ports.
		 NOTE: Meaning is discernable because if card has not yet
		 been discovered, both bponOntActualCardNumNonPotsPorts
		 and bponOntActualCardNumPotsPorts attributes will be 0.  They both
		 cannot be 0 if card has been discovered.

		For GPON - SUPPORTED as of ISAM4.0.10
		For XG-PON1 - SUPPORTED as of ISAM4.6.02
		For NG-PON2 - SUPPORTED as of ISAM5.2 (only support value 0 since POTS NOT SUPPORTED).  "
	::= { bponOntActualCardEntry 12 }


-- *********************************************
--
-- BPON ONT OPERATIONAL INFO TABLE
--
-- This is a new table beginning with FGU4.1.  It is
-- used to retrieve operational information regarding
-- an ONT. This information resides in this table (instead
-- of the bponOntTable) because the OLT NT must acquire
-- the data from a distributed LT source.  It is more efficient 
-- to place it in a separate table than to mix it with the
-- information in the bponOntTable.
-- 
-- Rows are created automatically by OLT when the
-- corresponding row is created in the bponOntTable.
--
-- For ISAM4.0.10, this table is being re-used. 
-- Noted which attributes are relevant for ISAM4.0.10.
--
--	For GPON - SUPPORTED as of ISAM4.0.10
--	For XG-PON1 - SUPPORTED as of ISAM4.6.02
--	For NG-PON2 - SUPPORTED as of ISAM5.2 
--  
-- *********************************************

bponOntOpInfoTable  OBJECT-TYPE
	SYNTAX SEQUENCE OF BponOntOpInfoEntry
	ACCESS	not-accessible
	STATUS	mandatory
	::= { bponOntGroup 4 }

bponOntOpInfoEntry  OBJECT-TYPE
	SYNTAX 	BponOntOpInfoEntry
	ACCESS	not-accessible
	STATUS	mandatory
	INDEX	{ bponOntOpInfoIndex }
	::= { bponOntOpInfoTable 1 }

BponOntOpInfoEntry ::= SEQUENCE {
	bponOntOpInfoIndex			IfIndex,
	bponOntOpInfoPloamCurrStatus		INTEGER,
	bponOntOpInfoDistance			INTEGER	
}

bponOntOpInfoIndex  OBJECT-TYPE
	SYNTAX 	IfIndex
	ACCESS	read-only
	STATUS	mandatory
	DESCRIPTION 
		"Each row is indexed by the ifIndex of the ONT.

		For ISAM4.0.10 - stays the same as latest FGU4.x  "
	::= { bponOntOpInfoEntry 1 }


bponOntOpInfoPloamCurrStatus OBJECT-TYPE
       	SYNTAX       INTEGER
       	ACCESS       read-only
       	STATUS       mandatory
       	DESCRIPTION
           		"Indicates current state of the ONT (with regards to PLOAM conditions/alarms.
		 This is a bit-map of possible conditions, and multiple conditions can be 
		 simultaneously present.  For example, when an ONT currently has an INACTIVE
		 alarm raised, this attribute can be used to determine all the other PLOAM 
		 conditions/alarms that are present (but which may be masked due to alarm hierarchy).
           		 The bit positions and meanings are as follows:

           		 All Bits Zero = No defect
		 1 = Loss of Signal (LOS)
		 2 = Loss of Acknowlwdgement (LOA)
		 3 = Undefined - Not Supported
		 4 = Loss of GEM Channel Delineation (LCD)
		 5 = Undefined - Not Supported
		 6 = Physical Equipment Error (PEE)
		 7 = Startup Failure (SUF)
		 8 = Undefined - Not Supported
		 9 = Signal Degrade (SD)
		 10 = Undefined - Not Supported
		 11 = Undefined - Not Supported
		 12 = ONT Disabled (ONTDISABLED)
		 13 = Message Error Message (MEM)
		 14 = Undefined - Not Supported
		 15 = Inactive (INACT)
		 16 = Loss of Frame (LOF)
		 17 = Signal fail (SF)
		 18 = Dying Gasp (DG)
		 19 = Deactivate Failure (DF)
		 20 = Loss of PLOAM (LOAM)
		 21 = Drift of Window (DOW)
		 22 = Remote Defect Indication (RDI)
		 23 = Undefined - Not Supported
		 24 = Loss of Key Synchronzation (LOKS)
		 25 = ONT Power Up Error (ONTPWRERR)  - added as of ISAM4.3
		 26 = Rogue ONT Disabled (ROGUEONTDIS) - added as of ISAM4.3
		 27 = Differential Reach Exceeded (DIFREACH)  - added as of ISAM4.3		 
		 28 = Loss of OMCI channel (LOOC)- added as of ISAM5.2 for NG-PON2 
		 29 thru 32 = Undefined - Not Supported


		 Default = 0 = No Defects

		For ISAM4.0.10 - stays the same as latest FGU4.x
		As of ISAM4.3, added support for codepoints 25, 26 and 27.

		For ISAM 5.2 (for NG-PON2) added codepoint 28.  "
        ::= { bponOntOpInfoEntry 2 }


bponOntOpInfoDistance  OBJECT-TYPE
	SYNTAX 	INTEGER
	ACCESS	read-only
	STATUS	mandatory
	DESCRIPTION 
		" This attribute contains as estimate of the distance between this ONT and the OLT.

		  Units are kilometers (with a 0.1 kilometer granularity). 	

		  Valid values are 0.0 kilometers to 100.0 kilometers, along with the special values 65534 and 65535.  
		  This is represented by the INTEGER range: 0 to +1000, and the special values 65534 and 65535.  

		  NOTE: The special value 65534 is used to indicate INVALID (meaning a valid measurement is currently
			unattainable for some reason). Try again later and might get a valid measurement.
		  NOTE: The special value 65535 is used to indicate NOT SUPPORTED (meaning the measurement
			functionality is not supported by this particular unit). Try again later and will get same answer
			(i.e. NOT SUPPORTED).
		  NOTE: For any actual reading lower or higher than the range, OLT will report the lower or higher limit
			of valid values 0 or +1000.

		  Default = 65534 = INVALID

		For ISAM4.0.10 - stays the same as latest FGU4.x  "
        ::= { bponOntOpInfoEntry 3 }

-- *********************************************
--
-- GPON ONT ONT-SIDE AGGREGATE GEM PERFORMANCE MONITOR 
-- CURRENT INTERVAL TABLE
--
-- This is a new table beginning with FGU4.2.
-- This current interval table contains various statistics collected for 
-- aggregate ONT GEM ports (from ONT side of the PON) during the current
-- 15 minute interval of operation.  Statistics include the summation of all
-- GEM ports (excluding the GEM ports associated with OMCI and Multicast).
--
-- An instance of this table is auto-created/deleted in accordance with the 
-- 'ONT-side Aggregate GEM PM Collect Indicator' setting of the ONT Table.
--
-- For GETs of table attributes, the OLT must go directly to the ONT (via OMCI)
-- in order to acquire fresh current counts. 
--
-- For ISAM4.0.10, this table is being re-used. 
-- Noted which attributes are relevant for ISAM4.0.10.
--
--	For GPON - SUPPORTED as of ISAM4.0.10
--	For XG-PON1 - SUPPORTED as of ISAM4.6.02
--	For NG-PON2 - SUPPORTED as of ISAM5.2 
-- 
-- *********************************************


gponOntOntsideAggGemCurrentIntervalTable  OBJECT-TYPE
	SYNTAX SEQUENCE OF GponOntOntsideAggGemCurrentIntervalEntry
	ACCESS	not-accessible
	STATUS	mandatory
	::= { bponOntGroup 5 }


gponOntOntsideAggGemCurrentIntervalEntry  OBJECT-TYPE
	SYNTAX 	GponOntOntsideAggGemCurrentIntervalEntry
	ACCESS	not-accessible
	STATUS	mandatory
	DESCRIPTION 
		"An entry in the GPON ONT ONT-side GEM PM
		 Aggregate CurrentInterval Table. "
	INDEX	{ gponOntOntsideAggGemCurrentIntervalIndex }
	::= { gponOntOntsideAggGemCurrentIntervalTable 1 }

GponOntOntsideAggGemCurrentIntervalEntry ::= SEQUENCE {
	gponOntOntsideAggGemCurrentIntervalIndex			IfIndex,
	gponOntOntsideAggGemCurrentIntervalValidInd			Boolean,
	gponOntOntsideAggGemCurrentIntervalLostFragsDown			Counter,
	gponOntOntsideAggGemCurrentIntervalLostFragsUp			Counter,
	gponOntOntsideAggGemCurrentIntervalReceiveFrags		Counter,
	gponOntOntsideAggGemCurrentIntervalReceiveBlocks		Counter,
	gponOntOntsideAggGemCurrentIntervalTransmitBlocks		Counter,
	gponOntOntsideAggGemCurrentIntervalTransmitFrags		Counter,
	gponOntOntsideAggGemCurrentIntervalBadHeaders		Counter,
	gponOntOntsideAggGemCurrentIntervalReceiveBlocksCounter64	OCTET STRING,
	gponOntOntsideAggGemCurrentIntervalTransmitBlocksCounter64	OCTET STRING
}


gponOntOntsideAggGemCurrentIntervalIndex  OBJECT-TYPE
	SYNTAX 	IfIndex
	ACCESS	read-only
	STATUS	mandatory
	DESCRIPTION 
		"This index is the ifIndex of the Ont.

		For ISAM4.0.10 - stays the same as latest FGU4.x  "
	::= { gponOntOntsideAggGemCurrentIntervalEntry 1 }


gponOntOntsideAggGemCurrentIntervalValidInd  OBJECT-TYPE
	SYNTAX 	Boolean
	ACCESS	read-only
	STATUS	mandatory
	DESCRIPTION 
		"Indicates whether or not this CurrentInterval contains
		 valid PM counts.

		 As of FGU4.2, NOT SUPPORTED

		For ISAM4.0.10 - stays the same as latest FGU4.x  "
	::= { gponOntOntsideAggGemCurrentIntervalEntry 2 }


gponOntOntsideAggGemCurrentIntervalLostFragsDown  OBJECT-TYPE
	SYNTAX 	Counter
	ACCESS	read-only
	STATUS	mandatory
	DESCRIPTION 
		"A count of Lost GEM Fragments (downstream).

		For ISAM4.0.10 - stays the same as latest FGU4.x "
	::= { gponOntOntsideAggGemCurrentIntervalEntry 3 }

gponOntOntsideAggGemCurrentIntervalLostFragsUp  OBJECT-TYPE
	SYNTAX 	Counter
	ACCESS	read-only
	STATUS	mandatory
	DESCRIPTION 
		"A count of Lost GEM Fragments (upstream).

		For ISAM4.0.10 - stays the same as latest FGU4.x "
	::= { gponOntOntsideAggGemCurrentIntervalEntry 4 }

gponOntOntsideAggGemCurrentIntervalReceiveFrags  OBJECT-TYPE
	SYNTAX 	Counter
	ACCESS	read-only
	STATUS	mandatory
	DESCRIPTION 
		"A count of Received GEM Fragments.

		For ISAM4.0.10 - stays the same as latest FGU4.x "
	::= { gponOntOntsideAggGemCurrentIntervalEntry 5 }


gponOntOntsideAggGemCurrentIntervalReceiveBlocks  OBJECT-TYPE
	SYNTAX 	Counter
	ACCESS	read-only
	STATUS	mandatory
	DESCRIPTION 
		"A count of Received GEM Blocks.

		For ISAM4.0.10 - stays the same as latest FGU4.x

		 As of ISAM4.5, the plan is to effectively DEPRECATE this attribute.  Manager should instead use equivalent 
		 64-bit counter attribute gponOntOntsideAggGemCurrentIntervalReceiveBlocksCounter64. "
	::= { gponOntOntsideAggGemCurrentIntervalEntry 6 }


gponOntOntsideAggGemCurrentIntervalTransmitBlocks  OBJECT-TYPE
	SYNTAX 	Counter
	ACCESS	read-only
	STATUS	mandatory
	DESCRIPTION 
		"A count of Transmitted GEM Blocks.

		For ISAM4.0.10 - stays the same as latest FGU4.x

		 As of ISAM4.5, the plan is to effectively DEPRECATE this attribute.  Manager should instead use equivalent 
		 64-bit counter attribute gponOntOntsideAggGemCurrentIntervalTransmitBlocksCounter64. "
	::= { gponOntOntsideAggGemCurrentIntervalEntry 7 }


gponOntOntsideAggGemCurrentIntervalTransmitFrags  OBJECT-TYPE
	SYNTAX 	Counter
	ACCESS	read-only
	STATUS	mandatory
	DESCRIPTION 
		"A count of Transmitted GEM Fragments.

		For ISAM4.0.10 - stays the same as latest FGU4.x "
	::= { gponOntOntsideAggGemCurrentIntervalEntry 8 }


gponOntOntsideAggGemCurrentIntervalBadHeaders  OBJECT-TYPE
	SYNTAX 	Counter
	ACCESS	read-only
	STATUS	mandatory
	DESCRIPTION 
		"A count of Received GEM Headers that are bad.

		For ISAM4.0.10 - stays the same as latest FGU4.x "
	::= { gponOntOntsideAggGemCurrentIntervalEntry 9 }

gponOntOntsideAggGemCurrentIntervalReceiveBlocksCounter64  OBJECT-TYPE
	SYNTAX 	OCTET STRING (SIZE(8))
	ACCESS	read-only
	STATUS	mandatory
	DESCRIPTION 
		" This represents the equivalent of a 64-bit count of Received GEM Blocks.

		 Introduced for readiness in ISAM 4.5 MIB.  Plan to support 32-bit counts in this attribute with ISAM4.5
		 with target implementation of 64-bit counts in ISAM4.5.01. "
	::= { gponOntOntsideAggGemCurrentIntervalEntry 10 }


gponOntOntsideAggGemCurrentIntervalTransmitBlocksCounter64  OBJECT-TYPE
	SYNTAX 	OCTET STRING (SIZE(8))
	ACCESS	read-only
	STATUS	mandatory
	DESCRIPTION 
		" This represents the equivalent of a 64-bit count of Transmitted GEM Blocks.

		 Introduced for readiness in ISAM 4.5 MIB.  Plan to support 32-bit counts in this attribute with ISAM4.5
		 with target implementation of 64-bit counts in ISAM4.5.01. "
	::= { gponOntOntsideAggGemCurrentIntervalEntry 11 }

-- *********************************************
--
-- GPON ONT ONT-SIDE AGGREGATE GEM PERFORMANCE MONITOR 
-- INTERVAL TABLE
--
-- This is a new table beginning with FGU4.2.
-- This interval table contains various statistics collected for 
-- aggregate ONT GEM ports (from ONT side of the PON) over the previous
-- 8 hours of operation.  The past 8 hours are broken into 32 completed 15
-- minute intervals. Each row in this table represents one such interval. 
-- Statistics include the summation of all GEM ports (excluding the GEM ports
-- associated with OMCI and Multicast).
--
-- An instance of this table is auto-created/deleted in accordance with the 
-- 'ONT-side Aggregate GEM PM Collect Indicator' setting of the ONT Table.
--
-- For ISAM4.0.10, this table is being re-used. 
-- Noted which attributes are relevant for ISAM4.0.10.
--
--	For GPON - SUPPORTED as of ISAM4.0.10
--	For XG-PON1 - SUPPORTED as of ISAM4.6.02
--	For NG-PON2 - SUPPORTED as of ISAM5.2 
-- 
-- *********************************************


gponOntOntsideAggGemIntervalTable  OBJECT-TYPE
	SYNTAX SEQUENCE OF GponOntOntsideAggGemIntervalEntry
	ACCESS	not-accessible
	STATUS	mandatory
	::= { bponOntGroup 6 }


gponOntOntsideAggGemIntervalEntry  OBJECT-TYPE
	SYNTAX 	GponOntOntsideAggGemIntervalEntry
	ACCESS	not-accessible
	STATUS	mandatory
	DESCRIPTION 
		"An entry in the GPON ONT ONT-side GEM PM
		 Aggregate CurrentInterval Table. "
	INDEX	{ gponOntOntsideAggGemIntervalIndex,
		  gponOntOntsideAggGemIntervalNumber }
	::= { gponOntOntsideAggGemIntervalTable 1 }

GponOntOntsideAggGemIntervalEntry ::= SEQUENCE {
	gponOntOntsideAggGemIntervalIndex			IfIndex,
	gponOntOntsideAggGemIntervalNumber		INTEGER,
	gponOntOntsideAggGemIntervalValidInd			Boolean,
	gponOntOntsideAggGemIntervalLostFragsDown			Counter,
	gponOntOntsideAggGemIntervalLostFragsUp			Counter,
	gponOntOntsideAggGemIntervalReceiveFrags		Counter,
	gponOntOntsideAggGemIntervalReceiveBlocks		Counter,
	gponOntOntsideAggGemIntervalTransmitBlocks		Counter,
	gponOntOntsideAggGemIntervalTransmitFrags		Counter,
	gponOntOntsideAggGemIntervalBadHeaders		Counter,
	gponOntOntsideAggGemIntervalReceiveBlocksCounter64		OCTET STRING,
	gponOntOntsideAggGemIntervalTransmitBlocksCounter64		OCTET STRING
}


gponOntOntsideAggGemIntervalIndex  OBJECT-TYPE
	SYNTAX 	IfIndex
	ACCESS	read-only
	STATUS	mandatory
	DESCRIPTION 
		"This index is the ifIndex of the Ont.

		For ISAM4.0.10 - stays the same as latest FGU4.x  "
	::= { gponOntOntsideAggGemIntervalEntry 1 }

gponOntOntsideAggGemIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.

		For ISAM4.0.10 - stays the same as latest FGU4.x  "
	::= { gponOntOntsideAggGemIntervalEntry 2 }


gponOntOntsideAggGemIntervalValidInd  OBJECT-TYPE
	SYNTAX 	Boolean
	ACCESS	read-only
	STATUS	mandatory
	DESCRIPTION 
		"Indicates whether or not this CurrentInterval contains
		 valid PM counts. 

		 As of FGU4.2, NOT SUPPORTED

		For ISAM4.0.10 - stays the same as latest FGU4.x "
	::= { gponOntOntsideAggGemIntervalEntry 3 }


gponOntOntsideAggGemIntervalLostFragsDown  OBJECT-TYPE
	SYNTAX 	Counter
	ACCESS	read-only
	STATUS	mandatory
	DESCRIPTION 
		"A count of Lost GEM Fragments (downstream).

		For ISAM4.0.10 - stays the same as latest FGU4.x "
	::= { gponOntOntsideAggGemIntervalEntry 4 }

gponOntOntsideAggGemIntervalLostFragsUp  OBJECT-TYPE
	SYNTAX 	Counter
	ACCESS	read-only
	STATUS	mandatory
	DESCRIPTION 
		"A count of Lost GEM Fragments (upstream).

		For ISAM4.0.10 - stays the same as latest FGU4.x "
	::= { gponOntOntsideAggGemIntervalEntry 5 }

gponOntOntsideAggGemIntervalReceiveFrags  OBJECT-TYPE
	SYNTAX 	Counter
	ACCESS	read-only
	STATUS	mandatory
	DESCRIPTION 
		"A count of Received GEM Fragments.

		For ISAM4.0.10 - stays the same as latest FGU4.x "
	::= { gponOntOntsideAggGemIntervalEntry 6 }


gponOntOntsideAggGemIntervalReceiveBlocks  OBJECT-TYPE
	SYNTAX 	Counter
	ACCESS	read-only
	STATUS	mandatory
	DESCRIPTION 
		"A count of Received GEM Blocks.

		For ISAM4.0.10 - stays the same as latest FGU4.x

		 As of ISAM4.5, the plan is to effectively DEPRECATE this attribute.  Manager should instead use equivalent 
		 64-bit counter attribute gponOntOntsideAggGemIntervalReceiveBlocksCounter64. "
	::= { gponOntOntsideAggGemIntervalEntry 7 }


gponOntOntsideAggGemIntervalTransmitBlocks  OBJECT-TYPE
	SYNTAX 	Counter
	ACCESS	read-only
	STATUS	mandatory
	DESCRIPTION 
		"A count of Transmitted GEM Blocks.

		For ISAM4.0.10 - stays the same as latest FGU4.x

		 As of ISAM4.5, the plan is to effectively DEPRECATE this attribute.  Manager should instead use equivalent 
		 64-bit counter attribute gponOntOntsideAggGemIntervalTransmitBlocksCounter64. "
	::= { gponOntOntsideAggGemIntervalEntry 8 }


gponOntOntsideAggGemIntervalTransmitFrags  OBJECT-TYPE
	SYNTAX 	Counter
	ACCESS	read-only
	STATUS	mandatory
	DESCRIPTION 
		"A count of Transmitted GEM Fragments.

		For ISAM4.0.10 - stays the same as latest FGU4.x "
	::= { gponOntOntsideAggGemIntervalEntry 9 }


gponOntOntsideAggGemIntervalBadHeaders  OBJECT-TYPE
	SYNTAX 	Counter
	ACCESS	read-only
	STATUS	mandatory
	DESCRIPTION 
		"A count of Received GEM Headers that are bad.

		For ISAM4.0.10 - stays the same as latest FGU4.x "
	::= { gponOntOntsideAggGemIntervalEntry 10 }

gponOntOntsideAggGemIntervalReceiveBlocksCounter64  OBJECT-TYPE
	SYNTAX 	OCTET STRING (SIZE(8))
	ACCESS	read-only
	STATUS	mandatory
	DESCRIPTION 
		" This represents the equivalent of a 64-bit count of Received GEM Blocks.

		 Introduced for readiness in ISAM 4.5 MIB.  Plan to support 32-bit counts in this attribute with ISAM4.5
		 with target implementation of 64-bit counts in ISAM4.5.01. "
	::= { gponOntOntsideAggGemIntervalEntry 11 }


gponOntOntsideAggGemIntervalTransmitBlocksCounter64  OBJECT-TYPE
	SYNTAX 	OCTET STRING (SIZE(8))
	ACCESS	read-only
	STATUS	mandatory
	DESCRIPTION 
		" This represents the equivalent of a 64-bit count of Transmitted GEM Blocks.

		 Introduced for readiness in ISAM 4.5 MIB.  Plan to support 32-bit counts in this attribute with ISAM4.5
		 with target implementation of 64-bit counts in ISAM4.5.01. "
	::= { gponOntOntsideAggGemIntervalEntry 12 }

-- *********************************************
--
-- GPON ONT OLT-SIDE ON-DEMAND AGGREGATE GEM PERFORMANCE
-- MONITOR CURRENT INTERVAL TABLE
--
-- This is a new table beginning with FGU4.2.
-- This current interval table contains various statistics collected for 
-- aggregate ONT GEM ports (from OLT side of the PON) during the current
-- 15 minute interval of operation.  Statistics include the summation of all
-- GEM ports (excluding the GEM ports associated with OMCI and Multicast).
--
-- An instance of this table is auto-created/deleted in accordance with the 
-- 'OLT-side On Demand Aggregate GEM PM Collect Indicator' setting of the ONT Table'.
--
-- For GETs of table attributes, the OLT must go directly to the ONT (via OMCI)
-- in order to acquire fresh current counts. 
--
-- For ISAM4.0.10, this table is being re-used. 
-- Noted which attributes are relevant for ISAM4.0.10.
--
--	For GPON - SUPPORTED as of ISAM4.0.10
--	For XG-PON1 - SUPPORTED as of ISAM4.6.02
--	For NG-PON2 - SUPPORTED as of ISAM5.2 
-- 
-- *********************************************


gponOntOltsideODAggGemCurrentIntervalTable  OBJECT-TYPE
	SYNTAX SEQUENCE OF GponOntOltsideODAggGemCurrentIntervalEntry
	ACCESS	not-accessible
	STATUS	mandatory
	::= { bponOntGroup 7 }


gponOntOltsideODAggGemCurrentIntervalEntry  OBJECT-TYPE
	SYNTAX 	GponOntOltsideODAggGemCurrentIntervalEntry
	ACCESS	not-accessible
	STATUS	mandatory
	DESCRIPTION 
		"An entry in the GPON ONT OLT-side GEM PM
		 Aggregate CurrentInterval Table. "
	INDEX	{ gponOntOltsideODAggGemCurrentIntervalIndex }
	::= { gponOntOltsideODAggGemCurrentIntervalTable 1 }

GponOntOltsideODAggGemCurrentIntervalEntry ::= SEQUENCE {
	gponOntOltsideODAggGemCurrentIntervalIndex			IfIndex,
	gponOntOltsideODAggGemCurrentIntervalValidInd			Boolean,
	gponOntOltsideODAggGemCurrentIntervalLostFragsDown			Counter,
	gponOntOltsideODAggGemCurrentIntervalLostFragsUp			Counter,
	gponOntOltsideODAggGemCurrentIntervalReceiveFrags		Counter,
	gponOntOltsideODAggGemCurrentIntervalReceiveBlocks		Counter,
	gponOntOltsideODAggGemCurrentIntervalTransmitBlocks		Counter,
	gponOntOltsideODAggGemCurrentIntervalTransmitFrags		Counter,
	gponOntOltsideODAggGemCurrentIntervalReceiveBlocksCounter64		OCTET STRING,
	gponOntOltsideODAggGemCurrentIntervalTransmitBlocksCounter64		OCTET STRING
}


gponOntOltsideODAggGemCurrentIntervalIndex  OBJECT-TYPE
	SYNTAX 	IfIndex
	ACCESS	read-only
	STATUS	mandatory
	DESCRIPTION 
		"This index is the ifIndex of the Ont.

		For ISAM4.0.10 - stays the same as latest FGU4.x  "
	::= { gponOntOltsideODAggGemCurrentIntervalEntry 1 }


gponOntOltsideODAggGemCurrentIntervalValidInd  OBJECT-TYPE
	SYNTAX 	Boolean
	ACCESS	read-only
	STATUS	mandatory
	DESCRIPTION 
		"Indicates whether or not this CurrentInterval contains
		 valid PM counts.

		 As of FGU4.2, NOT SUPPORTED

		For ISAM4.0.10 - stays the same as latest FGU4.x  "
	::= { gponOntOltsideODAggGemCurrentIntervalEntry 2 }


gponOntOltsideODAggGemCurrentIntervalLostFragsDown  OBJECT-TYPE
	SYNTAX 	Counter
	ACCESS	read-only
	STATUS	mandatory
	DESCRIPTION 
		"A count of Lost GEM Fragments (downstream).

		 As of FGU4.2, this is NOT SUPPORTED

		For ISAM4.0.10 - stays the same as latest FGU4.x "
	::= { gponOntOltsideODAggGemCurrentIntervalEntry 3 }

gponOntOltsideODAggGemCurrentIntervalLostFragsUp  OBJECT-TYPE
	SYNTAX 	Counter
	ACCESS	read-only
	STATUS	mandatory
	DESCRIPTION 
		"A count of Lost GEM Fragments (upstream).

		For ISAM4.0.10 - stays the same as latest FGU4.x "
	::= { gponOntOltsideODAggGemCurrentIntervalEntry 4 }

gponOntOltsideODAggGemCurrentIntervalReceiveFrags  OBJECT-TYPE
	SYNTAX 	Counter
	ACCESS	read-only
	STATUS	mandatory
	DESCRIPTION 
		"A count of Received GEM Fragments.

		For ISAM4.0.10 - stays the same as latest FGU4.x "
	::= { gponOntOltsideODAggGemCurrentIntervalEntry 5 }


gponOntOltsideODAggGemCurrentIntervalReceiveBlocks  OBJECT-TYPE
	SYNTAX 	Counter
	ACCESS	read-only
	STATUS	mandatory
	DESCRIPTION 
		"A count of Received GEM Blocks

		For ISAM4.0.10 - stays the same as latest FGU4.x.

		 As of ISAM4.5, the plan is to effectively DEPRECATE this attribute.  Manager should instead use equivalent 
		 64-bit counter attribute gponOntOltsideODAggGemCurrentIntervalReceiveBlocksCounter64. "
	::= { gponOntOltsideODAggGemCurrentIntervalEntry 6 }


gponOntOltsideODAggGemCurrentIntervalTransmitBlocks  OBJECT-TYPE
	SYNTAX 	Counter
	ACCESS	read-only
	STATUS	mandatory
	DESCRIPTION 
		"A count of Transmitted GEM Blocks.

		For ISAM4.0.10 - stays the same as latest FGU4.x

		 As of ISAM4.5, the plan is to effectively DEPRECATE this attribute.  Manager should instead use equivalent 
		 64-bit counter attribute gponOntOltsideODAggGemCurrentIntervalTransmitBlocksCounter64. "
	::= { gponOntOltsideODAggGemCurrentIntervalEntry 7 }


gponOntOltsideODAggGemCurrentIntervalTransmitFrags  OBJECT-TYPE
	SYNTAX 	Counter
	ACCESS	read-only
	STATUS	mandatory
	DESCRIPTION 
		"A count of Transmitted GEM Fragments.

		For ISAM4.0.10 - stays the same as latest FGU4.x "
	::= { gponOntOltsideODAggGemCurrentIntervalEntry 8 }

gponOntOltsideODAggGemCurrentIntervalReceiveBlocksCounter64  OBJECT-TYPE
	SYNTAX 	OCTET STRING (SIZE(8))
	ACCESS	read-only
	STATUS	mandatory
	DESCRIPTION 
		" This represents the equivalent of a 64-bit count of Received GEM Blocks.

		 Introduced for readiness in ISAM 4.5 MIB.  Plan to support 32-bit counts in this attribute with ISAM4.5
		 with target implementation of 64-bit counts in ISAM4.5.01. "
	::= { gponOntOltsideODAggGemCurrentIntervalEntry 9 }


gponOntOltsideODAggGemCurrentIntervalTransmitBlocksCounter64  OBJECT-TYPE
	SYNTAX 	OCTET STRING (SIZE(8))
	ACCESS	read-only
	STATUS	mandatory
	DESCRIPTION 
		" This represents the equivalent of a 64-bit count of Transmitted GEM Blocks.

		 Introduced for readiness in ISAM 4.5 MIB.  Plan to support 32-bit counts in this attribute with ISAM4.5
		 with target implementation of 64-bit counts in ISAM4.5.01. "
	::= { gponOntOltsideODAggGemCurrentIntervalEntry 10 }



-- *********************************************
--
-- GPON ONT OLT-SIDE ON-DEMAND AGGREGATE GEM PERFORMANCE  
-- MONITOR INTERVAL TABLE
--
-- This is a new table beginning with FGU4.2.
-- This interval table contains various statistics collected for 
-- aggregate ONT GEM ports (from OLT side of the PON) over the previous
-- 8 hours of operation.  The past 8 hours are broken into 32 completed 15
-- minute intervals. Each row in this table represents one such interval. 
-- Statistics include the summation of all GEM ports (excluding the GEM ports
-- associated with OMCI and Multicast).
--
-- An instance of this table is auto-created/deleted in accordance with the 
-- 'OLT-side On Demand Aggregate GEM PM Collect Indicator' setting of the ONT Table.
--
-- For ISAM4.0.10, this table is being re-used. 
-- Noted which attributes are relevant for ISAM4.0.10.
--
--	For GPON - SUPPORTED as of ISAM4.0.10
--	For XG-PON1 - SUPPORTED as of ISAM4.6.02
--	For NG-PON2 - SUPPORTED as of ISAM5.2 
-- 
-- *********************************************


gponOntOltsideODAggGemIntervalTable  OBJECT-TYPE
	SYNTAX SEQUENCE OF GponOntOltsideODAggGemIntervalEntry
	ACCESS	not-accessible
	STATUS	mandatory
	::= { bponOntGroup 8 }


gponOntOltsideODAggGemIntervalEntry  OBJECT-TYPE
	SYNTAX 	GponOntOltsideODAggGemIntervalEntry
	ACCESS	not-accessible
	STATUS	mandatory
	DESCRIPTION 
		"An entry in the GPON ONT ONT-side GEM PM
		 Aggregate CurrentInterval Table. "
	INDEX	{ gponOntOltsideODAggGemIntervalIndex,
		  gponOntOltsideODAggGemIntervalNumber }
	::= { gponOntOltsideODAggGemIntervalTable 1 }

GponOntOltsideODAggGemIntervalEntry ::= SEQUENCE {
	gponOntOltsideODAggGemIntervalIndex			IfIndex,
	gponOntOltsideODAggGemIntervalNumber		INTEGER,
	gponOntOltsideODAggGemIntervalValidInd			Boolean,
	gponOntOltsideODAggGemIntervalLostFragsDown			Counter,
	gponOntOltsideODAggGemIntervalLostFragsUp			Counter,
	gponOntOltsideODAggGemIntervalReceiveFrags		Counter,
	gponOntOltsideODAggGemIntervalReceiveBlocks		Counter,
	gponOntOltsideODAggGemIntervalTransmitBlocks		Counter,
	gponOntOltsideODAggGemIntervalTransmitFrags		Counter,
	gponOntOltsideODAggGemIntervalReceiveBlocksCounter64	OCTET STRING,
	gponOntOltsideODAggGemIntervalTransmitBlocksCounter64	OCTET STRING
}


gponOntOltsideODAggGemIntervalIndex  OBJECT-TYPE
	SYNTAX 	IfIndex
	ACCESS	read-only
	STATUS	mandatory
	DESCRIPTION 
		"This index is the ifIndex of the Ont.

		For ISAM4.0.10 - stays the same as latest FGU4.x  "
	::= { gponOntOltsideODAggGemIntervalEntry 1 }

gponOntOltsideODAggGemIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.

		For ISAM4.0.10 - stays the same as latest FGU4.x  "
	::= { gponOntOltsideODAggGemIntervalEntry 2 }


gponOntOltsideODAggGemIntervalValidInd  OBJECT-TYPE
	SYNTAX 	Boolean
	ACCESS	read-only
	STATUS	mandatory
	DESCRIPTION 
		"Indicates whether or not this CurrentInterval contains
		 valid PM counts. 

		 As of FGU4.2, NOT SUPPORTED

		For ISAM4.0.10 - stays the same as latest FGU4.x "
	::= { gponOntOltsideODAggGemIntervalEntry 3 }


gponOntOltsideODAggGemIntervalLostFragsDown  OBJECT-TYPE
	SYNTAX 	Counter
	ACCESS	read-only
	STATUS	mandatory
	DESCRIPTION 
		"A count of Lost GEM Fragments (downstream).

		 As of FGU4.2, this is NOT SUPPORTED

		For ISAM4.0.10 - stays the same as latest FGU4.x "
	::= { gponOntOltsideODAggGemIntervalEntry 4 }

gponOntOltsideODAggGemIntervalLostFragsUp  OBJECT-TYPE
	SYNTAX 	Counter
	ACCESS	read-only
	STATUS	mandatory
	DESCRIPTION 
		"A count of Lost GEM Fragments (upstream).

		For ISAM4.0.10 - stays the same as latest FGU4.x "
	::= { gponOntOltsideODAggGemIntervalEntry 5 }

gponOntOltsideODAggGemIntervalReceiveFrags  OBJECT-TYPE
	SYNTAX 	Counter
	ACCESS	read-only
	STATUS	mandatory
	DESCRIPTION 
		"A count of Received GEM Fragments.

		For ISAM4.0.10 - stays the same as latest FGU4.x "
	::= { gponOntOltsideODAggGemIntervalEntry 6 }


gponOntOltsideODAggGemIntervalReceiveBlocks  OBJECT-TYPE
	SYNTAX 	Counter
	ACCESS	read-only
	STATUS	mandatory
	DESCRIPTION 
		"A count of Received GEM Blocks.

		For ISAM4.0.10 - stays the same as latest FGU4.x

		 As of ISAM4.5, the plan is to effectively DEPRECATE this attribute.  Manager should instead use equivalent 
		 64-bit counter attribute gponOntOltsideODAggGemIntervalReceiveBlocksCounter64. "
	::= { gponOntOltsideODAggGemIntervalEntry 7 }


gponOntOltsideODAggGemIntervalTransmitBlocks  OBJECT-TYPE
	SYNTAX 	Counter
	ACCESS	read-only
	STATUS	mandatory
	DESCRIPTION 
		"A count of Transmitted GEM Blocks.

		For ISAM4.0.10 - stays the same as latest FGU4.x

		 As of ISAM4.5, the plan is to effectively DEPRECATE this attribute.  Manager should instead use equivalent 
		 64-bit counter attribute gponOntOltsideODAggGemIntervalTransmitBlocksCounter64. "
	::= { gponOntOltsideODAggGemIntervalEntry 8 }


gponOntOltsideODAggGemIntervalTransmitFrags  OBJECT-TYPE
	SYNTAX 	Counter
	ACCESS	read-only
	STATUS	mandatory
	DESCRIPTION 
		"A count of Transmitted GEM Fragments.

		For ISAM4.0.10 - stays the same as latest FGU4.x "
	::= { gponOntOltsideODAggGemIntervalEntry 9 }

gponOntOltsideODAggGemIntervalReceiveBlocksCounter64  OBJECT-TYPE
	SYNTAX 	OCTET STRING (SIZE(8))
	ACCESS	read-only
	STATUS	mandatory
	DESCRIPTION 
		" This represents the equivalent of a 64-bit count of Received GEM Blocks.

		 Introduced for readiness in ISAM 4.5 MIB.  Plan to support 32-bit counts in this attribute with ISAM4.5
		 with target implementation of 64-bit counts in ISAM4.5.01. "
	::= { gponOntOltsideODAggGemIntervalEntry 10 }


gponOntOltsideODAggGemIntervalTransmitBlocksCounter64  OBJECT-TYPE
	SYNTAX 	OCTET STRING (SIZE(8))
	ACCESS	read-only
	STATUS	mandatory
	DESCRIPTION 
		" This represents the equivalent of a 64-bit count of Transmitted GEM Blocks.

		 Introduced for readiness in ISAM 4.5 MIB.  Plan to support 32-bit counts in this attribute with ISAM4.5
		 with target implementation of 64-bit counts in ISAM4.5.01. "
	::= { gponOntOltsideODAggGemIntervalEntry 11 }

-- *********************************************
--
-- GPON ONT ONT-SIDE AGGREGATE GEM PERFORMANCE MONITOR 
-- TCA THRESHOLD TABLE
--
-- This is a new table beginning with FGU4.2.
-- This table allows the manager to set TCA thresholds for various PMs collected for 
-- aggregate ONT GEM ports (from ONT side of the PON) during the current
-- 15 minute interval of operation.
--
-- An instance of this table is auto-created/deleted in accordance with the 
-- 'ONT-side Aggregate GEM PM Collect Indicator' setting of the ONT Table.
--
-- For ISAM4.0.10, this table is being re-used. 
-- Noted which attributes are relevant for ISAM4.0.10.
--
--	For GPON - SUPPORTED as of ISAM4.0.10
--	For XG-PON1 - SUPPORTED as of ISAM4.6.02
--	For NG-PON2 - SUPPORTED as of ISAM5.2 
-- 
-- *********************************************


gponOntOntsideAggGemTCAThresholdTable  OBJECT-TYPE
	SYNTAX SEQUENCE OF GponOntOntsideAggGemTCAThresholdEntry
	ACCESS	not-accessible
	STATUS	mandatory
	::= { bponOntGroup 9 }


gponOntOntsideAggGemTCAThresholdEntry  OBJECT-TYPE
	SYNTAX 	GponOntOntsideAggGemTCAThresholdEntry
	ACCESS	not-accessible
	STATUS	mandatory
	DESCRIPTION 
		"An entry in the GPON ONT ONT-side GEM PM
		 Aggregate TCAThreshold Table. "
	INDEX	{ gponOntOntsideAggGemTCAThresholdIndex }
	::= { gponOntOntsideAggGemTCAThresholdTable 1 }

GponOntOntsideAggGemTCAThresholdEntry ::= SEQUENCE {
	gponOntOntsideAggGemTCAThresholdIndex			IfIndex,
	gponOntOntsideAggGemTCAEnable			INTEGER,
	gponOntOntsideAggGemTCAThresholdLostFragsDown			Threshold,
	gponOntOntsideAggGemTCAThresholdLostFragsUp			Threshold,
	gponOntOntsideAggGemTCAThresholdBadHeadersDown		Threshold
}


gponOntOntsideAggGemTCAThresholdIndex  OBJECT-TYPE
	SYNTAX 	IfIndex
	ACCESS	read-only
	STATUS	mandatory
	DESCRIPTION 
		"This index is the ifIndex of the Ont.

		For ISAM4.0.10 - stays the same as latest FGU4.x  "
	::= { gponOntOntsideAggGemTCAThresholdEntry 1 }


gponOntOntsideAggGemTCAEnable  OBJECT-TYPE
	SYNTAX 	INTEGER
	ACCESS	read-write
	STATUS	mandatory
	DESCRIPTION 
		"Allows the manager to enable/disable the reporting of
		 ONT-side Aggregate GEM TCAs for this ONT. 

	
		  1 = TCA's enabled
		  2 = TCA's disabled

		 Default = 2 = disabled.

		For ISAM4.0.10 - stays the same as latest FGU4.x "
	::= { gponOntOntsideAggGemTCAThresholdEntry 2 }


gponOntOntsideAggGemTCAThresholdLostFragsDown  OBJECT-TYPE
	SYNTAX 	Threshold
	ACCESS	read-write
	STATUS	mandatory
	DESCRIPTION 
		"TCA setting for Lost GEM Fragments (downstream).
		 A value of 4294967295 means that this threshold is disabled.

		 Default = 4294967295

		For ISAM4.0.10 - stays the same as latest FGU4.x  "
	::= { gponOntOntsideAggGemTCAThresholdEntry 3 }

gponOntOntsideAggGemTCAThresholdLostFragsUp  OBJECT-TYPE
	SYNTAX 	Threshold
	ACCESS	read-write
	STATUS	mandatory
	DESCRIPTION 
		"TCA setting for Lost GEM Fragments (upstream).
		 A value of 4294967295 means that this threshold is disabled.

		 Default = 4294967295

		For ISAM4.0.10 - stays the same as latest FGU4.x  "
	::= { gponOntOntsideAggGemTCAThresholdEntry 4 }

gponOntOntsideAggGemTCAThresholdBadHeadersDown  OBJECT-TYPE
	SYNTAX 	Threshold
	ACCESS	read-write
	STATUS	mandatory
	DESCRIPTION 
		"TCA setting for Bad GEM Headers (downstream).
		 A value of 4294967295 means that this threshold is disabled.

		 Default = 4294967295

		For ISAM4.0.10 - stays the same as latest FGU4.x  "
	::= { gponOntOntsideAggGemTCAThresholdEntry 5 }


-- *********************************************
--
-- GPON ONT OLT-SIDE ALWAYS-ON AGGREGATE GEM PERFORMANCE
-- MONITOR CURRENT INTERVAL TABLE
--
-- This is a new table beginning with FGU4.2.
-- This current interval table contains various statistics collected for 
-- aggregate ONT GEM ports (from OLT side of the PON) during the current
-- 15 minute interval of operation.  Statistics include the summation of all
-- GEM ports (excluding the GEM ports associated with OMCI and Multicast).
--
-- An instance of this table is auto-created/deleted in accordance with the 
-- 'OLT-side Aggregate GEM PM Collect Indicator' setting of the ONT Table.
--
-- For ISAM4.0.10, this table is being re-used. 
-- Noted which attributes are relevant for ISAM4.0.10.
--
--	For GPON - SUPPORTED as of ISAM4.0.10
--	For XG-PON1 - SUPPORTED as of ISAM4.6.02
--	For NG-PON2 - SUPPORTED as of ISAM5.2 
-- 
-- *********************************************


gponOntOltsideAggGemCurrentIntervalTable  OBJECT-TYPE
	SYNTAX SEQUENCE OF GponOntOltsideAggGemCurrentIntervalEntry
	ACCESS	not-accessible
	STATUS	mandatory
	::= { bponOntGroup 10 }


gponOntOltsideAggGemCurrentIntervalEntry  OBJECT-TYPE
	SYNTAX 	GponOntOltsideAggGemCurrentIntervalEntry
	ACCESS	not-accessible
	STATUS	mandatory
	DESCRIPTION 
		"An entry in the GPON ONT OLT-side GEM PM
		 Aggregate CurrentInterval Table. "
	INDEX	{ gponOntOltsideAggGemCurrentIntervalIndex }
	::= { gponOntOltsideAggGemCurrentIntervalTable 1 }

GponOntOltsideAggGemCurrentIntervalEntry ::= SEQUENCE {
	gponOntOltsideAggGemCurrentIntervalIndex			IfIndex,
	gponOntOltsideAggGemCurrentIntervalValidInd			Boolean,
	gponOntOltsideAggGemCurrentIntervalErrorFragsUp			Counter

}


gponOntOltsideAggGemCurrentIntervalIndex  OBJECT-TYPE
	SYNTAX 	IfIndex
	ACCESS	read-only
	STATUS	mandatory
	DESCRIPTION 
		"This index is the ifIndex of the Ont.

		For ISAM4.0.10 - stays the same as latest FGU4.x  "
	::= { gponOntOltsideAggGemCurrentIntervalEntry 1 }


gponOntOltsideAggGemCurrentIntervalValidInd  OBJECT-TYPE
	SYNTAX 	Boolean
	ACCESS	read-only
	STATUS	mandatory
	DESCRIPTION 
		"Indicates whether or not this CurrentInterval contains
		 valid PM counts. 

		 As of FGU4.2, NOT SUPPORTED

		For ISAM4.0.10 - stays the same as latest FGU4.x "
	::= { gponOntOltsideAggGemCurrentIntervalEntry 2 }


gponOntOltsideAggGemCurrentIntervalErrorFragsUp  OBJECT-TYPE
	SYNTAX 	Counter
	ACCESS	read-only
	STATUS	mandatory
	DESCRIPTION 
		"A count of Errored GEM Fragments (upstream).

		For ISAM4.0.10 - stays the same as latest FGU4.x "
	::= { gponOntOltsideAggGemCurrentIntervalEntry 3 }


-- *********************************************
--
-- GPON ONT OLT-SIDE ALWAYS-ON AGGREGATE GEM PERFORMANCE  
-- MONITOR INTERVAL TABLE
--
-- This is a new table beginning with FGU4.2.
-- This interval table contains various statistics collected for 
-- aggregate ONT GEM ports (from OLT side of the PON) over the previous
-- 8 hours of operation.  The past 8 hours are broken into 32 completed 15
-- minute intervals. Each row in this table represents one such interval. 
-- Statistics include the summation of all GEM ports (excluding the GEM ports
-- associated with OMCI and Multicast).
--
-- An instance of this table is auto-created/deleted in accordance with the 
-- 'OLT-side Aggregate GEM PM Collect Indicator' setting of the ONT Table.
--
-- For ISAM4.0.10, this table is being re-used. 
-- Noted which attributes are relevant for ISAM4.0.10.
--
--	For GPON - SUPPORTED as of ISAM4.0.10
--	For XG-PON1 - SUPPORTED as of ISAM4.6.02
--	For NG-PON2 - SUPPORTED as of ISAM5.2 
-- 
-- *********************************************


gponOntOltsideAggGemIntervalTable  OBJECT-TYPE
	SYNTAX SEQUENCE OF GponOntOltsideAggGemIntervalEntry
	ACCESS	not-accessible
	STATUS	mandatory
	::= { bponOntGroup 11 }


gponOntOltsideAggGemIntervalEntry  OBJECT-TYPE
	SYNTAX 	GponOntOltsideAggGemIntervalEntry
	ACCESS	not-accessible
	STATUS	mandatory
	DESCRIPTION 
		"An entry in the GPON ONT OLT-side GEM PM
		 Aggregate Interval Table. "
	INDEX	{ gponOntOltsideAggGemIntervalIndex,
		  gponOntOltsideAggGemIntervalNumber }
	::= { gponOntOltsideAggGemIntervalTable 1 }

GponOntOltsideAggGemIntervalEntry ::= SEQUENCE {
	gponOntOltsideAggGemIntervalIndex			IfIndex,
	gponOntOltsideAggGemIntervalNumber		INTEGER,
	gponOntOltsideAggGemIntervalValidInd			Boolean,
	gponOntOltsideAggGemIntervalErrorFragsUp			Counter

}


gponOntOltsideAggGemIntervalIndex  OBJECT-TYPE
	SYNTAX 	IfIndex
	ACCESS	read-only
	STATUS	mandatory
	DESCRIPTION 
		"This index is the ifIndex of the Ont.

		For ISAM4.0.10 - stays the same as latest FGU4.x  "
	::= { gponOntOltsideAggGemIntervalEntry 1 }

gponOntOltsideAggGemIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.

		For ISAM4.0.10 - stays the same as latest FGU4.x  "
	::= { gponOntOltsideAggGemIntervalEntry 2 }


gponOntOltsideAggGemIntervalValidInd  OBJECT-TYPE
	SYNTAX 	Boolean
	ACCESS	read-only
	STATUS	mandatory
	DESCRIPTION 
		"Indicates whether or not this Interval contains
		 valid PM counts. 

		 As of FGU4.2, NOT SUPPORTED

		For ISAM4.0.10 - stays the same as latest FGU4.x "
	::= { gponOntOltsideAggGemIntervalEntry 3 }


gponOntOltsideAggGemIntervalErrorFragsUp  OBJECT-TYPE
	SYNTAX 	Counter
	ACCESS	read-only
	STATUS	mandatory
	DESCRIPTION 
		"A count of Errored GEM Fragments (upstream).

		For ISAM4.0.10 - stays the same as latest FGU4.x "
	::= { gponOntOltsideAggGemIntervalEntry 4 }


-- *********************************************
--
-- GPON ONT OLT-SIDE AGGREGATE GEM PERFORMANCE MONITOR 
-- TCA THRESHOLD TABLE
--
-- This is a new table beginning with FGU4.2.
-- This table allows the manager to set TCA thresholds for various PMs collected for 
-- aggregate ONT GEM ports (from OLT side of the PON) during the current
-- 15 minute interval of operation.
--
-- An instance of this table is auto-created/deleted in accordance with the 
-- 'OLT-side Aggregate GEM PM Collect Indicator' setting of the ONT Table.
--
-- For ISAM4.0.10, this table is being re-used. 
-- Noted which attributes are relevant for ISAM4.0.10.
--
--	For GPON - SUPPORTED as of ISAM4.0.10
--	For XG-PON1 - NOT SUPPORTED as of ISAM4.6.02
--	For NG-PON2 - SUPPORTED as of ISAM5.2 
-- 
-- *********************************************


gponOntOltsideAggGemTCAThresholdTable  OBJECT-TYPE
	SYNTAX SEQUENCE OF GponOntOltsideAggGemTCAThresholdEntry
	ACCESS	not-accessible
	STATUS	mandatory
	::= { bponOntGroup 12 }


gponOntOltsideAggGemTCAThresholdEntry  OBJECT-TYPE
	SYNTAX 	GponOntOltsideAggGemTCAThresholdEntry
	ACCESS	not-accessible
	STATUS	mandatory
	DESCRIPTION 
		"An entry in the GPON ONT OLT-side GEM PM
		 Aggregate TCAThreshold Table. "
	INDEX	{ gponOntOltsideAggGemTCAThresholdIndex }
	::= { gponOntOltsideAggGemTCAThresholdTable 1 }

GponOntOltsideAggGemTCAThresholdEntry ::= SEQUENCE {
	gponOntOltsideAggGemTCAThresholdIndex			IfIndex,
	gponOntOltsideAggGemTCAEnable			INTEGER,
	gponOntOltsideAggGemTCAThresholdErrorFragsUp		Threshold
}


gponOntOltsideAggGemTCAThresholdIndex  OBJECT-TYPE
	SYNTAX 	IfIndex
	ACCESS	read-only
	STATUS	mandatory
	DESCRIPTION 
		"This index is the ifIndex of the Ont.

		For ISAM4.0.10 - stays the same as latest FGU4.x  "
	::= { gponOntOltsideAggGemTCAThresholdEntry 1 }


gponOntOltsideAggGemTCAEnable  OBJECT-TYPE
	SYNTAX 	INTEGER
	ACCESS	read-write
	STATUS	mandatory
	DESCRIPTION 
		"Allows the manager to enable/disable the reporting of
		 OLT-side Aggregate GEM TCAs for this ONT. 

	
		  1 = TCA's enabled
		  2 = TCA's disabled

		 Default = 2 = disabled.

		For ISAM4.0.10 - stays the same as latest FGU4.x "
	::= { gponOntOltsideAggGemTCAThresholdEntry 2 }


gponOntOltsideAggGemTCAThresholdErrorFragsUp  OBJECT-TYPE
	SYNTAX 	Threshold
	ACCESS	read-write
	STATUS	mandatory
	DESCRIPTION 
		"TCA setting for Errored GEM Fragments (upstream).
		 A value of 4294967295 means that this threshold is disabled.

		 Default = 4294967295 

		For ISAM4.0.10 - stays the same as latest FGU4.x "
	::= { gponOntOltsideAggGemTCAThresholdEntry 3 }


-- *********************************************
--
-- GPON ONT ANI TABLE
--
-- This is a new table beginning with FGU4.3. 
--
-- This table contains configuration information 
-- with regard to the ONT ANI for a specific ONT
-- (that is specific to the ANI-G OMCI Managed Entity).
-- The OLT automatically creates/deletes a single row per
-- ONT when the ONT itself is created/deleted (i.e. has a 
-- one-to-one relationship with bponOntTable rows).
--
-- For ISAM4.0.10, this table is being re-used. 
-- Noted which attributes are relevant for ISAM4.0.10. 
-- 
--	For GPON - SUPPORTED as of ISAM4.0.10
--	For XG-PON1 - SUPPORTED as of ISAM4.6.02
--	For NG-PON2 - SUPPORTED as of ISAM5.2 
-- 
-- *********************************************

gponOntAniTable  OBJECT-TYPE
	SYNTAX SEQUENCE OF GponOntAniEntry
	ACCESS	not-accessible
	STATUS	mandatory
	::= { bponOntGroup 13 }

gponOntAniEntry  OBJECT-TYPE
	SYNTAX 	GponOntAniEntry
	ACCESS	not-accessible
	STATUS	mandatory
	INDEX	{ gponOntAniIndex }
	::= { gponOntAniTable 1 }

GponOntAniEntry ::= SEQUENCE {
	gponOntAniIndex			IfIndex,
	gponOntAniLowerOpticalThreshold		INTEGER,
	gponOntAniUpperOpticalThreshold		INTEGER,
	gponOntAniRSSIProfileId		AsamProfileIndexOrZero
}

gponOntAniIndex  OBJECT-TYPE
	SYNTAX 	IfIndex
	ACCESS	read-only
	STATUS	mandatory
	DESCRIPTION 
		"Each row is indexed by the ifIndex of the ONT.

		For ISAM4.0.10 - stays the same as latest FGU4.x  "
	::= { gponOntAniEntry 1 }


gponOntAniLowerOpticalThreshold  OBJECT-TYPE
	SYNTAX 	INTEGER
	ACCESS	read-write
	STATUS	mandatory
	DESCRIPTION 
		" This attribute indicates the optical level the ONT uses to declare the Low received
		   optical power alarm  When the optical level of the received signal drops below this 
		   attribute setting, the ONTANI-OOR Low alarm is generated.  

		   From this GPON MIB perspective, valid values are -127.0 dBm
		   to +0.0 dBm (in 0.5 dB increments) along with a special value. This is represented by the INTEGER range:
		   -254 to +1  -  with interger value +1 meaning use ONT internal policy.

		   From an OMCI perspective, this is an 8-bit field field ranging from -127 dBm (coded as 254)
		   to 0 dBm (coded as 0) in 0.5 dB increments. The OMCI value 0xFF selects the ONT's
		   internal policy.

		   Default =  +1 (meaning - use ONT internal policy)

		For ISAM4.0.10 - stays the same as latest FGU4.x  "
	::= { gponOntAniEntry 2 }


gponOntAniUpperOpticalThreshold  OBJECT-TYPE
	SYNTAX 	INTEGER
	ACCESS	read-write
	STATUS	mandatory
	DESCRIPTION 
		" This attribute indicates the optical level the ONT uses to declare the High received
		   optical power alarm  When the optical level of the received signal raises above this 
		   attribute setting, the ONTANI-OOR High alarm is generated.  

		   From this GPON MIB perspective, valid values are -127.0 dBm
		   to +0.0 dBm (in 0.5 dB increments) along with a special value. This is represented by the INTEGER range:
		   -254 to +1  -  with interger value +1 meaning use ONT internal policy.

		   From an OMCI perspective, this is an 8-bit field field ranging from -127 dBm (coded as 254)
		   to 0 dBm (coded as 0) in 0.5 dB increments. The OMCI value 0xFF selects the ONT's
		   internal policy.

		   Default = +1 (meaning - use ONT internal policy)

		For ISAM4.0.10 - stays the same as latest FGU4.x  "
	::= { gponOntAniEntry 3 }

gponOntAniRSSIProfileId OBJECT-TYPE
       SYNTAX	AsamProfileIndexOrZero 
       ACCESS read-write
       STATUS  mandatory
       DESCRIPTION 

              " Indicates the RSSI TCA profile, refer to SfpRSSIProfileTable (in SFP MIB).
              0 means no profile is selected, gponOntAniLowerOpticalThreshold and gponOntAniUpperOpticalThreshold will be effective.
              If non-zero value is provisioned, thresholds in profile will be effective.

              Prior to ISAM5.3, the range of profile is 0 and 21..200.
	      As of ISAM5.3, the range of profile is 0..200.

		Default = 0

	As of ISAM4.5.02, this attribute is SUPPORTED. "
	::= { gponOntAniEntry 9}



-- *********************************************
--
-- GPON ONT ANI OPERATIONAL INFO TABLE
--
-- This is a new table beginning with FGU4.3. 
--
-- It is used to retrieve operational information regarding
-- an ONT (that is specific to the ANI-G OMCI Managed Entity). 
-- The operational information is significant in that
-- each time it is requested, the OLT issues OMCI GET messages   
-- to obtain the latest information directly from the ONT.
-- A table row is created/deleted automatically by the OLT in a 
-- one-to-one relationship with the GPON ONT ANI TABLE.
--
-- For ISAM4.0.10, this table is being re-used. 
-- Noted which attributes are relevant for ISAM4.0.10.
--
--	For GPON - SUPPORTED as of ISAM4.0.10
--	For XG-PON1 - SUPPORTED as of ISAM4.6.02
--	For NG-PON2 - SUPPORTED as of ISAM5.2 
--  
-- *********************************************

gponOntAniOpInfoTable  OBJECT-TYPE
	SYNTAX SEQUENCE OF GponOntAniOpInfoEntry
	ACCESS	not-accessible
	STATUS	mandatory
	::= { bponOntGroup 14 }

gponOntAniOpInfoEntry  OBJECT-TYPE
	SYNTAX 	GponOntAniOpInfoEntry
	ACCESS	not-accessible
	STATUS	mandatory
	INDEX	{ gponOntAniOpInfoIndex }
	::= { gponOntAniOpInfoTable 1 }

GponOntAniOpInfoEntry ::= SEQUENCE {
	gponOntAniOpInfoIndex			IfIndex,
	gponOntAniOpInfoOpticalSignalLevel		INTEGER,
	gponOntAniOpInfoPowerFeedVoltage		INTEGER,
	gponOntAniOpInfoTxOpticalSignalLevel	INTEGER,
	gponOntAniOpInfoLaserBiasCurrent		INTEGER,
	gponOntAniOpInfoTemperature		INTEGER	
}

gponOntAniOpInfoIndex  OBJECT-TYPE
	SYNTAX 	IfIndex
	ACCESS	read-only
	STATUS	mandatory
	DESCRIPTION 
		"Each row is indexed by the ifIndex of the ONT.

		For ISAM4.0.10 - stays the same as latest FGU4.x  "
	::= { gponOntAniOpInfoEntry 1 }


gponOntAniOpInfoOpticalSignalLevel  OBJECT-TYPE
	SYNTAX 	INTEGER
	ACCESS	read-only
	STATUS	mandatory
	DESCRIPTION 
		" This attribute indicates the current measurement of the total receive optical
		   signal level. 

		   From this GPON MIB perspective, valid values are -65.536 dBm to +65.538 dBm
		   (in 0.002 dB increments).  This is represented by the INTEGER range:
		   -32768 to +32769.  

		   From an OMCI perspective, the attribute is a 16-bit,  2s complement
	                 integer referred to 1 mW (ie in dBm), with 0.002 dB granularity. 		   

		  NOTE: +65.536 Volts (MIB value +32768) means UNKNOWN (because OLT has not yet communicated
		   with ONT for OMCI discovery purposes).  
		  NOTE: +65.538 Volts (MIB value +32769) means that ONT does not support measurement of this attribute.
		  NOTE also that these values cannot ever actually be acquired from the ONT - because 
	                it cannot be represented in a 16-bit, 2s compliment integer. 

		  Default = +65.536 Volts (MIB value +32768) = UNKNOWN (and human display should indicate
		                 the measurement is unknown). 

		  SUPPORTED prior to FGU4.5.5, but extended upper range starting with FGU4.5.5 

		For ISAM4.0.10 - stays the same as latest FGU4.x  "
        ::= { gponOntAniOpInfoEntry 2 }

gponOntAniOpInfoPowerFeedVoltage  OBJECT-TYPE
	SYNTAX 	INTEGER
	ACCESS	read-only
	STATUS	mandatory
	DESCRIPTION 
		" This attribute indicates the power feed voltage for the ONT's optical module. 

		   From this GPON MIB perspective, valid values are -655.36 V to +655.38 V
		   (in 0.02 Volt increments).  This is represented by the INTEGER range:
		   -32768 to +32769.  

		   From an OMCI perspective, the attribute is a 16-bit,  2s complement
	                 integer with 20mV resolution. 		   

		  NOTE: +655.36 Volts (MIB value +32768) means UNKNOWN (because OLT has not yet communicated
		   with ONT for OMCI discovery purposes).  
		  NOTE: +655.38 Volts (MIB value +32769) means that ONT does not support measurement of this attribute.
		  NOTE also that these values cannot ever actually be acquired from the ONT - because 
	                it cannot be represented in a 16-bit, 2s compliment integer.

		  Default = +655.36 Volts (MIB value +32768) = UNKNOWN (and human display should indicate
		                 the measurement is unknown). 

		 SUPPORTED as of FGU4.5.5 

		For ISAM4.0.10 - stays the same as latest FGU4.x "
        ::= { gponOntAniOpInfoEntry 3 }


gponOntAniOpInfoTxOpticalSignalLevel  OBJECT-TYPE
	SYNTAX 	INTEGER
	ACCESS	read-only
	STATUS	mandatory
	DESCRIPTION 
		" This attribute indicates the current measurement of the transmit optical
		   signal level. 

		   From this GPON MIB perspective, valid values are -65.536 dBm to +65.538 dBm
		   (in 0.002 dB increments).  This is represented by the INTEGER range:
		   -32768 to +32769.  

		   From an OMCI perspective, the attribute is a 16-bit,  2s complement
	                 integer referred to 1 mW (ie in dBm), with 0.002 dB granularity. 		   

		  NOTE: +65.536 Volts (MIB value +32768) means UNKNOWN (because OLT has not yet communicated
		   with ONT for OMCI discovery purposes).  
		  NOTE: +65.538 Volts (MIB value +32769) means that ONT does not support measurement of this attribute.
		  NOTE also that these values cannot ever actually be acquired from the ONT - because 
	                it cannot be represented in a 16-bit, 2s compliment integer.

		  Default = +65.536 Volts (MIB value +32768) = UNKNOWN (and human display should indicate
		                 the measurement is unknown).

		For ISAM4.0.10 - stays the same as latest FGU4.x   "
        ::= { gponOntAniOpInfoEntry 4 }


gponOntAniOpInfoLaserBiasCurrent  OBJECT-TYPE
	SYNTAX 	INTEGER
	ACCESS	read-only
	STATUS	mandatory
	DESCRIPTION 
		" This attribute indicates the laser bias current for the ONT's optical module. 

		   From this GPON MIB perspective, valid values are 0 uAmps to +131074 uAmps
		   (in 2uA increments).  This is represented by the INTEGER range:
		   0 to +65537.  

		   From an OMCI perspective, the attribute is a 16-bit, unsigned
	                 integer with 2 uA resolution.		   

		  NOTE: +131072 uAmps (MIB value +65536) means UNKNOWN (because OLT has not yet communicated
		   with ONT for OMCI discovery purposes).  
		  NOTE: +131074 uAmps (MIB value +65537) means that ONT does not support measurement of this attribute.
		  NOTE also that these values cannot ever actually be acquired from the ONT - because 
	                it cannot be represented in a 16-bit, unsigned integer.

		  Default = +131072 uAmps (MIB value +65536) = UNKNOWN (and human display should indicate
		                 the measurement is unknown). 

		 SUPPORTED as of FGU4.5.5

		For ISAM4.0.10 - stays the same as latest FGU4.x  "
        ::= { gponOntAniOpInfoEntry 5 }


gponOntAniOpInfoTemperature  OBJECT-TYPE
	SYNTAX 	INTEGER
	ACCESS	read-only
	STATUS	mandatory
	DESCRIPTION 
		" This attribute indicates the temperature for the ONT's optical module. 

		   From this GPON MIB perspective, valid values are -128.000 degrees C to +128.004 degrees C
		   (in 1/256 degree C increments).  This is represented by the INTEGER range:
		   -32768 to +32769.  

		   From an OMCI perspective, the attribute is a 16-bit,  2s complement
	                 integer with 1/256 degree C resolution. 		   

		  NOTE: +128.000 degrees C (MIB value +32768) means UNKNOWN (because OLT has not yet communicated
		   with ONT for OMCI discovery purposes).  
		  NOTE: +128.004 degrees C (MIB value +32769) means that ONT does not support measurement of this 
		   attribute.
		  NOTE also that these values cannot ever actually be acquired from the ONT - because 
	                 it cannot be represented in a 16-bit, 2s compliment integer.

		  Default = +128.000 degrees C (MIB value +32768) = UNKNOWN (and human display should indicate
		                 the measurement is unknown). 

		 SUPPORTED as of FGU4.5.5 

		For ISAM4.0.10 - stays the same as latest FGU4.x "
        ::= { gponOntAniOpInfoEntry 6 }


-- *********************************************
--
-- GPON ONT NTP TABLE
--
-- This is a new table beginning with FGU4.3.   It is
-- used to establish configuration information for how an ONT
-- should acquire time from an NTP Server network. 
-- Rows are created/deleted automatically by OLT, as a result of 
-- creation/deletion of the ONT itself.
--
-- For ISAM4.0.10, this table is being re-used. 
-- Noted which attributes are relevant for ISAM4.0.10.
--
--	For GPON - SUPPORTED as of ISAM4.0.10
--	For XG-PON1 - SUPPORTED as of ISAM4.6.02
--	For NG-PON2 - NOT SUPPORTED as of ISAM5.2 (since no VoIP is supported)
-- 
-- *********************************************

gponOntNtpTable  OBJECT-TYPE
	SYNTAX SEQUENCE OF GponOntNtpEntry
	ACCESS	not-accessible
	STATUS	mandatory
	::= { bponOntGroup 15 }

gponOntNtpEntry  OBJECT-TYPE
	SYNTAX 	GponOntNtpEntry
	ACCESS	not-accessible
	STATUS	mandatory
	INDEX	{ gponOntNtpIndex }
	::= { gponOntNtpTable 1 }

GponOntNtpEntry ::= SEQUENCE {
	gponOntNtpIndex				IfIndex,
	gponOntNtpClientState			INTEGER,
	gponOntNtpConfigMode			INTEGER,
	gponOntNtpServer1IpAddr			IpAddress,
	gponOntNtpServer2IpAddr			IpAddress,
	gponOntNtpServer3IpAddr			IpAddress,
	gponOntNtpOperMode			INTEGER,
	gponOntNtpKeyIdentifier			INTEGER,
	gponOntNtpKey				OCTET STRING
	
}

gponOntNtpIndex  OBJECT-TYPE
	SYNTAX 	IfIndex
	ACCESS	read-only
	STATUS	mandatory
	DESCRIPTION 
		"Each row is indexed by the ifIndex of the ONT.

		For ISAM4.0.10 - stays the same as latest FGU4.x  "
	::= { gponOntNtpEntry 1 }


gponOntNtpClientState  OBJECT-TYPE
	SYNTAX 	INTEGER
	ACCESS	read-write
	STATUS	mandatory
	DESCRIPTION 
		" Indicates whether NTP Client should be ON or OFF.
		  If OFF, the ONT will not generate any NTP alarms, and
		  the ONT will also clear any NTP alarm that may have been
		  raised previously. 

		  0 = OFF
		  1 = ON

		  Default = 1 = ON

		For ISAM4.0.10 - stays the same as latest FGU4.x   "
	::= { gponOntNtpEntry 2 }

gponOntNtpConfigMode  OBJECT-TYPE 
	SYNTAX	INTEGER
	ACCESS	read-write
	STATUS  mandatory
	DESCRIPTION 
		" Used to designate whether DHCP is designated as the 
  		method by which the ONT obtains NTP server addresses.
		Designating DHCP overrides any manual provisioning. 

 		1 = DHCP
  		2 = Manual
   
 		Default = 1 = DHCP

		For ISAM4.0.10 - stays the same as latest FGU4.x "
::= { gponOntNtpEntry 3 }


gponOntNtpServer1IpAddr  OBJECT-TYPE
	SYNTAX 	IpAddress
	ACCESS	read-write
	STATUS	mandatory
	DESCRIPTION 
		" The manually provisioned IP Address of the
		  1st NTP Server.  NOTE: If DHCP ConfigMode option
		  is enabled, this provisioned attribute will be overriden
		  by the one obtained by the ONT from the DHCP server.
		  This attribute has relevance for UNICAST, MULTICAST
		  and BROADCAST modes of operation. 

		  VALIDATION:  The OLT should prohibit entry of the 
		  following range of IP addresses:
    		  127.0.0.0 to 127.255.255.255   (loopback)

		  Default = 0.0.0.0

		For ISAM4.0.10 - stays the same as latest FGU4.x   "
::= { gponOntNtpEntry 4 }


gponOntNtpServer2IpAddr  OBJECT-TYPE
	SYNTAX 	IpAddress
	ACCESS	read-write
	STATUS	mandatory
	DESCRIPTION 
		" The manually provisioned IP Address of the
		  2nd NTP Server.  NOTE: If DHCP ConfigMode option
		  is enabled, this provisioned attribute will be overriden
		  by the one obtained by the ONT from the DHCP server. 
		  This attribute has relevance only for UNICAST mode of
		  operation.

		  VALIDATION:  The OLT should prohibit entry of the 
		  following range of IP addresses:
    		  127.0.0.0 to 127.255.255.255   (loopback)

		  Default = 0.0.0.0

		For ISAM4.0.10 - stays the same as latest FGU4.x   "
::= { gponOntNtpEntry 5 }


gponOntNtpServer3IpAddr  OBJECT-TYPE
	SYNTAX 	IpAddress
	ACCESS	read-write
	STATUS	mandatory
	DESCRIPTION 
		" The manually provisioned IP Address of the
		  3rd NTP Server.  NOTE: If DHCP ConfigMode option
		  is enabled, this provisioned attribute will be overriden
		  by the one obtained by the ONT from the DHCP server.
		  This attribute has relevance only for UNICAST mode of
		  operation. 

		  VALIDATION:  The OLT should prohibit entry of the 
		  following range of IP addresses:
    		  127.0.0.0 to 127.255.255.255   (loopback) 

		  Default = 0.0.0.0

		For ISAM4.0.10 - stays the same as latest FGU4.x  "
::= { gponOntNtpEntry 6 }


gponOntNtpOperMode  OBJECT-TYPE
	SYNTAX 	INTEGER
	ACCESS	read-write
	STATUS	mandatory
	DESCRIPTION 
		"The NTP Mode of Operation:

		1 = Unicast 
		2 = Multicast
		3 = Broadcast

		Default = 1 = Unicast.

		For ISAM4.0.10 - stays the same as latest FGU4.x   "
::= { gponOntNtpEntry 7 }


gponOntNtpKeyIdentifier OBJECT-TYPE 
	SYNTAX	INTEGER (0..65535)
	ACCESS	read-write
	STATUS  mandatory
	DESCRIPTION 
		" Used to specify the Key that should be used by the NTP server.
   
 		  Default = 0  (meaning the ONT should not use authentication).

		For ISAM4.0.10 - stays the same as latest FGU4.x   "
::= { gponOntNtpEntry 8 }


gponOntNtpKey OBJECT-TYPE 
	SYNTAX	OCTET STRING (SIZE(0..16))
	ACCESS	read-write
	STATUS  mandatory
	DESCRIPTION 
		" Used to specify the actual Key used by the ONT.

		  From an OMCI standpoint, the OLT will as necessary pad out
		  the OMCI message field to fill in the 16 byte field.  From an OMCI
		  standpoint, the OLT must send an OMCI SET for this attribute
		  after sending any OMCI CREATE or SET message that affects
		  the Key Identifier attribute.
   
 		  Default is null value.

		For ISAM4.0.10 - stays the same as latest FGU4.x   "
::= { gponOntNtpEntry 9 }


-- *********************************************
--
-- GPON ONT POWER SHED STATUS INFO TABLE
--
-- This is a new table beginning with FGU4.4.  It is
-- used to retrieve power shedding status information regarding
-- an ONT. The OLT must acquire this information directly from 
-- the ONT (via OMCI).
-- 
-- Rows are created automatically by OLT when the
-- corresponding row is created in the bponOntTable.
--
-- For ISAM4.0.10, this table is being re-used. 
-- Noted which attributes are relevant for ISAM4.0.10.
--
--	For GPON - SUPPORTED as of ISAM4.0.10
--	For XG-PON1 - SUPPORTED as of ISAM4.6.02
--	For NG-PON2 - SUPPORTED as of ISAM5.2 
--  
-- *********************************************

gponOntPwrShedInfoTable  OBJECT-TYPE
	SYNTAX SEQUENCE OF GponOntPwrShedInfoEntry
	ACCESS	not-accessible
	STATUS	mandatory
	::= { bponOntGroup 16 }

gponOntPwrShedInfoEntry  OBJECT-TYPE
	SYNTAX 	GponOntPwrShedInfoEntry
	ACCESS	not-accessible
	STATUS	mandatory
	INDEX	{ gponOntPwrShedInfoIndex }
	::= { gponOntPwrShedInfoTable 1 }

GponOntPwrShedInfoEntry ::= SEQUENCE {
	gponOntPwrShedInfoIndex			IfIndex,
	gponOntPwrShedInfoOntStatus		INTEGER,
	gponOntPwrShedInfoUniClassStatus		OCTET STRING	
}

gponOntPwrShedInfoIndex  OBJECT-TYPE
	SYNTAX 	IfIndex
	ACCESS	read-only
	STATUS	mandatory
	DESCRIPTION 
		"Each row is indexed by the ifIndex of the ONT.

		For ISAM4.0.10 - stays the same as latest FGU4.x   "
	::= { gponOntPwrShedInfoEntry 1 }

gponOntPwrShedInfoOntStatus OBJECT-TYPE
       	SYNTAX       INTEGER
       	ACCESS       read-only
       	STATUS       mandatory
       	DESCRIPTION
           		" This attribute indicates status regarding the whether the OLT has made OMCI
		   protocol contact with the ONT, and if so, whether the ONT supports the OMCI
		   power shed status feature.

		  0 = UNKNOWN (OLT has not yet communicated with ONT).
		  1 = ONT does not support power shedding status feature (known because
		        of some OMCI rejection message).
		  2 = OLT has communicated with ONT and the contents of the
		        gponOntPwrShedInfoUniClassStatus attribute below was aquired
		        directly from the ONT.

		  Default = 0 = UNKNOWN

		For ISAM4.0.10 - stays the same as latest FGU4.x  "
        ::= { gponOntPwrShedInfoEntry 2 }


gponOntPwrShedInfoUniClassStatus OBJECT-TYPE
       	SYNTAX       OCTET STRING (SIZE(2))
       	ACCESS       read-only
       	STATUS       mandatory
       	DESCRIPTION
           		" Attribute provides Boolean indication of power shedding status for each UNI Type 
		  shedding class.  Two byte field formatted ABCD EFGH IJKL MNOP, where
		  A = Data class
		  B = Voice class
		  C = Video overlay class
		  D = Video return class (NOT SUPPORTED - always zero)
		  E = DSL class
		  F = ATM class (NOT SUPPORTED - always zero)
		  G = CES class
		  H = Frame class (NOT SUPPORTED - always zero)
		  I = SONET class (NOT SUPPORTED - always zero)
		  J through P = reserved and set to zero.

		  This attribute maps to the Shedding Status attribute of the ONT Power Shedding
		  OMCI managed Entity.

		  The bit is set when shedding is in effect, and cleared when power is restored.

		 Default = All zeroes = No shedding in effect.

		For ISAM4.0.10 - stays the same as latest FGU4.x  "
        ::= { gponOntPwrShedInfoEntry 3 }


-- *********************************************
--
-- GPON ONT DATA STORAGE STATUS INFO TABLE
--
-- This is a new table beginning with FGU4.4.  It is
-- used to retrieve status information regarding the how the
-- ONT actually handled Data Storage Operations (resulting
-- from the operator setting the  bponOntForceDataStoreCmd
-- attribute in the bponOntTable).
-- 
-- Rows are created automatically by OLT when the
-- corresponding row is created in the bponOntTable.

-- For ISAM4.0.10, this table is being re-used. 
-- Noted which attributes are relevant for ISAM4.0.10.
--
--	For GPON - SUPPORTED as of ISAM4.0.10
--	For XG-PON1 - SUPPORTED as of ISAM4.6.02
--	For NG-PON2 - SUPPORTED as of ISAM5.2 
--  
-- *********************************************

gponOntDataStoreInfoTable  OBJECT-TYPE
	SYNTAX SEQUENCE OF GponOntDataStoreInfoEntry
	ACCESS	not-accessible
	STATUS	mandatory
	::= { bponOntGroup 17 }

gponOntDataStoreInfoEntry  OBJECT-TYPE
	SYNTAX 	GponOntDataStoreInfoEntry
	ACCESS	not-accessible
	STATUS	mandatory
	INDEX	{ gponOntDataStoreInfoIndex }
	::= { gponOntDataStoreInfoTable 1 }

GponOntDataStoreInfoEntry ::= SEQUENCE {
	gponOntDataStoreInfoIndex			IfIndex,
	gponOntDataStoreInfoOntStatus		INTEGER,
	gponOntDataStoreInfoTimeOfLastDump	INTEGER	
}

gponOntDataStoreInfoIndex  OBJECT-TYPE
	SYNTAX 	IfIndex
	ACCESS	read-only
	STATUS	mandatory
	DESCRIPTION 
		"Each row is indexed by the ifIndex of the ONT.

		For ISAM4.0.10 - stays the same as latest FGU4.x  "
	::= { gponOntDataStoreInfoEntry 1 }

gponOntDataStoreInfoOntStatus OBJECT-TYPE
       	SYNTAX       INTEGER
       	ACCESS       read-only
       	STATUS       mandatory
       	DESCRIPTION
           		" This attribute indicates status regarding the whether the OLT has made OMCI
		   protocol contact with the ONT, and if so, whether the ONT supports the OMCI
		   data store 'time of last storage operation' status feature.

		  0 = UNKNOWN (OLT has not yet communicated with ONT).
		  1 = ONT does not support data storage status feature (known because
		        of some OMCI rejection message).
		  2 = OLT has communicated with ONT and the contents of the
		        gponOntDataStoreInfoTimeOfLastDump attribute below was aquired
		        directly from the ONT.

		  Default = 0 = UNKNOWN

		For ISAM4.0.10 - stays the same as latest FGU4.x "
        ::= { gponOntDataStoreInfoEntry 2 }


gponOntDataStoreInfoTimeOfLastDump OBJECT-TYPE
       	SYNTAX       INTEGER (0..4294967295)
       	ACCESS       read-only
       	STATUS       mandatory
       	DESCRIPTION
           		" This attribute should be interpreted as Unix time seconds since midnight January 1,1970). 
		  This attributes represents the time that the ONT last successfully completed a Data Storage
		  Operation (resulting from the operator setting the  bponOntForceDataStoreCmd attribute in 
		  the bponOntTable.

		  This attribute maps to the Time of Last Data Storage Operation attribute of the ONT Generic
		  OMCI Managed Entity.

		 Default = 0 - which could indicate any of the following situations:
			- OLT has not yet communicated with ONT
			- ONT does not support data storage feature
			- ONT indicates that it supports the data storage operation, but
			  has never successfully completed one.

		For ISAM4.0.10 - stays the same as latest FGU4.x "
        ::= { gponOntDataStoreInfoEntry 3 }


-- *********************************************
--
-- GPON ONT OLTSIDE OPERATIONAL INFO TABLE
--
-- This is a new table beginning with FGU4.5.5. 
--
-- It is used to retrieve OLT-SIDE current operational information 
-- regarding an ONT (primarily optical receive levels). 
-- The operational information is significant in that
-- each time it is requested, the OLT directly retrieves   
-- the latest information regarding the ONT.
-- A table row is created/deleted automatically by the OLT in a 
-- one-to-one relationship with the BPON ONT TABLE.
--
-- For ISAM4.0.10, this table is being re-used. 
-- Noted which attributes are relevant for ISAM4.0.10
--
--	For GPON - SUPPORTED as of ISAM4.0.10
--	For XG-PON1 - SUPPORTED as of ISAM4.6.02
--	For NG-PON2 - SUPPORTED as of ISAM5.2 
--  
-- *********************************************

gponOntOltsideOpInfoTable  OBJECT-TYPE
	SYNTAX SEQUENCE OF GponOntOltsideOpInfoEntry
	ACCESS	not-accessible
	STATUS	mandatory
	::= { bponOntGroup 18 }

gponOntOltsideOpInfoEntry  OBJECT-TYPE
	SYNTAX 	GponOntOltsideOpInfoEntry
	ACCESS	not-accessible
	STATUS	mandatory
	INDEX	{ gponOntOltsideOpInfoIndex }
	::= { gponOntOltsideOpInfoTable 1 }

GponOntOltsideOpInfoEntry ::= SEQUENCE {
	gponOntOltsideOpInfoIndex			IfIndex,
	gponOntOltsideOpInfoRxOpticalSignalLevel		INTEGER	
}

gponOntOltsideOpInfoIndex  OBJECT-TYPE
	SYNTAX 	IfIndex
	ACCESS	read-only
	STATUS	mandatory
	DESCRIPTION 
		"Each row is indexed by the ifIndex of the ONT.

		For ISAM4.0.10 - stays the same as latest FGU4.x  "
	::= { gponOntOltsideOpInfoEntry 1 }


gponOntOltsideOpInfoRxOpticalSignalLevel  OBJECT-TYPE
	SYNTAX 	INTEGER
	ACCESS	read-only
	STATUS	mandatory
	DESCRIPTION 
		" This attribute indicates the current level of the ONT's optical signal
		  (as received by and measured at the OLT side). 

		  Units are dBm with 0.1 dBm granularity. 	

		  Valid values are -50.0 dBm to 0.0 dBm, along with the special values 65534 and 65535.  This is 
		  represented by the INTEGER range: -500 to 0, and the special values 65534 and 65535.  

		  NOTE: The special value 65534 is used to indicate INVALID (meaning a valid measurement is currently
			unattainable for some reason). Try again later and might get a valid measurement.
		  NOTE: The special value 65535 is used to indicate NOT SUPPORTED (meaning the measurement
			functionality is not supported by this particular unit). Try again later and will get same answer
			(i.e. NOT SUPPORTED).
		  NOTE: For any actual reading lower or higher than the range, OLT will report the lower or higher limit
			of valid values -500 or 0.

		  Default = 65534 = INVALID 

		For ISAM4.0.10 - stays the same as latest FGU4.x "
        ::= { gponOntOltsideOpInfoEntry 2 }


-- *********************************************
--
-- GPON ONT OPTICAL SUPERVISION DAILY TABLE
--
-- This is a new table beginning with FGU4.6. 
--
-- It is used to store 1 day of optical supervision information regarding
-- an ONT (ONT-side and OLT-side).  Every 24 hours, the data is overwritten
-- with new sample.   
--
-- An instance of this table is auto-created/deleted in accordance with the 
-- 'Optical Supervision Collect Indicator' setting of the ONT Table.
--
-- For ISAM4.0.10, this table is being re-used. 
-- Noted which attributes are relevant for ISAM4.0.10
--
--	For GPON - SUPPORTED as of ISAM4.0.10
--	For XG-PON1 - SUPPORTED as of ISAM4.6.02
--	For NG-PON2 - SUPPORTED as of ISAM5.2 
--  
-- *********************************************

gponOntOpticSupDailyTable  OBJECT-TYPE
	SYNTAX SEQUENCE OF GponOntOpticSupDailyEntry
	ACCESS	not-accessible
	STATUS	mandatory
	::= { bponOntGroup 19 }

gponOntOpticSupDailyEntry  OBJECT-TYPE
	SYNTAX 	GponOntOpticSupDailyEntry
	ACCESS	not-accessible
	STATUS	mandatory
	INDEX	{ gponOntOpticSupDailyIndex,
		  gponOntOpticSupDailyNumber }
	::= { gponOntOpticSupDailyTable 1 }

GponOntOpticSupDailyEntry ::= SEQUENCE {
	gponOntOpticSupDailyIndex			IfIndex,
	gponOntOpticSupDailyNumber		INTEGER,
	gponOntOpticSupDailyTime		INTEGER,
	gponOntOpticSupDailyOntsideRxOpticalSignalLevel		INTEGER,
	gponOntOpticSupDailyOntsidePowerFeedVoltage		INTEGER,
	gponOntOpticSupDailyOntsideTxOpticalSignalLevel	INTEGER,
	gponOntOpticSupDailyOntsideLaserBiasCurrent		INTEGER,
	gponOntOpticSupDailyOntsideTemperature		INTEGER,
	gponOntOpticSupDailyOltsideRxOpticalSignalLevel	INTEGER,
	gponOntOpticSupDailyOltsideTxOpticalSignalLevel	INTEGER,
	gponOntOpticSupDailyOltsideTemperature	INTEGER,
	gponOntOpticSupDailyOltsideVoltage		INTEGER,
	gponOntOpticSupDailyOltsideBiasCurrent		INTEGER	
}

gponOntOpticSupDailyIndex  OBJECT-TYPE
	SYNTAX 	IfIndex
	ACCESS	read-only
	STATUS	mandatory
	DESCRIPTION 
		"Each row is indexed by the ifIndex of the ONT.

		For ISAM4.0.10 - stays the same as latest FGU4.x  "
	::= { gponOntOpticSupDailyEntry 1 }

gponOntOpticSupDailyNumber  OBJECT-TYPE
	SYNTAX 	INTEGER 
	ACCESS	read-only
	STATUS	mandatory
	DESCRIPTION 
		"An index that represents the day.
		 As of FGU4.6, this number is fixed at 1, meaning that only a 
		 single day is stored.

		For ISAM4.0.10 - stays the same as latest FGU4.x  "
	::= { gponOntOpticSupDailyEntry 2 }


gponOntOpticSupDailyTime OBJECT-TYPE
       	SYNTAX       INTEGER (0..4294967295)
       	ACCESS       read-only
       	STATUS       mandatory
       	DESCRIPTION
           		" This attribute should be interpreted as Unix time (seconds since midnight January 1,1970). 
		  This attributes represents the time that the OLT acquired (or attempted to acquire) the data
		  for this row in the table.

		For ISAM4.0.10 - stays the same as latest FGU4.x  "
	::= { gponOntOpticSupDailyEntry 3 }


gponOntOpticSupDailyOntsideRxOpticalSignalLevel  OBJECT-TYPE
	SYNTAX 	INTEGER
	ACCESS	read-only
	STATUS	mandatory
	DESCRIPTION 
		" This attribute indicates the measurement of the total receive optical
		   signal level measured at ONT-side.

		   From this GPON MIB perspective, valid values are -65.536 dBm to +65.538 dBm
		   (in 0.002 dB increments).  This is represented by the INTEGER range:
		   -32768 to +32769.  

		   From an OMCI perspective, the attribute is a 16-bit,  2s complement
	                 integer referred to 1 mW (ie in dBm), with 0.002 dB granularity. 		   

		  NOTE: +65.536 Volts (MIB value +32768) means UNKNOWN (because OLT cannot communicate
		   with ONT for OMCI discovery purposes).  
		  NOTE: +65.538 Volts (MIB value +32769) means that ONT does not support measurement of this attribute.
		  NOTE also that these values cannot ever actually be acquired from the ONT - because 
	                it cannot be represented in a 16-bit, 2s compliment integer.

		For ISAM4.0.10 - stays the same as latest FGU4.x   "
        ::= { gponOntOpticSupDailyEntry 4 }

gponOntOpticSupDailyOntsidePowerFeedVoltage  OBJECT-TYPE
	SYNTAX 	INTEGER
	ACCESS	read-only
	STATUS	mandatory
	DESCRIPTION 
		" This attribute indicates the power feed voltage for the ONT's optical module. 
		   Measured at ONT-side.

		   From this GPON MIB perspective, valid values are -655.36 V to +655.38 V
		   (in 0.02 Volt increments).  This is represented by the INTEGER range:
		   -32768 to +32769.  

		   From an OMCI perspective, the attribute is a 16-bit,  2s complement
	                 integer with 20mV resolution. 		   

		  NOTE: +655.36 Volts (MIB value +32768) means UNKNOWN (because OLT cannot communicate
		   with ONT for OMCI discovery purposes).  
		  NOTE: +655.38 Volts (MIB value +32769) means that ONT does not support measurement of this attribute.
		  NOTE also that these values cannot ever actually be acquired from the ONT - because 
	                it cannot be represented in a 16-bit, 2s compliment integer.

		For ISAM4.0.10 - stays the same as latest FGU4.x  "
        ::= { gponOntOpticSupDailyEntry 5 }


gponOntOpticSupDailyOntsideTxOpticalSignalLevel  OBJECT-TYPE
	SYNTAX 	INTEGER
	ACCESS	read-only
	STATUS	mandatory
	DESCRIPTION 
		" This attribute indicates the measurement of the transmit optical
		   signal level measured at ONT-side.

		   From this GPON MIB perspective, valid values are -65.536 dBm to +65.538 dBm
		   (in 0.002 dB increments).  This is represented by the INTEGER range:
		   -32768 to +32769.  

		   From an OMCI perspective, the attribute is a 16-bit,  2s complement
	                 integer referred to 1 mW (ie in dBm), with 0.002 dB granularity. 		   

		  NOTE: +65.536 Volts (MIB value +32768) means UNKNOWN (because OLT cannot communicate
		   with ONT for OMCI discovery purposes).  
		  NOTE: +65.538 Volts (MIB value +32769) means that ONT does not support measurement of this attribute.
		  NOTE also that these values cannot ever actually be acquired from the ONT - because 
	                it cannot be represented in a 16-bit, 2s compliment integer.

		For ISAM4.0.10 - stays the same as latest FGU4.x    "
        ::= { gponOntOpticSupDailyEntry 6 }


gponOntOpticSupDailyOntsideLaserBiasCurrent  OBJECT-TYPE
	SYNTAX 	INTEGER
	ACCESS	read-only
	STATUS	mandatory
	DESCRIPTION 
		" This attribute indicates the laser bias current for the ONT's optical module. 
		   Measured at ONT-side.

		   From this GPON MIB perspective, valid values are 0 uAmps to +131074 uAmps
		   (in 2uA increments).  This is represented by the INTEGER range:
		   0 to +65537.  

		   From an OMCI perspective, the attribute is a 16-bit, unsigned
	                 integer with 2 uA resolution.		   

		  NOTE: +131072 uAmps (MIB value +65536) means UNKNOWN (because OLT cannot communicate
		   with ONT for OMCI discovery purposes).  
		  NOTE: +131074 uAmps (MIB value +65537) means that ONT does not support measurement of this attribute.
		  NOTE also that these values cannot ever actually be acquired from the ONT - because 
	                it cannot be represented in a 16-bit, unsigned integer.

		For ISAM4.0.10 - stays the same as latest FGU4.x   "
        ::= { gponOntOpticSupDailyEntry 7 }


gponOntOpticSupDailyOntsideTemperature  OBJECT-TYPE
	SYNTAX 	INTEGER
	ACCESS	read-only
	STATUS	mandatory
	DESCRIPTION 
		" This attribute indicates the temperature for the ONT's optical module. 
		   Measured at ONT-side.

		   From this GPON MIB perspective, valid values are -128.000 degrees C to +128.004 degrees C
		   (in 1/256 degree C increments).  This is represented by the INTEGER range:
		   -32768 to +32769.  

		   From an OMCI perspective, the attribute is a 16-bit,  2s complement
	                 integer with 1/256 degree C resolution. 		   

		  NOTE: +128.000 degrees C (MIB value +32768) means UNKNOWN (because OLT cannot communicate
		   with ONT for OMCI discovery purposes).  
		  NOTE: +128.004 degrees C (MIB value +32769) means that ONT does not support measurement of this 
		   attribute.
		  NOTE also that these values cannot ever actually be acquired from the ONT - because 
	                 it cannot be represented in a 16-bit, 2s compliment integer. 

		For ISAM4.0.10 - stays the same as latest FGU4.x  "
        ::= { gponOntOpticSupDailyEntry 8 }

gponOntOpticSupDailyOltsideRxOpticalSignalLevel  OBJECT-TYPE
	SYNTAX 	INTEGER
	ACCESS	read-only
	STATUS	mandatory
	DESCRIPTION 
		" This attribute indicates the current level of the ONT's optical signal
		  (as received by and measured at the OLT side). 

		  Units are dBm with 0.1 dBm granularity. 	

		  Valid values are -50.0 dBm to 0.0 dBm, along with the special values 65534 and 65535.  This is 
		  represented by the INTEGER range: -500 to 0, and the special values 65534 and 65535.  

		  NOTE: The special value 65534 is used to indicate INVALID (meaning a valid measurement is currently
			unattainable for some reason). Try again later and might get a valid measurement.
		  NOTE: The special value 65535 is used to indicate NOT SUPPORTED (meaning the measurement
			functionality is not supported by this particular unit). Try again later and will get same answer
			(i.e. NOT SUPPORTED).
		  NOTE: For any actual reading lower or higher than the range, OLT will report the lower or higher limit
			of valid values -500 or 0. 

		For ISAM4.0.10 - stays the same as latest FGU4.x   "
        ::= { gponOntOpticSupDailyEntry 9 }

gponOntOpticSupDailyOltsideTxOpticalSignalLevel  OBJECT-TYPE
	SYNTAX 	INTEGER
	ACCESS	read-only
	STATUS	mandatory
	DESCRIPTION 
		" This attribute indicates the current level of the OLT's transmit optical signal
		  (as measured at the OLT side for this PON). 

		  Units are dBm with 0.1 dBm granularity. 	

		  Valid values are -30.0 dBm to +30.0 dBm, along with the special values 65534 and 65535.  This is 
		  represented by the INTEGER range: -300 to +300, and the special values 65534 and 65535.  

		  NOTE: The special value 65534 is used to indicate INVALID (meaning a valid measurement is currently
			unattainable for some reason). Try again later and might get a valid measurement.
		  NOTE: The special value 65535 is used to indicate NOT SUPPORTED (meaning the measurement
			functionality is not supported by this particular unit). Try again later and will get same answer
			(i.e. NOT SUPPORTED).
		  NOTE: For any actual reading lower or higher than the range, OLT will report the lower or higher limit
			of valid values -300 or +300.

		For ISAM4.0.10 - stays the same as latest FGU4.x   "
        ::= { gponOntOpticSupDailyEntry 10 }

gponOntOpticSupDailyOltsideTemperature  OBJECT-TYPE
	SYNTAX 	INTEGER
	ACCESS	read-only
	STATUS	mandatory
	DESCRIPTION 
		" This attribute indicates the current temperature of the optics module associated with this PON
		  (as measured at the OLT side for this PON). 

		  Units are degrees centigrade (C) with 0.01 C granularity. 	

		  Valid values are -100.00 C to +100.00 C, along with the special values 65534 and 65535.  This is 
		  represented by the INTEGER range: -10,000 to +10,000, and the special values 65534 and 65535.  

		  NOTE: The special value 65534 is used to indicate INVALID (meaning a valid measurement is currently
			unattainable for some reason). Try again later and might get a valid measurement.
		  NOTE: The special value 65535 is used to indicate NOT SUPPORTED (meaning the measurement
			functionality is not supported by this particular unit). Try again later and will get same answer
			(i.e. NOT SUPPORTED).
		  NOTE: For any actual reading lower or higher than the range, OLT will report the lower or higher limit
			of valid values -10,000 or +10,000.

		For ISAM4.0.10 - stays the same as latest FGU4.x   "
        ::= { gponOntOpticSupDailyEntry 11 }


gponOntOpticSupDailyOltsideVoltage  OBJECT-TYPE
	SYNTAX 	INTEGER
	ACCESS	read-only
	STATUS	mandatory
	DESCRIPTION 
		" This attribute indicates the current voltage of the optics module associated with this PON
		  (as measured at the OLT side for this PON). 

		  Units are Volts (V) with 0.01 V granularity. 	

		  Valid values are 0 V to +20.00, along with the special values 65534 and 65535.  This is 
		  represented by the INTEGER range:  0 to +2000, and the special values 65534 and 65535.  

		  NOTE: The special value 65534 is used to indicate INVALID (meaning a valid measurement is currently
			unattainable for some reason). Try again later and might get a valid measurement.
		  NOTE: The special value 65535 is used to indicate NOT SUPPORTED (meaning the measurement
			functionality is not supported by this particular unit). Try again later and will get same answer
			(i.e. NOT SUPPORTED).
		  NOTE: For any actual reading lower or higher than the range, OLT will report the lower or higher limit
			of valid values 0 or +2000.

		For ISAM4.0.10 - stays the same as latest FGU4.x   "
        ::= { gponOntOpticSupDailyEntry 12 }

gponOntOpticSupDailyOltsideBiasCurrent  OBJECT-TYPE
	SYNTAX 	INTEGER
	ACCESS	read-only
	STATUS	mandatory
	DESCRIPTION 
		" This attribute indicates the current bias current of the laser associated with this PON
		  (as measured at the OLT side for this PON). 

		  Units are milliamps (mA) with 1 mA granularity. 	

		  Valid values are 0 mA to +500 mA, along with the special values 65534 and 65535.  This is 
		  represented by the INTEGER range:  0 to +500, and the special values 65534 and 65535.  

		  NOTE: The special value 65534 is used to indicate INVALID (meaning a valid measurement is currently
			unattainable for some reason). Try again later and might get a valid measurement.
		  NOTE: The special value 65535 is used to indicate NOT SUPPORTED (meaning the measurement
			functionality is not supported by this particular unit). Try again later and will get same answer
			(i.e. NOT SUPPORTED).
		  NOTE: For any actual reading lower or higher than the range, OLT will report the lower or higher limit
			of valid values 0 or +500.

		For ISAM4.0.10 - stays the same as latest FGU4.x   "
        ::= { gponOntOpticSupDailyEntry 13 }


-- *********************************************
--
-- GPON ONT-SIDE DOWNSTREAM FEC PERFORMANCE MONITOR CURRENT INTERVAL TABLE
--
-- This table was first introduced with ISAM4.2 MIB.
-- It is only SUPPORTED beginning with ISAM4.2.02 release.
--
-- This current interval table contains various downstream ONT-side FEC counters (for a specific ONT) during the current
-- 15 minute interval of operation.  
--
-- An instance of this table is auto-created/deleted in accordance with the 
-- 'FEC PM Collect Indicator' setting of the ONT Table.
--
-- For GETs of table attributes, the OLT must go directly to the ONT (via OMCI)
-- in order to acquire fresh current counts. 
--
--	For GPON - SUPPORTED as of ISAM4.2.02
--	For XG-PON1 - SUPPORTED as of ISAM4.6.02
--	For NG-PON2 - SUPPORTED as of ISAM5.2 
--
-- 
-- *********************************************


gponOntFecCurrentIntervalTable  OBJECT-TYPE
	SYNTAX SEQUENCE OF GponOntFecCurrentIntervalEntry
	ACCESS	not-accessible
	STATUS	mandatory
	::= { bponOntGroup 21 }


gponOntFecCurrentIntervalEntry  OBJECT-TYPE
	SYNTAX 	GponOntFecCurrentIntervalEntry
	ACCESS	not-accessible
	STATUS	mandatory
	DESCRIPTION 
		"An entry in the GPON ONT FEC CurrentInterval Table. "
	INDEX	{ gponOntFecCurrentIntervalIndex }
	::= { gponOntFecCurrentIntervalTable 1 }

GponOntFecCurrentIntervalEntry ::= SEQUENCE {
	gponOntFecCurrentIntervalIndex			IfIndex,
	gponOntFecCurrentIntervalValidInd			Boolean,
	gponOntFecCurrentIntervalCorrectedBytes			Counter,
	gponOntFecCurrentIntervalCorrectedCodeWords			Counter,
	gponOntFecCurrentIntervalUncorrectedCodeWords		Counter,
	gponOntFecCurrentIntervalTotalCodeWords		Counter,
	gponOntFecCurrentIntervalFecSeconds		Counter
}


gponOntFecCurrentIntervalIndex  OBJECT-TYPE
	SYNTAX 	IfIndex
	ACCESS	read-only
	STATUS	mandatory
	DESCRIPTION 
		"This index is the ifIndex of the Ont.  "
	::= { gponOntFecCurrentIntervalEntry 1 }


gponOntFecCurrentIntervalValidInd  OBJECT-TYPE
	SYNTAX 	Boolean
	ACCESS	read-only
	STATUS	mandatory
	DESCRIPTION 
		"Indicates whether or not this CurrentInterval contains
		 valid PM counts.

		 As of ISAM4.2, NOT SUPPORTED  "
	::= { gponOntFecCurrentIntervalEntry 2 }


gponOntFecCurrentIntervalCorrectedBytes  OBJECT-TYPE
	SYNTAX 	Counter
	ACCESS	read-only
	STATUS	mandatory
	DESCRIPTION 
		"A count of number of bytes that were corrected by the FEC function.  "
	::= { gponOntFecCurrentIntervalEntry 3 }

gponOntFecCurrentIntervalCorrectedCodeWords  OBJECT-TYPE
	SYNTAX 	Counter
	ACCESS	read-only
	STATUS	mandatory
	DESCRIPTION 
		"A count of number of code words that were corrected by the FEC function.  "
	::= { gponOntFecCurrentIntervalEntry 4 }

gponOntFecCurrentIntervalUncorrectedCodeWords  OBJECT-TYPE
	SYNTAX 	Counter
	ACCESS	read-only
	STATUS	mandatory
	DESCRIPTION 
		"A count of number of errored code words that could not be corrected by the FEC function.  "
	::= { gponOntFecCurrentIntervalEntry 5 }

gponOntFecCurrentIntervalTotalCodeWords  OBJECT-TYPE
	SYNTAX 	Counter
	ACCESS	read-only
	STATUS	mandatory
	DESCRIPTION 
		"A count of total number of received code words.  "
	::= { gponOntFecCurrentIntervalEntry 6 }

gponOntFecCurrentIntervalFecSeconds  OBJECT-TYPE
	SYNTAX 	Counter
	ACCESS	read-only
	STATUS	mandatory
	DESCRIPTION 
		"A count seconds during which there was a forward error correction anomaly.  "
	::= { gponOntFecCurrentIntervalEntry 7 }


-- *********************************************
--
-- GPON ONT-SIDE DOWNSTREAM FEC PERFORMANCE MONITOR INTERVAL TABLE
--
-- This table was first introduced with ISAM4.2 MIB.
-- It is NOT SUPPORTED as of ISAM4.2.02 release.
--
-- This interval table contains various FEC counters collected over the previous
-- 8 hours of operation.  The past 8 hours are broken into 32 completed 15
-- minute intervals. Each row in this table represents one such interval.  
--
-- An instance of this table is auto-created/deleted in accordance with the 
-- 'FEC PM Collect Indicator' setting of the ONT Table.
--
-- As of ISAM4.4.02, this table is NOT SUPPORTED.
--
--	For GPON - NOT SUPPORTED as of ISAM4.2.02
--	For XG-PON1 - NOT SUPPORTED as of ISAM4.6.02
--	For NG-PON2 - NOT SUPPORTED as of ISAM5.2 
-- 
-- *********************************************


gponOntFecIntervalTable  OBJECT-TYPE
	SYNTAX SEQUENCE OF GponOntFecIntervalEntry
	ACCESS	not-accessible
	STATUS	mandatory
	::= { bponOntGroup 22 }


gponOntFecIntervalEntry  OBJECT-TYPE
	SYNTAX 	GponOntFecIntervalEntry
	ACCESS	not-accessible
	STATUS	mandatory
	DESCRIPTION 
		"An entry in the GPON ONT FEC Interval Table. "
	INDEX	{ gponOntFecIntervalIndex,
		    gponOntFecIntervalNumber }
	::= { gponOntFecIntervalTable 1 }

GponOntFecIntervalEntry ::= SEQUENCE {
	gponOntFecIntervalIndex			IfIndex,
	gponOntFecIntervalNumber			INTEGER,
	gponOntFecIntervalValidInd			Boolean,
	gponOntFecIntervalCorrectedBytes			Counter,
	gponOntFecIntervalCorrectedCodeWords			Counter,
	gponOntFecIntervalUncorrectedCodeWords		Counter,
	gponOntFecIntervalTotalCodeWords		Counter,
	gponOntFecIntervalFecSeconds		Counter
}


gponOntFecIntervalIndex  OBJECT-TYPE
	SYNTAX 	IfIndex
	ACCESS	read-only
	STATUS	mandatory
	DESCRIPTION 
		"This index is the ifIndex of the Ont.  "
	::= { gponOntFecIntervalEntry 1 }

gponOntFecIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.

		For ISAM4.0.10 - stays the same as latest FGU4.x  "
	::= { gponOntFecIntervalEntry 2 }


gponOntFecIntervalValidInd  OBJECT-TYPE
	SYNTAX 	Boolean
	ACCESS	read-only
	STATUS	mandatory
	DESCRIPTION 
		"Indicates whether or not this CurrentInterval contains
		 valid PM counts.

		 As of ISAM4.2, NOT SUPPORTED  "
	::= { gponOntFecIntervalEntry 3 }


gponOntFecIntervalCorrectedBytes  OBJECT-TYPE
	SYNTAX 	Counter
	ACCESS	read-only
	STATUS	mandatory
	DESCRIPTION 
		"A count of number of bytes that were corrected by the FEC function.  "
	::= { gponOntFecIntervalEntry 4 }

gponOntFecIntervalCorrectedCodeWords  OBJECT-TYPE
	SYNTAX 	Counter
	ACCESS	read-only
	STATUS	mandatory
	DESCRIPTION 
		"A count of number of code words that were corrected by the FEC function.  "
	::= { gponOntFecIntervalEntry 5 }

gponOntFecIntervalUncorrectedCodeWords  OBJECT-TYPE
	SYNTAX 	Counter
	ACCESS	read-only
	STATUS	mandatory
	DESCRIPTION 
		"A count of number of errored code words that could not be corrected by the FEC function.  "
	::= { gponOntFecIntervalEntry 6 }

gponOntFecIntervalTotalCodeWords  OBJECT-TYPE
	SYNTAX 	Counter
	ACCESS	read-only
	STATUS	mandatory
	DESCRIPTION 
		"A count of total number of received code words.  "
	::= { gponOntFecIntervalEntry 7 }

gponOntFecIntervalFecSeconds  OBJECT-TYPE
	SYNTAX 	Counter
	ACCESS	read-only
	STATUS	mandatory
	DESCRIPTION 
		"A count seconds during which there was a forward error correction anomaly.  "
	::= { gponOntFecIntervalEntry 8 }


-- *********************************************
--
-- GPON ONT EQUIPMENT EXTENSIONS TABLE
--
-- This is a new table beginning with ISAM4.2.02.   It is
-- used to configure optional ONT equipment extensions.
-- From an OMCI standpoint, it maps primarily to the 
-- Equipment Extensions Package ME.
--
-- Rows are created/deleted automatically by OLT, as a result of 
-- creation/deletion of the ONT itself.
--
-- As of ISAM4.2.02, this table is NOT SUPPORTED.
--
--	For GPON - NOT SUPPORTED as of ISAM4.2.02
--	For XG-PON1 - NOT SUPPORTED as of ISAM4.6.02
--	For NG-PON2 - NOT SUPPORTED as of ISAM5.2
-- 
-- *********************************************

gponOntEquipExtenTable  OBJECT-TYPE
	SYNTAX SEQUENCE OF GponOntEquipExtenEntry
	ACCESS	not-accessible
	STATUS	mandatory
	::= { bponOntGroup 23 }

gponOntEquipExtenEntry  OBJECT-TYPE
	SYNTAX 	GponOntEquipExtenEntry
	ACCESS	not-accessible
	STATUS	mandatory
	INDEX	{ gponOntEquipExtenIndex }
	::= { gponOntEquipExtenTable 1 }

GponOntEquipExtenEntry ::= SEQUENCE {
	gponOntEquipExtenIndex				IfIndex,
	gponOntEquipExtenContactClosureOutput		OCTET STRING	
}

gponOntEquipExtenIndex  OBJECT-TYPE
	SYNTAX 	IfIndex
	ACCESS	read-only
	STATUS	mandatory
	DESCRIPTION 
		"Each row is indexed by the ifIndex of the ONT.  "
	::= { gponOntEquipExtenEntry 1 }


gponOntEquipExtenContactClosureOutput  OBJECT-TYPE
	SYNTAX 	OCTET STRING (SIZE(2))
	ACCESS	read-write
	STATUS	mandatory
	DESCRIPTION 
		" Provisions an ONT that supports external contact closure outputs, for example
		  sump pump or air conditioner activation ant an ONT enclosure.  A contact point is said
		  to be released when it is not energized.  Whether this corresponds to an open or closed 
		  electrical circuit depends on the ONT's wiring options.

 		  This is a bitmap where Bit 1 = LSB and Bit 16 = MSB.  The 8 least significant
		  bits map indirectly to the OMCI attribute (i.e. contact closure output).  The 8
		  most significant are unused, and must be set to 0.

		  Bit meanings are as follows:

		  Bit 1 -	0 means release contact point 8.
			1 means operate contact point 8.
		  Bit 2 -	0 means release contact point 7.
			1 means operate contact point 7.
		  Bit 3 -	0 means release contact point 6.
			1 means operate contact point 6.
		  Bit 4 -	0 means release contact point 5.
			1 means operate contact point 5.
		  Bit 5 -	0 means release contact point 4.
			1 means operate contact point 4.
		  Bit 6 -	0 means release contact point 3.
			1 means operate contact point 3.
		  Bit 7 -	0 means release contact point 2.
			1 means operate contact point 2.
		  Bit 8 -	0 means release contact point 1.
			1 means operate contact point 1.
		  Bits 9..16 - not used, must be set to 0.

		  Default = all bits zero (i.e. all contact points released.  "
	::= { gponOntEquipExtenEntry 2 }


-- *********************************************
--
-- GPON ONT EQUIPMENT EXTENSIONS INFO TABLE
--
-- This is a new table beginning with ISAM4.2.02.   It is
-- used to retrieve optional ONT equipment extensions information
-- directly from the ONT.
-- From an OMCI standpoint, it maps primarily to the 
-- Equipment Extensions Package ME.
-- 
-- Rows are created automatically by OLT when the
-- corresponding row is created in the bponOntTable.
--
-- As of ISAM4.2.02, this table is NOT SUPPORTED.
--
--	For GPON - NOT SUPPORTED as of ISAM4.2.02
--	For XG-PON1 - NOT SUPPORTED as of ISAM4.6.02
--	For NG-PON2 - NOT SUPPORTED as of ISAM5.2
--  
-- *********************************************

gponOntEquipExtenInfoTable  OBJECT-TYPE
	SYNTAX SEQUENCE OF GponOntEquipExtenInfoEntry
	ACCESS	not-accessible
	STATUS	mandatory
	::= { bponOntGroup 24 }

gponOntEquipExtenInfoEntry  OBJECT-TYPE
	SYNTAX 	GponOntEquipExtenInfoEntry
	ACCESS	not-accessible
	STATUS	mandatory
	INDEX	{ gponOntEquipExtenInfoIndex }
	::= { gponOntEquipExtenInfoTable 1 }

GponOntEquipExtenInfoEntry ::= SEQUENCE {
	gponOntEquipExtenInfoIndex			IfIndex,
	gponOntEquipExtenInfoContactClosure	OCTET STRING	
}

gponOntEquipExtenInfoIndex  OBJECT-TYPE
	SYNTAX 	IfIndex
	ACCESS	read-only
	STATUS	mandatory
	DESCRIPTION 
		"Each row is indexed by the ifIndex of the ONT.   "
	::= { gponOntEquipExtenInfoEntry 1 }


gponOntEquipExtenInfoContactClosure OBJECT-TYPE
	SYNTAX 	OCTET STRING (SIZE(2))
	ACCESS	read-only
	STATUS	mandatory
	DESCRIPTION 
		" Indicates the status of the contact closures supported by this ONT.
		  This is a bitmap where Bit 1 = LSB and Bit 16= MSB.  The 8 least significant
		  bits map indirectly to OMCI attribute (i.e. contact closure output).  The 8
		  most significant bits are populated by the OLT agent to convey extra information
		  for the manager (for user interface).

		  Bit meanings are as follows:
		  Bit 1 -	0 means contact point 8 is released.
			1 means contact point 8 is operated.
		  Bit 2 -	0 means contact point 7 is released.
			1 means contact point 7 is operated.
		  Bit 3 -	0 means contact point 6 is released.
			1 means contact point 6 is operated.
		  Bit 4 -	0 means contact point 5 is released.
			1 means contact point 5 is operated.
		  Bit 5 -	0 means contact point 4 is released.
			1 means contact point 4 is operated.
		  Bit 6 -	0 means contact point 3 is released.
			1 means contact point 3 is operated.
		  Bit 7 -	0 means contact point 2 is released.
			1 means contact point 2 is operated.
		  Bit 8 -	0 means contact point 1 is released.
			1 means contact point 1 is operated.
		  Bit 9 -	0 means this response came directly from the ONT
			1 means UNKNOWN (because OLT cannot communicate with ONT for OMCI discovery purposes).
		  Bit 10 -	0 means ONT supports GET of this attribute
			1 means that ONT does NOT support GET of this attribute.
		  Bits 11..16 - no meaning in ISAM4.2 (ignore)  

		  Default = all bits zero except Bit 9 equals 1 (i.e. UNKNOWN). "
        ::= { gponOntEquipExtenInfoEntry 2 }

-- *********************************************
--
-- GPON ONT SUMMARY INFO TABLE
--
-- This is a new table beginning with ISAM4.2. 
--
-- It is used to retrieve various service summary information for a specific ONT.
--
-- A table row is created/deleted automatically by the OLT in a 
-- one-to-one relationship with the bponOntTable.
--
-- Support was descoped, so table is NOT SUPPORTED.
--
--	For GPON - NOT SUPPORTED as of ISAM4.2
--	For XG-PON1 - NOT SUPPORTED as of ISAM4.6.02
--	For NG-PON2 - NOT SUPPORTED as of ISAM5.2
--  
-- *********************************************

gponOntSummaryInfoTable  OBJECT-TYPE
	SYNTAX SEQUENCE OF GponOntSummaryInfoEntry
	ACCESS	not-accessible
	STATUS	mandatory
	::= { bponOntGroup 25 }

gponOntSummaryInfoEntry  OBJECT-TYPE
	SYNTAX 	GponOntSummaryInfoEntry
	ACCESS	not-accessible
	STATUS	mandatory
	INDEX	{ gponOntSummaryInfoIndex }
	::= { gponOntSummaryInfoTable 1 }

GponOntSummaryInfoEntry ::= SEQUENCE {
	gponOntSummaryInfoIndex			IfIndex,
	gponOntSummaryInfoServices		OCTET STRING	
}

gponOntSummaryInfoIndex  OBJECT-TYPE
	SYNTAX 	IfIndex
	ACCESS	read-only
	STATUS	mandatory
	DESCRIPTION 
		"Each row is indexed by the ifIndex of the ONT. "
	::= { gponOntSummaryInfoEntry 1 }

gponOntSummaryInfoServices OBJECT-TYPE
       	SYNTAX       OCTET STRING (SIZE(20)) 
       	ACCESS       read-only
       	STATUS       mandatory
       	DESCRIPTION
           		" This attribute summarizes whether certain service types are provisioned on an ONT.

		  This is a bytesmap/bitmap where Byte 1 implies Most Significant Byte, and Bit 1 implies 
		  Most Significant Bit (of the relevant byte).  

		  Byte/Bit meanings are as follows:

		Byte 1 - Bit 1:
			Value 0 means:  No data services provisioned on this ONT.
			Value 1 means:  At least 1 data service is provisioned on this ONT.
		Byte 1 - Bits 2 through 5:
			Reserved for future use - should be set to 0 by OLT.
		Byte 1 - Bit 6:
			Value 0 means:  No data services provisioned on VEIP UNIs.
			Value 1 means:  At least 1 data service is provisioned on some VEIP UNI.
		Byte 1 - Bit 7:
			Value 0 means:  No data services provisioned on Ethernet UNIs.
			Value 1 means:  At least 1 data service is provisioned on some Ethernet UNI.
		Byte 1 - Bit 8:
			Value 0 means:  No data services provisioned on XDSL UNIs.
			Value 1 means:  At least 1 data service is provisioned on some XDSL UNI.
		Byte 2 - all Bits:
			Reserved for future use - should be set to 0 by OLT.
		Byte 3 - Bit 1:
			Value 0 means:  No Voice services provisioned on this ONT.
			Value 1 means:  At least 1 voice service is provisioned on this ONT.
		Byte 3 - Bits 2 through 8:
			Reserved for future use - should be set to 0 by OLT.
		Byte 4 - all Bits:
			Reserved for future use - should be set to 0 by OLT.
		Byte 5 - Bit 1:
			Value 0 means:  No CES services provisioned on this ONT.
			Value 1 means:  At least 1 CES service is provisioned on this ONT.
		Byte 5 - Bits 2 through 8:
			Reserved for future use - should be set to 0 by OLT.
		Byte 6 - all Bits:
			Reserved for future use - should be set to 0 by OLT.
		Byte 7 - Bit 1:
			Value 0 means:  No RF Video service provisioned on this ONT.
			Value 1 means:  At least one RF Video service is provisioned on this ONT.
		Byte 7 - Bits 2 through 8:
			Reserved for future use - should be set to 0 by OLT.
		Byte 8 - all Bits:
			Reserved for future use - should be set to 0 by OLT.
		Bytes 9 through 20 - all Bits
			Reserved for future use - should be set to 0 by OLT. 

		Default - all bits of all bytes = 0. "
        ::= { gponOntSummaryInfoEntry 2 }



-- *********************************************
--
-- GPON ONT ONT-SIDE PON AGGREGATE ETHERNET PERFORMANCE MONITOR 
-- CURRENT INTERVAL TABLE
--
-- This is a new table beginning with ISAM R4.5
-- This current interval table contains statistics collected for 
-- Ethernet traffic (from ONT side of the PON) during the current
-- 15 minute interval of operation.  Statistics include the summation of all
-- Ethernet traffic.
--
-- An instance of this table is auto-created/deleted in accordance with the 
-- 'ONT-side PON Aggregate Ethernet PM Collect Indicator' setting of the ONT Table.
--
-- For GETs of table attributes, the OLT must go directly to the ONT (via OMCI)
-- in order to acquire fresh current counts. 
--
--	For GPON - SUPPORTED as of ISAM4.5
--	For XG-PON1 - SUPPORTED as of ISAM4.6.02
--	For NG-PON2 - SUPPORTED as of ISAM5.2
--
-- *********************************************

gponOntOntsidePonAggEtherCurrentIntervalTable  OBJECT-TYPE
    SYNTAX SEQUENCE OF GponOntOntsidePonAggEtherCurrentIntervalEntry
    ACCESS    not-accessible
    STATUS    mandatory
    ::= { bponOntGroup 26 }

gponOntOntsidePonAggEtherCurrentIntervalEntry  OBJECT-TYPE
    SYNTAX    GponOntOntsidePonAggEtherCurrentIntervalEntry
    ACCESS    not-accessible
    STATUS    mandatory
    DESCRIPTION
        "An entry in the GPON ONT ONT-side PON Aggregate
         ETHERNET PM CurrentInterval Table. "
    INDEX    { gponOntOntsidePonAggEtherCurrentIntervalIndex }
    ::= { gponOntOntsidePonAggEtherCurrentIntervalTable 1 }

GponOntOntsidePonAggEtherCurrentIntervalEntry ::= SEQUENCE {
    gponOntOntsidePonAggEtherCurrentIntervalIndex        IfIndex,
    gponOntOntsidePonAggEtherCurrentIntervalValidInd     Boolean,
    gponOntOntsidePonAggEtherCurrentIntervalDownErrors   Counter,
    gponOntOntsidePonAggEtherCurrentIntervalUpErrors  Counter,
	gponOntOntsidePonAggEtherCurrentIntervalTxFramesUnicast	OCTET STRING (SIZE (8)),
	gponOntOntsidePonAggEtherCurrentIntervalRxFramesUnicast	OCTET STRING (SIZE (8)),
	gponOntOntsidePonAggEtherCurrentIntervalTxFramesMulticast	OCTET STRING (SIZE (8)),
	gponOntOntsidePonAggEtherCurrentIntervalRxFramesMulticast	OCTET STRING (SIZE (8)),
	gponOntOntsidePonAggEtherCurrentIntervalTxFramesBroadcast	OCTET STRING (SIZE (8)),
	gponOntOntsidePonAggEtherCurrentIntervalRxFramesBroadcast	OCTET STRING (SIZE (8)),
	gponOntOntsidePonAggEtherCurrentIntervalTxFrames		OCTET STRING (SIZE (8)),
	gponOntOntsidePonAggEtherCurrentIntervalRxFrames		OCTET STRING (SIZE (8)),
	gponOntOntsidePonAggEtherCurrentIntervalTxBytes		OCTET STRING (SIZE (8)),
	gponOntOntsidePonAggEtherCurrentIntervalRxBytes		OCTET STRING (SIZE (8)),
	gponOntOntsidePonAggEtherCurrentIntervalTxRate		OCTET STRING (SIZE (8)),
	gponOntOntsidePonAggEtherCurrentIntervalRxRate		OCTET STRING (SIZE (8))
}

gponOntOntsidePonAggEtherCurrentIntervalIndex  OBJECT-TYPE
    SYNTAX    IfIndex
    ACCESS    read-only
    STATUS    mandatory
    DESCRIPTION
        "This index is the ifIndex of the Ont"

    ::= { gponOntOntsidePonAggEtherCurrentIntervalEntry 1 }

gponOntOntsidePonAggEtherCurrentIntervalValidInd  OBJECT-TYPE
	SYNTAX 	Boolean
	ACCESS	read-only
	STATUS	mandatory
	DESCRIPTION 
		"Indicates whether or not this CurrentInterval contains
		 valid PM counts. 

		 As of ISAM4.5, NOT SUPPORTED.  "
    ::= { gponOntOntsidePonAggEtherCurrentIntervalEntry 2 }

gponOntOntsidePonAggEtherCurrentIntervalDownErrors  OBJECT-TYPE
    SYNTAX    Counter
    ACCESS    read-only
    STATUS    mandatory
    DESCRIPTION 
        "Indicates the sum of the Ethernet error statistics
        caused due to:
           1) CRC Align Errors
           2) Fragments
           3) Jabbers
           4) Collisions
         in the downstream direction."

    ::= { gponOntOntsidePonAggEtherCurrentIntervalEntry 3 }

gponOntOntsidePonAggEtherCurrentIntervalUpErrors  OBJECT-TYPE
    SYNTAX    Counter
    ACCESS    read-only
    STATUS    mandatory
    DESCRIPTION
        "Indicates the sum of the Ethernet error statistics
        caused due to:
           1) CRC Align Errors
           2) Fragments
           3) Jabbers
           4) Collisions
         in the upstream direction."

    ::= { gponOntOntsidePonAggEtherCurrentIntervalEntry 4 }

gponOntOntsidePonAggEtherCurrentIntervalTxFramesUnicast OBJECT-TYPE
	SYNTAX	OCTET STRING (SIZE (8))
    	ACCESS    read-only
    	STATUS    mandatory
    	DESCRIPTION
       	 "Indicates the number of transmitted Unicast Ethernet Frames
	As of ISAM5.0 -> SUPPORTED. "

    ::= { gponOntOntsidePonAggEtherCurrentIntervalEntry 5 }

gponOntOntsidePonAggEtherCurrentIntervalRxFramesUnicast OBJECT-TYPE
	SYNTAX	OCTET STRING (SIZE (8))
    	ACCESS    read-only
    	STATUS    mandatory
    	DESCRIPTION
        "Indicates the number of received Unicast Ethernet Frames
	As of ISAM5.0 -> SUPPORTED. "

    ::= { gponOntOntsidePonAggEtherCurrentIntervalEntry 6 }

gponOntOntsidePonAggEtherCurrentIntervalTxFramesMulticast OBJECT-TYPE
	SYNTAX	OCTET STRING (SIZE (8))
    	ACCESS    read-only
    	STATUS    mandatory
    	DESCRIPTION
        "Indicates the number of transmitted Multicast Ethernet Frames
	As of ISAM5.0 -> SUPPORTED. "

    ::= { gponOntOntsidePonAggEtherCurrentIntervalEntry 7 }

gponOntOntsidePonAggEtherCurrentIntervalRxFramesMulticast OBJECT-TYPE
	SYNTAX	OCTET STRING (SIZE (8))
    	ACCESS    read-only
    	STATUS    mandatory
    	DESCRIPTION
        "Indicates the number of received Multicast Ethernet Frames
	As of ISAM5.0 -> SUPPORTED. "

    ::= { gponOntOntsidePonAggEtherCurrentIntervalEntry 8 }

gponOntOntsidePonAggEtherCurrentIntervalTxFramesBroadcast OBJECT-TYPE
	SYNTAX	OCTET STRING (SIZE (8))
    	ACCESS    read-only
    	STATUS    mandatory
    	DESCRIPTION
        "Indicates the number of transmitted Broadcast Ethernet Frames
	As of ISAM5.0 -> SUPPORTED. "

    ::= { gponOntOntsidePonAggEtherCurrentIntervalEntry 9 }

gponOntOntsidePonAggEtherCurrentIntervalRxFramesBroadcast OBJECT-TYPE
	SYNTAX	OCTET STRING (SIZE (8))
    	ACCESS    read-only
    	STATUS    mandatory
    	DESCRIPTION
        "Indicates the number of received Broadcast Ethernet Frames
	As of ISAM5.0 -> SUPPORTED. "

    ::= { gponOntOntsidePonAggEtherCurrentIntervalEntry 10 }

gponOntOntsidePonAggEtherCurrentIntervalTxFrames OBJECT-TYPE
	SYNTAX	OCTET STRING (SIZE (8))
    	ACCESS    read-only
    	STATUS    mandatory
    	DESCRIPTION
        "Indicates the total number of transmitted Ethernet Frames
	As of ISAM5.0 -> SUPPORTED. "

    ::= { gponOntOntsidePonAggEtherCurrentIntervalEntry 11 }

gponOntOntsidePonAggEtherCurrentIntervalRxFrames OBJECT-TYPE
	SYNTAX	OCTET STRING (SIZE (8))
    	ACCESS    read-only
    	STATUS    mandatory
    	DESCRIPTION
        "Indicates the total number of received Ethernet Frames
	As of ISAM5.0 -> SUPPORTED. "

    ::= { gponOntOntsidePonAggEtherCurrentIntervalEntry 12 }

gponOntOntsidePonAggEtherCurrentIntervalTxBytes OBJECT-TYPE
	SYNTAX	OCTET STRING (SIZE (8))
    	ACCESS    read-only
    	STATUS    mandatory
    	DESCRIPTION
        "Indicates the total number of transmitted Ethernet Bytes
	As of ISAM5.0 -> SUPPORTED. "

    ::= { gponOntOntsidePonAggEtherCurrentIntervalEntry 13 }

gponOntOntsidePonAggEtherCurrentIntervalRxBytes OBJECT-TYPE
	SYNTAX	OCTET STRING (SIZE (8))
    	ACCESS    read-only
    	STATUS    mandatory
    	DESCRIPTION
        "Indicates the total number of received Ethernet Bytes
	As of ISAM5.0 -> SUPPORTED. "

::= { gponOntOntsidePonAggEtherCurrentIntervalEntry 14 }


gponOntOntsidePonAggEtherCurrentIntervalTxRate OBJECT-TYPE
	SYNTAX	OCTET STRING (SIZE (8))
    	ACCESS    read-only
    	STATUS    mandatory
    	DESCRIPTION
        "Indicates present traffic rate of upstream in units of bps
	As of ISAM5.0 -> SUPPORTED. "

    ::= { gponOntOntsidePonAggEtherCurrentIntervalEntry 15 }

gponOntOntsidePonAggEtherCurrentIntervalRxRate OBJECT-TYPE
	SYNTAX	OCTET STRING (SIZE (8))
    	ACCESS    read-only
    	STATUS    mandatory
    	DESCRIPTION
        " Indicates present traffic rate of downstream in units of bps
	As of ISAM5.0 -> SUPPORTED. "

::= { gponOntOntsidePonAggEtherCurrentIntervalEntry 16 }


-- *********************************************
--
-- GPON ONT ONT-SIDE PON AGGREGATE ETHERNET PERFORMANCE MONITOR 
-- CURRENT INTERVAL TABLE
--
-- This is a new table beginning with ISAM R4.5
-- This interval table contains statistics collected for 
-- Ethernet traffic (from ONT side of the PON) over the previous
-- 8 hours of operation.  The past 8 hours are broken into 32 completed 15
-- minute intervals. Each row in this table represents one such interval. 
-- Statistics include the summation of all Ethernet traffic.
--
-- An instance of this table is auto-created/deleted in accordance with the 
-- 'ONT-side PON Aggregate Ethernet PM Collect Indicator' setting of the ONT Table.
--
--	For GPON - SUPPORTED as of ISAM4.5
--	For XG-PON1 - SUPPORTED as of ISAM4.6.02
--	For NG-PON2 - SUPPORTED as of ISAM5.2
--
-- *********************************************

gponOntOntsidePonAggEtherIntervalTable  OBJECT-TYPE
    SYNTAX SEQUENCE OF GponOntOntsidePonAggEtherIntervalEntry
    ACCESS    not-accessible
    STATUS    mandatory
    ::= { bponOntGroup 27 }

gponOntOntsidePonAggEtherIntervalEntry  OBJECT-TYPE
    SYNTAX    GponOntOntsidePonAggEtherIntervalEntry
    ACCESS    not-accessible
    STATUS    mandatory
    DESCRIPTION 
        "An entry in the GPON ONT ONT-side PON Aggregate
         ETHERNET PM Interval Table. "
    INDEX    { gponOntOntsidePonAggEtherIntervalIndex,
               gponOntOntsidePonAggEtherIntervalNumber }
    ::= { gponOntOntsidePonAggEtherIntervalTable 1 }

GponOntOntsidePonAggEtherIntervalEntry ::= SEQUENCE {
    gponOntOntsidePonAggEtherIntervalIndex        IfIndex,
    gponOntOntsidePonAggEtherIntervalNumber       INTEGER,
    gponOntOntsidePonAggEtherIntervalValidInd     Boolean,       
    gponOntOntsidePonAggEtherIntervalDownErrors   Counter,
    gponOntOntsidePonAggEtherIntervalUpErrors  Counter,
	gponOntOntsidePonAggEtherIntervalTxFramesUnicast	OCTET STRING (SIZE (8)),
	gponOntOntsidePonAggEtherIntervalRxFramesUnicast	OCTET STRING (SIZE (8)),
	gponOntOntsidePonAggEtherIntervalTxFramesMulticast	OCTET STRING (SIZE (8)),
	gponOntOntsidePonAggEtherIntervalRxFramesMulticast	OCTET STRING (SIZE (8)),
	gponOntOntsidePonAggEtherIntervalTxFramesBroadcast	OCTET STRING (SIZE (8)),
	gponOntOntsidePonAggEtherIntervalRxFramesBroadcast	OCTET STRING (SIZE (8)),
	gponOntOntsidePonAggEtherIntervalTxFrames	OCTET STRING (SIZE (8)),
	gponOntOntsidePonAggEtherIntervalRxFrames	OCTET STRING (SIZE (8)),
	gponOntOntsidePonAggEtherIntervalTxBytes	OCTET STRING (SIZE (8)),
	gponOntOntsidePonAggEtherIntervalRxBytes	OCTET STRING (SIZE (8)),
	gponOntOntsidePonAggEtherIntervalTxRate		OCTET STRING (SIZE (8)),
	gponOntOntsidePonAggEtherIntervalRxRate		OCTET STRING (SIZE (8))
}


gponOntOntsidePonAggEtherIntervalIndex  OBJECT-TYPE
    SYNTAX    IfIndex
    ACCESS    read-only
    STATUS    mandatory
    DESCRIPTION
        "This index is the ifIndex of the Ont"

    ::= { gponOntOntsidePonAggEtherIntervalEntry 1 }


gponOntOntsidePonAggEtherIntervalNumber  OBJECT-TYPE
    SYNTAX    INTEGER (1..32)
    ACCESS    read-only
    STATUS    mandatory
    DESCRIPTION
        "A number between 1 and 32, where 1 is the most
         recently completed 15 minute interval and 32
         is the 15 minute interval completed 7 hours 
         and 45 minutes prior to interval 1."

    ::= { gponOntOntsidePonAggEtherIntervalEntry 2 }

gponOntOntsidePonAggEtherIntervalValidInd OBJECT-TYPE
	SYNTAX 	Boolean
	ACCESS	read-only
	STATUS	mandatory
	DESCRIPTION 
		"Indicates whether or not this Interval contains
		 valid PM counts. 

		 As of ISAM4.5, NOT SUPPORTED.  "
    ::= { gponOntOntsidePonAggEtherIntervalEntry 3 }

gponOntOntsidePonAggEtherIntervalDownErrors  OBJECT-TYPE
    SYNTAX    Counter
    ACCESS    read-only
    STATUS    mandatory
    DESCRIPTION
        "Indicates the sum of the Ethernet error statistics
        caused due to:
           1) CRC Align Errors
           2) Fragments
           3) Jabbers
           4) Collisions
         in the downstream direction."

    ::= { gponOntOntsidePonAggEtherIntervalEntry 4 }


gponOntOntsidePonAggEtherIntervalUpErrors  OBJECT-TYPE
    SYNTAX    Counter
    ACCESS    read-only
    STATUS    mandatory
    DESCRIPTION 
        "Indicates the sum of the Ethernet error statistics
        caused due to:
           1) CRC Align Errors
           2) Fragments
           3) Jabbers
           4) Collisions
         in the upstream direction."

    ::= { gponOntOntsidePonAggEtherIntervalEntry 5 }

gponOntOntsidePonAggEtherIntervalTxFramesUnicast OBJECT-TYPE
	SYNTAX	OCTET STRING (SIZE (8))
    	ACCESS    read-only
    	STATUS    mandatory
    	DESCRIPTION
        "Indicates the number of transmitted Unicast Ethernet Frames
	As of ISAM5.0 -> SUPPORTED. "

    ::= { gponOntOntsidePonAggEtherIntervalEntry 6 }

gponOntOntsidePonAggEtherIntervalRxFramesUnicast OBJECT-TYPE
	SYNTAX	OCTET STRING (SIZE (8))
    	ACCESS    read-only
    	STATUS    mandatory
    	DESCRIPTION
        "Indicates the number of received Unicast Ethernet Frames
	As of ISAM5.0 -> SUPPORTED. "

    ::= { gponOntOntsidePonAggEtherIntervalEntry 7 }

gponOntOntsidePonAggEtherIntervalTxFramesMulticast OBJECT-TYPE
	SYNTAX	OCTET STRING (SIZE (8))
    	ACCESS    read-only
    	STATUS    mandatory
   	 DESCRIPTION
        "Indicates the number of transmitted Multicast Ethernet Frames
	As of ISAM5.0 -> SUPPORTED. "

    ::= { gponOntOntsidePonAggEtherIntervalEntry 8 }

gponOntOntsidePonAggEtherIntervalRxFramesMulticast OBJECT-TYPE
	SYNTAX	OCTET STRING (SIZE (8))
    	ACCESS    read-only
    	STATUS    mandatory
    	DESCRIPTION
        "Indicates the number of received Multicast Ethernet Frames
	As of ISAM5.0 -> SUPPORTED. "

    ::= { gponOntOntsidePonAggEtherIntervalEntry 9 }

gponOntOntsidePonAggEtherIntervalTxFramesBroadcast OBJECT-TYPE
	SYNTAX	OCTET STRING (SIZE (8))
    	ACCESS    read-only
    	STATUS    mandatory
    	DESCRIPTION
        "Indicates the number of transmitted Broadcast Ethernet Frames
	As of ISAM5.0 -> SUPPORTED. "

    ::= { gponOntOntsidePonAggEtherIntervalEntry 10 }

gponOntOntsidePonAggEtherIntervalRxFramesBroadcast OBJECT-TYPE
	SYNTAX	OCTET STRING (SIZE (8))
    	ACCESS    read-only
    	STATUS    mandatory
    	DESCRIPTION
        "Indicates the number of received Broadcast Ethernet Frames
	As of ISAM5.0 -> SUPPORTED. "

    ::= { gponOntOntsidePonAggEtherIntervalEntry 11 }

gponOntOntsidePonAggEtherIntervalTxFrames OBJECT-TYPE
	SYNTAX	OCTET STRING (SIZE (8))
    	ACCESS    read-only
    	STATUS    mandatory
    	DESCRIPTION
        "Indicates the total number of transmitted Ethernet Frames
	As of ISAM5.0 -> SUPPORTED. "

    ::= { gponOntOntsidePonAggEtherIntervalEntry 12 }

gponOntOntsidePonAggEtherIntervalRxFrames OBJECT-TYPE
	SYNTAX	OCTET STRING (SIZE (8))
    	ACCESS    read-only
    	STATUS    mandatory
    	DESCRIPTION
        "Indicates the total number of received Ethernet Frames
	As of ISAM5.0 -> SUPPORTED. "

    ::= { gponOntOntsidePonAggEtherIntervalEntry 13 }

gponOntOntsidePonAggEtherIntervalTxBytes OBJECT-TYPE
	SYNTAX	OCTET STRING (SIZE (8))
    	ACCESS    read-only
    	STATUS    mandatory
    	DESCRIPTION
        "Indicates the total number of transmitted Ethernet Bytes
	As of ISAM5.0 -> SUPPORTED. "

    ::= { gponOntOntsidePonAggEtherIntervalEntry 14 }

gponOntOntsidePonAggEtherIntervalRxBytes OBJECT-TYPE
	SYNTAX	OCTET STRING (SIZE (8))
    	ACCESS    read-only
    	STATUS    mandatory
    	DESCRIPTION
        "Indicates the total number of received Ethernet Bytes
	As of ISAM5.0 -> SUPPORTED. "

::= { gponOntOntsidePonAggEtherIntervalEntry 15 }


gponOntOntsidePonAggEtherIntervalTxRate OBJECT-TYPE
	SYNTAX	OCTET STRING (SIZE (8))
    	ACCESS    read-only
    	STATUS    mandatory
    	DESCRIPTION
        "Indicates the average traffic rate in this interval of upstream in units of bps
	As of ISAM5.0 -> SUPPORTED. "

    ::= { gponOntOntsidePonAggEtherIntervalEntry 16 }

gponOntOntsidePonAggEtherIntervalRxRate OBJECT-TYPE
	SYNTAX	OCTET STRING (SIZE (8))
    	ACCESS    read-only
    	STATUS    mandatory
    	DESCRIPTION
        " Indicates the average traffic rate in this interval of downstream in units of bps
	As of ISAM5.0 -> SUPPORTED. "

::= { gponOntOntsidePonAggEtherIntervalEntry 17 }



-- *********************************************
--
-- GPON ONT LOOP DETECT TABLE
--
-- This table was added to ISAM4.5 MIB (and SUPPORTED as of  ISAM4.6).
-- It is used to configure 'loop detection' features for ONTs which support such feature.
-- 
-- Rows are created/deleted automatically by OLT when the
-- corresponding row is created/deleted in the bponOntTable.
--
--	For GPON - SUPPORTED as of ISAM4.5
--	For XG-PON1 - SUPPORTED as of ISAM4.6.02
--	For NG-PON2 - NOT SUPPORTED as of ISAM5.2
--
--  
-- *********************************************

gponOntLoopDetectTable  OBJECT-TYPE
	SYNTAX SEQUENCE OF GponOntLoopDetectEntry
	ACCESS	not-accessible
	STATUS	mandatory
	::= { bponOntGroup 28 }

gponOntLoopDetectEntry  OBJECT-TYPE
	SYNTAX 	GponOntLoopDetectEntry
	ACCESS	not-accessible
	STATUS	mandatory
	INDEX	{ gponOntLoopDetectIndex }
	::= { gponOntLoopDetectTable 1 }

GponOntLoopDetectEntry ::= SEQUENCE {
	gponOntLoopDetectIndex			IfIndex,
	gponOntLoopDetectAdminState		INTEGER,
	gponOntLoopDetectAutoShutoff		INTEGER	
}

gponOntLoopDetectIndex  OBJECT-TYPE
	SYNTAX 	IfIndex
	ACCESS	read-only
	STATUS	mandatory
	DESCRIPTION 
		" Each row is indexed by the ifIndex of the ONT.   "
	::= { gponOntLoopDetectEntry 1 }

gponOntLoopDetectAdminState OBJECT-TYPE
 	SYNTAX 	INTEGER 
	ACCESS	read-write
	STATUS	mandatory
	DESCRIPTION 
		" This object is used to enable/disable loop detection on applicable ONT LAN ports.

		0 = nocontrol (meaning ONT is not expected to support loop detection function, so OMCI is suppressed).
		      When set to 0 = nocontrol, all other attributes of table are ignored by system.
		1 = disable
		2 = enable

		Default = 0 = nocontrol 

		Modification is permitted.

		As of ISAM4.6, attribute is SUPPORTED. "

        ::= { gponOntLoopDetectEntry 2 }


gponOntLoopDetectAutoShutoff OBJECT-TYPE
 	SYNTAX 	INTEGER 
	ACCESS	read-write
	STATUS	mandatory
	DESCRIPTION 
		" This object is used to enable/disable whether applicable ONT LAN ports should automatically 
		  shut down upon detection of loop.

		0 = disable
		1 = enable

		Default = 1 = enable

		As of ISAM4.6, attribute is SUPPORTED. "

        ::= { gponOntLoopDetectEntry 3 }


-- *********************************************
--
-- GPON ONT OLTSIDE UPSTREAM FEC PERFORMANCE MONITOR CURRENT INTERVAL TABLE
--
-- This table was first introduced with ISAM4.6 MIB.
-- It is only SUPPORTED beginning with ISAM4.6.01 release (only for XGPON).
--
-- This current interval table contains various OLT-side Upstream FEC counters (for a specific ONT) during the current
-- 15 minute interval of operation.  
--
-- An instance of this table is auto-created/deleted in accordance with the 
-- 'OLT-side UP FEC PM Collect Indicator' setting of the ONT Table.
--
--	For GPON - NOT SUPPORTED as of ISAM4.0.10
--	For XG-PON1 - SUPPORTED as of ISAM4.6.02
--	For NG-PON2 - SUPPORTED as of ISAM5.2
--
-- 
-- *********************************************


gponOntOltsideFecCurrentIntervalTable  OBJECT-TYPE
	SYNTAX SEQUENCE OF GponOntOltsideFecCurrentIntervalEntry
	ACCESS	not-accessible
	STATUS	mandatory
	::= { bponOntGroup 29 }


gponOntOltsideFecCurrentIntervalEntry  OBJECT-TYPE
	SYNTAX 	GponOntOltsideFecCurrentIntervalEntry
	ACCESS	not-accessible
	STATUS	mandatory
	DESCRIPTION 
		"An entry in the GPON ONT OLT-side FEC CurrentInterval Table. "
	INDEX	{ gponOntOltsideFecCurrentIntervalIndex }
	::= { gponOntOltsideFecCurrentIntervalTable 1 }

GponOntOltsideFecCurrentIntervalEntry ::= SEQUENCE {
	gponOntOltsideFecCurrentIntervalIndex			IfIndex,
	gponOntOltsideFecCurrentIntervalValidInd			Boolean,
	gponOntOltsideFecCurrentIntervalCorrectedBytes			Counter,
	gponOntOltsideFecCurrentIntervalCorrectedCodeWords			Counter,
	gponOntOltsideFecCurrentIntervalUncorrectedCodeWords		Counter,
	gponOntOltsideFecCurrentIntervalTotalCodeWords		Counter
}


gponOntOltsideFecCurrentIntervalIndex  OBJECT-TYPE
	SYNTAX 	IfIndex
	ACCESS	read-only
	STATUS	mandatory
	DESCRIPTION 
		"This index is the ifIndex of the Ont.  "
	::= { gponOntOltsideFecCurrentIntervalEntry 1 }


gponOntOltsideFecCurrentIntervalValidInd  OBJECT-TYPE
	SYNTAX 	Boolean
	ACCESS	read-only
	STATUS	mandatory
	DESCRIPTION 
		"Indicates whether or not this CurrentInterval contains
		 valid PM counts.

		 NOT SUPPORTED  "
	::= { gponOntOltsideFecCurrentIntervalEntry 2 }


gponOntOltsideFecCurrentIntervalCorrectedBytes  OBJECT-TYPE
	SYNTAX 	Counter
	ACCESS	read-only
	STATUS	mandatory
	DESCRIPTION 
		"A count of number of bytes that were corrected by the FEC function.  "
	::= { gponOntOltsideFecCurrentIntervalEntry 3 }

gponOntOltsideFecCurrentIntervalCorrectedCodeWords  OBJECT-TYPE
	SYNTAX 	Counter
	ACCESS	read-only
	STATUS	mandatory
	DESCRIPTION 
		"A count of number of code words that were corrected by the FEC function.  "
	::= { gponOntOltsideFecCurrentIntervalEntry 4 }

gponOntOltsideFecCurrentIntervalUncorrectedCodeWords  OBJECT-TYPE
	SYNTAX 	Counter
	ACCESS	read-only
	STATUS	mandatory
	DESCRIPTION 
		"A count of number of errored code words that could not be corrected by the FEC function.  "
	::= { gponOntOltsideFecCurrentIntervalEntry 5 }

gponOntOltsideFecCurrentIntervalTotalCodeWords  OBJECT-TYPE
	SYNTAX 	Counter
	ACCESS	read-only
	STATUS	mandatory
	DESCRIPTION 
		"A count of total number of received code words.  "
	::= { gponOntOltsideFecCurrentIntervalEntry 6 }



-- *********************************************
--
-- GPON ONT OLTSIDE UPSTREAM FEC PERFORMANCE MONITOR INTERVAL TABLE
--
-- This table was first introduced with ISAM4.6 MIB.
--
-- This interval table contains various FEC counters collected over the previous
-- 8 hours of operation.  The past 8 hours are broken into 32 completed 15
-- minute intervals. Each row in this table represents one such interval.  
--
-- An instance of this table is auto-created/deleted in accordance with the 
-- 'OLT-side UP FEC PM Collect Indicator' setting of the ONT Table.
--
-- As of ISAM4.6, this table is NOT SUPPORTED.
--
--	For GPON - NOT SUPPORTED as of ISAM4.6
--	For XG-PON1 - NOT SUPPORTED as of ISAM4.6.02
--	For NG-PON2 - NOT SUPPORTED as of ISAM5.2
-- 
-- *********************************************


gponOntOltsideFecIntervalTable  OBJECT-TYPE
	SYNTAX SEQUENCE OF GponOntOltsideFecIntervalEntry
	ACCESS	not-accessible
	STATUS	mandatory
	::= { bponOntGroup 30 }


gponOntOltsideFecIntervalEntry  OBJECT-TYPE
	SYNTAX 	GponOntOltsideFecIntervalEntry
	ACCESS	not-accessible
	STATUS	mandatory
	DESCRIPTION 
		"An entry in the GPON ONT OLT-side FEC Interval Table. "
	INDEX	{ gponOntOltsideFecIntervalIndex,
		    gponOntOltsideFecIntervalNumber }
	::= { gponOntOltsideFecIntervalTable 1 }

GponOntOltsideFecIntervalEntry ::= SEQUENCE {
	gponOntOltsideFecIntervalIndex			IfIndex,
	gponOntOltsideFecIntervalNumber			INTEGER,
	gponOntOltsideFecIntervalValidInd			Boolean,
	gponOntOltsideFecIntervalCorrectedBytes			Counter,
	gponOntOltsideFecIntervalCorrectedCodeWords			Counter,
	gponOntOltsideFecIntervalUncorrectedCodeWords		Counter,
	gponOntOltsideFecIntervalTotalCodeWords		Counter
}


gponOntOltsideFecIntervalIndex  OBJECT-TYPE
	SYNTAX 	IfIndex
	ACCESS	read-only
	STATUS	mandatory
	DESCRIPTION 
		"This index is the ifIndex of the Ont.  "
	::= { gponOntOltsideFecIntervalEntry 1 }

gponOntOltsideFecIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.  "
	::= { gponOntOltsideFecIntervalEntry 2 }


gponOntOltsideFecIntervalValidInd  OBJECT-TYPE
	SYNTAX 	Boolean
	ACCESS	read-only
	STATUS	mandatory
	DESCRIPTION 
		"Indicates whether or not this CurrentInterval contains
		 valid PM counts.

		 NOT SUPPORTED  "
	::= { gponOntOltsideFecIntervalEntry 3 }


gponOntOltsideFecIntervalCorrectedBytes  OBJECT-TYPE
	SYNTAX 	Counter
	ACCESS	read-only
	STATUS	mandatory
	DESCRIPTION 
		"A count of number of bytes that were corrected by the FEC function.  "
	::= { gponOntOltsideFecIntervalEntry 4 }

gponOntOltsideFecIntervalCorrectedCodeWords  OBJECT-TYPE
	SYNTAX 	Counter
	ACCESS	read-only
	STATUS	mandatory
	DESCRIPTION 
		"A count of number of code words that were corrected by the FEC function.  "
	::= { gponOntOltsideFecIntervalEntry 5 }

gponOntOltsideFecIntervalUncorrectedCodeWords  OBJECT-TYPE
	SYNTAX 	Counter
	ACCESS	read-only
	STATUS	mandatory
	DESCRIPTION 
		"A count of number of errored code words that could not be corrected by the FEC function.  "
	::= { gponOntOltsideFecIntervalEntry 6 }

gponOntOltsideFecIntervalTotalCodeWords  OBJECT-TYPE
	SYNTAX 	Counter
	ACCESS	read-only
	STATUS	mandatory
	DESCRIPTION 
		"A count of total number of received code words.  "
	::= { gponOntOltsideFecIntervalEntry 7 }


-- *********************************************
--
-- GPON ONT OLTSIDE PHYSICAL LAYER  PERFORMANCE MONITOR CURRENT INTERVAL TABLE
--
-- This table was first introduced with ISAM4.6 MIB.
-- It is only SUPPORTED beginning with ISAM4.6.01 release (only for XGPON).
--
-- This current interval table contains various OLT-side PHY counters (for a specific ONT) during the current
-- 15 minute interval of operation.  
--
-- An instance of this table is auto-created/deleted in accordance with the 
-- 'OLT-side Phy Layer PM Collect Indicator' setting of the ONT Table.
--
--	For GPON - NOT SUPPORTED as of ISAM4.6
--	For XG-PON1 - SUPPORTED as of ISAM4.6.02
--	For NG-PON2 - SUPPORTED as of ISAM5.2
-- 
-- *********************************************


gponOntOltsidePhyCurrentIntervalTable  OBJECT-TYPE
	SYNTAX SEQUENCE OF GponOntOltsidePhyCurrentIntervalEntry
	ACCESS	not-accessible
	STATUS	mandatory
	::= { bponOntGroup 31 }


gponOntOltsidePhyCurrentIntervalEntry  OBJECT-TYPE
	SYNTAX 	GponOntOltsidePhyCurrentIntervalEntry
	ACCESS	not-accessible
	STATUS	mandatory
	DESCRIPTION 
		"An entry in the GPON ONT OLT-side Phy CurrentInterval Table. "
	INDEX	{ gponOntOltsidePhyCurrentIntervalIndex }
	::= { gponOntOltsidePhyCurrentIntervalTable 1 }

GponOntOltsidePhyCurrentIntervalEntry ::= SEQUENCE {
	gponOntOltsidePhyCurrentIntervalIndex			IfIndex,
	gponOntOltsidePhyCurrentIntervalValidInd			Boolean,
	gponOntOltsidePhyCurrentIntervalUpBip32ProtWords		OCTET STRING,
	gponOntOltsidePhyCurrentIntervalUpBip32BitErrors		OCTET STRING
}


gponOntOltsidePhyCurrentIntervalIndex  OBJECT-TYPE
	SYNTAX 	IfIndex
	ACCESS	read-only
	STATUS	mandatory
	DESCRIPTION 
		"This index is the ifIndex of the Ont.  "
	::= { gponOntOltsidePhyCurrentIntervalEntry 1 }


gponOntOltsidePhyCurrentIntervalValidInd  OBJECT-TYPE
	SYNTAX 	Boolean
	ACCESS	read-only
	STATUS	mandatory
	DESCRIPTION 
		"Indicates whether or not this CurrentInterval contains
		 valid PM counts.

		 NOT SUPPORTED  "
	::= { gponOntOltsidePhyCurrentIntervalEntry 2 }


gponOntOltsidePhyCurrentIntervalUpBip32ProtWords  OBJECT-TYPE
	SYNTAX 	OCTET STRING (SIZE(8))
	ACCESS	read-only
	STATUS	mandatory
	DESCRIPTION 
		" 64-bit counter of upstream received 4-byte words that are included in/protected by BIP-32 check  "
	::= { gponOntOltsidePhyCurrentIntervalEntry 3 }

gponOntOltsidePhyCurrentIntervalUpBip32BitErrors  OBJECT-TYPE
	SYNTAX 	OCTET STRING (SIZE(8))
	ACCESS	read-only
	STATUS	mandatory
	DESCRIPTION 
		" 64-bit counter of upstream received bit errors according to BIP-32 check  "
	::= { gponOntOltsidePhyCurrentIntervalEntry 4 }


-- *********************************************
--
-- GPON ONT OLTSIDE PHYSICAL LAYER PERFORMANCE MONITOR INTERVAL TABLE
--
-- This table was first introduced with ISAM4.6 MIB.
--
-- This interval table contains various PHY layer counters collected over the previous
-- 8 hours of operation.  The past 8 hours are broken into 32 completed 15
-- minute intervals. Each row in this table represents one such interval.  
--
-- An instance of this table is auto-created/deleted in accordance with the 
-- 'OLT-side Phy layer PM Collect Indicator' setting of the ONT Table.
--
-- As of ISAM4.6, this table is NOT SUPPORTED.
--
--	For GPON - NOT SUPPORTED as of ISAM4.6
--	For XG-PON1 - NOT SUPPORTED as of ISAM4.6.02
--	For NG-PON2 - NOT SUPPORTED as of ISAM5.2
-- 
-- *********************************************


gponOntOltsidePhyIntervalTable  OBJECT-TYPE
	SYNTAX SEQUENCE OF GponOntOltsidePhyIntervalEntry
	ACCESS	not-accessible
	STATUS	mandatory
	::= { bponOntGroup 32 }


gponOntOltsidePhyIntervalEntry  OBJECT-TYPE
	SYNTAX 	GponOntOltsidePhyIntervalEntry
	ACCESS	not-accessible
	STATUS	mandatory
	DESCRIPTION 
		"An entry in the GPON ONT OLT-side PHY Interval Table. "
	INDEX	{ gponOntOltsidePhyIntervalIndex,
		    gponOntOltsidePhyIntervalNumber }
	::= { gponOntOltsidePhyIntervalTable 1 }

GponOntOltsidePhyIntervalEntry ::= SEQUENCE {
	gponOntOltsidePhyIntervalIndex			IfIndex,
	gponOntOltsidePhyIntervalNumber			INTEGER,
	gponOntOltsidePhyIntervalValidInd			Boolean,
	gponOntOltsidePhyIntervalUpBip32ProtWords		OCTET STRING,
	gponOntOltsidePhyIntervalUpBip32BitErrors		OCTET STRING
}


gponOntOltsidePhyIntervalIndex  OBJECT-TYPE
	SYNTAX 	IfIndex
	ACCESS	read-only
	STATUS	mandatory
	DESCRIPTION 
		"This index is the ifIndex of the Ont.  "
	::= { gponOntOltsidePhyIntervalEntry 1 }

gponOntOltsidePhyIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.  "
	::= { gponOntOltsidePhyIntervalEntry 2 }


gponOntOltsidePhyIntervalValidInd  OBJECT-TYPE
	SYNTAX 	Boolean
	ACCESS	read-only
	STATUS	mandatory
	DESCRIPTION 
		"Indicates whether or not this CurrentInterval contains
		 valid PM counts.

		 NOT SUPPORTED  "
	::= { gponOntOltsidePhyIntervalEntry 3 }


gponOntOltsidePhyIntervalUpBip32ProtWords  OBJECT-TYPE
	SYNTAX 	OCTET STRING (SIZE(8))
	ACCESS	read-only
	STATUS	mandatory
	DESCRIPTION 
		" 64-bit counter of upstream received 4-byte words that are included in/protected by BIP-32 check  "
	::= { gponOntOltsidePhyIntervalEntry 4 }

gponOntOltsidePhyIntervalUpBip32BitErrors  OBJECT-TYPE
	SYNTAX 	OCTET STRING (SIZE(8))
	ACCESS	read-only
	STATUS	mandatory
	DESCRIPTION 
		" 64-bit counter of upstream received bit errors according to BIP-32 check  "
	::= { gponOntOltsidePhyIntervalEntry 5 }


-- *********************************************
--
-- GPON ONT ONTSIDE XGPON TC LAYER  PERFORMANCE MONITOR CURRENT INTERVAL TABLE
--
-- This table was first introduced with ISAM4.6 MIB.
-- It is only SUPPORTED beginning with ISAM4.6.01 release (only for XGPON).
--
-- This current interval table contains various ONT-side XG TC counters (for a specific ONT) during the current
-- 15 minute interval of operation.  
--
-- An instance of this table is auto-created/deleted in accordance with the 
-- 'ONT-side XG TC Layer PM Collect Indicator' setting of the ONT Table.
--
--	For GPON - NOT SUPPORTED as of ISAM4.6
--	For XG-PON1 - SUPPORTED as of ISAM4.6.02
--	For NG-PON2 - SUPPORTED as of ISAM5.2
-- 
-- *********************************************


gponOntOntsideXgTcCurrentIntervalTable  OBJECT-TYPE
	SYNTAX SEQUENCE OF GponOntOntsideXgTcCurrentIntervalEntry
	ACCESS	not-accessible
	STATUS	mandatory
	::= { bponOntGroup 33 }


gponOntOntsideXgTcCurrentIntervalEntry  OBJECT-TYPE
	SYNTAX 	GponOntOntsideXgTcCurrentIntervalEntry
	ACCESS	not-accessible
	STATUS	mandatory
	DESCRIPTION 
		"An entry in the GPON ONT ONT-side XG TC CurrentInterval Table. "
	INDEX	{ gponOntOntsideXgTcCurrentIntervalIndex }
	::= { gponOntOntsideXgTcCurrentIntervalTable 1 }

GponOntOntsideXgTcCurrentIntervalEntry ::= SEQUENCE {
	gponOntOntsideXgTcCurrentIntervalIndex			IfIndex,
	gponOntOntsideXgTcCurrentIntervalValidInd			Boolean,
	gponOntOntsideXgTcCurrentIntervalHecErrors		Counter,
	gponOntOntsideXgTcCurrentIntervalKeyErrors		Counter,
	gponOntOntsideXgTcCurrentIntervalRangeTimeMsgs		Counter
}


gponOntOntsideXgTcCurrentIntervalIndex  OBJECT-TYPE
	SYNTAX 	IfIndex
	ACCESS	read-only
	STATUS	mandatory
	DESCRIPTION 
		"This index is the ifIndex of the Ont.  "
	::= { gponOntOntsideXgTcCurrentIntervalEntry 1 }


gponOntOntsideXgTcCurrentIntervalValidInd  OBJECT-TYPE
	SYNTAX 	Boolean
	ACCESS	read-only
	STATUS	mandatory
	DESCRIPTION 
		"Indicates whether or not this CurrentInterval contains
		 valid PM counts.

		 NOT SUPPORTED  "
	::= { gponOntOntsideXgTcCurrentIntervalEntry 2 }


gponOntOntsideXgTcCurrentIntervalHecErrors  OBJECT-TYPE
	SYNTAX 	Counter
	ACCESS	read-only
	STATUS	mandatory
	DESCRIPTION 
		" Count of downstream HEC errors   "
	::= { gponOntOntsideXgTcCurrentIntervalEntry 3 }

gponOntOntsideXgTcCurrentIntervalKeyErrors  OBJECT-TYPE
	SYNTAX 	Counter
	ACCESS	read-only
	STATUS	mandatory
	DESCRIPTION 
		" Count of downstream frames having invalid key specs  "
	::= { gponOntOntsideXgTcCurrentIntervalEntry 4 }

gponOntOntsideXgTcCurrentIntervalRangeTimeMsgs  OBJECT-TYPE
	SYNTAX 	Counter
	ACCESS	read-only
	STATUS	mandatory
	DESCRIPTION 
		" Count of downstream ranging time messages received  "
	::= { gponOntOntsideXgTcCurrentIntervalEntry 5 }


-- *********************************************
--
-- GPON ONT ONTSIDE XGPON TC LAYER  PERFORMANCE MONITOR INTERVAL TABLE
--
-- This table was first introduced with ISAM4.6 MIB.
-- It is only SUPPORTED beginning with ISAM4.6.01 release (only for XGPON).
--
-- This interval table contains various XG TC layer counters collected over the previous
-- 8 hours of operation.  The past 8 hours are broken into 32 completed 15
-- minute intervals. Each row in this table represents one such interval.  
--
-- An instance of this table is auto-created/deleted in accordance with the 
-- 'ONT-side XG TC layer PM Collect Indicator' setting of the ONT Table.
--
--	For GPON - NOT SUPPORTED as of ISAM4.6
--	For XG-PON1 - SUPPORTED as of ISAM4.6.02
--	For NG-PON2 - SUPPORTED as of ISAM5.2
-- 
-- *********************************************


gponOntOntsideXgTcIntervalTable  OBJECT-TYPE
	SYNTAX SEQUENCE OF GponOntOntsideXgTcIntervalEntry
	ACCESS	not-accessible
	STATUS	mandatory
	::= { bponOntGroup 34 }


gponOntOntsideXgTcIntervalEntry  OBJECT-TYPE
	SYNTAX 	GponOntOntsideXgTcIntervalEntry
	ACCESS	not-accessible
	STATUS	mandatory
	DESCRIPTION 
		"An entry in the GPON ONT ONT-side XG TC CurrentInterval Table. "
	INDEX	{ gponOntOntsideXgTcIntervalIndex,
		gponOntOntsideXgTcIntervalNumber }
	::= { gponOntOntsideXgTcIntervalTable 1 }

GponOntOntsideXgTcIntervalEntry ::= SEQUENCE {
	gponOntOntsideXgTcIntervalIndex			IfIndex,
	gponOntOntsideXgTcIntervalNumber		INTEGER,
	gponOntOntsideXgTcIntervalValidInd			Boolean,
	gponOntOntsideXgTcIntervalHecErrors		Counter,
	gponOntOntsideXgTcIntervalKeyErrors		Counter,
	gponOntOntsideXgTcIntervalRangeTimeMsgs		Counter
}


gponOntOntsideXgTcIntervalIndex  OBJECT-TYPE
	SYNTAX 	IfIndex
	ACCESS	read-only
	STATUS	mandatory
	DESCRIPTION 
		"This index is the ifIndex of the Ont.  "
	::= { gponOntOntsideXgTcIntervalEntry 1 }

gponOntOntsideXgTcIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.  "
	::= { gponOntOntsideXgTcIntervalEntry 2 }


gponOntOntsideXgTcIntervalValidInd  OBJECT-TYPE
	SYNTAX 	Boolean
	ACCESS	read-only
	STATUS	mandatory
	DESCRIPTION 
		"Indicates whether or not this CurrentInterval contains
		 valid PM counts.

		 NOT SUPPORTED  "
	::= { gponOntOntsideXgTcIntervalEntry 3 }


gponOntOntsideXgTcIntervalHecErrors  OBJECT-TYPE
	SYNTAX 	Counter
	ACCESS	read-only
	STATUS	mandatory
	DESCRIPTION 
		" Count of downstream HEC errors   "
	::= { gponOntOntsideXgTcIntervalEntry 4 }

gponOntOntsideXgTcIntervalKeyErrors  OBJECT-TYPE
	SYNTAX 	Counter
	ACCESS	read-only
	STATUS	mandatory
	DESCRIPTION 
		" Count of downstream frames having invalid key specs  "
	::= { gponOntOntsideXgTcIntervalEntry 5 }

gponOntOntsideXgTcIntervalRangeTimeMsgs  OBJECT-TYPE
	SYNTAX 	Counter
	ACCESS	read-only
	STATUS	mandatory
	DESCRIPTION 
		" Count of downstream ranging time messages received  "
	::= { gponOntOntsideXgTcIntervalEntry 6 }


-- *********************************************
--
-- GPON ONT OLTSIDE XGPON TC LAYER  PERFORMANCE MONITOR CURRENT INTERVAL TABLE
--
-- This table was first introduced with ISAM4.6 MIB.
-- It is only SUPPORTED beginning with ISAM4.6.01 release (only for XGPON).
--
-- This current interval table contains various OLT-side XG TC counters (for a specific ONT) during the current
-- 15 minute interval of operation.  
--
-- An instance of this table is auto-created/deleted in accordance with the 
-- 'OLT-side XG TC Layer PM Collect Indicator' setting of the ONT Table.
--
--	For GPON - NOT SUPPORTED as of ISAM4.6
--	For XG-PON1 - SUPPORTED as of ISAM4.6.02
--	For NG-PON2 - SUPPORTED as of ISAM5.2
-- 
-- *********************************************


gponOntOltsideXgTcCurrentIntervalTable  OBJECT-TYPE
	SYNTAX SEQUENCE OF GponOntOltsideXgTcCurrentIntervalEntry
	ACCESS	not-accessible
	STATUS	mandatory
	::= { bponOntGroup 35 }


gponOntOltsideXgTcCurrentIntervalEntry  OBJECT-TYPE
	SYNTAX 	GponOntOltsideXgTcCurrentIntervalEntry
	ACCESS	not-accessible
	STATUS	mandatory
	DESCRIPTION 
		"An entry in the GPON ONT OLT-side XG TC CurrentInterval Table. "
	INDEX	{ gponOntOltsideXgTcCurrentIntervalIndex }
	::= { gponOntOltsideXgTcCurrentIntervalTable 1 }

GponOntOltsideXgTcCurrentIntervalEntry ::= SEQUENCE {
	gponOntOltsideXgTcCurrentIntervalIndex			IfIndex,
	gponOntOltsideXgTcCurrentIntervalValidInd			Boolean,
	gponOntOltsideXgTcCurrentIntervalHecErrors		Counter,
	gponOntOltsideXgTcCurrentIntervalKeyErrors		Counter,
	gponOntOltsideXgTcCurrentIntervalRangeTimeMsgs		Counter
}


gponOntOltsideXgTcCurrentIntervalIndex  OBJECT-TYPE
	SYNTAX 	IfIndex
	ACCESS	read-only
	STATUS	mandatory
	DESCRIPTION 
		"This index is the ifIndex of the Ont.  "
	::= { gponOntOltsideXgTcCurrentIntervalEntry 1 }


gponOntOltsideXgTcCurrentIntervalValidInd  OBJECT-TYPE
	SYNTAX 	Boolean
	ACCESS	read-only
	STATUS	mandatory
	DESCRIPTION 
		"Indicates whether or not this CurrentInterval contains
		 valid PM counts.

		 NOT SUPPORTED  "
	::= { gponOntOltsideXgTcCurrentIntervalEntry 2 }


gponOntOltsideXgTcCurrentIntervalHecErrors  OBJECT-TYPE
	SYNTAX 	Counter
	ACCESS	read-only
	STATUS	mandatory
	DESCRIPTION 
		" Count of number of events involving loss of XGEM channel deliniation   "
	::= { gponOntOltsideXgTcCurrentIntervalEntry 3 }

gponOntOltsideXgTcCurrentIntervalKeyErrors  OBJECT-TYPE
	SYNTAX 	Counter
	ACCESS	read-only
	STATUS	mandatory
	DESCRIPTION 
		" Count of number of XGEM frames discarded due to key errors  "
	::= { gponOntOltsideXgTcCurrentIntervalEntry 4 }

gponOntOltsideXgTcCurrentIntervalRangeTimeMsgs  OBJECT-TYPE
	SYNTAX 	Counter
	ACCESS	read-only
	STATUS	mandatory
	DESCRIPTION 
		" Count of downstream ranging time messages sent  "
	::= { gponOntOltsideXgTcCurrentIntervalEntry 5 }


-- *********************************************
--
-- GPON ONT OLTSIDE XGPON TC LAYER  PERFORMANCE MONITOR INTERVAL TABLE
--
-- This table was first introduced with ISAM4.6 MIB.
-- It is only SUPPORTED beginning with ISAM4.6.01 release (only for XGPON).
--
-- This interval table contains various XG TC layer counters collected over the previous
-- 8 hours of operation.  The past 8 hours are broken into 32 completed 15
-- minute intervals. Each row in this table represents one such interval.  
--
-- An instance of this table is auto-created/deleted in accordance with the 
-- 'OLT-side XG TC layer PM Collect Indicator' setting of the ONT Table.
--
--	For GPON - NOT SUPPORTED as of ISAM4.6
--	For XG-PON1 - SUPPORTED as of ISAM4.6.02
--	For NG-PON2 - SUPPORTED as of ISAM5.2
-- 
-- *********************************************


gponOntOltsideXgTcIntervalTable  OBJECT-TYPE
	SYNTAX SEQUENCE OF GponOntOltsideXgTcIntervalEntry
	ACCESS	not-accessible
	STATUS	mandatory
	::= { bponOntGroup 36 }


gponOntOltsideXgTcIntervalEntry  OBJECT-TYPE
	SYNTAX 	GponOntOltsideXgTcIntervalEntry
	ACCESS	not-accessible
	STATUS	mandatory
	DESCRIPTION 
		"An entry in the GPON ONT OLT-side XG TC CurrentInterval Table. "
	INDEX	{ gponOntOltsideXgTcIntervalIndex,
		gponOntOltsideXgTcIntervalNumber }
	::= { gponOntOltsideXgTcIntervalTable 1 }

GponOntOltsideXgTcIntervalEntry ::= SEQUENCE {
	gponOntOltsideXgTcIntervalIndex			IfIndex,
	gponOntOltsideXgTcIntervalNumber		INTEGER,
	gponOntOltsideXgTcIntervalValidInd			Boolean,
	gponOntOltsideXgTcIntervalHecErrors		Counter,
	gponOntOltsideXgTcIntervalKeyErrors		Counter,
	gponOntOltsideXgTcIntervalRangeTimeMsgs		Counter
}


gponOntOltsideXgTcIntervalIndex  OBJECT-TYPE
	SYNTAX 	IfIndex
	ACCESS	read-only
	STATUS	mandatory
	DESCRIPTION 
		"This index is the ifIndex of the Ont.  "
	::= { gponOntOltsideXgTcIntervalEntry 1 }

gponOntOltsideXgTcIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.  "
	::= { gponOntOltsideXgTcIntervalEntry 2 }


gponOntOltsideXgTcIntervalValidInd  OBJECT-TYPE
	SYNTAX 	Boolean
	ACCESS	read-only
	STATUS	mandatory
	DESCRIPTION 
		"Indicates whether or not this CurrentInterval contains
		 valid PM counts.

		 NOT SUPPORTED  "
	::= { gponOntOltsideXgTcIntervalEntry 3 }


gponOntOltsideXgTcIntervalHecErrors  OBJECT-TYPE
	SYNTAX 	Counter
	ACCESS	read-only
	STATUS	mandatory
	DESCRIPTION 
		" Count of number of events involving loss of XGEM channel deliniation   "
	::= { gponOntOltsideXgTcIntervalEntry 4 }

gponOntOltsideXgTcIntervalKeyErrors  OBJECT-TYPE
	SYNTAX 	Counter
	ACCESS	read-only
	STATUS	mandatory
	DESCRIPTION 
		" Count of number of XGEM frames discarded due to key errors  "
	::= { gponOntOltsideXgTcIntervalEntry 5 }

gponOntOltsideXgTcIntervalRangeTimeMsgs  OBJECT-TYPE
	SYNTAX 	Counter
	ACCESS	read-only
	STATUS	mandatory
	DESCRIPTION 
		" Count of downstream ranging time messages sent  "
	::= { gponOntOltsideXgTcIntervalEntry 6 }


-- *********************************************
--
-- GPON ONT SIDE AGGREGATE PREVIOUS ETHERNET PERFORMANCE TABLE
-- This is a new table beginning with ISAM R5.0
-- This table contains the sum of all the previous intervals of ONT level Ethernet PM since PM was enabled.
-- The gponOntOntsidePonAggEtherIntervalTable only retains the latest 32 previous intervals, but this table will sum all the
-- intervals together including the intervals had been replaced by newer intervals.
-- An instance of this table is auto-created/deleted in accordance with the 
-- 'ONT-side PON Aggregate Ethernet PM Collect Indicator' setting of the ONT Table.
--
-- For GETs of table attributes, OLT will return the values in memory without having to access ONT directly. 
--
--	For GPON - SUPPORTED as of ISAM5.0
--	For XG-PON1 - NOT SUPPORTED as of ISAM4.6.02
--	For NG-PON2 - SUPPORTED as of ISAM5.2
--
-- *********************************************

gponOntOntsidePonAggEtherTable  OBJECT-TYPE
    SYNTAX SEQUENCE OF GponOntOntsidePonAggEtherEntry
    ACCESS    not-accessible
    STATUS    mandatory
    ::= { bponOntGroup 37 }

gponOntOntsidePonAggEtherEntry  OBJECT-TYPE
    SYNTAX    GponOntOntsidePonAggEtherEntry
    ACCESS    not-accessible
    STATUS    mandatory
    DESCRIPTION
        "An entry in the GPON ONT side Aggregate Previous ETHERNET PM Table. "
    INDEX    { gponOntOntsidePonAggEtherIndex }
    ::= { gponOntOntsidePonAggEtherTable 1 }

GponOntOntsidePonAggEtherEntry ::= SEQUENCE {
    	gponOntOntsidePonAggEtherIndex        IfIndex,
	gponOntOntsidePonAggEtherTxFramesUnicast	OCTET STRING (SIZE (8)),
	gponOntOntsidePonAggEtherRxFramesUnicast	OCTET STRING (SIZE (8)),
	gponOntOntsidePonAggEtherTxFramesMulticast	OCTET STRING (SIZE (8)),
	gponOntOntsidePonAggEtherRxFramesMulticast	OCTET STRING (SIZE (8)),
	gponOntOntsidePonAggEtherTxFramesBroadcast	OCTET STRING (SIZE (8)),
	gponOntOntsidePonAggEtherRxFramesBroadcast	OCTET STRING (SIZE (8)),
	gponOntOntsidePonAggEtherTxFrames	OCTET STRING (SIZE (8)),
	gponOntOntsidePonAggEtherRxFrames	OCTET STRING (SIZE (8)),
	gponOntOntsidePonAggEtherTxBytes	OCTET STRING (SIZE (8)),
	gponOntOntsidePonAggEtherRxBytes	OCTET STRING (SIZE (8))
}

gponOntOntsidePonAggEtherIndex  OBJECT-TYPE
    SYNTAX    IfIndex
    ACCESS    read-only
    STATUS    mandatory
    DESCRIPTION
        "This index is the ifIndex of the Ont"

    ::= { gponOntOntsidePonAggEtherEntry 1 }

gponOntOntsidePonAggEtherTxFramesUnicast OBJECT-TYPE
	SYNTAX	OCTET STRING (SIZE (8))
    	ACCESS    read-only
    	STATUS    mandatory
   	 DESCRIPTION
        "Indicates the number of transmitted Unicast Ethernet Frames
	As of ISAM5.0 -> SUPPORTED. "

    ::= { gponOntOntsidePonAggEtherEntry 2 }

gponOntOntsidePonAggEtherRxFramesUnicast OBJECT-TYPE
	SYNTAX	OCTET STRING (SIZE (8))
    	ACCESS    read-only
    	STATUS    mandatory
    	DESCRIPTION
        "Indicates the number of received Unicast Ethernet Frames
	As of ISAM5.0 -> SUPPORTED. "

    ::= { gponOntOntsidePonAggEtherEntry 3 }

gponOntOntsidePonAggEtherTxFramesMulticast OBJECT-TYPE
	SYNTAX	OCTET STRING (SIZE (8))
    	ACCESS    read-only
    	STATUS    mandatory
    	DESCRIPTION
        "Indicates the number of transmitted Multicast Ethernet Frames
	As of ISAM5.0 -> SUPPORTED. "

    ::= { gponOntOntsidePonAggEtherEntry 4 }

gponOntOntsidePonAggEtherRxFramesMulticast OBJECT-TYPE
	SYNTAX	OCTET STRING (SIZE (8))
    	ACCESS    read-only
    	STATUS    mandatory
    	DESCRIPTION
        "Indicates the number of received Multicast Ethernet Frames
	As of ISAM5.0 -> SUPPORTED. "

    ::= { gponOntOntsidePonAggEtherEntry 5 }

gponOntOntsidePonAggEtherTxFramesBroadcast OBJECT-TYPE
	SYNTAX	OCTET STRING (SIZE (8))
    		ACCESS    read-only
    	STATUS    mandatory
    	DESCRIPTION
        "Indicates the number of transmitted Broadcast Ethernet Frames
	As of ISAM5.0 -> SUPPORTED. "

    ::= { gponOntOntsidePonAggEtherEntry 6 }

gponOntOntsidePonAggEtherRxFramesBroadcast OBJECT-TYPE
	SYNTAX	OCTET STRING (SIZE (8))
    	ACCESS    read-only
    	STATUS    mandatory
    	DESCRIPTION
        "Indicates the number of received Broadcast Ethernet Frames
	As of ISAM5.0 -> SUPPORTED. "

    ::= { gponOntOntsidePonAggEtherEntry 7 }

gponOntOntsidePonAggEtherTxFrames OBJECT-TYPE
	SYNTAX	OCTET STRING (SIZE (8))
    	ACCESS    read-only
    	STATUS    mandatory
    	DESCRIPTION
        "Indicates the total number of transmitted Ethernet Frames
	As of ISAM5.0 -> SUPPORTED. "

    ::= { gponOntOntsidePonAggEtherEntry 8 }

gponOntOntsidePonAggEtherRxFrames OBJECT-TYPE
	SYNTAX	OCTET STRING (SIZE (8))
    	ACCESS    read-only
    	STATUS    mandatory
    	DESCRIPTION
        "Indicates the total number of received Ethernet Frames
	As of ISAM5.0 -> SUPPORTED. "

    ::= { gponOntOntsidePonAggEtherEntry 9 }

gponOntOntsidePonAggEtherTxBytes OBJECT-TYPE
	SYNTAX	OCTET STRING (SIZE (8))
    	ACCESS    read-only
    	STATUS    mandatory
    	DESCRIPTION
        "Indicates the total number of transmitted Ethernet Bytes
	As of ISAM5.0 -> SUPPORTED. "

    ::= { gponOntOntsidePonAggEtherEntry 10 }

gponOntOntsidePonAggEtherRxBytes OBJECT-TYPE
	SYNTAX	OCTET STRING (SIZE (8))
    	ACCESS    read-only
    	STATUS    mandatory
    	DESCRIPTION
        "Indicates the total number of received Ethernet Bytes
	As of ISAM5.0 -> SUPPORTED. "

::= { gponOntOntsidePonAggEtherEntry 11 }


-- *********************************************
--
-- GPON HGU TR069 SHORT KEY-VALUE PROVISION TABLE
-- This is a new table beginning with ISAM R5.3
-- This table contains the short TR069 parameter names and values of HGU
--
--  For GETs of table attributes, OLT will return the values in memory without having to access ONT directly. 
--
--  For GPON - SUPPORTED as of ISAM5.3
--  For XG-PON1 - NOT SUPPORTED as of ISAM5.3
--  For NG-PON2 - NOT SUPPORTED as of ISAM5.3
--
-- *********************************************

gponHGUTR069SKeyProvisionTable  OBJECT-TYPE
    SYNTAX SEQUENCE OF GponHGUTR069SKeyProvisionEntry
    ACCESS  not-accessible
    STATUS  mandatory
    ::= { bponOntGroup 38 }

gponHGUTR069SKeyProvisionEntry  OBJECT-TYPE
    SYNTAX  GponHGUTR069SKeyProvisionEntry
    ACCESS  not-accessible
    STATUS  mandatory
    DESCRIPTION
        "An entry in the GPON HGU TR069 short key provision Table. "
    INDEX   { gponHGUTR069SKeyProvisionOntIndex,
            gponHGUTR069SKeyProvisionParamIndex }
    ::= { gponHGUTR069SKeyProvisionTable 1 }

GponHGUTR069SKeyProvisionEntry ::= SEQUENCE {
    gponHGUTR069SKeyProvisionOntIndex          IfIndex,
    gponHGUTR069SKeyProvisionParamIndex        INTEGER,
    gponHGUTR069SKeyProvisionParamName         DisplayString,
    gponHGUTR069SKeyProvisionParamValue        DisplayString,
    gponHGUTR069SKeyProvisionRowStatus         RowStatus
}

gponHGUTR069SKeyProvisionOntIndex  OBJECT-TYPE
    SYNTAX  IfIndex
    ACCESS  read-only
    STATUS  mandatory
    DESCRIPTION
        "Each row is indexed by the ifIndex of the ONT.
        
         Introduced in ISAM5.3 MIB

        For GPON - SUPPORTED as of ISAM5.3
        For XG-PON1 - NOT SUPPORTED as of ISAM5.3
        For NG-PON2 - NOT SUPPORTED as of ISAM5.3  "
    ::= { gponHGUTR069SKeyProvisionEntry 1 }
    
gponHGUTR069SKeyProvisionParamIndex  OBJECT-TYPE
    SYNTAX  INTEGER (1..35)
    ACCESS  read-only
    STATUS  mandatory
    DESCRIPTION
        " Each row is also indexed by a number that
         indicate the TR069 short key parameter index.
                 
         Introduced in ISAM5.3 MIB

        For GPON - SUPPORTED as of ISAM5.3
        For XG-PON1 - NOT SUPPORTED as of ISAM5.3
        For NG-PON2 - NOT SUPPORTED as of ISAM5.3  "
    ::= { gponHGUTR069SKeyProvisionEntry 2 }

gponHGUTR069SKeyProvisionParamName  OBJECT-TYPE
    SYNTAX  DisplayString (SIZE(0..127))
    ACCESS  read-write
    STATUS  mandatory
    DESCRIPTION 
        "Indicate the TR069 short key parameter name.
         Modification is NOT permitted.  
                 
         Introduced in ISAM5.3 MIB

        For GPON - SUPPORTED as of ISAM5.3
        For XG-PON1 - NOT SUPPORTED as of ISAM5.3
        For NG-PON2 - NOT SUPPORTED as of ISAM5.3 "
    ::= { gponHGUTR069SKeyProvisionEntry 3 }

gponHGUTR069SKeyProvisionParamValue  OBJECT-TYPE
    SYNTAX  DisplayString (SIZE(0..31))
    ACCESS  read-write
    STATUS  mandatory
    DESCRIPTION 
        "Indicate the TR069 short key parameter value.
	 Modification is permitted. 
                
         Introduced in ISAM5.3 MIB

        For GPON - SUPPORTED as of ISAM5.3
        For XG-PON1 - NOT SUPPORTED as of ISAM5.3
        For NG-PON2 - NOT SUPPORTED as of ISAM5.3 "
    ::= { gponHGUTR069SKeyProvisionEntry 4 }
    
gponHGUTR069SKeyProvisionRowStatus  OBJECT-TYPE
    SYNTAX  RowStatus
    ACCESS  read-write
    STATUS  mandatory
    DESCRIPTION
        " All rows instantiated using 'create-and-go' to
         provision a short key parameter. Set to 'destroy' to delete
         a short key parameter. 
                 
         Introduced in ISAM5.3 MIB

        For GPON - SUPPORTED as of ISAM5.3
        For XG-PON1 - NOT SUPPORTED as of ISAM5.3
        For NG-PON2 - NOT SUPPORTED as of ISAM5.3 "
    ::= { gponHGUTR069SKeyProvisionEntry 5 }


-- *********************************************
--
-- GPON HGU TR069 LONG KEY-VALUE PROVISION TABLE
-- This is a new table beginning with ISAM R5.3
-- This table contains the long TR069 parameter names and values of HGU
--
-- For GETs of table attributes, OLT will return the values in memory without having to access ONT directly. 
--
--  For GPON - SUPPORTED as of ISAM5.3
--  For XG-PON1 - NOT SUPPORTED as of ISAM5.3
--  For NG-PON2 - NOT SUPPORTED as of ISAM5.3
--
-- *********************************************

gponHGUTR069LKeyProvisionTable  OBJECT-TYPE
    SYNTAX SEQUENCE OF GponHGUTR069LKeyProvisionEntry
    ACCESS  not-accessible
    STATUS  mandatory
    ::= { bponOntGroup 39 }

gponHGUTR069LKeyProvisionEntry  OBJECT-TYPE
    SYNTAX  GponHGUTR069LKeyProvisionEntry
    ACCESS  not-accessible
    STATUS  mandatory
    DESCRIPTION
        "An entry in the GPON HGU TR069 long key provision Table. "
    INDEX   { gponHGUTR069LKeyProvisionOntIndex,
            gponHGUTR069LKeyProvisionParamIndex }
    ::= { gponHGUTR069LKeyProvisionTable 1 }

GponHGUTR069LKeyProvisionEntry ::= SEQUENCE {
    gponHGUTR069LKeyProvisionOntIndex          IfIndex,
    gponHGUTR069LKeyProvisionParamIndex        INTEGER,
    gponHGUTR069LKeyProvisionParamName         DisplayString,
    gponHGUTR069LKeyProvisionParamValue        DisplayString,
    gponHGUTR069LKeyProvisionRowStatus         RowStatus
}

gponHGUTR069LKeyProvisionOntIndex  OBJECT-TYPE
    SYNTAX  IfIndex
    ACCESS  read-only
    STATUS  mandatory
    DESCRIPTION
        "Each row is indexed by the ifIndex of the ONT. 
                
         Introduced in ISAM5.3 MIB

        For GPON - SUPPORTED as of ISAM5.3
        For XG-PON1 - SUPPORTED as of ISAM5.3
        For NG-PON2 - NOT SUPPORTED as of ISAM5.3 "
    ::= { gponHGUTR069LKeyProvisionEntry 1 }
    
gponHGUTR069LKeyProvisionParamIndex  OBJECT-TYPE
    SYNTAX  INTEGER (1..5)
    ACCESS  read-only
    STATUS  mandatory
    DESCRIPTION
        " Each row is also indexed by a number that
         indicate the TR069 long key parameter index. 
                 
         Introduced in ISAM5.3 MIB

        For GPON - SUPPORTED as of ISAM5.3
        For XG-PON1 - NOT SUPPORTED as of ISAM5.3
        For NG-PON2 - NOT SUPPORTED as of ISAM5.3 "
    ::= { gponHGUTR069LKeyProvisionEntry 2 }

gponHGUTR069LKeyProvisionParamName  OBJECT-TYPE
    SYNTAX  DisplayString (SIZE(0..255))
    ACCESS  read-write
    STATUS  mandatory
    DESCRIPTION 
        "Indicate the TR069 long key parameter name.
         Modification is NOT permitted.  
                 
         Introduced in ISAM5.3 MIB

        For GPON - SUPPORTED as of ISAM5.3
        For XG-PON1 - NOT SUPPORTED as of ISAM5.3
        For NG-PON2 - NOT SUPPORTED as of ISAM5.3 "
    ::= { gponHGUTR069LKeyProvisionEntry 3 }

gponHGUTR069LKeyProvisionParamValue  OBJECT-TYPE
    SYNTAX  DisplayString (SIZE(0..255))
    ACCESS  read-write
    STATUS  mandatory
    DESCRIPTION 
        "Indicate the TR069 long key parameter value.
	 Modification is permitted. 
                
         Introduced in ISAM5.3 MIB

        For GPON - SUPPORTED as of ISAM5.3
        For XG-PON1 - NOT SUPPORTED as of ISAM5.3
        For NG-PON2 - NOT SUPPORTED as of ISAM5.3 "
    ::= { gponHGUTR069LKeyProvisionEntry 4 }
    
gponHGUTR069LKeyProvisionRowStatus  OBJECT-TYPE
    SYNTAX  RowStatus
    ACCESS  read-write
    STATUS  mandatory
    DESCRIPTION
        " All rows instantiated using 'create-and-go' to
         provision a long key parameter. Set to 'destroy' to delete
         a long key parameter. 
                 
         Introduced in ISAM5.3 MIB

        For GPON - SUPPORTED as of ISAM5.3
        For XG-PON1 - NOT SUPPORTED as of ISAM5.3
        For NG-PON2 - NOT SUPPORTED as of ISAM5.3 "
    ::= { gponHGUTR069LKeyProvisionEntry 5 }

-- *********************************************
--
-- GPON ONT INDEX MAPPING TABLE
-- This is a new table beginning with ISAM R5.5
--
-- This table is for Searching ONT Index based on ONT SN
--
-- In the future, it will support to search ONT Index based on ONT LOID or SLID
--
--  For GPON - SUPPORTED as of ISAM5.5.01
--  For XG-PON1 - NOT SUPPORTED as of ISAM5.5.01
--  For NG-PON2 - SUPPORTED as of ISAM5.5.01
--
-- *********************************************
bponOntIndexMappingTable OBJECT-TYPE
    SYNTAX SEQUENCE OF BponOntIndexMappingEntry
    ACCESS  not-accessible
    STATUS  mandatory
    ::= { bponOntGroup 40 }

bponOntIndexMappingEntry  OBJECT-TYPE
    SYNTAX  BponOntIndexMappingEntry
    ACCESS  not-accessible
    STATUS  mandatory
    DESCRIPTION
        " An entry in bponOntIndexMappingTable 

          Introduced in ISAM5.5 MIB, with targeted implementation in ISAM5.5.01

          For GPON - SUPPORTED as of ISAM5.5.01
          For XG-PON1 - NOT SUPPORTED as of ISAM5.5.01
          For NG-PON2 - SUPPORTED as of ISAM5.5.01 "
    INDEX   { bponOntSearchMode,
              bponOntSearchString }
    ::= { bponOntIndexMappingTable 1 }

BponOntIndexMappingEntry ::= SEQUENCE {
    bponOntSearchMode        INTEGER,
    bponOntSearchString        DisplayString,
    bponMappingIfIndex        OntIndex
}

bponOntSearchMode  OBJECT-TYPE
    SYNTAX  INTEGER
    ACCESS  read-only
    STATUS  mandatory
    DESCRIPTION
        " This object indicates the search mode
          0 = SN ( meaning look for ONT index based on ONT SN)
          other values are reserved for LOID or SLID search mode

         Introduced in ISAM5.5 MIB, with targeted implementation in ISAM5.5.01

        For GPON - SUPPORTED as of ISAM5.5.01
        For XG-PON1 - NOT SUPPORTED as of ISAM5.5.01
        For NG-PON2 - SUPPORTED as of ISAM5.5.01 "
    ::= { bponOntIndexMappingEntry 1 }

bponOntSearchString  OBJECT-TYPE
    SYNTAX  DisplayString (SIZE(0..71))
    ACCESS  read-only
    STATUS  mandatory
    DESCRIPTION
        " This object indicates the search string

         Introduced in ISAM5.5 MIB, with targeted implementation in ISAM5.5.01

        For GPON - SUPPORTED as of ISAM5.5.01
        For XG-PON1 - NOT SUPPORTED as of ISAM5.5.01
        For NG-PON2 - SUPPORTED as of ISAM5.5.01 "
    ::= { bponOntIndexMappingEntry 2 }

bponMappingIfIndex  OBJECT-TYPE
    SYNTAX  OntIndex
    ACCESS  read-only
    STATUS  mandatory
    DESCRIPTION
        " This object indicates the ONT ifIndex

         Introduced in ISAM5.5 MIB, with targeted implementation in ISAM5.5.01

        For GPON - SUPPORTED as of ISAM5.5.01
        For XG-PON1 - NOT SUPPORTED as of ISAM5.5.01
        For NG-PON2 - SUPPORTED as of ISAM5.5.01 "
    ::= { bponOntIndexMappingEntry 3 }

-- *********************************************
--
-- GPON ONT GIS INFO TABLE
-- This is a new table beginning with ISAM R5.6
--
-- This table is for ONT GIS Info 
--
--
--  For GPON - SUPPORTED as of ISAM5.6.01
--  For XG-PON1 - NOT SUPPORTED as of ISAM5.6.01
--  For NG-PON2 - NOT SUPPORTED as of ISAM5.6.01
--  For XGS-PON - NOT SUPPORTED as of ISAM5.6.01
-- 
-- *********************************************
gponOntGISInfoTable OBJECT-TYPE
    SYNTAX SEQUENCE OF GponOntGISInfoEntry
    ACCESS  not-accessible
    STATUS  mandatory
    ::= { bponOntGroup 41 }

gponOntGISInfoEntry  OBJECT-TYPE
    SYNTAX  GponOntGISInfoEntry
    ACCESS  not-accessible
    STATUS  mandatory
    DESCRIPTION
        " An entry in Gpon Ont GIS Info Table 

          Introduced in ISAM5.6 MIB, with targeted implementation in ISAM5.6.01

          For GPON - SUPPORTED as of ISAM5.6.01
          For XG-PON1 - NOT SUPPORTED as of ISAM5.6.01
          For NG-PON2 - NOT SUPPORTED as of ISAM5.6.01 
          For XGS-PON - NOT SUPPORTED as of ISAM5.6.01"
    INDEX   { gponOntGISIndex }
    ::= { gponOntGISInfoTable 1 }

GponOntGISInfoEntry ::= SEQUENCE {
    gponOntGISIndex            IfIndex,
    gponOntGISMode             INTEGER,
    gponOntGISLng              INTEGER,
    gponOntGISLat              INTEGER,
    gponOntGISElev             INTEGER,
    gponOntGISHrzErr           INTEGER,
    gponOntGISAltErr           INTEGER,
    gponOntGISAreaCode         OCTET STRING,
    gponOntGISTimeStamp        INTEGER,
    gponOntGISDigest           OCTET STRING
}

gponOntGISIndex  OBJECT-TYPE
    SYNTAX  IfIndex
    ACCESS  read-only
    STATUS  mandatory
    DESCRIPTION
        "Each row is indexed by the IfIndex of the ONT
         
         ALCATEL NOTE:
           ACCESS:    NA
           USAGE:     NA
           PERSIST:   YES
           INSRVMOD:  NA
           RANGE:     NA
           DEFVALUE:  NA
           UNITS:     NA
           SPARSE:    NA
           DESCR:     NA
         
         Introduced in ISAM5.6 MIB, with targeted implementation in ISAM5.6.01

        For GPON - SUPPORTED as of ISAM5.6.01
        For XG-PON1 - NOT SUPPORTED as of ISAM5.6.01
        For NG-PON2 - NOT SUPPORTED as of ISAM5.6.01 
        For XGS-PON - NOT SUPPORTED as of ISAM5.6.01"
    ::= { gponOntGISInfoEntry 1 }
    
gponOntGISMode  OBJECT-TYPE
    SYNTAX  INTEGER 
    ACCESS  read-write
    STATUS  mandatory
    DESCRIPTION
        "This object indicates the GIS mode of the ONT
         Introduced in ISAM5.6 MIB, with targeted implementation in ISAM5.6.01
         
         0 =GIS Disabled
         1 =GIS Enabled
         Default =0 =Disabled
         
         ALCATEL NOTE:
           ACCESS:    NA
           USAGE:     NA
           PERSIST:   YES
           INSRVMOD:  YES
           RANGE:     0..1
           DEFVALUE:  0
           UNITS:     NA
           SPARSE:    NA
           DESCR:     NA
        
        For GPON - SUPPORTED as of ISAM5.6.01
        For XG-PON1 - NOT SUPPORTED as of ISAM5.6.01
        For NG-PON2 - NOT SUPPORTED as of ISAM5.6.01
        For XGS-PON - NOT SUPPORTED as of ISAM5.6.01 "
    ::= { gponOntGISInfoEntry 2 }

gponOntGISLng  OBJECT-TYPE
    SYNTAX  INTEGER (-18000000..18000000)
    ACCESS  read-only
    STATUS  mandatory
    DESCRIPTION
        " This object indicates the longitude of the geographical location
          The allowable range is constrained to (-18000000..18000000).
          The actual value should be devided by 100000.
          eg, 11639147 represents east longitude 116.39147
          
	        Default = 0 
          
          ALCATEL NOTE:
           ACCESS:    NA
           USAGE:     NA
           PERSIST:   NO
           INSRVMOD:  NA
           RANGE:     -18000000..18000000
           DEFVALUE:  0
           UNITS:     0.00001 degree
           SPARSE:    NA
           DESCR:     NA
           
          Introduced in ISAM5.6 MIB, with targeted implementation in ISAM5.6.01

          For GPON - SUPPORTED as of ISAM5.6.01
          For XG-PON1 - NOT SUPPORTED as of ISAM5.6.01
          For NG-PON2 - NOT SUPPORTED as of ISAM5.6.01 
          For XGS-PON - NOT SUPPORTED as of ISAM5.6.01 "
    ::= { gponOntGISInfoEntry 3 }

gponOntGISLat  OBJECT-TYPE
    SYNTAX  INTEGER (-9000000..9000000)
    ACCESS  read-only
    STATUS  mandatory
    DESCRIPTION
        " This object indicates the latitude of the geographical location
          The allowable range is constrained to (-9000000..9000000).
          The actual value should be devided by 100000.
          eg, 3990648 represents north latitude 39.90648
          
	        Default = 0 
	        
	        ALCATEL NOTE:
           ACCESS:    NA
           USAGE:     NA
           PERSIST:   NO
           INSRVMOD:  NA
           RANGE:     -9000000..9000000
           DEFVALUE:  0
           UNITS:     0.00001 degree
           SPARSE:    NA
           DESCR:     NA
           
          Introduced in ISAM5.6 MIB, with targeted implementation in ISAM5.6.01

         For GPON - SUPPORTED as of ISAM5.6.01
         For XG-PON1 - NOT SUPPORTED as of ISAM5.6.01
         For NG-PON2 - NOT SUPPORTED as of ISAM5.6.01 
         For XGS-PON - NOT SUPPORTED as of ISAM5.6.01 "
    ::= { gponOntGISInfoEntry 4 }
 
gponOntGISElev  OBJECT-TYPE
    SYNTAX  INTEGER (-32768..32767)
    ACCESS  read-only
    STATUS  mandatory
    DESCRIPTION
        " This object indicates the elevation of the geographical location
          The allowable range is constrained to (-32768..32767).
          The unit is meter.
          eg, 15 represents 15m
          
	        Default = 0 
	       	
	       	ALCATEL NOTE:
           ACCESS:    NA
           USAGE:     NA
           PERSIST:   NO
           INSRVMOD:  NA
           RANGE:     -32768..32767
           DEFVALUE:  0
           UNITS:     m
           SPARSE:    NA
           DESCR:     NA
            
         Introduced in ISAM5.6 MIB, with targeted implementation in ISAM5.6.01

         For GPON - SUPPORTED as of ISAM5.6.01
         For XG-PON1 - NOT SUPPORTED as of ISAM5.6.01
         For NG-PON2 - NOT SUPPORTED as of ISAM5.6.01 
         For XGS-PON - NOT SUPPORTED as of ISAM5.6.01 "
    ::= { gponOntGISInfoEntry 5 }
 
gponOntGISHrzErr  OBJECT-TYPE
    SYNTAX  INTEGER (0..65535)
    ACCESS  read-only
    STATUS  mandatory
    DESCRIPTION
        " This object indicates the horizontal error of the geographical location
          The allowable range is constrained to (0..65535).
          The unit is meter.
          eg, 15 represents 15m
          
	        Default = 0 
	        
	        ALCATEL NOTE:
           ACCESS:    NA
           USAGE:     NA
           PERSIST:   NO
           INSRVMOD:  NA
           RANGE:     0..65535
           DEFVALUE:  0
           UNITS:     m
           SPARSE:    NA
           DESCR:     NA
            
         Introduced in ISAM5.6 MIB, with targeted implementation in ISAM5.6.01

         For GPON - SUPPORTED as of ISAM5.6.01
         For XG-PON1 - NOT SUPPORTED as of ISAM5.6.01
         For NG-PON2 - NOT SUPPORTED as of ISAM5.6.01 
         For XGS-PON - NOT SUPPORTED as of ISAM5.6.01 "
    ::= { gponOntGISInfoEntry 6 }
  
gponOntGISAltErr  OBJECT-TYPE
    SYNTAX  INTEGER (0..65535)
    ACCESS  read-only
    STATUS  mandatory
    DESCRIPTION
        " This object indicates the altitude error of the geographical location
          The allowable range is constrained to (0..65535).
          The unit is meter.
          eg, 15 represents 15m
          
	        Default = 0 
	        
	       	ALCATEL NOTE:
           ACCESS:    NA
           USAGE:     NA
           PERSIST:   NO
           INSRVMOD:  NA
           RANGE:     0..65535
           DEFVALUE:  0
           UNITS:     m
           SPARSE:    NA
           DESCR:     NA 
           
         Introduced in ISAM5.6 MIB, with targeted implementation in ISAM5.6.01

         For GPON - SUPPORTED as of ISAM5.6.01
         For XG-PON1 - NOT SUPPORTED as of ISAM5.6.01
         For NG-PON2 - NOT SUPPORTED as of ISAM5.6.01 
         For XGS-PON - NOT SUPPORTED as of ISAM5.6.01 "
    ::= { gponOntGISInfoEntry 7 }
 
gponOntGISAreaCode  OBJECT-TYPE
    SYNTAX  OCTET STRING (SIZE(6))
    ACCESS  read-only
    STATUS  mandatory
    DESCRIPTION
        " This object indicates the area code of the geographical location
        
	        Default = all zeros. 
	        
	        ALCATEL NOTE:
           ACCESS:    NA
           USAGE:     NA
           PERSIST:   NO
           INSRVMOD:  NA
           RANGE:     NA
           DEFVALUE:  0
           UNITS:     NA
           SPARSE:    NA
           DESCR:     NA
            
         Introduced in ISAM5.6 MIB, with targeted implementation in ISAM5.6.01

         For GPON - SUPPORTED as of ISAM5.6.01
         For XG-PON1 - NOT SUPPORTED as of ISAM5.6.01
         For NG-PON2 - NOT SUPPORTED as of ISAM5.6.01 
         For XGS-PON - NOT SUPPORTED as of ISAM5.6.01 "
    ::= { gponOntGISInfoEntry 8 }
    
gponOntGISTimeStamp  OBJECT-TYPE
    SYNTAX  INTEGER (0..4294967295)
    ACCESS  read-only
    STATUS  mandatory
    DESCRIPTION
        " This object indicates the timestamp of the geographical location
          The allowable range is constrained to (0..4294967295).
          
	        Default = 0 
	       	
	       	ALCATEL NOTE:
           ACCESS:    NA
           USAGE:     NA
           PERSIST:   NO
           INSRVMOD:  NA
           RANGE:     0..4294967295
           DEFVALUE:  0
           UNITS:     seconds
           SPARSE:    NA
           DESCR:     NA
            
         Introduced in ISAM5.6 MIB, with targeted implementation in ISAM5.6.01

         For GPON - SUPPORTED as of ISAM5.6.01
         For XG-PON1 - NOT SUPPORTED as of ISAM5.6.01
         For NG-PON2 - NOT SUPPORTED as of ISAM5.6.01 
         For XGS-PON - NOT SUPPORTED as of ISAM5.6.01 "
    ::= { gponOntGISInfoEntry 9 }
     
gponOntGISDigest  OBJECT-TYPE
    SYNTAX  OCTET STRING (SIZE(8))
    ACCESS  read-only
    STATUS  mandatory
    DESCRIPTION
        " This object indicates the gis digest of the geographical location
          
	        Default = all zeros. 
	        
	       	ALCATEL NOTE:
           ACCESS:    NA
           USAGE:     NA
           PERSIST:   NO
           INSRVMOD:  NA
           RANGE:     NA
           DEFVALUE:  NULL
           UNITS:     NA
           SPARSE:    NA
           DESCR:     NA 
           
         Introduced in ISAM5.6 MIB, with targeted implementation in ISAM5.6.01

         For GPON - SUPPORTED as of ISAM5.6.01
         For XG-PON1 - NOT SUPPORTED as of ISAM5.6.01
         For NG-PON2 - NOT SUPPORTED as of ISAM5.6.01 
         For XGS-PON - NOT SUPPORTED as of ISAM5.6.01 "
    ::= { gponOntGISInfoEntry 10 }
    
-- *********************************************
-- The following table is essentially the same as the old 
-- aponPonConfigTable.  However, the prefix of everything was
-- changed from apon to bpon - and the OID was changed to move
-- the table into the appropriate bpon group.  Although not proper,
-- this was done so that the OLT software could reuse as much
-- previous code as feasible, while using bpon prefix for everything.
--
-- BPON PON CONFIGURATION TABLE
--
-- This table contains configuration information specific to
-- an OLT's control of a specific PON port. Upon creation of
-- an OLT line card, the agent automatically creates rows 
-- in this table (one for each PON port supported by the LT card).
--
-- For FGU4.0, this table is being re-used.  Comments are 
-- made regarding whether attribute is relevant to BPON,
-- GPON or both, etc.  
--
-- For ISAM4.0.10, this table is being re-used. 
-- Noted which attributes are relevant for ISAM4.0.10
--
--	For GPON - SUPPORTED as of ISAM4.0.10
--	For XG-PON1 - SUPPORTED as of ISAM4.6.02
--	For NG-PON2 - NOT SUPPORTED as of ISAM5.2 
--			(some similar attributes SUPPORTED ng2ChanPairConfigTable of NG-PON2 MIB)
-- 
-- *********************************************

bponPonConfigTable  OBJECT-TYPE
	SYNTAX SEQUENCE OF BponPonConfigEntry
	ACCESS	not-accessible
	STATUS	mandatory
	::= { bponPonGroup 2 }

bponPonConfigEntry  OBJECT-TYPE
	SYNTAX 	BponPonConfigEntry
	ACCESS	not-accessible
	STATUS	mandatory
	INDEX	{ bponPonConfigIfIndex }
	::= { bponPonConfigTable 1 }

BponPonConfigEntry ::= SEQUENCE {
	bponPonConfigIfIndex			IfIndex,
	bponPonConfigRowStatus			RowStatus,
	bponPonConfigOntDistance		INTEGER,
	bponPonConfigPollingPeriod		INTEGER,
	bponPonConfigChurnKeyUpdatePeriod	INTEGER,
	bponPonConfigChurnKeyUpdateInd	INTEGER,
	bponPonConfigBerCalcPeriod		INTEGER,
	bponPonConfigAllocatedUpstrmBw	INTEGER,
	bponPonConfigAllocUpstrmBwTca		INTEGER,
	bponPonConfigUbrPcrTca			INTEGER,
	bponPonConfigMulticastGemPort		INTEGER,
	bponPonConfigSigFailThreshold		INTEGER,
	bponPonConfigSigDegradeThreshold		INTEGER,
	bponPonConfigFecDownstreamInd		INTEGER,
	bponPonConfigClosestOntDistance		INTEGER,
	bponPonConfigAggGemPmCollectInd		INTEGER,
	bponPonConfigAggGemPmNumPMIntervals		INTEGER,
	bponPonConfigRamanReductionInd		INTEGER,
	bponPonConfigLabel			DisplayString,
	bponPonConfigRogueTestEnableDisableCmd	INTEGER,
	bponPonConfigUpProvCIR			INTEGER,
	bponPonConfigUpProvAIR			INTEGER,
	bponPonConfigDownProvCIR			INTEGER,
	bponPonConfigDownProvAIR			INTEGER,
	bponPonConfigGuarUpBwRemaining		INTEGER,
	bponPonConfigGuarDownBwRemaining	INTEGER,
	bponPonConfigReach 			INTEGER,
	bponPonConfigMcastGemPmCollectInd       	INTEGER,
  	bponPonConfigMcastGemPmNumPMIntervals    INTEGER,
	bponPonConfigBkgdRogueTestEnableDisableCmd	INTEGER,
  	bponPonConfigAuthMethod  			INTEGER,
	bponPonConfigBkgdRogueTestInterval		INTEGER,
	bponPonConfigBkgdStuckLaserTestCmd	INTEGER,
	bponPonConfigTrafficThresholdUp		Gauge,
	bponPonConfigTrafficThresholdDn		Gauge,
	bponPonConfigXgTag			OCTET STRING,
	bponPonConfigDsMulticastEncryptInd		INTEGER,
	bponPonConfigOltsideUpFecPmCollectInd	INTEGER,
	bponPonConfigOltsideUpFecPmNumPMIntervals	INTEGER,
	bponPonConfigOltsidePhyPmCollectInd	INTEGER,
	bponPonConfigOltsidePhyPmNumPMIntervals	INTEGER,
	bponPonConfigOltsideXgTcPmCollectInd	INTEGER,
	bponPonConfigOltsideXgTcPmNumPMIntervals	INTEGER,
	bponPonConfigXgId			OCTET STRING,
    	bponPonConfigPonUtilPmCollectInd      INTEGER,
    	bponPonConfigPonUtilNumPmIntervals    INTEGER,
	bponPonConfigPonUtilOntDetailSelector	INTEGER,
	bponPonConfigPonUtilOntBulkDetailSelector	INTEGER,
	bponPonConfigAlienTestCmd		INTEGER,
	bponPonConfigBkgdAlienTestCmd		INTEGER,		
	bponPonConfigBkgdAlienTestInterval	INTEGER,
	bponPonConfigPonIdInterval		INTEGER,
	bponPonConfigPonIdOdnClass		INTEGER,
	bponPonConfigPonIdIdentifier		OCTET STRING,
	bponPonConfigMaxRangingOnts             INTEGER,
	bponPonConfigTcontsPerFrame             INTEGER,
	bponPonConfigClearAlmRngMismatch	INTEGER

}

bponPonConfigIfIndex  OBJECT-TYPE
	SYNTAX 	IfIndex
	ACCESS	read-only
	STATUS	mandatory
	DESCRIPTION 
		"Each row is indexed by the ifIndex of the
		 PON (which is statically assigned based
		 on slot/port on the OLT line card). 

		Applicable for both BPON and GPON.

		For ISAM4.0.10 - stays the same as latest FGU4.x

	For GPON - SUPPORTED as of ISAM4.0.10
	For XG-PON1 - SUPPORTED as of ISAM4.6.02 "
	::= { bponPonConfigEntry 1 }

bponPonConfigRowStatus  OBJECT-TYPE
	SYNTAX 	RowStatus
	ACCESS	read-write
	STATUS	obsolete
	DESCRIPTION 
		"All rows initially created 'notInService',
		 when an associated  LT card is planned.
		 Manager sets to 'active', when PON is actually
		 provisioned, and to 'notInService' when PON is
		 de-provisioned.

		  Applicable only for BPON
		 Since FGU4.0--> Not Supported

	For GPON - NOT SUPPORTED as of ISAM4.0.10
	For XG-PON1 - NOT SUPPORTED as of ISAM4.6.02 "
	::= { bponPonConfigEntry 2 }


bponPonConfigOntDistance  OBJECT-TYPE
	SYNTAX 	INTEGER {
		zeroToTen(1),
		tenToTwenty(2),
		zeroToTwenty(3)
	}
	ACCESS	read-write
	STATUS	obsolete
	DESCRIPTION 
		"Setting this attribute bounds the distance
		 (in kms)  for all ONTs connected to this PON.
		 Shorter distances translate into more efficiency
		 in the ranging process.  Note:  This parameter
		 only has effect when there are no active ONTs
		 on the PON. Once 1 ONT becomes active, the 
		 initially selected value sticks.
		 Default = 3 
		 Has never been supported in any release - OLT will
		 hard-code the setting to reflect zeroToTwenty

		Applicable only for BPON. 

		Since FGU4.0 --> Not supported 

	For GPON - SUPPORTED as of ISAM4.0.10
	For XG-PON1 - SUPPORTED as of ISAM4.6.02 "
	::= { bponPonConfigEntry 3 }


bponPonConfigPollingPeriod  OBJECT-TYPE
	SYNTAX 	INTEGER (1..864000)	
	ACCESS	read-write
	STATUS	mandatory
	DESCRIPTION 
		"The period between two consecutive times the
		 autodetection procedure on the PON is executed.
		 Value represents tenths of seconds
		 (e.g. 1 = 1 tenth sec, 864000 = 24 hours).
		 Modification permitted even after row becomes
		 'active'.	 
		 Default = 100

		  Applicable for both BPON and GPON.

	For GPON - SUPPORTED as of ISAM4.0.10
	For XG-PON1 - SUPPORTED as of ISAM4.6.02 "
	::= { bponPonConfigEntry 4 }


bponPonConfigChurnKeyUpdatePeriod  OBJECT-TYPE
	SYNTAX 	INTEGER (5..10)	
	ACCESS	read-write
	STATUS	mandatory
	DESCRIPTION 
		"The period between consecutive requests from the
		 OLT to the PON to update the churning key.
		 Value represents tenths of seconds
		 (e.g. 5 = one-half sec, 10 = one sec).
		 Modification permitted even after row becomes
		 'active'.	 
		 Default = 5 
		Applicable only for BPON. 

		Since FGU4.0 --> Not supported

	For GPON - NOT SUPPORTED as of ISAM4.0.10
	For XG-PON1 - NOT SUPPORTED as of ISAM4.6.02 "
	::= { bponPonConfigEntry 5 }


bponPonConfigChurnKeyUpdateInd  OBJECT-TYPE
	SYNTAX 	INTEGER {
		enable(1),
		disable(2)
	}
	ACCESS	read-write
	STATUS	mandatory
	DESCRIPTION 
		"Whether the churning key update function is enabled
		 or disabled. Modification permitted even after row
		 becomes 'active'.
		 Default = 1

		Applicable only for BPON. 

		Since FGU4.0 --> Not supported

	For GPON - NOT SUPPORTED as of ISAM4.0.10
	For XG-PON1 - NOT SUPPORTED as of ISAM4.6.02 "
	::= { bponPonConfigEntry 6 }

bponPonConfigBerCalcPeriod  OBJECT-TYPE
	SYNTAX 	INTEGER (1..864000)	
	ACCESS	read-write
	STATUS	mandatory
	DESCRIPTION 
		"The measurement period which is used to determine
		 whether an SDi alarm has occurred for an ONT. This
		 period is called T-measure in 983.1.
		 Value represents tenths of seconds
		 (e.g. 1 = 1 tenth sec, 864000 = 24 hours).
		 Modification permitted even after row becomes
		 'active'.	 
		 Default = 10

		  Applicable for both BPON and GPON.

	For GPON - SUPPORTED as of ISAM4.0.10
	For XG-PON1 - SUPPORTED as of ISAM4.6.02 "
	::= { bponPonConfigEntry 7 }

bponPonConfigAllocatedUpstrmBw  OBJECT-TYPE
	SYNTAX 	INTEGER 
	ACCESS	read-only
	STATUS	mandatory
	DESCRIPTION 
		"The total upstream bandwidth currently allocated
		 for this PON (in Cells Per Second).  The total
		 aggregated upstream bandwidth for all active
		 ONTs on any PON cannot exceed 343414 Cells Per
		 Second. Cannot be created by operator.
		 Default = 0

		Applicable only for BPON. 

		Since FGU4.0 --> Not supported

	For GPON - NOT SUPPORTED as of ISAM4.0.10
	For XG-PON1 - NOT SUPPORTED as of ISAM4.6.02 "
	::= { bponPonConfigEntry 8 }

bponPonConfigAllocUpstrmBwTca  OBJECT-TYPE
	SYNTAX 	INTEGER (0..100)
	ACCESS	read-write
	STATUS	mandatory
	DESCRIPTION 
		"Represents the threshold crossing value
		 (as a percentage) of maximum PON rate of 343414
		 cells per second) with regards to
		 total 'non-dynamic guaranteed' upstream bandwidth 
		 currently granted for this PON. When the
		 total aggregated CBR PCR and UBR MCR upstream
		 bandwidth for all active ONTs on this PON exceeds
		 (this value x 343414) a Threshold Crossing Alert
		 (TCA) is generated.
		 Modification permitted even after row becomes
		 'active'.	 
		 Default = 0 (meaning TCA functionality is
		              turned-off).
		 NOTE: As of FGU2.0, this attribute is no longer
		 supported.

		For FGU4.0 --> Not supported

	For GPON - NOT SUPPORTED as of ISAM4.0.10
	For XG-PON1 - NOT SUPPORTED as of ISAM4.6.02 "
	::= { bponPonConfigEntry 9 }

bponPonConfigUbrPcrTca  OBJECT-TYPE
	SYNTAX 	INTEGER (0..100)
	ACCESS	read-write
	STATUS	mandatory
	DESCRIPTION 
		"Represents the threshold crossing value
		 (as a percentage) with regards to
		 total 'dynamic un-guaranteed' upstream bandwidth 
		 currently allocated for this PON. When the
		 total aggregated UBR PCR upstream
		 bandwidth for all VCLs on this PON exceeds
		 (this value x 343414 x UBR PCR Overbook Factor)
		 a Threshold Crossing Alert (TCA) is generated.
		 Modification permitted even after row becomes
		 'active'.	 
		 Default = 0 (meaning TCA functionality is
		              turned-off). 
		 NOTE: As of FGU2.0, this attribute is no longer
		 supported.  
		Prior to FGU4.0--> Not Supported
		Since FGU4.0 --> Not Supported

	For GPON - NOT SUPPORTED as of ISAM4.0.10
	For XG-PON1 - NOT SUPPORTED as of ISAM4.6.02 "
	::= { bponPonConfigEntry 10 }

bponPonConfigMulticastGemPort  OBJECT-TYPE
	SYNTAX 	INTEGER
	ACCESS	read-write
	STATUS	mandatory
	DESCRIPTION 
		" Used to specify the GEM Port ID that carries
		   multicast traffic for this PON.

 		  Default = 4095 (and that is the only value
		  supported for FGU4.0).

		  Applicable only for GPON

		 As of FGU4.0, NOT SUPPORTED. 

	For GPON - NOT SUPPORTED as of ISAM4.0.10
	For XG-PON1 - NOT SUPPORTED as of ISAM4.6.02 "
	::= { bponPonConfigEntry 11 }


bponPonConfigSigFailThreshold  OBJECT-TYPE
	SYNTAX 	INTEGER
	ACCESS	read-write
	STATUS	mandatory
	DESCRIPTION 
		" Represents the BER threshold used to
		  detect Signal Fail (SF) alarms for ONTs
		  on this PON.

		  Setting this value to y means that the BER
		  threshold for SF is 10^(-y).

		  Range is 3 to 8 inclusive.

 		  Default = 5.

		  Applicable only for GPON 

	For GPON - SUPPORTED as of ISAM4.0.10
	For XG-PON1 - SUPPORTED as of ISAM4.6.02 "
	::= { bponPonConfigEntry 12 }

bponPonConfigSigDegradeThreshold  OBJECT-TYPE
	SYNTAX 	INTEGER
	ACCESS	read-write
	STATUS	mandatory
	DESCRIPTION 
		" Represents the BER threshold used to
		  detect Signal Degrade (SD) alarms for ONTs
		  on this PON.

		  Setting this value to x means that the BER
		  threshold for SF is 10^(-x).

		  Range is 4 to 10 inclusive.

 		  Default = 9.

		  RULE: SD threshold must be smaller than SF
		  threshold.  This means that x must must be greater than y.

		  Applicable only for GPON 

	For GPON - SUPPORTED as of ISAM4.0.10
	For XG-PON1 - SUPPORTED as of ISAM4.6.02 "
	::= { bponPonConfigEntry 13 }

bponPonConfigFecDownstreamInd  OBJECT-TYPE
	SYNTAX 	INTEGER {
		enable(1),
		disable(2)
	}
	ACCESS	read-write
	STATUS	mandatory
	DESCRIPTION 
		" Used to Enable/Disable use of FEC in Downstream direction
		   for all OLT transmissions on this PON.

		 Applicable for GPON and X-GPON , but with different behaviors as follows:

		 For GPON (as of ISAM4.0.10):
			Default = 2 = Disable
			Modification SUPPORTED (while in-service) 

		 For X-GPON (as of ISAM4.6.01):
			Default = 1 = Enable
			Modification NOT SUPPORTED "
	::= { bponPonConfigEntry 14 }


bponPonConfigClosestOntDistance  OBJECT-TYPE
	SYNTAX 	INTEGER 
	ACCESS	read-write
	STATUS	mandatory
	DESCRIPTION 
		"Setting this attribute establishes the distance
		 (in kms) of the closest ONT on the PON.  This is used
		 by the OLT to determine how to equalize delay between
		 the ONTs.  ONTs are allowed to be within a 20 km band
		 (relative to each other).  The furthest an ONT can be in a 
		 PON is 60 kms.  
		 RANGE is:   0 (km) - 40 (km).

		 Default = 0 

		Applicable only for GPON. 

		Prior to FGU4.1 --> Not Supported
		Since FGU4.2 --> Supported

	For GPON - SUPPORTED as of ISAM4.0.10
	For XG-PON1 - SUPPORTED as of ISAM4.6.02 "
	::= { bponPonConfigEntry 15 }

bponPonConfigAggGemPmCollectInd  OBJECT-TYPE
	SYNTAX 	INTEGER
	ACCESS	read-write
	STATUS	mandatory
	DESCRIPTION 
		" This indicates whether OLT-side aggregate
		   GEM Port Performance Monitors should be collected for this PON.
	
		  1 = PM collection enabled
		  2 = PM collection disabled

		 Default = 1 = enabled.

	For GPON - SUPPORTED as of ISAM4.0.10
	For XG-PON1 - SUPPORTED as of ISAM4.6.02 "
	::= { bponPonConfigEntry 16 }


bponPonConfigAggGemPmNumPMIntervals  OBJECT-TYPE
	SYNTAX 	INTEGER
	ACCESS	read-only
	STATUS	mandatory
	DESCRIPTION 
		" Indicates the number of rows currently present
		  in the gponPonAggGemIntervalTable.  This
		  is for convenience of the EMS, so that it can
		 quickly determine how many rows should be 
		 uploaded.

	For GPON - SUPPORTED as of ISAM4.0.10
	For XG-PON1 - SUPPORTED as of ISAM4.6.02 "
	::= { bponPonConfigEntry 17 }


bponPonConfigRamanReductionInd  OBJECT-TYPE
	SYNTAX 	INTEGER
	ACCESS	read-write
	STATUS	mandatory
	DESCRIPTION 
		" This indicates whether Raman Reduction code is 
		   enabled or disabled for this PON.
	
		  1 = enabled
		  2 = disabled

		 Default = 2 = disabled.

	For GPON - SUPPORTED as of ISAM4.0.10
	For XG-PON1 - SUPPORTED as of ISAM4.6.02 "
	::= { bponPonConfigEntry 18 }

bponPonConfigLabel  OBJECT-TYPE
	SYNTAX 	DisplayString (SIZE(0..80))
	ACCESS	read-write
	STATUS	mandatory
	DESCRIPTION 
		"This is a textual string that can be used
		 to label the PON port.

		 Default - null string. 

		 Modification is permitted.

	For GPON - SUPPORTED as of ISAM4.0.10
	For XG-PON1 - SUPPORTED as of ISAM4.6.02 "
	::= { bponPonConfigEntry 19 }

bponPonConfigRogueTestEnableDisableCmd  OBJECT-TYPE
	SYNTAX 	INTEGER 
	ACCESS	read-write
	STATUS	mandatory
	DESCRIPTION 
		" This attribute allows the manager to manually enable or disable
		   PON rogue test diagnostic.
		    
		   Attribute values are as follows:
		   1 - Initiate PON Rogue Test (SUPPORTED as of ISAM4.0.10)
		   2 - Disable PON Rogue test (SUPPORTED as of ISAM4.0.10)
		   3 - Initiate 'PATTERN TEST' PON Rogue Test (SUPPORTED in ISAM4.2.33, and brought into ISAM4.4)

		  Default = 2 (as of ISAM4.0.10)
		  Default = 3 (in ISAM4.2.33)
		  Default = 2 (as of ISAM4.4)

	For GPON - SUPPORTED as of ISAM4.0.10
	For XG-PON1 - SUPPORTED as of ISAM4.6.02 "
	::= { bponPonConfigEntry 20 }

bponPonConfigUpProvCIR OBJECT-TYPE 
	SYNTAX INTEGER
	ACCESS read-only
	STATUS mandatory
	DESCRIPTION
	    	" Contains the aggregate upstream provisioned Committed Information Rate (CIR)
		   for this PON.  Units are Kilobits per second.
		   Range is 0 to 1,200,000 (1.2 Gig).

	For GPON - NOT SUPPORTED as of ISAM4.0.10
	For XG-PON1 - NOT SUPPORTED as of ISAM4.6.02 "
	::= { bponPonConfigEntry 21 }

bponPonConfigUpProvAIR OBJECT-TYPE 
	SYNTAX INTEGER
	ACCESS read-only
	STATUS mandatory
	DESCRIPTION
	    	" Contains the aggregate upstream provisioned Assured Information Rate (AIR)
		   for this PON.  Units are Kilobits per second. 
		   Range is 0 to 1,200,000 (1.2 Gig).

		For ISAM4.0.10 - this attribute is NOT SUPPORTED.   "
	::= { bponPonConfigEntry 22 }

bponPonConfigDownProvCIR OBJECT-TYPE 
	SYNTAX INTEGER
	ACCESS read-only
	STATUS mandatory
	DESCRIPTION
	    	" Contains the aggregate downstream provisioned Committed Information Rate (CIR)
		   for this PON.  Units are Kilobits per second.
		   Range is 0 to 2,400,000 (2.4 Gig).

	For GPON - NOT SUPPORTED as of ISAM4.0.10
	For XG-PON1 - NOT SUPPORTED as of ISAM4.6.02 "
	::= { bponPonConfigEntry 23 }

bponPonConfigDownProvAIR OBJECT-TYPE 
	SYNTAX INTEGER
	ACCESS read-only
	STATUS mandatory
	DESCRIPTION
	    	" Contains the aggregate downstream provisioned Assured Information Rate (AIR)
		   for this PON.  Units are Kilobits per second.
		   Range is 0 to 2,400,000 (2.4 Gig). 

		   NOTE:  Attribute NOT SUPPORTED as of FGU4.6.

	For GPON - NOT SUPPORTED as of ISAM4.0.10
	For XG-PON1 - NOT SUPPORTED as of ISAM4.6.02 "
	::= { bponPonConfigEntry 24 }

bponPonConfigGuarUpBwRemaining OBJECT-TYPE 
	SYNTAX INTEGER
	ACCESS read-only
	STATUS mandatory
	DESCRIPTION
	    	" Contains the guaranteed upstream bandwidth that remains for further
		   provisioning for this PON.  Units are Kilobits per second.
		   Range is 0 to 1,200,000 (1.2 Gig).

	For GPON - NOT SUPPORTED as of ISAM4.0.10
	For XG-PON1 - NOT SUPPORTED as of ISAM4.6.02 "
	::= { bponPonConfigEntry 25 }

bponPonConfigGuarDownBwRemaining OBJECT-TYPE 
	SYNTAX INTEGER
	ACCESS read-only
	STATUS mandatory
	DESCRIPTION
	    	" Contains the guaranteed downstream bandwidth that remains for further
		   provisioning for this PON.  Units are Kilobits per second.
		   Range is 0 to 2,400,000 (2.4 Gig).

	For GPON - NOT SUPPORTED as of ISAM4.0.10
	For XG-PON1 - NOT SUPPORTED as of ISAM4.6.02 "
	::= { bponPonConfigEntry 26 }


 bponPonConfigReach  OBJECT-TYPE
 	SYNTAX 	INTEGER
 	ACCESS	read-write
 	STATUS	mandatory
 	DESCRIPTION 
		 " This attribute provides the ability to set the maximum differential logical reach on the PON.
		   (Ranging differential window on the PON interface).

		Applicable only for GPON.

 		Range is 0 to 40. In FGU Release 4.7.4 only valid allowed values are 20, 34 and 40.  All other values will be denied for this attribute.

		 Default = 20 (KM).

 		Note: Modification of the value for this attribute is allowed only when PON is OOS

 		NOTE - For ISAM4.2, this attribute is NOT SUPPORTED.

 		NOTE: As of ISAM4.3, this attribute is SUPPORTED (with same allowed value constraints as FTTU4.7.4).
	For GPON - SUPPORTED as of ISAM4.3
	For XG-PON1 - SUPPORTED as of ISAM4.6.02 "
 
 ::= { bponPonConfigEntry 27 }


bponPonConfigMcastGemPmCollectInd  OBJECT-TYPE
   SYNTAX   INTEGER
   ACCESS   read-write
   STATUS   mandatory
   DESCRIPTION
      " This indicates whether OLT-side Multicast
         GEM Port Performance Monitors should be collected for this PON.

        1 = PM collection enabled
        2 = PM collection disabled

       Default = 2 = disabled. 

	For ISAM4.2, attribute is SUPPORTED (merged from FGU4.7.4).
	For GPON - SUPPORTED as of ISAM4.2
	For XG-PON1 - SUPPORTED as of ISAM4.6.02 "
   ::= { bponPonConfigEntry 28 }

bponPonConfigMcastGemPmNumPMIntervals  OBJECT-TYPE
   SYNTAX   INTEGER
   ACCESS   read-only
   STATUS   mandatory
   DESCRIPTION
      " Indicates the number of rows currently present
        in the gponMulticastServiceOltsideGemIntervalTable.  This
        is for convenience of the EMS, so that it can
       quickly determine how many rows should be
       uploaded. 

	For ISAM4.2, attribute is SUPPORTED (merged from FGU4.7.4). 
	For GPON - SUPPORTED as of ISAM4.2
	For XG-PON1 - SUPPORTED as of ISAM4.6.02 "
   ::= { bponPonConfigEntry 29 }

bponPonConfigBkgdRogueTestEnableDisableCmd  OBJECT-TYPE
        SYNTAX  INTEGER
        ACCESS  read-write
        STATUS  mandatory
        DESCRIPTION
                " This attribute allows the manager to manually enable or disable
                   Background PON rogue test diagnostic. Once enabled the test runs
		   autonomously every 12 hours.

                   Attribute values are as follows:
                   1 - Initiate Background 'PATTERN TEST' PON Rogue Test
                   2 - Disable Background 'PATTERN TEST' PON Rogue test

                 Default = 1 (in ISAM4.2.33) - Enable
	   Default = 2 (as of ISAM4.4) - Disable

	   In ISAM4.2.33, this is SUPPORTED.
	   As of ISAM4.4, this attribute is SUPPORTED (using the interval context established by the 
		bponPonConfigBkgdRogueTestInterval attribute). 
	For GPON - SUPPORTED as of ISAM4.2.33
	For XG-PON1 - SUPPORTED as of ISAM4.6.02 "
        ::= { bponPonConfigEntry 30 }

bponPonConfigAuthMethod  OBJECT-TYPE
   SYNTAX   INTEGER
   ACCESS   read-write
   STATUS   mandatory
   DESCRIPTION
      " ONT Authentication mode option for this pon interface level.
        supported values are:

         	1 = SN and SLID authentication only
         	2 = CT proprietary logical authentication (LOID) only
	3 = CT proprietary LOID precedence mix authentication - meaning both CHT LOID and SN  (SUPPORTED as of ISAM4.5)
	4 = LoidStd - means 988 standard LOID only - (introduced in ISAM4.5 for mib-readiness. SUPPORTED as of ISAM4.5.02)
	5 = LoidPreStd - 988 standard LOID precedence mix - means both standard LOID and SN - (introduced in ISAM4.5 for mib-readiness.
		SUPPORTED as of ISAM4.5.02)
	6 = LOID, SN and SLID mixing authentication

        Default = 1 = SN and SLID authentication.

        Modification is SUPPORTED, but only if PON port is Admin DOWN.

	For GPON - SUPPORTED as of ISAM4.5.02
	For XG-PON1 - SUPPORTED as of ISAM4.6.02 "
   ::= { bponPonConfigEntry 33 }


bponPonConfigBkgdRogueTestInterval  OBJECT-TYPE
        SYNTAX  INTEGER
        ACCESS  read-write
        STATUS  mandatory
        DESCRIPTION
                " This attribute is used in context with the bponPonConfigBkgdRogueTestEnableDisableCmd.
                   When background rogue test is enabled for this PON, this attribute establishes the frequency of test execution.

	     RANGE is 1 hour to 24 hours (in 15 minute intervals).
	     UNITS of this attribute is minutes (so only numbers divisible by 15 are permitted.
	     So allowed values are as follows: 60 ... 1410, 1440

                   Default = 720 (i.e. every 12 hours)

	For GPON - SUPPORTED as of ISAM4.4
	For XG-PON1 - SUPPORTED as of ISAM4.6.02 "
        ::= { bponPonConfigEntry 34 }

bponPonConfigBkgdStuckLaserTestCmd  OBJECT-TYPE
        SYNTAX  INTEGER
        ACCESS  read-write
        STATUS  mandatory
        DESCRIPTION
                " This attribute allows the manager to manually enable or disable
                   autonomous execution of the test for rogue ONTs with a stuck laser. 	     

                   Attribute values are as follows:
                   1 - Enable Stuck Laser Test autonomous execution
                   2 - Disable Stuck Laser Test autonomous execution

                 Default = 2

	For GPON - SUPPORTED as of ISAM4.4
	For XG-PON1 - SUPPORTED as of ISAM4.6.02 "
        ::= { bponPonConfigEntry 35 }

bponPonConfigTrafficThresholdUp OBJECT-TYPE 
	SYNTAX Gauge 
	ACCESS read-write 
	STATUS mandatory 
	DESCRIPTION 
	" This attribute is used to specify the upstream traffic threshold. Unit is kbps. If current transport rate is 
	higher than this value, pon traffic TCA will be raised. 
	This threshold will only take effect in case of PON trouble-shooting is enabled. 

	Default = 0, means threshold is disabled.
 
	For GPON - SUPPORTED as of ISAM4.6
	For XG-PON1 - SUPPORTED as of ISAM4.6.02 "
::= { bponPonConfigEntry 36 } 


bponPonConfigTrafficThresholdDn OBJECT-TYPE 
	SYNTAX Gauge 
	ACCESS read-write 
	STATUS mandatory 
	DESCRIPTION 
	" This attribute is used to specify the downstream traffic threshold. Unit is kbps. If current transport rate is 
	higher than this value, pon traffic TCA will be raised. 
	This threshold will only take effect in case of PON trouble-shooting is enabled. 

	Default = 0, means threshold is disabled. 

	For GPON - SUPPORTED as of ISAM4.6
	For XG-PON1 - SUPPORTED as of ISAM4.6.02 "
::= { bponPonConfigEntry 37 } 


bponPonConfigXgTag  OBJECT-TYPE
	SYNTAX 	OCTET STRING
	ACCESS	read-write
	STATUS	mandatory
	DESCRIPTION 
		" Used to specify PON-TAG attribute in 987.3 downstream PLOAM messages for this PON.

		 NOTE:  in the actual PLOAM message structure 'on the wire', this field is 8 bytes in length.

		 The 987.3 spec hints (but does not demand) that suggested format is similar to an ONT Serial Number, which is:
			1st 4 bytes are ASCII Vendor ID, and
			2nd 4 bytes are a 32 bit number

		 For ISAM4.6 migration purposes, assume this field is 8 bytes in length.

		VALIDATION:  Other than the value 'all zeroes', the value of this attribute must be UNIQUE among all PONs on the shelf.

		 For non-XGPON LT cards - Default = all zeroes
		 For XGPON LT cards - Default = all zeroes

		Modification SUPPORTED, but only if PON is Admin Down
	
		Introduced in ISAM4.6 MIB
	For GPON - NOT SUPPORTED as of ISAM4.6
	For XG-PON1 - SUPPORTED as of ISAM4.6.02 "
	::= { bponPonConfigEntry 38 }

bponPonConfigDsMulticastEncryptInd  OBJECT-TYPE
	SYNTAX 	INTEGER
	ACCESS	read-write
	STATUS	mandatory
	DESCRIPTION 
		" This indicates encryption mode for Multicast GEM.
	
		  1 = AES Encryption enabled
		  2 = Encryption Disabled

		 Default = 2 = disabled

		Modification SUPPORTED

		Introduced in ISAM4.6 MIB
	For GPON - NOT SUPPORTED as of ISAM4.6
	For XG-PON1 - SUPPORTED as of ISAM4.6.02 "
	::= { bponPonConfigEntry 39 }


bponPonConfigOltsideUpFecPmCollectInd  OBJECT-TYPE
	SYNTAX 	INTEGER
	ACCESS	read-write
	STATUS	mandatory
	DESCRIPTION 
		" This indicates whether upstream FEC Performance Monitors should be collected for this PON (at OLT-side).
	
		  1 = PM collection enabled
		  2 = PM collection disabled

		 Default = 2 = disabled

		Introduced in ISAM4.6 MIB
	For GPON - NOT SUPPORTED as of ISAM4.6
	For XG-PON1 - SUPPORTED as of ISAM4.6.02 "
	::= { bponPonConfigEntry 40 }


bponPonConfigOltsideUpFecPmNumPMIntervals  OBJECT-TYPE
	SYNTAX 	INTEGER
	ACCESS	read-only
	STATUS	mandatory
	DESCRIPTION 
		" Indicates the number of rows currently present
		  in the gponPonOltsideFecIntervalTable.  This
		  is for convenience of the EMS, so that it can
		 quickly determine how many rows should be 
		 uploaded.

		Introduced in ISAM4.6 MIB
 
	For GPON - NOT SUPPORTED as of ISAM4.6
	For XG-PON1 - NOT SUPPORTED as of ISAM4.6.02 
			attribute will always be zero, since associated history table is NOT SUPPORTED. "
	::= { bponPonConfigEntry 41 }

bponPonConfigOltsidePhyPmCollectInd  OBJECT-TYPE
	SYNTAX 	INTEGER
	ACCESS	read-write
	STATUS	mandatory
	DESCRIPTION 
		" This indicates whether Physical Layer Performance Monitors should be collected for this PON (at OLT-side).
	
		  1 = PM collection enabled
		  2 = PM collection disabled

		 Default = 2 = disabled

		Introduced in ISAM4.6 MIB
	For GPON - NOT SUPPORTED as of ISAM4.6
	For XG-PON1 - SUPPORTED as of ISAM4.6.02 "
	::= { bponPonConfigEntry 42 }


bponPonConfigOltsidePhyPmNumPMIntervals  OBJECT-TYPE
	SYNTAX 	INTEGER
	ACCESS	read-only
	STATUS	mandatory
	DESCRIPTION 
		" Indicates the number of rows currently present
		  in the gponPonOltsidePhyIntervalTable.  This
		  is for convenience of the EMS, so that it can
		 quickly determine how many rows should be 
		 uploaded.

		Introduced in ISAM4.6 MIB
 
	For GPON - NOT SUPPORTED as of ISAM4.6
	For XG-PON1 - NOT SUPPORTED as of ISAM4.6.02, 
		attribute will always be zero, since associated history table is NOT SUPPORTED. "
	::= { bponPonConfigEntry 43 }

bponPonConfigOltsideXgTcPmCollectInd  OBJECT-TYPE
	SYNTAX 	INTEGER
	ACCESS	read-write
	STATUS	mandatory
	DESCRIPTION 
		" This indicates whether XgTc Performance Monitors should be collected for this PON (at OLT-side).
	
		  1 = PM collection enabled
		  2 = PM collection disabled

		 Default = 2 = disabled

		Introduced in ISAM4.6 MIB
	For GPON - NOT SUPPORTED as of ISAM4.6
	For XG-PON1 - SUPPORTED as of ISAM4.6.02
	For NG-PON2 - NOT SUPPORTED as of ISAM5.2 (similar attribute SUPPORTED in 
		ng2ChanPairConfigTable of NG-PON2 MIB "
	::= { bponPonConfigEntry 44 }


bponPonConfigOltsideXgTcPmNumPMIntervals  OBJECT-TYPE
	SYNTAX 	INTEGER
	ACCESS	read-only
	STATUS	mandatory
	DESCRIPTION 
		" Indicates the number of rows currently present
		  in the gponPonOltsideXgTcIntervalTable.  This
		  is for convenience of the EMS, so that it can
		 quickly determine how many rows should be 
		 uploaded.

		Introduced in ISAM4.6 MIB
	For GPON - NOT SUPPORTED as of ISAM4.6
	For XG-PON1 - SUPPORTED as of ISAM4.6.02
	For NG-PON2 - NOT SUPPORTED as of ISAM5.2 (similar attribute SUPPORTED in 
		ng2ChanPairConfigTable of NG-PON2 MIB) "
	 

	::= { bponPonConfigEntry 45 }

bponPonConfigXgId		OBJECT-TYPE
	SYNTAX 	OCTET STRING
	ACCESS	read-write
	STATUS	mandatory
	DESCRIPTION 
		" Used to specify PON-ID field in 987.3 downstream PLOAM messages for this PON.

		 NOTE:  in the actual PLOAM message structure 'on the wire', this field is 51 bits in length.

		 For ISAM4.6 migration purposes, assume this field is 7 bytes in length.
		 For these 7 bytes (i.e. 56 bits), only the low-order 51 bits are relevant.
		 
		 VALIDATION:  The high-order 5 bits MUST all be zero.

		 For non-XGPON LT cards - Default = all zeroes
		 For XGPON LT cards - Default = all zeroes

		Modification SUPPORTED, but only if PON is Admin Down
	
		Introduced in ISAM4.6 MIB
	For GPON - NOT SUPPORTED as of ISAM4.6
	For XG-PON1 - SUPPORTED as of ISAM4.6.02  "
	::= { bponPonConfigEntry 46 }


bponPonConfigPonUtilPmCollectInd OBJECT-TYPE
	SYNTAX 	INTEGER
	ACCESS	read-write
	STATUS	mandatory
	DESCRIPTION 
		" This attribute was first introduced with ISAM5.2 (copied from FTTU4.9.20). 
           
           This attribute indicates whether Pon Utilization 
           Performance Monitors should be collected for this PON.
		1 = Enable PM collection 
		2 = Disable PM collection 
		3 = Inherit from System Level configuration 

		 Default = 3 = INHERIT 

		Introduced in ISAM5.2 MIB
	For GPON - SUPPORTED as of ISAM5.2
	For XG-PON1 - NOT SUPPORTED as of ISAM4.6.02 "
	::= { bponPonConfigEntry 47 }


bponPonConfigPonUtilNumPmIntervals OBJECT-TYPE
	SYNTAX 	INTEGER
	ACCESS	read-only
	STATUS	mandatory
	DESCRIPTION 
		" This attribute was first introduced with ISAM5.2 (copied from FTTU4.9.20). 

		  This attribute indicates the number of rows currently present
		  in the gponOltSidePonUtilPmIntervalTable.  This
		  is for convenience of the EMS, so that it can
		 quickly determine how many rows should be 
		 uploaded.

		Introduced in ISAM5.2 MIB
	For GPON - SUPPORTED as of ISAM5.2
	For XG-PON1 - NOT SUPPORTED as of ISAM4.6.02 "
	::= { bponPonConfigEntry 48 }


bponPonConfigPonUtilOntDetailSelector OBJECT-TYPE
	SYNTAX 	INTEGER
	ACCESS	read-write
	STATUS	mandatory
	DESCRIPTION 
		" This attribute was first introduced with ISAM5.2. 
           
           When PON Utilization PM collection is in enabled for this PON,
	   this attribute specifies whether detailed ONT PMs are
	   collected for following tables:
		- gponOltSideOntUtilPmCurrentIntervalTable
		- gponOltSideOntUtilPmIntervalTable

		1 = Enable PM collection 
		2 = Disable PM collection 
		3 = Inherit from System Level configuration 

		 Default = 3 = INHERIT

	For GPON - SUPPORTED as of ISAM5.2
	For XG-PON1 - NOT SUPPORTED as of ISAM4.6.02 "
	::= { bponPonConfigEntry 49 }


bponPonConfigPonUtilOntBulkDetailSelector OBJECT-TYPE
	SYNTAX 	INTEGER
	ACCESS	read-write
	STATUS	mandatory
	DESCRIPTION 
		" This attribute was first introduced with ISAM5.2. 
           
           When bponPonConfigPonUtilOntDetailSelector PM collection is in enabled for this PON,
	   this attribute specifies whether bulk detailed ONT PMs are
	   collected for following tables:

		- gponOltSideOntUtilBulkPmIntervalTable

		1 = Enable Bulk PM collection 
		2 = Disable Bulk PM collection 


		 Default = 2 = DISABLE

	For GPON - SUPPORTED as of ISAM5.2
	For XG-PON1 - NOT SUPPORTED as of ISAM4.6.02 "
	::= { bponPonConfigEntry 50 }


bponPonConfigAlienTestCmd  OBJECT-TYPE
        SYNTAX  INTEGER
        ACCESS  read-write
        STATUS  mandatory
        DESCRIPTION
                " This attribute allows the manager to manually enable or disable
                  execution of the test for alien disturbers. 	     

                   Attribute values are as follows:
                   1 - Enable Alien ONT Test execution
                   2 - Disable Alien ONT Test execution

                 Default = 2 = DISABLE

	For GPON - SUPPORTED as of ISAM5.2
	For XG-PON1 - not SUPPORTED as of ISAM4.6.02 "
        ::= { bponPonConfigEntry 51 }


bponPonConfigBkgdAlienTestCmd  OBJECT-TYPE
        SYNTAX  INTEGER
        ACCESS  read-write
        STATUS  mandatory
        DESCRIPTION
                " This attribute allows the manager to manually enable or disable
                   Background PON alien test diagnostic. Once enabled the test runs
		   autonomously periodically (using the interval context established by the 
		   bponPonConfigBkgdRogueTestInterval attribute).

                   Attribute values are as follows:
                   1 - Initiate Background PON Alien Test
                   2 - Disable Background PON Alien Test

	   	Default = 2

	For GPON - SUPPORTED as of ISAM5.2
	For XG-PON1 - not SUPPORTED as of ISAM4.6.02 "
        ::= { bponPonConfigEntry 52 }


bponPonConfigBkgdAlienTestInterval  OBJECT-TYPE
        SYNTAX  INTEGER
        ACCESS  read-write
        STATUS  mandatory
        DESCRIPTION
                " This attribute is used in context with the bponPonConfigBkgdAlienTestCmd.
                   When background alien test is enabled for this PON, this attribute establishes
		  the frequency of test execution.

	     RANGE is 30 minutes to 4 hours (in 30 minute intervals).
	     UNITS of this attribute is minutes (so only numbers divisible by 30 are permitted.
	     So allowed values are as follows: 30 ... 210, 240

                   Default = 30

	For GPON - SUPPORTED as of ISAM5.2
	For XG-PON1 - not SUPPORTED as of ISAM4.6.02 "
 
       ::= { bponPonConfigEntry 53 }

bponPonConfigPonIdInterval  OBJECT-TYPE
        SYNTAX  INTEGER
        ACCESS  read-write
        STATUS  mandatory
        DESCRIPTION
                " This attribute is used to specify the frequency of transmission of the PON-ID
		  PLOAM message for this PON.

	     RANGE is 0..60 (in 1 second intervals.

	     Default = 0 (meaning DO NOT send the message)

	     In-service modification is SUPPORTED

	For GPON - SUPPORTED as of ISAM5.2
	For XG-PON1 - not SUPPORTED as of ISAM4.6.02 "
        ::= { bponPonConfigEntry 54 }


bponPonConfigPonIdOdnClass  OBJECT-TYPE
        SYNTAX  INTEGER
        ACCESS  read-write
        STATUS  mandatory
        DESCRIPTION
                " This attribute is used to specify the Optical Class field of the PON laser in the PON-ID
		  PLOAM message for this PON.
		  
		0 = Class A
		1 = Class B
		2 = Class B+
		3 = Class C
		4 = Class C+
		255 = means to auto-detect from the optical transceive2

	     Default = 255

	     In-service modification is SUPPORTED

	For GPON - SUPPORTED as of ISAM5.2
	For XG-PON1 - not SUPPORTED as of ISAM4.6.02 "
        ::= { bponPonConfigEntry 55 }


bponPonConfigPonIdIdentifier	OBJECT-TYPE
	SYNTAX 	OCTET STRING
	ACCESS	read-write
	STATUS	mandatory
	DESCRIPTION 
		" This attribute is used to specify PON-ID field in the PON-ID PLOAM message for this PON.

		For ISAM5.2 migration purposes, assume this field is 7 bytes in length.

		VALIDATION:  Other than the value 'all zeroes', the value of this attribute 
		must be UNIQUE among all GPON PONs on the shelf.

		Modification SUPPORTED, but only if PON is Admin Down
	
	For GPON - SUPPORTED as of ISAM5.2
	For XG-PON1 - not SUPPORTED as of ISAM4.6.02 "
	::= { bponPonConfigEntry 56 }

bponPonConfigMaxRangingOnts  OBJECT-TYPE
        SYNTAX  INTEGER
        ACCESS  read-write
        STATUS  mandatory
        DESCRIPTION
                " This attribute allows the operator to configure the max raning onts
                   number in specified pon. The upstream bandwidth is calculated
                   according to this value.

		   Attribute values are as followings:
                   0         - indicate guaranteed bandwidth is calculated according to provisioned onts
                   1..128    - number pre-configured to calculate guaranteed bandwidth


	For GPON - SUPPORTED as of ISAM5.5
	For XG-PON1 - NOT SUPPORTED"

        DEFVAL  { 128 }
        ::= { bponPonConfigEntry 57 }

bponPonConfigTcontsPerFrame  OBJECT-TYPE
        SYNTAX  INTEGER
        ACCESS  read-write
        STATUS  mandatory
        DESCRIPTION
                " Represents the max service tconts number
                   per frame. The attribute is used to calculate
                   the guaranteed bandwidth.

		   Range is 1 to 64.


	For GPON - SUPPORTED as of ISAM5.5
	For XG-PON1 - NOT SUPPORTED"

        DEFVAL  { 64 }
        ::= { bponPonConfigEntry 58 }

bponPonConfigClearAlmRngMismatch OBJECT-TYPE
        SYNTAX  INTEGER {
                            clear(1)
                        }
        ACCESS  write-only
        STATUS  mandatory
        DESCRIPTION

                 "Represents the action of clearing the alarm of ranging
                   number mismatch.

                 
                 For GPON - SUPPORTED as of ISAM5.5
                 For XG-PON1 - NOT SUPPORTED"
        ::= { bponPonConfigEntry  59 }



-- *********************************************
-- The following table is essentially the same as the old 
-- aponPonDiscovOntTable.  However, the prefix of everything was
-- changed from apon to bpon - and the OID was changed to move
-- the table into the appropriate bpon group.  Although not proper,
-- this was done so that the OLT software could reuse as much
-- previous code as feasible, while using bpon prefix for everything.
--
--
-- BPON PON DISCOVERED ONT TABLE
--
--
-- For a specific PON, this table contains the 
-- Serial Numbers (and possibly SLID values) of
-- ONTs that have been auto-discovered via
-- Method B, but have not yet been manually
-- provisioned (i.e. ENTERED)
-- by the operator. In TL1, these are referred to as 
-- NEWONT alarms. The operator does not directly
-- create or delete rows in this table.  The OLT
-- agent automatically manages the creation and
-- deletion of rows. Rows are automatically created
-- when an ONT is auto-discovered on a specific PON.
-- Rows are not automatically deleted just because a
-- NEWONT alarm is cleared (the reason being that the
-- AMS still needs to reference the associated row to
-- determine the Serial Number and SLID for the
-- cleared NEWONT alarm). So, as opposed to fixed
-- rules for deleting entries, the OLT tends to re-use
-- entries as necessary. NEWONT alarms are normally
-- cleared under the following 2 circumstances:
-- 1) An operator (or the system) creates an ONT on a
-- PON (with a Serial Number) that has a match in this
-- table or 2) The OATD informs the OLT that a
-- previously dicovered Serial Number has dis-appeared.
-- This table is used to store ONT information that
-- is required to be displayed with the NEWONT alarm
-- (i.e. ONT's Serial Number and the Subscriber
-- Location ID - SLID). The table indexes (i.e. 
-- bponPonDiscovOntIfIndex and bponPonDiscovOntNum)
-- match up with the Index1 and Index 2 fields 
-- actually contained in the Alarm MIB (for a
-- NEWONT alarm).
--
-- For FGU4.0, this table is being re-used.  Comments are 
-- made regarding whether attribute is relevant to BPON,
-- GPON or both, etc. 
--
-- For ISAM4.0.10, this table is being re-used. 
-- Noted which attributes are relevant for ISAM4.0.10
--
-- This table is applicable for GPON, XG-PON1 and NG-PON2 
-- Noted which attributes are relevant for each flavor of each.
--
--	For GPON - SUPPORTED as of ISAM4.0.10
--	For XG-PON1 - SUPPORTED as of ISAM4.6.02
--	For NG-PON2 - SUPPORTED as of ISAM5.2 (for channel pairs) 
-- 
-- *********************************************

bponPonDiscovOntTable  OBJECT-TYPE
	SYNTAX SEQUENCE OF BponPonDiscovOntEntry
	ACCESS	not-accessible
	STATUS	mandatory
	::= { bponPonGroup 3 }

bponPonDiscovOntEntry  OBJECT-TYPE
	SYNTAX 	BponPonDiscovOntEntry
	ACCESS	not-accessible
	STATUS	mandatory
	INDEX	{ bponPonDiscovOntIfIndex,
		  bponPonDiscovOntNum }
	::= { bponPonDiscovOntTable 1 }

BponPonDiscovOntEntry ::= SEQUENCE {
	bponPonDiscovOntIfIndex			IfIndex,
	bponPonDiscovOntNum			INTEGER,
	bponPonDiscovOntSerialNum		OCTET STRING,
	bponPonDiscovOntSubsLocId		OCTET STRING,
	bponPonDiscovOntDisableIndicator		DisplayString,
	bponPonDiscovOntLogicalAuthId		DisplayString,
	bponPonDiscovOntEquipmentId		OCTET STRING,
	bponPonDiscovOntActualRateUp    ActualRateUp
}

bponPonDiscovOntIfIndex  OBJECT-TYPE
	SYNTAX 	IfIndex
	ACCESS	read-only
	STATUS	mandatory
	DESCRIPTION 
		"Each row is indexed by the ifIndex of the
		 PON or channel pair (which is algorithmically assigned based
		 on slot/port on the OLT line card).

		Applicable for both BPON and GPON.

		For ISAM4.0.10 - stays the same as latest FGU4.x 

		As of ISAM5.2, this table is also shared for NG-PON2 channel 
		pairs. Therefore, this index can represent the following:
		- PON ifIndex (for PONs)
		- ChannelPair ifIndex (for channel pairs)

		For GPON - SUPPORTED as of ISAM4.0.10
		For XG-PON1 - SUPPORTED as of ISAM4.6.02
		For NG-PON2 - SUPPORTED as of ISAM5.2 "
	::= { bponPonDiscovOntEntry 1 }

bponPonDiscovOntNum  OBJECT-TYPE
	SYNTAX 	INTEGER (1..128)
	ACCESS	read-only
	STATUS	mandatory
	DESCRIPTION 
		"Each row is also indexed by an
		 arbitrary number that ranges from 1 to 128.
		 This number is not viewable by the operator.
		 It is merely an index that is internally
		 managed by the OLT.

		Applicable for both BPON and GPON.

		For GPON - SUPPORTED as of ISAM4.0.10
		For XG-PON1 - SUPPORTED as of ISAM4.6.02
		For NG-PON2 - SUPPORTED as of ISAM5.2 "
	::= { bponPonDiscovOntEntry 2 }


bponPonDiscovOntSerialNum  OBJECT-TYPE
	SYNTAX 	OCTET STRING (SIZE(0..12))
	ACCESS	read-only
	STATUS	mandatory
	DESCRIPTION 
		"The displayable 983.2 Serial Number
		 of the ONT that has been auto-discovered
		 on the specific PON. A real Serial Number
		 is 8 bytes - i.e. 4 bytes of ASCII
		 Vendor ID (e.g. ALCL or CACC), followed by
		 4 bytes of pure binary. For display purposes,
		 this attribute is usually translated into
		 12 bytes of ASCII (with the last 8 bytes
		 being the ASCII hex translation of the 32
		 bit binary field).  This attribute contains
		 the displayable representation.

		  Applicable for both BPON and GPON.

		For GPON - SUPPORTED as of ISAM4.0.10
		For XG-PON1 - SUPPORTED as of ISAM4.6.02
		For NG-PON2 - SUPPORTED as of ISAM5.2 "
	::= { bponPonDiscovOntEntry 3 }

bponPonDiscovOntSubsLocId  OBJECT-TYPE
	SYNTAX 	OCTET STRING (SIZE(0..36))
	ACCESS	read-only
	STATUS	mandatory
	DESCRIPTION 
		"The Subscriber Location ID. This attribute is
		 received via proprietary PLOAM message
		 from those ONT's that support localized
		 entry from the ONT. 
  
		 Contains the binary representation of the SLID,
		 which could consist of ASCII characters and/or
		 non-ASCII octets. Management applications
		 (e.g. EMS, TL1 interface) should use the setting of
		 gponOltSlidInterpretationMode attribute in this MIB 
		 to interpret whether ASCII or hex display format.

		 For FGU4.4, the SYNTAX was changed from DisplayString
		 to OCTET STRING to expand the representation format.

		As of ISAM5.2, the SIZE of this attribute was expanded from 
		10 bytes to 36 bytes, in order to also accommodate the 
		36 byte Registration ID for NG-PON2 as defined in G989.3

		For GPON - SUPPORTED as of ISAM4.0.10 (10 SLID)
		For XG-PON1 - SUPPORTED as of ISAM4.6.02 (10 byte SLID)
		For NG-PON2 - SUPPORTED as of ISAM5.2 (36 byte Registration ID) "
	::= { bponPonDiscovOntEntry 4 }


bponPonDiscovOntDisableIndicator  OBJECT-TYPE
	SYNTAX 	DisplayString (SIZE(0..8))
	ACCESS	read-only
	STATUS	mandatory
	DESCRIPTION 
		" This attribute contains additional textual informaion
		 to be appended to a NEWONT alarm.  As of 4.6, the 
		 possible text strings are as follows:
		
		  DISABLED - meaning ONT has been told via a PLOAM message to turn off it's laser.
		  PWRERR - meaning extraneous power bursts have been detected for this ONT.
    		  DIFREACH - meaning ONT has been deactivated because its location on the PON has 
			exceeded its differential reach capability. This was added as of ISAM4.3.
		  SNBUNDLE - meaning ONT failed to bundle SN with LOID/SLID.  This was added as of ISAM4.6. 

		  'null string' (i.e. no text) - meaning none of the above are true.

		  Applicable only for GPON.

		For ISAM4.0.10 - stays the same as latest FGU4.x
		As of ISAM4.3, added support for DIFREACH string.
                 	As of ISAM4.6, added support for SNBUNDLE string. 

		For GPON - SUPPORTED as of ISAM4.6 (as above)
		For XG-PON1 - SUPPORTED as of ISAM4.6.02
		For NG-PON2 - SUPPORTED as of ISAM5.2  "
	::= { bponPonDiscovOntEntry 5 }


bponPonDiscovOntLogicalAuthId  OBJECT-TYPE
	SYNTAX 	DisplayString (SIZE(0..24))
	ACCESS	read-only
	STATUS	mandatory
	DESCRIPTION 
		" This attribute record the learned LOID from the ONU, 
		if ONT is failed in LOID authentication.

		For GPON - SUPPORTED as of ISAM4.6
		For XG-PON1 - SUPPORTED as of ISAM4.6.02
		For NG-PON2 - NOT SUPPORTED as of ISAM5.2, start to support from ISAM5.5. Only MIB is ready in ISAM5.4.01 " 
		
	::= { bponPonDiscovOntEntry 6 }

bponPonDiscovOntEquipmentId  OBJECT-TYPE
	SYNTAX 	OCTET STRING (SIZE(0..20))
	ACCESS	read-only
	STATUS	mandatory
	DESCRIPTION 
	" This attribute record the EquipmentId from the ONU,
    indicate the typeInfo of ONT.
           
	For GPON - SUPPORTED as of ISAM5.6.01" 
	
	::= { bponPonDiscovOntEntry 7 }
	
bponPonDiscovOntActualRateUp  OBJECT-TYPE
    SYNTAX  ActualRateUp
    ACCESS  read-only
    STATUS  mandatory
    DESCRIPTION
        " This object represents the actual ONT upstream rate as detected during ONT activation.

              Supported values (see also ActualRateUp) :
              unknown              (0) : the ONT is not yet activated (default)
              twoDotFiveGbps       (1) : the actual upstream rate of the ONT is 2.5Gpbs, applicable for NG-PON2/XG-PON ONTs
              tenGbps              (2) : the actual upstream rate of the ONT is 10Gpbs, applicable for NG-PON2/XGS-PON ONTs
              oneDotTwentyFiveGbps (3) : the actual upstream rate of the ONT is 1.25Gpbs, applicable for GPON ONTs

            SUPPORTED as of ISAM5.7.0.0"

    ::= { bponPonDiscovOntEntry 8 }

-- *********************************************
--
-- BPON PON ONT BIT ERROR STATS TABLE
--
--
-- For a specific PON, this table contains the 
-- the Upstream and Downstream Bit Error counts
-- for each ONT on the PON. For each ONT row,
-- this table also indicates whether the particular
-- ONT is ranged, not ranged (not disabled), manually disabled,
-- automatically disabled.  Table rows are automatically
-- created by the OLT when the PON is created. 
-- A row is created for each potential ONT on the PON
-- whether or not the ONT is registerd or physically
-- present.
-- 
-- This table was first introduced for FGU2.6.1, and
-- the feature will be carried forward for the FGU4.0 release.
-- For both those releases, the number of ONTs 
-- supported on a PON is 32. In future releases, when
-- greater numbers of ONTs on a PON are supported,
-- more ONT rows will be auto-created in this table.
--
-- For FGU4.0, this table is being re-used.  Comments are 
-- made regarding whether attribute is relevant to
-- GPON, XG-PON1, or NG-PON2. 
--
-- For GPON, as of ISAM4.0.10, this table is being re-used and SUPPORTED.
--
-- For XG-PON1 (as of ISAM4.6.01), this table exists but some attributes are
-- effectively NOT SUPPORTED.  See comments within attributes.
--
-- For NG-PON2, this table is NOT SUPPORTED
--
--	For GPON - SUPPORTED as of ISAM4.0.10 (for PONs)
--	For XG-PON1 - SUPPORTED as of ISAM4.6.02 
--	For NG-PON2 - NOT SUPPORTED
-- 
-- *********************************************

bponPonStatsBerTable  OBJECT-TYPE
	SYNTAX SEQUENCE OF BponPonStatsBerEntry
	ACCESS	not-accessible
	STATUS	mandatory
	::= { bponPonGroup 4 }

bponPonStatsBerEntry  OBJECT-TYPE
	SYNTAX 	BponPonStatsBerEntry
	ACCESS	not-accessible
	STATUS	mandatory
	INDEX	{ bponPonStatsBerIfIndex,
		  bponPonStatsBerOntNum }
	::= { bponPonStatsBerTable 1 }

BponPonStatsBerEntry ::= SEQUENCE {
	bponPonStatsBerIfIndex			IfIndex,
	bponPonStatsBerOntNum			INTEGER,
	bponPonStatsBerUpstream			Counter,
	bponPonStatsBerDownstream		Counter,
	bponPonStatsBerRangedInd		INTEGER
}

bponPonStatsBerIfIndex  OBJECT-TYPE
	SYNTAX 	IfIndex
	ACCESS	read-only
	STATUS	mandatory
	DESCRIPTION 
		"Each row is indexed by the ifIndex of the
		 PON  (which is algorithmically assigned based
		on slot/port on the OLT line card).


	For GPON - SUPPORTED as of ISAM4.0.10
	For XG-PON1 - SUPPORTED as of ISAM4.6.02
	For NG-PON2 - NOT SUPPORTED as of ISAM5.2 "
	::= { bponPonStatsBerEntry 1 }

bponPonStatsBerOntNum  OBJECT-TYPE
	SYNTAX 	INTEGER 
	ACCESS	read-only
	STATUS	mandatory
	DESCRIPTION 
		"Each row is also indexed by the number
		 of the ONT on the PON. Effectively, this
		 number is the last portion of the ONT's
		 TL1 AID.

		Applicable for both BPON and GPON.

	For GPON - SUPPORTED as of ISAM4.0.10
	For XG-PON1 - SUPPORTED as of ISAM4.6.02
	For NG-PON2 - NOT SUPPORTED as of ISAM5.2 "
	::= { bponPonStatsBerEntry 2 }


bponPonStatsBerUpstream  OBJECT-TYPE
	SYNTAX 	Counter
	ACCESS	read-only
	STATUS	mandatory
	DESCRIPTION 
		"Represents the number of Upstream Bit Error
		 counts for an ONT - since row creation
		 or since all counts for the entire PON were last
		 reset.

		 Default is 0 when row initially created.

	For GPON - SUPPORTED as of ISAM4.0.10
	For XG-PON1 - SUPPORTED as of ISAM4.6.02 (but count is always zero)
	For NG-PON2 - NOT SUPPORTED as of ISAM5.2 "

	::= { bponPonStatsBerEntry 3 }

bponPonStatsBerDownstream  OBJECT-TYPE
	SYNTAX 	Counter
	ACCESS	read-only
	STATUS	mandatory
	DESCRIPTION 
		"Represents the number of Downstream Bit Error
		 counts for an ONT - since row creation
		 or since all counts for the entire PON were last
		 reset.

		 Default is 0 when row initially created.

	For GPON - SUPPORTED as of ISAM4.0.10
	For XG-PON1 - SUPPORTED as of ISAM4.6.02 (but count is always zero)
	For NG-PON2 - NOT SUPPORTED as of ISAM5.2 "
	::= { bponPonStatsBerEntry 4 }


bponPonStatsBerRangedInd  OBJECT-TYPE
	SYNTAX 	INTEGER
	ACCESS	read-only
	STATUS	mandatory
	DESCRIPTION 
		" Indicates whether this ONT is currently
		  ranged or not - as follows:

		  0 = Not Ranged (and Not DISABLED)
		  1 = Ranged
		  2 = manually-DISABLED (by the operator)
 		  3 = auto-DISABLED (by the OLT)


		 Default is 0 when row initially created.


	For GPON - SUPPORTED as of ISAM4.0.10
	For XG-PON1 - SUPPORTED as of ISAM4.6.02 
	For NG-PON2 - NOT SUPPORTED as of ISAM5.2  "
	::= { bponPonStatsBerEntry 5 }


-- *********************************************
--
-- BPON PON BIT ERROR STATS RESET TABLE
--
--
-- For a specific PON, this table is used to reset all 
-- the Bit Error counts for all of the ONTs on that PON.
-- A row is automatically created by the OLT when the 
-- PON is created.
-- 
-- This table was first introduced for FGU2.6.1, and
-- the feature will be carried forward for the FGU4.0 release.
--
-- For FGU4.0, this table is being re-used.  Comments are 
-- made regarding whether attribute is relevant to BPON,
-- GPON or both, etc.
--  
-- For GPON, as of ISAM4.0.10, this table is being re-used and SUPPORTED.
--
-- For XG-PON1 (as of ISAM4.6.01), this table exists but some attributes are
-- effectively NOT SUPPORTED.  See comments within attributes.
--
-- For NG-PON2 (as of ISAM5.2), this table is NOT SUPPORTED.
--
--	For GPON - SUPPORTED as of ISAM4.0.10 (for PONs)
--	For XG-PON1 - SUPPORTED as of ISAM4.6.02
--	For NG-PON2 - NOT SUPPORTED as of ISAM5.2
-- 
-- *********************************************

bponPonStatsBerResetTable  OBJECT-TYPE
	SYNTAX SEQUENCE OF BponPonStatsBerResetEntry
	ACCESS	not-accessible
	STATUS	mandatory
	::= { bponPonGroup 5 }

bponPonStatsBerResetEntry  OBJECT-TYPE
	SYNTAX 	BponPonStatsBerResetEntry
	ACCESS	not-accessible
	STATUS	mandatory
	INDEX	{ bponPonStatsBerResetIfIndex }
	::= { bponPonStatsBerResetTable 1 }

BponPonStatsBerResetEntry ::= SEQUENCE {
	bponPonStatsBerResetIfIndex			IfIndex,
	bponPonStatsBerResetTrigger			INTEGER
}

bponPonStatsBerResetIfIndex  OBJECT-TYPE
	SYNTAX 	IfIndex
	ACCESS	read-only
	STATUS	mandatory
	DESCRIPTION 
		"Each row is indexed by the ifIndex of the
		 PON (which is algorithmically assigned based
		 on slot/port on the OLT line card).


	For GPON - SUPPORTED as of ISAM4.0.10 (for PONs)
	For XG-PON1 - SUPPORTED as of ISAM4.6.02
	For NG-PON2 - NOT SUPPORTED as of ISAM5.2 "
	::= { bponPonStatsBerResetEntry 1 }

bponPonStatsBerResetTrigger  OBJECT-TYPE
	SYNTAX 	INTEGER {
		reset(1)
	}
	ACCESS	read-write
	STATUS	mandatory
	DESCRIPTION 
		"Manager sets this attribute to trigger
		 reset of PON Bit Error counts.

		For GPON (as of ISAM4.0.10) this attribute is SUPPORTED.

		For XG-PON1 (as of ISAM4.6.01), this attribute can be SET, 
		but setting the trigger is effectively a NO-OP since the relevant counts are always 0.

	For GPON - SUPPORTED as of ISAM4.0.10 (for PONs)
	For XG-PON1 - SUPPORTED as of ISAM4.6.02
	For NG-PON2 - NOT SUPPORTED as of ISAM5.2 "
	::= { bponPonStatsBerResetEntry 2 }


-- *********************************************
--
-- GPON PON ALWAYS-ON AGGREGATE GEM PERFORMANCE
-- MONITOR CURRENT INTERVAL TABLE
--
-- This is a new table beginning with FGU4.2.
-- This current interval table contains various statistics collected for 
-- aggregate PON GEM ports (from OLT side of the PON) during the current
-- 15 minute interval of operation.  Statistics include the summation of all
-- GEM ports (excluding the GEM ports associated with OMCI and Multicast).
--
-- An instance of this table is auto-created/deleted in accordance with the setting of:
-- 'OLT-side Aggregate GEM PM Collect Indicator' setting of the PON Table (in this GPON MIB).
-- 'OLT-side Aggregate GEM PM Collect Indicator' setting of the ChannelPair Table (in NG-PON2 MIB).
--
-- For ISAM4.0.10, this table is being re-used. 
-- Noted which attributes are relevant for ISAM4.0.10  
--
--	For GPON - SUPPORTED as of ISAM4.0.10
--	For XG-PON1 - SUPPORTED as of ISAM4.6.02
--	For NG-PON2 - SUPPORTED as of ISAM5.2 (for channel pairs)
--
-- 
-- *********************************************


gponPonAggGemCurrentIntervalTable  OBJECT-TYPE
	SYNTAX SEQUENCE OF GponPonAggGemCurrentIntervalEntry
	ACCESS	not-accessible
	STATUS	mandatory
	::= { bponPonGroup 6 }


gponPonAggGemCurrentIntervalEntry  OBJECT-TYPE
	SYNTAX 	GponPonAggGemCurrentIntervalEntry
	ACCESS	not-accessible
	STATUS	mandatory
	DESCRIPTION 
		"An entry in the GPON PON GEM PM
		 Aggregate CurrentInterval Table. "
	INDEX	{ gponPonAggGemCurrentIntervalIndex }
	::= { gponPonAggGemCurrentIntervalTable 1 }

GponPonAggGemCurrentIntervalEntry ::= SEQUENCE {
	gponPonAggGemCurrentIntervalIndex			IfIndex,
	gponPonAggGemCurrentIntervalValidInd			Boolean,
	gponPonAggGemCurrentIntervalErrorFragsUp			Counter

}


gponPonAggGemCurrentIntervalIndex  OBJECT-TYPE
	SYNTAX 	IfIndex
	ACCESS	read-only
	STATUS	mandatory
	DESCRIPTION 
		"This index is the ifIndex of the PON or channel pair.

		For ISAM4.0.10 - stays the same as latest FGU4.x

		As of ISAM5.2, this table is also shared for NG-PON2 channel 
		pairs. Therefore, this index can represent the following:
		- PON ifIndex (for PONs)
		- ChannelPair ifIndex (for channel pairs)  "
	::= { gponPonAggGemCurrentIntervalEntry 1 }


gponPonAggGemCurrentIntervalValidInd  OBJECT-TYPE
	SYNTAX 	Boolean
	ACCESS	read-only
	STATUS	mandatory
	DESCRIPTION 
		"Indicates whether or not this CurrentInterval contains
		 valid PM counts. 

		 As of FGU4.2, NOT SUPPORTED

		For ISAM4.0.10 - stays the same as latest FGU4.x "
	::= { gponPonAggGemCurrentIntervalEntry 2 }


gponPonAggGemCurrentIntervalErrorFragsUp  OBJECT-TYPE
	SYNTAX 	Counter
	ACCESS	read-only
	STATUS	mandatory
	DESCRIPTION 
		"A count of Errored GEM Fragments (upstream).

		For ISAM4.0.10 - stays the same as latest FGU4.x "
	::= { gponPonAggGemCurrentIntervalEntry 3 }


-- *********************************************
--
-- GPON PON ALWAYS-ON AGGREGATE GEM PERFORMANCE  
-- MONITOR INTERVAL TABLE
--
-- This is a new table beginning with FGU4.2.
-- This interval table contains various statistics collected for 
-- aggregate PON GEM ports (from OLT side of the PON) over the previous
-- 8 hours of operation.  The past 8 hours are broken into 32 completed 15
-- minute intervals. Each row in this table represents one such interval. 
-- Statistics include the summation of all GEM ports (excluding the GEM ports
-- associated with OMCI and Multicast).
--
-- An instance of this table is auto-created/deleted in accordance with the setting of:
-- 'OLT-side Aggregate GEM PM Collect Indicator' setting of the PON Table (in this GPON MIB).
-- 'OLT-side Aggregate GEM PM Collect Indicator' setting of the ChannelPair Table (in NG-PON2 MIB).
--
-- For ISAM4.0.10, this table is being re-used. 
-- Noted which attributes are relevant for ISAM4.0.10
--
--	For GPON - SUPPORTED as of ISAM4.0.10
--	For XG-PON1 - SUPPORTED as of ISAM4.6.02
--	For NG-PON2 - SUPPORTED as of ISAM5.2 (for channel pairs)
--
-- 
-- *********************************************


gponPonAggGemIntervalTable  OBJECT-TYPE
	SYNTAX SEQUENCE OF GponPonAggGemIntervalEntry
	ACCESS	not-accessible
	STATUS	mandatory
	::= { bponPonGroup 7 }


gponPonAggGemIntervalEntry  OBJECT-TYPE
	SYNTAX 	GponPonAggGemIntervalEntry
	ACCESS	not-accessible
	STATUS	mandatory
	DESCRIPTION 
		"An entry in the GPON PON GEM PM
		 Aggregate Interval Table. "
	INDEX	{ gponPonAggGemIntervalIndex,
		  gponPonAggGemIntervalNumber }
	::= { gponPonAggGemIntervalTable 1 }

GponPonAggGemIntervalEntry ::= SEQUENCE {
	gponPonAggGemIntervalIndex			IfIndex,
	gponPonAggGemIntervalNumber		INTEGER,
	gponPonAggGemIntervalValidInd			Boolean,
	gponPonAggGemIntervalErrorFragsUp			Counter

}


gponPonAggGemIntervalIndex  OBJECT-TYPE
	SYNTAX 	IfIndex
	ACCESS	read-only
	STATUS	mandatory
	DESCRIPTION 
		"This index is the ifIndex of the PON or channel pair.

		For ISAM4.0.10 - stays the same as latest FGU4.x

		As of ISAM5.2, this table is also shared for NG-PON2 channel 
		pairs. Therefore, this index can represent the following:
		- PON ifIndex (for PONs)
		- ChannelPair ifIndex (for channel pairs)  "
	::= { gponPonAggGemIntervalEntry 1 }

gponPonAggGemIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.

		For ISAM4.0.10 - stays the same as latest FGU4.x  "
	::= { gponPonAggGemIntervalEntry 2 }


gponPonAggGemIntervalValidInd  OBJECT-TYPE
	SYNTAX 	Boolean
	ACCESS	read-only
	STATUS	mandatory
	DESCRIPTION 
		"Indicates whether or not this Interval contains
		 valid PM counts. 

		 As of FGU4.2, NOT SUPPORTED

		For ISAM4.0.10 - stays the same as latest FGU4.x "
	::= { gponPonAggGemIntervalEntry 3 }


gponPonAggGemIntervalErrorFragsUp  OBJECT-TYPE
	SYNTAX 	Counter
	ACCESS	read-only
	STATUS	mandatory
	DESCRIPTION 
		"A count of Errored GEM Fragments (upstream).

		For ISAM4.0.10 - stays the same as latest FGU4.x "
	::= { gponPonAggGemIntervalEntry 4 }


-- *********************************************
--
-- GPON PON AGGREGATE GEM PERFORMANCE MONITOR 
-- TCA THRESHOLD TABLE
--
-- This is a new table beginning with FGU4.2.
-- This table allows the manager to set TCA thresholds for various PMs collected for 
-- aggregate PON GEM ports (from OLT side of the PON) during the current
-- 15 minute interval of operation.
--
-- An instance of this table is auto-created/deleted in accordance with the setting of:
-- 'OLT-side Aggregate GEM PM Collect Indicator' setting of the PON Table (in this GPON MIB).
-- 'OLT-side Aggregate GEM PM Collect Indicator' setting of the ChannelPair Table (in NG-PON2 MIB).
--
-- For ISAM4.0.10, this table is being re-used. 
-- Noted which attributes are relevant for ISAM4.0.10 
--
--	For GPON - SUPPORTED as of ISAM4.0.10
--	For XG-PON1 - SUPPORTED as of ISAM4.6.02
--	For NG-PON2 - SUPPORTED as of ISAM5.2 (for channel pairs)
--
-- 
-- *********************************************


gponPonAggGemTCAThresholdTable  OBJECT-TYPE
	SYNTAX SEQUENCE OF GponPonAggGemTCAThresholdEntry
	ACCESS	not-accessible
	STATUS	mandatory
	::= { bponPonGroup 8 }


gponPonAggGemTCAThresholdEntry  OBJECT-TYPE
	SYNTAX 	GponPonAggGemTCAThresholdEntry
	ACCESS	not-accessible
	STATUS	mandatory
	DESCRIPTION 
		"An entry in the GPON PON GEM PM
		 Aggregate TCAThreshold Table. "
	INDEX	{ gponPonAggGemTCAThresholdIndex }
	::= { gponPonAggGemTCAThresholdTable 1 }

GponPonAggGemTCAThresholdEntry ::= SEQUENCE {
	gponPonAggGemTCAThresholdIndex			IfIndex,
	gponPonAggGemTCAEnable			INTEGER,
	gponPonAggGemTCAThresholdErrorFragsUp		Threshold


}


gponPonAggGemTCAThresholdIndex  OBJECT-TYPE
	SYNTAX 	IfIndex
	ACCESS	read-only
	STATUS	mandatory
	DESCRIPTION 
		"This index is the ifIndex of the PON or channel pair.

		For ISAM4.0.10 - stays the same as latest FGU4.x

		As of ISAM5.2, this table is also shared for NG-PON2 channel 
		pairs. Therefore, this index can represent the following:
		- PON ifIndex (for PONs)
		- ChannelPair ifIndex (for channel pairs)  "
	::= { gponPonAggGemTCAThresholdEntry 1 }


gponPonAggGemTCAEnable  OBJECT-TYPE
	SYNTAX 	INTEGER
	ACCESS	read-write
	STATUS	mandatory
	DESCRIPTION 
		"Allows the manager to enable/disable the reporting of
		 OLT-side Aggregate GEM TCAs for this PON. 

	
		  1 = TCA's enabled
		  2 = TCA's disabled

		 Default = 2 = disabled.

		For ISAM4.0.10 - stays the same as latest FGU4.x "
	::= { gponPonAggGemTCAThresholdEntry 2 }


gponPonAggGemTCAThresholdErrorFragsUp  OBJECT-TYPE
	SYNTAX 	Threshold
	ACCESS	read-write
	STATUS	mandatory
	DESCRIPTION 
		"TCA setting for Errored GEM Fragments (upstream).
		 A value of 4294967295 means that this threshold is disabled.

		 Default = 4294967295 

		For ISAM4.0.10 - stays the same as latest FGU4.x "
	::= { gponPonAggGemTCAThresholdEntry 3 }


-- *********************************************
--
-- GPON PON OLTSIDE OPERATIONAL INFO TABLE
--
-- This is a new table beginning with FGU4.5.5. 
--
-- It is used to retrieve OLT-SIDE current operational information 
-- regarding a PON (primarily optical transmit levels and laser
-- parameters). 
-- The operational information is significant in that
-- each time it is requested, the OLT directly retrieves   
-- the latest information regarding the PON.
-- A table row is created/deleted automatically by the OLT in a 
-- one-to-one relationship with the PonConfigTable (for PONs) or,
-- the ChanPairConfigTable (for channel pairs).
--
-- For ISAM4.0.10, this table is being re-used. 
-- Noted which attributes are relevant for ISAM4.0.10 
--
--	For GPON - SUPPORTED as of ISAM4.0.10
--	For XG-PON1 - SUPPORTED as of ISAM4.6.02
--	For NG-PON2 - SUPPORTED as of ISAM5.2 (for channel pairs)
--  
-- *********************************************

gponPonOltsideOpInfoTable  OBJECT-TYPE
	SYNTAX SEQUENCE OF GponPonOltsideOpInfoEntry
	ACCESS	not-accessible
	STATUS	mandatory
	::= { bponPonGroup 9 }

gponPonOltsideOpInfoEntry  OBJECT-TYPE
	SYNTAX 	GponPonOltsideOpInfoEntry
	ACCESS	not-accessible
	STATUS	mandatory
	INDEX	{ gponPonOltsideOpInfoIndex }
	::= { gponPonOltsideOpInfoTable 1 }

GponPonOltsideOpInfoEntry ::= SEQUENCE {
	gponPonOltsideOpInfoIndex			IfIndex,
	gponPonOltsideOpInfoTxOpticalSignalLevel		INTEGER,
	gponPonOltsideOpInfoTemp		INTEGER,
	gponPonOltsideOpInfoVoltage	INTEGER,
	gponPonOltsideOpInfoBiasCurrent	INTEGER,
	gponPonOltsideOpInfoVendorName	DisplayString,
	gponPonOltsideOpInfoPartNumber	DisplayString,
	gponPonOltsideOpInfoSerialNumber	DisplayString,
	gponPonOltsideOpInfoMfgDateCode	DisplayString,
	gponPonOltsideOpInfoSpecialFeatures INTEGER
}

gponPonOltsideOpInfoIndex  OBJECT-TYPE
	SYNTAX 	IfIndex
	ACCESS	read-only
	STATUS	mandatory
	DESCRIPTION 
		"Each row is indexed by the ifIndex of the PON or channel pair.

		For ISAM4.0.10 - stays the same as latest FGU4.x 


		As of ISAM5.2, this table is also shared for NG-PON2 channel 
		pairs. Therefore, this index can represent the following:
		- PON ifIndex (for PONs)
		- ChannelPair ifIndex (for channel pairs)  "
	::= { gponPonOltsideOpInfoEntry 1 }


gponPonOltsideOpInfoTxOpticalSignalLevel  OBJECT-TYPE
	SYNTAX 	INTEGER
	ACCESS	read-only
	STATUS	mandatory
	DESCRIPTION 
		" This attribute indicates the current level of the OLT's transmit optical signal
		  (as measured at the OLT side for this PON). 

		  Units are dBm with 0.1 dBm granularity. 	

		  Valid values are -30.0 dBm to +30.0 dBm, along with the special values 65534 and 65535.  This is 
		  represented by the INTEGER range: -300 to +300, and the special values 65534 and 65535.  

		  NOTE: The special value 65534 is used to indicate INVALID (meaning a valid measurement is currently
			unattainable for some reason). Try again later and might get a valid measurement.
		  NOTE: The special value 65535 is used to indicate NOT SUPPORTED (meaning the measurement
			functionality is not supported by this particular unit). Try again later and will get same answer
			(i.e. NOT SUPPORTED).
		  NOTE: For any actual reading lower or higher than the range, OLT will report the lower or higher limit
			of valid values -300 or +300.

		  Default = 65534 = INVALID

		For ISAM4.0.10 - stays the same as latest FGU4.x  "
        ::= { gponPonOltsideOpInfoEntry 2 }

gponPonOltsideOpInfoTemp  OBJECT-TYPE
	SYNTAX 	INTEGER
	ACCESS	read-only
	STATUS	mandatory
	DESCRIPTION 
		" This attribute indicates the current temperature of the optics module associated with this PON
		  (as measured at the OLT side for this PON). 

		  Units are degrees centigrade (C) with 0.01 C granularity. 	

		  Valid values are -100.00 C to +100.00 C, along with the special values 65534 and 65535.  This is 
		  represented by the INTEGER range: -10,000 to +10,000, and the special values 65534 and 65535.  

		  NOTE: The special value 65534 is used to indicate INVALID (meaning a valid measurement is currently
			unattainable for some reason). Try again later and might get a valid measurement.
		  NOTE: The special value 65535 is used to indicate NOT SUPPORTED (meaning the measurement
			functionality is not supported by this particular unit). Try again later and will get same answer
			(i.e. NOT SUPPORTED).
		  NOTE: For any actual reading lower or higher than the range, OLT will report the lower or higher limit
			of valid values -10,000 or +10,000.

		  Default = 65534 = INVALID 

		  Attribute is SUPPORTED as of FGU4.5.5 release.

		For ISAM4.0.10 - stays the same as latest FGU4.x  "
        ::= { gponPonOltsideOpInfoEntry 3 }


gponPonOltsideOpInfoVoltage  OBJECT-TYPE
	SYNTAX 	INTEGER
	ACCESS	read-only
	STATUS	mandatory
	DESCRIPTION 
		" This attribute indicates the current voltage of the optics module associated with this PON
		  (as measured at the OLT side for this PON). 

		  Units are Volts (V) with 0.01 V granularity. 	

		  Valid values are 0 V to +20.00, along with the special values 65534 and 65535.  This is 
		  represented by the INTEGER range:  0 to +2000, and the special values 65534 and 65535.  

		  NOTE: The special value 65534 is used to indicate INVALID (meaning a valid measurement is currently
			unattainable for some reason). Try again later and might get a valid measurement.
		  NOTE: The special value 65535 is used to indicate NOT SUPPORTED (meaning the measurement
			functionality is not supported by this particular unit). Try again later and will get same answer
			(i.e. NOT SUPPORTED).
		  NOTE: For any actual reading lower or higher than the range, OLT will report the lower or higher limit
			of valid values 0 or +2000.

		  Default = 65534 = INVALID 

		  Attribute is SUPPORTED as of FGU4.5.5 release.

		For ISAM4.0.10 - stays the same as latest FGU4.x  "
        ::= { gponPonOltsideOpInfoEntry 4 }

gponPonOltsideOpInfoBiasCurrent  OBJECT-TYPE
	SYNTAX 	INTEGER
	ACCESS	read-only
	STATUS	mandatory
	DESCRIPTION 
		" This attribute indicates the current bias current of the laser associated with this PON
		  (as measured at the OLT side for this PON). 

		  Units are milliamps (mA) with 1 mA granularity. 	

		  Valid values are 0 mA to +500 mA, along with the special values 65534 and 65535.  This is 
		  represented by the INTEGER range:  0 to +500, and the special values 65534 and 65535.  

		  NOTE: The special value 65534 is used to indicate INVALID (meaning a valid measurement is currently
			unattainable for some reason). Try again later and might get a valid measurement.
		  NOTE: The special value 65535 is used to indicate NOT SUPPORTED (meaning the measurement
			functionality is not supported by this particular unit). Try again later and will get same answer
			(i.e. NOT SUPPORTED).
		  NOTE: For any actual reading lower or higher than the range, OLT will report the lower or higher limit
			of valid values 0 or +500.

		  Default = 65534 = INVALID 

		  Attribute is SUPPORTED as of FGU4.5.5 release.

		For ISAM4.0.10 - stays the same as latest FGU4.x  "
        ::= { gponPonOltsideOpInfoEntry 5 }

gponPonOltsideOpInfoVendorName  OBJECT-TYPE
	SYNTAX  DisplayString
	ACCESS	read-only
	STATUS	mandatory
	DESCRIPTION 
		" This attribute indicates the vendor name associated with the optics module for this PON
		  (as measured at the OLT side for this PON). 

		  Maximum of 16 displayable characters (OLT will truncate if necessary).	  

		  NOTE: The special string UNKNOWN is used to indicate that a reading is currently
			unattainable for some reason.. Try again later and might get a valid reading.
		  NOTE: The null string is used to indicate NOT SUPPORTED (meaning that functionality is not
			supported by this particular unit). Try again later and will get same answer
			(i.e. NOT SUPPORTED).

		  Default = UNKNOWN 

		  Attribute is SUPPORTED as of FGU4.6 release.

		For ISAM4.0.10 - stays the same as latest FGU4.x  "
        ::= { gponPonOltsideOpInfoEntry 6 }

gponPonOltsideOpInfoPartNumber  OBJECT-TYPE
	SYNTAX  DisplayString
	ACCESS	read-only
	STATUS	mandatory
	DESCRIPTION 
		" This attribute indicates the model part number associated with the optics module for this PON
		  (as measured at the OLT side for this PON).

		  Maximum of 16 displayable characters (OLT will truncate if necessary). 	  

		  NOTE: The special string UNKNOWN is used to indicate that a reading is currently
			unattainable for some reason.. Try again later and might get a valid reading.
		  NOTE: The null string is used to indicate NOT SUPPORTED (meaning that functionality is not
			supported by this particular unit). Try again later and will get same answer
			(i.e. NOT SUPPORTED).

		  Default = UNKNOWN 

		  Attribute is SUPPORTED as of FGU4.6 release. 

		For ISAM4.0.10 - stays the same as latest FGU4.x "
        ::= { gponPonOltsideOpInfoEntry 7 }

gponPonOltsideOpInfoSerialNumber  OBJECT-TYPE
	SYNTAX  DisplayString
	ACCESS	read-only
	STATUS	mandatory
	DESCRIPTION 
		" This attribute indicates the serial number associated with the optics module for this PON
		  (as measured at the OLT side for this PON). 

		  Maximum of 16 displayable characters (OLT will truncate if necessary).	  

		  NOTE: The special string UNKNOWN is used to indicate that a reading is currently
			unattainable for some reason.. Try again later and might get a valid reading.
		  NOTE: The null string is used to indicate NOT SUPPORTED (meaning that functionality is not
			supported by this particular unit). Try again later and will get same answer
			(i.e. NOT SUPPORTED).

		  Default = UNKNOWN 

		  Attribute is SUPPORTED as of FGU4.6 release. 

		For ISAM4.0.10 - stays the same as latest FGU4.x "
        ::= { gponPonOltsideOpInfoEntry 8 }

gponPonOltsideOpInfoMfgDateCode  OBJECT-TYPE
	SYNTAX  DisplayString
	ACCESS	read-only
	STATUS	mandatory
	DESCRIPTION 
		" This attribute indicates the manufacturing date code associated with the optics module for this PON
		  (as measured at the OLT side for this PON). 

		  Maximum of 8 displayable characters (OLT will truncate if necessary).	  

		  NOTE: The special string UNKNOWN is used to indicate that a reading is currently
			unattainable for some reason.. Try again later and might get a valid reading.
		  NOTE: The null string is used to indicate NOT SUPPORTED (meaning that functionality is not
			supported by this particular unit). Try again later and will get same answer
			(i.e. NOT SUPPORTED).

		  Default = UNKNOWN 

		  Attribute is SUPPORTED as of FGU4.6 release.

		For ISAM4.0.10 - stays the same as latest FGU4.x  "
        ::= { gponPonOltsideOpInfoEntry 9 }

gponPonOltsideOpInfoSpecialFeatures  OBJECT-TYPE
	SYNTAX 	INTEGER (0..255)
	ACCESS	read-only
	STATUS	mandatory
	DESCRIPTION 
		"SpecialFeatures byte at address 116(decimal) of the EEPROM of the SFP module or
                 address 158(decimal) of the EEPROM of the XFP module. 
                 Following values are meaningfull for SFP:
                   20H : Default
                   21H : Supports 2500BASE-X 
                   22H : 10/100BASE FX/LX with PHY/SGMII
                   23H : 10/100/1000BASE-T Electrical with PHY/SGMII and without LOS
                   24H : 10/100/1000BASE-T with PHY/SGMII and with LOS
                   25H : Ethernet to E1/T1 
                   26H : GPON OLT
                   27H : GPON OLT OTDR capable 
                   2AH : EPON OLT
                   2BH : EPON OLT OTDR capable
                 Following values are meaningfull for XFP:
                   20H : Default
                   21H : 10/2.5G XG-PON1 OLT
                   22H : 10/10G, 10/2.5G TWDM NGPON2 OLT
                   25H : Dual GPON OLT
                   2AH : 10G EPON Asym OLT
                   2BH : 10G EPON Sym OLT

	  This attribute was first added in ISAM4.3
	  Values for XFP module were added as of ISAM5.2   "

	::= { gponPonOltsideOpInfoEntry 10 }



-- *********************************************
--
-- GPON PON PROTECTION TABLE
--
-- This table is used to associate 2 PONs into a protection arrangement.
-- PONs are designated as Primary and Secondary.  Rows are indexed by 
-- primary PON.  
--
-- Rows are created and deleted by the operator. 

-- For ISAM4.0.10, this table is being re-used. 
-- Noted which attributes are relevant for ISAM4.0.10
--
-- As of ISAM4.4, this entire table is NOT SUPPORTED.
-- As of ISAM4.4, PON protection mechanisms are subsumed into the EQUIPMENT MIB.
--
--	For GPON - NOT SUPPORTED as of ISAM4.4
--	For XG-PON1 - NOT SUPPORTED as of ISAM4.6.02
--	For NG-PON2 - NOT SUPPORTED as of ISAM5.2 
-- 
-- *********************************************

gponPonProtectTable  OBJECT-TYPE
	SYNTAX SEQUENCE OF GponPonProtectEntry
	ACCESS	not-accessible
	STATUS	mandatory
	::= { bponPonGroup 10 }

gponPonProtectEntry  OBJECT-TYPE
	SYNTAX 	GponPonProtectEntry
	ACCESS	not-accessible
	STATUS	mandatory
	INDEX	{ gponPonProtectPriPon }
	::= { gponPonProtectTable 1 }

GponPonProtectEntry ::= SEQUENCE {
	gponPonProtectPriPon			IfIndex,
	gponPonProtectRowStatus			RowStatus,
	gponPonProtectSecPon			IfIndex,
	gponPonProtectPriPonStatus		INTEGER,
	gponPonProtectSecPonStatus		INTEGER,
	gponPonProtectSwitchCommand		INTEGER,
	gponPonProtectLastSwitchReason		INTEGER	
}

gponPonProtectPriPon  OBJECT-TYPE
	SYNTAX 	IfIndex
	ACCESS	read-only
	STATUS	mandatory
	DESCRIPTION 
		"Each row is indexed by the ifIndex of the
		 primary PON.

		For ISAM4.0.10 - stays the same as latest FGU4.x

		As of ISAM4.4, this attribute (and entire table) are NOT SUPPORTED.  "
	::= { gponPonProtectEntry 1 }

gponPonProtectRowStatus  OBJECT-TYPE
	SYNTAX 	RowStatus
	ACCESS	read-write
	STATUS	mandatory
	DESCRIPTION 
		" All rows instantiated using 'create-and-go' to
		 mate 2 PONs in a protection group. Set to 'destroy' to eliminate 
		 the protection group.

		 RULE 1 - Cannot create a protection group on an LT card that doesn't support PON protection.

		 RULE 2 - Cannot delete a protection group if secondary PON is Admin UP.

		For ISAM4.0.10 - stays the same as latest FGU4.x

		As of ISAM4.4, this attribute (and entire table) are NOT SUPPORTED.   "
	::= { gponPonProtectEntry 2 }


gponPonProtectSecPon  OBJECT-TYPE
	SYNTAX 	IfIndex
	ACCESS	read-write
	STATUS	mandatory
	DESCRIPTION 
		" This attribute represents the ifIndex of the secondary PON. 
		
		   Must satisfy the following VALIDATIONs (otherwise
		   OLT should reject):
		   1) ifIndex must represent a real PON.
		   2) PON cannot have any provisioned (planned) ONTs.
		   3) Cannot mate a PON with itself.
		   4) Cannot mate with a PON that is already mated in a protection scheme.
		   5) As of FGU4.7, only very specific PONs can be mated for protection (i.e. 1 and 2 on same LT card,
		       3 and 4 on same LT card, etc).


		   No Default - must be supplied by manager. 

		   Modification NOT permitted.

		For ISAM4.0.10 - stays the same as latest FGU4.x

		As of ISAM4.4, this attribute (and entire table) are NOT SUPPORTED.  "
	::= { gponPonProtectEntry 3 }


gponPonProtectPriPonStatus OBJECT-TYPE
	SYNTAX 	INTEGER
	ACCESS	read-only
	STATUS	mandatory
	DESCRIPTION 
		" This attribute represents the status of the primary PON. 

		   Following DEFINITIONS apply:
		   Active - means the PON the system is using (or intends to use) for transmission.
		   Inactive - means the PON the system is NOT using for transmission.
		   Up - means the PON is capable of being used for transmission/reception.
		   Down - means the PON is NOT capable of being used for transmission/reception.
			This includes a PON that is ADMIN down as well as a PON that is down
			due to an operational fault).

		   Enumerations are as follows:

		   1 = Active Up
		   2 = Active Down
		   3 = Inactive Up
		   4 = Inctive Down 

		For ISAM4.0.10 - stays the same as latest FGU4.x

		As of ISAM4.4, this attribute (and entire table) are NOT SUPPORTED. "
	::= { gponPonProtectEntry 4 }

gponPonProtectSecPonStatus OBJECT-TYPE
	SYNTAX 	INTEGER
	ACCESS	read-only
	STATUS	mandatory
	DESCRIPTION 
		" This attribute represents the status of the secondary PON. 

		   Following DEFINITIONS apply:
		   Active - means the PON the system is using (or intends to use) for transmission.
		   Inactive - means the PON the system is NOT using for transmission.
		   Up - means the PON is capable of being used for transmission/reception.
		   Down - means the PON is NOT capable of being used for transmission/reception.
			This includes a PON that is ADMIN down as well as a PON that is down
			due to an operational fault).

		   Enumerations are as follows:

		   1 = Active Up
		   2 = Active Down
		   3 = Inactive Up
		   4 = Inctive Down 

		For ISAM4.0.10 - stays the same as latest FGU4.x

		As of ISAM4.4, this attribute (and entire table) are NOT SUPPORTED. "
	::= { gponPonProtectEntry 5 }

gponPonProtectSwitchCommand OBJECT-TYPE
	SYNTAX 	INTEGER
	ACCESS	read-write
	STATUS	mandatory
	DESCRIPTION 
		" This attribute is used to command a PON switch action.

		   Manager cannot supply a value for this attribute in row creation.  Attribute is not
		   intended to be read by manager.

		   0  = No switch action.  This is the DEFAULT auto-created by the system during 
		          row creation.  The manager cannot set this value..
		   1 = Switch from Primary PON to Secondary PON
		   2 = Switch from Secondary PON to Primary PON 

		   Following RULES apply:
		   1) Cannot switch to a PON that is Down (see above attribute for definition of Down).
		   2) Cannot switch to a PON that is already Active  (see above attribute for definition of Active).

		For ISAM4.0.10 - stays the same as latest FGU4.x

		As of ISAM4.4, this attribute (and entire table) are NOT SUPPORTED.  "
	::= { gponPonProtectEntry 6 }

gponPonProtectLastSwitchReason OBJECT-TYPE
	SYNTAX 	INTEGER
	ACCESS	read-only
	STATUS	mandatory
	DESCRIPTION 
		" This attribute contains the reason for the last PON switch (if any).

		   0 = No switch has occurred (since last LT startup).
		   1 = Manual switch due to PON Admin State change.
		   2 = Manual switch due to usage of Switch command.
		   3 = Automatic switch due to system determination. 

		For ISAM4.0.10 - stays the same as latest FGU4.x

		As of ISAM4.4, this attribute (and entire table) are NOT SUPPORTED.  "
	::= { gponPonProtectEntry 7 }

-- *********************************************
--
-- GPON PON SUMMARY INFO TABLE
--
-- This is a new table beginning with ISAM4.2. 
--
-- It is used to retrieve summary information for a specific PON.
--
-- A table row is created/deleted automatically by the OLT in a 
-- one-to-one relationship with the BPON PON CONFIG TABLE.
--
-- Support was descoped, so table is NOT SUPPORTED.
--
--	For GPON - NOT SUPPORTED as of ISAM4.2
--	For XG-PON1 - NOT SUPPORTED as of ISAM4.6.02
--	For NG-PON2 - NOT SUPPORTED as of ISAM5.2 
--  
-- *********************************************

gponPonSummaryInfoTable  OBJECT-TYPE
	SYNTAX SEQUENCE OF GponPonSummaryInfoEntry
	ACCESS	not-accessible
	STATUS	mandatory
	::= { bponPonGroup 12 }

gponPonSummaryInfoEntry  OBJECT-TYPE
	SYNTAX 	GponPonSummaryInfoEntry
	ACCESS	not-accessible
	STATUS	mandatory
	INDEX	{ gponPonSummaryInfoIndex }
	::= { gponPonSummaryInfoTable 1 }

GponPonSummaryInfoEntry ::= SEQUENCE {
	gponPonSummaryInfoIndex			IfIndex,
	gponPonSummaryInfoNumProvOnts		INTEGER,
	gponPonSummaryInfoNumDiscovOnts		INTEGER
}

gponPonSummaryInfoIndex  OBJECT-TYPE
	SYNTAX 	IfIndex
	ACCESS	read-only
	STATUS	mandatory
	DESCRIPTION 
		"Each row is indexed by the ifIndex of the PON.  "
	::= { gponPonSummaryInfoEntry 1 }


gponPonSummaryInfoNumProvOnts  OBJECT-TYPE
	SYNTAX 	INTEGER
	ACCESS	read-only
	STATUS	mandatory
	DESCRIPTION 
		" This attribute contains the number of provisioned ONTs for this PON
		  (i.e. number of relevant instances in bponOntTable). 

		  Range is 0 .. 128.

		  Default = 0  "
        ::= { gponPonSummaryInfoEntry 2 }

gponPonSummaryInfoNumDiscovOnts  OBJECT-TYPE
	SYNTAX 	INTEGER
	ACCESS	read-only
	STATUS	mandatory
	DESCRIPTION 
		" This attribute contains the number of ranged ONTs for this PON
		  that have not been provisioned.
		  (i.e. number of relevant instances in bponPonDiscovOntTable). 

		  Range is 0 .. 128.

		  Default = 0  "
        ::= { gponPonSummaryInfoEntry 3 }


-- *********************************************
--
-- GPON PON OLTSIDE UPSTREAM FEC PERFORMANCE MONITOR CURRENT INTERVAL TABLE
--
-- This table was first introduced with ISAM4.6 MIB.
-- It is only SUPPORTED beginning with ISAM4.6.01 release (only for XGPON).
--
-- This current interval table contains various OLT-side Upstream FEC counters
-- (for aggregate PON or channel pair) during the current
-- 15 minute interval of operation.  
--
-- An instance of this table is auto-created/deleted in accordance with the setting of:
-- 'OLT-side UP FEC PM Collect Indicator' setting of the PON Table (in this GPON MIB).
-- 'OLT-side UP FEC PM Collect Indicator' setting of the ChannelPair Table (in NG-PON2 MIB).
--
--	For GPON - NOT SUPPORTED as of ISAM4.6
--	For XG-PON1 - SUPPORTED as of ISAM4.6.02 (for PONs)
--	For NG-PON2 - SUPPORTED as of ISAM5.2 (for channel pairs)
--
-- 
-- *********************************************


gponPonOltsideFecCurrentIntervalTable  OBJECT-TYPE
	SYNTAX SEQUENCE OF GponPonOltsideFecCurrentIntervalEntry
	ACCESS	not-accessible
	STATUS	mandatory
	::= { bponPonGroup 14 }


gponPonOltsideFecCurrentIntervalEntry  OBJECT-TYPE
	SYNTAX 	GponPonOltsideFecCurrentIntervalEntry
	ACCESS	not-accessible
	STATUS	mandatory
	DESCRIPTION 
		"An entry in the GPON PON OLT-side FEC CurrentInterval Table. "
	INDEX	{ gponPonOltsideFecCurrentIntervalIndex }
	::= { gponPonOltsideFecCurrentIntervalTable 1 }

GponPonOltsideFecCurrentIntervalEntry ::= SEQUENCE {
	gponPonOltsideFecCurrentIntervalIndex			IfIndex,
	gponPonOltsideFecCurrentIntervalValidInd			Boolean,
	gponPonOltsideFecCurrentIntervalCorrectedBytes		OCTET STRING,
	gponPonOltsideFecCurrentIntervalCorrectedCodeWords		Counter,
	gponPonOltsideFecCurrentIntervalUncorrectedCodeWords		Counter,
	gponPonOltsideFecCurrentIntervalTotalCodeWords		Counter
}


gponPonOltsideFecCurrentIntervalIndex  OBJECT-TYPE
	SYNTAX 	IfIndex
	ACCESS	read-only
	STATUS	mandatory
	DESCRIPTION 
		"This index is the ifIndex of the PON or channel pair.

		As of ISAM5.2, this table is also shared for NG-PON2 channel 
		pairs. Therefore, this index can represent the following:
		- PON ifIndex (for PONs)
		- ChannelPair ifIndex (for channel pairs)  "
	::= { gponPonOltsideFecCurrentIntervalEntry 1 }


gponPonOltsideFecCurrentIntervalValidInd  OBJECT-TYPE
	SYNTAX 	Boolean
	ACCESS	read-only
	STATUS	mandatory
	DESCRIPTION 
		"Indicates whether or not this CurrentInterval contains
		 valid PM counts.

		 NOT SUPPORTED  "
	::= { gponPonOltsideFecCurrentIntervalEntry 2 }

gponPonOltsideFecCurrentIntervalCorrectedBytes  OBJECT-TYPE
	SYNTAX 	OCTET STRING (SIZE(8))
	ACCESS	read-only
	STATUS	mandatory
	DESCRIPTION 
		"A count of number of bytes that were corrected by the FEC function.  "
	::= { gponPonOltsideFecCurrentIntervalEntry 3 }

gponPonOltsideFecCurrentIntervalCorrectedCodeWords  OBJECT-TYPE
	SYNTAX 	Counter
	ACCESS	read-only
	STATUS	mandatory
	DESCRIPTION 
		"A count of number of code words that were corrected by the FEC function.  "
	::= { gponPonOltsideFecCurrentIntervalEntry 4 }

gponPonOltsideFecCurrentIntervalUncorrectedCodeWords  OBJECT-TYPE
	SYNTAX 	Counter
	ACCESS	read-only
	STATUS	mandatory
	DESCRIPTION 
		"A count of number of errored code words that could not be corrected by the FEC function.  "
	::= { gponPonOltsideFecCurrentIntervalEntry 5 }

gponPonOltsideFecCurrentIntervalTotalCodeWords  OBJECT-TYPE
	SYNTAX 	Counter
	ACCESS	read-only
	STATUS	mandatory
	DESCRIPTION 
		"A count of total number of received code words.  "
	::= { gponPonOltsideFecCurrentIntervalEntry 6 }


-- *********************************************
--
-- GPON PON OLTSIDE UPSTREAM FEC PERFORMANCE MONITOR INTERVAL TABLE
--
-- This table was first introduced with ISAM4.6 MIB.
--
-- This interval table contains various upstream FEC counters (for specified PON) collected over the previous
-- 8 hours of operation.  The past 8 hours are broken into 32 completed 15
-- minute intervals. Each row in this table represents one such interval.  
--
-- An instance of this table is auto-created/deleted in accordance with the 
-- 'OLT-side FEC PM Collect Indicator' setting of the ONT Table.
--
--	For GPON - NOT SUPPORTED as of ISAM4.6
--	For XG-PON1 - NOT SUPPORTED as of ISAM4.6.02
--	For NG-PON2 - NOT SUPPORTED as of ISAM5.2 
-- 
-- *********************************************


gponPonOltsideFecIntervalTable  OBJECT-TYPE
	SYNTAX SEQUENCE OF GponPonOltsideFecIntervalEntry
	ACCESS	not-accessible
	STATUS	mandatory
	::= { bponPonGroup 15 }


gponPonOltsideFecIntervalEntry  OBJECT-TYPE
	SYNTAX 	GponPonOltsideFecIntervalEntry
	ACCESS	not-accessible
	STATUS	mandatory
	DESCRIPTION 
		"An entry in the GPON PON OLT-side FEC Interval Table. "
	INDEX	{ gponPonOltsideFecIntervalIndex,
		    gponPonOltsideFecIntervalNumber }
	::= { gponPonOltsideFecIntervalTable 1 }

GponPonOltsideFecIntervalEntry ::= SEQUENCE {
	gponPonOltsideFecIntervalIndex			IfIndex,
	gponPonOltsideFecIntervalNumber			INTEGER,
	gponPonOltsideFecIntervalValidInd			Boolean,
	gponPonOltsideFecIntervalCorrectedBytes		OCTET STRING,
	gponPonOltsideFecIntervalCorrectedCodeWords		Counter,
	gponPonOltsideFecIntervalUncorrectedCodeWords		Counter,
	gponPonOltsideFecIntervalTotalCodeWords		Counter
}


gponPonOltsideFecIntervalIndex  OBJECT-TYPE
	SYNTAX 	IfIndex
	ACCESS	read-only
	STATUS	mandatory
	DESCRIPTION 
		"This index is the ifIndex of the PON.  "
	::= { gponPonOltsideFecIntervalEntry 1 }

gponPonOltsideFecIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.  "
	::= { gponPonOltsideFecIntervalEntry 2 }


gponPonOltsideFecIntervalValidInd  OBJECT-TYPE
	SYNTAX 	Boolean
	ACCESS	read-only
	STATUS	mandatory
	DESCRIPTION 
		"Indicates whether or not this Interval contains
		 valid PM counts.

		 NOT SUPPORTED  "
	::= { gponPonOltsideFecIntervalEntry 3 }

gponPonOltsideFecIntervalCorrectedBytes  OBJECT-TYPE
	SYNTAX 	OCTET STRING (SIZE(8))
	ACCESS	read-only
	STATUS	mandatory
	DESCRIPTION 
		"A count of number of bytes that were corrected by the FEC function.  "
	::= { gponPonOltsideFecIntervalEntry 4 }

gponPonOltsideFecIntervalCorrectedCodeWords  OBJECT-TYPE
	SYNTAX 	Counter
	ACCESS	read-only
	STATUS	mandatory
	DESCRIPTION 
		"A count of number of code words that were corrected by the FEC function.  "
	::= { gponPonOltsideFecIntervalEntry 5 }

gponPonOltsideFecIntervalUncorrectedCodeWords  OBJECT-TYPE
	SYNTAX 	Counter
	ACCESS	read-only
	STATUS	mandatory
	DESCRIPTION 
		"A count of number of errored code words that could not be corrected by the FEC function.  "
	::= { gponPonOltsideFecIntervalEntry 6 }

gponPonOltsideFecIntervalTotalCodeWords  OBJECT-TYPE
	SYNTAX 	Counter
	ACCESS	read-only
	STATUS	mandatory
	DESCRIPTION 
		"A count of total number of received code words.  "
	::= { gponPonOltsideFecIntervalEntry 7 }


-- *********************************************
--
-- GPON PON OLTSIDE PHYSICAL LAYER  PERFORMANCE MONITOR CURRENT INTERVAL TABLE
--
-- This table was first introduced with ISAM4.6 MIB.
-- It is only SUPPORTED beginning with ISAM4.6.01 release (only for XGPON).
--
-- This current interval table contains various OLT-side PHY counters 
-- (for a specific PON or channel-pair) during the current
-- 15 minute interval of operation.  
--
-- An instance of this table is auto-created/deleted in accordance with the setting of:
-- 'OLT-side Phy Layer PM Collect Indicator' setting of the PON Table (in this GPON MIB).
-- 'OLT-side Phy Layer PM Collect Indicator' setting of the ChannelPair Table (in NG-PON2 MIB). 
--
--	For GPON - NOT SUPPORTED as of ISAM4.6
--	For XG-PON1 - SUPPORTED as of ISAM4.6.02 (for PONs)
--	For NG-PON2 - SUPPORTED as of ISAM5.2 (for channel pairs)
--
-- 
-- *********************************************


gponPonOltsidePhyCurrentIntervalTable  OBJECT-TYPE
	SYNTAX SEQUENCE OF GponPonOltsidePhyCurrentIntervalEntry
	ACCESS	not-accessible
	STATUS	mandatory
	::= { bponPonGroup 16 }


gponPonOltsidePhyCurrentIntervalEntry  OBJECT-TYPE
	SYNTAX 	GponPonOltsidePhyCurrentIntervalEntry
	ACCESS	not-accessible
	STATUS	mandatory
	DESCRIPTION 
		"An entry in the GPON PON OLT-side Phy CurrentInterval Table. "
	INDEX	{ gponPonOltsidePhyCurrentIntervalIndex }
	::= { gponPonOltsidePhyCurrentIntervalTable 1 }

GponPonOltsidePhyCurrentIntervalEntry ::= SEQUENCE {
	gponPonOltsidePhyCurrentIntervalIndex			IfIndex,
	gponPonOltsidePhyCurrentIntervalValidInd			Boolean,
	gponPonOltsidePhyCurrentIntervalUpBip32ProtWords		OCTET STRING,
	gponPonOltsidePhyCurrentIntervalUpBip32BitErrors		OCTET STRING
}


gponPonOltsidePhyCurrentIntervalIndex  OBJECT-TYPE
	SYNTAX 	IfIndex
	ACCESS	read-only
	STATUS	mandatory
	DESCRIPTION 
		"This index is the ifIndex of the PON or channel pair.

		As of ISAM5.2, this table is also shared for NG-PON2 channel 
		pairs. Therefore, this index can represent the following:
		- PON ifIndex (for PONs)
		- ChannelPair ifIndex (for channel pairs)  "
	::= { gponPonOltsidePhyCurrentIntervalEntry 1 }


gponPonOltsidePhyCurrentIntervalValidInd  OBJECT-TYPE
	SYNTAX 	Boolean
	ACCESS	read-only
	STATUS	mandatory
	DESCRIPTION 
		"Indicates whether or not this CurrentInterval contains
		 valid PM counts.

		 NOT SUPPORTED  "
	::= { gponPonOltsidePhyCurrentIntervalEntry 2 }


gponPonOltsidePhyCurrentIntervalUpBip32ProtWords  OBJECT-TYPE
	SYNTAX 	OCTET STRING (SIZE(8))
	ACCESS	read-only
	STATUS	mandatory
	DESCRIPTION 
		" 64-bit counter of upstream received 4-byte words that are included in/protected by BIP-32 check  "
	::= { gponPonOltsidePhyCurrentIntervalEntry 3 }

gponPonOltsidePhyCurrentIntervalUpBip32BitErrors  OBJECT-TYPE
	SYNTAX 	OCTET STRING (SIZE(8))
	ACCESS	read-only
	STATUS	mandatory
	DESCRIPTION 
		" 64-bit counter of upstream received bit errors according to BIP-32 check  "
	::= { gponPonOltsidePhyCurrentIntervalEntry 4 }


-- *********************************************
--
-- GPON PON OLTSIDE PHYSICAL LAYER PERFORMANCE MONITOR INTERVAL TABLE
--
-- This table was first introduced with ISAM4.6 MIB.
--
-- This interval table contains various PHY layer counters collected over the previous
-- 8 hours of operation.  The past 8 hours are broken into 32 completed 15
-- minute intervals. Each row in this table represents one such interval.  
--
-- An instance of this table is auto-created/deleted in accordance with the 
-- 'OLT-side Phy layer PM Collect Indicator' setting of the PON Table.
--
--	For GPON - NOT SUPPORTED as of ISAM4.6
--	For XG-PON1 - NOT SUPPORTED as of ISAM4.6.02
--	For NG-PON2 - NOT SUPPORTED as of ISAM5.2 
-- 
-- *********************************************


gponPonOltsidePhyIntervalTable  OBJECT-TYPE
	SYNTAX SEQUENCE OF GponPonOltsidePhyIntervalEntry
	ACCESS	not-accessible
	STATUS	mandatory
	::= { bponPonGroup 17 }


gponPonOltsidePhyIntervalEntry  OBJECT-TYPE
	SYNTAX 	GponPonOltsidePhyIntervalEntry
	ACCESS	not-accessible
	STATUS	mandatory
	DESCRIPTION 
		"An entry in the GPON PON OLT-side PHY Interval Table. "
	INDEX	{ gponPonOltsidePhyIntervalIndex,
		    gponPonOltsidePhyIntervalNumber }
	::= { gponPonOltsidePhyIntervalTable 1 }

GponPonOltsidePhyIntervalEntry ::= SEQUENCE {
	gponPonOltsidePhyIntervalIndex			IfIndex,
	gponPonOltsidePhyIntervalNumber			INTEGER,
	gponPonOltsidePhyIntervalValidInd			Boolean,
	gponPonOltsidePhyIntervalUpBip32ProtWords		OCTET STRING,
	gponPonOltsidePhyIntervalUpBip32BitErrors		OCTET STRING
}


gponPonOltsidePhyIntervalIndex  OBJECT-TYPE
	SYNTAX 	IfIndex
	ACCESS	read-only
	STATUS	mandatory
	DESCRIPTION 
		"This index is the ifIndex of the PON.  "
	::= { gponPonOltsidePhyIntervalEntry 1 }

gponPonOltsidePhyIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.  "
	::= { gponPonOltsidePhyIntervalEntry 2 }


gponPonOltsidePhyIntervalValidInd  OBJECT-TYPE
	SYNTAX 	Boolean
	ACCESS	read-only
	STATUS	mandatory
	DESCRIPTION 
		"Indicates whether or not this CurrentInterval contains
		 valid PM counts.

		 NOT SUPPORTED  "
	::= { gponPonOltsidePhyIntervalEntry 3 }


gponPonOltsidePhyIntervalUpBip32ProtWords  OBJECT-TYPE
	SYNTAX 	OCTET STRING (SIZE(8))
	ACCESS	read-only
	STATUS	mandatory
	DESCRIPTION 
		" 64-bit counter of upstream received 4-byte words that are included in/protected by BIP-32 check  "
	::= { gponPonOltsidePhyIntervalEntry 4 }

gponPonOltsidePhyIntervalUpBip32BitErrors  OBJECT-TYPE
	SYNTAX 	OCTET STRING (SIZE(8))
	ACCESS	read-only
	STATUS	mandatory
	DESCRIPTION 
		" 64-bit counter of upstream received bit errors according to BIP-32 check  "
	::= { gponPonOltsidePhyIntervalEntry 5 }


-- *********************************************
--
-- GPON PON OLTSIDE XGPON TC  PERFORMANCE MONITOR CURRENT INTERVAL TABLE
--
-- This table was first introduced with ISAM4.6 MIB.
-- It is only SUPPORTED beginning with ISAM4.6.01 release (only for XGPON).
--
-- This current interval table contains various OLT-side XG TC counters 
-- (for a specific PON or channel-pair) during the current
-- 15 minute interval of operation.  
--
-- An instance of this table is auto-created/deleted in accordance with the setting of:
-- 'OLT-side XG TC Layer PM Collect Indicator' setting of the PON Table (in this GPON MIB).
-- 'OLT-side XG TX Layer PM Collect Indicator' setting of the ChannelPair Table (in NG-PON2 MIB). 
--
--	For GPON - NOT SUPPORTED as of ISAM4.6
--	For XG-PON1 - SUPPORTED as of ISAM4.6.02 (for PONs)
--	For NG-PON2 - SUPPORTED as of ISAM5.2 (for channel pairs)
--
-- 
-- *********************************************


gponPonOltsideXgTcCurrentIntervalTable  OBJECT-TYPE
	SYNTAX SEQUENCE OF GponPonOltsideXgTcCurrentIntervalEntry
	ACCESS	not-accessible
	STATUS	mandatory
	::= { bponPonGroup 18 }


gponPonOltsideXgTcCurrentIntervalEntry  OBJECT-TYPE
	SYNTAX 	GponPonOltsideXgTcCurrentIntervalEntry
	ACCESS	not-accessible
	STATUS	mandatory
	DESCRIPTION 
		"An entry in the GPON PON OLT-side XG TC CurrentInterval Table. "
	INDEX	{ gponPonOltsideXgTcCurrentIntervalIndex }
	::= { gponPonOltsideXgTcCurrentIntervalTable 1 }

GponPonOltsideXgTcCurrentIntervalEntry ::= SEQUENCE {
	gponPonOltsideXgTcCurrentIntervalIndex			IfIndex,
	gponPonOltsideXgTcCurrentIntervalValidInd			Boolean,
	gponPonOltsideXgTcCurrentIntervalRangeTimeMsgs		Counter
}


gponPonOltsideXgTcCurrentIntervalIndex  OBJECT-TYPE
	SYNTAX 	IfIndex
	ACCESS	read-only
	STATUS	mandatory
	DESCRIPTION 
		"This index is the ifIndex of the PON or channel pair.

		As of ISAM5.2, this table is also shared for NG-PON2 channel 
		pairs. Therefore, this index can represent the following:
		- PON ifIndex (for PONs)
		- ChannelPair ifIndex (for channel pairs)  "
	::= { gponPonOltsideXgTcCurrentIntervalEntry 1 }


gponPonOltsideXgTcCurrentIntervalValidInd  OBJECT-TYPE
	SYNTAX 	Boolean
	ACCESS	read-only
	STATUS	mandatory
	DESCRIPTION 
		"Indicates whether or not this CurrentInterval contains
		 valid PM counts.

		 NOT SUPPORTED  "
	::= { gponPonOltsideXgTcCurrentIntervalEntry 2 }


gponPonOltsideXgTcCurrentIntervalRangeTimeMsgs  OBJECT-TYPE
	SYNTAX 	Counter
	ACCESS	read-only
	STATUS	mandatory
	DESCRIPTION 
		" Count of downstream ranging time messages sent   "
	::= { gponPonOltsideXgTcCurrentIntervalEntry 3 }



-- *********************************************
--
-- GPON PON OLTSIDE XGPON TC PERFORMANCE MONITOR INTERVAL TABLE
--
-- This table was first introduced with ISAM4.6 MIB.
-- It is only SUPPORTED beginning with ISAM4.6.01 release (only for XGPON).
--
-- This interval table contains various XG TC layer counters collected over the previous
-- 8 hours of operation.  The past 8 hours are broken into 32 completed 15
-- minute intervals. Each row in this table represents one such interval.  
--
-- An instance of this table is auto-created/deleted in accordance with the setting of:
-- 'OLT-side XG TC Layer PM Collect Indicator' setting of the PON Table (in this GPON MIB).
-- 'OLT-side XG TX Layer PM Collect Indicator' setting of the ChannelPair Table (in NG-PON2 MIB).
--
--	For GPON - NOT SUPPORTED as of ISAM4.6
--	For XG-PON1 - SUPPORTED as of ISAM4.6.02
--	For NG-PON2 - SUPPORTED as of ISAM5.2 (for channel pairs)
--
-- 
-- *********************************************


gponPonOltsideXgTcIntervalTable  OBJECT-TYPE
	SYNTAX SEQUENCE OF GponPonOltsideXgTcIntervalEntry
	ACCESS	not-accessible
	STATUS	mandatory
	::= { bponPonGroup 19 }


gponPonOltsideXgTcIntervalEntry  OBJECT-TYPE
	SYNTAX 	GponPonOltsideXgTcIntervalEntry
	ACCESS	not-accessible
	STATUS	mandatory
	DESCRIPTION 
		"An entry in the GPON PON OLT-side XG TC Interval Table. "
	INDEX	{ gponPonOltsideXgTcIntervalIndex,
		    gponPonOltsideXgTcIntervalNumber }
	::= { gponPonOltsideXgTcIntervalTable 1 }

GponPonOltsideXgTcIntervalEntry ::= SEQUENCE {
	gponPonOltsideXgTcIntervalIndex			IfIndex,
	gponPonOltsideXgTcIntervalNumber			INTEGER,
	gponPonOltsideXgTcIntervalValidInd			Boolean,
	gponPonOltsideXgTcIntervalRangeTimeMsgs		Counter
}


gponPonOltsideXgTcIntervalIndex  OBJECT-TYPE
	SYNTAX 	IfIndex
	ACCESS	read-only
	STATUS	mandatory
	DESCRIPTION 
		"This index is the ifIndex of the PON or channel-pair.

		As of ISAM5.2, this table is also shared for NG-PON2 channel 
		pairs. Therefore, this index can represent the following:
		- PON ifIndex (for PONs)
		- ChannelPair ifIndex (for channel pairs)  "
	::= { gponPonOltsideXgTcIntervalEntry 1 }

gponPonOltsideXgTcIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.  "
	::= { gponPonOltsideXgTcIntervalEntry 2 }


gponPonOltsideXgTcIntervalValidInd  OBJECT-TYPE
	SYNTAX 	Boolean
	ACCESS	read-only
	STATUS	mandatory
	DESCRIPTION 
		"Indicates whether or not this CurrentInterval contains
		 valid PM counts.

		 NOT SUPPORTED  "
	::= { gponPonOltsideXgTcIntervalEntry 3 }


gponPonOltsideXgTcIntervalRangeTimeMsgs  OBJECT-TYPE
	SYNTAX 	Counter
	ACCESS	read-only
	STATUS	mandatory
	DESCRIPTION 
		" Count of downstream ranging time messages sent  "
	::= { gponPonOltsideXgTcIntervalEntry 4 }


-- *********************************************
--
-- GPON OLT-SIDE PON UTILIZATION PERFORMANCE MONITOR 
-- TCA THRESHOLD TABLE
--
-- This is a new table beginning with ISAM5.2 (copied and modified from FTTU4.9.20).
-- This table allows the manager to set TCA thresholds for various PON Utilization
-- PM attributes.
--
-- An instance of this table is auto-created/deleted in accordance with the setting of:
-- 'PON Util PM Collect Indicator' setting of the PON Table (in this GPON MIB).
-- 'Chan Pair Util PM Collect Indicator' setting of the ChannelPair Table (in NG-PON2 MIB).
--
-- This table is SUPPORTED as of ISAM5.2

--	For GPON - SUPPORTED as of ISAM5.2 (for PONs)
--	For XG-PON1 - NOT SUPPORTED as of ISAM4.6.02
--	For NG-PON2 - NOT SUPPORTED as of ISAM5.2.01 (for channel pairs), but see individual attributes for
--		noted exceptions.
-- *********************************************

gponOltSidePonUtilTCAThresholdTable  OBJECT-TYPE
	SYNTAX SEQUENCE OF GponOltSidePonUtilTCAThresholdEntry 
	ACCESS	not-accessible
	STATUS	mandatory
	::= { bponPonGroup 20 }


gponOltSidePonUtilTCAThresholdEntry  OBJECT-TYPE
	SYNTAX 	GponOltSidePonUtilTCAThresholdEntry 
	ACCESS	not-accessible
	STATUS	mandatory
	DESCRIPTION 
		"An entry in the GPON PON Utilization PM
		 TCA Threshold Table. "
	INDEX	{ gponOltSidePonUtilTCAThresholdIndex }
	::= { gponOltSidePonUtilTCAThresholdTable 1 }

GponOltSidePonUtilTCAThresholdEntry ::= SEQUENCE {
	gponOltSidePonUtilTCAThresholdIndex			IfIndex,
	gponOltSidePonUtilHighTCAEnable		INTEGER,
	gponOltSidePonUtilHighThresholdLevelDown	Threshold,
	gponOltSidePonUtilHighThresholdLevelUp		Threshold,
    	gponOltSidePonMcastUtilHighThresholdLevelDown    Threshold,
    	gponOltSidePonUtilHighThresholdDBACongestionUp    Threshold,
    	gponOltSidePonNumTcIntervals       INTEGER,
	gponOltSidePonUtilHighThresholdTxUcastDroppedPackets	OCTET STRING,
	gponOltSidePonUtilHighThresholdRxTotalDroppedPackets	OCTET STRING,
	gponOltSidePonUtilHighThresholdTxMcastDroppedPackets	OCTET STRING,
	gponOltSidePonUtilHighThresholdTxBcastDroppedPackets	OCTET STRING,
	gponOltSidePonUtilMediumThresholdLevelDown	Threshold,
	gponOltSidePonUtilMediumThresholdLevelUp		Threshold,
    	gponOltSidePonMcastUtilMediumThresholdLevelDown    Threshold,	
    	gponOltSidePonUtilMediumThresholdDBACongestionUp    Threshold,
	gponOltSidePonUtilMediumThresholdTxUcastDroppedPackets	OCTET STRING,
	gponOltSidePonUtilMediumThresholdRxTotalDroppedPackets	OCTET STRING,
	gponOltSidePonUtilMediumThresholdTxMcastDroppedPackets	OCTET STRING,
	gponOltSidePonUtilMediumThresholdTxBcastDroppedPackets	OCTET STRING,
	gponOltSidePonUtilLowThresholdLevelDown	Threshold,
	gponOltSidePonUtilLowThresholdLevelUp		Threshold,
    	gponOltSidePonMcastUtilLowThresholdLevelDown    Threshold,
    	gponOltSidePonUtilLowThresholdDBACongestionUp    Threshold,
	gponOltSidePonUtilLowThresholdTxUcastDroppedPackets	OCTET STRING,
	gponOltSidePonUtilLowThresholdRxTotalDroppedPackets	OCTET STRING,
	gponOltSidePonUtilLowThresholdTxMcastDroppedPackets	OCTET STRING,
	gponOltSidePonUtilLowThresholdTxBcastDroppedPackets	OCTET STRING,
	gponOltSidePonUtilDbaCongestionThreshold	Threshold,
	gponOltSidePonNumDbaTcIntervals		INTEGER

}

gponOltSidePonUtilTCAThresholdIndex  OBJECT-TYPE
	SYNTAX 	IfIndex
	ACCESS	read-only
	STATUS	mandatory
	DESCRIPTION 
		" This index is the ifIndex of the PON or channel pair.

		As of ISAM5.2.01, this table is also shared by GPON PONs and NG-PON2
		channel pairs. Therefore, this index can represent the following:
		- PON ifIndex (for PONs) - as of ISAM5.2
		- ChannelPair ifIndex (for channel pairs) - as of ISAM5.2.01

	For GPON - SUPPORTED as of ISAM5.2	
	For XG-PON1 - NOT SUPPORTED as of ISAM4.6.02	
	For NG-PON2 - NOT SUPPORTED as of ISAM5.2.01 (for channel-pairs) "

	::= { gponOltSidePonUtilTCAThresholdEntry 1 }


gponOltSidePonUtilHighTCAEnable  OBJECT-TYPE
	SYNTAX 	INTEGER
	ACCESS	read-write
	STATUS	mandatory
	DESCRIPTION
		" This attribute is used choose whether/how TCA alarms are enabled for this PON/channel-pair.
		 A value of 1 means that TCA alarms are enabled for this PON/channel pair.
        	 A value of 2 means that TCA alarms are disabled for this PON/channel-pair.
		 A value of 3 means - INHERIT - Inherits the system-wide TCA setting for the BW Utilization TCAs.  

		Default = 3

	For GPON - SUPPORTED as of ISAM5.2 (for PONs)	
	For XG-PON1 - NOT SUPPORTED as of ISAM4.6.02	
	For NG-PON2 - NOT SUPPORTED as of ISAM5.2.01 (for channel-pairs) "
   	::= { gponOltSidePonUtilTCAThresholdEntry 2 }

gponOltSidePonUtilHighThresholdLevelDown  OBJECT-TYPE
	SYNTAX 	Threshold
	ACCESS	read-write
	STATUS	mandatory
	DESCRIPTION 
         " High threshold TCA setting in percentage for total downstream traffic.

		 
		Range is 0..100, represented in percentage.

		A value of 0 means that this threshold is disabled.

           Default = 0

	For GPON - SUPPORTED as of ISAM5.2 	
	For XG-PON1 - NOT SUPPORTED as of ISAM4.6.02	
	For NG-PON2 - NOT SUPPORTED as of ISAM5.2.01 (for channel pairs) "
	::= { gponOltSidePonUtilTCAThresholdEntry 3 }


gponOltSidePonUtilHighThresholdLevelUp  OBJECT-TYPE
	SYNTAX 	Threshold
	ACCESS	read-write
	STATUS	mandatory
	DESCRIPTION 
        " High threshold TCA setting in percentage for total upstream traffic.

		 
		Range is 0..100, represented in percentage

		A value of 0 means that this threshold is disabled.

           Default = 0

	For GPON - SUPPORTED as of ISAM5.2 
	For XG-PON1 - NOT SUPPORTED as of ISAM4.6.02	
	For NG-PON2 - NOT SUPPORTED as of ISAM5.2.01 (for channel pairs)  "
	::= { gponOltSidePonUtilTCAThresholdEntry 4 }


gponOltSidePonMcastUtilHighThresholdLevelDown  OBJECT-TYPE
	SYNTAX 	Threshold
	ACCESS	read-write
	STATUS	mandatory
	DESCRIPTION 
         " High threshold TCA setting in percentage for downstream multicast traffic.
		 
		Range is 0..100, represented in percentage

		A value of 0 means that this threshold is disabled.

           Default = 0

	For GPON - SUPPORTED as of ISAM5.2	
	For XG-PON1 - NOT SUPPORTED as of ISAM4.6.02	
	For NG-PON2 - NOT SUPPORTED as of ISAM5.2.01 (for channel pairs)  "
	::= { gponOltSidePonUtilTCAThresholdEntry 5 }

gponOltSidePonUtilHighThresholdDBACongestionUp   OBJECT-TYPE
	SYNTAX 	Threshold
	ACCESS	read-write
	STATUS	mandatory
	DESCRIPTION 
        " High threshold TCA setting in percentage for DBA Congestion.
	  This percentage is in relationship to the 5-minute PM/TCA interval.

		Range is 0..100, represented in percentage

		A value of 0 means that this threshold is disabled.

           Default = 0


	For GPON - SUPPORTED as of ISAM5.2	
	For XG-PON1 - NOT SUPPORTED as of ISAM4.6.02	
	For NG-PON2 - NOT SUPPORTED as of ISAM5.2.01 (for channel pairs) "
	::= { gponOltSidePonUtilTCAThresholdEntry 6 }
 

gponOltSidePonNumTcIntervals   OBJECT-TYPE
	SYNTAX 	INTEGER (1..96)
	ACCESS	read-write
	STATUS	mandatory
	DESCRIPTION 
		" Number of contiguous intervals (history) necessary for the non-DBA 
          thresholds to be exceeded for TCA alarm generation.

		  Default = 1

	For GPON - SUPPORTED as of ISAM5.2	
	For XG-PON1 - NOT SUPPORTED as of ISAM4.6.02	
	For NG-PON2 - NOT SUPPORTED as of ISAM5.2.01 (for channel pairs) "
	::= { gponOltSidePonUtilTCAThresholdEntry 7 }



gponOltSidePonUtilHighThresholdTxUcastDroppedPackets     OBJECT-TYPE
        SYNTAX  OCTET STRING (SIZE(8))
        ACCESS  read-write
        STATUS  mandatory
        DESCRIPTION
                "High threshold for count of transmit downstream unicast dropped packets
		 in order to declare TCA alarm. 

		Range is 0 to  1,000,000,000

		A value of 0 means that this threshold is disabled.

		Default = 0  

	For GPON - SUPPORTED as of ISAM5.2	
	For XG-PON1 - NOT SUPPORTED as of ISAM4.6.02	
	For NG-PON2 - NOT SUPPORTED as of ISAM5.2.01 (for channel pairs)"                    
        ::= { gponOltSidePonUtilTCAThresholdEntry 8 }                    
               
   

gponOltSidePonUtilHighThresholdRxTotalDroppedPackets     OBJECT-TYPE
        SYNTAX  OCTET STRING (SIZE(8))
        ACCESS  read-write
        STATUS  mandatory
        DESCRIPTION
                "High threshold for count of receive upstream total dropped packets
		 in order to declare TCA alarm. 

		Range is 0 to  1,000,000,000

		A value of 0 means that this threshold is disabled.

		Default = 0  

	For GPON - SUPPORTED as of ISAM5.2	
	For XG-PON1 - NOT SUPPORTED as of ISAM4.6.02	
	For NG-PON2 - NOT SUPPORTED as of ISAM5.2.01 (for channel pairs) "                    
        ::= { gponOltSidePonUtilTCAThresholdEntry 9 }                                       


gponOltSidePonUtilHighThresholdTxMcastDroppedPackets     OBJECT-TYPE
        SYNTAX  OCTET STRING (SIZE(8))
        ACCESS  read-write
        STATUS  mandatory
        DESCRIPTION
                "High threshold for count of transmit downstream multicast dropped packets
		 in order to declare TCA alarm. 

		Range is 0 to  1,000,000,000

		A value of 0 means that this threshold is disabled.

		Default = 0  

	For GPON - SUPPORTED as of ISAM5.2	
	For XG-PON1 - NOT SUPPORTED as of ISAM4.6.02	
	For NG-PON2 - NOT SUPPORTED as of ISAM5.2.01 (for channel pairs) "                    
        ::= { gponOltSidePonUtilTCAThresholdEntry 10 }                                       
                

gponOltSidePonUtilHighThresholdTxBcastDroppedPackets     OBJECT-TYPE
        SYNTAX  OCTET STRING (SIZE(8))
        ACCESS  read-write
        STATUS  mandatory
        DESCRIPTION
                "High threshold for count of transmit downstream broadcast dropped packets
		 in order to declare TCA alarm. 

		Range is 0 to  1,000,000,000

		A value of 0 means that this threshold is disabled.

		Default = 0  

	For GPON - SUPPORTED as of ISAM5.2	
	For XG-PON1 - NOT SUPPORTED as of ISAM4.6.02	
	For NG-PON2 - NOT SUPPORTED as of ISAM5.2.01 (for channel pairs) "                    
        ::= { gponOltSidePonUtilTCAThresholdEntry 11 }



gponOltSidePonUtilMediumThresholdLevelDown  OBJECT-TYPE
	SYNTAX 	Threshold
	ACCESS	read-write
	STATUS	mandatory
	DESCRIPTION
         " Medium threshold TCA setting in percentage for total downstream traffic.

		 
		Range is 0..100, represented in percentage

		A value of 0 means that this threshold is disabled.

           Default = 0

 	For GPON - SUPPORTED as of ISAM5.2	
	For XG-PON1 - NOT SUPPORTED as of ISAM4.6.02	
	For NG-PON2 - NOT SUPPORTED as of ISAM5.2.01 (for channel pairs)  "
	::= { gponOltSidePonUtilTCAThresholdEntry 12 }


gponOltSidePonUtilMediumThresholdLevelUp  OBJECT-TYPE
	SYNTAX 	Threshold
	ACCESS	read-write
	STATUS	mandatory
	DESCRIPTION 
        " Medium threshold TCA setting in percentage for total upstream traffic.

		 
		Range is 0..100, represented in percentage

		A value of 0 means that this threshold is disabled.

           Default = 0

 	For GPON - SUPPORTED as of ISAM5.2	
	For XG-PON1 - NOT SUPPORTED as of ISAM4.6.02	
	For NG-PON2 - NOT SUPPORTED as of ISAM5.2.01 (for channel pairs)  "
	::= { gponOltSidePonUtilTCAThresholdEntry 13 }


gponOltSidePonMcastUtilMediumThresholdLevelDown  OBJECT-TYPE
	SYNTAX 	Threshold
	ACCESS	read-write
	STATUS	mandatory
	DESCRIPTION 
         " Medium threshold TCA setting in percentage for downstream multicast traffic.
		 
		Range is 0..100, represented in percentage

		A value of 0 means that this threshold is disabled.

           Default = 0

 	For GPON - SUPPORTED as of ISAM5.2	
	For XG-PON1 - NOT SUPPORTED as of ISAM4.6.02	
	For NG-PON2 - NOT SUPPORTED as of ISAM5.2.01 (for channel pairs)  "
	::= { gponOltSidePonUtilTCAThresholdEntry 14 }


gponOltSidePonUtilMediumThresholdDBACongestionUp   OBJECT-TYPE
	SYNTAX 	Threshold
	ACCESS	read-write
	STATUS	mandatory 
	DESCRIPTION 
        " Medium threshold TCA setting in percentage for DBA Congestion.
	  This percentage is in relationship to the 5-minute PM/TCA interval.

		Range is 0..100, represented in percentage

		A value of 0 means that this threshold is disabled.

           Default = 0

	For GPON - SUPPORTED as of ISAM5.2	
	For XG-PON1 - NOT SUPPORTED as of ISAM4.6.02	
	For NG-PON2 - NOT SUPPORTED as of ISAM5.2.01 (for channel pairs) "
	::= { gponOltSidePonUtilTCAThresholdEntry 15 }

gponOltSidePonUtilMediumThresholdTxUcastDroppedPackets     OBJECT-TYPE
        SYNTAX  OCTET STRING (SIZE(8))
        ACCESS  read-write
        STATUS  mandatory
        DESCRIPTION
                "Medium threshold for count of transmit downstream unicast dropped packets
		 in order to declare TCA alarm. 

		Range is 0 to  1,000,000,000

		A value of 0 means that this threshold is disabled.

		Default = 0  

	For GPON - SUPPORTED as of ISAM5.2	
	For XG-PON1 - NOT SUPPORTED as of ISAM4.6.02	
	For NG-PON2 - NOT SUPPORTED as of ISAM5.2.01 (for channel pairs) "                    
        ::= { gponOltSidePonUtilTCAThresholdEntry 16 }                    
               
   

gponOltSidePonUtilMediumThresholdRxTotalDroppedPackets     OBJECT-TYPE
        SYNTAX  OCTET STRING (SIZE(8))
        ACCESS  read-write
        STATUS  mandatory
        DESCRIPTION
                "Medium threshold for count of receive upstream total dropped packets
		 in order to declare TCA alarm. 

		Range is 0 to  1,000,000,000

		A value of 0 means that this threshold is disabled.

		Default = 0  

	For GPON - SUPPORTED as of ISAM5.2	
	For XG-PON1 - NOT SUPPORTED as of ISAM4.6.02	
	For NG-PON2 - NOT SUPPORTED as of ISAM5.2.01 (for channel pairs) "                    
        ::= { gponOltSidePonUtilTCAThresholdEntry 17 }                                       


gponOltSidePonUtilMediumThresholdTxMcastDroppedPackets     OBJECT-TYPE
        SYNTAX  OCTET STRING (SIZE(8))
        ACCESS  read-write
        STATUS  mandatory
        DESCRIPTION
                "Medium threshold for count of transmit downstream multicast dropped packets
		 in order to declare TCA alarm. 

		Range is 0 to  1,000,000,000

		A value of 0 means that this threshold is disabled.

		Default = 0  

	For GPON - SUPPORTED as of ISAM5.2	
	For XG-PON1 - NOT SUPPORTED as of ISAM4.6.02	
	For NG-PON2 - NOT SUPPORTED as of ISAM5.2.01 (for channel pairs) "                    
        ::= { gponOltSidePonUtilTCAThresholdEntry 18 }                                       
                

gponOltSidePonUtilMediumThresholdTxBcastDroppedPackets     OBJECT-TYPE
        SYNTAX  OCTET STRING (SIZE(8))
        ACCESS  read-write
        STATUS  mandatory
        DESCRIPTION
                "Medium threshold for count of transmit downstream broadcast dropped packets
		 in order to declare TCA alarm. 

		Range is 0 to  1,000,000,000

		A value of 0 means that this threshold is disabled.

		Default = 0  

	For GPON - SUPPORTED as of ISAM5.2	
	For XG-PON1 - NOT SUPPORTED as of ISAM4.6.02	
	For NG-PON2 - NOT SUPPORTED as of ISAM5.2.01 (for channel pairs) "                    
        ::= { gponOltSidePonUtilTCAThresholdEntry 19 }


gponOltSidePonUtilLowThresholdLevelDown  OBJECT-TYPE
	SYNTAX 	Threshold
	ACCESS	read-write
	STATUS	mandatory
	DESCRIPTION 
         " Low threshold TCA setting in percentage for total downstream traffic.

		 
		Range is 0..100, represented in percentage

		A value of 0 means that this threshold is disabled.

           Default = 0

	For GPON - SUPPORTED as of ISAM5.2	
	For XG-PON1 - NOT SUPPORTED as of ISAM4.6.02	
	For NG-PON2 - NOT SUPPORTED as of ISAM5.2.01 (for channel pairs)  "
	::= { gponOltSidePonUtilTCAThresholdEntry 20 }


gponOltSidePonUtilLowThresholdLevelUp  OBJECT-TYPE
	SYNTAX 	Threshold
	ACCESS	read-write
	STATUS	mandatory
	DESCRIPTION 
        " Low threshold TCA setting in percentage for total upstream traffic.

		 
		Range is 0..100, represented in percentage

		A value of 0 means that this threshold is disabled.

           Default = 0

	For GPON - SUPPORTED as of ISAM5.2	
	For XG-PON1 - NOT SUPPORTED as of ISAM4.6.02	
	For NG-PON2 - NOT SUPPORTED as of ISAM5.2.01 (for channel pairs)  "
	::= { gponOltSidePonUtilTCAThresholdEntry 21 }


gponOltSidePonMcastUtilLowThresholdLevelDown  OBJECT-TYPE
	SYNTAX 	Threshold
	ACCESS	read-write
	STATUS	mandatory
	DESCRIPTION 
         " Low threshold TCA setting in percentage for downstream multicast traffic.
		 
		Range is 0..100, represented in percentage

		A value of 0 means that this threshold is disabled.

           Default = 0

	For GPON - SUPPORTED as of ISAM5.2	
	For XG-PON1 - NOT SUPPORTED as of ISAM4.6.02	
	For NG-PON2 - NOT SUPPORTED as of ISAM5.2.01 (for channel pairs)  "
	::= { gponOltSidePonUtilTCAThresholdEntry 22 }


gponOltSidePonUtilLowThresholdDBACongestionUp   OBJECT-TYPE
	SYNTAX 	Threshold
	ACCESS	read-write
	STATUS	mandatory
 	DESCRIPTION 
        " Low threshold TCA setting in percentage for DBA Congestion.
	  This percentage is in relationship to the 5-minute PM/TCA interval.

		Range is 0..100, represented in percentage

		A value of 0 means that this threshold is disabled.

           Default = 0


	For GPON - SUPPORTED as of ISAM5.2	
	For XG-PON1 - NOT SUPPORTED as of ISAM4.6.02	
	For NG-PON2 - NOT SUPPORTED as of ISAM5.2.01 (for channel pairs) "
	::= { gponOltSidePonUtilTCAThresholdEntry 23 }


gponOltSidePonUtilLowThresholdTxUcastDroppedPackets     OBJECT-TYPE
        SYNTAX  OCTET STRING (SIZE(8))
        ACCESS  read-write
        STATUS  mandatory
        DESCRIPTION
                "Low threshold for count of transmit downstream unicast dropped packets
		 in order to declare TCA alarm. 

		Range is 0 to  1,000,000,000

		A value of 0 means that this threshold is disabled.

		Default = 0  

	For GPON - SUPPORTED as of ISAM5.2	
	For XG-PON1 - NOT SUPPORTED as of ISAM4.6.02	
	For NG-PON2 - NOT SUPPORTED as of ISAM5.2.01 (for channel pairs) "                    
        ::= { gponOltSidePonUtilTCAThresholdEntry 24 }                    
               
   

gponOltSidePonUtilLowThresholdRxTotalDroppedPackets     OBJECT-TYPE
        SYNTAX  OCTET STRING (SIZE(8))
        ACCESS  read-write
        STATUS  mandatory
        DESCRIPTION
                "Low threshold for count of receive upstream total dropped packets
		 in order to declare TCA alarm. 

		Range is 0 to  1,000,000,000

		A value of 0 means that this threshold is disabled.

		Default = 0  

	For GPON - SUPPORTED as of ISAM5.2	
	For XG-PON1 - NOT SUPPORTED as of ISAM4.6.02	
	For NG-PON2 - NOT SUPPORTED as of ISAM5.2.01 (for channel pairs) "                    
        ::= { gponOltSidePonUtilTCAThresholdEntry 25 }                                       


gponOltSidePonUtilLowThresholdTxMcastDroppedPackets     OBJECT-TYPE
        SYNTAX  OCTET STRING (SIZE(8))
        ACCESS  read-write
        STATUS  mandatory
        DESCRIPTION
                "Low threshold for count of transmit downstream multicast dropped packets
		 in order to declare TCA alarm. 

		Range is 0 to  1,000,000,000

		A value of 0 means that this threshold is disabled.

		Default = 0  

	For GPON - SUPPORTED as of ISAM5.2	
	For XG-PON1 - NOT SUPPORTED as of ISAM4.6.02	
	For NG-PON2 - NOT SUPPORTED as of ISAM5.2.01 (for channel pairs) "                    
        ::= { gponOltSidePonUtilTCAThresholdEntry 26 }                                       
                

gponOltSidePonUtilLowThresholdTxBcastDroppedPackets     OBJECT-TYPE
        SYNTAX  OCTET STRING (SIZE(8))
        ACCESS  read-write
        STATUS  mandatory
        DESCRIPTION
                "Low threshold for count of transmit downstream broadcast dropped packets
		 in order to declare TCA alarm. 

		Range is 0 to  1,000,000,000

		A value of 0 means that this threshold is disabled.

		Default = 0  

	For GPON - SUPPORTED as of ISAM5.2	
	For XG-PON1 - NOT SUPPORTED as of ISAM4.6.02	
	For NG-PON2 - NOT SUPPORTED as of ISAM5.2.01 (for channel pairs) "                    
        ::= { gponOltSidePonUtilTCAThresholdEntry 27 }

gponOltSidePonUtilDbaCongestionThreshold  OBJECT-TYPE
	SYNTAX 	Threshold
	ACCESS	read-write
	STATUS	mandatory
	DESCRIPTION
         " The percentage of actual congestion within a DBA grant window wherein
	   the system declares a congested window. NOTE:  This window is NOT the
	   same as the 5-minute PM/TCA periods.

		 
		Range is 0..100, represented in percentage

           Default = 90

 	For GPON - SUPPORTED as of ISAM5.2	
	For XG-PON1 - NOT SUPPORTED as of ISAM4.6.02	
	For NG-PON2 - NOT SUPPORTED as of ISAM5.2.01 (for channel pairs)  "
	::= { gponOltSidePonUtilTCAThresholdEntry 28 }

gponOltSidePonNumDbaTcIntervals   OBJECT-TYPE
	SYNTAX 	INTEGER (1..96)
	ACCESS	read-write
	STATUS	mandatory
	DESCRIPTION 
		" Number of contiguous intervals (history) necessary for the DBA 
          thresholds to be exceeded for TCA alarm generation.

		  Default = 1

	For GPON - SUPPORTED as of ISAM5.2	
	For XG-PON1 - NOT SUPPORTED as of ISAM4.6.02	
	For NG-PON2 - NOT SUPPORTED as of ISAM5.2.01 (for channel pairs) "
	::= { gponOltSidePonUtilTCAThresholdEntry 29 }


-- *********************************************
--
-- GPON OLTSIDE PON UTILIZATION STATS RESET TABLE
--
--
-- For a specific PON, this table is used to reset all 
-- current PMs in the following tables:
--	gponOltSidePonUtilPmCurrentIntervalTable
--	gponOltSidePonUtilTxOntPmCurrentIntervalTable
--	gponOltSidePonUtilRxOntPmCurrentIntervalTable
--	gponOltSideOntUtilPmCurrentIntervalTable
-- 
-- This table was first introduced for ISAM5.2
--
--
--	For GPON - SUPPORTED as of ISAM5.2
--	For XG-PON1 - NOT SUPPORTED as of ISAM4.6.02
--	For NG-PON2 - NOT SUPPORTED as of ISAM5.2.01 (for channel pairs)
-- 
-- *********************************************

gponOltSidePonUtilStatsResetTable  OBJECT-TYPE
	SYNTAX SEQUENCE OF GponOltSidePonUtilStatsResetEntry
	ACCESS	not-accessible
	STATUS	mandatory
	::= { bponPonGroup 21 }

gponOltSidePonUtilStatsResetEntry  OBJECT-TYPE
	SYNTAX 	GponOltSidePonUtilStatsResetEntry
	ACCESS	not-accessible
	STATUS	mandatory
	INDEX	{ ifIndex }
	::= { gponOltSidePonUtilStatsResetTable 1 }
-- ifIndex is the ifIndex of the PON or channel pair
--
--		As of ISAM5.2.01, this table is also shared by GPON PONs and NG-PON2
--		channel pairs. Therefore, this index can represent the following:
--			> PON ifIndex (for PONs) - as of ISAM5.2
--			> ChannelPair ifIndex (for channel pairs) - as of ISAM5.2.01

GponOltSidePonUtilStatsResetEntry ::= SEQUENCE {
	gponOltSidePonUtilStatsResetTrigger			INTEGER
}
gponOltSidePonUtilStatsResetTrigger  OBJECT-TYPE
	SYNTAX 	INTEGER 
	ACCESS	read-write
	STATUS	mandatory
	DESCRIPTION 
		"Manager sets this attribute to trigger
		 reset of PON Utilization Statistics.

		 The only valid SET for this attribute is the value = 1 (meaning to trigger the reset action).
		 For GET, GET-NEXT, the agent can return value 0 (which is meaningless, since this attribute is really intended to 
			be a trigger, and manager obtains no useful information from a GET).

		 Default = 0

	For GPON - SUPPORTED as of ISAM5.2	
	For XG-PON1 - NOT SUPPORTED as of ISAM4.6.02	
	For NG-PON2 - NOT SUPPORTED as of ISAM5.2.01 (for channel pairs) "
	::= { gponOltSidePonUtilStatsResetEntry 2 }

  
-- *********************************************
--
-- BPON POTS PORT TABLE
--
-- This is a new table beginning with FGU2.5.
-- This table contains a row for each provisioned POTS port on a
-- specific ONT. Rows are created dynamically by operator via
-- Create-and-go.  Some parameters are changeable once created.  
--
-- For FGU4.0, this table is being re-used.  Comments are 
-- made regarding whether attribute is relevant to BPON,
-- GPON or both, etc.  
--
-- For ISAM4.0.10, this table is being re-used. However, for ISAM 4.0.10,
-- rows are auto-created by agent.  The number of rows auto-created is
-- determined from the bponOntPlanCardTable.
-- Noted which attributes are relevant for ISAM4.0.10  
-- 
-- For ISAM4.2, this table is being re-used.
-- Noted which attributes are relevant for ISAM4.2 
--
-- VALIDATION: Beginning with ISAM4.2.02, for a specific ONT, a POTS port
-- can be associated with one of the following 3 Voip agent types: legacy, standard MGC,
-- or standard SIP.  The legacy versus standard style decision is controlled via the
-- bponOntVoipCapability attribute in bponOntVoipTable.  The standard MGC versus 
-- standard SIP decision is controlled via mutually exclusive pointers in the 
-- bponPotsPortMgcConfigPointer and bponPotsPortSipConfigPointer attributes of this table.
-- Once the OLT has sufficient information to clearly know the VoIP agent type selection, it
-- should reject SET commands on POTS port attributes that are irrelevant for the known VoIP agent type.
--
-- VALIDATION:  As of ISAM4.3,  bponOntVoipCapability attribute was extended to also support what is
-- known as Veip-style VOIP.  POTS ports (as represented in this table) are also relevant for provisioning
-- when mode is Veip-style VOIP, but only a subset of table attributes are relevant for this mode. Hopefully,
-- the specific relevance is indicated within the individual attribute descriptions within.
--
--	For GPON - SUPPORTED as of ISAM4.0.10
--	For XG-PON1 - SUPPORTED as of ISAM4.6.02
--  For NG-PON2 - SUPPORTED as of ISAM5.4.01
--                Attributes that are only relevant for legacy and/or MEGACO 
--                are not relevant for NG-PON2.
--
-- *********************************************

bponPotsPortTable  OBJECT-TYPE
	SYNTAX SEQUENCE OF BponPotsPortEntry
	ACCESS	not-accessible
	STATUS	mandatory
	::= { bponPotsGroup 1 }


bponPotsPortEntry  OBJECT-TYPE
	SYNTAX 	BponPotsPortEntry
	ACCESS	not-accessible
	STATUS	mandatory
	INDEX	{ bponPotsPortOntIndex,
		   bponPotsPortSpIndex }
	::= { bponPotsPortTable 1 }

BponPotsPortEntry ::= SEQUENCE {
	bponPotsPortOntIndex		IfIndex,
	bponPotsPortSpIndex		SpIndex,
	bponPotsPortRowStatus		RowStatus,
	bponPotsPortAdminState		AdminState,
	bponPotsPortArc			INTEGER,
	bponPotsPortArcInterval		INTEGER,
	bponPotsPortImpedance		INTEGER,
	bponPotsPortTransmissionPath	INTEGER,
        	bponPotsPortRxGain		INTEGER,
	bponPotsPortTxGain		INTEGER,
	bponPotsPortSignallingCode		INTEGER,
	bponPotsPortRobbedBitSig		INTEGER,
	bponPotsPortSilenceSuppressInd 		Boolean,
	bponPotsPortVoiceCompression		INTEGER,
	bponPotsPortVpi					INTEGER,
	bponPotsPortVci				INTEGER,
	bponPotsPortCid				INTEGER,
	bponPotsPortMltTestCmd			INTEGER,
	bponPotsPortMltTestResult		OCTET STRING,
	bponPotsPortCustomerInfo		OCTET STRING,
	bponPotsPortOperState		OperState,
	bponPotsPortVoipServiceIndex		INTEGER,
	bponPotsPortCurrStatus		INTEGER,
	bponPotsPortTerminationId		OCTET STRING,
	bponPotsPortDscpSetting		INTEGER,
	bponPotsPortPwrShedOverride	Boolean,
	bponPotsPortCallHistCollectInd	INTEGER,
	bponPotsPortVoltageHoldoverTimer	INTEGER,
	bponPotsPortSipMsgTimeoutTCAThreshold	INTEGER,
	bponPotsPortBearerPktLossTCAThreshold	INTEGER,
	bponPotsPortJitterTCAThreshold	INTEGER,
	bponPotsPortMgcConfigPointer		InterfaceIndexOrZero,
	bponPotsPortSipConfigPointer		InterfaceIndexOrZero,
	bponPotsPortVoipMediaPointer	AsamProfilePointer,
	bponPotsPortSipUserPartAorPointer	DisplayString,
	bponPotsPortSipDisplayName	DisplayString,
--	bponPotsPortSipUserPassPointer		AsamProfilePointer,
	bponPotsPortSipVoicemailUriPointer	AsamProfilePointer,
	bponPotsPortSipVoicemailExpireTime	INTEGER,
	bponPotsPortSipNetDialPlanPointer	AsamProfilePointer,
	bponPotsPortSipAppServicesPointer	AsamProfilePointer,
	bponPotsPortSipFeatAccessCodePointer		AsamProfilePointer,
	bponPotsPortSipReleaseTimer	INTEGER,
	bponPotsPortSipRohTimer		INTEGER,
	bponPotsPortCallCntlPmCollectInd	INTEGER,
	bponPotsPortCallCntlNumPMIntervals	INTEGER,
	bponPotsPortRtpPmCollectInd	INTEGER,
	bponPotsPortRtpNumPMIntervals	INTEGER,
	bponPotsPortSipValidScheme	INTEGER,
	bponPotsPortSipUsername		DisplayString,
	bponPotsPortSipPassword		DisplayString,
	bponPotsPortSipRealm		DisplayString,
	bponPotsPortFileNamePart		DisplayString,
	bponPotsPortVeipPointer		SpIndexOrZero
}


bponPotsPortOntIndex  OBJECT-TYPE
	SYNTAX 	IfIndex
	ACCESS	read-only
	STATUS	mandatory
	DESCRIPTION 
		"Each row is indexed by the ifIndex of the ONT

		Applicable for both BPON, GPON, and NG-PON2.

		For ISAM4.0.10 - stays the same as latest FGU4.x
		For ISAM4.2, stays the same as previous ISAM.
		For ISAM4.3, stays the same as previous ISAM.  "
	::= { bponPotsPortEntry 1 }


bponPotsPortSpIndex  OBJECT-TYPE
	SYNTAX 	SpIndex
	ACCESS	read-only
	STATUS	mandatory
	DESCRIPTION 
		"Each row is also indexed by a number that
		 contains the slot number and port number
		 within the ONT.

		Applicable for both BPON, GPON, and NG-PON2.

		For ISAM4.0.10 - stays the same as latest FGU4.x
		For ISAM4.2, stays the same as previous ISAM. 
		For ISAM4.3, stays the same as previous ISAM. "
	::= { bponPotsPortEntry 2 }



bponPotsPortRowStatus  OBJECT-TYPE
	SYNTAX 	RowStatus
	ACCESS	read-write
	STATUS	mandatory
	DESCRIPTION 
		" All rows instantiated using 'create-and-go' to
		 provision a POTS port. Set to 'destroy' to delete
		 a POTS port.

		  Applicable for both BPON, GPON, and NG-PON2.

		For ISAM4.0.10 - this attribute is NOT SUPPORTED.
		For ISAM4.2, stays the same as previous ISAM.
		For ISAM4.3, stays the same as previous ISAM.  "
	::= { bponPotsPortEntry 3 }

bponPotsPortAdminState  OBJECT-TYPE
	SYNTAX 	AdminState
	ACCESS	read-write
	STATUS	mandatory
	DESCRIPTION 
		"For OMCI messaging, this attribute translates
		 into Admin State for the PPTP POTS UNI.  
		 Setting it to 'locked' deactivates the particular
		 POTS port.
		 Modification permitted even after row
		 becomes 'active'.
		 Default = locked

		  Applicable for both BPON, GPON, and NG-PON2.

		For ISAM4.0.10 - stays the same as latest FGU4.x
		For ISAM4.2, stays the same as previous ISAM.
		For ISAM4.3, stays the same as previous ISAM (including for Veip-style VoIP). "
	::= { bponPotsPortEntry 4 }


bponPotsPortArc  OBJECT-TYPE
	SYNTAX 	INTEGER
	ACCESS	read-write
	STATUS	mandatory
	DESCRIPTION 
		"Alarm Reporting Control.  Valid values are:

		0 = Off (meaning alarm reporting allowed
		             immediately)
		1 = On (meaning alarm reporting inhibited until
		             valid signal is detected for time period
		             specified by ARC Interval).
		 Default = 1  - function is not implemented or supported
			for either BPON, GPON, or NG-PON2

		 Prior to FGU4.0--> Not Supported
		 Since FGU4.0--> Not  Supported

		For ISAM4.0.10 - stays the same as latest FGU4.x
		For ISAM4.2, stays the same as previous ISAM - NOT SUPPORTED.
		For ISAM4.3, stays the same as previous ISAM - NOT SUPPORTED.  "
	::= { bponPotsPortEntry 5 }

bponPotsPortArcInterval  OBJECT-TYPE
	SYNTAX 	INTEGER
	ACCESS	read-write
	STATUS	mandatory
	DESCRIPTION 
		"Alarm Reporting Control Interval (in minutes).

		 0 means alarms are inhibited indefinitely (if ARC
		   is set to inhibited)
		 Default = 0  - function is not implemented or supported
			for either BPON, GPON, or NG-PON2

		 Prior to FGU4.0--> Not Supported
		 Since FGU4.0--> Not  Supported 

		For ISAM4.0.10 - stays the same as latest FGU4.x
		For ISAM4.2, stays the same as previous ISAM - NOT SUPPORTED.
		For ISAM4.3, stays the same as previous ISAM - NOT SUPPORTED. "
	::= { bponPotsPortEntry 6 }


bponPotsPortImpedance  OBJECT-TYPE
	SYNTAX 	INTEGER
	ACCESS	read-write
	STATUS	mandatory
	DESCRIPTION 
		"Allows for impedance of port to be set by user as follows:

		 0 = 600 ohms
		 1 = 900 ohms
		And from Annex C of ETSI TS 101 270-1
		 2 = C1=150 nF, R1=750 ohm, R2 270 ohm
		 3 = C1=115 nF, R1=820 ohm, R2 220 ohm
		 4 = C1=230 nF, R1=1050 ohm, R2 320 ohm

		 255 = Unspecified (meaning no value is sent to the ONT via OMCI).

		 Default = 255

		 Prior to FGU4.0--> Not Supported
		 Since FGU4.0--> Not  Supported 

		For ISAM4.0.10 - stays the same as latest FGU4.x
		As of ISAM4.2.02, this attribute is SUPPORTED.
		For ISAM4.3, this attribute is SUPPORTED (including for Veip-style VoIP).  "
	::= { bponPotsPortEntry 7 }


bponPotsPortTransmissionPath  OBJECT-TYPE
	SYNTAX 	INTEGER
	ACCESS	read-write
	STATUS	mandatory
	DESCRIPTION 
		"Allows setting to full-time or part-time transmission

		 0 = full-time on-hook transmission
		 1 = part-time on-hook transmission

		 Default = 0  - function is not implemented or supported.

		Not applicable for GPON, or NG-PON2. 

		 Prior to FGU4.0--> Not Supported
		 Since FGU4.0--> Not  Supported

		For ISAM4.0.10 - stays the same as latest FGU4.x
		For ISAM4.2, stays the same as previous ISAM - NOT SUPPORTED.
		For ISAM4.3, stays the same as previous ISAM - NOT SUPPORTED. "
	::= { bponPotsPortEntry 8 }


bponPotsPortRxGain  OBJECT-TYPE
	SYNTAX 	INTEGER
	ACCESS	read-write
	STATUS	mandatory
	DESCRIPTION 
		"Allows setting the gain value for the received signal.

		 NOTE: This attribute is only relevant for a Cambridge ONT (i.e. Vendor ID = CIGG).

		 Valid values are -120 (-12.0 db) to +60 (+6.0 db) in 0.1db increments.

		 Default = 0 

		 SUPPORTED as of FGU4.6.4. 

		 Modification is permitted.

		For ISAM4.0.10 - stays the same as latest FGU4.x
		For ISAM4.2, stays the same as previous ISAM.
		For ISAM4.3, this attribute is SUPPORTED (including for Veip-style VoIP).  "
	::= { bponPotsPortEntry 9 }


bponPotsPortTxGain  OBJECT-TYPE
	SYNTAX 	INTEGER
	ACCESS	read-write
	STATUS	mandatory
	DESCRIPTION 
		"Allows setting the gain value for the transmit signal.

		 NOTE: This attribute is only relevant for a Cambridge ONT (i.e. Vendor ID = CIGG).

		 Valid values are -120 (-12.0 db) to +60 (+6.0 db) in 0.1db increments.

		 Default = 0 

		 SUPPORTED as of FGU4.6.4. 

		 Modification is permitted.

		For ISAM4.0.10 - stays the same as latest FGU4.x
		For ISAM4.2, stays the same as previous ISAM.
		For ISAM4.3, this attribute is SUPPORTED (including for Veip-style VoIP). "
	::= { bponPotsPortEntry 10 }


bponPotsPortSignallingCode  OBJECT-TYPE
	SYNTAX 	INTEGER
	ACCESS	read-write
	STATUS	mandatory
	DESCRIPTION 
		"Allows setting as follows:

		 1 = loop start
		 2 = ground start
		 3 = loop reverse battery
		 4 = coin first
		 5 = dial tone first
		 6 = multi-party

		 Default = 1

		Not applicable for GPON, NG-PON2. 

		 Prior to FGU4.0--> Not Supported
		 Since FGU4.0--> Not  Supported

		For ISAM4.0.10 - stays the same as latest FGU4.x
		For ISAM4.2 -> only supported value is the Default = 1.
		For ISAM4.3, this attribute is SUPPORTED as in previous ISAM (including for Veip-style VoIP). "
	::= { bponPotsPortEntry 11 }


bponPotsPortRobbedBitSig  OBJECT-TYPE
	SYNTAX 	INTEGER
	ACCESS	read-write
	STATUS	mandatory
	DESCRIPTION 
		"Allows setting as follows:

		 1 = a
		 2 = ab
		 3 = abcd
		 4 = other

		 Default = 3  - function is not implemented or supported.

		Not applicable for GPON, NG-PON2. 

		 Prior to FGU4.0--> Not Supported
		 Since FGU4.0--> Not  Supported

		For ISAM4.0.10 - stays the same as latest FGU4.x
		For ISAM4.2, stays the same as previous ISAM - NOT SUPPORTED.
		For ISAM4.3, stays the same as previous ISAM - NOT SUPPORTED.  "
	::= { bponPotsPortEntry 12 }


bponPotsPortSilenceSuppressInd  OBJECT-TYPE
	SYNTAX 	Boolean
	ACCESS	read-write
	STATUS	mandatory
	DESCRIPTION 
		"Allows setting as follows:

		 TRUE = Suppression On
		 FALSE = Suppression Off

		 Default = 0 = FALSE  - function is not implemented or supported.

		Not applicable for GPON, NG-PON2.

		 Prior to FGU4.0--> Not Supported
		 Since FGU4.0--> Not  Supported

		For ISAM4.0.10 - stays the same as latest FGU4.x
		For ISAM4.2, stays the same as previous ISAM - NOT SUPPORTED.
		For ISAM4.3, stays the same as previous ISAM - NOT SUPPORTED. "
	::= { bponPotsPortEntry 13 }


bponPotsPortVoiceCompression  OBJECT-TYPE
	SYNTAX 	INTEGER
	ACCESS	read-write
	STATUS	mandatory
	DESCRIPTION 
		"Allows setting as follows:

		 1 = PCM-64
		 2 = ADPCM-32
		 3 = LD-CELP16
		 4 = CS-ACELP8
		 255 = other


		 Default = 1  - function is not implemented or supported.

		Not applicable for GPON, or NG-PON2.

		 Prior to FGU4.0--> Not Supported
		 Since FGU4.0--> Not  Supported

		For ISAM4.0.10 - stays the same as latest FGU4.x
		For ISAM4.2, stays the same as previous ISAM - NOT SUPPORTED.
		For ISAM4.3, stays the same as previous ISAM - NOT SUPPORTED. "
	::= { bponPotsPortEntry 14 }


bponPotsPortVpi  OBJECT-TYPE
	SYNTAX 	INTEGER 
	ACCESS	read-write
	STATUS	mandatory
	DESCRIPTION 
		" The VPI value of the VCL to which this POTS port 
		  is assigned.

		Not applicable for GPON, NG-PON2.

		For ISAM4.0.10 - stays the same as latest FGU4.x
		For ISAM4.2, stays the same as previous ISAM - NOT SUPPORTED.
		For ISAM4.3, stays the same as previous ISAM - NOT SUPPORTED. "
	::= { bponPotsPortEntry 15 }


bponPotsPortVci  OBJECT-TYPE
	SYNTAX 	INTEGER
	ACCESS	read-write
	STATUS	mandatory
	DESCRIPTION 
		" The VCI value of the VCL to which this POTS port 
  		  is assigned.

		Not applicable for GPON, or NG-PON2.

		For ISAM4.0.10 - stays the same as latest FGU4.x
		For ISAM4.2, stays the same as previous ISAM - NOT SUPPORTED.
		For ISAM4.3, stays the same as previous ISAM - NOT SUPPORTED. "
	::= { bponPotsPortEntry 16 }


bponPotsPortCid  OBJECT-TYPE
	SYNTAX 	INTEGER
	ACCESS	read-write
	STATUS	mandatory
	DESCRIPTION 
		" The AAL2 Channel ID of the VCL to which this POTS port 
  		  is assigned.
  
		  Range is 16 to 255
		  For FGU2.6, the ONT hardcodes the CID values of POTS ports, 
		  so this function is not implemented or supported. 

		Not applicable for GPON, NG-PON2.

		 Prior to FGU4.0--> Not Supported
		 Since FGU4.0--> Not  Supported

		For ISAM4.0.10 - stays the same as latest FGU4.x
		For ISAM4.2, stays the same as previous ISAM - NOT SUPPORTED.
		For ISAM4.3, stays the same as previous ISAM - NOT SUPPORTED.  "
	::= { bponPotsPortEntry 17 }


bponPotsPortMltTestCmd  OBJECT-TYPE
	SYNTAX 	INTEGER 
	ACCESS	read-write
	STATUS	mandatory
	DESCRIPTION 
		"Manager is only permitted to SET this attribute
		 to (1), indicating desire to execute POTS port MLT test.
		 Thereafter, manager issues SNMP GET to determine
		 status/result of the MLT test. Agent changes
		 attribute value accordingly as follows:
		 0 - This is the initial default value, meaning an MLT test
		          has never been executed on this port since initialization.
		 1 - Only value settable by manager (to initiate test)  
		 2 - meaning MLT test is in progress,
		 3 - meaning MLT test failed because ONT failed
		       to respond within reasonable time,
		 4 - meaning MLT test has completed execution.
		 5 - meaning OLT didn't issue the MLT command.

		Manager must read results in 
  		bponPotsPortMltTestResult attribute to discern
   		the specifics of the actual MLT test results.

		Default = 0

		Applicable for both BPON, GPON, and NG-PON2.

		NOT SUPPORTED starting with FGU4.5.

		For ISAM4.0.10 - stays the same as latest FGU4.x
		For ISAM4.2, stays the same as previous ISAM - NOT SUPPORTED.
		For ISAM4.3, stays the same as previous ISAM - NOT SUPPORTED. "
	::= { bponPotsPortEntry 18 }

bponPotsPortMltTestResult  OBJECT-TYPE
	SYNTAX 	OCTET STRING (SIZE(1))
	ACCESS	read-only
	STATUS	mandatory
	DESCRIPTION 
		"Indicates the MLT Test Result for a 
		 specific POTS port.  Represented as a
		 bitmap as follows (where Bit 1 is the 
		 least significant bit). 
		 Bit 1     = Don't care. N/A for POTS.
		 Bit 2 - 0 = ringer failed
			 - 1 = ringer passed
		 Bit 3 - 0 = receiver off-hook failed
			 - 1 = receiver off-hook passed
		 Bit 4 - 0 = resistive faults failed
			 - 1 = resistive faults passed
		 Bit 5 - 0 = foreign EMF failed
			 - 1 = foreign EMF passed
		 Bit 6 - 0 = hazardous potential failed
			 - 1 = hazardous potential passed
		 Bit 7     = Always 0
		 Bit 8     = Always 0 

		 Applicable for both BPON, GPON, and NG-PON2.

		NOT SUPPORTED starting with FGU4.5.

		For ISAM4.0.10 - stays the same as latest FGU4.x
		For ISAM4.2, stays the same as previous ISAM - NOT SUPPORTED.
		For ISAM4.3, stays the same as previous ISAM - NOT SUPPORTED. "
	::= { bponPotsPortEntry 19 }

bponPotsPortCustomerInfo  OBJECT-TYPE
	SYNTAX 	OCTET STRING (SIZE(0..80))
	ACCESS	read-write
	STATUS	mandatory
	DESCRIPTION 
		"This is a 80 byte free-form textual field that the
		  operator can use to provide info for a POTS port. 
		 Default - null string. 

		 Applicable for both BPON, GPON, and NG-PON2.

		For ISAM4.0.10 - stays the same as latest FGU4.x
		For ISAM4.2, stays the same as previous ISAM - SUPPORTED.
		For ISAM4.3, stays the same as previous ISAM - SUPPORTED (including for Veip-style VoIP). "
	::= { bponPotsPortEntry 20 }

bponPotsPortOperState  OBJECT-TYPE
	SYNTAX 	OperState
	ACCESS	read-only
	STATUS	mandatory
	DESCRIPTION 
		"Indicates operational state of the
		  POTS port.  State is related to ability of port
		  to perform its function (e.g. whether service
		  affecting alarm is present). 
		  Default = 0 = Enabled

		 Applicable for both BPON, GPON, and NG-PON2.

		For ISAM4.0.10 - stays the same as latest FGU4.x
		For ISAM4.2, stays the same as previous ISAM - SUPPORTED.
		For ISAM4.3, stays the same as previous ISAM - SUPPORTED (including for Veip-style VoIP). "
	::= { bponPotsPortEntry 21 }

bponPotsPortVoipServiceIndex  OBJECT-TYPE
	SYNTAX 	INTEGER (1..2147483647)
	ACCESS	read-write
	STATUS	mandatory
	DESCRIPTION 
		" This is the Service Number of the VoIP Client
		   Service - with which this physical POTS
		   UNI is associated.

		   Since FGU4.0, the only supported value is 1,
		   since only 1 VoIP Client per ONT is supported.

		   Default = 1.

		   Only applicable for GPON, and NG-PON2.

		   For ISAM4.0.10 - stays the same as latest FGU4.x (except
		   default is 1). 

		   For ISAM4.2, stays the same as previous ISAM.
		   This attribute is only relevant if corresponding row exists in 
		   gponVoipServiceTable for this ONT (i.e. legacy VoIP provisioning style).
		   For ISAM4.3, stays the same as previous ISAM.

           For ISAM5.4.01, is not relevant for NG-PON2 since it is only relevant for legacy. "
	::= { bponPotsPortEntry 22 }

bponPotsPortCurrStatus  OBJECT-TYPE
	SYNTAX 	INTEGER
	ACCESS	read-only
	STATUS	mandatory
	DESCRIPTION 
		" Indicates current state of the POTS port.
		  This is a bit-map of possible conditions.  The
		  bit positions are as follows:

		0 - No defects on line
		1 - OMCI Mismatch Problem

		 Default = 0.

		Applicable only for GPON, and NG-PON2.

		For ISAM4.0.10 - stays the same as latest FGU4.x
		For ISAM4.2, stays the same as previous ISAM. 
		For ISAM4.3, stays the same as previous ISAM.  "
	::= { bponPotsPortEntry 23 }

bponPotsPortTerminationId  OBJECT-TYPE
	SYNTAX 	OCTET STRING (SIZE(0..25))
	ACCESS	read-write
	STATUS	mandatory
	DESCRIPTION 
		"This is a 25 byte free-form textual field that 
		  is used to identify the POTS port in H248 VoIP 
		  signalling messages. This parameter is only 
		  relevant and required if the associated VoIP Client
		  is in a H248 mode of operation - (i.e. it is not
		  applicable for SIP modes of operation). See gponVoipServiceGwyOption
		  attribute in gponVoipServiceTable to determine VoIP Client mode of operation.


		 VALIDITY RULE:  The following uniqueness and validity rules are only relevant
		 if associated VoIP Client is in a H248 mode of operation (i.e. it is not
		 applicable for SIP modes of operation).
		 For H248 modes, this field must be unique across
		 POTS ports that are associated to the same VoIP
		 Client Service.  Also - for this uniqueness check -
		 the field must be considered case insensitive.
		 Termination ID is a case insensitive string up to 25 characters
		 long. Only the following characters are allowed: 
		 ['a'..'z', 'A'..'Z', '0'..'9', '*', '/', '-', '_', '$', '@', or '.']. 
		 The first character must be alphabetic.
		 The string 'ROOT' is not allowed. 

		 Default - null string. 

		 Applicable only for GPON, and NG-PON2.

		 For ISAM4.0.10 - stays the same as latest FGU4.x

		 For ISAM4.2, stays the same as previous ISAM.
		   This attribute is only relevant if corresponding row exists in 
		   gponVoipServiceTable for this ONT (i.e. legacy VoIP provisioning style).
		 For ISAM4.3, stays the same as previous ISAM. 
         For ISAM5.4.01, is not relevant for NG-PON2 since it is only relevant for H.248. "
	::= { bponPotsPortEntry 24 }

bponPotsPortDscpSetting OBJECT-TYPE 
	SYNTAX	INTEGER
	ACCESS	read-write
	STATUS  mandatory
	DESCRIPTION 
		" Used to set the DSCP value that the Voip Client
		  will use to tag bearer channel voice packets.
		  Only the low order 6 bits are relevant - since that is
		  the size of the DSCP field in IP packets.
   
 		 Default = 46 (decimal) = 0x002E (hex) = 101110 (binary) - Expedited Forwarding.

		 For ISAM4.0.10 - stays the same as latest FGU4.x

		 For ISAM4.2, stays the same as previous ISAM.
		   This attribute is only relevant if corresponding row exists in 
		   gponVoipServiceTable for this ONT (i.e. legacy VoIP provisioning style).
		 For ISAM4.3, stays the same as previous ISAM.
         For ISAM5.4.01, is not relevant for NG-PON2 since it is only relevant for legacy. "
::= { bponPotsPortEntry 25 }

bponPotsPortPwrShedOverride  OBJECT-TYPE
	SYNTAX 	Boolean
	ACCESS	read-write
	STATUS	mandatory
	DESCRIPTION 
		"Allows setting as follows:

		 TRUE = 1 = port excluded from voice class power shedding
		 FALSE = 0 = port included in voice class power shedding

		 Default = 0 = FALSE  

		 As of FGU4.4, this is Supported.

		For ISAM4.0.10 - stays the same as latest FGU4.x
		 For ISAM4.2, stays the same as previous ISAM.
		 For ISAM4.3, stays the same as previous ISAM (including for Veip-style VoIP). "
	::= { bponPotsPortEntry 26 }

bponPotsPortCallHistCollectInd  OBJECT-TYPE
	SYNTAX 	INTEGER
	ACCESS	read-write
	STATUS	mandatory
	DESCRIPTION 
		" This indicates whether Call History information
		   should be collected for this POTS Port.
	
		  1 = PM collection enabled
		  2 = PM collection disabled

		 Default = 2 = disabled.

		For ISAM4.0.10 - stays the same as latest FGU4.x
		 For ISAM4.2, stays the same as previous ISAM.
		 For ISAM4.3, stays the same as previous ISAM (except CANNOT be enabled for Veip-style VoIP).

		As of targeted release ISAM4.5.02, enable/disable must also be SUPPORTED for Veip-style VoIP.  "
	::= { bponPotsPortEntry 27 }

bponPotsPortVoltageHoldoverTimer  OBJECT-TYPE
	SYNTAX 	INTEGER
	ACCESS	read-write
	STATUS	mandatory
	DESCRIPTION 
		" This attribute determines the time during which POTS 
		   loop voltage (for this port) is held up when the ONT is not ranged on 
		   the PON. After the specified time elapses, the ONT drops
		   POTS loop voltage, and may thereby cause premises intrusion
		   alarm circuits to go active. When the ONT ranges successfully
		   on the PON, it restores POTS loop voltage immediately and resets
		   the timer. The attribute is expressed in seconds. The default value 0
		   selects the vendor's factory policy.

		  Range is 0 - 65535 (units are seconds).

		  Default = 0

		For ISAM4.0.10 - stays the same as latest FGU4.x
		 For ISAM4.2, stays the same as previous ISAM.
		 For ISAM4.3, stays the same as previous ISAM (including for Veip-style VoIP).  "
	::= { bponPotsPortEntry 28 }

bponPotsPortSipMsgTimeoutTCAThreshold  OBJECT-TYPE
	SYNTAX 	INTEGER
	ACCESS	read-write
	STATUS	mandatory
	DESCRIPTION 
		" Used to establish the threshold for raising the SIP Message Timeout TCA Alarm
		  for this POTS UNI (See Alarm Definition Spec).

		  Range is 0 - 65535

		  Default = 0 - which means associated TCA alarm is inhibited at ONT.

		For ISAM4.0.10 - stays the same as latest FGU4.x

		 For ISAM4.2, stays the same as previous ISAM.
		   This attribute is only relevant if corresponding row exists in 
		   gponVoipServiceTable for this ONT (i.e. legacy VoIP provisioning style).
		 For ISAM4.3, stays the same as previous ISAM. 
         For ISAM5.4.01, is not relevant for NG-PON2 since it is only relevant for legacy. "
	::= { bponPotsPortEntry 29 }

bponPotsPortBearerPktLossTCAThreshold  OBJECT-TYPE
	SYNTAX 	INTEGER
	ACCESS	read-write
	STATUS	mandatory
	DESCRIPTION 
		" Used to establish the threshold for raising the Bearer Packet Loss TCA Alarm
		   for this POTS UNI (See Alarm Definition Spec).

		  Range is 0 - 255

		  This number is scaled to 256ths (e.g. a value of 10 means a ratio of 10/256ths).

		  Default = 0 - which means associated TCA alarm is inhibited at ONT.

		For ISAM4.0.10 - stays the same as latest FGU4.x

		 For ISAM4.2, stays the same as previous ISAM.
		   This attribute is only relevant if corresponding row exists in 
		   gponVoipServiceTable for this ONT (i.e. legacy VoIP provisioning style).
		 For ISAM4.3, stays the same as previous ISAM. 
         For ISAM5.4.01, is not relevant for NG-PON2 since it is only relevant for legacy. "
	::= { bponPotsPortEntry 30 }


bponPotsPortJitterTCAThreshold  OBJECT-TYPE
	SYNTAX 	INTEGER
	ACCESS	read-write
	STATUS	mandatory
	DESCRIPTION 
		" Used to establish the threshold for raising the Jitter TCA Alarm
		   for this POTS UNI (See Alarm Definition Spec).

		  Range is 0 - 65535

		  Units are milliseconds.

		  Default = 0 - which means associated TCA alarm is inhibited at ONT.

		For ISAM4.0.10 - stays the same as latest FGU4.x

		 For ISAM4.2, stays the same as previous ISAM.
		   This attribute is only relevant if corresponding row exists in 
		   gponVoipServiceTable for this ONT (i.e. legacy VoIP provisioning style).
		 For ISAM4.3, stays the same as previous ISAM. 
         For ISAM5.4.01, is not relevant for NG-PON2 since it is only relevant for legacy. "
	::= { bponPotsPortEntry 31 }


bponPotsPortMgcConfigPointer  OBJECT-TYPE
	SYNTAX 	InterfaceIndexOrZero
	ACCESS	read-write
	STATUS	mandatory
	DESCRIPTION 
		"  This attribute was introduced with ISAM4.2.
		   When non-zero, this attribute effectively associates this POTS port with a row in the gponOntMgcConfigTable,
		    by specifying the same ifIndex (of IP Host UNI) that is used to index the gponOntMgcConfigTable.
		    It is only relevant if the VoIP method used for the ONT is H248 oriented.

		    This attribute and bponPotsPortSipConfigPointer (see below) cannot both
		    be non-zero (i.e. POTS port can only work with SIP or MGC at one time).

		  Default = 0  - meaning POTS port is unassociated to MGC agent.
		   This attribute is only relevant if corresponding row exists in 
		   gponOntMgcConfigTable for this ONT (i.e. standard VoIP provisioning style).
		 For ISAM4.3, stays the same as previous ISAM. 
         For ISAM5.4.01, is not relevant for NG-PON2 since it is only relevant for H.248. "
	::= { bponPotsPortEntry 32 }

bponPotsPortSipConfigPointer  OBJECT-TYPE
	SYNTAX 	InterfaceIndexOrZero
	ACCESS	read-write
	STATUS	mandatory
	DESCRIPTION 
		"  This attribute was introduced with ISAM4.2.
		   When non-zero, This attribute effectively associates this POTS port with a row in the gponOntSipConfigTable,
		    by specifying the same ifIndex (of IP Host UNI) that is used to index the gponOntSipConfigTable.
		    It is only relevant if the VoIP method used for the ONT is SIP oriented .

		    This attribute and bponPotsPortMgcConfigPointer (see above) cannot both
		    be non-zero (i.e. POTS port can only work with SIP or MGC at one time).

		  Default = 0 - meaning POTS port is unassociated to SIP agent.
		   This attribute is only relevant if corresponding row exists in 
		   gponOntSipConfigTable for this ONT (i.e. standard VoIP provisioning style).
		 For ISAM4.3, stays the same as previous ISAM. "
	::= { bponPotsPortEntry 33 }

bponPotsPortVoipMediaPointer  OBJECT-TYPE
	SYNTAX 	AsamProfilePointer
	ACCESS	read-write
	STATUS	mandatory
	DESCRIPTION 
		" This attribute was introduced with ISAM4.2.
		  This attribute points to a row in gponVoipMediaProfileTable.

		 Value 0 (i.e. null pointer) is permitted - but only if bponPotsPortAdminState = locked.

		 Default = 0.

		 Modification is permitted, but only if bponPotsPortAdminState = locked.

		 RULE1: OLT will REJECT any provisioning which would cause ALL of following to be
			 TRUE for 2 or more POTs ports:
		 1) POTS ports are on same ONT.
		 2) POTS ports are associated with same SIP agent or same MGC agent
		 3) POTS ports are In-Service (i.e. bponPotsPortAdminState = unlocked).
		 4) POTS ports point to different Media Profiles (i.e. value of this pointer attribute is NOT identical).

		   This attribute is only relevant if corresponding row exists in either gponOntMgcConfigTable or
		   gponOntSipConfigTable for this ONT (i.e. standard VoIP provisioning style).
		 For ISAM4.3, stays the same as previous ISAM. "
	::= { bponPotsPortEntry 34 }

bponPotsPortSipUserPartAorPointer  OBJECT-TYPE
	SYNTAX 	DisplayString
	ACCESS	read-write
	STATUS	mandatory
	DESCRIPTION 
		" This attribute was introduced with ISAM4.2.
		  It is only relevant in SIP modes (i.e. if bponPotsPortSipConfigPointer
		  is non-zero). 
		  It contains the user identification part of the Address of Record.
		  For example,  it could take the form of an alphanumeric string or the subscriber's
		  directory number.

		  Maximum string size is 50 bytes.

		  Null string is permitted - meaning this is determined via other means.

		  Default = null string.

		  Modification is permitted.
		   This attribute is only relevant if corresponding row exists in 
		   gponOntSipConfigTable for this ONT (i.e. standard VoIP provisioning style).
		 For ISAM4.3, stays the same as previous ISAM. "
	::= { bponPotsPortEntry 35 }

bponPotsPortSipDisplayName  OBJECT-TYPE
	SYNTAX 	DisplayString
	ACCESS	read-write
	STATUS	mandatory
	DESCRIPTION 
		" This attribute was introduced with ISAM4.2.
		  It is only relevant in SIP modes (i.e. if bponPotsPortSipConfigPointer
		  is non-zero). 
		  This attribute defines the customer ID used for the display attribute in outgoing 
		  SIP messages.

		  Maximum string size is 25 bytes.

		  Null string (default) is permitted.

		  Modification is permitted.
		   This attribute is only relevant if corresponding row exists in 
		   gponOntSipConfigTable for this ONT (i.e. standard VoIP provisioning style).
		 For ISAM4.3, stays the same as previous ISAM. "
	::= { bponPotsPortEntry 36 }

-- bponPotsPortSipUserPassPointer  OBJECT-TYPE
--	SYNTAX 	AsamProfilePointer
--	ACCESS	read-write 
--	STATUS	mandatory
--	DESCRIPTION 
--		" This attribute was introduced with ISAM4.2.
--		  It is only relevant in SIP modes (i.e. if bponPotsPortSipConfigPointer
--		  is non-zero). 
--		  This attribute points to a row in gponAuthSecurityProfileTable.
--		  which contains the SIP username and password used for authentication.
--
--		  Value 0 (null pointer) is permitted - meaning this is determined via other means.
--
--		  Default = 0.
--
--		  Modification is permitted.
--		   This attribute is only relevant if corresponding row exists in 
--		   gponOntSipConfigTable for this ONT (i.e. standard VoIP provisioning style).
--
--		   This attribute is NOT SUPPORTED in any release - has been commented out.  "
--	::= { bponPotsPortEntry 37 }

bponPotsPortSipVoicemailUriPointer  OBJECT-TYPE
	SYNTAX 	AsamProfilePointer
	ACCESS	read-write
	STATUS	mandatory
	DESCRIPTION 
		" This attribute was introduced with ISAM4.2.
		  It is only relevant in SIP modes (i.e. if bponPotsPortSipConfigPointer
		  is non-zero). 
		  This attribute points to a row in gponSecureUriProfileTable,
		  which contains the name (IP address or URI) of the SIP voicemail server for SIP 
		  signalling messages.

		  Value 0 (null pointer) is permitted - meaning this is determined via other means.

		  Default = 0.

		  Modification is permitted.
		   This attribute is only relevant if corresponding row exists in 
		   gponOntSipConfigTable for this ONT (i.e. standard VoIP provisioning style).
		 For ISAM4.3, stays the same as previous ISAM. "
	::= { bponPotsPortEntry 38 }



bponPotsPortSipVoicemailExpireTime  OBJECT-TYPE
	SYNTAX 	INTEGER
	ACCESS	read-write
	STATUS	mandatory
	DESCRIPTION 
		" This attribute was introduced with ISAM4.2.
		  It is only relevant in SIP modes (i.e. if bponPotsPortSipConfigPointer
		  is non-zero). 
		  This attribute defines the voicemail subscription expiration time (in seconds).

		  Range is 0..86400

		  Value 0 means the SIP agent uses an implementation-specific value.

		  Default = 3600.

		  Modification is permitted.
		   This attribute is only relevant if corresponding row exists in 
		   gponOntSipConfigTable for this ONT (i.e. standard VoIP provisioning style).
		 For ISAM4.3, stays the same as previous ISAM. "
	::= { bponPotsPortEntry 39 }

bponPotsPortSipNetDialPlanPointer  OBJECT-TYPE
	SYNTAX 	AsamProfilePointer
	ACCESS	read-write
	STATUS	mandatory
	DESCRIPTION 
		" This attribute was introduced with ISAM4.2.
		  It is only relevant in SIP modes (i.e. if bponPotsPortSipConfigPointer
		  is non-zero). 
		  This attribute points to a row in gponNetDialPlanProfileTable.

		  Value 0 is permitted - meaning this is determined via other means.

		  Default = 0.

		  Modification is permitted.
		   This attribute is only relevant if corresponding row exists in 
		   gponOntSipConfigTable for this ONT (i.e. standard VoIP provisioning style).
		 For ISAM4.3, stays the same as previous ISAM. "
	::= { bponPotsPortEntry 40 }

bponPotsPortSipAppServicesPointer  OBJECT-TYPE
	SYNTAX 	AsamProfilePointer
	ACCESS	read-write
	STATUS	mandatory
	DESCRIPTION 
		" This attribute was introduced with ISAM4.2.
		  It is only relevant in SIP modes (i.e. if bponPotsPortSipConfigPointer
		  is non-zero). 
		  This attribute points to a row in gponVoipAppServProfileTable.

		  Value 0 is permitted - meaning this is determined via other means.

		  Default = 0.

		  Modification is permitted.
		   This attribute is only relevant if corresponding row exists in 
		   gponOntSipConfigTable for this ONT (i.e. standard VoIP provisioning style).
		 For ISAM4.3, stays the same as previous ISAM. "
	::= { bponPotsPortEntry 41 }

bponPotsPortSipFeatAccessCodePointer  OBJECT-TYPE
	SYNTAX 	AsamProfilePointer
	ACCESS	read-write
	STATUS	mandatory
	DESCRIPTION 
		" This attribute was introduced with ISAM4.2.
		  It is only relevant in SIP modes (i.e. if bponPotsPortSipConfigPointer
		  is non-zero). 
		  This attribute points to a row in gponVoipFeatAccessCodeProfileTable.

		  Value 0 is permitted - meaning this is determined via other means.

		  Default = 0.

		  Modification is permitted.
		   This attribute is only relevant if corresponding row exists in 
		   gponOntSipConfigTable for this ONT (i.e. standard VoIP provisioning style).
		 For ISAM4.3, stays the same as previous ISAM. "
	::= { bponPotsPortEntry 42 }

bponPotsPortSipReleaseTimer  OBJECT-TYPE
	SYNTAX 	INTEGER
	ACCESS	read-write
	STATUS	mandatory
	DESCRIPTION 
		" This attribute was introduced with ISAM4.2.
		  It is only relevant in SIP modes (i.e. if bponPotsPortSipConfigPointer
		  is non-zero). 
		  This attribute defines the SIP release timer (in seconds).

		  Range is 0..60

		  Value 0 means the SIP agent uses internal default.

		  Default = 10.

		  Modification is permitted.
		   This attribute is only relevant if corresponding row exists in 
		   gponOntSipConfigTable for this ONT (i.e. standard VoIP provisioning style).
		 For ISAM4.3, stays the same as previous ISAM. "
	::= { bponPotsPortEntry 43 }

bponPotsPortSipRohTimer  OBJECT-TYPE
	SYNTAX 	INTEGER
	ACCESS	read-write
	STATUS	mandatory
	DESCRIPTION 
		" This attribute was introduced with ISAM4.2.
		  It is only relevant in SIP modes (i.e. if bponPotsPortSipConfigPointer
		  is non-zero). 
		  This attribute defines the time (in seconds) for the receiver off hook condition
		  before ROH tone is applied.

		  Range is 0..60

		  Value 0 disables ROH timing.

		  Default = 15.

		  Modification is permitted.
		   This attribute is only relevant if corresponding row exists in 
		   gponOntSipConfigTable for this ONT (i.e. standard VoIP provisioning style).
		 For ISAM4.3, stays the same as previous ISAM. "
	::= { bponPotsPortEntry 44 }

bponPotsPortCallCntlPmCollectInd  OBJECT-TYPE
	SYNTAX 	INTEGER
	ACCESS	read-write
	STATUS	mandatory
	DESCRIPTION 
		" This indicates whether Call Control Performance Monitors
		   should be collected for this POTS Port.
	
		  1 = PM collection enabled
		  2 = PM collection disabled

		 Default = 2 = disabled.

		   This attribute is only relevant if corresponding row exists in either gponOntMgcConfigTable or
		   gponOntSipConfigTable for this ONT (i.e. standard VoIP provisioning style).
		 For ISAM4.3, stays the same as previous ISAM.

		As of targeted release ISAM4.5.02, enable/disable must also be SUPPORTED for Veip-style VoIP. "
	::= { bponPotsPortEntry 45 }

bponPotsPortCallCntlNumPMIntervals  OBJECT-TYPE
	SYNTAX 	INTEGER
	ACCESS	read-only
	STATUS	mandatory
	DESCRIPTION 
		" Indicates the number of rows currently present
		  in the gponPotsCallCntlIntervalTable.  This
		  is for convenience of the EMS, so that it can
		 quickly determine how many rows should be 
		 uploaded.

		   This attribute is only relevant if corresponding row exists in either gponOntMgcConfigTable or
		   gponOntSipConfigTable for this ONT (i.e. standard VoIP provisioning style).
		 For ISAM4.3, stays the same as previous ISAM.


		As of targeted release ISAM4.5.02, must also be SUPPORTED for Veip-style VoIP. "
	::= { bponPotsPortEntry 46 }

bponPotsPortRtpPmCollectInd  OBJECT-TYPE
	SYNTAX 	INTEGER
	ACCESS	read-write
	STATUS	mandatory
	DESCRIPTION 
		" This indicates whether RTP Performance Monitors
		   should be collected for this POTS Port.
	
		  1 = PM collection enabled
		  2 = PM collection disabled

		 Default = 2 = disabled.

		   Originally, this attribute is only relevant if corresponding row exists in either gponOntMgcConfigTable or
		   gponOntSipConfigTable for this ONT (i.e. standard VoIP provisioning style).
		 For ISAM4.3, stays the same as previous ISAM.

		As of targeted release ISAM4.5.02, enable/disable must also be SUPPORTED for Veip-style VoIP. "
	::= { bponPotsPortEntry 47 }

bponPotsPortRtpNumPMIntervals  OBJECT-TYPE
	SYNTAX 	INTEGER
	ACCESS	read-only
	STATUS	mandatory
	DESCRIPTION 
		" Indicates the number of rows currently present
		  in the gponPotsRtpIntervalTable.  This
		  is for convenience of the EMS, so that it can
		 quickly determine how many rows should be 
		 uploaded.

		   This attribute is only relevant if corresponding row exists in either gponOntMgcConfigTable or
		   gponOntSipConfigTable for this ONT (i.e. standard VoIP provisioning style).
		 For ISAM4.3, stays the same as previous ISAM.

		As of targeted release ISAM4.5.02, must also be SUPPORTED for Veip-style VoIP. "
	::= { bponPotsPortEntry 48 }

bponPotsPortSipValidScheme  OBJECT-TYPE
	SYNTAX 	INTEGER
	ACCESS	read-write
	STATUS	mandatory
	DESCRIPTION 
		"This attribute contains the Validation Scheme required for authentication.

		 0 = Validation disabled
		 1 = Validate using MD5 digest authentication as defined in RFC 2617 
		 2 = Validate using basic authentication as defined in [IETF RFC 2617]

		Default = 0 = disabled.

		 Modification is permitted.

		   This attribute is only relevant if corresponding row exists in 
		   gponOntSipConfigTable for this ONT (i.e. standard VoIP provisioning style).
		 For ISAM4.3, stays the same as previous ISAM.  "
	::= { bponPotsPortEntry 49 }


bponPotsPortSipUsername  OBJECT-TYPE
	SYNTAX 	DisplayString (SIZE(0..50))
	ACCESS	read-write
	STATUS	mandatory
	DESCRIPTION 
		"This is a textual string that contains the Username required for authentication.

		 Default - null string. 

		 Modification is permitted.

		   This attribute is only relevant if corresponding row exists in 
		   gponOntSipConfigTable for this ONT (i.e. standard VoIP provisioning style).
		 For ISAM4.3, stays the same as previous ISAM.  "
	::= { bponPotsPortEntry 50 }


bponPotsPortSipPassword  OBJECT-TYPE
	SYNTAX 	DisplayString (SIZE(0..25))
	ACCESS	read-write
	STATUS	mandatory
	DESCRIPTION 
		"This is a textual string that contains the Password required for authentication. 

		 Default - null string. 

		 Modification is permitted.

		   This attribute is only relevant if corresponding row exists in 
		   gponOntSipConfigTable for this ONT (i.e. standard VoIP provisioning style).
		 For ISAM4.3, stays the same as previous ISAM.  "
	::= { bponPotsPortEntry 51 }


bponPotsPortSipRealm  OBJECT-TYPE
	SYNTAX 	DisplayString (SIZE(0..25))
	ACCESS	read-write
	STATUS	mandatory
	DESCRIPTION 
		"This is a textual string that contains the Realm for authentication. 

		 Default - null string. 

		 Modification is permitted 

		   This attribute is only relevant if corresponding row exists in 
		   gponOntSipConfigTable for this ONT (i.e. standard VoIP provisioning style).
		 For ISAM4.3, stays the same as previous ISAM. "
	::= { bponPotsPortEntry 52 }

bponPotsPortFileNamePart OBJECT-TYPE 
	SYNTAX 	DisplayString (SIZE(0..50))
	ACCESS	read-write
	STATUS	mandatory
	DESCRIPTION 
		" This is a textual string that typically contains the filename part of an XML file
		 that may be associated with this POTS port. For the complete address/path/filename
		 for such file, the user should consider that this port specific attribute is conjoined
		 (appended after) the common part that is contained in the following attribute reference chain:
		 - gponUriProfileAddress attribute in gponUriProfile referenced by,
		 - gponSecureUriProfile referenced by,
		 - gponVoiceServiceProfileNetSpecificExtensionsPointer attribute in gponVoiceServiceProfile referenced by,
		 - gponVoipMediaProfile referenced by, 
		 - bponPotsPortVoipMediaPointer attribute in this bponPotsPortTable.

		 Null string is permitted, meaning that any relevant address/path/filename is fully contained in common part
		 (as described above).

		 Default - null string. 

		 Modification is permitted, but only if bponPotsPortAdminState = locked.

		 RULE1: OLT will REJECT any provisioning which would cause ALL of following to be
			 TRUE for 2 or more POTs ports:
		 1) POTS ports are on same ONT.
		 2) POTS ports are associated with same SIP agent or same MGC agent
		 3) POTS ports are In-Service (i.e. bponPotsPortAdminState = unlocked).
		 4) POTS ports have different file name parts  (i.e. value of this attribute is NOT identical).

		   This attribute is only relevant if corresponding row exists in either gponOntMgcConfigTable or
		   gponOntSipConfigTable for this ONT (i.e. standard VoIP provisioning style).
		 For ISAM4.3, stays the same as previous ISAM.  "
::= { bponPotsPortEntry 53 }


bponPotsPortVeipPointer  OBJECT-TYPE
	SYNTAX 	SpIndexOrZero
	ACCESS	read-write
	STATUS	mandatory
	DESCRIPTION 
		"  This attribute was first introduced with ISAM4.3.
		   When non-zero, this attribute effectively associates this POTS port with a row in the gponVeipPortTable
		   for the same ONT. This is done by specifying the same SpIndex (slot/port) that is used for the SpIndex (slot/port) of a
		   gponVeipPortTable (for the same ONT). 
		   
		   VALIDATION:  This attribute can only be set to a non-zero value if both of following are TRUE:
			1) bponVoipCapability attribute in same ONT is set to 3 = Veip-Style VoIP.
			2) The associated Veip UNI (i.e. slot/port) for this same ONT actually exists.

		   Default = 0 - meaning POTS port is unassociated to a Veip UNI.
		   This attribute is only relevant if bponVoipCapability attribute in same ONT is set to 3 = Veip-Style VoIP 
           For ISAM5.4.01, is not relevant for NG-PON2 since it is only relevant for VEIP. "
	::= { bponPotsPortEntry 54 }


-- *********************************************
--
-- GPON POTS CALL HISTORY TABLE
--
-- This is a new table beginning with FGU4.2.
-- This table contains a row for per historical call on a specific
-- POTS line. The row contains statistical data regarding the call.
-- For FGU4.3.5, the table can contain information for 
-- up to the last 32 calls terminated on this POTS line.
--
-- All rows of this table are auto-created/deleted in accordance with the 
-- setting of bponPotsPortCallHistCollectInd of the associated POTS UNI port.
-- The rows of the table are completely re-plenished by the agent
-- each time a GET is issued for the 1st row.  At that time - the OLT 
-- goes directly to the ONT for the freshist information
-- (using OMCI Get/GetNext commands
-- issued to the VoIP Call History Managed Entity).
--
-- For this initial GET of the 1st row, the OLT agent will delay
-- the GET-RESPONSE while it replenishes the entire
-- table with fresh information.
--
-- For ISAM4.0.10, this table is being re-used. 
-- Noted which attributes are relevant for ISAM4.0.10 
-- 
-- As of targeted release ISAM4.5.02, this table must also be SUPPORTED for Veip-style Voip.
--
--	For GPON - SUPPORTED as of ISAM4.0.10
--	For XG-PON1 - SUPPORTED as of ISAM4.6.02
--  For NG-PON2 - SUPPORTED as of ISAM5.4.01
--
-- *********************************************

gponPotsCallHistTable  OBJECT-TYPE
	SYNTAX SEQUENCE OF GponPotsCallHistEntry
	ACCESS	not-accessible
	STATUS	mandatory
	::= { bponPotsGroup 4 }


gponPotsCallHistEntry  OBJECT-TYPE
	SYNTAX 	GponPotsCallHistEntry
	ACCESS	not-accessible
	STATUS	mandatory
	INDEX	{ gponPotsCallHistOntIndex,
		  gponPotsCallHistSpIndex,
		  gponPotsCallHistNumber }
	::= { gponPotsCallHistTable 1 }

GponPotsCallHistEntry ::= SEQUENCE {
	gponPotsCallHistOntIndex		IfIndex,
	gponPotsCallHistSpIndex		SpIndex,
	gponPotsCallHistNumber		INTEGER,
	gponPotsCallHistValidInd		Boolean,
	gponPotsCallHistDate		OCTET STRING,
	gponPotsCallHistTime		OCTET STRING,
	gponPotsCallHistDuration			INTEGER,
	gponPotsCallHistCalledNumber		OCTET STRING,
	gponPotsCallHistCallingNumber		OCTET STRING,
	gponPotsCallHistRtpTxPkts		INTEGER,
	gponPotsCallHistRtpRxPkts		INTEGER,
	gponPotsCallHistRtpPktsLost		INTEGER,
	gponPotsCallHistRtpPktsDiscarded		INTEGER,
	gponPotsCallHistRtpOverruns		INTEGER,
	gponPotsCallHistRtpUnderruns		INTEGER,
	gponPotsCallHistRtpAvgJitter		INTEGER,
	gponPotsCallHistRtcpParticipation		INTEGER,
	gponPotsCallHistRtpPeakJitter		INTEGER,
	gponPotsCallHistAvgJitterBufferDepth		INTEGER,
	gponPotsCallHistRtcpXrParticipation		INTEGER,
	gponPotsCallHistAvgMos			INTEGER,
	gponPotsCallHistPeakRoundtripDelay		INTEGER,
	gponPotsCallHistAvgRoundtripDelay		INTEGER
}


gponPotsCallHistOntIndex  OBJECT-TYPE
	SYNTAX 	IfIndex
	ACCESS	read-only
	STATUS	mandatory
	DESCRIPTION 
		"Each row is indexed by the ifIndex of the ONT

		For ISAM4.0.10 - stays the same as latest FGU4.x  "
	::= { gponPotsCallHistEntry 1 }


gponPotsCallHistSpIndex  OBJECT-TYPE
	SYNTAX 	SpIndex
	ACCESS	read-only
	STATUS	mandatory
	DESCRIPTION 
		"Each row is also indexed by a number that
		 contains the slot number and port number
		 within the ONT

		For ISAM4.0.10 - stays the same as latest FGU4.x. "
	::= { gponPotsCallHistEntry 2 }



gponPotsCallHistNumber  OBJECT-TYPE
	SYNTAX 	INTEGER
	ACCESS	read-only
	STATUS	mandatory
	DESCRIPTION 
		" Each row is also indexed by a number to distinguish
		  the calls from one another.  Up to the last 32 calls
		  can be contained in the table (indexed 1 to 32).

		For ISAM4.0.10 - stays the same as latest FGU4.x "
	::= { gponPotsCallHistEntry 3 }

gponPotsCallHistValidInd OBJECT-TYPE
	SYNTAX 	Boolean
	ACCESS	read-only
	STATUS	mandatory
	DESCRIPTION 
		" Indicates whether or not this row reflects valid call information.
		  E.G. invalid is used to indicate that this information could not
		  be obtained from the ONT for some reason, or that information
		  for this call doesn't exist on the ONT. 
		  
		  Default = 0 = Invalid

		  As of FGU4.2, NOT SUPPORTED

		For ISAM4.0.10 - stays the same as latest FGU4.x "
	::= { gponPotsCallHistEntry 4 }

gponPotsCallHistDate  OBJECT-TYPE
	SYNTAX 	OCTET STRING (SIZE(0..8))
	ACCESS	read-only
	STATUS	mandatory
	DESCRIPTION 
		" Date (YY-MM-DD) when the call was initiated 
		  (start of ringing for terminating call, off-hook for originating call).
		  Null string means attribute is not supported by ONT. 
		  
		  Default = null

		For ISAM4.0.10 - stays the same as latest FGU4.x "
	::= { gponPotsCallHistEntry 5 }


gponPotsCallHistTime  OBJECT-TYPE
	SYNTAX 	OCTET STRING (SIZE(0..8))
	ACCESS	read-only
	STATUS	mandatory
	DESCRIPTION 
		" Time (HH:MM:SS) when the call was initiated.
		  Null string means attribute is not supported by ONT. 
		  
		  Default = null

		For ISAM4.0.10 - stays the same as latest FGU4.x "
	::= { gponPotsCallHistEntry 6 }


gponPotsCallHistDuration  OBJECT-TYPE
	SYNTAX 	INTEGER
	ACCESS	read-only
	STATUS	mandatory
	DESCRIPTION 
		" Duration of call (in seconds).
		  Minus 1 if not supported by ONT. 
		  
		  Default = -1

		For ISAM4.0.10 - stays the same as latest FGU4.x "
	::= { gponPotsCallHistEntry 7 }


gponPotsCallHistCalledNumber  OBJECT-TYPE
	SYNTAX 	OCTET STRING (SIZE(0..25))
	ACCESS	read-only
	STATUS	mandatory
	DESCRIPTION 
		" Called number (character string).
		  Null string means attribute is not supported by ONT. 
		  
		  Default = null 

		For ISAM4.0.10 - stays the same as latest FGU4.x"
	::= { gponPotsCallHistEntry 8 }


gponPotsCallHistCallingNumber  OBJECT-TYPE
	SYNTAX 	OCTET STRING (SIZE(0..25))
	ACCESS	read-only
	STATUS	mandatory
	DESCRIPTION 
		" Calling number (character string).
		  Null string means attribute is not supported by ONT. 
		  
		  Default = null

		For ISAM4.0.10 - stays the same as latest FGU4.x "
	::= { gponPotsCallHistEntry 9 }


gponPotsCallHistRtpTxPkts  OBJECT-TYPE
	SYNTAX 	INTEGER
	ACCESS	read-only
	STATUS	mandatory
	DESCRIPTION 
		" Number of RTP packets transmitted. 
		  Minus 1 if not supported by ONT. 
		  
		  Default = -1

		For ISAM4.0.10 - stays the same as latest FGU4.x "
	::= { gponPotsCallHistEntry 10 }

gponPotsCallHistRtpRxPkts  OBJECT-TYPE
	SYNTAX 	INTEGER
	ACCESS	read-only
	STATUS	mandatory
	DESCRIPTION 
		" Number of RTP packets received. 
		  Minus 1 if not supported by ONT. 
		  
		  Default = -1

		For ISAM4.0.10 - stays the same as latest FGU4.x "
	::= { gponPotsCallHistEntry 11 }


gponPotsCallHistRtpPktsLost OBJECT-TYPE
	SYNTAX 	INTEGER
	ACCESS	read-only
	STATUS	mandatory
	DESCRIPTION 
		" Number of RTP packets that were not received (which can
		  be determined from missing sequence numbers). 
		  Minus 1 if not supported by ONT. 
		  
		  Default = -1

		For ISAM4.0.10 - stays the same as latest FGU4.x "
	::= { gponPotsCallHistEntry 12 }

gponPotsCallHistRtpPktsDiscarded OBJECT-TYPE
	SYNTAX 	INTEGER
	ACCESS	read-only
	STATUS	mandatory
	DESCRIPTION 
		" Number of RTP packets discarded due to errors. 
		  Minus 1 if not supported by ONT. 
		  
		  Default = -1

		For ISAM4.0.10 - stays the same as latest FGU4.x "
	::= { gponPotsCallHistEntry 13 }


gponPotsCallHistRtpOverruns OBJECT-TYPE
	SYNTAX 	INTEGER
	ACCESS	read-only
	STATUS	mandatory
	DESCRIPTION 
		" Number of jitter buffer over-runs (number of RTP 
		  packets discarded because the jitter buffer was full). 
		  Minus 1 if not supported by ONT. 
		  
		  Default = -1

		For ISAM4.0.10 - stays the same as latest FGU4.x "
	::= { gponPotsCallHistEntry 14 }

gponPotsCallHistRtpUnderruns OBJECT-TYPE
	SYNTAX 	INTEGER
	ACCESS	read-only
	STATUS	mandatory
	DESCRIPTION 
		" Number of jitter buffer under-runs (number of RTP packets
		  that were not processed to provide PCM voice because the 
		  jitter buffer was empty).  
		  Minus 1 if not supported by ONT. 
		  
		  Default = -1

		For ISAM4.0.10 - stays the same as latest FGU4.x "
	::= { gponPotsCallHistEntry 15 }


gponPotsCallHistRtpAvgJitter OBJECT-TYPE
	SYNTAX 	INTEGER
	ACCESS	read-only
	STATUS	mandatory
	DESCRIPTION 
		" Average jitter (msec) in the received RTP stream.  
		  Minus 1 if not supported by ONT. 
		  
		  Default = -1
		For ISAM4.0.10 - stays the same as latest FGU4.x "
	::= { gponPotsCallHistEntry 16 }


gponPotsCallHistRtcpParticipation OBJECT-TYPE
	SYNTAX 	INTEGER
	ACCESS	read-only
	STATUS	mandatory
	DESCRIPTION 
		" Whether or not the far end participated in RTCP (NO = 0, YES = 1).
		  Minus 1 if not supported by ONT. 
		  
		  Default = -1

		For ISAM4.0.10 - stays the same as latest FGU4.x  "
	::= { gponPotsCallHistEntry 17 }


gponPotsCallHistRtpPeakJitter OBJECT-TYPE
	SYNTAX 	INTEGER
	ACCESS	read-only
	STATUS	mandatory
	DESCRIPTION 
		" Peak jitter (msec) in the received RTP stream.  
		  Minus 1 if not supported by ONT. 
		  
		  Default = -1

		For ISAM4.0.10 - stays the same as latest FGU4.x "
	::= { gponPotsCallHistEntry 18 }


gponPotsCallHistAvgJitterBufferDepth OBJECT-TYPE
	SYNTAX 	INTEGER
	ACCESS	read-only
	STATUS	mandatory
	DESCRIPTION 
		" Average jitter buffer depth (msec) for the call.  
		  Minus 1 if not supported by ONT. 
		  
		  Default = -1

		For ISAM4.0.10 - stays the same as latest FGU4.x   "
	::= { gponPotsCallHistEntry 19 }

gponPotsCallHistRtcpXrParticipation OBJECT-TYPE
	SYNTAX 	INTEGER
	ACCESS	read-only
	STATUS	mandatory
	DESCRIPTION 
		" Whether or not the far-end participated in RTCP-XR (NO = 0, YES = 1).
		  Minus 1 if not supported by ONT. 
		  
		  Default = -1 

		For ISAM4.0.10 - stays the same as latest FGU4.x  "
	::= { gponPotsCallHistEntry 20 }


gponPotsCallHistAvgMos OBJECT-TYPE
	SYNTAX 	INTEGER
	ACCESS	read-only
	STATUS	mandatory
	DESCRIPTION 
		" Average Mean Opinion Score (MOS).  Only available if far-end 
		  participated in RTCP-XR.
		  Range of values from 0 to 50 represent MOS scores from
		  0.0 to 5.0 (i.e. units are in tenths).  
		  Minus 1 if not supported by ONT. 
		  
		  Default = -1

		For ISAM4.0.10 - stays the same as latest FGU4.x  "
	::= { gponPotsCallHistEntry 21 }


gponPotsCallHistPeakRoundtripDelay OBJECT-TYPE
	SYNTAX 	INTEGER
	ACCESS	read-only
	STATUS	mandatory
	DESCRIPTION 
		" Peak round trip delay (msec).  Only available if far-end 
		  participated in RTCP-XR.
		  Minus 1 if not supported by ONT. 
		  
		  Default = -1

		For ISAM4.0.10 - stays the same as latest FGU4.x  "
	::= { gponPotsCallHistEntry 22 }


gponPotsCallHistAvgRoundtripDelay OBJECT-TYPE
	SYNTAX 	INTEGER
	ACCESS	read-only
	STATUS	mandatory
	DESCRIPTION 
		" Average round trip delay (msec).  Only available if far-end 
		  participated in RTCP-XR.
		  Minus 1 if not supported by ONT. 
		  
		  Default = -1

		For ISAM4.0.10 - stays the same as latest FGU4.x  "
	::= { gponPotsCallHistEntry 23 }

-- *********************************************
--
-- GPON POTS DIALTONE TEST TABLE
--
-- This is a new table beginning with FG4.3.
-- This table contains a row for each provisioned POTS port on a
-- specific ONT. Rows are created/deleted automatically by the 
-- OLT agent in a one-to-one association with creation/deletion of 
-- POTS ports. 
--
-- For ISAM4.0.10, this table is being re-used. 
-- Noted which attributes are relevant for ISAM4.0.10 
--
--
--	For GPON - SUPPORTED as of ISAM4.0.10
--	For XG-PON1 - SUPPORTED as of ISAM4.6.02
--  For NG-PON2 - SUPPORTED as of ISAM5.4.01
--
-- *********************************************

gponPotsDialTestTable  OBJECT-TYPE
	SYNTAX SEQUENCE OF GponPotsDialTestEntry
	ACCESS	not-accessible
	STATUS	mandatory
	::= { bponPotsGroup 5 }


gponPotsDialTestEntry  OBJECT-TYPE
	SYNTAX 	GponPotsDialTestEntry
	ACCESS	not-accessible
	STATUS	mandatory
	INDEX	{ gponPotsDialTestOntIndex,
		   gponPotsDialTestSpIndex }
	::= { gponPotsDialTestTable 1 }

GponPotsDialTestEntry ::= SEQUENCE {
	gponPotsDialTestOntIndex		IfIndex,
	gponPotsDialTestSpIndex		SpIndex,
	gponPotsDialTestMode		INTEGER,
	gponPotsDialTestSlowMakeThresholdTimer	INTEGER,
	gponPotsDialTestNoMakeThresholdTimer	INTEGER,
	gponPotsDialTestSlowBreakThresholdTimer	INTEGER,
	gponPotsDialTestNoBreakThresholdTimer	INTEGER,
	gponPotsDialTestToneOrPulse		INTEGER,
	gponPotsDialTestDigit		OCTET STRING,
	gponPotsDialTestCmd		INTEGER,
	gponPotsDialTestMakeResult	INTEGER,
	gponPotsDialTestBreakResult	INTEGER,
	gponPotsDialTestTimeToMakeMeasure	INTEGER,
	gponPotsDialTestTimeToBreakMeasure	INTEGER,
	gponPotsDialTestDialtoneFrequency1		INTEGER,
	gponPotsDialTestDialtoneFrequency2		INTEGER,
	gponPotsDialTestDialtoneFrequency3		INTEGER,
	gponPotsDialTestDialtonePowerThreshold	INTEGER,
	gponPotsDialTestIdleChannelPowerThreshold	INTEGER,
	gponPotsDialTestDialtonePowerResult		INTEGER,
	gponPotsDialTestIdleChannelPowerResult		INTEGER,
	gponPotsDialTestDialtonePowerMeasure	INTEGER,
	gponPotsDialTestIdleChannelPowerMeasure	INTEGER
}


gponPotsDialTestOntIndex  OBJECT-TYPE
	SYNTAX 	IfIndex
	ACCESS	read-only
	STATUS	mandatory
	DESCRIPTION 
		"Each row is indexed by the ifIndex of the ONT 

		For ISAM4.0.10 - stays the same as latest FGU4.x "
	::= { gponPotsDialTestEntry 1 }


gponPotsDialTestSpIndex  OBJECT-TYPE
	SYNTAX 	SpIndex
	ACCESS	read-only
	STATUS	mandatory
	DESCRIPTION 
		"Each row is also indexed by a number that
		 contains the slot number and port number
		 within the ONT.

		For ISAM4.0.10 - stays the same as latest FGU4.x "
	::= { gponPotsDialTestEntry 2 }



gponPotsDialTestMode  OBJECT-TYPE
	SYNTAX 	INTEGER
	ACCESS	read-write
	STATUS	mandatory
	DESCRIPTION 
		" Indicates what ONT should do if POTS line is busy (when
		  actual test is requested):

		  0 = deny the test
		  1 = force the test (NOT SUPPORTED as of FGU4.3 and beyond)

		  Default = 0 = deny the test

		For ISAM4.0.10 - stays the same as latest FGU4.x. "
	::= { gponPotsDialTestEntry 3 }


gponPotsDialTestSlowMakeThresholdTimer  OBJECT-TYPE
	SYNTAX 	INTEGER 
	ACCESS	read-write
	STATUS	mandatory
	DESCRIPTION 
		" Indicates the threshold timer which the ONT should use 
		  to determine if dialtone was obtained slowly.
		  Range 0.0 to 6.0 seconds, in units of 0.1 second


		  Default = 0.0 = meaning ONT should use its own default timer.

		For ISAM4.0.10 - stays the same as latest FGU4.x  "
	::= { gponPotsDialTestEntry 4 }


gponPotsDialTestNoMakeThresholdTimer  OBJECT-TYPE
	SYNTAX 	INTEGER (0 | 10..100)
	ACCESS	read-write
	STATUS	mandatory
	DESCRIPTION 
		" Indicates the threshold timer which the ONT should use 
		  to determine if dialtone was not obtained.
		  Range 1.0 to 10.0 seconds, in units of 0.1 second (as well
		  as the value 0).


		  Default = 0 = meaning ONT should use its own default timer.

		For ISAM4.0.10 - stays the same as latest FGU4.x  "
	::= { gponPotsDialTestEntry 5 }


gponPotsDialTestSlowBreakThresholdTimer  OBJECT-TYPE
	SYNTAX 	INTEGER
	ACCESS	read-write
	STATUS	mandatory
	DESCRIPTION 
		" Indicates the threshold timer which the ONT should use 
		  to determine if dialtone break obtained slowly.
		  Range 0.0 to 3.0 seconds, in units of 0.1 second


		  Default = 0.0 = meaning ONT should use its own default timer.

		For ISAM4.0.10 - stays the same as latest FGU4.x  "
	::= { gponPotsDialTestEntry 6 }


gponPotsDialTestNoBreakThresholdTimer  OBJECT-TYPE
	SYNTAX 	INTEGER (0 | 10..30)
	ACCESS	read-write
	STATUS	mandatory
	DESCRIPTION 
		" Indicates the threshold timer which the ONT should use 
		  to determine if dialtone break was not obtained.
		  Range 1.0 to 3.0 seconds, in units of 0.1 second (as well
		  as the value 0).


		  Default = 0 = meaning ONT should use its own default timer.

		For ISAM4.0.10 - stays the same as latest FGU4.x  "
	::= { gponPotsDialTestEntry 7 }


gponPotsDialTestToneOrPulse OBJECT-TYPE
	SYNTAX 	INTEGER
	ACCESS	read-write
	STATUS	mandatory
	DESCRIPTION 
		" Indicates whether digit to be dialed should be sent as
		  tone or pulse:

		  0 = tone
		  1 = pulse (NOT SUPPORTED for FGU4.3)

		  Default = 0 = tone.

		For ISAM4.0.10 - stays the same as latest FGU4.x     "
	::= { gponPotsDialTestEntry 8 }


gponPotsDialTestDigit OBJECT-TYPE
	SYNTAX 	OCTET STRING (SIZE(0..1))
	ACCESS	read-write
	STATUS	mandatory
	DESCRIPTION 
		" Indicates the digit that the ONT should use to break the 
		  dial tone:

		  Valid values are null string and the following printable
		  ASCII characters:  0 thru 9, * and #.

		  The null value means to let the ONT use its own default digit
		  (see OMCI spec regarding how to encode this value in OMCI
		  Test Command message).

		  Default = null

		For ISAM4.0.10 - stays the same as latest FGU4.x   "
	::= { gponPotsDialTestEntry 9 }


gponPotsDialTestCmd  OBJECT-TYPE
	SYNTAX 	INTEGER 
	ACCESS	read-write
	STATUS	mandatory
	DESCRIPTION 
		" Manager is only permitted to SET this attribute
		 to (1), indicating desire to execute POTS make-break
		 dialtone test.
		 Thereafter, manager issues SNMP GET to determine
		 status/result of the dialtone test. Agent changes
		 attribute value accordingly as follows:
		 0 - This is the initial default value, meaning a dialtone test
		          has never been executed on this port since initialization.
		 1 - Only value settable by manager (to initiate test)  
		 2 - meaning dialtone test is in progress.
		 3 - meaning dialtone test failed because ONT failed
		       to respond within reasonable time.
		 4 - meaning dialtone test has completed execution.
		 5 - meaning OLT didn't issue the dialtone command.
		 6 - meaning ONT rejected the test command for some reason
		      (e.g. OMCI reject because ONT doesn't implement this test).

		Manager must read results in 
  		gponPotsDialTestMakeResult and gponPotsDialTestBreakResult
		attributes to discern the specifics of the actual dialtone test results.

		Default = 0

		For ISAM4.0.10 - stays the same as latest FGU4.x
		For ISAM4.2.02 - stays the same as latest ISAM (including for legacy and standard VoIP modes).
		For ISAM4.3, continues to be SUPPORTED as latest ISAM (except NOT SUPPORTED for Veip-style VoIP).  "
	::= { gponPotsDialTestEntry 10 }

gponPotsDialTestMakeResult  OBJECT-TYPE
	SYNTAX 	INTEGER
	ACCESS	read-only
	STATUS	mandatory
	DESCRIPTION 
		"Indicates the result of the make part of the dialtone test for a 
		 specific POTS port as follows:

		 0 =  ONT did not run test (e.g. because subscriber was off-hook already
		        and the test mode was NOT forced)
		 1 = Failed to draw dialtone (no measurement reported)
		 2 = Slow draw of dialtone (no measurement reported)
		 3 = Passed (no measurement reported)
		 4 = Failed to draw dialtone (measurement reported)
		 5 = Slow draw of dialtone (measurement reported)
		 6 = Passed (measurement reported)

		If measurement is reported, it is contained in 
		gponPotsDialTestTimeToMakeMeasure attribute.

		Default = 0 

		For ISAM4.0.10 - stays the same as latest FGU4.x  "
	::= { gponPotsDialTestEntry 11 }


gponPotsDialTestBreakResult  OBJECT-TYPE
	SYNTAX 	INTEGER
	ACCESS	read-only
	STATUS	mandatory
	DESCRIPTION 
		"Indicates the result of the break part of the dialtone test for a 
		 specific POTS port as follows:

		 0 =  ONT did not run test (e.g. because subscriber was off-hook already
		        and the test mode was NOT forced)
		 1 = Failed to break dialtone (no measurement reported)
		 2 = Slow break of dialtone (no measurement reported)
		 3 = Passed (no measurement reported)
		 4 = Failed to break dialtone (measurement reported)
		 5 = Slow break of dialtone (measurement reported)
		 6 = Passed (measurement reported)

		If measurement is reported, it is contained in 
		gponPotsDialTestTimeToBreakMeasure attribute.

		Default = 0 

		For ISAM4.0.10 - stays the same as latest FGU4.x  "
	::= { gponPotsDialTestEntry 12 }


gponPotsDialTestTimeToMakeMeasure OBJECT-TYPE
	SYNTAX 	INTEGER
	ACCESS	read-only
	STATUS	mandatory
	DESCRIPTION 
		"Indicates the measured time to make dialtone
		 from the make-break dialtone test.
		 
		 This attribute contains valid data only if 
		 gponPotsDialTestMakeResult attribute coding is:

		 4 = Failed to draw dialtone (measurement reported)
		 5 = Slow draw of dialtone (measurement reported)
		 6 = Passed (measurement reported)

		 Units are seconds  (resolution is 0.1 second)
		 Range is 0 - 255.

		Default = 0 

		For ISAM4.0.10 - stays the same as latest FGU4.x  "
	::= { gponPotsDialTestEntry 13 }


gponPotsDialTestTimeToBreakMeasure OBJECT-TYPE
	SYNTAX 	INTEGER
	ACCESS	read-only
	STATUS	mandatory
	DESCRIPTION 
		"Indicates the measured time to break dialtone
		 from the make-break dialtone test.
		 
		 This attribute contains valid data only if 
		 gponPotsDialTestBreakResult attribute coding is:

		 4 = Failed to break dialtone (measurement reported)
		 5 = Slow break of dialtone (measurement reported)
		 6 = Passed (measurement reported)

		 Units are seconds  (resolution is 0.1 second)
		 Range is 0 - 255.

		Default = 0

		For ISAM4.0.10 - stays the same as latest FGU4.x   "
	::= { gponPotsDialTestEntry 14 }


gponPotsDialTestDialtoneFrequency1  OBJECT-TYPE
	SYNTAX 	INTEGER (0 | 300..3500)
	ACCESS	read-write
	STATUS	mandatory
	DESCRIPTION 
		" Indicates 1st dialtone frequency component.
		  Units are 1 Hz.

		  If 1st, 2nd and 3rd frequency components are all 0,
		  then ONT uses its own defaults.

		  1st component cannot be 0 if 2nd component is not 0.

		  Default = 0  

		  As of FGU4.5, this attribute is NOT SUPPORTED.

		For ISAM4.0.10 - stays the same as latest FGU4.x  "
	::= { gponPotsDialTestEntry 15 }

gponPotsDialTestDialtoneFrequency2  OBJECT-TYPE
	SYNTAX 	INTEGER (0 | 300..3500)
	ACCESS	read-write
	STATUS	mandatory
	DESCRIPTION 
		" Indicates 2nd dialtone frequency component.
		  Units are 1 Hz.

		  If 1st, 2nd and 3rd frequency components are all 0,
		  then ONT uses its own defaults.

		  2nd component cannot be 0 if 3rd component is not 0.

		  Default = 0

		  As of FGU4.5, this attribute is NOT SUPPORTED.

		For ISAM4.0.10 - stays the same as latest FGU4.x  "
	::= { gponPotsDialTestEntry 16 }

gponPotsDialTestDialtoneFrequency3  OBJECT-TYPE
	SYNTAX 	INTEGER (0 | 300..3500)
	ACCESS	read-write
	STATUS	mandatory
	DESCRIPTION 
		" Indicates 3rd dialtone frequency component.
		  Units are 1 Hz.

		  If 1st, 2nd and 3rd frequency components are all 0,
		  then ONT uses its own defaults.

		  Default = 0

		  As of FGU4.5, this attribute is NOT SUPPORTED.

		For ISAM4.0.10 - stays the same as latest FGU4.x  "
	::= { gponPotsDialTestEntry 17 }


gponPotsDialTestDialtonePowerThreshold  OBJECT-TYPE
	SYNTAX 	INTEGER (-253..0)
	ACCESS	read-write
	STATUS	mandatory
	DESCRIPTION 
		" Indicates the threshold for declaring dialtone power
		  pass/fail.  Units are dBm0 (resolution is 0.1 dB)
		  Range is -25.3 - 0.0 (the value 0 means that
		  ONT should use its own default threshold).

		  Default = 0

		  As of FGU4.5, this attribute is NOT SUPPORTED.

		For ISAM4.0.10 - stays the same as latest FGU4.x  "
	::= { gponPotsDialTestEntry 18 }

gponPotsDialTestIdleChannelPowerThreshold  OBJECT-TYPE
	SYNTAX 	INTEGER (-90..0)
	ACCESS	read-write
	STATUS	mandatory
	DESCRIPTION 
		" Indicates the threshold for declaring Idle Channel power
		  pass/fail.  Units are dBm0 (resolution is 1 dB)
		  Range is -90 - 0 (the value 0 means that
		  ONT should use its own default threshold).

		  Default = 0

		  As of FGU4.5, this attribute is NOT SUPPORTED. 

		For ISAM4.0.10 - stays the same as latest FGU4.x "
	::= { gponPotsDialTestEntry 19 }

gponPotsDialTestDialtonePowerResult  OBJECT-TYPE
	SYNTAX 	INTEGER
	ACCESS	read-only
	STATUS	mandatory
	DESCRIPTION 
		"Indicates the summary result of 
		 Dialtone Power test.
		 Coding is as follows:

		 0 = Test Not Run
		 1 = Test Failed (measurement reported)
		 2 = Test Failed (no measurement reported)
		 3 = Test Passed (measurement reported)
		 4 = Test Passed (no measurement reported)

		 For cases where the measurement is reported, the 
		 actual value is contained in 
		 gponPotsDialTestDialtonePowerMeasure attribute.

		 As of FGU4.5, this attribute is NOT SUPPORTED. 

		For ISAM4.0.10 - stays the same as latest FGU4.x "
	::= { gponPotsDialTestEntry 20 }

gponPotsDialTestIdleChannelPowerResult  OBJECT-TYPE
	SYNTAX 	INTEGER
	ACCESS	read-only
	STATUS	mandatory
	DESCRIPTION 
		"Indicates the summary result of 
		 Idle Channel Power test.
		 Coding is as follows:

		 0 = Test Not Run
		 1 = Test Failed (measurement reported)
		 2 = Test Failed (no measurement reported)
		 3 = Test Passed (measurement reported)
		 4 = Test Passed (no measurement reported)

		 For cases where the measurement is reported, the 
		 actual value is contained in 
		 gponPotsDialTestIdleChannelPowerMeasure attribute.

		 As of FGU4.5, this attribute is NOT SUPPORTED.

		For ISAM4.0.10 - stays the same as latest FGU4.x  "
	::= { gponPotsDialTestEntry 21 }

gponPotsDialTestDialtonePowerMeasure  OBJECT-TYPE
	SYNTAX 	INTEGER
	ACCESS	read-only
	STATUS	mandatory
	DESCRIPTION 
		"Contains the measurement from the 
		 Dialtone Power test.

		 This attribute contains valid data only if 
		 gponPotsDialTestDialtonePowerResult attribute coding is:

		 1 = Test Failed (measurement reported)
		 3 = Test Passed (measurement reported)

		 Units are dBm0 (resolution is 0.1 dB)
		 Range is -255 - 0.

		 Default is 0.

		 As of FGU4.5, this attribute is NOT SUPPORTED.

		For ISAM4.0.10 - stays the same as latest FGU4.x   "
	::= { gponPotsDialTestEntry 22 }

gponPotsDialTestIdleChannelPowerMeasure  OBJECT-TYPE
	SYNTAX 	INTEGER
	ACCESS	read-only
	STATUS	mandatory
	DESCRIPTION 
		"Contains the measurement from the 
		 Idle Channel Power test.

		 This attribute contains valid data only if 
		 gponPotsDialTestIdleChannelPowerResult attribute coding is:

		 1 = Test Failed (measurement reported)
		 3 = Test Passed (measurement reported)

		 Units are dBm0 (resolution is 1 dB)
		 Range is -255 - 0.

		 Default is 0.

		 As of FGU4.5, this attribute is NOT SUPPORTED.

		For ISAM4.0.10 - stays the same as latest FGU4.x   "
	::= { gponPotsDialTestEntry 23 }

-- *********************************************
--
-- GPON POTS SIP DIALTONE TEST TABLE
--
-- This is a new table beginning with FG4.3.5
-- This table contains a row for each provisioned POTS port on a
-- specific ONT. Rows are created/deleted automatically by the 
-- OLT agent in a one-to-one association with creation/deletion of 
-- POTS ports. 
--
-- This table is used to execute the SIP pull-break dialtone test,
-- and to sumarize the results of the test.
--
-- For ISAM4.0.10, this table is being re-used. 
-- Noted which attributes are relevant for ISAM4.0.10 
--
--
--	For GPON - SUPPORTED as of ISAM4.0.10
--	For XG-PON1 - SUPPORTED as of ISAM4.6.02
--  For NG-PON2 - SUPPORTED as of ISAM5.4.01
--
-- *********************************************

gponPotsSipDialTestTable  OBJECT-TYPE
	SYNTAX SEQUENCE OF GponPotsSipDialTestEntry
	ACCESS	not-accessible
	STATUS	mandatory
	::= { bponPotsGroup 6 }


gponPotsSipDialTestEntry  OBJECT-TYPE
	SYNTAX 	GponPotsSipDialTestEntry
	ACCESS	not-accessible
	STATUS	mandatory
	INDEX	{ gponPotsSipDialTestOntIndex,
		   gponPotsSipDialTestSpIndex }
	::= { gponPotsSipDialTestTable 1 }

GponPotsSipDialTestEntry ::= SEQUENCE {
	gponPotsSipDialTestOntIndex		IfIndex,
	gponPotsSipDialTestSpIndex		SpIndex,
	gponPotsSipDialTestMode		INTEGER,
	gponPotsSipDialTestPhoneNumber	DisplayString,
	gponPotsSipDialTestCmd		INTEGER,
	gponPotsSipDialTestSummaryResult	INTEGER,
	gponPotsSipDialTestDelayMeasure	INTEGER,
	gponPotsSipDialTestText		DisplayString,
	gponPotsSipDialTestPingResult	INTEGER
}


gponPotsSipDialTestOntIndex  OBJECT-TYPE
	SYNTAX 	IfIndex
	ACCESS	read-only
	STATUS	mandatory
	DESCRIPTION 
		"Each row is indexed by the ifIndex of the ONT

		For ISAM4.0.10 - stays the same as latest FGU4.x   "
	::= { gponPotsSipDialTestEntry 1 }


gponPotsSipDialTestSpIndex  OBJECT-TYPE
	SYNTAX 	SpIndex
	ACCESS	read-only
	STATUS	mandatory
	DESCRIPTION 
		"Each row is also indexed by a number that
		 contains the slot number and port number
		 within the ONT.

		For ISAM4.0.10 - stays the same as latest FGU4.x  "
	::= { gponPotsSipDialTestEntry 2 }



gponPotsSipDialTestMode  OBJECT-TYPE
	SYNTAX 	INTEGER
	ACCESS	read-write
	STATUS	mandatory
	DESCRIPTION 
		" Indicates what ONT should do if POTS line is busy (when
		  actual test is requested):

		  0 = deny the test
		  1 = force the test (NOT SUPPORTED as of FGU4.3 and beyond)

		  Default = 0 = deny the test.

		For ISAM4.0.10 - stays the same as latest FGU4.x  "
	::= { gponPotsSipDialTestEntry 3 }


gponPotsSipDialTestPhoneNumber  OBJECT-TYPE
	SYNTAX 	DisplayString (SIZE(0..16))
	ACCESS	read-write
	STATUS	mandatory
	DESCRIPTION 
		" This represents the phone number to be dialed for the SIP pull-break test.

		  Default = null string (when row is autonomously created by OLT).  
		  This attribute cannot be null when test is invoked,
		  and when test is invoked, this attribute must contain at least 1 character.

		  Valid characters are 0 thru 9, * and #

		For ISAM4.0.10 - stays the same as latest FGU4.x  "
	::= { gponPotsSipDialTestEntry 4 }


gponPotsSipDialTestCmd  OBJECT-TYPE
	SYNTAX 	INTEGER 
	ACCESS	read-write
	STATUS	mandatory
	DESCRIPTION 
		" Manager is only permitted to SET this attribute
		 to (1), indicating desire to execute POTS SIP make-break
		 dialtone test.
		 Thereafter, manager issues SNMP GET to determine
		 status/result of the dialtone test. Agent changes
		 attribute value accordingly as follows:
		 0 - This is the initial default value, meaning a SIP dialtone test
		          has never been executed on this port since initialization.
		 1 - Only value settable by manager (to initiate test)  
		 2 - meaning dialtone test is in progress.
		 3 - meaning dialtone test failed because ONT failed
		       to respond within reasonable time.
		 4 - meaning dialtone test has completed execution.
		 5 - meaning OLT didn't issue the dialtone command.
		 6 - meaning ONT rejected the test command for some reason
		      (e.g. OMCI reject because ONT doesn't implement this test).

		Manager must read results in subsequent attributes in this table
		to discern the specifics of the actual dialtone test results.

		Default = 0

		For ISAM4.0.10 - stays the same as latest FGU4.x 
		For ISAM4.2.02 - stays the same as latest ISAM (including for legacy and standard VoIP modes).
		For ISAM4.3, continues to be SUPPORTED as latest ISAM (except NOT SUPPORTED for Veip-style VoIP).   "
	::= { gponPotsSipDialTestEntry 5 }

gponPotsSipDialTestSummaryResult  OBJECT-TYPE
	SYNTAX 	INTEGER
	ACCESS	read-only
	STATUS	mandatory
	DESCRIPTION 
		"Indicates the summary result of the draw-break portion of the SIP  
		 dialtone test for a specific POTS port as follows:

		 0 = Failed
		 1 = Passed
		 2 = ONT did not run test (because subscriber was off-hook already
		        and the test mode was NOT forced)
		 3 = ONT did not run test (for some other reason)

		Default = 0 

		For ISAM4.0.10 - stays the same as latest FGU4.x   "
	::= { gponPotsSipDialTestEntry 6 }


gponPotsSipDialTestDelayMeasure  OBJECT-TYPE
	SYNTAX 	INTEGER
	ACCESS	read-only
	STATUS	mandatory
	DESCRIPTION 
		" This represents the measure of post dial delay (e.g. how
		   long it took to get bearer packets after the SIP INVITE message
		   is sent).
		   Units are tenths of seconds.

		Default = 0 

		For ISAM4.0.10 - stays the same as latest FGU4.x   "
	::= { gponPotsSipDialTestEntry 7 }


gponPotsSipDialTestText  OBJECT-TYPE
	SYNTAX 	DisplayString (SIZE(0..29))
	ACCESS	read-only
	STATUS	mandatory
	DESCRIPTION 
		" This represents readable text regarding the result of this test
		   (as reported directly from the ONT). 

		  Default = null string

		For ISAM4.0.10 - stays the same as latest FGU4.x   "
	::= { gponPotsSipDialTestEntry 8 }

gponPotsSipDialTestPingResult  OBJECT-TYPE
	SYNTAX 	INTEGER
	ACCESS	read-only
	STATUS	mandatory
	DESCRIPTION 
		"Indicates the summary result of the automatic ping portion of the SIP  
		 dialtone test for a specific POTS port as follows:

		 0 = Ping not attempted
		 1 = Ping attempted and failed
		 2 = Ping passed

		Default = 0  

		As of FGU4.5, this attribute is NOT SUPPORTED. 

		For ISAM4.0.10 - stays the same as latest FGU4.x  "
	::= { gponPotsSipDialTestEntry 9 }


-- *********************************************
--
-- GPON POTS MLT TEST TABLE
--
-- This is a new table beginning with FG4.5.
-- This table contains a row for each provisioned POTS port on a
-- specific ONT. Rows are created/deleted automatically by the 
-- OLT agent in a one-to-one association with creation/deletion of 
-- POTS ports. 
--
-- For ISAM4.0.10, this table is being re-used. 
-- Noted which attributes are relevant for ISAM4.0.10 
--
--
--	For GPON - SUPPORTED as of ISAM4.0.10
--	For XG-PON1 - SUPPORTED as of ISAM4.6.02
--  For NG-PON2 - SUPPORTED as of ISAM5.4.01
--
-- *********************************************

gponPotsMltTestTable  OBJECT-TYPE
	SYNTAX SEQUENCE OF GponPotsMltTestEntry
	ACCESS	not-accessible
	STATUS	mandatory
	::= { bponPotsGroup 7 }


gponPotsMltTestEntry  OBJECT-TYPE
	SYNTAX 	GponPotsMltTestEntry
	ACCESS	not-accessible
	STATUS	mandatory
	INDEX	{ gponPotsMltTestOntIndex,
		   gponPotsMltTestSpIndex }
	::= { gponPotsMltTestTable 1 }

GponPotsMltTestEntry ::= SEQUENCE {
	gponPotsMltTestOntIndex		IfIndex,
	gponPotsMltTestSpIndex		SpIndex,
	gponPotsMltTestMode		INTEGER,
	gponPotsMltTestHazardDCThreshold	INTEGER,
	gponPotsMltTestHazardACThreshold	INTEGER,
	gponPotsMltTestForeignDCThreshold	INTEGER,
	gponPotsMltTestForeignACThreshold	INTEGER,
	gponPotsMltTestTipGndRingGndThreshold	INTEGER,
	gponPotsMltTestTipRingThreshold	INTEGER,
	gponPotsMltTestRingEquivMinThreshold	INTEGER,
	gponPotsMltTestRingEquivMaxThreshold	INTEGER,
	gponPotsMltTestCmd		INTEGER,
	gponPotsMltTestSummaryResult	OCTET STRING,
	gponPotsMltTestDcTipGroundResult	INTEGER,
	gponPotsMltTestDcRingGroundResult	INTEGER,
	gponPotsMltTestAcTipGroundResult	INTEGER,
	gponPotsMltTestAcRingGroundResult	INTEGER,
	gponPotsMltTestTipGroundResistResult	INTEGER,
	gponPotsMltTestRingGroundResistResult	INTEGER,
	gponPotsMltTestTipRingResistResult	INTEGER,
	gponPotsMltTestRingerLoadResult	INTEGER,
	gponPotsMltTestDcTipGroundMeasure		INTEGER,
	gponPotsMltTestDcRingGroundMeasure	INTEGER,
	gponPotsMltTestAcTipGroundMeasure		INTEGER,
	gponPotsMltTestAcRingGroundMeasure	INTEGER,
	gponPotsMltTestTipGroundResistMeasure	INTEGER,
	gponPotsMltTestRingGroundResistMeasure	INTEGER,
	gponPotsMltTestTipRingResistMeasure	INTEGER,
	gponPotsMltTestRingerLoadMeasure		INTEGER

}


gponPotsMltTestOntIndex  OBJECT-TYPE
	SYNTAX 	IfIndex
	ACCESS	read-only
	STATUS	mandatory
	DESCRIPTION 
		"Each row is indexed by the ifIndex of the ONT 

		For ISAM4.0.10 - stays the same as latest FGU4.x "
	::= { gponPotsMltTestEntry 1 }


gponPotsMltTestSpIndex  OBJECT-TYPE
	SYNTAX 	SpIndex
	ACCESS	read-only
	STATUS	mandatory
	DESCRIPTION 
		"Each row is also indexed by a number that
		 contains the slot number and port number
		 within the ONT.

		For ISAM4.0.10 - stays the same as latest FGU4.x "
	::= { gponPotsMltTestEntry 2 }



gponPotsMltTestMode  OBJECT-TYPE
	SYNTAX 	INTEGER
	ACCESS	read-write
	STATUS	mandatory
	DESCRIPTION 
		" Indicates what ONT should do if POTS line is busy (when
		  actual test is requested):

		  0 = deny the test
		  1 = force the test

		  Default = 0 = deny the test. 

		For ISAM4.0.10 - stays the same as latest FGU4.x"
	::= { gponPotsMltTestEntry 3 }


gponPotsMltTestHazardDCThreshold  OBJECT-TYPE
	SYNTAX 	INTEGER (0 | 80..150)
	ACCESS	read-write
	STATUS	mandatory
	DESCRIPTION 
		" Indicates the threshold for declaring DC hazardous voltage
		  pass/fail.  Units are Volts.
		  Range is 80 - 150 (and includes the value 0, which means that
		  ONT should use its own default threshold).

		  Default = 0 - meaning ONT should use its own default. 

		For ISAM4.0.10 - stays the same as latest FGU4.x  "
	::= { gponPotsMltTestEntry 4 }


gponPotsMltTestHazardACThreshold  OBJECT-TYPE
	SYNTAX 	INTEGER (0 | 50..150)
	ACCESS	read-write
	STATUS	mandatory
	DESCRIPTION 
		" Indicates the threshold for declaring AC hazardous voltage
		  pass/fail.  Units are Volts RMS.
		  Range is 50 - 150 (and includes the value 0, which means that
		  ONT should use its own default threshold).

		  Default = 0 - meaning ONT should use its own default.

		For ISAM4.0.10 - stays the same as latest FGU4.x   "
	::= { gponPotsMltTestEntry 5 }

gponPotsMltTestForeignDCThreshold  OBJECT-TYPE
	SYNTAX 	INTEGER (0..10)
	ACCESS	read-write
	STATUS	mandatory
	DESCRIPTION 
		" Indicates the threshold for declaring DC foreign voltage
		  pass/fail.  Units are Volts.
		  Range is 0 - 10 (the value 0 means that
		  ONT should use its own default threshold).

		  Default = 0 - meaning ONT should use its own default. 

		For ISAM4.0.10 - stays the same as latest FGU4.x  "
	::= { gponPotsMltTestEntry 6 }


gponPotsMltTestForeignACThreshold  OBJECT-TYPE
	SYNTAX 	INTEGER (0 | 10..50)
	ACCESS	read-write
	STATUS	mandatory
	DESCRIPTION 
		" Indicates the threshold for declaring AC foreign voltage
		  pass/fail.  Units are Volts RMS.
		  Range is 10 - 50 (and includes the value 0, which means that
		  ONT should use its own default threshold).

		  Default = 0 - meaning ONT should use its own default. 

		For ISAM4.0.10 - stays the same as latest FGU4.x  "
	::= { gponPotsMltTestEntry 7 }

gponPotsMltTestTipGndRingGndThreshold  OBJECT-TYPE
	SYNTAX 	INTEGER (0..250)
	ACCESS	read-write
	STATUS	mandatory
	DESCRIPTION 
		" Indicates the threshold for declaring tip-ground ro ring-ground
		  resistance pass/fail.  Units are kilo-ohms.
		  Range is 0 - 250 ( the value 0 means that
		  ONT should use its own default threshold).

		  Default = 0 - meaning ONT should use its own default.

		For ISAM4.0.10 - stays the same as latest FGU4.x   "
	::= { gponPotsMltTestEntry 8 }

gponPotsMltTestTipRingThreshold  OBJECT-TYPE
	SYNTAX 	INTEGER (0..250)
	ACCESS	read-write
	STATUS	mandatory
	DESCRIPTION 
		" Indicates the threshold for declaring tip-ring
		  resistance pass/fail.  Units are kilo-ohms.
		  Range is 0 - 250 ( the value 0 means that
		  ONT should use its own default threshold).

		  Default = 0 - meaning ONT should use its own default.

		For ISAM4.0.10 - stays the same as latest FGU4.x   "
	::= { gponPotsMltTestEntry 9 }

gponPotsMltTestRingEquivMinThreshold  OBJECT-TYPE
	SYNTAX 	INTEGER (0..700)
	ACCESS	read-write
	STATUS	mandatory
	DESCRIPTION 
		" Indicates the minimum threshold for declaring the 
		  ringer load test pass/fail.  Units are 0.01 RENs. 
		  Range is 0 - 700 ( the value 0 means that
		  ONT should use its own default threshold).

		  Default = 0 - meaning ONT should use its own default.

		For ISAM4.0.10 - stays the same as latest FGU4.x   "
	::= { gponPotsMltTestEntry 10 }

gponPotsMltTestRingEquivMaxThreshold  OBJECT-TYPE
	SYNTAX 	INTEGER (0..700)
	ACCESS	read-write
	STATUS	mandatory
	DESCRIPTION 
		" Indicates the maximum threshold for declaring the 
		  ringer load test pass/fail.  Units are 0.01 RENs. 
		  Range is 0 - 700 ( the value 0 means that
		  ONT should use its own default threshold).

		  Default = 0 - meaning ONT should use its own default.

		For ISAM4.0.10 - stays the same as latest FGU4.x   "
	::= { gponPotsMltTestEntry 11 }


gponPotsMltTestCmd  OBJECT-TYPE
	SYNTAX 	INTEGER 
	ACCESS	read-write
	STATUS	mandatory
	DESCRIPTION 
		"Manager is only permitted to SET this attribute
		 to (1), indicating desire to execute POTS port MLT test.
		 Thereafter, manager issues SNMP GET to determine
		 status/result of the MLT test. Agent changes
		 attribute value accordingly as follows:
		 0 - This is the initial default value, meaning an MLT test
		          has never been executed on this port since initialization.
		 1 - Only value settable by manager (to initiate test)  
		 2 - meaning MLT test is in progress,
		 3 - meaning MLT test failed because ONT failed
		       to respond within reasonable time,
		 4 - meaning MLT test has completed execution.
		 5 - meaning OLT didn't issue the MLT command.

		Manager must read results in 
  		gponPotsMltTestSummaryResult attribute to discern
   		the summary specifics of the actual MLT test results.

		Default = 0

		For ISAM4.0.10 - stays the same as latest FGU4.x 
		For ISAM4.2.02 - stays the same as latest ISAM (including for legacy and standard VoIP modes).
		For ISAM4.3, continues to be SUPPORTED as latest ISAM (including for Veip-style VoIP).   "
	::= { gponPotsMltTestEntry 12 }

gponPotsMltTestSummaryResult  OBJECT-TYPE
	SYNTAX 	OCTET STRING (SIZE(1))
	ACCESS	read-only
	STATUS	mandatory
	DESCRIPTION 
		"Indicates the MLT Test Result for a 
		 specific POTS port.  Represented as a
		 bitmap as follows (where Bit 1 is the 
		 least significant bit). 
		 Bit 1     = Don't care. N/A for POTS.
		 Bit 2 - 0 = ringer failed
			 - 1 = ringer passed
		 Bit 3 - 0 = receiver off-hook failed
			 - 1 = receiver off-hook passed
		 Bit 4 - 0 = resistive faults failed
			 - 1 = resistive faults passed
		 Bit 5 - 0 = foreign EMF failed
			 - 1 = foreign EMF passed
		 Bit 6 - 0 = hazardous potential failed
			 - 1 = hazardous potential passed
		 Bit 7     = Always 0
		 Bit 8     = Always 0 

		For ISAM4.0.10 - stays the same as latest FGU4.x "
	::= { gponPotsMltTestEntry 13 }

gponPotsMltTestDcTipGroundResult  OBJECT-TYPE
	SYNTAX 	INTEGER
	ACCESS	read-only
	STATUS	mandatory
	DESCRIPTION 
		"Indicates the summary result of 
		 Tip-Ground DC Voltage test.
		 Coding is as follows:

		 0 = Test Not Run
		 1 = Test Failed (measurement reported)
		 2 = Test Failed (no measurement reported)
		 3 = Test Passed (measurement reported)
		 4 = Test Passed (no measurement reported)

		 For cases where the measurement is reported, the 
		 actual value is contained in 
		 gponPotsMltTestDcTipGroundMeasure attribute.

		For ISAM4.0.10 - stays the same as latest FGU4.x  "
	::= { gponPotsMltTestEntry 14 }

gponPotsMltTestDcRingGroundResult  OBJECT-TYPE
	SYNTAX 	INTEGER
	ACCESS	read-only
	STATUS	mandatory
	DESCRIPTION 
		"Indicates the summary result of 
		 Ring-Ground DC Voltage test.
		 Coding is as follows:

		 0 = Test Not Run
		 1 = Test Failed (measurement reported)
		 2 = Test Failed (no measurement reported)
		 3 = Test Passed (measurement reported)
		 4 = Test Passed (no measurement reported)

		 For cases where the measurement is reported, the 
		 actual value is contained in 
		 gponPotsMltTestDcRingGroundMeasure attribute.

		For ISAM4.0.10 - stays the same as latest FGU4.x  "
	::= { gponPotsMltTestEntry 15 }

gponPotsMltTestAcTipGroundResult  OBJECT-TYPE
	SYNTAX 	INTEGER
	ACCESS	read-only
	STATUS	mandatory
	DESCRIPTION 
		"Indicates the summary result of 
		 Tip-Ground AC Voltage test.
		 Coding is as follows:

		 0 = Test Not Run
		 1 = Test Failed (measurement reported)
		 2 = Test Failed (no measurement reported)
		 3 = Test Passed (measurement reported)
		 4 = Test Passed (no measurement reported)

		 For cases where the measurement is reported, the 
		 actual value is contained in 
		 gponPotsMltTestAcTipGroundMeasure attribute.

		For ISAM4.0.10 - stays the same as latest FGU4.x  "
	::= { gponPotsMltTestEntry 16 }

gponPotsMltTestAcRingGroundResult  OBJECT-TYPE
	SYNTAX 	INTEGER
	ACCESS	read-only
	STATUS	mandatory
	DESCRIPTION 
		"Indicates the summary result of 
		 Ring-Ground AC Voltage test.
		 Coding is as follows:

		 0 = Test Not Run
		 1 = Test Failed (measurement reported)
		 2 = Test Failed (no measurement reported)
		 3 = Test Passed (measurement reported)
		 4 = Test Passed (no measurement reported)

		 For cases where the measurement is reported, the 
		 actual value is contained in 
		 gponPotsMltTestAcRingGroundMeasure attribute.

		For ISAM4.0.10 - stays the same as latest FGU4.x  "
	::= { gponPotsMltTestEntry 17 }

gponPotsMltTestTipGroundResistResult  OBJECT-TYPE
	SYNTAX 	INTEGER
	ACCESS	read-only
	STATUS	mandatory
	DESCRIPTION 
		"Indicates the summary result of 
		 Tip-Ground Resistance test.
		 Coding is as follows:

		 0 = Test Not Run
		 1 = Test Failed (measurement reported)
		 2 = Test Failed (no measurement reported)
		 3 = Test Passed (measurement reported)
		 4 = Test Passed (no measurement reported)

		 For cases where the measurement is reported, the 
		 actual value is contained in 
		 gponPotsMltTestTipGroundResistMeasure attribute.

		For ISAM4.0.10 - stays the same as latest FGU4.x  "
	::= { gponPotsMltTestEntry 18 }

gponPotsMltTestRingGroundResistResult  OBJECT-TYPE
	SYNTAX 	INTEGER
	ACCESS	read-only
	STATUS	mandatory
	DESCRIPTION 
		"Indicates the summary result of 
		 Ring-Ground Resistance test.
		 Coding is as follows:

		 0 = Test Not Run
		 1 = Test Failed (measurement reported)
		 2 = Test Failed (no measurement reported)
		 3 = Test Passed (measurement reported)
		 4 = Test Passed (no measurement reported)

		 For cases where the measurement is reported, the 
		 actual value is contained in 
		 gponPotsMltTestRingGroundResistMeasure attribute.

		For ISAM4.0.10 - stays the same as latest FGU4.x  "
	::= { gponPotsMltTestEntry 19 }

gponPotsMltTestTipRingResistResult  OBJECT-TYPE
	SYNTAX 	INTEGER
	ACCESS	read-only
	STATUS	mandatory
	DESCRIPTION 
		"Indicates the summary result of 
		 Tip-Ring Resistance test.
		 Coding is as follows:

		 0 = Test Not Run
		 1 = Test Failed (measurement reported)
		 2 = Test Failed (no measurement reported)
		 3 = Test Passed (measurement reported)
		 4 = Test Passed (no measurement reported)

		 For cases where the measurement is reported, the 
		 actual value is contained in 
		 gponPotsMltTestTipRingResistMeasure attribute.

		For ISAM4.0.10 - stays the same as latest FGU4.x  "
	::= { gponPotsMltTestEntry 20 }


gponPotsMltTestRingerLoadResult  OBJECT-TYPE
	SYNTAX 	INTEGER
	ACCESS	read-only
	STATUS	mandatory
	DESCRIPTION 
		"Indicates the summary result of 
		 Ringer Load test.
		 Coding is as follows:

		 0 = Test Not Run
		 1 = Test Failed (measurement reported)
		 2 = Test Failed (no measurement reported)
		 3 = Test Passed (measurement reported)
		 4 = Test Passed (no measurement reported)

		 For cases where the measurement is reported, the 
		 actual value is contained in 
		 gponPotsMltTestRingerLoadMeasure attribute. 

		For ISAM4.0.10 - stays the same as latest FGU4.x "
	::= { gponPotsMltTestEntry 21 }


gponPotsMltTestDcTipGroundMeasure  OBJECT-TYPE
	SYNTAX 	INTEGER
	ACCESS	read-only
	STATUS	mandatory
	DESCRIPTION 
		"Contains the measurement from the 
		 Tip-Ground DC Voltage test.

		 This attribute contains valid data only if 
		 gponPotsMltTestDcTipGroundResult attribute coding is:

		 1 = Test Failed (measurement reported)
		 3 = Test Passed (measurement reported)

		 Units are Volts  (resolution is 1 Volt)
		 Range is -32768 to +32768.
		 Default is 0.

		For ISAM4.0.10 - stays the same as latest FGU4.x   "
	::= { gponPotsMltTestEntry 22 }

gponPotsMltTestDcRingGroundMeasure  OBJECT-TYPE
	SYNTAX 	INTEGER
	ACCESS	read-only
	STATUS	mandatory
	DESCRIPTION 
		"Contains the measurement from the 
		 Ring-Ground DC Voltage test.

		 This attribute contains valid data only if 
		 gponPotsMltTestDcRingGroundResult attribute coding is:

		 1 = Test Failed (measurement reported)
		 3 = Test Passed (measurement reported)

		 Units are Volts  (resolution is 1 Volt)
		 Range is -32768 to +32768.
		 Default is 0. 

		For ISAM4.0.10 - stays the same as latest FGU4.x  "
	::= { gponPotsMltTestEntry 23 }

gponPotsMltTestAcTipGroundMeasure  OBJECT-TYPE
	SYNTAX 	INTEGER
	ACCESS	read-only
	STATUS	mandatory
	DESCRIPTION 
		"Contains the measurement from the 
		 Tip-Ground AC Voltage test.

		 This attribute contains valid data only if 
		 gponPotsMltTestAcTipGroundResult attribute coding is:

		 1 = Test Failed (measurement reported)
		 3 = Test Passed (measurement reported)

		 Units are Volts RMS  (resolution is 1 Volt)
		 Range is 0 to +255.
		 Default is 0.

		For ISAM4.0.10 - stays the same as latest FGU4.x   "
	::= { gponPotsMltTestEntry 24 }

gponPotsMltTestAcRingGroundMeasure  OBJECT-TYPE
	SYNTAX 	INTEGER
	ACCESS	read-only
	STATUS	mandatory
	DESCRIPTION 
		"Contains the measurement from the 
		 Ring-Ground AC Voltage test.

		 This attribute contains valid data only if 
		 gponPotsMltTestAcRingGroundResult attribute coding is:

		 1 = Test Failed (measurement reported)
		 3 = Test Passed (measurement reported)

		 Units are Volts RMS (resolution is 1 Volt)
		 Range is 0 to +255.
		 Default is 0. 

		For ISAM4.0.10 - stays the same as latest FGU4.x  "
	::= { gponPotsMltTestEntry 25 }

gponPotsMltTestTipGroundResistMeasure  OBJECT-TYPE
	SYNTAX 	INTEGER
	ACCESS	read-only
	STATUS	mandatory
	DESCRIPTION 
		"Contains the measurement from the 
		 Tip-Ground DC Resistance test.

		 This attribute contains valid data only if 
		 gponPotsMltTestTipGroundResistResult attribute coding is:

		 1 = Test Failed (measurement reported)
		 3 = Test Passed (measurement reported)

		 Units are Ohms  (resolution is 1 kOhm)
		 Range is 0 to +65535.  +65535 represents infinite resistance.
		 Default is 0. 

		For ISAM4.0.10 - stays the same as latest FGU4.x  "
	::= { gponPotsMltTestEntry 26 }

gponPotsMltTestRingGroundResistMeasure  OBJECT-TYPE
	SYNTAX 	INTEGER
	ACCESS	read-only
	STATUS	mandatory
	DESCRIPTION 
		"Contains the measurement from the 
		 Ring-Ground DC Resistance test.

		 This attribute contains valid data only if 
		 gponPotsMltTestRingGroundResistResult attribute coding is:

		 1 = Test Failed (measurement reported)
		 3 = Test Passed (measurement reported)

		 Units are Ohms  (resolution is 1 kOhm)
		 Range is 0 to +65535.  +65535 represents infinite resistance.
		 Default is 0. 

		For ISAM4.0.10 - stays the same as latest FGU4.x  "
	::= { gponPotsMltTestEntry 27 }

gponPotsMltTestTipRingResistMeasure  OBJECT-TYPE
	SYNTAX 	INTEGER
	ACCESS	read-only
	STATUS	mandatory
	DESCRIPTION 
		"Contains the measurement from the 
		 Tip-Ring DC Resistance test.

		 This attribute contains valid data only if 
		 gponPotsMltTestTipRingResistResult attribute coding is:

		 1 = Test Failed (measurement reported)
		 3 = Test Passed (measurement reported)

		 Units are Ohms  (resolution is 1 kOhm)
		 Range is 0 to +65535.  +65535 represents infinite resistance.
		 Default is 0. 

		For ISAM4.0.10 - stays the same as latest FGU4.x  "
	::= { gponPotsMltTestEntry 28 }

gponPotsMltTestRingerLoadMeasure  OBJECT-TYPE
	SYNTAX 	INTEGER
	ACCESS	read-only
	STATUS	mandatory
	DESCRIPTION 
		"Contains the measurement from the 
		 Ringer Load test.

		 This attribute contains valid data only if 
		 gponPotsMltTestRingerLoadResult attribute coding is:

		 1 = Test Failed (measurement reported)
		 3 = Test Passed (measurement reported)

		 Units are RENs  (resolution is 0.1 REN)
		 Range is 0 to +255.  
		 Default is 0.  

		For ISAM4.0.10 - stays the same as latest FGU4.x "
	::= { gponPotsMltTestEntry 29 }

-- *********************************************
--
-- GPON POTS PORT OPSTAT TABLE
--
-- This is a new table beginning with ISAM4.3.
--
-- This table contains various physical status for each provisioned POTS port on a
-- specific ONT. 
--
-- From an OMCI standpoint, it maps primarily to the PPTP POTS UNI ME.
--
-- Each time status is requested, the OLT directly retrieves   
-- the latest information (via OMCI) for the relevant POTS port.
--
-- Rows are created/deleted automatically by the 
-- OLT agent in a one-to-one association with creation/deletion of 
-- POTS ports - regardless of the VoIP provisioning style..
--
--	For GPON - SUPPORTED as of ISAM4.3
--	For XG-PON1 - SUPPORTED as of ISAM4.6.02
--  For NG-PON2 - SUPPORTED as of ISAM5.4.01
--
-- *********************************************

gponPotsPortOpstatTable  OBJECT-TYPE
	SYNTAX SEQUENCE OF GponPotsPortOpstatEntry
	ACCESS	not-accessible
	STATUS	mandatory
	::= { bponPotsGroup 8 }


gponPotsPortOpstatEntry  OBJECT-TYPE
	SYNTAX 	GponPotsPortOpstatEntry
	ACCESS	not-accessible
	STATUS	mandatory
	INDEX	{ gponPotsPortOpstatOntIndex,
		   gponPotsPortOpstatSpIndex }
	::= { gponPotsPortOpstatTable 1 }

GponPotsPortOpstatEntry ::= SEQUENCE {
	gponPotsPortOpstatOntIndex		IfIndex,
	gponPotsPortOpstatSpIndex		SpIndex,
	gponPotsPortOpstatHookState		INTEGER
}


gponPotsPortOpstatOntIndex  OBJECT-TYPE
	SYNTAX 	IfIndex
	ACCESS	read-only
	STATUS	mandatory
	DESCRIPTION 
		"Each row is indexed by the ifIndex of the ONT   "
	::= { gponPotsPortOpstatEntry 1 }


gponPotsPortOpstatSpIndex  OBJECT-TYPE
	SYNTAX 	SpIndex
	ACCESS	read-only
	STATUS	mandatory
	DESCRIPTION 
		"Each row is also indexed by a number that
		 contains the slot number and port number
		 within the ONT.  "
	::= { gponPotsPortOpstatEntry 2 }


gponPotsPortOpstatHookState  OBJECT-TYPE
	SYNTAX 	INTEGER
	ACCESS	read-only
	STATUS	mandatory
	DESCRIPTION 
		" Indicates the current state of the subscriber line:

		 0 = means on-hook
		 1 = means off-hook

		 256 -  means UNKNOWN (because OLT cannot communicate with ONT for OMCI discovery purposes).
		 257 -  means that ONT does NOT support GET of this attribute.

		 Default = 256 = UNKNOWN	 "
	::= { gponPotsPortOpstatEntry 3 }


-- *********************************************
--
-- GPON POTS VOIP OPSTAT TABLE
--
-- This is a new table beginning with ISAM4.2.
-- It is only SUPPORTED beginning with ISAM4.2.02 release, when 
-- VoIP provisioning style is standard (not legacy)
--
-- This table contains VoIP line status for each provisioned POTS port on a
-- specific ONT. 
--
-- From an OMCI standpoint, it maps primarily to the VoIP Line Status ME.
--
-- Each time status is requested, the OLT directly retrieves   
-- the latest information (via OMCI) for the relevant POTS port.
--
-- Rows are created/deleted automatically by the 
-- OLT agent in a one-to-one association with creation/deletion of 
-- POTS ports - but only if VoIP provisioning style is standard (not legacy).
--
-- As of targeted release ISAM4.5.02, this table must also be SUPPORTED for Veip-style Voip.
-- 	(i.e. auto creation/deletion of rows in concert with creation/deletion of associated POTS ports).
--
-- As of targeted release ISAM5.1, this table must also be SUPPORTED for legacy Voip.
-- 	(i.e. auto creation/deletion of rows in concert with creation/deletion of associated POTS ports).
--
--	For GPON - SUPPORTED as of ISAM4.2
--	For XG-PON1 - SUPPORTED as of ISAM4.6.02
--  For NG-PON2 - SUPPORTED as of ISAM5.4.01
--
-- *********************************************

gponPotsVoipOpstatTable  OBJECT-TYPE
	SYNTAX SEQUENCE OF GponPotsVoipOpstatEntry
	ACCESS	not-accessible
	STATUS	mandatory
	::= { bponPotsGroup 10 }


gponPotsVoipOpstatEntry  OBJECT-TYPE
	SYNTAX 	GponPotsVoipOpstatEntry
	ACCESS	not-accessible
	STATUS	mandatory
	INDEX	{ gponPotsVoipOpstatOntIndex,
		   gponPotsVoipOpstatSpIndex }
	::= { gponPotsVoipOpstatTable 1 }

GponPotsVoipOpstatEntry ::= SEQUENCE {
	gponPotsVoipOpstatOntIndex		IfIndex,
	gponPotsVoipOpstatSpIndex		SpIndex,
	gponPotsVoipOpstatCodecUsed		INTEGER,
	gponPotsVoipOpstatVoiceServerStatus	INTEGER,
	gponPotsVoipOpstatPortSessionType		INTEGER,
	gponPotsVoipOpstatCall1PacketPeriod	INTEGER,
	gponPotsVoipOpstatCall2PacketPeriod	INTEGER,
	gponPotsVoipOpstatCall1DestAddress	DisplayString,
	gponPotsVoipOpstatCall2DestAddress	DisplayString,
	gponPotsVoipOpstatVoiceLineStatus	INTEGER
}


gponPotsVoipOpstatOntIndex  OBJECT-TYPE
	SYNTAX 	IfIndex
	ACCESS	read-only
	STATUS	mandatory
	DESCRIPTION 
		"Each row is indexed by the ifIndex of the ONT   "
	::= { gponPotsVoipOpstatEntry 1 }


gponPotsVoipOpstatSpIndex  OBJECT-TYPE
	SYNTAX 	SpIndex
	ACCESS	read-only
	STATUS	mandatory
	DESCRIPTION 
		"Each row is also indexed by a number that
		 contains the slot number and port number
		 within the ONT.  "
	::= { gponPotsVoipOpstatEntry 2 }


gponPotsVoipOpstatCodecUsed  OBJECT-TYPE
	SYNTAX 	INTEGER
	ACCESS	read-only
	STATUS	mandatory
	DESCRIPTION 
		" Indicates the current codec used for the VoIP POTS port, per IETF RFC 3551:

		Value		Name		Clock Rate (Hz)	
		0 		PCMU		8000		
		1		reserved				
		2		reserved				
		3		GSM		8000		
		4		G723		8000		
		5		DVI4		8000		
		6		DVI4		16000		
		7		LPC		8000		
		8		PCMA		8000		
		9		G722		8000		
		10		L16, 2 channels	41000		
		11		L16, 1 channel	41000		
		12		QCELP		8000		
		13		CN		8000		
		14		MPA		90000		
		15		G728		8000		
		16		DVI4		11025		
		17		DVI4		22050		
		18		G729		8000

		 256 -  means UNKNOWN (because OLT cannot communicate with ONT for OMCI discovery purposes).
		 257 -  means that ONT does NOT support GET of this attribute.

		 Default = 256 = UNKNOWN	 "
	::= { gponPotsVoipOpstatEntry 3 }

gponPotsVoipOpstatVoiceServerStatus  OBJECT-TYPE
	SYNTAX 	INTEGER
	ACCESS	read-only
	STATUS	mandatory
	DESCRIPTION 
		" Indicates the status of the VoIP session for this POTS port:

		0 - None/Initial		
		1 - Registered				
		2 - In session				
		3 - Failed Registration - ICMP Error
		4 - Failed Registration - Failed TCP	
		5 - Failed Registration - Failed Authentication	
		6 - Failed Registration - Timeout
		7 - Failed Registration - Server Fail Code
		8 - Failed Invite - ICMP Error
		9 - Failed Invite - Failed TCP	
		10 - Failed Invite - Failed Authentication	
		11 - Failed Invite - Timeout
		12 - Failed Invite - Server Fail Code	
		13 - Port Not Configured
		14 - Configuration Done
		15 - Disabled by Switch (SUPPORTED as of ISAM5.1.01)			

		 256 -  means UNKNOWN (because OLT cannot communicate with ONT for OMCI discovery purposes).
		 257 -  means that ONT does NOT support GET of this attribute.

		 Default = 256 = UNKNOWN	 "
	::= { gponPotsVoipOpstatEntry 4 }

gponPotsVoipOpstatPortSessionType  OBJECT-TYPE
	SYNTAX 	INTEGER
	ACCESS read-only
	STATUS	mandatory
	DESCRIPTION 
		" Indicates the current state of the VoIP POTS port session:

		0 - Idle/None		
		1 - 2way				
		2 - 3way				
		3 - Fax
		4 - Telemetry	
		5 - Conference	

		 256 -  means UNKNOWN (because OLT cannot communicate with ONT for OMCI discovery purposes).
		 257 -  means that ONT does NOT support GET of this attribute.

		 Default = 256 = UNKNOWN	 "
	::= { gponPotsVoipOpstatEntry 5 }

gponPotsVoipOpstatCall1PacketPeriod  OBJECT-TYPE
	SYNTAX 	INTEGER
	ACCESS read-only
	STATUS	mandatory
	DESCRIPTION 
		" Indicates the packet period for the first call on the VoIP POTS port:

		Range is 0 - 65535 (in milliseconds), along with the following special values:		

		 65536 -  means UNKNOWN (because OLT cannot communicate with ONT for OMCI discovery purposes).
		 65537 -  means that ONT does NOT support GET of this attribute.

		 Default = 65536 = UNKNOWN	 "
	::= { gponPotsVoipOpstatEntry 6 }

gponPotsVoipOpstatCall2PacketPeriod  OBJECT-TYPE
	SYNTAX 	INTEGER
	ACCESS	read-only
	STATUS	mandatory
	DESCRIPTION 
		" Indicates the packet period for the second call on the VoIP POTS port:

		Range is 0 - 65535 (in milliseconds), along with the following special values:		

		 65536 -  means UNKNOWN (because OLT cannot communicate with ONT for OMCI discovery purposes).
		 65537 -  means that ONT does NOT support GET of this attribute.

		 Default = 65536 = UNKNOWN	 "
	::= { gponPotsVoipOpstatEntry 7 }

gponPotsVoipOpstatCall1DestAddress  OBJECT-TYPE
	SYNTAX 	DisplayString (SIZE(0..25))
	ACCESS	read-only
	STATUS	mandatory
	DESCRIPTION 
		" Indicates the destination address for the first call on the VoIP POTS port:

		This is an ASCII string - with the following values having the following special meanings:	

		 UNKNOWN -  means UNKNOWN (because OLT cannot communicate with ONT for OMCI discovery purposes).
		 UNSUPPORTED -  means that ONT does NOT support GET of this attribute.

		 Default = UNKNOWN	 "
	::= { gponPotsVoipOpstatEntry 8 }

gponPotsVoipOpstatCall2DestAddress  OBJECT-TYPE
	SYNTAX 	DisplayString (SIZE(0..25))
	ACCESS	read-only
	STATUS	mandatory
	DESCRIPTION 
		" Indicates the destination address for the second call on the VoIP POTS port:

		This is an ASCII string - with the following values having the following special meanings:	

		 UNKNOWN -  means UNKNOWN (because OLT cannot communicate with ONT for OMCI discovery purposes).
		 UNSUPPORTED -  means that ONT does NOT support GET of this attribute.

		 Default = UNKNOWN	 "
	::= { gponPotsVoipOpstatEntry 9 }


gponPotsVoipOpstatVoiceLineStatus  OBJECT-TYPE
    SYNTAX     INTEGER
    ACCESS    read-only
    STATUS    mandatory
    DESCRIPTION 
        " Indicates the status of the VoIP Line for this POTS port:

        0 Idle, on-hook
        1 Off-hook dial tone
        2 Dialling
        3 Ringing or FSK alerting/data
        4 Audible ringback
        5 Connecting
        6 Connected
        7 Disconnecting, audible indication
        8 Receiver off hook (ROH), no tone
        9 ROH with tone
        10 -  means UNKNOWN or undefined (as reported directly from ONT via OMCI)
 
        256 -  means UNKNOWN (because OLT cannot communicate with ONT for OMCI discovery purposes).
        257 -  means that ONT does NOT support GET of this attribute.
 
        Default = 256 = UNKNOWN


	SUPPORTED as of ISAM5.1.01           "
    ::= { gponPotsVoipOpstatEntry 10 }


-- *********************************************
--
-- GPON POTS CALL CONTROL PERFORMANCE MONITOR CURRENT INTERVAL TABLE
--
-- This is a new table beginning with ISAM4.2.
-- It is only SUPPORTED beginning with ISAM4.2.02 release, when 
-- VoIP provisioning style is standard (not legacy)
--
-- This current interval table contains various call control channel data collected
-- at an ONT's POTs interface during the current 15 minute interval 
-- of operation.  
--
-- An instance of this table is auto-created/deleted in accordance with the 
-- 'Call Control PM Collect Indicator' setting of the POTS UNI.
--
-- For GETs of table attributes, the OLT must go directly to the ONT (via OMCI)
-- in order to acquire fresh current counts. 
--
-- As of targeted release ISAM4.5.02, this table must also be SUPPORTED for Veip-style Voip.
--
--	For GPON - SUPPORTED as of ISAM4.2
--	For XG-PON1 - SUPPORTED as of ISAM4.6.02
--  For NG-PON2 - SUPPORTED as of ISAM5.4.01
--
-- 
-- *********************************************


gponPotsCallCntlCurrentIntervalTable  OBJECT-TYPE
	SYNTAX SEQUENCE OF GponPotsCallCntlCurrentIntervalEntry
	ACCESS	not-accessible
	STATUS	mandatory
	::= { bponPotsGroup 11 }


gponPotsCallCntlCurrentIntervalEntry  OBJECT-TYPE
	SYNTAX 	GponPotsCallCntlCurrentIntervalEntry
	ACCESS	not-accessible
	STATUS	mandatory
	DESCRIPTION 
		"An entry in the Gpon POTS Call Control CurrentInterval 
		 Table. "
	INDEX	{ gponPotsCallCntlCurrentIntervalOntIndex, 
		   gponPotsCallCntlCurrentIntervalSpIndex }
	::= { gponPotsCallCntlCurrentIntervalTable 1 }

GponPotsCallCntlCurrentIntervalEntry ::= SEQUENCE {
	gponPotsCallCntlCurrentIntervalOntIndex			IfIndex,
	gponPotsCallCntlCurrentIntervalSpIndex			SpIndex,
	gponPotsCallCntlCurrentIntervalValidInd			Boolean,
	gponPotsCallCntlCurrentIntervalSetupFails			Counter,
	gponPotsCallCntlCurrentIntervalSetupTimer			Counter,
	gponPotsCallCntlCurrentIntervalTerminateFails			Counter,
	gponPotsCallCntlCurrentIntervalPortReleases			Counter,
	gponPotsCallCntlCurrentIntervalPortOffhookTimer		Counter

}


gponPotsCallCntlCurrentIntervalOntIndex  OBJECT-TYPE
	SYNTAX 	IfIndex
	ACCESS	read-only
	STATUS	mandatory
	DESCRIPTION 
		"Each row is indexed by the ifIndex of the ONT.  "
	::= { gponPotsCallCntlCurrentIntervalEntry 1 }

gponPotsCallCntlCurrentIntervalSpIndex  OBJECT-TYPE
	SYNTAX 	SpIndex
	ACCESS	read-only
	STATUS	mandatory
	DESCRIPTION 
		"Each row is also indexed by a number that
		 contains the slot number and port number
 		 within the ONT.  "
	::= { gponPotsCallCntlCurrentIntervalEntry 2 }


gponPotsCallCntlCurrentIntervalValidInd  OBJECT-TYPE
	SYNTAX 	Boolean
	ACCESS	read-only
	STATUS	mandatory
	DESCRIPTION 
		"Indicates whether or not this CurrentInterval contains
		 valid PM counts. 

		 NOT SUPPORTED "
	::= { gponPotsCallCntlCurrentIntervalEntry 3 }


gponPotsCallCntlCurrentIntervalSetupFails  OBJECT-TYPE
	SYNTAX 	Counter
	ACCESS	read-only
	STATUS	mandatory
	DESCRIPTION 
		"A count of Call Setup Failures. "
	::= { gponPotsCallCntlCurrentIntervalEntry 4 }

gponPotsCallCntlCurrentIntervalSetupTimer  OBJECT-TYPE
	SYNTAX 	Counter
	ACCESS	read-only
	STATUS	mandatory
	DESCRIPTION 
		" Represents a high water mark that records the longest duration of a single
		  call setup detected during this interval.  Time is measured in milliseconds from the
		  time an initial setup was requested by the subscriber until the time at which a response
		  was provided to the subscriber in the form of a busy tone, audible ring tone, etc.  "
	::= { gponPotsCallCntlCurrentIntervalEntry 5 }

gponPotsCallCntlCurrentIntervalTerminateFails  OBJECT-TYPE
	SYNTAX 	Counter
	ACCESS	read-only
	STATUS	mandatory
	DESCRIPTION 
		"A count of Call Terminate Failures. "
	::= { gponPotsCallCntlCurrentIntervalEntry 6 }

gponPotsCallCntlCurrentIntervalPortReleases  OBJECT-TYPE
	SYNTAX 	Counter
	ACCESS	read-only
	STATUS	mandatory
	DESCRIPTION 
		"A count of the analog port releases without dialing detected (abandoned calls). "
	::= { gponPotsCallCntlCurrentIntervalEntry 7 }

gponPotsCallCntlCurrentIntervalPortOffhookTimer  OBJECT-TYPE
	SYNTAX 	Counter
	ACCESS	read-only
	STATUS	mandatory
	DESCRIPTION 
		" Represents a high water mark that records the longest period of a single
		  off-hook detected on the analog port during this interval.  Time is measured in milliseconds.   "
	::= { gponPotsCallCntlCurrentIntervalEntry 8 }


-- *********************************************
--
-- GPON  POTS CALL CONTROL PERFORMANCE MONITOR INTERVAL TABLE
--
-- This is a new table beginning with ISAM4.2.
-- It is NOT SUPPORTED as of  ISAM4.2.02 release.
-- Only relevant when VoIP provisioning style is standard (not legacy).
--
--
-- This interval table contains various call control channel data collected
-- at an ONT's POTs interface over the previous 8 hours 
-- of operation.  The past 8 hours are broken into 32  
-- completed 15 minute intervals.  Each row in this table
-- represents one such interval for a specific POTS port
-- on a specific ONT.
--
-- An instance of this table is auto-created/deleted in accordance with the 
-- 'Call Control PM Collect Indicator' setting of the POTS UNI.
--
-- As of targeted release ISAM4.5.02, this table must be SUPPORTED for Veip-style Voip.
--
--	For GPON - SUPPORTED as of ISAM4.2
--	For XG-PON1 - SUPPORTED as of ISAM4.6.02
--  For NG-PON2 - SUPPORTED as of ISAM5.4.01
--
-- 
-- *********************************************


gponPotsCallCntlIntervalTable  OBJECT-TYPE
	SYNTAX SEQUENCE OF GponPotsCallCntlIntervalEntry
	ACCESS	not-accessible
	STATUS	mandatory
	::= { bponPotsGroup 12 }


gponPotsCallCntlIntervalEntry  OBJECT-TYPE
	SYNTAX 	GponPotsCallCntlIntervalEntry
	ACCESS	not-accessible
	STATUS	mandatory
	DESCRIPTION 
		"An entry in the gponPotsCallCntlIntervalTable  "
	INDEX	{ gponPotsCallCntlIntervalOntIndex, 
		   gponPotsCallCntlIntervalSpIndex,
		  gponPotsCallCntlIntervalNumber }
	::= { gponPotsCallCntlIntervalTable 1 }

GponPotsCallCntlIntervalEntry ::= SEQUENCE {
	gponPotsCallCntlIntervalOntIndex			IfIndex,
	gponPotsCallCntlIntervalSpIndex			SpIndex,
	gponPotsCallCntlIntervalNumber			INTEGER,
	gponPotsCallCntlIntervalValidInd			Boolean,
	gponPotsCallCntlIntervalSetupFails			Counter,
	gponPotsCallCntlIntervalSetupTimer			Counter,
	gponPotsCallCntlIntervalTerminateFails			Counter,
	gponPotsCallCntlIntervalPortReleases			Counter,
	gponPotsCallCntlIntervalPortOffhookTimer		Counter

}


gponPotsCallCntlIntervalOntIndex  OBJECT-TYPE
	SYNTAX 	IfIndex
	ACCESS	read-only
	STATUS	mandatory
	DESCRIPTION 
		"Each row is indexed by the ifIndex of the ONT.  "
	::= { gponPotsCallCntlIntervalEntry 1 }

gponPotsCallCntlIntervalSpIndex  OBJECT-TYPE
	SYNTAX 	SpIndex
	ACCESS	read-only
	STATUS	mandatory
	DESCRIPTION 
		"Each row is also indexed by a number that
		 contains the slot number and port number
 		 within the ONT. "
	::= { gponPotsCallCntlIntervalEntry 2 }

gponPotsCallCntlIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.  "
	::= { gponPotsCallCntlIntervalEntry 3 }

gponPotsCallCntlIntervalValidInd  OBJECT-TYPE
	SYNTAX 	Boolean
	ACCESS	read-only
	STATUS	mandatory
	DESCRIPTION 
		"Indicates whether or not this interval contains
		 valid PM counts. 

	`	NOT SUPPORTED "
	::= { gponPotsCallCntlIntervalEntry 4 }

gponPotsCallCntlIntervalSetupFails  OBJECT-TYPE
	SYNTAX 	Counter
	ACCESS	read-only
	STATUS	mandatory
	DESCRIPTION 
		"A count of Call Setup Failures. "
	::= { gponPotsCallCntlIntervalEntry 5 }

gponPotsCallCntlIntervalSetupTimer  OBJECT-TYPE
	SYNTAX 	Counter
	ACCESS	read-only
	STATUS	mandatory
	DESCRIPTION 
		" Represents a high water mark that records the longest duration of a single
		  call setup detected during this interval.  Time is measured in milliseconds from the
		  time an initial setup was requested by the subscriber until the time at which a response
		  was provided to the subscriber in the form of a busy tone, audible ring tone, etc.  "
	::= { gponPotsCallCntlIntervalEntry 6 }

gponPotsCallCntlIntervalTerminateFails  OBJECT-TYPE
	SYNTAX 	Counter
	ACCESS	read-only
	STATUS	mandatory
	DESCRIPTION 
		"A count of Call Terminate Failures. "
	::= { gponPotsCallCntlIntervalEntry 7 }

gponPotsCallCntlIntervalPortReleases  OBJECT-TYPE
	SYNTAX 	Counter
	ACCESS	read-only
	STATUS	mandatory
	DESCRIPTION 
		"A count of the analog port releases without dialing detected (abandoned calls). "
	::= { gponPotsCallCntlIntervalEntry 8 }

gponPotsCallCntlIntervalPortOffhookTimer  OBJECT-TYPE
	SYNTAX 	Counter
	ACCESS	read-only
	STATUS	mandatory
	DESCRIPTION 
		" Represents a high water mark that records the longest period of a single
		  off-hook detected on the analog port during this interval.  Time is measured in milliseconds.   "
	::= { gponPotsCallCntlIntervalEntry 9 }


-- *********************************************
--
-- GPON POTS RTP PERFORMANCE MONITOR CURRENT INTERVAL TABLE
--
-- This is a new table beginning with ISAM4.2.
-- It is only SUPPORTED beginning with ISAM4.2.02 release, when 
-- VoIP provisioning style is standard (not legacy)
--
-- This current interval table contains various RTP session data collected
-- at an ONT's POTs interface during the current 15 minute interval 
-- of operation.  
--
-- An instance of this table is auto-created/deleted in accordance with the 
-- 'RTP PM Collect Indicator' setting of the POTS UNI.
--
-- For GETs of table attributes, the OLT must go directly to the ONT (via OMCI)
-- in order to acquire fresh current counts. 
--
-- As of targeted release ISAM4.5.02, this table must also be SUPPORTED for Veip-style Voip.
--
--	For GPON - SUPPORTED as of ISAM4.2
--	For XG-PON1 - SUPPORTED as of ISAM4.6.02
--  For NG-PON2 - SUPPORTED as of ISAM5.4.01
-- 
-- *********************************************


gponPotsRtpCurrentIntervalTable  OBJECT-TYPE
	SYNTAX SEQUENCE OF GponPotsRtpCurrentIntervalEntry
	ACCESS	not-accessible
	STATUS	mandatory
	::= { bponPotsGroup 13 }


gponPotsRtpCurrentIntervalEntry  OBJECT-TYPE
	SYNTAX 	GponPotsRtpCurrentIntervalEntry
	ACCESS	not-accessible
	STATUS	mandatory
	DESCRIPTION 
		"An entry in the gponPotsRtpCurrentIntervalTable  "
	INDEX	{ gponPotsRtpCurrentIntervalOntIndex, 
		   gponPotsRtpCurrentIntervalSpIndex }
	::= { gponPotsRtpCurrentIntervalTable 1 }

GponPotsRtpCurrentIntervalEntry ::= SEQUENCE {
	gponPotsRtpCurrentIntervalOntIndex			IfIndex,
	gponPotsRtpCurrentIntervalSpIndex			SpIndex,
	gponPotsRtpCurrentIntervalValidInd			Boolean,
	gponPotsRtpCurrentIntervalRtpErrors			Counter,
	gponPotsRtpCurrentIntervalPacketLoss		Counter,
	gponPotsRtpCurrentIntervalMaxJitter			Counter,
	gponPotsRtpCurrentIntervalMaxRtcpInterval		Counter,
	gponPotsRtpCurrentIntervalBufferUnderflows			Counter,
	gponPotsRtpCurrentIntervalBufferOverflows		Counter

}


gponPotsRtpCurrentIntervalOntIndex  OBJECT-TYPE
	SYNTAX 	IfIndex
	ACCESS	read-only
	STATUS	mandatory
	DESCRIPTION 
		"Each row is indexed by the ifIndex of the ONT.  "
	::= { gponPotsRtpCurrentIntervalEntry 1 }

gponPotsRtpCurrentIntervalSpIndex  OBJECT-TYPE
	SYNTAX 	SpIndex
	ACCESS	read-only
	STATUS	mandatory
	DESCRIPTION 
		"Each row is also indexed by a number that
		 contains the slot number and port number
 		 within the ONT.  "
	::= { gponPotsRtpCurrentIntervalEntry 2 }


gponPotsRtpCurrentIntervalValidInd  OBJECT-TYPE
	SYNTAX 	Boolean
	ACCESS	read-only
	STATUS	mandatory
	DESCRIPTION 
		"Indicates whether or not this CurrentInterval contains
		 valid PM counts. 

		 NOT SUPPORTED "
	::= { gponPotsRtpCurrentIntervalEntry 3 }


gponPotsRtpCurrentIntervalRtpErrors  OBJECT-TYPE
	SYNTAX 	Counter
	ACCESS	read-only
	STATUS	mandatory
	DESCRIPTION 
		"A count of RTP Packet Errors. "
	::= { gponPotsRtpCurrentIntervalEntry 4 }

gponPotsRtpCurrentIntervalPacketLoss  OBJECT-TYPE
	SYNTAX 	Counter
	ACCESS	read-only
	STATUS	mandatory
	DESCRIPTION 
		" Represents the fraction of packets lost.  The attribute is calculated at the end of the 15-minute,
		  and is undefined for a current interval request.  The value 0 indicates no packet loss scaling linearly
		  to 0xFFFF FFFF to indicate 100 percent packet loss.

		 SUPPORTED as of ISAM4.5.02, since some ONTs may actually calculate the loss fraction on a current interval
		  basis "
	::= { gponPotsRtpCurrentIntervalEntry 5 }

gponPotsRtpCurrentIntervalMaxJitter  OBJECT-TYPE
	SYNTAX 	Counter
	ACCESS	read-only
	STATUS	mandatory
	DESCRIPTION 
		" This is a high water mark that represents the maximum jitter identified during the measured interval,
		  expressed in RTP timestamp units. "
	::= { gponPotsRtpCurrentIntervalEntry 6 }

gponPotsRtpCurrentIntervalMaxRtcpInterval  OBJECT-TYPE
	SYNTAX 	Counter
	ACCESS	read-only
	STATUS	mandatory
	DESCRIPTION 
		" This is a high water mark that represents the maximum time between RTCP packets during the
		  measured interval, in milliseconds. "
	::= { gponPotsRtpCurrentIntervalEntry 7 }

gponPotsRtpCurrentIntervalBufferUnderflows  OBJECT-TYPE
	SYNTAX 	Counter
	ACCESS	read-only
	STATUS	mandatory
	DESCRIPTION 
		" Counts the number of times the reassembly buffer underflows.   "
	::= { gponPotsRtpCurrentIntervalEntry 8 }

gponPotsRtpCurrentIntervalBufferOverflows  OBJECT-TYPE
	SYNTAX 	Counter
	ACCESS	read-only
	STATUS	mandatory
	DESCRIPTION 
		" Counts the number of times the reassembly buffer overflows.   "
	::= { gponPotsRtpCurrentIntervalEntry 9 }

-- *********************************************
--
-- GPON  POTS RTP PERFORMANCE MONITOR INTERVAL TABLE
--
-- This is a new table beginning with ISAM4.2.
-- It is NOT SUPPORTED as of  ISAM4.2.02 release.
-- Only relevant when VoIP provisioning style is standard (not legacy).
--
-- This interval table contains various RTP session data collected
-- at an ONT's POTs interface over the previous 8 hours 
-- of operation.  The past 8 hours are broken into 32  
-- completed 15 minute intervals.  Each row in this table
-- represents one such interval for a specific POTS port
-- on a specific ONT.
--
-- An instance of this table is auto-created/deleted in accordance with the 
-- 'RTP PM Collect Indicator' setting of the POTS UNI.
--
-- As of targeted release ISAM4.5.02, this table must be SUPPORTED for Veip-style Voip.
-- 
--	For GPON - SUPPORTED as of ISAM4.2
--	For XG-PON1 - SUPPORTED as of ISAM4.6.02
--  For NG-PON2 - SUPPORTED as of ISAM5.4.01
--
-- *********************************************


gponPotsRtpIntervalTable  OBJECT-TYPE
	SYNTAX SEQUENCE OF GponPotsRtpIntervalEntry
	ACCESS	not-accessible
	STATUS	mandatory
	::= { bponPotsGroup 14 }


gponPotsRtpIntervalEntry  OBJECT-TYPE
	SYNTAX 	GponPotsRtpIntervalEntry
	ACCESS	not-accessible
	STATUS	mandatory
	DESCRIPTION 
		"An entry in the gponPotsRtpIntervalTable  "
	INDEX	{ gponPotsRtpIntervalOntIndex, 
		   gponPotsRtpIntervalSpIndex,
		  gponPotsRtpIntervalNumber }
	::= { gponPotsRtpIntervalTable 1 }

GponPotsRtpIntervalEntry ::= SEQUENCE {
	gponPotsRtpIntervalOntIndex			IfIndex,
	gponPotsRtpIntervalSpIndex			SpIndex,
	gponPotsRtpIntervalNumber			INTEGER,
	gponPotsRtpIntervalValidInd			Boolean,
	gponPotsRtpIntervalRtpErrors			Counter,
	gponPotsRtpIntervalPacketLoss		Counter,
	gponPotsRtpIntervalMaxJitter			Counter,
	gponPotsRtpIntervalMaxRtcpInterval		Counter,
	gponPotsRtpIntervalBufferUnderflows			Counter,
	gponPotsRtpIntervalBufferOverflows		Counter

}


gponPotsRtpIntervalOntIndex  OBJECT-TYPE
	SYNTAX 	IfIndex
	ACCESS	read-only
	STATUS	mandatory
	DESCRIPTION 
		"Each row is indexed by the ifIndex of the ONT.  "
	::= { gponPotsRtpIntervalEntry 1 }

gponPotsRtpIntervalSpIndex  OBJECT-TYPE
	SYNTAX 	SpIndex
	ACCESS	read-only
	STATUS	mandatory
	DESCRIPTION 
		"Each row is also indexed by a number that
		 contains the slot number and port number
 		 within the ONT. "
	::= { gponPotsRtpIntervalEntry 2 }

gponPotsRtpIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.  "
	::= { gponPotsRtpIntervalEntry 3 }

gponPotsRtpIntervalValidInd  OBJECT-TYPE
	SYNTAX 	Boolean
	ACCESS	read-only
	STATUS	mandatory
	DESCRIPTION 
		"Indicates whether or not this interval contains
		 valid PM counts. 

	`	NOT SUPPORTED "
	::= { gponPotsRtpIntervalEntry 4 }

gponPotsRtpIntervalRtpErrors  OBJECT-TYPE
	SYNTAX 	Counter
	ACCESS	read-only
	STATUS	mandatory
	DESCRIPTION 
		"A count of RTP Packet Errors. "
	::= { gponPotsRtpIntervalEntry 5 }

gponPotsRtpIntervalPacketLoss  OBJECT-TYPE
	SYNTAX 	Counter
	ACCESS	read-only
	STATUS	mandatory
	DESCRIPTION 
		" Represents the fraction of packets lost.  The attribute is calculated at the end of the 15-minute,
		  and is undefined for a current interval request.  The value 0 indicates no packet loss scaling linearly
		  to 0xFFFF FFFF to indicate 100 percent packet loss.

		 SUPPORTED as of ISAM4.5.02 "
	::= { gponPotsRtpIntervalEntry 6 }

gponPotsRtpIntervalMaxJitter  OBJECT-TYPE
	SYNTAX 	Counter
	ACCESS	read-only
	STATUS	mandatory
	DESCRIPTION 
		" This is a high water mark that represents the maximum jitter identified during the measured interval,
		  expressed in RTP timestamp units. "
	::= { gponPotsRtpIntervalEntry 7 }

gponPotsRtpIntervalMaxRtcpInterval  OBJECT-TYPE
	SYNTAX 	Counter
	ACCESS	read-only
	STATUS	mandatory
	DESCRIPTION 
		" This is a high water mark that represents the maximum time between RTCP packets during the
		  measured interval, in milliseconds. "
	::= { gponPotsRtpIntervalEntry 8 }

gponPotsRtpIntervalBufferUnderflows  OBJECT-TYPE
	SYNTAX 	Counter
	ACCESS	read-only
	STATUS	mandatory
	DESCRIPTION 
		" Counts the number of times the reassembly buffer underflows.   "
	::= { gponPotsRtpIntervalEntry 9 }

gponPotsRtpIntervalBufferOverflows  OBJECT-TYPE
	SYNTAX 	Counter
	ACCESS	read-only
	STATUS	mandatory
	DESCRIPTION 
		" Counts the number of times the reassembly buffer overflows.   "
	::= { gponPotsRtpIntervalEntry 10 }


-- *********************************************
--
-- BPON POTS PORT PROFILE STATUS TABLE
--
-- This is a new table beginning with FGU4.7.4
-- This table contains a row for each provisioned POTS port on a
-- specific ONT. Rows are created automatically by the system when a POTS port 
-- is created.    
--
-- As of ISAM5.0, this table is SUPPORTED
--
--	For GPON - SUPPORTED as of ISAM5.0
--	For XG-PON1 - NOT SUPPORTED as of ISAM4.6.02
--  For NG-PON2 - SUPPORTED as of ISAM5.4.01
--
-- *********************************************

bponPotsPortProfileStatusTable  OBJECT-TYPE
	SYNTAX SEQUENCE OF BponPotsPortProfileStatusEntry
	ACCESS	not-accessible
	STATUS	mandatory
	::= { bponPotsGroup 15 }


bponPotsPortProfileStatusEntry  OBJECT-TYPE
	SYNTAX 	BponPotsPortProfileStatusEntry
	ACCESS	not-accessible
	STATUS	mandatory
	INDEX	{ bponPotsPortProfileStatusOntIndex,
		   bponPotsPortProfileStatusSpIndex }
	::= { bponPotsPortProfileStatusTable 1 }

BponPotsPortProfileStatusEntry ::= SEQUENCE {
	bponPotsPortProfileStatusOntIndex		IfIndex,
	bponPotsPortProfileStatusSpIndex		SpIndex,
	bponPotsPortProfileStatus 	    DisplayString

}


bponPotsPortProfileStatusOntIndex  OBJECT-TYPE
	SYNTAX 	IfIndex
	ACCESS	read-only
	STATUS	mandatory
	DESCRIPTION 
		"Each row is indexed by the ifIndex of the ONT

		Applicable for GPON.  "
	::= { bponPotsPortProfileStatusEntry 1 }


bponPotsPortProfileStatusSpIndex  OBJECT-TYPE
	SYNTAX 	SpIndex
	ACCESS	read-only
	STATUS	mandatory
	DESCRIPTION 
		"Each row is also indexed by a number that
		 contains the slot number and port number
		 within the ONT.

		Applicable for GPON. "
	::= { bponPotsPortProfileStatusEntry 2 }


-- the following object show the Voice Config profiles download status at
-- the ONT per POTS line. BDFam46123

bponPotsPortProfileStatus  OBJECT-TYPE
	SYNTAX 	DisplayString
	ACCESS	read-only
	STATUS	mandatory
	DESCRIPTION 
	"This attribute shows the profile download status for a number of profiles separated
     by delimiters of  \n. The order in which the profile status is returned is always device 
     profile, application profile and user profile. The download status for each can be OKAY, 
     PENDING or FAILED stored as ASCII strings."
	::= { bponPotsPortProfileStatusEntry 3}



-- *********************************************
--
-- BPON LAN ETHERNET PORT TABLE
--
-- This is a new table beginning with FGU2.5.
-- This table contains a row for each provisioned Ethernet port on a
-- specific ONT.  This table contains attributes that describe the behavior
-- of the Ethernet port as well as the port's association to a port on
-- a MAC Bridge.  Rows are created dynamically by operator via
-- Create-and-go.  Some parameters are changeable once created.  
--
-- For FGU4.0, this table is being re-used.  Comments are 
-- made regarding whether attribute is relevant to BPON,
-- GPON or both, etc. 
--
-- For ISAM4.0.10, this table is being re-used. However, for ISAM 4.0.10,
-- rows are auto-created by agent.  The number of rows auto-created is
-- determined from the bponOntPlanCardTable.
-- Noted which attributes are relevant for ISAM4.0.10. 
--
--	For GPON - SUPPORTED as of ISAM4.0.10
--	For XG-PON1 - SUPPORTED as of ISAM4.6.02
--	For NG-PON2 - SUPPORTED as of ISAM5.2
--
-- *********************************************

bponLanEtherPortTable  OBJECT-TYPE
	SYNTAX SEQUENCE OF BponLanEtherPortEntry
	ACCESS	not-accessible
	STATUS	mandatory
	::= { bponLanGroup 2 }


bponLanEtherPortEntry  OBJECT-TYPE
	SYNTAX 	BponLanEtherPortEntry
	ACCESS	not-accessible
	STATUS	mandatory
	INDEX	{ bponLanEtherPortOntIndex,
		   bponLanEtherPortSpIndex }
	::= { bponLanEtherPortTable 1 }

BponLanEtherPortEntry ::= SEQUENCE {
	bponLanEtherPortOntIndex		IfIndex,
	bponLanEtherPortSpIndex		SpIndex,
	bponLanEtherPortRowStatus		RowStatus,
	bponLanEtherPortMacBrdgId		INTEGER,
	bponLanEtherPortAutoDetectConfig	INTEGER,
	bponLanEtherPortLoopbackConfig	INTEGER,
	bponLanEtherPortAdminState		AdminState,
	bponLanEtherPortOperState		OperState,
	bponLanEtherPortMaxFrameSize	INTEGER,
	bponLanEtherPortDteOrDceInd	INTEGER,
	bponLanEtherPortPauseTime		INTEGER,
	bponLanEtherPortBridgeOrIpInd	INTEGER,
	bponLanEtherPortArc		INTEGER,
	bponLanEtherPortArcInterval		INTEGER,
	bponLanEtherPortPPPoEFilter		INTEGER,
	bponLanEtherPortBrdgPort		INTEGER,
	bponLanEtherPortPriority		INTEGER,
	bponLanEtherPortPathCost		INTEGER,
	bponLanEtherPortSpanTreeInd		INTEGER,
	bponLanEtherPortEncapsMethod 	INTEGER,
	bponLanEtherPortLanFcsInd		INTEGER,
	bponLanEtherPortPmCollectInd	INTEGER,
	bponLanEtherPortNumPMIntervals	INTEGER,
	bponLanEtherPortCustVlan		INTEGER,
	bponLanEtherPortCurrStatus		INTEGER,
	bponLanEtherPortQosProfile		AsamProfilePointer,
	bponLanEtherPortEtherTrafficPmCollectInd	INTEGER,
	bponLanEtherPortEtherTrafficNumPMIntervals	INTEGER,
	bponLanEtherPortPwrShedOverride		Boolean,
	bponLanEtherPortLabel		DisplayString,
	bponLanEtherPortDscpPbitMapProfile	AsamProfilePointer,
	bponLanEtherPortPowerControl	INTEGER,
--	bponLanEtherPortPowerPairPinoutControl	INTEGER,
	bponLanEtherPortPseClassControl	INTEGER,
	bponLanEtherPortGwayPonLossBehaveMode	INTEGER,
        bponLanEtherPortShutdownAIS  INTEGER
}


bponLanEtherPortOntIndex  OBJECT-TYPE
	SYNTAX 	IfIndex
	ACCESS	read-only
	STATUS	mandatory
	DESCRIPTION 
		"Each row is indexed by the ifIndex of the ONT

		Applicable for both BPON and GPON.

		For ISAM4.0.10 - stays the same as latest FGU4.x  "
	::= { bponLanEtherPortEntry 1 }


bponLanEtherPortSpIndex  OBJECT-TYPE
	SYNTAX 	SpIndex
	ACCESS	read-only
	STATUS	mandatory
	DESCRIPTION 
		"Each row is also indexed by a number that
		 contains the Ethernet slot number and port number
 		 within the ONT. 

		Applicable for both BPON and GPON.

		For ISAM4.0.10 - stays the same as latest FGU4.x  "
	::= { bponLanEtherPortEntry 2 }



bponLanEtherPortRowStatus  OBJECT-TYPE
	SYNTAX 	RowStatus
	ACCESS	read-write
	STATUS	mandatory
	DESCRIPTION 
		" Prior to ISAM 4.0.10, all rows instantiated using 'create-and-go' to
		 provision a LAN port. Set to 'destroy' to delete
		 a LAN port. 

		Applicable for both BPON and GPON.

		 For ISAM 4.0.10, this attribute is NOT SUPPORTED.  "
	::= { bponLanEtherPortEntry 3 }

bponLanEtherPortMacBrdgId  OBJECT-TYPE
	SYNTAX 	INTEGER
	ACCESS	read-write
	STATUS	mandatory
	DESCRIPTION 
		" This represents the ID of the MAC Bridge (with which
		   this Ethernet port is associated). 

		 Not applicable for GPON.

		For ISAM4.0.10 - stays the same as latest FGU4.x "
	::= { bponLanEtherPortEntry 4 }

bponLanEtherPortAutoDetectConfig  OBJECT-TYPE
	SYNTAX 	INTEGER
	ACCESS	read-write
	STATUS	mandatory
	DESCRIPTION 
		" Used to set the Ethernet UNI Auto Detect and 
		  fixed configuration options as follows:

		NOTE:  Starting with FGU4.5.5, the meaning and 
		interpretation of the codepoints changed to be compliant
		with changes to standard OMCI.  The new meaning of the 
		codepoints deals with the varied options associated with
		rate and duplexity.  Some new codepoints were added.
		In addition (for backward compatibility of EMS and TL1), old
		codepoints were retained.  We kept OMCI codepoints as standard.
		So we have a situation where multiple MIB codepoints must be 
		translated to same OMCI codepoint, and old user interface may
		not translate into exact behavior.  But the upside is we don't take
		away old TL1 text that may be embedded in customer OSS. The MIB values,
		meanings, and OMCI translations shake out as follows:

		 0 (MIB Value) = 10/100Auto (retained for pre FGU4.5.5 legacy)
		       OMCI Translation = 0 = RATE - Auto & DUPLEXITY - Auto
		 1 (MIB Value) = 10FD
		       OMCI Translation = 1 =  RATE - 10 only & DUPLEXITY - Full Duplex only
		 2 (MIB Value) = 100FD
		       OMCI Translation = 2 = RATE - 100 only & DUPLEXITY - Full Duplex only
		 3 (MIB Value) = 1000FD
		       OMCI Translation = 3 = RATE - 1000 only & DUPLEXITY - Full Duplex only
		 4 (MIB Value) = AutoFD (new starting with FGU4.5.5)
		       OMCI Translation = 4 = RATE - Auto & DUPLEXITY - Full Duplex only
		 5 (MIB Value) = 10GigFD (new starting ISAM5.2)
		       OMCI Translation = 5 = RATE - 10Gig & DUPLEXITY - Full Duplex only
		 16 (MIB Value) = 10Auto
		        OMCI Translation = 16 = RATE - 10 only & DUPLEXITY - Auto
		 17 (MIB Value) = 10HD
		        OMCI Translation = 17 = RATE - 10 only & DUPLEXITY - Half Duplex only
		 18 (MIB Value) = 100HD
		        OMCI Translation = 18 = RATE - 100 only & DUPLEXITY - Half Duplex only
		 19 (MIB Value) = 1000HD
		        OMCI Translation = 19 = RATE - 1000 only & DUPLEXITY - Half Duplex only
		 20 (MIB Value) = AutoHD (new starting with FGU4.5.5)
		        OMCI Translation = 20 = RATE - Auto & DUPLEXITY - Half Duplex only
		 32 (MIB Value) = 10/100/1000Auto (retained for pre FGU4.5.5 legacy)
		        OMCI Translation = 0 = RATE - Auto & DUPLEXITY - Auto
		 48 (MIB Value)  = 100Auto (new starting with FGU4.5.5)
		        OMCI Translation = 48 = RATE - 100 only & DUPLEXITY - Auto
		 96 (MIB Value)  = AutoAuto (new starting with FGU4.5.5)
		        OMCI Translation = 0 = RATE - Auto & DUPLEXITY - Auto
		 97 (MIB Value)  = 1000Auto (new starting with FGU4.5.5)
		        OMCI Translation = 32 = RATE - 1000 only & DUPLEXITY - Auto

		 Default = 96 (MIB Value) = AutoAuto
		        OMCI Translation = 0 = RATE - Auto & DUPLEXITY - Auto

		Applicable for both BPON and GPON. 

		For ISAM4.0.10 - stays the same as latest FGU4.x "
	::= { bponLanEtherPortEntry 5 }

bponLanEtherPortLoopbackConfig  OBJECT-TYPE
	SYNTAX 	INTEGER
	ACCESS	read-write
	STATUS	mandatory
	DESCRIPTION 
		"Loopback configuration options:

		 0 = No Loopback
		 3 = Loop of downstream after Phy
		       (see Fig 11-a in 983.2)
		 Default = 0  (only supported option)

		Applicable for both BPON and GPON.

		For ISAM4.0.10 - stays the same as latest FGU4.x "
	::= { bponLanEtherPortEntry 6 }

bponLanEtherPortAdminState  OBJECT-TYPE
	SYNTAX 	AdminState
	ACCESS	read-write
	STATUS	mandatory
	DESCRIPTION 
		"For OMCI messaging, this attribute translates
		 into Admin State for the PPTP Ethernet UNI.  
		 Setting it to 'locked' deactivates the particular
		 Ethernet port.
		 Modification permitted even after row
		 becomes 'active'.
		 Default = 1 = locked 

		Applicable for both BPON and GPON.

		For ISAM4.0.10 - this attribute is NOT SUPPORTED. "
	::= { bponLanEtherPortEntry 7 }

bponLanEtherPortOperState  OBJECT-TYPE
	SYNTAX 	OperState
	ACCESS	read-only
	STATUS	mandatory
	DESCRIPTION 
		"Indicates operational state of the
		  Ethernet port. State is related to ability of port
		  to perform its function (e.g. whether service
		  affecting alarm is present).
		  Default = 0 = Enabled 

		  Applicable for both BPON and GPON.

		For ISAM4.0.10 - this attribute is NOT SUPPORTED. "
	::= { bponLanEtherPortEntry 8 }


bponLanEtherPortMaxFrameSize  OBJECT-TYPE
	SYNTAX 	INTEGER
	ACCESS	read-write
	STATUS	mandatory
	DESCRIPTION 
		"Maximum allowed frame size across the Ethernet 
		 UNI interface.
		 
		 This attribute NOT BE SET by any manager (neither TL1 or AMS).
		 And OLT SHOULD NOT send this attribute via OMCI.
		 It can be read via GET, but managers (TL1 and EMS) are discouraged from doing this.
		 Eventually, this attribute will become NOT SUPPORTED (but not yet).

		 OLT default = 2000	 

		Applicable for both BPON and GPON.

		For ISAM4.0.10 - this attribute is NOT SUPPORTED "
	::= { bponLanEtherPortEntry 9 }

bponLanEtherPortDteOrDceInd  OBJECT-TYPE
	SYNTAX 	INTEGER
	ACCESS	read-write
	STATUS	mandatory
	DESCRIPTION 
		"Indicates whether Ethernet Interface wiring is
		 DCE or DTE.

		 0 = DCE
		 1 = DTE
		 Only DCE is supported.
		 Default = 0 

		Applicable for both BPON and GPON.

		For ISAM4.0.10, this attribute is NOT SUPPORTED.  "
	::= { bponLanEtherPortEntry 10 }

bponLanEtherPortPauseTime  OBJECT-TYPE
	SYNTAX 	INTEGER
	ACCESS	read-write
	STATUS	mandatory
	DESCRIPTION 
		"Allows Ethernet linecard to request that customer
		  terminal temporarily suspend sending data to this
		  Ethernet port. Units are in 'pause quanta', where 1
		  pause quantum equals 512 bit times of particular
		  implementation.
		 Default = 0  - not implemented or supported for either
			BPON or GPON. 

		 Prior to FGU4.0--> Not Supported
		 Since FGU4.0--> Not  Supported

		For ISAM4.0.10 - stays the same as latest FGU4.x "
	::= { bponLanEtherPortEntry 11 }

bponLanEtherPortBridgeOrIpInd  OBJECT-TYPE
	SYNTAX 	INTEGER
	ACCESS	read-write
	STATUS	mandatory
	DESCRIPTION 
		"Indicates whether Ethernet Interface is bridged
		 or derived from an IP router.

		 0 = Bridged
		 1 = IP Router
		 2 = Depends on setting of Subscriber Line Card
		       (meaning that similar attribute for SLC is
		        set to either 0 or 1)
		 Cannot be modified once provisioned.
		 Only Bridged is supported.  
		 Default = 0 

		Not applicable for GPON.

		For ISAM4.0.10 - stays the same as latest FGU4.x "
	::= { bponLanEtherPortEntry 12 }

bponLanEtherPortArc  OBJECT-TYPE
	SYNTAX 	INTEGER
	ACCESS	read-write
	STATUS	mandatory
	DESCRIPTION 
		"Alarm Reporting Control.  Valid values are:

		0 = Off (meaning alarm reporting allowed
		             immediately)
		1 = On (meaning alarm reporting inhibited until
		             valid signal is detected for time period
		             specified by ARC Interval).
		 Default = 1  - function is not implemented or supported 
			for either BPON or GPON. 

		 Prior to FGU4.0--> Not Supported
		 Since FGU4.0--> Not  Supported

		For ISAM4.0.10 - stays the same as latest FGU4.x "
	::= { bponLanEtherPortEntry 13 }

bponLanEtherPortArcInterval  OBJECT-TYPE
	SYNTAX 	INTEGER
	ACCESS	read-write
	STATUS	mandatory
	DESCRIPTION 
		"Alarm Reporting Control Interval (in minutes).

		 0 means alarms are inhibited indefinitely (if ARC
		   is set to inhibited)
		 Default = 0  - function is not implemented or supported 
			for either BPON or GPON. 

		 Prior to FGU4.0--> Not Supported
		 Since FGU4.0--> Not  Supported

		For ISAM4.0.10 - stays the same as latest FGU4.x "
	::= { bponLanEtherPortEntry 14 }

bponLanEtherPortPPPoEFilter  OBJECT-TYPE
	SYNTAX 	INTEGER
	ACCESS	read-write
	STATUS	mandatory
	DESCRIPTION 
		" Used to control filtering of PPPoE packets on the 
		  Ethernet port.

		  0 = Disable Filtering
		  1 = Enable Filtering (meaning all packets other than PPPoE
				packets will be discarded).

		 Default = 0  - function is not implemented or supported 
			in either BPON or GPON.

		 Prior to FGU4.0--> Not Supported
		 Since FGU4.0--> Not  Supported

		For ISAM4.0.10 - stays the same as latest FGU4.x  "
	::= { bponLanEtherPortEntry 15 }


bponLanEtherPortBrdgPort  OBJECT-TYPE
	SYNTAX 	INTEGER
	ACCESS	read-write
	STATUS	mandatory
	DESCRIPTION 
		"Used to designate the port ID on MAC Bridge.
		 This port ID must be unique across all Ethernet
		 ports and LAN VCLs connected to the same bridge.

		 Default = 1 

		 Prior to FGU4.0--> Not Supported.

		 Not applicable for GPON.

		For ISAM4.0.10 - stays the same as latest FGU4.x  "
	::= { bponLanEtherPortEntry 16 }


bponLanEtherPortPriority  OBJECT-TYPE
	SYNTAX 	INTEGER 
	ACCESS	read-write
	STATUS	mandatory
	DESCRIPTION 
		"The priority of the MAC Bridge port  
		  (for Spanning Tree purposes).

		 Range is 0 to 255.
		 Default = 128

		 Prior to FGU4.0--> Not Supported.

		 Not applicable for GPON.

		For ISAM4.0.10 - stays the same as latest FGU4.x   "
	::= { bponLanEtherPortEntry 17 }

bponLanEtherPortPathCost  OBJECT-TYPE
	SYNTAX 	INTEGER 
	ACCESS	read-write
	STATUS	mandatory
	DESCRIPTION 
		"The cost contribution of the port to the
		   path cost towards the spanning tree root
		   bridge  (for Spanning Tree purposes).

		 Range is 1 to 65535.
		 Default = 100
 
		 Prior to FGU4.0--> Not Supported.

		 Not applicable for GPON.

		For ISAM4.0.10 - stays the same as latest FGU4.x  "
	::= { bponLanEtherPortEntry 18 }

bponLanEtherPortSpanTreeInd  OBJECT-TYPE
	SYNTAX 	INTEGER 
	ACCESS	read-write
	STATUS	mandatory
	DESCRIPTION 
		"Indicates whether Spanning Tree Protocol
		  is enabled at this bridge port.

		 0 = Disabled
		 1 = Enabled
		 Default = 0 = Disabled 

		 Prior to FGU4.0--> Not Supported..
		 Not applicable for GPON.

		For ISAM4.0.10 - stays the same as latest FGU4.x   "
	::= { bponLanEtherPortEntry 19 }

bponLanEtherPortEncapsMethod  OBJECT-TYPE
	SYNTAX 	INTEGER 
	ACCESS	read-write
	STATUS	mandatory
	DESCRIPTION 
		"Identifies the frame encapsulation method
		  used at this bridge port.

		 0 = ATM VC
		 1 = LLC SNAP
		 Default = 1 (only method supported)  

		 Prior to FGU4.0--> Not Supported.

		 Not applicable for GPON.

		For ISAM4.0.10 - stays the same as latest FGU4.x "
	::= { bponLanEtherPortEntry 20 }

bponLanEtherPortLanFcsInd  OBJECT-TYPE
	SYNTAX 	INTEGER 
	ACCESS	read-write
	STATUS	mandatory
	DESCRIPTION 
		"Indicates whether LAN Frame Check Sequence (FCS)
		  bytes are forwarded or discarded towards the OLT:

		 0 = Forwarded
		 1 = Discarded
		 Default = 0   

		 Prior to FGU4.0--> Not Supported.

		 Not applicable for GPON. 

		For ISAM4.0.10 - stays the same as latest FGU4.x  "
	::= { bponLanEtherPortEntry 21 }

bponLanEtherPortPmCollectInd  OBJECT-TYPE
	SYNTAX 	INTEGER
	ACCESS	read-write
	STATUS	mandatory
	DESCRIPTION 
		" This indicates whether Ethernet Performance Monitors
		   should be collected for this Ethernet Port.
	
		  1 = PM collection enabled
		  2 = PM collection disabled

		 Default = 2 = disabled.

		Applicable for both BPON and GPON.

		For ISAM4.0.10 - stays the same as latest FGU4.x   "
	::= { bponLanEtherPortEntry 22 }

bponLanEtherPortNumPMIntervals  OBJECT-TYPE
	SYNTAX 	INTEGER
	ACCESS	read-only
	STATUS	mandatory
	DESCRIPTION 
		" Indicates the number of rows currently present
		  in the bponLanEtherPortIntervalTable.  This
		  is for convenience of the EMS, so that it can
		 quickly determine how many rows should be 
		 uploaded.

		Applicable only for GPON.

		For ISAM4.0.10 - stays the same as latest FGU4.x   "
	::= { bponLanEtherPortEntry 23 }

bponLanEtherPortCustVlan  OBJECT-TYPE
	SYNTAX 	INTEGER
	ACCESS	read-write
	STATUS	mandatory
	DESCRIPTION 
		" This is the default Customer VLAN ID
		  used by the ONT for this Ethernet UNI.
		  Based on certain 'tagging modes', the ONT
		  inserts this VLAN tag into certain Ethernet
		  frames. 

		  Range is 0 - 4095.

		 Default = 0.

		Applicable only for GPON.

		For ISAM 4.0.10, this attribute is NOT SUPPORTED.   "
	::= { bponLanEtherPortEntry 24 }


bponLanEtherPortCurrStatus  OBJECT-TYPE
	SYNTAX 	INTEGER
	ACCESS	read-only
	STATUS	mandatory
	DESCRIPTION 
		" Indicates current status of the Ethernet port.
		  This is a bit-map of possible conditions.  The
		  bit positions are as follows:

		0 - No defects on line
		1 - OMCI Mismatch Problem
		2 - Loss of Signal

		 Default = 0.

		Applicable only for GPON.

		For ISAM4.0.10 - stays the same as latest FGU4.x   "
	::= { bponLanEtherPortEntry 25 }


bponLanEtherPortQosProfile OBJECT-TYPE
	SYNTAX	AsamProfilePointer
	ACCESS read-write
	STATUS	mandatory
	DESCRIPTION
		" This object is used to reference the appropriate
		 QOS Profile (in the QOS MIB) --> for tag marking.

		 The ONT LAN UNI is associated with one OLT bridge port
		 which is associated with one QOS Profile.

		Applicable only for GPON. 

		For ISAM 4.0.10, this attribute is NOT SUPPORTED. "
	::= { bponLanEtherPortEntry 26 }


bponLanEtherPortEtherTrafficPmCollectInd  OBJECT-TYPE
	SYNTAX 	INTEGER
	ACCESS	read-write
	STATUS	mandatory
	DESCRIPTION 
		" This indicates whether Ethernet Traffic Performance Monitors
		   should be collected for this Ethernet Port.
	
		  1 = PM collection enabled
		  2 = PM collection disabled

		 Default = 2 = disabled.

		Applicable only for GPON.

		For ISAM4.0.10 - stays the same as latest FGU4.x   "
	::= { bponLanEtherPortEntry 27 }

bponLanEtherPortEtherTrafficNumPMIntervals  OBJECT-TYPE
	SYNTAX 	INTEGER
	ACCESS	read-only
	STATUS	mandatory
	DESCRIPTION 
		" Indicates the number of rows currently present
		  in the gponEtherTrafficIntervalTable.  This
		  is for convenience of the EMS, so that it can
		 quickly determine how many rows should be 
		 uploaded.

		Applicable only for GPON.

		For ISAM4.0.10 - stays the same as latest FGU4.x   "
	::= { bponLanEtherPortEntry 28 }

bponLanEtherPortPwrShedOverride  OBJECT-TYPE
	SYNTAX 	Boolean
	ACCESS	read-write
	STATUS	mandatory
	DESCRIPTION 
		"Allows setting as follows:

		 TRUE = 1 = port excluded from data class power shedding
		 FALSE = 0 = port included in data class power shedding

		 Default = 0 = FALSE 

		 As of FGU4.4, this is Supported.

		For ISAM4.0.10 - stays the same as latest FGU4.x   "
	::= { bponLanEtherPortEntry 29 }


bponLanEtherPortLabel  OBJECT-TYPE
	SYNTAX 	DisplayString (SIZE(0..80))
	ACCESS	read-write
	STATUS	mandatory
	DESCRIPTION 
		"This is a textual string that can be used
		 to label the Ethernet port.

		 Default - null string. 

		 Modification is permitted.

		For ISAM4.0.10 - stays the same as latest FGU4.x  "
	::= { bponLanEtherPortEntry 30 }


bponLanEtherPortDscpPbitMapProfile OBJECT-TYPE
	SYNTAX	AsamProfilePointer
	ACCESS read-write
	STATUS	mandatory
	DESCRIPTION
		" This object is used to reference the appropriate
		  DSCP-to-Pbit mapping profile (in the GPON MIB).

		  The value 0 means that the system-wide DSCP-to-Pbit mapping
		  specified in auto-created Profile Number 51 is used for this UNI. 
		  When a value other than 0 is specified, must point to a valid profile
		  in the GPON MIB.

		  Valid range is 0 - 50.

		  Modification is permitted (without having to ADMIN DOWN the UNI).
		  Default = 0 = meaning use system-wide mapping. 

		  Supported as of FGU4.4

		  Applicable only for GPON.

		For ISAM4.0.10, this attribute is NOT SUPPORTED.  "
	::= { bponLanEtherPortEntry 31 }

bponLanEtherPortPowerControl  OBJECT-TYPE
	SYNTAX 	INTEGER
	ACCESS	read-write
	STATUS	mandatory
	DESCRIPTION 
		" This attribute controls whether power is provided to external equipment over this Ethernet UNI.

		  0 = PoE Disabled (Default)
		  1 = PoE Enabled

		As of ISAM4.4, this attribute is SUPPORTED.   "
	::= { bponLanEtherPortEntry 32 }

-- bponLanEtherPortPowerPairPinoutControl  OBJECT-TYPE
--	SYNTAX 	INTEGER
--	ACCESS	read-write
--	STATUS	mandatory
--	DESCRIPTION 
--		" Used to configure the PSE power pair pinout (if supported by this port - as indicated
--		  by bponLanEtherPortOpstatPoECapabilities attribute).
--		  Maps to a SET of OMCI attribute (i.e. Power Pair Pinout Control of PoE Control ME).
--
--		  0 = Pinout Alternative A (signal pairs).
--		  1 = Pinout Alternative B (spare pairs).
--
--		 255 = Unspecified (meaning no value is sent to the ONT via OMCI).
--
--		 Default = 255
--
--		As of ISAM4.4, this attribute is NOT SUPPORTED.  "
--	::= { bponLanEtherPortEntry 33 }

bponLanEtherPortPseClassControl  OBJECT-TYPE
	SYNTAX 	INTEGER
	ACCESS	read-write
	STATUS	mandatory
	DESCRIPTION 
		" Used to place specific limits on the class of power supported by this port.
		  Maps to a SET of OMCI attribute (i.e. PsE Class Control of PoE Control ME).

		  0 = Power Feed Enabled at default level.
		  1 = Power Feed Enabled at Class 0 power level.
		  2 = Power Feed Enabled at Class 1 power level.
		  3 = Power Feed Enabled at Class 2 power level.
		  4 = Power Feed Enabled at Class 3 power level.
		  5 = Power Feed Enabled at Class 4 power level.

		  Default = 0 

		As of ISAM4.4, this attribute is SUPPORTED.  "
	::= { bponLanEtherPortEntry 34 }

bponLanEtherPortGwayPonLossBehaveMode  OBJECT-TYPE
	SYNTAX 	INTEGER
	ACCESS	read-write
	STATUS	mandatory
	DESCRIPTION 
		" Indicates how gateway connected Ethernet UNI state should behave following ONT PON loss 
		  (e.g in regards to DHCP session re-establishment).

		   0 = 'Do Not Care and do not send any OMCI' (DEFAULT)		
		   1 = Link Pass Thru (LPT) Enable. Means the UNI goes Down when PON goes Down.
		   2 = Link Pass Thru (LPT) Disable.  Means UNI stays Up when PON goes Down.

		  Modification is permitted.   "
	::= { bponLanEtherPortEntry 35 }

bponLanEtherPortShutdownAIS  OBJECT-TYPE
        SYNTAX    INTEGER
   	ACCESS    read-write
   	STATUS    mandatory
   	DESCRIPTION 
             "This attribute is linked to a CFM functionality on the ONU. It indicates if the ONU is programmed to autonomously shut down its UNI upon reception of a downstream AIS PDU on an UP MEP residing on top of the ONU UNI. This would typically allow a router connected the UNI to switch to another port (via LOS detection, assuming that router has two uplinks in redundancy mode) without having to rely on CFM. For a given ONU, the operator has the choice to activate or deactivate this autonomous shutdown on a per UNI basis. This function, even when enabled, won't be effective unless there is a MEP on the ONU UNI. 
          1 - Enabled (shutdown ethernet port)
          2 - Disabled (NOT shutdown ethernet port)
              
          Default = 2 = Disabled

          As of ISAM5.4, this attribute is SUPPORTED."

        ::= {bponLanEtherPortEntry 36 }

-- *********************************************
--
-- BPON LAN ETHERNET PERFORMANCE MONITOR INTERVAL TABLE
--
-- This is a new table beginning with FGU2.5.
-- This interval table contains various statistics collected
-- at an ONT's Ethernet interface over the previous 8 hours 
-- of operation.  The past 8 hours are broken into 32  
-- completed 15 minute intervals.  Each row in this table
-- represents one such interval for a specific Ethernet port
-- on a specific ONT.
--
-- For FGU4.0, this table is being re-used.  Ethernrt PMs
-- are the same for BPON and GPON.
--
-- For ISAM4.0.10, this table is being re-used. 
-- Noted which attributes are relevant for ISAM4.0.10 
-- 
--
--	For GPON - SUPPORTED as of ISAM4.0.10
--	For XG-PON1 - SUPPORTED as of ISAM4.6.02
--	For NG-PON2 - SUPPORTED as of ISAM5.2
--
-- *********************************************


bponLanEtherIntervalTable  OBJECT-TYPE
	SYNTAX SEQUENCE OF BponLanEtherIntervalEntry
	ACCESS	not-accessible
	STATUS	mandatory
	::= { bponLanGroup 4 }


bponLanEtherIntervalEntry  OBJECT-TYPE
	SYNTAX 	BponLanEtherIntervalEntry
	ACCESS	not-accessible
	STATUS	mandatory
	DESCRIPTION 
		"An entry in the Apon Lan Ethernet Interval 
		 Table. "
	INDEX	{ bponLanEtherIntervalOntIndex, 
		   bponLanEtherIntervalSpIndex,
		  bponLanEtherIntervalNumber }
	::= { bponLanEtherIntervalTable 1 }

BponLanEtherIntervalEntry ::= SEQUENCE {
	bponLanEtherIntervalOntIndex			IfIndex,
	bponLanEtherIntervalSpIndex			SpIndex,
	bponLanEtherIntervalNumber			INTEGER,
	bponLanEtherIntervalValidInd			Boolean,
	bponLanEtherIntervalFCSEs			Counter,
	bponLanEtherIntervalECs			Counter,
	bponLanEtherIntervalLCs			Counter,
	bponLanEtherIntervalFTLs			Counter,
	bponLanEtherIntervalRBOs			Counter,
	bponLanEtherIntervalTBOs			Counter,
	bponLanEtherIntervalSCFs			Counter,
	bponLanEtherIntervalMCFs			Counter,
	bponLanEtherIntervalSQEs			Counter,
	bponLanEtherIntervalDTs			Counter,
	bponLanEtherIntervalIMTEs			Counter,
	bponLanEtherIntervalCSEs			Counter,
	bponLanEtherIntervalAEs			Counter,
	bponLanEtherIntervalIMREs			Counter

}


bponLanEtherIntervalOntIndex  OBJECT-TYPE
	SYNTAX 	IfIndex
	ACCESS	read-only
	STATUS	mandatory
	DESCRIPTION 
		"Each row is indexed by the ifIndex of the ONT. 

		Applicable for both BPON and GPON.

		For ISAM4.0.10 - stays the same as latest FGU4.x "
	::= { bponLanEtherIntervalEntry 1 }

bponLanEtherIntervalSpIndex  OBJECT-TYPE
	SYNTAX 	SpIndex
	ACCESS	read-only
	STATUS	mandatory
	DESCRIPTION 
		"Each row is also indexed by a number that
		 contains the slot number and port number
 		 within the ONT.

		Applicable for both BPON and GPON.

		For ISAM4.0.10 - stays the same as latest FGU4.x "
	::= { bponLanEtherIntervalEntry 2 }

bponLanEtherIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1. 

		Applicable for both BPON and GPON.

		For ISAM4.0.10 - stays the same as latest FGU4.x "
	::= { bponLanEtherIntervalEntry 3 }

bponLanEtherIntervalValidInd  OBJECT-TYPE
	SYNTAX 	Boolean
	ACCESS	read-only
	STATUS	mandatory
	DESCRIPTION 
		"Indicates whether or not this interval contains
		 valid PM counts. 

		Applicable for both BPON and GPON.

	`	As of FGU4.2, NOT SUPPORTED

		For ISAM4.0.10 - stays the same as latest FGU4.x "
	::= { bponLanEtherIntervalEntry 4 }


bponLanEtherIntervalFCSEs  OBJECT-TYPE
	SYNTAX 	Counter
	ACCESS	read-only
	STATUS	mandatory
	DESCRIPTION 
		"A count of Frame Check Sequence(FCS)Errors.

		Applicable for both BPON and GPON.

		For ISAM4.0.10 - stays the same as latest FGU4.x "
	::= { bponLanEtherIntervalEntry 5 }

bponLanEtherIntervalECs  OBJECT-TYPE
	SYNTAX 	Counter
	ACCESS	read-only
	STATUS	mandatory
	DESCRIPTION 
		"A count of Excessive Collisions.

		Applicable for both BPON and GPON.

		For ISAM4.0.10 - stays the same as latest FGU4.x "
	::= { bponLanEtherIntervalEntry 6 }

bponLanEtherIntervalLCs  OBJECT-TYPE
	SYNTAX 	Counter
	ACCESS	read-only
	STATUS	mandatory
	DESCRIPTION 
		"A count of Late Collisions.

		Applicable for both BPON and GPON.

		For ISAM4.0.10 - stays the same as latest FGU4.x "
	::= { bponLanEtherIntervalEntry 7 }

bponLanEtherIntervalFTLs  OBJECT-TYPE
	SYNTAX 	Counter
	ACCESS	read-only
	STATUS	mandatory
	DESCRIPTION 
		"A count of Frames that are Too Long.

		Applicable for both BPON and GPON.

		For ISAM4.0.10 - stays the same as latest FGU4.x "
	::= { bponLanEtherIntervalEntry 8 }

bponLanEtherIntervalRBOs  OBJECT-TYPE
	SYNTAX 	Counter
	ACCESS	read-only
	STATUS	mandatory
	DESCRIPTION 
		"A count of Receive Buffer Overflows.

		Applicable for both BPON and GPON.

		For ISAM4.0.10 - stays the same as latest FGU4.x "
	::= { bponLanEtherIntervalEntry 9 }

bponLanEtherIntervalTBOs  OBJECT-TYPE
	SYNTAX 	Counter
	ACCESS	read-only
	STATUS	mandatory
	DESCRIPTION 
		"A count of Transmit Buffer Overflows.

		Applicable for both BPON and GPON.

		For ISAM4.0.10 - stays the same as latest FGU4.x "
	::= { bponLanEtherIntervalEntry 10 }

bponLanEtherIntervalSCFs  OBJECT-TYPE
	SYNTAX 	Counter
	ACCESS	read-only
	STATUS	mandatory
	DESCRIPTION 
		"A count of successfully transmitted
		 Single Collision Frames.

		Applicable for both BPON and GPON.

		For ISAM4.0.10 - stays the same as latest FGU4.x "
	::= { bponLanEtherIntervalEntry 11 }

bponLanEtherIntervalMCFs  OBJECT-TYPE
	SYNTAX 	Counter
	ACCESS	read-only
	STATUS	mandatory
	DESCRIPTION 
		"A count of successfully transmitted
		 Multiple Collision Frames.

		Applicable for both BPON and GPON.

		For ISAM4.0.10 - stays the same as latest FGU4.x "
	::= { bponLanEtherIntervalEntry 12 }


bponLanEtherIntervalSQEs  OBJECT-TYPE
	SYNTAX 	Counter
	ACCESS	read-only
	STATUS	mandatory
	DESCRIPTION 
		"A count of SQE Test Error messages generated.

		Applicable for both BPON and GPON.

		For ISAM4.0.10 - stays the same as latest FGU4.x "
	::= { bponLanEtherIntervalEntry 13 }

bponLanEtherIntervalDTs  OBJECT-TYPE
	SYNTAX 	Counter
	ACCESS	read-only
	STATUS	mandatory
	DESCRIPTION 
		"A count of frames delayed due to Deferred
		 Transmission.

		Applicable for both BPON and GPON.

		For ISAM4.0.10 - stays the same as latest FGU4.x "
	::= { bponLanEtherIntervalEntry 14 }

bponLanEtherIntervalIMTEs  OBJECT-TYPE
	SYNTAX 	Counter
	ACCESS	read-only
	STATUS	mandatory
	DESCRIPTION 
		"A count of unsuccessfully transmitted frames
		 due to Internal MAC Transmit Error.

		Applicable for both BPON and GPON.

		For ISAM4.0.10 - stays the same as latest FGU4.x "
	::= { bponLanEtherIntervalEntry 15 }


bponLanEtherIntervalCSEs  OBJECT-TYPE
	SYNTAX 	Counter
	ACCESS	read-only
	STATUS	mandatory
	DESCRIPTION 
		"A count of Carrier Sense Errors.

		Applicable for both BPON and GPON.

		For ISAM4.0.10 - stays the same as latest FGU4.x "
	::= { bponLanEtherIntervalEntry 16 }

bponLanEtherIntervalAEs  OBJECT-TYPE
	SYNTAX 	Counter
	ACCESS	read-only
	STATUS	mandatory
	DESCRIPTION 
		"A count of frames having Alignment Errors.

		Applicable for both BPON and GPON.

		For ISAM4.0.10 - stays the same as latest FGU4.x "
	::= { bponLanEtherIntervalEntry 17 }

bponLanEtherIntervalIMREs  OBJECT-TYPE
	SYNTAX 	Counter
	ACCESS	read-only
	STATUS	mandatory
	DESCRIPTION 
		"A count of unsuccessfully received frames
		 due to Internal MAC Receive Error.

		Applicable for both BPON and GPON.

		For ISAM4.0.10 - stays the same as latest FGU4.x "
	::= { bponLanEtherIntervalEntry 18 }



-- *********************************************
--
-- BPON LAN ETHERNET PORT OPERATIONAL STATUS TABLE
--
-- This is a new table beginning with FGU2.5.
-- This table contains a row for each provisioned Ethernet port on a
-- specific ONT.  This table contains status attributes about the Ethernet
-- port that must be obtained directly via OMCI get messages.
-- Rows are created automatically by the OLT after the associated row
-- is created in the bponEtherPortTable. 
--
-- For FGU4.0, this table is being re-used.  Ethernet Op Status
-- attributes are the same for BPON and GPON.
--
-- For ISAM4.0.10, this table is being re-used. 
-- Noted which attributes are relevant for ISAM4.0.10 
--
--
--	For GPON - SUPPORTED as of ISAM4.0.10
--	For XG-PON1 - SUPPORTED as of ISAM4.6.02
--	For NG-PON2 - SUPPORTED as of ISAM5.2
--
-- *********************************************

bponLanEtherPortOpstatTable  OBJECT-TYPE
	SYNTAX SEQUENCE OF BponLanEtherPortOpstatEntry
	ACCESS	not-accessible
	STATUS	mandatory
	::= { bponLanGroup 6 }


bponLanEtherPortOpstatEntry  OBJECT-TYPE
	SYNTAX 	BponLanEtherPortOpstatEntry
	ACCESS	not-accessible
	STATUS	mandatory
	INDEX	{ bponLanEtherPortOpstatOntIndex,
		   bponLanEtherPortOpstatSpIndex }
	::= { bponLanEtherPortOpstatTable 1 }

BponLanEtherPortOpstatEntry ::= SEQUENCE {
	bponLanEtherPortOpstatOntIndex		IfIndex,
	bponLanEtherPortOpstatSpIndex		SpIndex,
	bponLanEtherPortOpstatConfigIndicator		INTEGER,
	bponLanEtherPortOpstatLinkStatus		INTEGER,
	bponLanEtherPortOpstatPoECapabilities	OCTET STRING,
	bponLanEtherPortOpstatPowerPairPinoutActual		INTEGER,
	bponLanEtherPortOpstatPowerDetectionStatus	INTEGER,
	bponLanEtherPortOpstatPowerClassStatus	INTEGER
}


bponLanEtherPortOpstatOntIndex  OBJECT-TYPE
	SYNTAX 	IfIndex
	ACCESS	read-only
	STATUS	mandatory
	DESCRIPTION 
		"Each row is indexed by the ifIndex of the ONT

		For ISAM4.0.10 - stays the same as latest FGU4.x "
	::= { bponLanEtherPortOpstatEntry 1 }


bponLanEtherPortOpstatSpIndex  OBJECT-TYPE
	SYNTAX 	SpIndex
	ACCESS	read-only
	STATUS	mandatory
	DESCRIPTION 
		"Each row is also indexed by a number that
		 contains the Ethernet slot number and port number
 		 within the ONT.

		For ISAM4.0.10 - stays the same as latest FGU4.x  "
	::= { bponLanEtherPortOpstatEntry 2 }

bponLanEtherPortOpstatConfigIndicator  OBJECT-TYPE
	SYNTAX 	INTEGER
	ACCESS	read-only
	STATUS	mandatory
	DESCRIPTION 
		" Used to indicate configuration status of the Ethernet
		  UNI as follows: 

		 0 = Status not detected
		 1 = 10BaseT (full duplex)
		 2 = 100BaseT (full duplex)
		 3 = GigE (full duplex)
		 4 = 10GigE (full duplex) - SUPPORTED as of ISAM5.2
		 17 = 10BaseT (half duplex)
		 18 = 100BaseT (half duplex)
		 19 = GigE (half duplex)

		NOTE:  Retrievals of this attribute (via either
		REPT-OPSTAT-ONTLAN or SNMP GET) will result
		in the OLT going directly to the ONT via OMCI to get the 
		freshest information. The related OMCI attribute is called
		ConfigurationIndicator within PPTP Ethernet UNI Managed
		Entity.

		 Default = 0 = Status not detected

		Applicable for both BPON and GPON.

		For ISAM4.0.10 - stays the same as latest FGU4.x

		For ISAM5.2, codpoint 4 is SUPPORTED  "
	::= { bponLanEtherPortOpstatEntry 3 }


bponLanEtherPortOpstatLinkStatus  OBJECT-TYPE
	SYNTAX 	INTEGER
	ACCESS	read-only
	STATUS	mandatory
	DESCRIPTION 
		"Used to indicate the carrier detection status of the 
		  Ethernet UNI as follows: 

		 0 = No carrier detected
		 1 = Carrier detected

		 Default = 0 = No carrier detected

		 NOTE:  The agent discerns this status via 
		 raise/clear status of the LAN-LOS alarm associated
		 with the PPTP Ethernet UNI OMCI ME of 983.2 

		Applicable for both BPON and GPON.

		For ISAM4.0.10 - stays the same as latest FGU4.x  "
	::= { bponLanEtherPortOpstatEntry 4 }

bponLanEtherPortOpstatPoECapabilities  OBJECT-TYPE
	SYNTAX 	OCTET STRING (SIZE(3))
	ACCESS	read-only
	STATUS	mandatory
	DESCRIPTION 
		" Indicates the PoE capabilities of the port.
		  This is a bitmap where Bit 1 = LSB and Bit 24 = MSB.  The 16 least significant
		  bits map directly to OMCI attribute (i.e. PoE Capabilities of PoE Control ME).  The 8
		  most significant bits are populated by the OLT agent to convey extra information
		  for the manager (for user interface).

		  Bit meanings are as follows:

		  Bit 1 -	0 means PSE pinout is FIXED.
			1 means PSE pinout is CONTROLLABLE.
		  Bits 2..16 - reserved for future standardization - no meaning (ignore)
		  Bit 17 -	0 means this response came directly from the ONT
			1 means UNKNOWN (because OLT cannot communicate with ONT for OMCI discovery purposes).
		  Bit 18 -	0 means ONT supports GET of this attribute
			1 means that ONT does NOT support GET of this attribute.
		  Bits 19..24 - no meaning (ignore)  

		  Default = all bits zero except Bit 17 equals 1 (i.e. UNKNOWN).

		  As of ISAM4.4, this attribute is SUPPORTED.  "
	::= { bponLanEtherPortOpstatEntry 5 }

bponLanEtherPortOpstatPowerPairPinoutActual  OBJECT-TYPE
	SYNTAX 	INTEGER
	ACCESS	read-only
	STATUS	mandatory
	DESCRIPTION 
		" Indicates the actual Power Pair Pinout of the port.
		  Maps to a GET of OMCI attribute (i.e. Power Pair Pinout Control of PoE Control ME).

		  0 = Pinout Alternative A (signal pairs).
		  1 = Pinout Alternative B (spare pairs).
		  254 = UNKNOWN - (because OLT cannot communicate with ONT for OMCI discovery purposes).
		  255 = NOSUPPORT - means that ONT does NOT support GET of this attribute.

		  Default = 254 = UNKNOWN - (because OLT cannot communicate with ONT for OMCI discovery purposes).

		As of ISAM4.4, this attribute is SUPPORTED.  "
	::= { bponLanEtherPortOpstatEntry 6 }

bponLanEtherPortOpstatPowerDetectionStatus  OBJECT-TYPE
	SYNTAX 	INTEGER
	ACCESS	read-only
	STATUS	mandatory
	DESCRIPTION 
		" Indicates the power detection status of the port.
		  Maps to a GET of OMCI attribute (i.e. Power Detection Status of PoE Control ME).

		  0 = PSE Disabled.
		  1 = PSE Searching.
		  2 = PSE Delivering Power.
		  3 = PSE Test Mode.
		  4 = PSE Fault Detected.
		  5 = PSE Implementation Specific Fault Detected.
		  254 = UNKNOWN - (because OLT cannot communicate with ONT for OMCI discovery purposes).
		  255 = NOSUPPORT - means that ONT does NOT support GET of this attribute.

		  Default = 254 = UNKNOWN - (because OLT cannot communicate with ONT for OMCI discovery purposes).

		As of ISAM4.4, this attribute is SUPPORTED.  "
	::= { bponLanEtherPortOpstatEntry 7 }

bponLanEtherPortOpstatPowerClassStatus  OBJECT-TYPE
	SYNTAX 	INTEGER
	ACCESS	read-only
	STATUS	mandatory
	DESCRIPTION 
		" Indicates the PD class of the detected PD for the port.
		  Maps to a GET of OMCI attribute (i.e. Power Classification Status of PoE Control ME).

		  0 = NOSUPPORT - means that ONT does NOT support this attribute. Could be deduced because ONT 
		        rejected a GET or because ONT explicitly returned value of 0 (meaning undefined).
		  1 = Class 0 PD.
		  2 = Class 1 PD.
		  3 = Class 2 PD.
		  4 = Class 3 PD.
		  5 = Class 4 PD.
		  254 = UNKNOWN - (because OLT cannot communicate with ONT for OMCI discovery purposes).

		  Default = 254 = UNKNOWN - (because OLT cannot communicate with ONT for OMCI discovery purposes).

		As of ISAM4.4, this attribute is SUPPORTED.  "
	::= { bponLanEtherPortOpstatEntry 8 }

-- *********************************************
--
-- GPON LAN ETHERNET PERFORMANCE MONITOR CURRENT INTERVAL TABLE
--
-- This is a new table beginning with FGU4.2.
-- This current interval table contains various statistics collected
-- at an ONT's Ethernet interface during the current 15 minute interval 
-- of operation.  
--
-- An instance of this table is auto-created/deleted in accordance with the 
-- 'PM Collect Indicator' setting of the Ethernet UNI.
--
-- For GETs of table attributes, the OLT must go directly to the ONT (via OMCI)
-- in order to acquire fresh current counts. 
--
-- For ISAM4.0.10, this table is being re-used. 
-- Noted which attributes are relevant for ISAM4.0.10 
-- 
--
--	For GPON - SUPPORTED as of ISAM4.0.10
--	For XG-PON1 - SUPPORTED as of ISAM4.6.02
--	For NG-PON2 - SUPPORTED as of ISAM5.2
--
-- *********************************************


gponLanEtherCurrentIntervalTable  OBJECT-TYPE
	SYNTAX SEQUENCE OF GponLanEtherCurrentIntervalEntry
	ACCESS	not-accessible
	STATUS	mandatory
	::= { bponLanGroup 7 }


gponLanEtherCurrentIntervalEntry  OBJECT-TYPE
	SYNTAX 	GponLanEtherCurrentIntervalEntry
	ACCESS	not-accessible
	STATUS	mandatory
	DESCRIPTION 
		"An entry in the Gpon Lan Ethernet CurrentInterval 
		 Table. "
	INDEX	{ gponLanEtherCurrentIntervalOntIndex, 
		   gponLanEtherCurrentIntervalSpIndex }
	::= { gponLanEtherCurrentIntervalTable 1 }

GponLanEtherCurrentIntervalEntry ::= SEQUENCE {
	gponLanEtherCurrentIntervalOntIndex			IfIndex,
	gponLanEtherCurrentIntervalSpIndex			SpIndex,
	gponLanEtherCurrentIntervalValidInd			Boolean,
	gponLanEtherCurrentIntervalFCSEs			Counter,
	gponLanEtherCurrentIntervalECs			Counter,
	gponLanEtherCurrentIntervalLCs			Counter,
	gponLanEtherCurrentIntervalFTLs			Counter,
	gponLanEtherCurrentIntervalRBOs			Counter,
	gponLanEtherCurrentIntervalTBOs			Counter,
	gponLanEtherCurrentIntervalSCFs			Counter,
	gponLanEtherCurrentIntervalMCFs			Counter,
	gponLanEtherCurrentIntervalSQEs			Counter,
	gponLanEtherCurrentIntervalDTs			Counter,
	gponLanEtherCurrentIntervalIMTEs			Counter,
	gponLanEtherCurrentIntervalCSEs			Counter,
	gponLanEtherCurrentIntervalAEs			Counter,
	gponLanEtherCurrentIntervalIMREs			Counter

}


gponLanEtherCurrentIntervalOntIndex  OBJECT-TYPE
	SYNTAX 	IfIndex
	ACCESS	read-only
	STATUS	mandatory
	DESCRIPTION 
		"Each row is indexed by the ifIndex of the ONT.

		For ISAM4.0.10 - stays the same as latest FGU4.x  "
	::= { gponLanEtherCurrentIntervalEntry 1 }

gponLanEtherCurrentIntervalSpIndex  OBJECT-TYPE
	SYNTAX 	SpIndex
	ACCESS	read-only
	STATUS	mandatory
	DESCRIPTION 
		"Each row is also indexed by a number that
		 contains the slot number and port number
 		 within the ONT.

		For ISAM4.0.10 - stays the same as latest FGU4.x "
	::= { gponLanEtherCurrentIntervalEntry 2 }


gponLanEtherCurrentIntervalValidInd  OBJECT-TYPE
	SYNTAX 	Boolean
	ACCESS	read-only
	STATUS	mandatory
	DESCRIPTION 
		"Indicates whether or not this CurrentInterval contains
		 valid PM counts. 

		 As of FGU4.2, NOT SUPPORTED

		For ISAM4.0.10 - stays the same as latest FGU4.x "
	::= { gponLanEtherCurrentIntervalEntry 3 }


gponLanEtherCurrentIntervalFCSEs  OBJECT-TYPE
	SYNTAX 	Counter
	ACCESS	read-only
	STATUS	mandatory
	DESCRIPTION 
		"A count of Frame Check Sequence(FCS)Errors.

		For ISAM4.0.10 - stays the same as latest FGU4.x "
	::= { gponLanEtherCurrentIntervalEntry 4 }

gponLanEtherCurrentIntervalECs  OBJECT-TYPE
	SYNTAX 	Counter
	ACCESS	read-only
	STATUS	mandatory
	DESCRIPTION 
		"A count of Excessive Collisions.

		For ISAM4.0.10 - stays the same as latest FGU4.x "
	::= { gponLanEtherCurrentIntervalEntry 5 }

gponLanEtherCurrentIntervalLCs  OBJECT-TYPE
	SYNTAX 	Counter
	ACCESS	read-only
	STATUS	mandatory
	DESCRIPTION 
		"A count of Late Collisions.

		For ISAM4.0.10 - stays the same as latest FGU4.x "
	::= { gponLanEtherCurrentIntervalEntry 6 }

gponLanEtherCurrentIntervalFTLs  OBJECT-TYPE
	SYNTAX 	Counter
	ACCESS	read-only
	STATUS	mandatory
	DESCRIPTION 
		"A count of Frames that are Too Long.

		For ISAM4.0.10 - stays the same as latest FGU4.x "
	::= { gponLanEtherCurrentIntervalEntry 7 }

gponLanEtherCurrentIntervalRBOs  OBJECT-TYPE
	SYNTAX 	Counter
	ACCESS	read-only
	STATUS	mandatory
	DESCRIPTION 
		"A count of Receive Buffer Overflows.

		For ISAM4.0.10 - stays the same as latest FGU4.x "
	::= { gponLanEtherCurrentIntervalEntry 8 }

gponLanEtherCurrentIntervalTBOs  OBJECT-TYPE
	SYNTAX 	Counter
	ACCESS	read-only
	STATUS	mandatory
	DESCRIPTION 
		"A count of Transmit Buffer Overflows.

		For ISAM4.0.10 - stays the same as latest FGU4.x "
	::= { gponLanEtherCurrentIntervalEntry 9 }

gponLanEtherCurrentIntervalSCFs  OBJECT-TYPE
	SYNTAX 	Counter
	ACCESS	read-only
	STATUS	mandatory
	DESCRIPTION 
		"A count of successfully transmitted
		 Single Collision Frames.

		For ISAM4.0.10 - stays the same as latest FGU4.x "
	::= { gponLanEtherCurrentIntervalEntry 10 }

gponLanEtherCurrentIntervalMCFs  OBJECT-TYPE
	SYNTAX 	Counter
	ACCESS	read-only
	STATUS	mandatory
	DESCRIPTION 
		"A count of successfully transmitted
		 Multiple Collision Frames.

		For ISAM4.0.10 - stays the same as latest FGU4.x "
	::= { gponLanEtherCurrentIntervalEntry 11 }


gponLanEtherCurrentIntervalSQEs  OBJECT-TYPE
	SYNTAX 	Counter
	ACCESS	read-only
	STATUS	mandatory
	DESCRIPTION 
		"A count of SQE Test Error messages generated.

		For ISAM4.0.10 - stays the same as latest FGU4.x "
	::= { gponLanEtherCurrentIntervalEntry 12 }

gponLanEtherCurrentIntervalDTs  OBJECT-TYPE
	SYNTAX 	Counter
	ACCESS	read-only
	STATUS	mandatory
	DESCRIPTION 
		"A count of frames delayed due to Deferred
		 Transmission.

		For ISAM4.0.10 - stays the same as latest FGU4.x "
	::= { gponLanEtherCurrentIntervalEntry 13 }

gponLanEtherCurrentIntervalIMTEs  OBJECT-TYPE
	SYNTAX 	Counter
	ACCESS	read-only
	STATUS	mandatory
	DESCRIPTION 
		"A count of unsuccessfully transmitted frames
		 due to Internal MAC Transmit Error.

		For ISAM4.0.10 - stays the same as latest FGU4.x "
	::= { gponLanEtherCurrentIntervalEntry 14 }


gponLanEtherCurrentIntervalCSEs  OBJECT-TYPE
	SYNTAX 	Counter
	ACCESS	read-only
	STATUS	mandatory
	DESCRIPTION 
		"A count of Carrier Sense Errors.

		For ISAM4.0.10 - stays the same as latest FGU4.x "
	::= { gponLanEtherCurrentIntervalEntry 15 }

gponLanEtherCurrentIntervalAEs  OBJECT-TYPE
	SYNTAX 	Counter
	ACCESS	read-only
	STATUS	mandatory
	DESCRIPTION 
		"A count of frames having Alignment Errors.

		For ISAM4.0.10 - stays the same as latest FGU4.x "
	::= { gponLanEtherCurrentIntervalEntry 16 }

gponLanEtherCurrentIntervalIMREs  OBJECT-TYPE
	SYNTAX 	Counter
	ACCESS	read-only
	STATUS	mandatory
	DESCRIPTION 
		"A count of unsuccessfully received frames
		 due to Internal MAC Receive Error.

		For ISAM4.0.10 - stays the same as latest FGU4.x "
	::= { gponLanEtherCurrentIntervalEntry 17 }



-- *********************************************
--
-- GPON LAN ETHERNET PERFORMANCE MONITOR TCA THRESHOLD TABLE
--
-- This is a new table beginning with FGU4.2.
-- This table allows the manager to set TCA thresholds for various PMs
-- at an ONT's Ethernet interface.  
--
-- An instance of this table is auto-created/deleted in accordance with the 
-- 'PM Collect Indicator' setting of the Ethernet UNI.
--
-- NOTE: As of FGU4.2, this entire table is NOT SUPPORTED
--
-- For ISAM 4.0.10, this table continues to be NOT SUPPORTED.
--
--	For GPON - NOT SUPPORTED as of ISAM4.0.10
--	For XG-PON1 - NOT SUPPORTED as of ISAM4.6.02
--	For NG-PON2 - NOT SUPPORTED as of ISAM5.2
--
-- 
-- *********************************************


gponLanEtherTCAThresholdTable  OBJECT-TYPE
	SYNTAX SEQUENCE OF GponLanEtherTCAThresholdEntry
	ACCESS	not-accessible
	STATUS	mandatory
	::= { bponLanGroup 8 }


gponLanEtherTCAThresholdEntry  OBJECT-TYPE
	SYNTAX 	GponLanEtherTCAThresholdEntry
	ACCESS	not-accessible
	STATUS	mandatory
	DESCRIPTION 
		"An entry in the Gpon Lan Ethernet TCAThreshold 
		 Table. "
	INDEX	{ gponLanEtherTCAThresholdOntIndex, 
		   gponLanEtherTCAThresholdSpIndex }
	::= { gponLanEtherTCAThresholdTable 1 }

GponLanEtherTCAThresholdEntry ::= SEQUENCE {
	gponLanEtherTCAThresholdOntIndex			IfIndex,
	gponLanEtherTCAThresholdSpIndex			SpIndex,
	gponLanEtherTCAEnable				INTEGER,
	gponLanEtherTCAThresholdFCSEs			Threshold,
	gponLanEtherTCAThresholdECs			Threshold,
	gponLanEtherTCAThresholdLCs			Threshold,
	gponLanEtherTCAThresholdFTLs			Threshold,
	gponLanEtherTCAThresholdRBOs			Threshold,
	gponLanEtherTCAThresholdTBOs			Threshold,
	gponLanEtherTCAThresholdSCFs			Threshold,
	gponLanEtherTCAThresholdMCFs			Threshold,
	gponLanEtherTCAThresholdSQEs			Threshold,
	gponLanEtherTCAThresholdDTs			Threshold,
	gponLanEtherTCAThresholdIMTEs			Threshold,
	gponLanEtherTCAThresholdCSEs			Threshold,
	gponLanEtherTCAThresholdAEs			Threshold,
	gponLanEtherTCAThresholdIMREs			Threshold

}


gponLanEtherTCAThresholdOntIndex  OBJECT-TYPE
	SYNTAX 	IfIndex
	ACCESS	read-only
	STATUS	mandatory
	DESCRIPTION 
		"Each row is indexed by the ifIndex of the ONT.  "
	::= { gponLanEtherTCAThresholdEntry 1 }

gponLanEtherTCAThresholdSpIndex  OBJECT-TYPE
	SYNTAX 	SpIndex
	ACCESS	read-only
	STATUS	mandatory
	DESCRIPTION 
		"Each row is also indexed by a number that
		 contains the slot number and port number
 		 within the ONT. "
	::= { gponLanEtherTCAThresholdEntry 2 }


gponLanEtherTCAEnable  OBJECT-TYPE
	SYNTAX 	INTEGER
	ACCESS	read-write
	STATUS	mandatory
	DESCRIPTION 
		"Allows the manager to enable/disable the reporting of
		 TCAs for this Ethernet port. 

	
		  1 = TCA's enabled
		  2 = TCA's disabled

		 Default = 2 = disabled. "
	::= { gponLanEtherTCAThresholdEntry 3 }


gponLanEtherTCAThresholdFCSEs  OBJECT-TYPE
	SYNTAX 	Threshold
	ACCESS	read-write
	STATUS	mandatory
	DESCRIPTION 
		"TCA setting for Frame Check Sequence(FCS)Errors.
		 A value of 4294967295 means that this threshold is disabled.

		 Default = 4294967295 "
	::= { gponLanEtherTCAThresholdEntry 4 }

gponLanEtherTCAThresholdECs  OBJECT-TYPE
	SYNTAX 	Threshold
	ACCESS	read-write
	STATUS	mandatory
	DESCRIPTION 
		"TCA setting for Excessive Collisions.
		 A value of 4294967295 means that this threshold is disabled.

		 Default = 4294967295 "
	::= { gponLanEtherTCAThresholdEntry 5 }

gponLanEtherTCAThresholdLCs  OBJECT-TYPE
	SYNTAX 	Threshold
	ACCESS	read-write
	STATUS	mandatory
	DESCRIPTION 
		"TCA setting for Late Collisions.
		 A value of 4294967295 means that this threshold is disabled.

		 Default = 4294967295 "
	::= { gponLanEtherTCAThresholdEntry 6 }

gponLanEtherTCAThresholdFTLs  OBJECT-TYPE
	SYNTAX 	Threshold
	ACCESS	read-write
	STATUS	mandatory
	DESCRIPTION 
		"TCA setting for Frames that are Too Long. 
		 A value of 4294967295 means that this threshold is disabled.

		 Default = 4294967295 "
	::= { gponLanEtherTCAThresholdEntry 7 }

gponLanEtherTCAThresholdRBOs  OBJECT-TYPE
	SYNTAX 	Threshold
	ACCESS	read-write
	STATUS	mandatory
	DESCRIPTION 
		"TCA setting for Receive Buffer Overflows.
		 A value of 4294967295 means that this threshold is disabled.

		 Default = 4294967295 "
	::= { gponLanEtherTCAThresholdEntry 8 }

gponLanEtherTCAThresholdTBOs  OBJECT-TYPE
	SYNTAX 	Threshold
	ACCESS	read-write
	STATUS	mandatory
	DESCRIPTION 
		"TCA setting for Transmit Buffer Overflows.
		 A value of 4294967295 means that this threshold is disabled.

		 Default = 4294967295 "
	::= { gponLanEtherTCAThresholdEntry 9 }

gponLanEtherTCAThresholdSCFs  OBJECT-TYPE
	SYNTAX 	Threshold
	ACCESS	read-write
	STATUS	mandatory
	DESCRIPTION 
		"TCA setting for successfully transmitted
		 Single Collision Frames.
		 A value of 4294967295 means that this threshold is disabled.

		 Default = 4294967295 "
	::= { gponLanEtherTCAThresholdEntry 10 }

gponLanEtherTCAThresholdMCFs  OBJECT-TYPE
	SYNTAX 	Threshold
	ACCESS	read-write
	STATUS	mandatory
	DESCRIPTION 
		"TCA setting for successfully transmitted
		 Multiple Collision Frames.
		 A value of 4294967295 means that this threshold is disabled.

		 Default = 4294967295 "
	::= { gponLanEtherTCAThresholdEntry 11 }


gponLanEtherTCAThresholdSQEs  OBJECT-TYPE
	SYNTAX 	Threshold
	ACCESS	read-write
	STATUS	mandatory
	DESCRIPTION 
		"TCA setting for SQE Test Error messages generated.
		 A value of 4294967295 means that this threshold is disabled.

		 Default = 4294967295 "
	::= { gponLanEtherTCAThresholdEntry 12 }

gponLanEtherTCAThresholdDTs  OBJECT-TYPE
	SYNTAX 	Threshold
	ACCESS	read-write
	STATUS	mandatory
	DESCRIPTION 
		"TCA setting for frames delayed due to Deferred
		 Transmission.
		 A value of 4294967295 means that this threshold is disabled.

		 Default = 4294967295 "
	::= { gponLanEtherTCAThresholdEntry 13 }

gponLanEtherTCAThresholdIMTEs  OBJECT-TYPE
	SYNTAX 	Threshold
	ACCESS	read-write
	STATUS	mandatory
	DESCRIPTION 
		"TCA setting for unsuccessfully transmitted frames
		 due to Internal MAC Transmit Error.
		 A value of 4294967295 means that this threshold is disabled.

		 Default = 4294967295 "
	::= { gponLanEtherTCAThresholdEntry 14 }


gponLanEtherTCAThresholdCSEs  OBJECT-TYPE
	SYNTAX 	Threshold
	ACCESS	read-write
	STATUS	mandatory
	DESCRIPTION 
		"TCA setting for Carrier Sense Errors.
		 A value of 4294967295 means that this threshold is disabled.

		 Default = 4294967295 "
	::= { gponLanEtherTCAThresholdEntry 15 }

gponLanEtherTCAThresholdAEs  OBJECT-TYPE
	SYNTAX 	Threshold
	ACCESS	read-write
	STATUS	mandatory
	DESCRIPTION 
		"TCA setting for frames having Alignment Errors.
		 A value of 4294967295 means that this threshold is disabled.

		 Default = 4294967295 "
	::= { gponLanEtherTCAThresholdEntry 16 }

gponLanEtherTCAThresholdIMREs  OBJECT-TYPE
	SYNTAX 	Threshold
	ACCESS	read-write
	STATUS	mandatory
	DESCRIPTION 
		"TCA setting for unsuccessfully received frames
		 due to Internal MAC Receive Error.
		 A value of 4294967295 means that this threshold is disabled.

		 Default = 4294967295 "
	::= { gponLanEtherTCAThresholdEntry 17 }


-- *********************************************
--
-- BPON CES PORT TABLE
--
-- This is a new table beginning with FGU2.5.
-- This table contains a row for each provisioned CES port on a
-- specific ONT.  This table contains attributes that describe the
-- physical port behavior. Rows are created dynamically by operator 
-- Create-and-go.  Can change some RW parameters for a row, once 
-- CES port is created.  
--
-- For FGU4.3, this table is supported (for pseudowires).
--
-- For ISAM4.0.10, this table is being re-used. However, for ISAM 4.0.10,
-- rows are auto-created by agent.  The number of rows auto-created is
-- determined from the bponOntPlanCardNumPorts attribute in the
-- bponOntPlanCardTable.
-- Noted which attributes are relevant for ISAM4.0.10
--
--
--	For GPON - SUPPORTED as of ISAM4.0.10
--	For XG-PON1 - SUPPORTED as of ISAM4.6.02
--	For NG-PON2 - NOT SUPPORTED as of ISAM5.2 (CES Card Type is NOT SUPPORTED)
--  
-- 
-- *********************************************

bponCesPortTable  OBJECT-TYPE
	SYNTAX SEQUENCE OF BponCesPortEntry
	ACCESS	not-accessible
	STATUS	mandatory
	::= { bponCesGroup 1 }


bponCesPortEntry  OBJECT-TYPE
	SYNTAX 	BponCesPortEntry
	ACCESS	not-accessible
	STATUS	mandatory
	INDEX	{ bponCesPortOntIndex,
		  bponCesPortSpIndex 
                }
	::= { bponCesPortTable 1 }

BponCesPortEntry ::= SEQUENCE {
	bponCesPortOntIndex		IfIndex,
	bponCesPortSpIndex			SpIndex,
	bponCesPortRowStatus		RowStatus,
	bponCesPortStructureInd		INTEGER,
	bponCesPortAdminState		AdminState,
	bponCesPortOperState			OperState,
	bponCesPortCesLoopConfig		INTEGER,
	bponCesPortFraming		INTEGER,
	bponCesPortEncoding		INTEGER,
	bponCesPortLineLength		INTEGER,
	bponCesPortDs1Mode		INTEGER,
	bponCesPortArc			INTEGER,
	bponCesPortArcInterval		INTEGER,
	bponCesPortPmCollectInd		INTEGER,
	bponCesPortNumPMIntervals	INTEGER,
	bponCesPortPwrShedOverride	Boolean
}


bponCesPortOntIndex  OBJECT-TYPE
	SYNTAX 	IfIndex
	ACCESS	read-only
	STATUS	mandatory
	DESCRIPTION 
		"Each row is indexed by the ifIndex of the ONT 

		For ISAM4.0.10 - stays the same as latest FGU4.x "
	::= { bponCesPortEntry 1 }


bponCesPortSpIndex  OBJECT-TYPE
	SYNTAX 	SpIndex
	ACCESS	read-only
	STATUS	mandatory
	DESCRIPTION 
		"Each row is also indexed by a number that
		 contains the slot number and port number
		 within the ONT.

		For ISAM4.0.10 - stays the same as latest FGU4.x "
	::= { bponCesPortEntry 2 }



bponCesPortRowStatus  OBJECT-TYPE
	SYNTAX 	RowStatus
	ACCESS	read-write
	STATUS	mandatory
	DESCRIPTION 
		"Prior to ISAM 4.0.10, all rows instantiated using 'create-and-go' to
		 provision a CES port. Set to 'destroy' to delete
		 a CES port.


		 For ISAM 4.0.10, this attribute is NOT SUPPORTED.  "
	::= { bponCesPortEntry 3 }


bponCesPortStructureInd  OBJECT-TYPE
	SYNTAX 	INTEGER
	ACCESS	read-write
	STATUS	mandatory
	DESCRIPTION 
		" This is used to designate whether the DS1/E1 port
		 will operate in Structured or Unstructured Mode.
		 From OMCI perspective, this determines whether 
		 Interworking TP Pointer points to PPTP CES UNI or
 		 to DS0 timeslot map ME - Nx64kbps subport TP.

		 1 = Unstructured
		 2 = Octet alligned unstructured (NOT SUPPORTED)
		 3 = Structured
		 Default = 1 Unstructured

		 Also, from OMCI perspective, this choice gets reflected in 
		 Service Type attribute of Pseudowire Termination Point ME
		 (for all CES services on a specific CES UNI).

		 For FGU4.3, both Unstructured and Structured supported

		 Modification is PERMITTED - but only if NO pseudowire service is 
		 defined on this CES port.

		For ISAM4.0.10 - stays the same as latest FGU4.x "
	::= { bponCesPortEntry 4 }



bponCesPortAdminState  OBJECT-TYPE
	SYNTAX 	AdminState
	ACCESS	read-write
	STATUS	mandatory
	DESCRIPTION 
		"For OMCI messaging, this attribute translates
		 into Admin State for the PPTP CES UNI.  Setting it
		 to 'locked' deactivates the particulat DS1.
		 Modification permitted even after row
		 becomes 'active'.
		 Default = 1 = locked

		 NOTE: ONT uses unlocked setting of this attribute as trigger
		 	to update Resolute hardware.

		For ISAM4.0.10 - this attribute is NOT SUPPORTED  "
	::= { bponCesPortEntry 5 }

bponCesPortOperState  OBJECT-TYPE
	SYNTAX 	OperState
	ACCESS	read-only
	STATUS	mandatory
	DESCRIPTION 
		"Indicates operational state of the
		 CES port. State is related to ability of port
		  to perform its function (e.g. whether service
		  affecting alarm is present).
		  Default = 0 = Enabled

		For ISAM4.0.10 - this attribute is NOT SUPPORTED "
	::= { bponCesPortEntry 6 }


bponCesPortCesLoopConfig  OBJECT-TYPE
	SYNTAX 	INTEGER
	ACCESS	read-write
	STATUS	mandatory
	DESCRIPTION 
		"DS1/E1 Loopback configuration options:
		 Used to place an B-ONT's DS1 into
		 a specific loopback configuration.

		 noLoopback(0),
		 payloadLoopback (1), - not implemented
		 lineLoopback (2),
		 inwardLoopback(3),
		 outwardLoopback (4) - not implemented,
		 linePlusInwardLoopback (5) - not implemented,

		 For FGU4.3, B-ONT only supports options:
		 0 = No Loopback
		 2 = Line Loopback
		 3 = Inward Loopback

		 Modification permitted even after row becomes
		 'active'.
		 Default = 0

		 NOTE: Any edit of this parameter is service-affecting.

		 NOTE: The CES UNI must be Admin In-Service in order to actually implement
		            a requested loopback.

		For ISAM4.0.10 - stays the same as latest FGU4.x  "
	::= { bponCesPortEntry 7 }


bponCesPortFraming  OBJECT-TYPE
	SYNTAX 	INTEGER
	ACCESS	read-write
	STATUS	mandatory
	DESCRIPTION 
		"FGU4.3 should support following options:

		 0 = Extended Superframe -ESF- (only for DS1)
		 1 = Superframe -SF- (only for DS1),
		 2 = Unframed (for both DS1 and E1),
		 16 = PCM30 (only for E1)
		 17 = PCM31 (only for E1)
		 
		 Modification permitted even after row becomes
		 'active'.
		 Default = 2 = Unframed

		 If line is set to Unstructured, then this attribute can only
		 be set to Unframed.

		 If line is set to Structured, then this attribute can NOT
		 be set to Unframed.

		 NOTE: Any edit of this parameter is service-affecting.

		For ISAM4.0.10 - stays the same as latest FGU4.x "
	::= { bponCesPortEntry 8 }

bponCesPortEncoding  OBJECT-TYPE
	SYNTAX 	INTEGER 
	ACCESS	read-write
	STATUS	mandatory
	DESCRIPTION 
		"DS1 Encoding scheme options:

		 0 = B8ZS(only for DS1),
		 1 = AMI (for both DS1 and E1),
		 2 = HDB3 (only for E1),

		 Default = 0

		 NOTE: Any edit of this parameter is service-affecting.

		For ISAM4.0.10 - stays the same as latest FGU4.x "
	::= { bponCesPortEntry 9 }

bponCesPortLineLength  OBJECT-TYPE
	SYNTAX 	INTEGER 
	ACCESS	read-write
	STATUS	mandatory
	DESCRIPTION 
		"Provides the length of the twisted pair cable from
		 the B-ONT to the DS1 cross-connect as follows:

		For DS1:
		6 = 0 - 133 ft
		7 = 133 - 266 ft
		8 = 266 - 399 ft
		9 = 399 - 533 ft
	   	10 = 533 - 655 ft
		11 = 0 dB (NOT SUPPORTED by Resolute for FGU4.3)
		12 = 7.5 dB
		13 = 15 dB
		14 = 22.5 dB

		For E1:
		32 = 75 ohms
		33 = 120 ohms

		 Modification permitted even after row becomes
		 'active'.
		 Default = 6

		 NOTE: Any edit of this parameter is service-affecting.

		For ISAM4.0.10 - stays the same as latest FGU4.x "
	::= { bponCesPortEntry 10 }

bponCesPortDs1Mode  OBJECT-TYPE
	SYNTAX 	INTEGER 
	ACCESS	read-write
	STATUS	mandatory
	DESCRIPTION 
		"Used to designate DS1 Mode as follows:

		 0 = Mode 1 - DS1 CPE short haul
		 1 = Mode 2
		 2 = Mode 3
		 3 = Mode 4

		 Attribute is not relevant for E1.
		 For FGU4.3, only allowed value is 0.
		 Default = 0

		For ISAM4.0.10 - stays the same as latest FGU4.x "
	::= { bponCesPortEntry 11 }


bponCesPortArc  OBJECT-TYPE
	SYNTAX 	INTEGER
	ACCESS	read-write
	STATUS	mandatory
	DESCRIPTION 
		"Alarm Reporting Control.  Valid values are:

		0 = Off (meaning alarm reporting allowed
		             immediately)
		1 = On (meaning alarm reporting inhibited until
		             valid signal is detected for time period
		             specified by ARC Interval).
		 Default = 1  - function is not implemented or supported.

		For ISAM4.0.10 - stays the same as latest FGU4.x"
	::= { bponCesPortEntry 12 }


bponCesPortArcInterval  OBJECT-TYPE
	SYNTAX 	INTEGER
	ACCESS	read-write
	STATUS	mandatory
	DESCRIPTION 
		"Alarm Reporting Control Interval (in minutes).

		 0 means alarms are inhibited indefinitely (if ARC
		   is set to inhibited)
		 Default = 0  - function is not implemented or supported.

		For ISAM4.0.10 - stays the same as latest FGU4.x"
	::= { bponCesPortEntry 13 }


bponCesPortPmCollectInd  OBJECT-TYPE
	SYNTAX 	INTEGER
	ACCESS	read-write
	STATUS	mandatory
	DESCRIPTION 
		" This indicates whether CES Performance Monitors
		   should be collected for this CES Port.
	
		  1 = PM collection enabled
		  2 = PM collection disabled

		 Default = 2 = disabled

		For ISAM4.0.10 - stays the same as latest FGU4.x  "
	::= { bponCesPortEntry 14 }

bponCesPortNumPMIntervals  OBJECT-TYPE
	SYNTAX 	INTEGER
	ACCESS	read-only
	STATUS	mandatory
	DESCRIPTION 
		" Indicates the number of rows currently present
		  in the bponCesPortTrafficIntervalTable.  This
		  is for convenience of the EMS, so that it can
		 quickly determine how many rows should be 
		 uploaded.

		For ISAM4.0.10 - stays the same as latest FGU4.x   "
	::= { bponCesPortEntry 15 }

bponCesPortPwrShedOverride  OBJECT-TYPE
	SYNTAX 	Boolean
	ACCESS	read-write
	STATUS	mandatory
	DESCRIPTION 
		"Allows setting as follows:

		 TRUE = 1 = port excluded from CES class power shedding
		 FALSE = 0 = port included in CES class power shedding

		 Default = 0 = FALSE 

		 As of FGU4.4, this is Supported.

		For ISAM4.0.10 - stays the same as latest FGU4.x   "
	::= { bponCesPortEntry 16 }



-- *********************************************
--
-- BPON CES PERFORMANCE MONITOR INTERVAL TABLE
--
-- This is a new table beginning with FGU2.5.
-- This interval table contains various near-end statistics 
-- collected at an ONT/ONU  DS1/E1 interface over the previous 
-- 8 hours of operation.  The past 8 hours are broken into 32  
-- completed 15 minute intervals.  Each row in this table
-- represents one such interval  for one specific DS1/E1 port 
-- on a specific ONT/ONU. 
--
-- For FGU4.3, this table is supported (for pseudowires).
--
-- For ISAM4.0.10, this table is being re-used. 
-- Noted which attributes are relevant for ISAM4.0.10
-- 
--
--	For GPON - SUPPORTED as of ISAM4.0.10
--	For XG-PON1 - SUPPORTED as of ISAM4.6.02
--	For NG-PON2 - NOT SUPPORTED as of ISAM5.2 (CES Card Type is NOT SUPPORTED)
--  
-- *********************************************

bponCesIntervalTable  OBJECT-TYPE
	SYNTAX SEQUENCE OF BponCesIntervalEntry
	ACCESS	not-accessible
	STATUS	mandatory
	::= { bponCesGroup 4 }


bponCesIntervalEntry  OBJECT-TYPE
	SYNTAX 	BponCesIntervalEntry
	ACCESS	not-accessible
	STATUS	mandatory
	DESCRIPTION 
		"An entry in the bpon Ces Interval 
		 Table. "
	INDEX	{ bponCesIntervalOntIndex,
		  bponCesIntervalSpIndex, 
		  bponCesIntervalNumber }
	::= { bponCesIntervalTable 1 }

BponCesIntervalEntry ::= SEQUENCE {
	bponCesIntervalOntIndex			IfIndex,
	bponCesIntervalSpIndex			SpIndex,
	bponCesIntervalNumber			INTEGER,
	bponCesIntervalValidInd			Boolean,
	bponCesIntervalESs			Counter,
	bponCesIntervalSESs			Counter,
	bponCesIntervalBESs			Counter,
	bponCesIntervalUASs			Counter,
	bponCesIntervalCSSs			Counter
}


bponCesIntervalOntIndex  OBJECT-TYPE
	SYNTAX 	IfIndex
	ACCESS	read-only
	STATUS	mandatory
	DESCRIPTION 
		"Each row is indexed by the ifIndex of the ONT. "
	::= { bponCesIntervalEntry 1 }


bponCesIntervalSpIndex  OBJECT-TYPE
	SYNTAX 	SpIndex
	ACCESS	read-only
	STATUS	mandatory
	DESCRIPTION 
		"Each row is also indexed by a number that
		 contains the slot number and port number
 		 within the ONT.

		For ISAM4.0.10 - stays the same as latest FGU4.x "
	::= { bponCesIntervalEntry 2 }


bponCesIntervalNumber  OBJECT-TYPE
	SYNTAX 	INTEGER (1..32)
	ACCESS	read-only
	STATUS	mandatory
	DESCRIPTION 
		"A number between 1 and 24, where 1 is the most
		 recently completed 15 minute interval and 24
		 is the 15 minute interval completed 7 hours 
		 and 45 minutes prior to interval 1. 
		 OLT only stores up to 32 intervals.

		For ISAM4.0.10 - stays the same as latest FGU4.x "
	::= { bponCesIntervalEntry 3 }

bponCesIntervalValidInd  OBJECT-TYPE
	SYNTAX 	Boolean
	ACCESS	read-only
	STATUS	mandatory
	DESCRIPTION 
		"Indicates whether or not this interval contains
		 valid PM counts.

		 As of FGU4.3, this is NOT SUPPORTED.

		For ISAM4.0.10 - stays the same as latest FGU4.x  "
	::= { bponCesIntervalEntry 4 }

bponCesIntervalESs  OBJECT-TYPE
	SYNTAX 	Counter
	ACCESS	read-only
	STATUS	mandatory
	DESCRIPTION 
		"A count of Errored Seconds during this interval.

		For ISAM4.0.10 - stays the same as latest FGU4.x "
	::= { bponCesIntervalEntry 5 }

bponCesIntervalSESs  OBJECT-TYPE
	SYNTAX 	Counter
	ACCESS	read-only
	STATUS	mandatory
	DESCRIPTION 
		"A count of Severely Errored Seconds during this
		 interval.

		For ISAM4.0.10 - stays the same as latest FGU4.x "
	::= { bponCesIntervalEntry 6 }

bponCesIntervalBESs  OBJECT-TYPE
	SYNTAX 	Counter
	ACCESS	read-only
	STATUS	mandatory
	DESCRIPTION 
		"A count of Bursty Errored Seconds during this
		 interval.

		For ISAM4.0.10 - stays the same as latest FGU4.x "
	::= { bponCesIntervalEntry 7 }

bponCesIntervalUASs  OBJECT-TYPE
	SYNTAX 	Counter
	ACCESS	read-only
	STATUS	mandatory
	DESCRIPTION 
		"A count of Unavailable Seconds during this interval.

		For ISAM4.0.10 - stays the same as latest FGU4.x "
	::= { bponCesIntervalEntry 8 }

bponCesIntervalCSSs  OBJECT-TYPE
	SYNTAX 	Counter
	ACCESS	read-only
	STATUS	mandatory
	DESCRIPTION 
		"A count of Controlled Slip Seconds during this
		 interval.

		For ISAM4.0.10 - stays the same as latest FGU4.x "
	::= { bponCesIntervalEntry 9 }


-- *********************************************
--
-- BPON CES PERFORMANCE MONITOR CURRENT INTERVAL TABLE
--
-- This is a new table beginning with FGU4.3.
-- This current interval table contains near-end statistics collected
-- at an ONT's DS1/E1 during the current 15 minute interval 
-- of operation.  
--
-- An instance of this table is auto-created/deleted in accordance with the 
-- CES Traffic PM Collect Indicator' setting of the particular CES UNI.
--
-- For GETs of table attributes, the OLT must go directly to the ONT (via OMCI)
-- in order to acquire fresh current counts. 
--
-- For FGU4.3, this table is supported (for pseudowires).
--
-- For ISAM4.0.10, this table is being re-used. 
-- Noted which attributes are relevant for ISAM4.0.10
--
--
--	For GPON - SUPPORTED as of ISAM4.0.10
--	For XG-PON1 - SUPPORTED as of ISAM4.6.02
--	For NG-PON2 - NOT SUPPORTED as of ISAM5.2 (CES Card Type is NOT SUPPORTED)
--   
-- *********************************************

bponCesCurrentIntervalTable  OBJECT-TYPE
	SYNTAX SEQUENCE OF BponCesCurrentIntervalEntry
	ACCESS	not-accessible
	STATUS	mandatory
	::= { bponCesGroup 5 }


bponCesCurrentIntervalEntry  OBJECT-TYPE
	SYNTAX 	BponCesCurrentIntervalEntry
	ACCESS	not-accessible
	STATUS	mandatory
	DESCRIPTION 
		"An entry in the bpon Ces CurrentInterval 
		 Table. "
	INDEX	{ bponCesCurrentIntervalOntIndex,
		  bponCesCurrentIntervalSpIndex }
	::= { bponCesCurrentIntervalTable 1 }

BponCesCurrentIntervalEntry ::= SEQUENCE {
	bponCesCurrentIntervalOntIndex			IfIndex,
	bponCesCurrentIntervalSpIndex			SpIndex,
	bponCesCurrentIntervalValidInd			Boolean,
	bponCesCurrentIntervalESs			Counter,
	bponCesCurrentIntervalSESs			Counter,
	bponCesCurrentIntervalBESs			Counter,
	bponCesCurrentIntervalUASs			Counter,
	bponCesCurrentIntervalCSSs			Counter
}


bponCesCurrentIntervalOntIndex  OBJECT-TYPE
	SYNTAX 	IfIndex
	ACCESS	read-only
	STATUS	mandatory
	DESCRIPTION 
		"Each row is indexed by the ifIndex of the ONT.

		For ISAM4.0.10 - stays the same as latest FGU4.x "
	::= { bponCesCurrentIntervalEntry 1 }


bponCesCurrentIntervalSpIndex  OBJECT-TYPE
	SYNTAX 	SpIndex
	ACCESS	read-only
	STATUS	mandatory
	DESCRIPTION 
		"Each row is also indexed by a number that
		 contains the slot number and port number
 		 within the ONT.

		For ISAM4.0.10 - stays the same as latest FGU4.x "
	::= { bponCesCurrentIntervalEntry 2 }


bponCesCurrentIntervalValidInd  OBJECT-TYPE
	SYNTAX 	Boolean
	ACCESS	read-only
	STATUS	mandatory
	DESCRIPTION 
		"Indicates whether or not this CurrentInterval contains
		 valid PM counts.

		 As of FGU4.3, this is NOT SUPPORTED.

		For ISAM4.0.10 - stays the same as latest FGU4.x "
	::= { bponCesCurrentIntervalEntry 3 }

bponCesCurrentIntervalESs  OBJECT-TYPE
	SYNTAX 	Counter
	ACCESS	read-only
	STATUS	mandatory
	DESCRIPTION 
		"A count of Errored Seconds during this CurrentInterval.

		For ISAM4.0.10 - stays the same as latest FGU4.x "
	::= { bponCesCurrentIntervalEntry 4 }

bponCesCurrentIntervalSESs  OBJECT-TYPE
	SYNTAX 	Counter
	ACCESS	read-only
	STATUS	mandatory
	DESCRIPTION 
		"A count of Severely Errored Seconds during this
		 CurrentInterval.

		For ISAM4.0.10 - stays the same as latest FGU4.x "
	::= { bponCesCurrentIntervalEntry 5 }

bponCesCurrentIntervalBESs  OBJECT-TYPE
	SYNTAX 	Counter
	ACCESS	read-only
	STATUS	mandatory
	DESCRIPTION 
		"A count of Bursty Errored Seconds during this
		 CurrentInterval.

		For ISAM4.0.10 - stays the same as latest FGU4.x "
	::= { bponCesCurrentIntervalEntry 6 }

bponCesCurrentIntervalUASs  OBJECT-TYPE
	SYNTAX 	Counter
	ACCESS	read-only
	STATUS	mandatory
	DESCRIPTION 
		"A count of Unavailable Seconds during this CurrentInterval.

		For ISAM4.0.10 - stays the same as latest FGU4.x "
	::= { bponCesCurrentIntervalEntry 7 }

bponCesCurrentIntervalCSSs  OBJECT-TYPE
	SYNTAX 	Counter
	ACCESS	read-only
	STATUS	mandatory
	DESCRIPTION 
		"A count of Controlled Slip Seconds during this
		 CurrentInterval.

		For ISAM4.0.10 - stays the same as latest FGU4.x "
	::= { bponCesCurrentIntervalEntry 8 }


-- *********************************************
--
-- GPON CES PORT PERFORMANCE MONITOR TCA THRESHOLD TABLE
--
-- This is a new table beginning with FGU4.3.
-- This table allows the manager to set TCA thresholds for various PMs
-- at an ONT's CES interface.  
--
-- An instance of this table is auto-created/deleted in accordance with the 
-- 'PM Collect Indicator' setting of the CES UNI.
--
-- NOTE: As of FGU4.3, this entire table is NOT SUPPORTED
--
-- As of ISAM 4.0.10, this table continues to be NOT SUPPORTED.
-- 
--
--	For GPON - NOY SUPPORTED as of ISAM4.0.10
--	For XG-PON1 - NOT SUPPORTED as of ISAM4.6.02
--	For NG-PON2 - NOT SUPPORTED as of ISAM5.2 
--  
-- *********************************************


gponCesPortTCAThresholdTable  OBJECT-TYPE
	SYNTAX SEQUENCE OF GponCesPortTCAThresholdEntry
	ACCESS	not-accessible
	STATUS	mandatory
	::= { bponCesGroup 6 }


gponCesPortTCAThresholdEntry  OBJECT-TYPE
	SYNTAX 	GponCesPortTCAThresholdEntry
	ACCESS	not-accessible
	STATUS	mandatory
	DESCRIPTION 
		"An entry in the Gpon CES Port TCA Threshold 
		 Table. "
	INDEX	{ gponCesPortTCAThresholdOntIndex, 
		   gponCesPortTCAThresholdSpIndex }
	::= { gponCesPortTCAThresholdTable 1 }

GponCesPortTCAThresholdEntry ::= SEQUENCE {
	gponCesPortTCAThresholdOntIndex			IfIndex,
	gponCesPortTCAThresholdSpIndex			SpIndex,
	gponCesPortTCAEnable				INTEGER,
	gponCesPortTCAThresholdESs			Threshold,
	gponCesPortTCAThresholdSESs			Threshold,
	gponCesPortTCAThresholdBESs			Threshold,
	gponCesPortTCAThresholdUASs			Threshold,
	gponCesPortTCAThresholdCSSs			Threshold
}


gponCesPortTCAThresholdOntIndex  OBJECT-TYPE
	SYNTAX 	IfIndex
	ACCESS	read-only
	STATUS	mandatory
	DESCRIPTION 
		"Each row is indexed by the ifIndex of the ONT.  "
	::= { gponCesPortTCAThresholdEntry 1 }

gponCesPortTCAThresholdSpIndex  OBJECT-TYPE
	SYNTAX 	SpIndex
	ACCESS	read-only
	STATUS	mandatory
	DESCRIPTION 
		"Each row is also indexed by a number that
		 contains the slot number and port number
 		 within the ONT. "
	::= { gponCesPortTCAThresholdEntry 2 }


gponCesPortTCAEnable  OBJECT-TYPE
	SYNTAX 	INTEGER
	ACCESS	read-write
	STATUS	mandatory
	DESCRIPTION 
		"Allows the manager to enable/disable the reporting of
		 TCAs for this CES port. 

		  1 = TCA's enabled
		  2 = TCA's disabled

		 Default = 2 = disabled. "
	::= { gponCesPortTCAThresholdEntry 3 }


gponCesPortTCAThresholdESs  OBJECT-TYPE
	SYNTAX 	Threshold
	ACCESS	read-write
	STATUS	mandatory
	DESCRIPTION 
		"TCA setting for Errored Seconds (ES).
		 A value of 4294967295 means that this threshold is disabled.

		 Default = 4294967295 "
	::= { gponCesPortTCAThresholdEntry 4 }

gponCesPortTCAThresholdSESs  OBJECT-TYPE
	SYNTAX 	Threshold
	ACCESS	read-write
	STATUS	mandatory
	DESCRIPTION 
		"TCA setting for Severly Errored Seconds (SES)
		 A value of 4294967295 means that this threshold is disabled.

		 Default = 4294967295 "
	::= { gponCesPortTCAThresholdEntry 5 }

gponCesPortTCAThresholdBESs  OBJECT-TYPE
	SYNTAX 	Threshold
	ACCESS	read-write
	STATUS	mandatory
	DESCRIPTION 
		"TCA setting for Bursty Error Seconds (BES)
		 A value of 4294967295 means that this threshold is disabled.

		 Default = 4294967295

		 NOT SUPPORTED for FGU4.3.  "
	::= { gponCesPortTCAThresholdEntry 6 }

gponCesPortTCAThresholdUASs  OBJECT-TYPE
	SYNTAX 	Threshold
	ACCESS	read-write
	STATUS	mandatory
	DESCRIPTION 
		"TCA setting for Unavailable Seconds (UAS)
		 A value of 4294967295 means that this threshold is disabled.

		 Default = 4294967295 "
	::= { gponCesPortTCAThresholdEntry 7 }

gponCesPortTCAThresholdCSSs  OBJECT-TYPE
	SYNTAX 	Threshold
	ACCESS	read-write
	STATUS	mandatory
	DESCRIPTION 
		"TCA setting for Controlled Slop Seconds (CSS)
		 A value of 4294967295 means that this threshold is disabled.

		 Default = 4294967295

		 NOT SUPPORTED for FGU4.3. "
	::= { gponCesPortTCAThresholdEntry 8 }




-- *********************************************
--
-- BPON VIDEO PORT TABLE
--
-- This is a new table beginning with FGU2.5.
-- This table contains a row for each provisioned Video port on a
-- specific ONT. Rows are created dynamically by operator
-- via Create-and-go.
--
-- Beginning with GPON FTTU4.1, 
-- this table is supported for ONTs having Video Overlay
-- capability..
--
-- For ISAM4.0.10, this table is being re-used. However, for ISAM 4.0.10,
-- rows are auto-created by agent.  The number of rows auto-created is
-- determined from the bponOntPlanCardTable.
-- Noted which attributes are relevant for ISAM4.0.10. 
--
--
--	For GPON - SUPPORTED as of ISAM4.0.10
--	For XG-PON1 - SUPPORTED as of ISAM4.6.02
--	For NG-PON2 - NOT SUPPORTED as of ISAM5.2 (RF Video Type is NOT SUPPORTED)
--  
-- *********************************************

bponVideoPortTable  OBJECT-TYPE
	SYNTAX SEQUENCE OF BponVideoPortEntry
	ACCESS	not-accessible
	STATUS	mandatory
	::= { bponVideoGroup 1 }


bponVideoPortEntry  OBJECT-TYPE
	SYNTAX 	BponVideoPortEntry
	ACCESS	not-accessible
	STATUS	mandatory
	INDEX	{ bponVideoPortOntIndex,
		   bponVideoPortSpIndex }
	::= { bponVideoPortTable 1 }

BponVideoPortEntry ::= SEQUENCE {
	bponVideoPortOntIndex		IfIndex,
	bponVideoPortSpIndex		SpIndex,
	bponVideoPortRowStatus		RowStatus,
	bponVideoPortAdminState		AdminState,
	bponVideoPortOperState		OperState,
	bponVideoPortArc			INTEGER,
	bponVideoPortArcInterval		INTEGER,
	bponVideoPortPowerControl		INTEGER,
	bponVideoPortPwrShedOverride	Boolean,
	bponVideoPortServiceTimer		INTEGER
}


bponVideoPortOntIndex  OBJECT-TYPE
	SYNTAX 	IfIndex
	ACCESS	read-only
	STATUS	mandatory
	DESCRIPTION 
		"Each row is indexed by the ifIndex of the ONT.

		Applicable for both BPON and GPON (beginning
		with FGU4.1).
		For ISAM4.0.10 - stays the same as latest FGU4.x "
	::= { bponVideoPortEntry 1 }


bponVideoPortSpIndex  OBJECT-TYPE
	SYNTAX 	SpIndex
	ACCESS	read-only
	STATUS	mandatory
	DESCRIPTION 
		"Each row is also indexed by a number that
		 contains the slot number and port number
		 within the ONT.

		Applicable for both BPON and GPON (beginning
		with FGU4.1).

		For ISAM4.0.10 - stays the same as latest FGU4.x "
	::= { bponVideoPortEntry 2 }



bponVideoPortRowStatus  OBJECT-TYPE
	SYNTAX 	RowStatus
	ACCESS	read-write
	STATUS	mandatory
	DESCRIPTION 
		" All rows instantiated using 'create-and-go' to
		 provision a Video port. Set to 'destroy' to delete
		 a Video port.

		Applicable for both BPON and GPON (beginning
		with FGU4.1).

		For ISAM4.0.10 - this attribute is NOT SUPPORTED.  "
	::= { bponVideoPortEntry 3 }

bponVideoPortAdminState  OBJECT-TYPE
	SYNTAX 	AdminState
	ACCESS	read-write
	STATUS	mandatory
	DESCRIPTION 
		"For OMCI messaging, this attribute translates
		 into Admin State for the PPTP VIDEO UNI.  
		 Setting it to 'locked' deactivates the particular
		 VIDEO port.
		 Modification permitted even after row
		 becomes 'active'.
		 Default = 1 = locked

		Applicable for both BPON and GPON (beginning
		with FGU4.1).

		For ISAM4.0.10 - stays the same as latest FGU4.x "
	::= { bponVideoPortEntry 4 }

bponVideoPortOperState  OBJECT-TYPE
	SYNTAX 	OperState
	ACCESS	read-only
	STATUS	mandatory
	DESCRIPTION 
		"Indicates operational state of the
		 Video port.  State is related to ability of port
		  to perform its function (e.g. whether service
		  affecting alarm is present).
		  Default = 0 = Enabled

		Applicable for both BPON and GPON (beginning
		with FGU4.1).

		For ISAM4.0.10 - stays the same as latest FGU4.x "
	::= { bponVideoPortEntry 5 }



bponVideoPortArc  OBJECT-TYPE
	SYNTAX 	INTEGER
	ACCESS	read-write
	STATUS	mandatory
	DESCRIPTION 
		"Alarm Reporting Control.  Valid values are:

		0 = Off (meaning alarm reporting allowed
		             immediately)
		1 = On (meaning alarm reporting inhibited until
		             valid signal is detected for time period
		             specified by ARC Interval).
		 Default = 1  - function is not implemented or supported
				for either BPON or GPON.

		For ISAM4.0.10 - stays the same as latest FGU4.x "
	::= { bponVideoPortEntry 6 }

bponVideoPortArcInterval  OBJECT-TYPE
	SYNTAX 	INTEGER
	ACCESS	read-write
	STATUS	mandatory
	DESCRIPTION 
		"Alarm Reporting Control Interval (in minutes).

		 0 means alarms are inhibited indefinitely (if ARC
		   is set to inhibited)
		 Default = 0  - function is not implemented or supported
				for either BPON or GPON.

		For ISAM4.0.10 - stays the same as latest FGU4.x "
::= { bponVideoPortEntry 7 }


bponVideoPortPowerControl  OBJECT-TYPE
	SYNTAX 	INTEGER
	ACCESS	read-write
	STATUS	mandatory
	DESCRIPTION 
		" Controls whether power is provided to external equipment
		   over the subscriber Video port (i.e. Video PPTP UNI in OMCI).

		  0 = Disable power feed
		  1 = Enable power over co-ax feed 

		  Default = 0  - function is not implemented or supported
				for either BPON or GPON.

		For ISAM4.0.10 - stays the same as latest FGU4.x "
::= { bponVideoPortEntry 8 }


bponVideoPortPwrShedOverride  OBJECT-TYPE
	SYNTAX 	Boolean
	ACCESS	read-write
	STATUS	mandatory
	DESCRIPTION 
		"Allows setting as follows:

		 TRUE = 1 = port excluded from Video overlay class power shedding
		 FALSE = 0 = port included in Video overlay class power shedding

		 Default = 0 = FALSE 

		 As of FGU4.4, this is Supported. 

		For ISAM4.0.10 - stays the same as latest FGU4.x  "
	::= { bponVideoPortEntry 9 }

bponVideoPortServiceTimer  OBJECT-TYPE
	SYNTAX 	INTEGER
	ACCESS	read-write
	STATUS	mandatory
	DESCRIPTION 
		" Controls the amount of time (in hours) the ONT should sustain RF video service while unranged. 

		  As of FTTU4.7, this attribute is SUPPORTED with following qualifications:
			- Range is 0 - 48 (where 0 means drop ASAP).
			- Default = 48 (hours).
			- Modification permitted (while in-service).  
		
		 Prior to ISAM4.6, this attribute was NOT SUPPORTED

		 As of ISAM4.6, this attribute is SUPPORTED with following qualifications:
			- Range is -1 to 48
				where -1 means 'do not care' - and NO OMCI messaging is involved.
				and 0 still means 'drop ASAP'.
			- Default = -1 (do not care)
			- Modification SUPPORTED (while in-service)  "
	::= { bponVideoPortEntry 10 }


-- *********************************************
--
-- GPON  VIDEO ANI TABLE
--
-- This table contains configuration and capability information 
-- with regard to the ANI-side video overlay for a specific ONT.
-- The OLT automatically creates a single row per ONT when the
-- first (or only) video subscriber port is created for that ONT.  The 
-- OLT automatically deletes the single row per ONT when the last
-- (or only) video subscriber port is deleted from that ONT.
--
-- This tables was first introduced for FGU4.1, and it is only
--  applicable for GPON. 
--
-- For ISAM4.0.10, this table is being re-used. 
-- Noted which attributes are relevant for ISAM4.0.10 
--
--
--	For GPON - SUPPORTED as of ISAM4.0.10
--	For XG-PON1 - SUPPORTED as of ISAM4.6.02
--	For NG-PON2 - NOT SUPPORTED as of ISAM5.2 (RF Video Type is NOT SUPPORTED)
--   
-- *********************************************

gponVideoAniTable  OBJECT-TYPE
	SYNTAX SEQUENCE OF GponVideoAniEntry
	ACCESS	not-accessible
	STATUS	mandatory
	::= { bponVideoGroup 2 }

gponVideoAniEntry  OBJECT-TYPE
	SYNTAX 	GponVideoAniEntry
	ACCESS	not-accessible
	STATUS	mandatory
	INDEX	{ gponVideoAniOntIndex,
		  gponVideoAniIndex }
	::= { gponVideoAniTable 1 }

GponVideoAniEntry ::= SEQUENCE {
	gponVideoAniOntIndex			IfIndex,
	gponVideoAniIndex			INTEGER,
	gponVideoAniAdminState			AdminState,
	gponVideoAniOperState			OperState,
	gponVideoAniFreqRangeLow		INTEGER,
	gponVideoAniFreqRangeHigh		INTEGER,
	gponVideoAniSignalCapability		INTEGER,
	gponVideoAniSignalLevelMin		INTEGER,
	gponVideoAniSignalLevelMax		INTEGER,
	gponVideoAniPilotFreq			INTEGER,
	gponVideoAniAgcModePlanned			INTEGER,
	gponVideoAniAgcModeActual			INTEGER,
	gponVideoAniAgcSetting			INTEGER,
	gponVideoAniLowerOpticalThreshold		INTEGER,
	gponVideoAniUpperOpticalThreshold		INTEGER,
        gponVideoAniSignalLevelMinDbm                   INTEGER,
        gponVideoAniSignalLevelMaxDbm                   INTEGER

}

gponVideoAniOntIndex  OBJECT-TYPE
	SYNTAX 	IfIndex
	ACCESS	read-only
	STATUS	mandatory
	DESCRIPTION 
		"Each row is indexed by the ifIndex of the
		 ONT.

		For ISAM4.0.10 - stays the same as latest FGU4.x  "
	::= { gponVideoAniEntry 1 }

gponVideoAniIndex  OBJECT-TYPE
	SYNTAX 	INTEGER (1..2147483647)
	ACCESS	read-only
	STATUS	mandatory
	DESCRIPTION 
		"Each row is also indexed by the number of the Video ANI
		  associated with the ONT. For FGU4.1, this number is 
		  a fixed value of 1.

		For ISAM4.0.10 - stays the same as latest FGU4.x   "
	::= { gponVideoAniEntry 2 }


gponVideoAniAdminState  OBJECT-TYPE
	SYNTAX 	AdminState
	ACCESS	read-write
	STATUS	mandatory
	DESCRIPTION 
		"For OMCI messaging, this attribute translates
		 into Admin State for the PPTP Video ANI.  Setting it
		 to 'locked' deactivates the 1550 overlay reception.
		 Modification permitted even after row
		 becomes 'active'.
		 Default = 0 = unlocked

		 For FGU4.1, the default is the only value supported.

		For ISAM4.0.10 - stays the same as latest FGU4.x "
	::= { gponVideoAniEntry 3 }

gponVideoAniOperState  OBJECT-TYPE
	SYNTAX 	OperState
	ACCESS	read-only
	STATUS	mandatory
	DESCRIPTION 
		"Indicates operational state of the
		 1550 overlay reception capability. State is related to ability
		 to perform 1550 overlay reception function (e.g. whether service
		 affecting alarm is present).
		 Default = 0 = Enabled

		For ISAM4.0.10 - stays the same as latest FGU4.x "
	::= { gponVideoAniEntry 4 }

gponVideoAniFreqRangeLow  OBJECT-TYPE
	SYNTAX 	INTEGER
	ACCESS	read-only
	STATUS	mandatory
	DESCRIPTION 
		" Indicates the lower of two frequency ranges supported.
		 Coded as follows:
		 0 = No low band is supported
		 1 = 50 - 550 MHz is supported
		 2 = 50 - 750 MHz is supported
		 3 = 50 - 870 MHz is supported
		 256 = Unknown (because OLT has not yet communicated
			with ONT for OMCI discovery purposes).

		 Default = 256 = unknown

		For ISAM4.0.10 - stays the same as latest FGU4.x "
	::= { gponVideoAniEntry 5 }

gponVideoAniFreqRangeHigh  OBJECT-TYPE
	SYNTAX 	INTEGER
	ACCESS	read-only
	STATUS	mandatory
	DESCRIPTION 
		" Indicates the higher of two frequency ranges supported.
		 Coded as follows:
		 0 = No high band is supported
		 1 = 550 - 750 MHz is supported
		 2 = 550 - 870 MHz is supported
		 3 = 950 - 2050 MHz is supported
		 4 = 2150 - 3250 MHz is supported
		 5 = 950 - 3250 MHz is supported
		 256 = Unknown (because OLT has not yet communicated
			with ONT for OMCI discovery purposes).

		 Default = 256 = unknown

		For ISAM4.0.10 - stays the same as latest FGU4.x "
	::= { gponVideoAniEntry 6 }

gponVideoAniSignalCapability  OBJECT-TYPE
	SYNTAX 	INTEGER
	ACCESS	read-only
	STATUS	mandatory
	DESCRIPTION 
		" Indicates the capability of the ONT to measure the video
		  signal level.
		 Coded as follows:
		 0 = No signal level capability is supported
		 1 = Total optical power level is supported
		 2 = Fixed freq pilot tone is supported
		 3 = Total optical power level and fixed freq pilot tone is supported
		 4 = Variable freq pilot tone is supported
		 5 = Total optical power level and variable freq pilot tone is supported
		 6 = Broadband RF power level is supported
		 7 = Total optical power level and broadband RF power level is supported
		 256 = Unknown (because OLT has not yet communicated
			with ONT for OMCI discovery purposes).

		 Default = 256 = unknown

		For ISAM4.0.10 - stays the same as latest FGU4.x "
	::= { gponVideoAniEntry 7 }

gponVideoAniSignalLevelMin  OBJECT-TYPE
	SYNTAX 	INTEGER
	ACCESS	read-only
	STATUS	mandatory
	DESCRIPTION 
		" Indicates the minimum optical RF power per channel that will result
		  in a CNR of 47dBc for a channel of 4.5 Mhz in bandwidth at a receive
		  optical power of -5 dBm.  The unit of this attribute is dBuW optical.

		  Range is 0 - 256.

		  256 = Unknown (because OLT has not yet communicated
		  with ONT for OMCI discovery purposes).

		  Default = 256 = unknown

		For ISAM4.0.10 - stays the same as latest FGU4.x "
	::= { gponVideoAniEntry 8 }

gponVideoAniSignalLevelMax  OBJECT-TYPE
	SYNTAX 	INTEGER
	ACCESS	read-only
	STATUS	mandatory
	DESCRIPTION 
		" Indicates the maximum optical RF power per channel that will result
		  in a CTB of -57dBc for an 80-channel ensemble of carriers at a per-channel
		  optical modulation index of 3.5%. The unit of this attribute is dBuW optical.

		  Range is 0 - 256.

		  256 = Unknown (because OLT has not yet communicated
		  with ONT for OMCI discovery purposes).

		  Default = 256 = unknown

		For ISAM4.0.10 - stays the same as latest FGU4.x "
	::= { gponVideoAniEntry 9 }


gponVideoAniPilotFreq  OBJECT-TYPE
	SYNTAX 	INTEGER
	ACCESS	read-write
	STATUS	mandatory
	DESCRIPTION 
		" Indicates the frequency of the pilot channel receiver.  Units are Hz. 

		  Range is  -1 to  2147483647.

		  -1 = Unknown (because OLT has not yet communicated
		  with ONT for OMCI discovery purposes), and this parameter has
		  never been edited via management.  While the value is -1, edit
		  is not permitted. The OLT changes this value from -1 the first time
		  it is actually discovered via OMCI.  Thereafter, edits are permitted
		  depending on the ONT Signal capability.

		  Default = -1 = unknown

		  For FGU4.1 --> Not supported

		For ISAM4.0.10 - stays the same as latest FGU4.x  "
	::= { gponVideoAniEntry 10 }

gponVideoAniAgcModePlanned  OBJECT-TYPE
	SYNTAX 	INTEGER
	ACCESS	read-write
	STATUS	mandatory
	DESCRIPTION 
		" Allows provisioning of the ONT's AGC capabilities.

		 Coded as follows:
		 0 = No AGC is used
		 1 = Broadband RF AGC is used
		 2 = Optical AGC is used  (NOT SUPPORTED as of FGU4.4)

		 Default = 1 = Use Broadband RF

		For ISAM4.0.10 - stays the same as latest FGU4.x "
	::= { gponVideoAniEntry 11 }


gponVideoAniAgcModeActual  OBJECT-TYPE
	SYNTAX 	INTEGER
	ACCESS	read-only
	STATUS	mandatory
	DESCRIPTION 
		" Indicates the discovered value of ONT's AGC capabilities.

		 Coded as follows:
		 0 = No AGC is used
		 1 = Broadband RF AGC is used
		 2 = Optical AGC is used

		 256 = Unknown (because OLT has not yet communicated
			with ONT for OMCI discovery purposes).

		 Default = 256 = unknown

		For ISAM4.0.10 - stays the same as latest FGU4.x "
	::= { gponVideoAniEntry 12 }

gponVideoAniAgcSetting  OBJECT-TYPE
	SYNTAX 	INTEGER
	ACCESS	read-write
	STATUS	mandatory
	DESCRIPTION 
		" Indicates the measurement offset that the ONT should use if
		  using broadband RF signal level or total optical power as a basis
		  for AGC.  The theoretical nominal RF signal is 80 channels of NTSC
		  video, each having a per-channel optical modulation index of 3.5%.
		  An ONT presented with such a signal should produce its specified
		  output when this attribute is set to zero.  The attribute will have a step-size
		  of 0.1 db, represented as a single integer.  The usage of the attribute depends
		  on the signal capability used for the AGC.

		  If total optical power is used for AGC, then this attribute provides the ONT with
		  the OMI offset for any NTSC carriers present from the theoretical 3.5% value.
		  So, if the the actual signal uses an OMI of 7.0% per channel (3 db higher), 
		  then this MIB attribute should be set to 30, and the ONT should be given an 
		  AGC setting of 30.  (Coded in 2's compliment as 0x1E for OMCI messaging).

		  If broadband RF power is used for AGC, then this attribute provides the ONT
		  with the total power offset for any NTSC carriers present from the theoretical
		  80 channel value.  So, if an actual signal contains 40 NTSC channels (3 db lower),
		  then this MIB attribute should be set to -30, and the ONT should be given an 
		  AGC setting of -30. (Coded in 2's compliment as 0xE2 for OMCI messaging).

		 Range is -120 to +120

		 Default = 20 = 2.0dB

		For ISAM4.0.10 - stays the same as latest FGU4.x "
	::= { gponVideoAniEntry 13 }


gponVideoAniLowerOpticalThreshold  OBJECT-TYPE
	SYNTAX 	INTEGER
	ACCESS	read-write
	STATUS	mandatory
	DESCRIPTION 
		" This attribute indicates the optical level the ONT uses to declare the Video-OOR Low
		   alarm.  When the optical level of the received 1550nm signal drops below this 
		   attribute setting, the Video-OOR Low alarm is generated.  Valid values are -12 dBm
		   to +6 dBm (in 0.1 dB increments).

		   Examples:
		   -120 = -12.0 dBm = (Coded in 2's compliment as 0x88 for OMCI messaging)
		   0 = 0 dBm
		   60 = +6.0 dBm = (Coded in 2's compliment as 0x3C for OMCI messaging)

		   Range is -120 to +60

		   Default = -95 = -9.5 dBm = (Coded in 2's complement as 0xA1 for OMCI messaging)

		For ISAM4.0.10 - stays the same as latest FGU4.x  "
	::= { gponVideoAniEntry 14 }


gponVideoAniUpperOpticalThreshold  OBJECT-TYPE
	SYNTAX 	INTEGER
	ACCESS	read-write
	STATUS	mandatory
	DESCRIPTION 
		" This attribute indicates the optical level the ONT uses to declare the Video-OOR High
		   alarm.  When the optical level of the received 1550nm signal raises above this 
		   attribute setting, the Video-OOR High alarm is generated.  Valid values are -12 dBm
		   to +6 dBm (in 0.1 dB increments).

		   Examples:
		   -120 = -12.0 dBm = (Coded in 2's compliment as 0x88 for OMCI messaging)
		   0 = 0 dBm
		   60 = +6.0 dBm = (Coded in 2's compliment as 0x3C for OMCI messaging)

		   Range is -120 to +60 

		   Prior to ISAM5.6 - Default = +25 = +2.5 dBm = (Coded in 2's compliment as 0x19 for OMCI messaging)
                   As of ISAM5.6 - Default = +10 = +1.0 dBm = (Coded in 2's compliment as 0x0A for OMCI messaging)

		For ISAM4.0.10 - stays the same as latest FGU4.x  "
	::= { gponVideoAniEntry 15 }


gponVideoAniSignalLevelMinDbm  OBJECT-TYPE
        SYNTAX  INTEGER
        ACCESS  read-only
        STATUS  mandatory
        DESCRIPTION
                " Indicates the minimum optical RF power per channel that will result
                  in a CNR of 47dBc for a channel of 4.5 Mhz in bandwidth at a receive
                  optical power of -5 dBm.  This power value is a signed integer referred
                  to 1mW (i.e. dBm), with 1 dB granularity.

                  This value (units of dBm) is computed as gponVideoAniSignalLevelMin
                  (units of dBuW) minus 30.

                  Range is -30 to +226.

                  +226 = Unknown (because OLT has not yet communicated with ONT for OMCI discovery purposes).

                  Attribute was first introduced as of ISAM5.6 MIB, with targeted
                  implementation in ISAM5.6.01

                  Default = +226 = unknown

                  For GPON - SUPPORTED as of ISAM5.6
                  For XG-PON1 – NOT SUPPORTED as of ISAM5.6
                  For NG-PON2 – NOT SUPPORTED as of ISAM5.6"
        ::= { gponVideoAniEntry 16 }


gponVideoAniSignalLevelMaxDbm  OBJECT-TYPE
        SYNTAX  INTEGER
        ACCESS  read-only
        STATUS  mandatory
        DESCRIPTION
                " Indicates the maximum optical RF power per channel that will result
                  in a CTB of -57dBc for an 80-channel ensemble of carriers at a per-
                  channel optical modulation index of 3.5%. This power value is a signed
                  integer referred to 1mW (i.e. dBm), with 1 dB granularity.

                  This value (units of dBm) is computed as gponVideoAniSignalLevelMax (units of dBuW) minus 30.

                  Range is -30 to +226.

                  +226 = Unknown (because OLT has not yet communicated with ONT for OMCI discovery purposes).

                  Attribute was first introduced as of ISAM5.6 MIB, with targeted
                  implementation in ISAM5.6.01

                  Default = +226 = unknown

                  For GPON - SUPPORTED as of ISAM5.6
                  For XG-PON1 – NOT SUPPORTED as of ISAM5.6
                  For NG-PON2 – NOT SUPPORTED as of ISAM5.6"
        ::= { gponVideoAniEntry 17 }

-- *********************************************
--  GPON VIDEO ANI OPERATIONAL INFO TABLE
--
--This table is only used for GPON.
--
-- This table contains operational information regarding the 1550
-- video wavelength.  Specifically, it contains measurements
-- of the optical signal level and the broadband RF power level.
-- The operational information is significant in that
-- each time it is requested, the OLT issues OMCI GET messages   
-- to obtain the latest information directly from the ONT.
-- A table row is created/deleted automatically by the OLT in a 
-- one-to-one relationship with the GPON VIDEO ANI TABLE.
--
-- For ISAM4.0.10, this table is being re-used. 
-- Noted which attributes are relevant for ISAM4.0.10 
--
--
--	For GPON - SUPPORTED as of ISAM4.0.10
--	For XG-PON1 - SUPPORTED as of ISAM4.6.02
--	For NG-PON2 - NOT SUPPORTED as of ISAM5.2 (RF Video Type is NOT SUPPORTED)
--  
-- *********************************************

gponVideoAniOpInfoTable  OBJECT-TYPE
	SYNTAX SEQUENCE OF GponVideoAniOpInfoEntry
	ACCESS	not-accessible
	STATUS	mandatory
	::= { bponVideoGroup 3 }

gponVideoAniOpInfoEntry  OBJECT-TYPE
	SYNTAX 	GponVideoAniOpInfoEntry
	ACCESS	not-accessible
	STATUS	mandatory
	INDEX	{ gponVideoAniOpInfoOntIndex,
		  gponVideoAniOpInfoIndex }
	::= { gponVideoAniOpInfoTable 1 }

GponVideoAniOpInfoEntry ::= SEQUENCE {
	gponVideoAniOpInfoOntIndex			IfIndex,
	gponVideoAniOpInfoIndex			INTEGER,
	gponVideoAniOpInfoOpticalSignalLevel	 	INTEGER,
	gponVideoAniOpInfoRfPowerLevel		INTEGER,
        gponVideoAniOpInfoOpticalSignalLevelDbm INTEGER
}

gponVideoAniOpInfoOntIndex  OBJECT-TYPE
	SYNTAX 	IfIndex
	ACCESS	read-only
	STATUS	mandatory
	DESCRIPTION 
		"Each row is indexed by the ifIndex of the
		 ONT. 

		Applicable only for GPON.

		For ISAM4.0.10 - stays the same as latest FGU4.x "
	::= { gponVideoAniOpInfoEntry 1 }

gponVideoAniOpInfoIndex  OBJECT-TYPE
	SYNTAX 	INTEGER (1..2147483647)
	ACCESS	read-only
	STATUS	mandatory
	DESCRIPTION 
		"Each row is also indexed by the number of the Video ANI
		  associated with the ONT. For FGU4.1, this number is 
		  a fixed value of 1.

		For ISAM4.0.10 - stays the same as latest FGU4.x   "
	::= { gponVideoAniOpInfoEntry 2 }


gponVideoAniOpInfoOpticalSignalLevel  OBJECT-TYPE
	SYNTAX 	INTEGER
	ACCESS	read-only
	STATUS	mandatory
	DESCRIPTION 
		"Indicates the current measurement of the total optical
		 signal level . The unit of this attribute is dBuW optical.

		 If Signal Capability = 0, 2 or 4 then this attribute is undefined.

		 If Signal Capability = 1, 3, 5 or 7 then this attribute describes the
		 total optical power that is generating photocurrent on the receiver.

		  Range is 0 - 256.

		  256 = Unknown (because OLT has not yet communicated
		  with ONT for OMCI discovery purposes).

		  Default = 256 = unknown

		For ISAM4.0.10 - stays the same as latest FGU4.x "

	::= { gponVideoAniOpInfoEntry 3 }


gponVideoAniOpInfoRfPowerLevel  OBJECT-TYPE
	SYNTAX 	INTEGER
	ACCESS	read-only
	STATUS	mandatory
	DESCRIPTION 
		"Indicates the current measurement of the pilot signal level
		 or the broadband RF power level. The unit of this attribute
		 is dBuV.

		 If Signal Capability = 0 or 1 then this attribute is undefined.

		 If Signal Capability = 2, 3, 4 or 5 then this attribute describes the
		 pilot signal level at the output of the video UNI.

		 If Signal Capability = 6 or 7 then this attribute describes the total
		 RF power level at the output of the video UNI.

		 Range is 0 - 256.

		 256 = Unknown (because OLT has not yet communicated
		 with ONT for OMCI discovery purposes).

		 Default = 256 = unknown

		For ISAM4.0.10 - stays the same as latest FGU4.x "

	::= { gponVideoAniOpInfoEntry 4 }


gponVideoAniOpInfoOpticalSignalLevelDbm  OBJECT-TYPE
        SYNTAX  INTEGER
        ACCESS  read-only
        STATUS  mandatory
        DESCRIPTION
                "Indicates the current measurement of the total optical signal level .
                 This power measurement is a signed integer referred to 1mW (i.e. dBm), with 1 dB granularity.
                 This value (units of dBm) is computed as gponVideoAniOpInfoOpticalSignalLevel (units of dBuW) minus 30.

                 If Signal Capability = 0, 2 or 4 then this attribute is undefined.

                 If Signal Capability = 1, 3, 5 or 7 then this attribute describes the total optical power that is generating photocurrent on the receiver.

                 Range is -30 to +226.

                 +226 = Unknown (because OLT has not yet communicated with ONT for OMCI discovery purposes).

                 Attribute was first introduced as of ISAM5.6 MIB, with targeted
                 implementation in ISAM5.6.01

                 Default = +226 = unknown

                 For GPON - SUPPORTED as of ISAM5.6
                 For XG-PON1 – NOT SUPPORTED as of ISAM5.6
                 For NG-PON2 – NOT SUPPORTED as of ISAM5.6"
        ::= { gponVideoAniOpInfoEntry 5 }

-- ***************************************************************
-- hpnaPortTable
-- GPON HPNA PORT TABLE
--
-- This table was first introduced with ISAM4.4 MIB.

-- Rows are auto-created by agent.  The number of rows auto-created is
-- determined from the bponOntPlanCardTable.
--
--
--	For GPON - SUPPORTED as of ISAM4.4
--	For XG-PON1 - SUPPORTED as of ISAM4.6.02
--	For NG-PON2 - NOT SUPPORTED as of ISAM5.2 (HPNA Card Type is NOT SUPPORTED)
-- 
-- ******************************************************************

   hpnaPortTable OBJECT-TYPE
       SYNTAX       SEQUENCE OF HpnaPortEntry
       ACCESS       not-accessible
       STATUS       mandatory
       DESCRIPTION
           "This table contains attributes describing an ONT HPNA interface
            port.  "

       ::= { hpnaMIB 1 }

   hpnaPortEntry OBJECT-TYPE
       SYNTAX       HpnaPortEntry
       ACCESS       not-accessible
       STATUS       mandatory
       DESCRIPTION  "An entry in the hpnaPortTable."

       INDEX { hpnaPortOntIndex,
               hpnaPortSpIndex }

       ::= { hpnaPortTable 1 }

   HpnaPortEntry ::=
       SEQUENCE
           {
           hpnaPortOntIndex                   IfIndex,
           hpnaPortSpIndex                    SpIndex,

           hpnaPortEtherTrafficPmCollectInd   INTEGER, -- PM table in GPON MIB
           hpnaPortEtherTrafficNumPMIntervals INTEGER, 
--           hpnaPortEtherPmCollectInd          INTEGER, 
--           hpnaPortEtherNumPMIntervals        INTEGER, 
--           hpnaPortRowStatus                  RowStatus,
--           hpnaPortCustVlan                   INTEGER,
--           hpnaPortQosProfile                 AsamProfilePointer,
--           hpnaPortAdminState                 INTEGER, 
--           hpnaPortOpState                    INTEGER, 
--           hpnaPortARC                        INTEGER, 
--           hpnaPortARCInterval                INTEGER, 
           hpnaPortLabel                      OCTET STRING,
--           hpnaPortDscpPbitMapProfile         AsamProfilePointer,
           hpnaPortMasterSelect               INTEGER,
           hpnaPortMasterSelectMode                 INTEGER,
           hpnaPortConfigurationInd           INTEGER,
           hpnaPortBaseMacAddress             OCTET STRING,
           hpnaPortPwrShedOverride            Boolean


           }

   hpnaPortOntIndex  OBJECT-TYPE
	SYNTAX 	IfIndex
	ACCESS	read-only
	STATUS	mandatory
	DESCRIPTION 
		"Each row is indexed by the ifIndex of the ONT.

           ALCATEL NOTE:
           ACCESS:    NA
           USAGE:     NA
           PERSIST:   YES
           INSRVMOD:  NA
           RANGE:     NA
           DEFVALUE:  NA
           UNITS:     NA
           SPARSE:    NA "

	::= { hpnaPortEntry 1 }

   hpnaPortSpIndex  OBJECT-TYPE
	SYNTAX 	SpIndex
	ACCESS	read-only
	STATUS	mandatory
	DESCRIPTION 
		"Each row is also indexed by a number that
		 contains the slot number and port number
		 within the ONT.

           ALCATEL NOTE:
           ACCESS:    NA
           USAGE:     NA
           PERSIST:   YES
           INSRVMOD:  NA
           RANGE:     NA
           DEFVALUE:  NA
           UNITS:     NA
           SPARSE:    NA"
           
	::= { hpnaPortEntry 2 }

   hpnaPortEtherTrafficPmCollectInd  OBJECT-TYPE
	SYNTAX 	INTEGER
	ACCESS	read-write
	STATUS	mandatory
	DESCRIPTION 
                "This indicates whether Ethernet Traffic Performance Monitors (gponEtherTrafficIntervalTable in the GPON MIB) should be
                 collected for this Hpna Port.

                  1 = PM collection enabled
                  2 = PM collection disabled

                  Default = 2 = disabled.

           ALCATEL NOTE:
           ACCESS:    NA
           USAGE:     NA
           PERSIST:   YES
           INSRVMOD:  YES
           RANGE:     1..2
           DEFVALUE:  2
           UNITS:     NA
           SPARSE:    NA"

	::= { hpnaPortEntry 3 }

   hpnaPortEtherTrafficNumPMIntervals  OBJECT-TYPE
	SYNTAX 	INTEGER
	ACCESS	read-only
	STATUS	mandatory
	DESCRIPTION 
               "Indicates the number of rows currently present
                in the gponEtherTrafficIntervalTable.  This
                is for convenience of the EMS, so that it can
                quickly determine how many rows should be 
                uploaded.


           ALCATEL NOTE:
           ACCESS:    NA
           USAGE:     NA
           PERSIST:   NO
           INSRVMOD:  NA
           RANGE:     NA
           DEFVALUE:  NA
           UNITS:     NA
           SPARSE:    NA"

	::= { hpnaPortEntry 4 }

--   hpnaPortEtherPmCollectInd  OBJECT-TYPE
--	SYNTAX 	INTEGER
--	ACCESS	read-write
--	STATUS	mandatory
--	DESCRIPTION 
--              "Ethernet PM Collect Indicator
--
--                This indicates whether Ethernet Performance Monitors
--                  (hpnaIfIntervalTable in this MIB) should be collected
--                  for this Hpna Port.
--
--                  1 = PM collection enabled
--                  2 = PM collection disabled
--
--                  Default = 2 = disabled.
--
--            Applicable only for GPON. This object is not supported in R4.7.10.
--            Whatever value is written is accepted and ignored.
--
--           ALCATEL NOTE:
--           ACCESS:    NA
--           USAGE:     NA
--           PERSIST:   YES
--           INSRVMOD:  YES
--           RANGE:     1..2
--           DEFVALUE:  2
--           UNITS:     NA
--           SPARSE:    NA"
--
--	::= { hpnaPortEntry 5 }
--
--   hpnaPortEtherNumPMIntervals  OBJECT-TYPE
--	SYNTAX 	INTEGER
--	ACCESS	read-only
--	STATUS	mandatory
--	DESCRIPTION 
--             "Indicates the number of rows currently present
--                in the hpnaIfIntervalTable.  This
--                is for convenience of the EMS, so that it can
--                quickly determine how many rows should be 
--                uploaded.
--
--            Applicable only for GPON. This object is not supported in R4.7.10.
--            It will always return 0.
--
--           ALCATEL NOTE:
--           ACCESS:    NA
--           USAGE:     NA
--           PERSIST:   NO
--           INSRVMOD:  NA
--           RANGE:     NA
--           DEFVALUE:  NA
--           UNITS:     NA
--           SPARSE:    NA"
--
--	::= { hpnaPortEntry 6 }

--   hpnaPortRowStatus OBJECT-TYPE
--       SYNTAX RowStatus
--       ACCESS read-write
--       STATUS mandatory
--       DESCRIPTION
--           "This object is used to create a new row or modify or
--           delete an existing row in this table.
--
--           ALCATEL NOTE:
--           ACCESS:    NA
--           USAGE:     NA
--           PERSIST:   NO
--           INSRVMOD:  NA
--           RANGE:     NA
--           DEFVALUE:  NA
--           UNITS:     NA
--           SPARSE:    NA"
--
--       ::= { hpnaPortEntry 7 }

--   hpnaPortCustVlan  OBJECT-TYPE
--	SYNTAX INTEGER
--	ACCESS read-write
--	STATUS mandatory
--	DESCRIPTION 
--		" This is the default Customer VLAN ID
--		  used by the ONU for this hpna UNI.
--                Based on certain 'tagging modes', the ONT
--                  inserts this VLAN tag into certain Ethernet
--		  frames. 
--
--                  Range is 0 - 4095.
--
--                  Default = 0.
--
--               Applicable only for GPON.
--
--           ALCATEL NOTE:
--           ACCESS:    NA
--           USAGE:     NA
--           PERSIST:   YES
--           INSRVMOD:  NO
--           RANGE:     0..4095
--           DEFVALUE:  0
--           UNITS:     NA
--           SPARSE:    NA"
--
--	::= { hpnaPortEntry 8 }

--    hpnaPortQosProfile OBJECT-TYPE
--	    SYNTAX	AsamProfilePointer
--	    ACCESS read-write
--	    STATUS	mandatory
--	    DESCRIPTION
--		    " This object is used to reference the appropriate
--		     QOS Profile (in the QOS MIB) -> for tag marking.
--
--  		     The ONT LAN UNI is associated with one OLT bridge port
--		     which is associated with one QOS Profile.
--
--               Applicable only for GPON.
--
--           ALCATEL NOTE:
--           ACCESS:    NA
--           USAGE:     NA
--           PERSIST:   YES
--           INSRVMOD:  NO
--           RANGE:     NA
--           DEFVALUE:  NA
--           UNITS:     NA
--           SPARSE:    NA"
--
--     	::= { hpnaPortEntry 9 }


--   hpnaPortAdminState OBJECT-TYPE
--       SYNTAX AdminState
--       ACCESS read-write
--       STATUS mandatory
--       DESCRIPTION
--           "For OMCI messaging, this attribute translates
--            into Admin State for the PPTP Ethernet UNI.
--            Setting it to 'locked' deactivates the particular
--            Hpna port.
--              0=unlocked
--              1=locked (default)
--            Modification permitted even after row
--            becomes 'active'.
--
--               Applicable only for GPON.
--
--           ALCATEL NOTE:
--           ACCESS:    NA
--           USAGE:     NA
--           PERSIST:   YES
--           INSRVMOD:  NO
--           RANGE:     0..1
--           DEFVALUE:  1
--           UNITS:     NA
--           SPARSE:    NA"
--
--       DEFVAL  {1}
--
--       ::= { hpnaPortEntry 10 }

--   hpnaPortOpState OBJECT-TYPE
--       SYNTAX OperState
--       ACCESS read-only
--       STATUS mandatory
--       DESCRIPTION
--           "This attribute indicates whether or not Hpna interface port
--            is capable of performing its task.  The operational state
--            reflects the perceived ability to receive or to generate
--            a valid signal.
--              0=enabled (default)
--              1=disabled
--              2=unknown
--
--               Applicable only for GPON.
--
--           ALCATEL NOTE:
--           ACCESS:    NA
--           USAGE:     NA
--           PERSIST:   NO
--           INSRVMOD:  NA
--           RANGE:     0..2
--           DEFVALUE:  0
--           UNITS:     NA
--           SPARSE:    NA"
--           
--       ::= { hpnaPortEntry 11 }


--  hpnaPortARC OBJECT-TYPE
--       SYNTAX INTEGER
--       ACCESS read-write
--       STATUS mandatory
--       DESCRIPTION
--           "Defines alarm reporting mode for the hpna physical line.
--            When value is 1, alarms are inhibited until a valid signal
--            is detected for the time interval specified in hpnaPortARCInterval
--            object.
--              0 = Off (meaning alarm reporting allowed immediately)
--              1 = On (meaning alarm reporting inhibited until
--                  valid signal is detected for time period
--                  specified by ARC Interval).
--              Default = 1  - function is not implemented or supported for
--                             either BPON or GPON. 
--
--               Applicable only for GPON.
--
--           ALCATEL NOTE:
--           ACCESS:    NA
--           USAGE:     NA
--           PERSIST:   YES
--           INSRVMOD:  YES
--           RANGE:     0..1
--           DEFVALUE:  1
--           UNITS:     NA
--           SPARSE:    NA"
--
--       DEFVAL  {1}
--
--       ::= { hpnaPortEntry 12 }

--   hpnaPortARCInterval OBJECT-TYPE
--       SYNTAX       INTEGER (0..255)
--       ACCESS       read-write
--       STATUS       mandatory
--       DESCRIPTION
--           "Defines  the time interval in minutes during which alarm reporting is prohibited.
--              0 means alarms are inhibited indefinitely
--                (if ARC is set to inhibited)
--              Default = 0  - function is not implemented or supported 
--			for either BPON or GPON. 
--
--               Applicable only for GPON.
--
--           ALCATEL NOTE:
--           ACCESS:    NA
--           USAGE:     NA
--           PERSIST:   YES
--           INSRVMOD:  YES
--           RANGE:     0..255
--           DEFVALUE:  0
--           UNITS:     minutes
--           SPARSE:    NA"
--
--       DEFVAL  {0}
--
--       ::= { hpnaPortEntry 13 }


   hpnaPortLabel  OBJECT-TYPE
	    SYNTAX OCTET STRING (SIZE (0..80))
	    ACCESS read-write
	    STATUS mandatory
	    DESCRIPTION 
               "This is a textual string that can be used
                to label the Hpna port.

                Applicable only for GPON.

           ALCATEL NOTE:
           ACCESS:    NA
           USAGE:     NA
           PERSIST:   YES
           INSRVMOD:  YES
           RANGE:     NA
           DEFVALUE:  NULL
           UNITS:     NA
           SPARSE:    NA"

	::= { hpnaPortEntry 14 }

 
--hpnaPortDscpPbitMapProfile OBJECT-TYPE
--	 SYNTAX AsamProfilePointer
--	 ACCESS read-write
--	STATUS mandatory
-- 	DESCRIPTION
--	  " This object is used to reference the appropriate
-- 	   DSCP-to-Pbit mapping profile (in the GPON MIB).
-- 
--	    The value 0 means that DSCP-to-Pbit mapping is not 
-- 	   yet specified for this ONT. When specified, must point
-- 	   to a valid profile.
-- 
--  	  Modification is permitted (without having to ADMIN DOWN the UNI).
--	   Default = 0 = meaning no mapping specified. 
-- 
--
--	Applicable only for GPON.
--
--           ALCATEL NOTE:
--           ACCESS:    NA
--           USAGE:     NA
--           PERSIST:   YES
--           INSRVMOD:  YES
--           RANGE:     NA
--           DEFVALUE:  NULL
--           UNITS:     NA
--           SPARSE:    NA"
--
--	 ::= { hpnaPortEntry 15 }

hpnaPortMasterSelect OBJECT-TYPE
	 SYNTAX INTEGER
	 ACCESS read-write
	 STATUS mandatory
	 DESCRIPTION
  	" This attribute selects the master mode of the HomePNA MAC.
	0 - select the ONT internal policy. Accordingly ONT should select the own internal default on this SET. 
		It will allow ONT not only to start with the suitable default mode, but also return to it without knowledge
		on OLT what's mode is default for ONT.
	1 - select the auto master mode.
	2 - select the forced master mode.

	The default value of this attribute is zero.
 
 
	Applicable only for GPON.

           ALCATEL NOTE:
           ACCESS:    NA
           USAGE:     NA
           PERSIST:   YES
           INSRVMOD:  YES
           RANGE:     NA
           DEFVALUE:  NULL
           UNITS:     NA
           SPARSE:    NA"

 ::= { hpnaPortEntry 16 }

hpnaPortMasterSelectMode OBJECT-TYPE
	 SYNTAX INTEGER
	 ACCESS read-only
	 STATUS mandatory
	 DESCRIPTION
  " This attribute indicates the selected mode of the HomePNA MAC.
	0 - unknown master mode.
	1 - auto master mode.
	2 - forced master mode.
 
 
	Applicable only for GPON.

           ALCATEL NOTE:
           ACCESS:    NA
           USAGE:     NA
           PERSIST:   NO
           INSRVMOD:  YES
           RANGE:     NA
           DEFVALUE:  NULL
           UNITS:     NA
           SPARSE:    NA"

 ::= { hpnaPortEntry 17 }

hpnaPortConfigurationInd OBJECT-TYPE
	 SYNTAX INTEGER
	 ACCESS read-only
	 STATUS mandatory
	 DESCRIPTION
 	 " This attribute indicates the configuration status of the HPNA UNI. Valid values are:
		 0 - unknown (0), 
		 1 - coax 12_28 (1), 
		 2 - phone 12_28 (2).
 
 
	Applicable only for GPON.

           ALCATEL NOTE:
           ACCESS:    NA
           USAGE:     NA
           PERSIST:   NO
           INSRVMOD:  NO
           RANGE:     NA
           DEFVALUE:  NULL
           UNITS:     NA
           SPARSE:    NA"

 ::= { hpnaPortEntry 18 }

hpnaPortBaseMacAddress OBJECT-TYPE
	 SYNTAX OCTET STRING (SIZE (6))
	 ACCESS read-only
	 STATUS mandatory
	 DESCRIPTION
  	" This attribute indicates the unique layer 2 node address base for the HPNA hardware device.
 
 
	Applicable only for GPON.

           ALCATEL NOTE:
           ACCESS:    NA
           USAGE:     NA
           PERSIST:   NO
           INSRVMOD:  NO
           RANGE:     NA
           DEFVALUE:  NULL
           UNITS:     NA
           SPARSE:    NA"

 ::= { hpnaPortEntry 19 }

hpnaPortPwrShedOverride OBJECT-TYPE
	 SYNTAX  Boolean
	 ACCESS read-write
	 STATUS mandatory
	 DESCRIPTION 
	  "Allows setting as follows:
 
  	 TRUE = 1 = port excluded from data class power shedding
   	 FALSE = 0 = port included in data class power shedding
 
     	Default = 0 = FALSE 
 
   	As of FGU4.7.10, this is Supported.
	As of ISAM4.4, this is SUPPORTED.

           ALCATEL NOTE:
           ACCESS:    NA
           USAGE:     NA
           PERSIST:   YES
           INSRVMOD:  YES
           RANGE:     FALSE (0), TRUE (1)
           DEFVALUE:  FALSE (0)
           UNITS:     NA
           SPARSE:    NA"

 ::= { hpnaPortEntry 20 } 


-- *********************************************
--
-- GPON VEIP PORT TABLE
--
-- This table was first introduced with ISAM4.2 MIB.
-- It is only SUPPORTED beginning with ISAM4.2.02 release.

-- For ISAM 4.2.02, rows are auto-created by agent.  The number of rows auto-created is
-- determined from the bponOntPlanCardTable.
--
--	For GPON - SUPPORTED as of ISAM4.2.02
--	For XG-PON1 - SUPPORTED as of ISAM4.6.02
--	For NG-PON2 - NOT SUPPORTED as of ISAM5.2 (VEIP Card Type is NOT SUPPORTED)
-- 
-- 
-- *********************************************

gponVeipPortTable  OBJECT-TYPE
	SYNTAX SEQUENCE OF GponVeipPortEntry
	ACCESS	not-accessible
	STATUS	mandatory
	::= { gponVeipGroup 1 }


gponVeipPortEntry  OBJECT-TYPE
	SYNTAX 	GponVeipPortEntry
	ACCESS	not-accessible
	STATUS	mandatory
	INDEX	{ gponVeipPortOntIndex,
		  gponVeipPortSpIndex 
                }
	::= { gponVeipPortTable 1 }

GponVeipPortEntry ::= SEQUENCE {
	gponVeipPortOntIndex		IfIndex,
	gponVeipPortSpIndex			SpIndex,
	gponVeipPortInterdomainName	DisplayString,
	gponVeipPortEtherTrafficPmCollectInd		INTEGER,
	gponVeipPortEtherTrafficNumPMIntervals	INTEGER,
	gponVeipPortGwayPonLossBehaveMode	INTEGER
}

gponVeipPortOntIndex  OBJECT-TYPE
	SYNTAX 	IfIndex
	ACCESS	read-only
	STATUS	mandatory
	DESCRIPTION 
		" Each row is indexed by the ifIndex of the ONT  "
	::= { gponVeipPortEntry 1 }


gponVeipPortSpIndex  OBJECT-TYPE
	SYNTAX 	SpIndex
	ACCESS	read-only
	STATUS	mandatory
	DESCRIPTION 
		"Each row is also indexed by a number that
		 contains the slot number and port number
		 within the ONT.  "
	::= { gponVeipPortEntry 2 }

gponVeipPortInterdomainName  OBJECT-TYPE
	SYNTAX 	DisplayString
	ACCESS	read-write
	STATUS	mandatory
	DESCRIPTION 
		" Can be used to identify this Virtual Ethernet Interface Point to the non-OMCI management domain on the ONT.

		  Maximum of 25 displayable characters.

		  Default = null string

		  Modification is permitted. "

	::= { gponVeipPortEntry 3 }

gponVeipPortEtherTrafficPmCollectInd  OBJECT-TYPE
	SYNTAX 	INTEGER
	ACCESS	read-write
	STATUS	mandatory
	DESCRIPTION 
		" This indicates whether Ethernet Traffic Performance Monitors
		   should be collected for this VEIP Port.
	
		  1 = PM collection enabled
		  2 = PM collection disabled

		 Default = 2 = disabled.

		  Modification is permitted.   "
	::= { gponVeipPortEntry 4 }

gponVeipPortEtherTrafficNumPMIntervals  OBJECT-TYPE
	SYNTAX 	INTEGER
	ACCESS	read-only
	STATUS	mandatory
	DESCRIPTION 
		" Indicates the number of rows currently present
		  in the gponEtherTrafficIntervalTable.  This
		  is for convenience of the EMS, so that it can
		 quickly determine how many rows should be 
		 uploaded.   "
	::= { gponVeipPortEntry 5 }


gponVeipPortGwayPonLossBehaveMode  OBJECT-TYPE
	SYNTAX 	INTEGER
	ACCESS	read-write
	STATUS	mandatory
	DESCRIPTION 
		" Indicates how gateway connected VEIP UNI state should behave following ONT PON loss 
		  (e.g in regards to DHCP session re-establishment).

		   0 = 'Do Not Care and do not send any OMCI' (DEFAULT)		
		   1 = Link Pass Thru (LPT) Enable. Means the UNI goes Down when PON goes Down.
		   2 = Link Pass Thru (LPT) Disable.  Means UNI stays Up when PON goes Down.

		  Modification is permitted.   "
	::= { gponVeipPortEntry 6 }




-- *********************************************
-- GPON POWER SHED PROFILE TABLE
--
--This table is only used for GPON.
--
-- This table contains Power Shedding information that is
-- associated with a specific ONT.  Contains timers for
-- various UNI classes, regarding how long such UNI class
-- should remain powered when on battery backup. 
--  Rows are created by the operator.
--
-- NOTE: Profile cannot be deleted if associated 
-- with an ONT.  Profile cannot be modified at all.
--
-- NOTE: As of FGU4.4, this entire table is SUPPORTED.
--
-- For ISAM4.0.10, this table is being re-used. 
-- Noted which attributes are relevant for ISAM4.0.10
--
--	For GPON - SUPPORTED as of ISAM4.0.10
--	For XG-PON1 - SUPPORTED as of ISAM4.6.02
--	For NG-PON2 - SUPPORTED as of ISAM5.2 
-- 
--
-- *********************************************

gponPwrShedProfileTable OBJECT-TYPE
	SYNTAX	SEQUENCE OF GponPwrShedProfileEntry
	ACCESS	not-accessible
	STATUS	mandatory
	DESCRIPTION
		"This object contains a table for creating and storing
		Power Shed profiles. A  profile contains timers for
		how long a UNI class stays powered when on battery.  "
::= { gponProfilesGroup 9 }

gponPwrShedProfileEntry OBJECT-TYPE
	SYNTAX 	GponPwrShedProfileEntry
	ACCESS	not-accessible
	STATUS	mandatory
	DESCRIPTION
		"Rows of this table contain Power Shed Profiles"
	INDEX {gponPwrShedProfileIndex }
::= {gponPwrShedProfileTable 1}

GponPwrShedProfileEntry ::=
	SEQUENCE { 
		gponPwrShedProfileIndex		AsamProfileIndex,
		gponPwrShedProfileName		AsamProfileName,
		gponPwrShedProfileRefCount	AsamProfileRefCount,
		gponPwrShedProfileScope		AsamProfileScope,
		gponPwrShedProfileRowStatus 	RowStatus,
		gponPwrShedProfileRestoreTime		INTEGER,
		gponPwrShedProfileDataClassTime		INTEGER,
		gponPwrShedProfileVoiceClassTime		INTEGER,
		gponPwrShedProfileVideoClassTime		INTEGER,
		gponPwrShedProfileDslClassTime		INTEGER,
		gponPwrShedProfileCesClassTime		INTEGER
}

gponPwrShedProfileIndex OBJECT-TYPE 
	SYNTAX AsamProfileIndex
	ACCESS not-accessible
	STATUS mandatory
	DESCRIPTION
	    "This object is the index to the gponPwrShedProfileTable.

	For ISAM 4.0.10 -> stays the same as latest FGU4.x "
::= { gponPwrShedProfileEntry 1}

gponPwrShedProfileName 	OBJECT-TYPE 
	SYNTAX	AsamProfileName
	ACCESS read-write
	STATUS mandatory
	DESCRIPTION
	    "Octet string storing the operator-given name of the profile

	For ISAM 4.0.10 -> stays the same as latest FGU4.x "
::= {gponPwrShedProfileEntry 2}

gponPwrShedProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted.

		For ISAM 4.0.10 -> stays the same as latest FGU4.x "
::= { gponPwrShedProfileEntry  3}


gponPwrShedProfileScope OBJECT-TYPE
        	SYNTAX          AsamProfileScope
        	ACCESS          read-write
        	STATUS          mandatory
        	DESCRIPTION     
       		 "A  profile can be qualified as having a local scope or a network wide 
         		scope.

		Default = 1 = local scope.

		For ISAM 4.0.10 -> stays the same as latest FGU4.x "
::= {gponPwrShedProfileEntry  4}


gponPwrShedProfileRowStatus OBJECT-TYPE 
	SYNTAX	RowStatus
	ACCESS	read-write
	STATUS  mandatory
	DESCRIPTION
		"This object is used to create a new row or modify or
         		delete an existing row in this table. 
       		     o The entry associated with a Profile that is being used may
             		 not be deleted.

		For ISAM 4.0.10 -> stays the same as latest FGU4.x "
::= { gponPwrShedProfileEntry  5}


gponPwrShedProfileRestoreTime OBJECT-TYPE 
	SYNTAX INTEGER
	ACCESS read-write
	STATUS mandatory
	DESCRIPTION
	    	" Specifies the time delay required before resetting timers to zero
		  after a full power restore. Units are seconds.
	
		 Default = 0.

		For ISAM 4.0.10 -> stays the same as latest FGU4.x  "
::= { gponPwrShedProfileEntry  6}


gponPwrShedProfileDataClassTime OBJECT-TYPE 
	SYNTAX INTEGER
	ACCESS read-write
	STATUS mandatory
	DESCRIPTION
	    	" Specifies the time delay required before shedding power for
		  Data UNI classes (applies to Ethernet, HPNA and MoCA UNIs).
		  Units are seconds. Zero means no-shed, and one means
		  immediate-shed.

		  Range is 0 - 28800 (8 hours).
	
		 Default = 0.

		For ISAM 4.0.10 -> stays the same as latest FGU4.x "
::= { gponPwrShedProfileEntry  7 }


gponPwrShedProfileVoiceClassTime OBJECT-TYPE 
	SYNTAX INTEGER
	ACCESS read-write
	STATUS mandatory
	DESCRIPTION
	    	" Specifies the time delay required before shedding power for
		  Voice UNI classes (applies to POTS UNIs - and may also
		  apply to associated VDSL1/VDSL2 UNI if they share the same physical port
		  and the ONT cannot shed voice and DSL independently on same UNI port).
		  Units are seconds. Zero means no-shed, and one means
		  immediate-shed.

		  Range is 0 - 28800 (8 hours).
	
		 Default = 0.

		For ISAM 4.0.10 -> stays the same as latest FGU4.x "
::= { gponPwrShedProfileEntry  8 }

gponPwrShedProfileVideoClassTime OBJECT-TYPE 
	SYNTAX INTEGER
	ACCESS read-write
	STATUS mandatory
	DESCRIPTION
	    	" Specifies the time delay required before shedding power for
		  the Video ANI class.
		  Units are seconds. Zero means no-shed, and one means
		  immediate-shed.

		  Range is 0 - 28800 (8 hours).
	
		 Default = 0.

		For ISAM 4.0.10 -> stays the same as latest FGU4.x "
::= { gponPwrShedProfileEntry  9 }

gponPwrShedProfileDslClassTime OBJECT-TYPE 
	SYNTAX INTEGER
	ACCESS read-write
	STATUS mandatory
	DESCRIPTION
	    	" Specifies the time delay required before shedding power for
		  DSL UNI classes (applies to VDSL1 and VDSL2 UNIs that do not
		  have a shared POTS port provisioned and/or for an ONT that can
		  shed voice and DSL independently on same UNI port).
		  Units are seconds. Zero means no-shed, and one means
		  immediate-shed.

		  Range is 0 - 28800 (8 hours).
	
		 Default = 0.

		For ISAM 4.0.10 -> stays the same as latest FGU4.x "
::= { gponPwrShedProfileEntry  10 }

gponPwrShedProfileCesClassTime OBJECT-TYPE 
	SYNTAX INTEGER
	ACCESS read-write
	STATUS mandatory
	DESCRIPTION
	    	" Specifies the time delay required before shedding power for
		  CES UNI classes. Units are seconds. Zero means no-shed, 
		  and one means immediate-shed.

		  Range is 0 - 28800 (8 hours).
	
		 Default = 0.

		For ISAM 4.0.10 -> stays the same as latest FGU4.x "
::= { gponPwrShedProfileEntry  11 }


gponPwrShedProfileIndexNext        OBJECT-TYPE
        	SYNTAX          AsamNextProfileIndex
        	ACCESS          read-only
        	STATUS          mandatory
        	DESCRIPTION     
        	"This object contains an appropriate value to be used for 
         		gponPwrShedProfileIndex when creating entries in the
         		gponPwrShedProfileTable. 
         		The value 0 indicates that no unassigned entries are available. To 
         		obtain the next index value for a new entry, the
        		 manager issues a management protocol retrieval operation to obtain the
         		current value of this object.  After each retrieval, the agent should
        		 modify the value to the next unassigned index.

		As of FGU4.2, this is Not Supported.

		For ISAM 4.0.10 -> stays the same as latest FGU4.x  "
::= {gponProfilesGroup 10 }


  gponPwrShedProfileMaxIndex        OBJECT-TYPE
      	SYNTAX            AsamMaxProfileIndex
      	ACCESS            read-only
     	 STATUS            mandatory
      	DESCRIPTION
            	"This object represents the maximum number of
            		 gponPwrShedProfiles that can be created. The object
             		 gponPwrShedProfileIndexNext will have values ranging
            		 from 0 to the value represented by this object. 
		 For FGU4.0, initially set to 20.

		 As of FGU4.2, this is Not Supported.

		For ISAM 4.0.10 -> stays the same as latest FGU4.x "
::= {gponProfilesGroup 11 }


-- *********************************************
-- CES MAINTENANCE PROFILE TABLE
--
--This table is only used for GPON.
--
-- The CES maintenance profile permits the configuration of pseudowire service exception handling.
-- The maintenance profile affects the behavior of the CES performance monitoring data in establishing
-- criteria for counting severely errored seconds. The pseudowire maintenance profile primarily affects the
-- alarms declared by the subscribing pseudowire termination point (i.e. CES Service).
--
--  Rows are created by the operator.
--
-- NOTE: Profile cannot be deleted if associated 
-- with a CES Service.  Profile cannot be modified at all.
--
-- For ISAM4.0.10, this table is being re-used. 
-- Noted which attributes are relevant for ISAM4.0.10
--
--
--	For GPON - SUPPORTED as of ISAM4.0.10
--	For XG-PON1 - SUPPORTED as of ISAM4.6.02
--	For NG-PON2 - NOT SUPPORTED as of ISAM5.2 (CES Card Type is NOT SUPPORTED)
-- 
--
-- *********************************************

gponCesMaintProfileTable OBJECT-TYPE
	SYNTAX	SEQUENCE OF GponCesMaintProfileEntry
	ACCESS	not-accessible
	STATUS	mandatory
	DESCRIPTION
		"This object contains a table for creating and storing
		CES Maintenance profiles.  "
::= { gponProfilesGroup 12 }

gponCesMaintProfileEntry OBJECT-TYPE
	SYNTAX 	GponCesMaintProfileEntry
	ACCESS	not-accessible
	STATUS	mandatory
	DESCRIPTION
		"Rows of this table contain CES Maintenance Profiles"
	INDEX {gponCesMaintProfileIndex }
::= {gponCesMaintProfileTable 1}

GponCesMaintProfileEntry ::=
	SEQUENCE { 
		gponCesMaintProfileIndex		AsamProfileIndex,
		gponCesMaintProfileName		AsamProfileName,
		gponCesMaintProfileRefCount	AsamProfileRefCount,
		gponCesMaintProfileScope		AsamProfileScope,
		gponCesMaintProfileRowStatus 	RowStatus,
		gponCesMaintProfileJitterBufferMaxDepth		INTEGER,
		gponCesMaintProfileJitterBufferDesiredDepth		INTEGER,
		gponCesMaintProfileFillPolicy		INTEGER,
		gponCesMaintProfileMisconnectedPktsDeclarePolicy		INTEGER,
		gponCesMaintProfileMisconnectedPktsClearPolicy		INTEGER,
		gponCesMaintProfileLostPktsDeclarePolicy		INTEGER,
		gponCesMaintProfileLostPktsClearPolicy		INTEGER,
		gponCesMaintProfileBufferOverUnderRunDeclarePolicy	INTEGER,
		gponCesMaintProfileBufferOverUnderRunClearPolicy	INTEGER,
		gponCesMaintProfileMalformedPktsDeclarePolicy	INTEGER,
		gponCesMaintProfileMalformedPktsClearPolicy	INTEGER,
		gponCesMaintProfileRbitTransmitSetPolicy		INTEGER,
		gponCesMaintProfileRbitTransmitClearPolicy		INTEGER,
		gponCesMaintProfileRbitReceivePolicy			INTEGER,
		gponCesMaintProfileLbitReceivePolicy			INTEGER,
		gponCesMaintSESThreshold				INTEGER
}

gponCesMaintProfileIndex OBJECT-TYPE 
	SYNTAX AsamProfileIndex
	ACCESS not-accessible
	STATUS mandatory
	DESCRIPTION
	    "This object is the index to the gponCesMaintProfileTable.

	For ISAM 4.0.10 -> stays the same as latest FGU4.x "
::= { gponCesMaintProfileEntry 1}

gponCesMaintProfileName 	OBJECT-TYPE 
	SYNTAX	AsamProfileName
	ACCESS read-write
	STATUS mandatory
	DESCRIPTION
	    "Octet string storing the operator-given name of the profile

	For ISAM 4.0.10 -> stays the same as latest FGU4.x "
::= {gponCesMaintProfileEntry 2}

gponCesMaintProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted.

		For ISAM 4.0.10 -> stays the same as latest FGU4.x "
::= { gponCesMaintProfileEntry  3}


gponCesMaintProfileScope OBJECT-TYPE
        	SYNTAX          AsamProfileScope
        	ACCESS          read-write
        	STATUS          mandatory
        	DESCRIPTION     
       		 "A  profile can be qualified as having a local scope or a network wide 
         		scope.

		Default = 1 = local scope.

		For ISAM 4.0.10 -> stays the same as latest FGU4.x "
::= {gponCesMaintProfileEntry  4}


gponCesMaintProfileRowStatus OBJECT-TYPE 
	SYNTAX	RowStatus
	ACCESS	read-write
	STATUS  mandatory
	DESCRIPTION
		"This object is used to create a new row or modify or
         		delete an existing row in this table. 
       		     o The entry associated with a Profile that is being used may
             		 not be deleted.

		For ISAM 4.0.10 -> stays the same as latest FGU4.x "
::= { gponCesMaintProfileEntry  5}


gponCesMaintProfileJitterBufferMaxDepth OBJECT-TYPE 
	SYNTAX INTEGER
	ACCESS read-write
	STATUS mandatory
	DESCRIPTION
	    	" This attribute specifies the desired maximum depth of the playout buffer in 
		  the PSN to TDM direction. The value is expressed as a multiple of the 125 micro-second frame rate.
		  The default value 0 selects the ONT's internal policy.

		  NOTE: FGU4.3 ONT only provide millisecond resolution.  If OLT sends value that is not a 
		  multiple of 8, ONT will round to next highest millisecond.  ONT supports values 
		  from 1 - 200 milliseconds.

		  NOTE: OLT should enforce the following VALIDITY RULE:
		  Max Jitter Delay in msec > 1.5 * (payload length in frames) * 0.125

		For ISAM 4.0.10 -> stays the same as latest FGU4.x  "
::= { gponCesMaintProfileEntry  6}


gponCesMaintProfileJitterBufferDesiredDepth OBJECT-TYPE 
	SYNTAX INTEGER
	ACCESS read-write
	STATUS mandatory
	DESCRIPTION
	    	" This attribute specifies the desired nominal fill depth of the playout buffer in the PSN to TDM
		   direction. The value is expressed as a multiple of the 125 micro-second frame rate.  The default value 0 
		   selects the ONT's internal policy.

		   For FGU4.3, NOT SUPPORTED. Default = 0.

		For ISAM 4.0.10 -> stays the same as latest FGU4.x  "
::= { gponCesMaintProfileEntry  7 }


gponCesMaintProfileFillPolicy OBJECT-TYPE 
	SYNTAX INTEGER
	ACCESS read-write
	STATUS mandatory
	DESCRIPTION
	    	" This attribute defines the payload bit pattern to be applied toward the TDM service if no payload 
		   packet is available to play out. The default value 0 specifies that the ONT applies its internal policy.

		  0 - ONT default, vendor-specific (recommended: AIS for unstructured service, all 1s for structured service) (Default) (SUPPORTED)
		  1 - Play out AIS according to the service definition (for example, DS3 AIS) - NOT SUPPORTED
		  2 - Play out all 1s (SUPPORTED)
		  3 - Play out all 0s (NOT SUPPORTED)
		  4 - Repeat the previous data - NOT SUPPORTED
		  5 - Play out DS1 idle (ANSI T1.403-1999 appendix C) - (SUPPORTED)

		  NOTE: Within the same ONT, if multiple Maintenance Profiles are referenced, this atrribute values must
		  be the same across all profiles (ONT limitation).

		For ISAM 4.0.10 -> stays the same as latest FGU4.x "
::= { gponCesMaintProfileEntry  8 }

gponCesMaintProfileMisconnectedPktsDeclarePolicy OBJECT-TYPE 
	SYNTAX INTEGER
	ACCESS read-write
	STATUS mandatory
	DESCRIPTION
	    	" This attribute defines the packet anomaly rate that causes the misconnected packets alarm
		   to be declared. It is an integer percentage between 1-100. If this density of anomalies occurs 
		   during the alarm onset soak interval, the alarm is declared. The default value 0 selects the ONT's 
		   internal policy.
		
		   For FGU4.3, NOT SUPPORTED. Default = 0.

		For ISAM 4.0.10 -> stays the same as latest FGU4.x "
::= { gponCesMaintProfileEntry  9 }

gponCesMaintProfileMisconnectedPktsClearPolicy OBJECT-TYPE 
	SYNTAX INTEGER
	ACCESS read-write
	STATUS mandatory
	DESCRIPTION
	    	" This attribute defines the packet anomaly rate that causes the misconnected packets alarm to be 
		   cleared. It is an integer percentage between 0-99. If no more than this density of anomalies occurs
		   during the alarm clear soak interval, the alarm is cleared. The default value 255 selects the ONT's 
		   internal policy.

		   For FGU4.3, NOT SUPPORTED. Default = 255.

		For ISAM 4.0.10 -> stays the same as latest FGU4.x  "
::= { gponCesMaintProfileEntry  10 }

gponCesMaintProfileLostPktsDeclarePolicy OBJECT-TYPE 
	SYNTAX INTEGER
	ACCESS read-write
	STATUS mandatory
	DESCRIPTION
	    	" This attribute defines the criteria for declaring the loss of packets alarm.  It is an integer percentage
		  between 1-100. If this density of anomalies occurs during the alarm onset soak interval, the alarm
		  is declared. The default value 0 selects the ONT's internal policy.
		
		   For FGU4.3, NOT SUPPORTED. Default = 0.

		For ISAM 4.0.10 -> stays the same as latest FGU4.x "
::= { gponCesMaintProfileEntry  11 }

gponCesMaintProfileLostPktsClearPolicy OBJECT-TYPE 
	SYNTAX INTEGER
	ACCESS read-write
	STATUS mandatory
	DESCRIPTION
	    	" This attribute defines the criteria for clearing the loss of packets alarm. It is an integer percentage
		  between 0-99. If no more than this density of anomalies occurs during the alarm clear soak interval, 
		  the alarm is cleared. The default value 255 selects the ONT's internal policy.

		   For FGU4.3, NOT SUPPORTED. Default = 255.

		For ISAM 4.0.10 -> stays the same as latest FGU4.x  "
::= { gponCesMaintProfileEntry  12 }

gponCesMaintProfileBufferOverUnderRunDeclarePolicy OBJECT-TYPE 
	SYNTAX INTEGER
	ACCESS read-write
	STATUS mandatory
	DESCRIPTION
	    	" This attribute defines the criteria for declaring the buffer overrun and underrun alarms.  It is an integer
		  percentage between 1-100. If this density of anomalies occurs during the alarm onset soak interval, 
		  the alarm is declared.  The default value 0 selects the ONT's internal policy.
		
		   For FGU4.3, NOT SUPPORTED. Default = 0.

		For ISAM 4.0.10 -> stays the same as latest FGU4.x "
::= { gponCesMaintProfileEntry  13 }

gponCesMaintProfileBufferOverUnderRunClearPolicy OBJECT-TYPE 
	SYNTAX INTEGER
	ACCESS read-write
	STATUS mandatory
	DESCRIPTION
	    	" This attribute defines the criteria for clearing the buffer overrun and underrun alarms. It is an integer
		  percentage between 0-99. If no more than this density of anomalies occurs during the alarm clear 
		  soak interval, the alarm is cleared. The default value 255 selects the ONT's internal policy.

		   For FGU4.3, NOT SUPPORTED. Default = 255.

		For ISAM 4.0.10 -> stays the same as latest FGU4.x  "
::= { gponCesMaintProfileEntry  14 }

gponCesMaintProfileMalformedPktsDeclarePolicy OBJECT-TYPE 
	SYNTAX INTEGER
	ACCESS read-write
	STATUS mandatory
	DESCRIPTION
	    	" This attribute defines the criteria for declaring the malformed packets alarm.  It is an integer percentage
		  between 1-100. If this density of anomalies occurs during the alarm onset soak interval, the alarm
		  is declared. The default value 0 selects the ONT's internal policy.
		
		   For FGU4.3, NOT SUPPORTED. Default = 0.

		For ISAM 4.0.10 -> stays the same as latest FGU4.x "
::= { gponCesMaintProfileEntry  15 }

gponCesMaintProfileMalformedPktsClearPolicy OBJECT-TYPE 
	SYNTAX INTEGER
	ACCESS read-write
	STATUS mandatory
	DESCRIPTION
	    	" This attribute defines the criteria for clearing the malformed packets alarm. It is an integer percentage
		  between 0-99. If no more than this density of anomalies occurs during the alarm clear soak interval, 
		  the alarm is cleared. The default value 255 selects the ONT's internal policy.

		   For FGU4.3, NOT SUPPORTED. Default = 255.

		For ISAM 4.0.10 -> stays the same as latest FGU4.x  "
::= { gponCesMaintProfileEntry  16 }

gponCesMaintProfileRbitTransmitSetPolicy OBJECT-TYPE 
	SYNTAX INTEGER
	ACCESS read-write
	STATUS mandatory
	DESCRIPTION
	    	" This attribute defines the number of consecutive lost packets that causes the transmitted R bit
		   to be set in the TDM to PSN direction, indicating lost packets to the far end. The default value 0 
		   selects the ONT's internal policy. 
		
		   For FGU4.3, NOT SUPPORTED. Default = 0.

		For ISAM 4.0.10 -> stays the same as latest FGU4.x "
::= { gponCesMaintProfileEntry  17 }

gponCesMaintProfileRbitTransmitClearPolicy OBJECT-TYPE 
	SYNTAX INTEGER
	ACCESS read-write
	STATUS mandatory
	DESCRIPTION
	    	" This attribute defines the number of consecutive valid packets that causes the transmitted R bit
		   to be cleared in the TDM to PSN direction, removing the remote failure indication to the far end.
		   The default value 0 selects the ONT's internal policy. 

		   For FGU4.3, NOT SUPPORTED. Default = 255.

		For ISAM 4.0.10 -> stays the same as latest FGU4.x  "
::= { gponCesMaintProfileEntry  18 }

gponCesMaintProfileRbitReceivePolicy OBJECT-TYPE 
	SYNTAX INTEGER
	ACCESS read-write
	STATUS mandatory
	DESCRIPTION
	    	" This attribute defines the action toward the Nx64 TDM interface when remote failure is
		   indicated on packets received from the PSN (either R bit set or M = 0b10 while L bit is cleared).
		   0 - Do nothing (default)
		   1 - Play out service-specific RAI/REI/RDI code
		   2 - Send channel idle signalling and idle channel payload to all DS0s comprising the service

		   NOTE: Within the same ONT, if multiple Maintenance Profiles are referenced, this atrribute value
		   must be the same across all profiles (ONT limitation).

		For ISAM 4.0.10 -> stays the same as latest FGU4.x  "
::= { gponCesMaintProfileEntry  19 }

gponCesMaintProfileLbitReceivePolicy OBJECT-TYPE 
	SYNTAX INTEGER
	ACCESS read-write
	STATUS mandatory
	DESCRIPTION
	    	" This attribute defines the action toward the TDM interface when far end TDM failure is indicated
		   on packets received from the PSN (L bit set).
		   0 - Play out service-specific AIS (default)
		   1 - Repeat last received packet (NOT SUPPORTED by Resolute for FGU4.3)
		   2 - Send channel idle signalling and idle channel payload to all DS0s comprising the service

		  NOTE: Within the same ONT, if multiple Maintenance Profiles are referenced, this atrribute value
		  must be the same across all profiles (ONT limitation).

		For ISAM 4.0.10 -> stays the same as latest FGU4.x  "
::= { gponCesMaintProfileEntry  20 }

gponCesMaintSESThreshold OBJECT-TYPE 
	SYNTAX INTEGER
	ACCESS read-write
	STATUS mandatory
	DESCRIPTION
	    	" Number of lost, malformed or otherwise unusable packets expected in the PSN to TDM direction
		  within a one-second interval that causes a severely errored second to be counted. Stray packets
		  do not count toward a severely-errored second, nor do packets whose L bit is set at the far end. 
		  The default value is 3.  

		  For FGU4.3, NOT SUPPORTED. Default = 3.

		For ISAM 4.0.10 -> stays the same as latest FGU4.x "
::= { gponCesMaintProfileEntry  21 }


gponCesMaintProfileIndexNext        OBJECT-TYPE
        	SYNTAX          AsamNextProfileIndex
        	ACCESS          read-only
        	STATUS          mandatory
        	DESCRIPTION     
        	"This object contains an appropriate value to be used for 
         		gponCesMaintProfileIndex when creating entries in the
         		gponCesMaintProfileTable. 
         		The value 0 indicates that no unassigned entries are available. To 
         		obtain the next index value for a new entry, the
        		 manager issues a management protocol retrieval operation to obtain the
         		current value of this object.  After each retrieval, the agent should
        		 modify the value to the next unassigned index.

		For ISAM 4.0.10 -> stays the same as latest FGU4.x  "
::= {gponProfilesGroup 13 }


  gponCesMaintProfileMaxIndex        OBJECT-TYPE
      	SYNTAX            AsamMaxProfileIndex
      	ACCESS            read-only
     	 STATUS            mandatory
      	DESCRIPTION
            	"This object represents the maximum number of
            		 gponCesMaintProfiles that can be created. The object
             		 gponCesMaintProfileIndexNext will have values ranging
            		 from 0 to the value represented by this object. 
		 For FGU4.3, initially set to 20.

		For ISAM 4.0.10 -> stays the same as latest FGU4.x  "
::= {gponProfilesGroup 14 }



-- *********************************************
-- GPON LARGE STRING PROFILE TABLE
--
-- This table is only used for GPON.
--
-- This table contains entries of large strings.  The strings usually contain
-- network addresses, Fully Qualified Domain Names, etc. that can be 
-- pointed to from other entities (e.g. a Voip Client Service). Usage of this 
-- profile structure is most appropriate when a common address must be 
-- specified for multiple entities (e.g. many ONT Voip Clients needing to 
-- acquire a common SIP Server address).
--
-- From an OMCI standpoint, it maps primarily to the Large String ME.
--
--  Rows are created by the operator.
--
-- NOTE: For FGU4.4 -> Profile cannot be deleted if associated 
-- with a service.  Profile cannot be modified at all.
--
-- For ISAM4.0.10, this table is NOT SUPPORTED.
--
-- For ISAM4.2, this entire table is NOT SUPPORTED.
--
--	For GPON - SUPPORTED as of ISAM4.2
--	For XG-PON1 - SUPPORTED as of ISAM4.6.02
--	For NG-PON2 - NOT SUPPORTED as of ISAM5.2 (POTS Card Type is NOT SUPPORTED)
-- 
--
-- *********************************************

gponLargeStringProfileTable OBJECT-TYPE
	SYNTAX	SEQUENCE OF GponLargeStringProfileEntry
	ACCESS	not-accessible
	STATUS	mandatory
	DESCRIPTION
		"This object contains a table for creating and storing
		large string profiles (that represent network addresses). 
		These profiles are normally associated with Voip Services
		that must reference a common network address . "
::= { gponProfilesGroup 18 }

gponLargeStringProfileEntry OBJECT-TYPE
	SYNTAX 	GponLargeStringProfileEntry
	ACCESS	not-accessible
	STATUS	mandatory
	DESCRIPTION
		"Rows of this table contain large string Profiles"
	INDEX {gponLargeStringProfileIndex }
::= {gponLargeStringProfileTable 1}

GponLargeStringProfileEntry ::=
	SEQUENCE { 
		gponLargeStringProfileIndex		AsamProfileIndex,
		gponLargeStringProfileName		AsamProfileName,
		gponLargeStringProfileRefCount	AsamProfileRefCount,
		gponLargeStringProfileScope	AsamProfileScope,
		gponLargeStringProfileRowStatus 	RowStatus,
		gponLargeStringProfileAddress	DisplayString
}

gponLargeStringProfileIndex OBJECT-TYPE 
	SYNTAX AsamProfileIndex
	ACCESS not-accessible
	STATUS mandatory
	DESCRIPTION
	    "This object is the index to the gponLargeStringProfileTable.

		For ISAM 4.0.10 -> NOT SUPPORTED "
::= { gponLargeStringProfileEntry 1}

gponLargeStringProfileName 	OBJECT-TYPE 
	SYNTAX	AsamProfileName
	ACCESS read-write
	STATUS mandatory
	DESCRIPTION
	    "Octet string storing the operator-given name of the profile.

		For ISAM 4.0.10 -> NOT SUPPORTED "
::= {gponLargeStringProfileEntry 2}

gponLargeStringProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted.

		For ISAM 4.0.10 -> NOT SUPPORTED "
::= { gponLargeStringProfileEntry  3}


gponLargeStringProfileScope OBJECT-TYPE
        	SYNTAX          AsamProfileScope
        	ACCESS          read-write
        	STATUS          mandatory
        	DESCRIPTION     
       		 "A  profile can be qualified as having a local scope or a network wide 
         		scope.

		Default = 1 = local scope.

		For ISAM 4.0.10 -> NOT SUPPORTED "
::= {gponLargeStringProfileEntry  4}


gponLargeStringProfileRowStatus OBJECT-TYPE 
	SYNTAX	RowStatus
	ACCESS	read-write
	STATUS  mandatory
	DESCRIPTION
		"This object is used to create a new row or modify or
         		delete an existing row in this table. 
       		     o The entry associated with a Profile that is being used may
             		 not be deleted.

		For ISAM 4.0.10 -> NOT SUPPORTED "
::= { gponLargeStringProfileEntry  5}


gponLargeStringProfileAddress OBJECT-TYPE 
	SYNTAX 	DisplayString (SIZE(0..100))
	ACCESS	read-write
	STATUS	mandatory
	DESCRIPTION 
		"This is a textual string that contains an address.
		 This string can represent a Fully Qualified Domain
		 Name (FQDN), or an IP Address (in dot notation), or other formats
		 parseable by the ONT.

		 Default - null string. 

		 Modification is not permitted.

		For ISAM 4.0.10 -> NOT SUPPORTED  "
::= { gponLargeStringProfileEntry  6}


gponLargeStringProfileIndexNext        OBJECT-TYPE
        	SYNTAX          AsamNextProfileIndex
        	ACCESS          read-only
        	STATUS          mandatory
        	DESCRIPTION     
        	"This object contains an appropriate value to be used for 
         		gponLargeStringProfileIndex when creating entries in the
         		gponLargeStringProfileTable. 
         		The value 0 indicates that no unassigned entries are available. To 
         		obtain the next index value for a new entry, the
        		 manager issues a management protocol retrieval operation to obtain the
         		current value of this object.  After each retrieval, the agent should
        		 modify the value to the next unassigned index.

		For ISAM 4.0.10 -> NOT SUPPORTED "
::= {gponProfilesGroup 19 }


  gponLargeStringProfileMaxIndex        OBJECT-TYPE
      	SYNTAX            AsamMaxProfileIndex
      	ACCESS            read-only
     	 STATUS            mandatory
      	DESCRIPTION
            	"This object represents the maximum number of
            		 gponLargeStringProfiles that can be created. The object
             		 gponLargeStringProfileIndexNext will have values ranging
            		 from 0 to the value represented by this object. 
		 For FGU4.4, initially set to 20.

		For ISAM 4.0.10 -> NOT SUPPORTED "
::= {gponProfilesGroup 20 }



-- *********************************************
-- GPON AUTHENTICATION SECURITY PROFILE TABLE
--
-- This table was first introduced with ISAM4.2 MIB.
-- It is only SUPPORTED beginning with ISAM4.2.02 release.
--
-- This table contains authentication information (which is potentially required
-- when accessing a network address). 
-- From an OMCI standpoint, it maps primarily to the Authenticaton Security Data ME.
--
--  Rows are created by the operator.
--
-- NOTE: Profile cannot be deleted if associated with another table.
--
--	For GPON - SUPPORTED as of ISAM4.2.02
--	For XG-PON1 - SUPPORTED as of ISAM4.6.02
--  For NG-PON2 - SUPPORTED as of ISAM5.4.01
-- 
--
-- *********************************************

gponAuthSecurityProfileTable OBJECT-TYPE
	SYNTAX	SEQUENCE OF GponAuthSecurityProfileEntry
	ACCESS	not-accessible
	STATUS	mandatory
	DESCRIPTION
		"This object contains a table for creating and storing
		authentication security information for contacting
		network addresses.. 
		These profiles are normally associated with Voip Services
		that must reference a common authentication information . "
::= { gponProfilesGroup 26 }

gponAuthSecurityProfileEntry OBJECT-TYPE
	SYNTAX 	GponAuthSecurityProfileEntry
	ACCESS	not-accessible
	STATUS	mandatory
	DESCRIPTION
		"Rows of this table contain authentication security Profiles"
	INDEX {gponAuthSecurityProfileIndex }
::= {gponAuthSecurityProfileTable 1}

GponAuthSecurityProfileEntry ::=
	SEQUENCE { 
		gponAuthSecurityProfileIndex		AsamProfileIndex,
		gponAuthSecurityProfileName		AsamProfileName,
		gponAuthSecurityProfileRefCount	AsamProfileRefCount,
		gponAuthSecurityProfileScope	AsamProfileScope,
		gponAuthSecurityProfileRowStatus 	RowStatus,
		gponAuthSecurityProfileValidScheme	INTEGER,
		gponAuthSecurityProfileUsername	DisplayString,
		gponAuthSecurityProfilePassword	DisplayString,
		gponAuthSecurityProfileRealm	DisplayString
}

gponAuthSecurityProfileIndex OBJECT-TYPE 
	SYNTAX AsamProfileIndex
	ACCESS not-accessible
	STATUS mandatory
	DESCRIPTION
	    "This object is the index to the gponAuthSecurityProfileTable. "
::= { gponAuthSecurityProfileEntry 1}

gponAuthSecurityProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponAuthSecurityProfileEntry 2}

gponAuthSecurityProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponAuthSecurityProfileEntry  3}


gponAuthSecurityProfileScope OBJECT-TYPE
        	SYNTAX          AsamProfileScope
        	ACCESS          read-write
        	STATUS          mandatory
        	DESCRIPTION     
       		 "A  profile can be qualified as having a local scope or a network wide 
         		scope.

		Default = 1 = local scope. "
::= {gponAuthSecurityProfileEntry  4}


gponAuthSecurityProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponAuthSecurityProfileEntry  5}

gponAuthSecurityProfileValidScheme  OBJECT-TYPE
	SYNTAX 	INTEGER
	ACCESS	read-write
	STATUS	mandatory
	DESCRIPTION 
		"This attribute contains the Validation Scheme required for authentication.

		 0 = Validation disabled
		 1 = Validate using MD5 digest authentication as defined in RFC 2617 (default)
		 2 = Validate using basic authentication as defined in [IETF RFC 2617]

		 Modification is NOT permitted.  "
	::= { gponAuthSecurityProfileEntry  6 }


gponAuthSecurityProfileUsername  OBJECT-TYPE
	SYNTAX 	DisplayString (SIZE(0..50))
	ACCESS	read-write
	STATUS	mandatory
	DESCRIPTION 
		"This is a textual string that contains the Username required for authentication.

		 Default - null string. 

		 Modification is NOT permitted.  "
	::= { gponAuthSecurityProfileEntry  7 }


gponAuthSecurityProfilePassword  OBJECT-TYPE
	SYNTAX 	DisplayString (SIZE(0..25))
	ACCESS	read-write
	STATUS	mandatory
	DESCRIPTION 
		"This is a textual string that contains the Password required for authentication. 

		 Default - null string. 

		 Modification is NOT permitted.  "
	::= { gponAuthSecurityProfileEntry  8 }


gponAuthSecurityProfileRealm  OBJECT-TYPE
	SYNTAX 	DisplayString (SIZE(0..25))
	ACCESS	read-write
	STATUS	mandatory
	DESCRIPTION 
		"This is a textual string that contains the Realm for authentication. 

		 Default - null string. 

		 Modification NOT permitted  "
	::= { gponAuthSecurityProfileEntry  9 }


gponAuthSecurityProfileIndexNext        OBJECT-TYPE
        	SYNTAX          AsamNextProfileIndex
        	ACCESS          read-only
        	STATUS          mandatory
        	DESCRIPTION     
        	"This object contains an appropriate value to be used for 
         		gponAuthSecurityProfileIndex when creating entries in the
         		gponAuthSecurityProfileTable. 
         		The value 0 indicates that no unassigned entries are available. To 
         		obtain the next index value for a new entry, the
        		 manager issues a management protocol retrieval operation to obtain the
         		current value of this object.  After each retrieval, the agent should
        		 modify the value to the next unassigned index. "
::= {gponProfilesGroup 27 }


  gponAuthSecurityProfileMaxIndex        OBJECT-TYPE
      	SYNTAX            AsamMaxProfileIndex
      	ACCESS            read-only
     	 STATUS            mandatory
      	DESCRIPTION
            	"This object represents the maximum number of
            		 gponAuthSecurityProfiles that can be created. The object
             		 gponAuthSecurityProfileIndexNext will have values ranging
            		 from 0 to the value represented by this object. 
		 For ISAM4.2,  initially set to 20. "
::= {gponProfilesGroup 28 }

-- *********************************************
-- GPON AUTHENTICATION SECURITY PROFILE MAPPING TABLE
--
-- This table was first introduced with ISAM4.2 MIB.
-- It is only SUPPORTED beginning with ISAM4.2.02 release.
--
-- For the gponAuthSecurityProfileTable, this table provides a reverse mapping
-- (i.e. profile name to profile index number).
--
-- The system automatically creates an entry in this Table when a  corresponding entry
-- in gponAuthSecurityProfile is created. 
-- The system automatically deletes an entry in this Table when a  corresponding entry
-- in gponAuthSecurityProfile is deleted.
--
--	For GPON - SUPPORTED as of ISAM4.2
--	For XG-PON1 - SUPPORTED as of ISAM4.6.02
--  For NG-PON2 - SUPPORTED as of ISAM5.4.01
--   
--
-- *********************************************

 
gponAuthSecurityProfileMappingTable OBJECT-TYPE
   SYNTAX   SEQUENCE OF GponAuthSecurityProfileMappingEntry
   ACCESS   not-accessible
   STATUS   mandatory
   DESCRIPTION
   "This object contains a table for gponAuthSecurityProfile
name to index mapping"
::= { gponProfilesGroup 29 }
 
gponAuthSecurityProfileMappingEntry OBJECT-TYPE
   SYNTAX   GponAuthSecurityProfileMappingEntry
   ACCESS   not-accessible
   STATUS mandatory
   DESCRIPTION
   " An entry (conceptual row) representing the gponAuthSecurityProfile Name to Index mapping."
   INDEX {gponAuthSecurityProfileMappingName }
   ::= {gponAuthSecurityProfileMappingTable  1}
 
GponAuthSecurityProfileMappingEntry ::=
   SEQUENCE { 
	gponAuthSecurityProfileMappingName     AsamProfileName,
      	gponAuthSecurityProfileMappingIndex      AsamProfileIndex
  }
 
gponAuthSecurityProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponAuthSecurityProfileMappingEntry 1}
 
gponAuthSecurityProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponAuthSecurityProfileMappingEntry 2}


-- *********************************************
-- GPON SECURE URI PROFILE TABLE
--
-- This table was first introduced with ISAM4.2 MIB.
-- It is only SUPPORTED beginning with ISAM4.2.02 release.
--
-- This table contains information regarding reference to a Uniform Resource Indicator profile,
-- along with reference to a profile that contains security/authentication information.
-- From an OMCI standpoint, it maps primarily to the Network Address ME.
--
--  Rows are created by the operator.
--
-- NOTE: Profile cannot be deleted if associated with another table.
--
--	For GPON - SUPPORTED as of ISAM4.2.02
--	For XG-PON1 - SUPPORTED as of ISAM4.6.02
--  For NG-PON2 - SUPPORTED as of ISAM5.4.01
-- 
--
-- *********************************************

gponSecureUriProfileTable OBJECT-TYPE
	SYNTAX	SEQUENCE OF GponSecureUriProfileEntry
	ACCESS	not-accessible
	STATUS	mandatory
	DESCRIPTION
		"This object contains a table for creating and storing
		 URI profile references along with references to profiles that
		 contain security/authentication information. "
::= { gponProfilesGroup 30 }

gponSecureUriProfileEntry OBJECT-TYPE
	SYNTAX 	GponSecureUriProfileEntry
	ACCESS	not-accessible
	STATUS	mandatory
	DESCRIPTION
		"Rows of this table contain secure URI Profiles "
	INDEX {gponSecureUriProfileIndex }
::= {gponSecureUriProfileTable 1}

GponSecureUriProfileEntry ::=
	SEQUENCE { 
		gponSecureUriProfileIndex		AsamProfileIndex,
		gponSecureUriProfileName		AsamProfileName,
		gponSecureUriProfileRefCount		AsamProfileRefCount,
		gponSecureUriProfileScope		AsamProfileScope,
		gponSecureUriProfileRowStatus 	RowStatus,
		gponSecureUriProfileAuthSecurityPointer	AsamProfilePointer,
		gponSecureUriProfileUriPointer	AsamProfilePointer
}

gponSecureUriProfileIndex OBJECT-TYPE 
	SYNTAX AsamProfileIndex
	ACCESS not-accessible
	STATUS mandatory
	DESCRIPTION
	    "This object is the index to the gponSecureUriProfileTable. "
::= { gponSecureUriProfileEntry 1}

gponSecureUriProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponSecureUriProfileEntry 2}

gponSecureUriProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponSecureUriProfileEntry  3}


gponSecureUriProfileScope OBJECT-TYPE
        	SYNTAX          AsamProfileScope
        	ACCESS          read-write
        	STATUS          mandatory
        	DESCRIPTION     
       		 "A  profile can be qualified as having a local scope or a network wide 
         		scope.

		Default = 1 = local scope. "
::= {gponSecureUriProfileEntry  4}


gponSecureUriProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponSecureUriProfileEntry  5}

gponSecureUriProfileAuthSecurityPointer  OBJECT-TYPE
	SYNTAX 	AsamProfilePointer
	ACCESS	read-write
	STATUS	mandatory
	DESCRIPTION 
		"This attribute points to a row in gponAuthSecurityProfileTable

		 Value 0 (meaning no authentication necessary) is permitted.
		 Default = 0.

		 Modification is NOT permitted.  "
	::= { gponSecureUriProfileEntry  6 }


gponSecureUriProfileUriPointer  OBJECT-TYPE
	SYNTAX 	AsamProfilePointer
	ACCESS	read-write
	STATUS	mandatory
	DESCRIPTION 
		"This attribute points to a row in gponUriProfileTable

		 Value 0 is not permitted.  Must point to an existing profile.
		 No default - must be provided by manager. 

		 Modification is NOT permitted.  "
	::= { gponSecureUriProfileEntry  7 }


gponSecureUriProfileIndexNext        OBJECT-TYPE
        	SYNTAX          AsamNextProfileIndex
        	ACCESS          read-only
        	STATUS          mandatory
        	DESCRIPTION     
        	"This object contains an appropriate value to be used for 
         		gponSecureUriProfileIndex when creating entries in the
         		gponSecureUriProfileTable. 
         		The value 0 indicates that no unassigned entries are available. To 
         		obtain the next index value for a new entry, the
        		 manager issues a management protocol retrieval operation to obtain the
         		current value of this object.  After each retrieval, the agent should
        		 modify the value to the next unassigned index. "
::= {gponProfilesGroup 31 }


  gponSecureUriProfileMaxIndex        OBJECT-TYPE
      	SYNTAX            AsamMaxProfileIndex
      	ACCESS            read-only
     	 STATUS            mandatory
      	DESCRIPTION
            	"This object represents the maximum number of
            		 gponSecureUriProfiles that can be created. The object
             		 gponSecureUriProfileIndexNext will have values ranging
            		 from 0 to the value represented by this object. 
		 For ISAM4.2,  initially set to 50. "
::= {gponProfilesGroup 32 }

-- *********************************************
-- GPON SECURE URI PROFILE MAPPING TABLE
--
-- This table was first introduced with ISAM4.2 MIB.
-- It is only SUPPORTED beginning with ISAM4.2.02 release.
--
-- For the gponSecureUriProfileTable, this table provides a reverse mapping
-- (i.e. profile name to profile index number).
--
-- The system automatically creates an entry in this Table when a  corresponding entry
-- in gponSecureUriProfile is created. 
-- The system automatically deletes an entry in this Table when a  corresponding entry
-- in gponSecureUriProfile is deleted.
--
--	For GPON - SUPPORTED as of ISAM4.2.02
--	For XG-PON1 - SUPPORTED as of ISAM4.6.02
--  For NG-PON2 - SUPPORTED as of ISAM5.4.01
--   
--
-- *********************************************

 
gponSecureUriProfileMappingTable OBJECT-TYPE
   SYNTAX   SEQUENCE OF GponSecureUriProfileMappingEntry
   ACCESS   not-accessible
   STATUS   mandatory
   DESCRIPTION
   "This object contains a table for gponSecureUriProfile
name to index mapping"
::= { gponProfilesGroup 33 }
 
gponSecureUriProfileMappingEntry OBJECT-TYPE
   SYNTAX   GponSecureUriProfileMappingEntry
   ACCESS   not-accessible
   STATUS mandatory
   DESCRIPTION
   " An entry (conceptual row) representing the gponSecureUriProfile Name to Index mapping."
   INDEX {gponSecureUriProfileMappingName }
   ::= {gponSecureUriProfileMappingTable  1}
 
GponSecureUriProfileMappingEntry ::=
   SEQUENCE { 
	gponSecureUriProfileMappingName     AsamProfileName,
      	gponSecureUriProfileMappingIndex      AsamProfileIndex
  }
 
gponSecureUriProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponSecureUriProfileMappingEntry 1}
 
gponSecureUriProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponSecureUriProfileMappingEntry 2}


-- *********************************************
-- GPON RTP PROFILE TABLE
--
-- This table was first introduced with ISAM4.2 MIB.
-- It is only SUPPORTED beginning with ISAM4.2.02 release.
--
-- This table contains information required by the Real Time Protocol; (RTP)
-- that is used when POTS ports are associated to either a SIP agent or 
-- a MGC agent. 
-- From an OMCI standpoint, it maps primarily to the RTP Profile ME.
--
--  Rows are created by the operator.
--
-- NOTE: Profile cannot be deleted if associated with a VoIP Media
-- Profile.
--
--	For GPON - SUPPORTED as of ISAM4.2.02
--	For XG-PON1 - SUPPORTED as of ISAM4.6.02
--  For NG-PON2 - SUPPORTED as of ISAM5.4.01
-- 
--
-- *********************************************

gponRtpProfileTable OBJECT-TYPE
	SYNTAX	SEQUENCE OF GponRtpProfileEntry
	ACCESS	not-accessible
	STATUS	mandatory
	DESCRIPTION
		"This object contains a table for creating and storing
		RTP information used for the POTS bearer path.. 
		These profiles are normally associated with Voip Media Profile. "
::= { gponProfilesGroup 34 }

gponRtpProfileEntry OBJECT-TYPE
	SYNTAX 	GponRtpProfileEntry
	ACCESS	not-accessible
	STATUS	mandatory
	DESCRIPTION
		"Rows of this table contain RTP Profiles"
	INDEX {gponRtpProfileIndex }
::= {gponRtpProfileTable 1}

GponRtpProfileEntry ::=
	SEQUENCE { 
		gponRtpProfileIndex		AsamProfileIndex,
		gponRtpProfileName		AsamProfileName,
		gponRtpProfileRefCount	AsamProfileRefCount,
		gponRtpProfileScope	AsamProfileScope,
		gponRtpProfileRowStatus 	RowStatus,
		gponRtpProfileLocalPortMin	INTEGER,
		gponRtpProfileLocalPortMax	INTEGER,
		gponRtpProfileDscpMark	INTEGER,
		gponRtpProfilePiggybackEventsInd	INTEGER,
		gponRtpProfileToneEventsInd	INTEGER,
		gponRtpProfileDtmfEventsInd		INTEGER,
		gponRtpProfileCasEventsInd		INTEGER
}

gponRtpProfileIndex OBJECT-TYPE 
	SYNTAX AsamProfileIndex
	ACCESS not-accessible
	STATUS mandatory
	DESCRIPTION
	    "This object is the index to the gponRtpProfileTable. "
::= { gponRtpProfileEntry 1}

gponRtpProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponRtpProfileEntry 2}

gponRtpProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponRtpProfileEntry  3}


gponRtpProfileScope OBJECT-TYPE
        	SYNTAX          AsamProfileScope
        	ACCESS          read-write
        	STATUS          mandatory
        	DESCRIPTION     
       		 "A  profile can be qualified as having a local scope or a network wide 
         		scope.

		Default = 1 = local scope. "
::= {gponRtpProfileEntry  4}


gponRtpProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponRtpProfileEntry  5}

gponRtpProfileLocalPortMin  OBJECT-TYPE
	SYNTAX 	INTEGER
	ACCESS	read-write
	STATUS	mandatory
	DESCRIPTION 
		"This attribute defines the base RTP port that should be used for voice traffic.

		 Range is 5000 TO 65000

		  Default = 50000.

		 Modification is NOT permitted.  "
	::= { gponRtpProfileEntry  6 }

gponRtpProfileLocalPortMax  OBJECT-TYPE
	SYNTAX 	INTEGER
	ACCESS	read-write
	STATUS	mandatory
	DESCRIPTION 
		"This attribute defines the highest RTP port that should be used for voice traffic.
		  Must be greater than gponRtpProfileLocalPortMin.

		 Range is 5000 TO 65000

		  Default = 60000.

		 Modification is NOT permitted.  "
	::= { gponRtpProfileEntry  7 }



gponRtpProfileDscpMark  OBJECT-TYPE
	SYNTAX 	INTEGER
	ACCESS	read-write
	STATUS	mandatory
	DESCRIPTION 
		" Specifies the value of the DSCP field of the IP header for the bearer
		  packets associated with this RTP profile.

		  Only the low order 6 bits are relevant - since that is
		  the size of the DSCP field in IP packets.

 		 Default = 46 (decimal) = 0x002E (hex) = 101110 (binary) - Expedited Forwarding.
 
		 Modification is NOT SUPPORTED. "
	::= { gponRtpProfileEntry  8 }

gponRtpProfilePiggybackEventsInd  OBJECT-TYPE
	SYNTAX 	INTEGER
	ACCESS	read-write
	STATUS	mandatory
	DESCRIPTION 
		" Enables or disables RTP piggyback events.

		 0 = Disabled (default) 
		 1 = Enabled

		 Modification is NOT SUPPORTED. "
	::= { gponRtpProfileEntry  9 }

gponRtpProfileToneEventsInd  OBJECT-TYPE
	SYNTAX 	INTEGER
	ACCESS	read-write
	STATUS	mandatory
	DESCRIPTION 
		" Enables or disables handling of tones via RTP tone events per
		  IETF RFC 4733 and 4734.

		 0 = Disabled (default) 
		 1 = Enabled

		 Modification is NOT SUPPORTED. "
	::= { gponRtpProfileEntry  10 }

gponRtpProfileDtmfEventsInd  OBJECT-TYPE
	SYNTAX 	INTEGER
	ACCESS	read-write
	STATUS	mandatory
	DESCRIPTION 
		" Enables or disables handling of DTMF via RTP DTMF events per
		  IETF RFC 4733 and 4734.  This attribute is ignored unless the OOB DTMF
		  attribute in parent gponVoipMediaProfileTable is enabled.

		 0 = Disabled (default) 
		 1 = Enabled

		 Modification is NOT SUPPORTED. "
	::= { gponRtpProfileEntry  11 }

gponRtpProfileCasEventsInd  OBJECT-TYPE
	SYNTAX 	INTEGER
	ACCESS	read-write
	STATUS	mandatory
	DESCRIPTION 
		" Enables or disables handling of CAS via RTP CAS events per
		  IETF RFC 4733 and 4734.  

		 0 = Disabled (default) 
		 1 = Enabled

		 Modification is NOT SUPPORTED. "
	::= { gponRtpProfileEntry  12 }



gponRtpProfileIndexNext        OBJECT-TYPE
        	SYNTAX          AsamNextProfileIndex
        	ACCESS          read-only
        	STATUS          mandatory
        	DESCRIPTION     
        	"This object contains an appropriate value to be used for 
         		gponRtpProfileIndex when creating entries in the
         		gponRtpProfileTable. 
         		The value 0 indicates that no unassigned entries are available. To 
         		obtain the next index value for a new entry, the
        		 manager issues a management protocol retrieval operation to obtain the
         		current value of this object.  After each retrieval, the agent should
        		 modify the value to the next unassigned index. "
::= {gponProfilesGroup 35 }


  gponRtpProfileMaxIndex        OBJECT-TYPE
      	SYNTAX            AsamMaxProfileIndex
      	ACCESS            read-only
     	 STATUS            mandatory
      	DESCRIPTION
            	"This object represents the maximum number of
            		 gponRtpProfiles that can be created. The object
             		 gponRtpProfileIndexNext will have values ranging
            		 from 0 to the value represented by this object. 
		 For ISAM4.2,  initially set to 10. "
::= {gponProfilesGroup 36 }

-- *********************************************
-- GPON RTP PROFILE MAPPING TABLE
--
-- This table was first introduced with ISAM4.2 MIB.
-- It is only SUPPORTED beginning with ISAM4.2.02 release.
--
-- For the gponRtpProfileTable, this table provides a reverse mapping
-- (i.e. profile name to profile index number).
--
-- The system automatically creates an entry in this Table when a  corresponding entry
-- in gponRtpProfile is created. 
-- The system automatically deletes an entry in this Table when a  corresponding entry
-- in gponRtpProfile is deleted.
--
--	For GPON - SUPPORTED as of ISAM4.2.02
--	For XG-PON1 - SUPPORTED as of ISAM4.6.02
--  For NG-PON2 - SUPPORTED as of ISAM5.4.01
--   
--
-- *********************************************

 
gponRtpProfileMappingTable OBJECT-TYPE
   SYNTAX   SEQUENCE OF GponRtpProfileMappingEntry
   ACCESS   not-accessible
   STATUS   mandatory
   DESCRIPTION
   "This object contains a table for gponRtpProfile
name to index mapping"
::= { gponProfilesGroup 37 }
 
gponRtpProfileMappingEntry OBJECT-TYPE
   SYNTAX   GponRtpProfileMappingEntry
   ACCESS   not-accessible
   STATUS mandatory
   DESCRIPTION
   " An entry (conceptual row) representing the gponRtpProfile Name to Index mapping."
   INDEX {gponRtpProfileMappingName }
   ::= {gponRtpProfileMappingTable  1}
 
GponRtpProfileMappingEntry ::=
   SEQUENCE { 
	gponRtpProfileMappingName     AsamProfileName,
      	gponRtpProfileMappingIndex      AsamProfileIndex
  }
 
gponRtpProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponRtpProfileMappingEntry 1}
 
gponRtpProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponRtpProfileMappingEntry 2}


-- *********************************************
-- GPON VOIP MEDIA PROFILE TABLE
--
-- This table was first introduced with ISAM4.2 MIB.
-- It is only SUPPORTED beginning with ISAM4.2.02 release.
--
-- This table contains information pertaining to VoIP voice encoding
-- that is used when POTS ports are associated to either a SIP agent or 
-- a MGC agent. 
-- From an OMCI standpoint, it maps primarily to the VoIP Media Profile ME.
--
--  Rows are created by the operator.
--
-- NOTE: Profile cannot be deleted if associated with a POTS UNI.
--
--	For GPON - SUPPORTED as of ISAM4.2.02
--	For XG-PON1 - SUPPORTED as of ISAM4.6.02
--  For NG-PON2 - SUPPORTED as of ISAM5.4.01
-- 
--
-- *********************************************

gponVoipMediaProfileTable OBJECT-TYPE
	SYNTAX	SEQUENCE OF GponVoipMediaProfileEntry
	ACCESS	not-accessible
	STATUS	mandatory
	DESCRIPTION
		"This object contains a table for creating and storing
		 voice encoding information used for the VoIP POTS bearer path. 
		These profiles are associated with a POTS UNI. "
::= { gponProfilesGroup 38 }

gponVoipMediaProfileEntry OBJECT-TYPE
	SYNTAX 	GponVoipMediaProfileEntry
	ACCESS	not-accessible
	STATUS	mandatory
	DESCRIPTION
		"Rows of this table contain VoIP Media Profiles"
	INDEX {gponVoipMediaProfileIndex }
::= {gponVoipMediaProfileTable 1}

GponVoipMediaProfileEntry ::=
	SEQUENCE { 
		gponVoipMediaProfileIndex		AsamProfileIndex,
		gponVoipMediaProfileName		AsamProfileName,
		gponVoipMediaProfileRefCount	AsamProfileRefCount,
		gponVoipMediaProfileScope		AsamProfileScope,
		gponVoipMediaProfileRowStatus 	RowStatus,
		gponVoipMediaProfileFaxMode	INTEGER,
		gponVoipMediaProfileVoiceServicePointer	AsamProfilePointer,
		gponVoipMediaProfileCodec1stOrder		INTEGER,
		gponVoipMediaProfilePktPeriod1stOrder	INTEGER,
		gponVoipMediaProfileSilenceSupp1stOrder	INTEGER,
		gponVoipMediaProfileCodec2ndOrder		INTEGER,
		gponVoipMediaProfilePktPeriod2ndOrder	INTEGER,
		gponVoipMediaProfileSilenceSupp2ndOrder	INTEGER,
		gponVoipMediaProfileCodec3rdOrder		INTEGER,
		gponVoipMediaProfilePktPeriod3rdOrder	INTEGER,
		gponVoipMediaProfileSilenceSupp3rdOrder	INTEGER,
		gponVoipMediaProfileCodec4thOrder		INTEGER,
		gponVoipMediaProfilePktPeriod4thOrder	INTEGER,
		gponVoipMediaProfileSilenceSupp4thOrder	INTEGER,
		gponVoipMediaProfileOobDtmf		INTEGER,
		gponVoipMediaProfileRtpPointer		AsamProfilePointer
}

gponVoipMediaProfileIndex OBJECT-TYPE 
	SYNTAX AsamProfileIndex
	ACCESS not-accessible
	STATUS mandatory
	DESCRIPTION
	    "This object is the index to the gponVoipMediaProfileTable. "
::= { gponVoipMediaProfileEntry 1}

gponVoipMediaProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponVoipMediaProfileEntry 2}

gponVoipMediaProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponVoipMediaProfileEntry  3}


gponVoipMediaProfileScope OBJECT-TYPE
        	SYNTAX          AsamProfileScope
        	ACCESS          read-write
        	STATUS          mandatory
        	DESCRIPTION     
       		 "A  profile can be qualified as having a local scope or a network wide 
         		scope.

		Default = 1 = local scope. "
::= {gponVoipMediaProfileEntry  4}


gponVoipMediaProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponVoipMediaProfileEntry  5}

gponVoipMediaProfileFaxMode  OBJECT-TYPE
	SYNTAX 	INTEGER
	ACCESS	read-write
	STATUS	mandatory
	DESCRIPTION 
		"This attribute selects the fax mode

		 0 = Passthru (default) 
		 1 = T.38

		 Modification is NOT permitted.  "
	::= { gponVoipMediaProfileEntry  6 }

gponVoipMediaProfileVoiceServicePointer  OBJECT-TYPE
	SYNTAX 	AsamProfilePointer
	ACCESS	read-write
	STATUS	mandatory
	DESCRIPTION 
		"This attribute points to a row in gponVoiceServiceProfileTable

		 Value 0 (meaning determined via other means) is permitted.
		 Default = 0.

		 Modification is NOT permitted.  "
	::= { gponVoipMediaProfileEntry  7 }

gponVoipMediaProfileCodec1stOrder  OBJECT-TYPE
	SYNTAX 	INTEGER
	ACCESS	read-write
	STATUS	mandatory
	DESCRIPTION 
		" Specifies 1st order codec selection as defined by IETF RFC 3551

		Value		Name		Clock Rate (Hz)	Supported
		0 (default)	PCMU		8000		Y (as of ISAM4.2)
		1		reserved				N
		2		reserved				N
		3		GSM		8000		Y
		4		G723		8000		Y
		5		DVI4		8000		Y
		6		DVI4		16000		Y
		7		LPC		8000		Y
		8		PCMA		8000		Y
		9		G722		8000		Y
		10		L16, 2 channels	41000		Y
		11		L16, 1 channel	41000		Y
		12		QCELP		8000		Y
		13		CN		8000		Y
		14		MPA		90000		Y
		15		G728		8000		Y
		16		DVI4		11025		Y
		17		DVI4		22050		Y
		18		G729		8000		Y
 
		 Modification is NOT SUPPORTED. "
	::= { gponVoipMediaProfileEntry  8 }

gponVoipMediaProfilePktPeriod1stOrder OBJECT-TYPE
	SYNTAX 	INTEGER
	ACCESS	read-write
	STATUS	mandatory
	DESCRIPTION 
		"This attribute specifies 1st order packet period selection interval (in milliseconds).

		 Range is 10 ... 30.
		 Default = 10.

		 Modification is NOT permitted.  "
	::= { gponVoipMediaProfileEntry  9 }

gponVoipMediaProfileSilenceSupp1stOrder OBJECT-TYPE
	SYNTAX 	INTEGER
	ACCESS	read-write
	STATUS	mandatory
	DESCRIPTION 
		"This attribute specifies for 1st order whether silence suppression is ON of OFF..

		 0 = OFF (default)
		 1 = ON

		 Modification is NOT permitted.  "
	::= { gponVoipMediaProfileEntry  10 }

gponVoipMediaProfileCodec2ndOrder  OBJECT-TYPE
	SYNTAX 	INTEGER
	ACCESS	read-write
	STATUS	mandatory
	DESCRIPTION 
		" Specifies 2nd order codec selection as defined by IETF RFC 3551

		  Format definitions (and defaults) are same as 1st order.
 
		 Modification is NOT SUPPORTED. "
	::= { gponVoipMediaProfileEntry  11 }

gponVoipMediaProfilePktPeriod2ndOrder OBJECT-TYPE
	SYNTAX 	INTEGER
	ACCESS	read-write
	STATUS	mandatory
	DESCRIPTION 
		"This attribute specifies 2nd packet period selection interval (in milliseconds).

		  Format definitions (and defaults) are same as 1st order.

		 Modification is NOT permitted.  "
	::= { gponVoipMediaProfileEntry  12 }

gponVoipMediaProfileSilenceSupp2ndOrder OBJECT-TYPE
	SYNTAX 	INTEGER
	ACCESS	read-write
	STATUS	mandatory
	DESCRIPTION 
		"This attribute specifies whether 2nd order silence suppression is ON of OFF..

		  Format definitions (and defaults) are same as 1st order.

		 Modification is NOT permitted.  "
	::= { gponVoipMediaProfileEntry  13 }

gponVoipMediaProfileCodec3rdOrder  OBJECT-TYPE
	SYNTAX 	INTEGER
	ACCESS	read-write
	STATUS	mandatory
	DESCRIPTION 
		" Specifies 3rd order codec selection as defined by IETF RFC 3551

		  Format definitions (and defaults) are same as 1st order.
 
		 Modification is NOT SUPPORTED. "
	::= { gponVoipMediaProfileEntry  14 }

gponVoipMediaProfilePktPeriod3rdOrder OBJECT-TYPE
	SYNTAX 	INTEGER
	ACCESS	read-write
	STATUS	mandatory
	DESCRIPTION 
		"This attribute specifies 3rd packet period selection interval (in milliseconds).

		  Format definitions (and defaults) are same as 1st order.

		 Modification is NOT permitted.  "
	::= { gponVoipMediaProfileEntry  15 }

gponVoipMediaProfileSilenceSupp3rdOrder OBJECT-TYPE
	SYNTAX 	INTEGER
	ACCESS	read-write
	STATUS	mandatory
	DESCRIPTION 
		"This attribute specifies whether 3rd order silence suppression is ON of OFF..

		  Format definitions (and defaults) are same as 1st order.

		 Modification is NOT permitted.  "
	::= { gponVoipMediaProfileEntry  16 }

gponVoipMediaProfileCodec4thOrder  OBJECT-TYPE
	SYNTAX 	INTEGER
	ACCESS	read-write
	STATUS	mandatory
	DESCRIPTION 
		" Specifies 4th order codec selection as defined by IETF RFC 3551

		  Format definitions (and defaults) are same as 1st order.
 
		 Modification is NOT SUPPORTED. "
	::= { gponVoipMediaProfileEntry  17 }

gponVoipMediaProfilePktPeriod4thOrder OBJECT-TYPE
	SYNTAX 	INTEGER
	ACCESS	read-write
	STATUS	mandatory
	DESCRIPTION 
		"This attribute specifies 4th packet period selection interval (in milliseconds).

		  Format definitions (and defaults) are same as 1st order.

		 Modification is NOT permitted.  "
	::= { gponVoipMediaProfileEntry  18 }

gponVoipMediaProfileSilenceSupp4thOrder OBJECT-TYPE
	SYNTAX 	INTEGER
	ACCESS	read-write
	STATUS	mandatory
	DESCRIPTION 
		"This attribute specifies whether 4th order silence suppression is ON of OFF..

		  Format definitions (and defaults) are same as 1st order.

		 Modification is NOT permitted.  "
	::= { gponVoipMediaProfileEntry  19 }

gponVoipMediaProfileOobDtmf OBJECT-TYPE
	SYNTAX 	INTEGER
	ACCESS	read-write
	STATUS	mandatory
	DESCRIPTION 
		"This attribute specifies out-of-band DTMF carriage selection.

		 0 = Disabled - means DTMF tones are carried in the PCM stream.
		 1 = Enabled - means DTMF signals are carried out-of-band via RTP
		       or associated signalling protocol.

		 Default = 1 = Enabled.

		 Modification is NOT permitted.  "
	::= { gponVoipMediaProfileEntry  20 }

gponVoipMediaProfileRtpPointer  OBJECT-TYPE
	SYNTAX 	AsamProfilePointer
	ACCESS	read-write
	STATUS	mandatory
	DESCRIPTION 
		"This attribute points to a row in gponRtpProfileTable

		 Value 0 (meaning determined via other means) is permitted.
		 Default = 0.

		 Modification is NOT permitted.  "
	::= { gponVoipMediaProfileEntry  21 }


gponVoipMediaProfileIndexNext        OBJECT-TYPE
        	SYNTAX          AsamNextProfileIndex
        	ACCESS          read-only
        	STATUS          mandatory
        	DESCRIPTION     
        	"This object contains an appropriate value to be used for 
         		gponVoipMediaProfileIndex when creating entries in the
         		gponVoipMediaProfileTable. 
         		The value 0 indicates that no unassigned entries are available. To 
         		obtain the next index value for a new entry, the
        		 manager issues a management protocol retrieval operation to obtain the
         		current value of this object.  After each retrieval, the agent should
        		 modify the value to the next unassigned index. "
::= {gponProfilesGroup 39 }


  gponVoipMediaProfileMaxIndex        OBJECT-TYPE
      	SYNTAX            AsamMaxProfileIndex
      	ACCESS            read-only
     	 STATUS            mandatory
      	DESCRIPTION
            	"This object represents the maximum number of
            		 gponVoipMediaProfiles that can be created. The object
             		 gponVoipMediaProfileIndexNext will have values ranging
            		 from 0 to the value represented by this object. 
		 For ISAM4.2,  initially set to 10. "
::= {gponProfilesGroup 40 }

-- *********************************************
-- GPON VOIP MEDIA PROFILE MAPPING TABLE
--
-- This table was first introduced with ISAM4.2 MIB.
-- It is only SUPPORTED beginning with ISAM4.2.02 release.
--
-- For the gponVoipMediaProfileTable, this table provides a reverse mapping
-- (i.e. profile name to profile index number).
--
-- The system automatically creates an entry in this Table when a  corresponding entry
-- in gponVoipMediaProfile is created. 
-- The system automatically deletes an entry in this Table when a  corresponding entry
-- in gponVoipMediaProfile is deleted.
--
--	For GPON - SUPPORTED as of ISAM4.2.02
--	For XG-PON1 - SUPPORTED as of ISAM4.6.02
--  For NG-PON2 - SUPPORTED as of ISAM5.4.01
--   
--
-- *********************************************

 
gponVoipMediaProfileMappingTable OBJECT-TYPE
   SYNTAX   SEQUENCE OF GponVoipMediaProfileMappingEntry
   ACCESS   not-accessible
   STATUS   mandatory
   DESCRIPTION
   "This object contains a table for gponVoipMediaProfile
name to index mapping"
::= { gponProfilesGroup 25 }
 
gponVoipMediaProfileMappingEntry OBJECT-TYPE
   SYNTAX   GponVoipMediaProfileMappingEntry
   ACCESS   not-accessible
   STATUS mandatory
   DESCRIPTION
   " An entry (conceptual row) representing the gponVoipMediaProfile Name to Index mapping."
   INDEX {gponVoipMediaProfileMappingName }
   ::= {gponVoipMediaProfileMappingTable  1}
 
GponVoipMediaProfileMappingEntry ::=
   SEQUENCE { 
	gponVoipMediaProfileMappingName     AsamProfileName,
      	gponVoipMediaProfileMappingIndex      AsamProfileIndex
  }
 
gponVoipMediaProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponVoipMediaProfileMappingEntry 1}
 
gponVoipMediaProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponVoipMediaProfileMappingEntry 2}


-- *********************************************
-- GPON TONE PATTERN  PROFILE MAPPING TABLE
--
-- This table was first introduced with ISAM4.2 MIB.
-- It is only SUPPORTED beginning with ISAM4.2.02 release.
--
-- For the gponTonePatternProfileTable, this table provides a reverse mapping
-- (i.e. profile name to profile index number).
--
-- The system automatically creates an entry in this Table when a  corresponding entry
-- in gponTonePatternProfile is created. 
-- The system automatically deletes an entry in this Table when a  corresponding entry
-- in gponTonePatternProfile is deleted.
--
--	For GPON - SUPPORTED as of ISAM4.2.02
--	For XG-PON1 - SUPPORTED as of ISAM4.6.02
--  For NG-PON2 - SUPPORTED as of ISAM5.4.01
--   
--
-- *********************************************

 
gponTonePatternProfileMappingTable OBJECT-TYPE
   SYNTAX   SEQUENCE OF GponTonePatternProfileMappingEntry
   ACCESS   not-accessible
   STATUS   mandatory
   DESCRIPTION
   "This object contains a table for gponTonePatternProfile
name to index mapping"
::= { gponProfilesGroup 41 }
 
gponTonePatternProfileMappingEntry OBJECT-TYPE
   SYNTAX   GponTonePatternProfileMappingEntry
   ACCESS   not-accessible
   STATUS mandatory
   DESCRIPTION
   " An entry (conceptual row) representing the gponTonePatternProfile Name to Index mapping."
   INDEX {gponTonePatternProfileMappingName }
   ::= {gponTonePatternProfileMappingTable  1}
 
GponTonePatternProfileMappingEntry ::=
   SEQUENCE { 
	gponTonePatternProfileMappingName     AsamProfileName,
      	gponTonePatternProfileMappingIndex      AsamProfileIndex
  }
 
gponTonePatternProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponTonePatternProfileMappingEntry 1}
 
gponTonePatternProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponTonePatternProfileMappingEntry 2}



-- *********************************************
-- GPON TONE PATTERN PROFILE TABLE
--
-- This table was first introduced with ISAM4.2 MIB.
-- It is only SUPPORTED beginning with ISAM4.2.02 release.
--
-- This table contains information for defining a complex tone
-- (or silence) along with a duration.
-- From an OMCI standpoint, it maps primarily to the Tone Pattern Table
-- attribute in the Voice Service Profile ME.
--
--  Rows are created by the operator.
--
-- NOTE: Profile cannot be deleted if associated with another table.
--
--	For GPON - SUPPORTED as of ISAM4.2.02
--	For XG-PON1 - SUPPORTED as of ISAM4.6.02
--  For NG-PON2 - SUPPORTED as of ISAM5.4.01
-- 
--
-- *********************************************

gponTonePatternProfileTable OBJECT-TYPE
	SYNTAX	SEQUENCE OF GponTonePatternProfileEntry
	ACCESS	not-accessible
	STATUS	mandatory
	DESCRIPTION
		"This object contains a table for creating and storing
		tone pattern definitions. 
		These profiles are normally associated with Tone Sequence
		Profiles.  "
::= { gponProfilesGroup 42 }

gponTonePatternProfileEntry OBJECT-TYPE
	SYNTAX 	GponTonePatternProfileEntry
	ACCESS	not-accessible
	STATUS	mandatory
	DESCRIPTION
		"Rows of this table contain Tone Pattern Profiles "
	INDEX {gponTonePatternProfileIndex }
::= {gponTonePatternProfileTable 1}

GponTonePatternProfileEntry ::=
	SEQUENCE { 
		gponTonePatternProfileIndex		AsamProfileIndex,
		gponTonePatternProfileName		AsamProfileName,
		gponTonePatternProfileRefCount		AsamProfileRefCount,
		gponTonePatternProfileScope		AsamProfileScope,
		gponTonePatternProfileRowStatus 	RowStatus,
		gponTonePatternProfileOnOffInd	INTEGER,
		gponTonePatternProfileFrequency1		INTEGER,
		gponTonePatternProfilePower1		INTEGER,
		gponTonePatternProfileFrequency2		INTEGER,
		gponTonePatternProfilePower2		INTEGER,
		gponTonePatternProfileFrequency3		INTEGER,
		gponTonePatternProfilePower3		INTEGER,
		gponTonePatternProfileFrequency4		INTEGER,
		gponTonePatternProfilePower4		INTEGER,
		gponTonePatternProfileModulationFrequency	INTEGER,
		gponTonePatternProfileModulationPower	INTEGER,
		gponTonePatternProfileDuration		INTEGER
}

gponTonePatternProfileIndex OBJECT-TYPE 
	SYNTAX AsamProfileIndex
	ACCESS not-accessible
	STATUS mandatory
	DESCRIPTION
	    "This object is the index to the gponTonePatternProfileTable. "
::= { gponTonePatternProfileEntry 1}

gponTonePatternProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponTonePatternProfileEntry 2}

gponTonePatternProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponTonePatternProfileEntry  3}


gponTonePatternProfileScope OBJECT-TYPE
        	SYNTAX          AsamProfileScope
        	ACCESS          read-write
        	STATUS          mandatory
        	DESCRIPTION     
       		 "A  profile can be qualified as having a local scope or a network wide 
         		scope.

		Default = 1 = local scope. "
::= {gponTonePatternProfileEntry  4}


gponTonePatternProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponTonePatternProfileEntry  5}

gponTonePatternProfileOnOffInd  OBJECT-TYPE
	SYNTAX 	INTEGER
	ACCESS	read-write
	STATUS	mandatory
	DESCRIPTION 
		"This attribute controls whether tone is OFF or ON. If OFF, then
		  power and frequency fields are ignored - and only the duration
		  field is meaningful.

		 0 = OFF
		 1 = ON (default)

		 Modification is NOT permitted.  "
	::= { gponTonePatternProfileEntry  6 }


gponTonePatternProfileFrequency1  OBJECT-TYPE
	SYNTAX 	INTEGER
	ACCESS	read-write
	STATUS	mandatory
	DESCRIPTION 
		"This attribute specifies the frequency of one of the tone components (in Hz).

		 Range is 0 - 4000.

		 Modification is NOT permitted.  "
	::= { gponTonePatternProfileEntry  7 }

gponTonePatternProfilePower1  OBJECT-TYPE
	SYNTAX 	INTEGER
	ACCESS	read-write
	STATUS	mandatory
	DESCRIPTION 
		"This attribute specifies the power level of the corresponding frequency.
		  Units are dBm0 (with 0.1 dB resolution).

		 Range is -25.5 dBm TO  0.0 dBm0 (where 0 represents 0x00 dBm0 and 0xFF represents -25.5 dBm0). 

		 Modification is NOT permitted.  "
	::= { gponTonePatternProfileEntry  8 }

gponTonePatternProfileFrequency2  OBJECT-TYPE
	SYNTAX 	INTEGER
	ACCESS	read-write
	STATUS	mandatory
	DESCRIPTION 
		"This attribute specifies the frequency part of 2nd pair of frequency/power
		 components that may be specified to define a complex tone (in Hz).

		 Range is 0 - 4000.

		 Modification is NOT permitted.  "
	::= { gponTonePatternProfileEntry  9 }

gponTonePatternProfilePower2  OBJECT-TYPE
	SYNTAX 	INTEGER
	ACCESS	read-write
	STATUS	mandatory
	DESCRIPTION 
		"This attribute specifies the power part of 2nd pair of frequency/power
		 components that may be specified to define a complex tone.
		 Units are dBm0 (with 0.1 dB resolution).

		 Range is -25.5 dBm TO  0.0 dBm0 (where 0 represents 0x00 dBm0 and 0xFF represents -25.5 dBm0). 

		 Modification is NOT permitted.  "
	::= { gponTonePatternProfileEntry  10 }

gponTonePatternProfileFrequency3  OBJECT-TYPE
	SYNTAX 	INTEGER
	ACCESS	read-write
	STATUS	mandatory
	DESCRIPTION 
		"This attribute specifies the frequency part of 3rd pair of frequency/power
		 components that may be specified to define a complex tone (in Hz).

		 Range is 0 - 4000.

		 Modification is NOT permitted.  "
	::= { gponTonePatternProfileEntry  11 }

gponTonePatternProfilePower3  OBJECT-TYPE
	SYNTAX 	INTEGER
	ACCESS	read-write
	STATUS	mandatory
	DESCRIPTION 
		"This attribute specifies the power part of 3rd pair of frequency/power
		 components that may be specified to define a complex tone.
		 Units are dBm0 (with 0.1 dB resolution).

		 Range is -25.5 dBm TO  0.0 dBm0 (where 0 represents 0x00 dBm0 and 0xFF represents -25.5 dBm0). 

		 Modification is NOT permitted.  "
	::= { gponTonePatternProfileEntry  12 }

gponTonePatternProfileFrequency4  OBJECT-TYPE
	SYNTAX 	INTEGER
	ACCESS	read-write
	STATUS	mandatory
	DESCRIPTION 
		"This attribute specifies the frequency part of 4th pair of frequency/power
		 components that may be specified to define a complex tone (in Hz).

		 Range is 0 - 4000.

		 Modification is NOT permitted.  "
	::= { gponTonePatternProfileEntry  13 }

gponTonePatternProfilePower4  OBJECT-TYPE
	SYNTAX 	INTEGER
	ACCESS	read-write
	STATUS	mandatory
	DESCRIPTION 
		"This attribute specifies the power part of 4th pair of frequency/power
		 components that may be specified to define a complex tone.
		 Units are dBm0 (with 0.1 dB resolution).

		 Range is -25.5 dBm TO  0.0 dBm0 (where 0 represents 0x00 dBm0 and 0xFF represents -25.5 dBm0). 

		 Modification is NOT permitted.  "
	::= { gponTonePatternProfileEntry  14 }

gponTonePatternProfileModulationFrequency  OBJECT-TYPE
	SYNTAX 	INTEGER
	ACCESS	read-write
	STATUS	mandatory
	DESCRIPTION 
		"This attribute specifies the frequency part of the freq/power pair that allows a composite
		 tone to be modulated (e.g. warble effect). Units are Hz.

		 Range is 0 - 2000.
		 If composite modulation is not used, this field must be  0.

		 Modification is NOT permitted.  "
	::= { gponTonePatternProfileEntry  15 }

gponTonePatternProfileModulationPower  OBJECT-TYPE
	SYNTAX 	INTEGER
	ACCESS	read-write
	STATUS	mandatory
	DESCRIPTION 
		"This attribute specifies the power part of the freq/power pair that allows a composite
		 tone to be modulated (e.g. warble effect).
		 Units are dBm0 (with 0.1 dB resolution).

		 Range is -25.5 dBm TO  0.0 dBm0 (where 0 represents 0x00 dBm0 and 0xFF represents -25.5 dBm0). 
		 If composite modulation is not used, this field must be  0.

		 Modification is NOT permitted.  "
	::= { gponTonePatternProfileEntry  16 }

gponTonePatternProfileDuration  OBJECT-TYPE
	SYNTAX 	INTEGER
	ACCESS	read-write
	STATUS	mandatory
	DESCRIPTION 
		"This attribute specifies the duration of the phase (in milliseconds).  The value 0 specifies that
		 the phase endures indefinitely (i.e. until terminated by other events such as call abandonment).

		 Range is 0 - 65535 (milliseconds)

		 Modification is NOT permitted.  "
	::= { gponTonePatternProfileEntry  17 }


gponTonePatternProfileIndexNext        OBJECT-TYPE
        	SYNTAX          AsamNextProfileIndex
        	ACCESS          read-only
        	STATUS          mandatory
        	DESCRIPTION     
        	"This object contains an appropriate value to be used for 
         		gponTonePatternProfileIndex when creating entries in the
         		gponTonePatternProfileTable. 
         		The value 0 indicates that no unassigned entries are available. To 
         		obtain the next index value for a new entry, the
        		 manager issues a management protocol retrieval operation to obtain the
         		current value of this object.  After each retrieval, the agent should
        		 modify the value to the next unassigned index. "
::= {gponProfilesGroup 43 }


  gponTonePatternProfileMaxIndex        OBJECT-TYPE
      	SYNTAX            AsamMaxProfileIndex
      	ACCESS            read-only
     	 STATUS            mandatory
      	DESCRIPTION
            	"This object represents the maximum number of
            		 gponTonePatternProfiles that can be created. The object
             		 gponTonePatternProfileIndexNext will have values ranging
            		 from 0 to the value represented by this object. 
		 For ISAM4.2,  initially set to 50. "
::= {gponProfilesGroup 44 }

-- *********************************************
-- GPON TONE PATTERN SEQUENCE PROFILE TABLE
--
-- This table was first introduced with ISAM4.2 MIB.
-- It is only SUPPORTED beginning with ISAM4.2.02 release.
--
-- This table contains information for defining a sequence of
-- tone patterns.
-- From an OMCI standpoint, it maps primarily to the Tone Pattern Table
-- attribute in the Voice Service Profile ME.
--
--  Rows are created by the operator.
--
-- NOTE: Profile cannot be deleted if associated with another table.
--
--	For GPON - SUPPORTED as of ISAM4.2.02
--	For XG-PON1 - SUPPORTED as of ISAM4.6.02
--  For NG-PON2 - SUPPORTED as of ISAM5.4.01
-- 
--
-- *********************************************

gponToneSequenceProfileTable OBJECT-TYPE
	SYNTAX	SEQUENCE OF GponToneSequenceProfileEntry
	ACCESS	not-accessible
	STATUS	mandatory
	DESCRIPTION
		"This object contains a table for creating and storing
		tone sequences.
		These profiles are normally associated with a Tone Event
		Profile "
::= { gponProfilesGroup 45 }

gponToneSequenceProfileEntry OBJECT-TYPE
	SYNTAX 	GponToneSequenceProfileEntry
	ACCESS	not-accessible
	STATUS	mandatory
	DESCRIPTION
		"Rows of this table contain Tone Sequence Profiles "
	INDEX {gponToneSequenceProfileIndex }
::= {gponToneSequenceProfileTable 1}

GponToneSequenceProfileEntry ::=
	SEQUENCE { 
		gponToneSequenceProfileIndex		AsamProfileIndex,
		gponToneSequenceProfileName		AsamProfileName,
		gponToneSequenceProfileRefCount		AsamProfileRefCount,
		gponToneSequenceProfileScope		AsamProfileScope,
		gponToneSequenceProfileRowStatus 		RowStatus,
		gponToneSequenceProfilePattern1Pointer	AsamProfilePointer,
		gponToneSequenceProfilePattern2Pointer	AsamProfilePointer,
		gponToneSequenceProfilePattern3Pointer	AsamProfilePointer,
		gponToneSequenceProfilePattern4Pointer	AsamProfilePointer,
		gponToneSequenceProfilePattern5Pointer	AsamProfilePointer,
		gponToneSequenceProfilePattern6Pointer	AsamProfilePointer,
		gponToneSequenceProfilePattern7Pointer	AsamProfilePointer,
		gponToneSequenceProfilePattern8Pointer	AsamProfilePointer
}

gponToneSequenceProfileIndex OBJECT-TYPE 
	SYNTAX AsamProfileIndex
	ACCESS not-accessible
	STATUS mandatory
	DESCRIPTION
	    "This object is the index to the gponToneSequenceProfileTable. "
::= { gponToneSequenceProfileEntry 1}

gponToneSequenceProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponToneSequenceProfileEntry 2}

gponToneSequenceProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponToneSequenceProfileEntry  3}


gponToneSequenceProfileScope OBJECT-TYPE
        	SYNTAX          AsamProfileScope
        	ACCESS          read-write
        	STATUS          mandatory
        	DESCRIPTION     
       		 "A  profile can be qualified as having a local scope or a network wide 
         		scope.

		Default = 1 = local scope. "
::= {gponToneSequenceProfileEntry  4}


gponToneSequenceProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponToneSequenceProfileEntry  5}

gponToneSequenceProfilePattern1Pointer  OBJECT-TYPE
	SYNTAX 	AsamProfilePointer
	ACCESS	read-write
	STATUS	mandatory
	DESCRIPTION 
		"This attribute points to a row in gponTonePatternProfileTable

		 Value 0 is NOT permitted.
		 No default - must be supplied by manager.

		 Modification is NOT permitted.  "
	::= { gponToneSequenceProfileEntry  6 }

gponToneSequenceProfilePattern2Pointer  OBJECT-TYPE
	SYNTAX 	AsamProfilePointer
	ACCESS	read-write
	STATUS	mandatory
	DESCRIPTION 
		"This attribute points to a row in gponTonePatternProfileTable.  It
		 logically follows the previous tone pattern reference.

		 Value 0 is permitted - meaning that tone sequence STOPS.
		 If non-zero, must point to a tone pattern (defined in TonePatternProfileTable). 

		 If the pattern referenced here has already been previously referenced
		 within this profile - then it should be considered as a logical jump back to
		 that previous reference (and the sequence continues from that point forward).
		 This effectively allows the definition of a cyclical sequence of tone patterns.

		 Other than the zero value, the same tone pattern cannot be referenced more than twice
		 within the same gponToneSequenceProfile.

		 Default = 0 (null pointer).
		 VALIDATION:  Once a null value has been established for a pointer, all subsequent
			pattern pointers in this table must also be null.

		 Modification is NOT permitted.  "
	::= { gponToneSequenceProfileEntry  7 }

gponToneSequenceProfilePattern3Pointer  OBJECT-TYPE
	SYNTAX 	AsamProfilePointer
	ACCESS	read-write
	STATUS	mandatory
	DESCRIPTION 
		"This attribute points to a row in gponTonePatternProfileTable.  It
		 logically follows the previous tone pattern reference.

		 Value 0 is permitted - meaning that tone sequence STOPS.
		 If non-zero, must point to a tone pattern (defined in TonePatternProfileTable). 

		 If the pattern referenced here has already been previously referenced
		 within this profile - then it should be considered as a logical jump back to
		 that previous reference (and the sequence continues from that point forward).
		 This effectively allows the definition of a cyclical sequence of tone patterns.

		 Other than the zero value, the same tone pattern cannot be referenced more than twice
		 within the same gponToneSequenceProfile.

		 Default = 0 (null pointer).
		 VALIDATION:  Once a null value has been established for a pointer, all subsequent
			pattern pointers in this table must also be null.

		 Modification is NOT permitted.  "
	::= { gponToneSequenceProfileEntry  8 }

gponToneSequenceProfilePattern4Pointer  OBJECT-TYPE
	SYNTAX 	AsamProfilePointer
	ACCESS	read-write
	STATUS	mandatory
	DESCRIPTION 
		"This attribute points to a row in gponTonePatternProfileTable.  It
		 logically follows the previous tone pattern reference.

		 Value 0 is permitted - meaning that tone sequence STOPS.
		 If non-zero, must point to a tone pattern (defined in TonePatternProfileTable). 

		 If the pattern referenced here has already been previously referenced
		 within this profile - then it should be considered as a logical jump back to
		 that previous reference (and the sequence continues from that point forward).
		 This effectively allows the definition of a cyclical sequence of tone patterns.

		 Other than the zero value, the same tone pattern cannot be referenced more than twice
		 within the same gponToneSequenceProfile.

		 Default = 0 (null pointer).
		 VALIDATION:  Once a null value has been established for a pointer, all subsequent
			pattern pointers in this table must also be null.

		 Modification is NOT permitted.  "
	::= { gponToneSequenceProfileEntry  9 }

gponToneSequenceProfilePattern5Pointer  OBJECT-TYPE
	SYNTAX 	AsamProfilePointer
	ACCESS	read-write
	STATUS	mandatory
	DESCRIPTION 
		"This attribute points to a row in gponTonePatternProfileTable.  It
		 logically follows the previous tone pattern reference.

		 Value 0 is permitted - meaning that tone sequence STOPS.
		 If non-zero, must point to a tone pattern (defined in TonePatternProfileTable). 

		 If the pattern referenced here has already been previously referenced
		 within this profile - then it should be considered as a logical jump back to
		 that previous reference (and the sequence continues from that point forward).
		 This effectively allows the definition of a cyclical sequence of tone patterns.

		 Other than the zero value, the same tone pattern cannot be referenced more than twice
		 within the same gponToneSequenceProfile.

		 Default = 0 (null pointer).
		 VALIDATION:  Once a null value has been established for a pointer, all subsequent
			pattern pointers in this table must also be null.

		 Modification is NOT permitted.  "
	::= { gponToneSequenceProfileEntry  10 }

gponToneSequenceProfilePattern6Pointer  OBJECT-TYPE
	SYNTAX 	AsamProfilePointer
	ACCESS	read-write
	STATUS	mandatory
	DESCRIPTION 
		"This attribute points to a row in gponTonePatternProfileTable.  It
		 logically follows the previous tone pattern reference.

		 Value 0 is permitted - meaning that tone sequence STOPS.
		 If non-zero, must point to a tone pattern (defined in TonePatternProfileTable). 

		 If the pattern referenced here has already been previously referenced
		 within this profile - then it should be considered as a logical jump back to
		 that previous reference (and the sequence continues from that point forward).
		 This effectively allows the definition of a cyclical sequence of tone patterns.

		 Other than the zero value, the same tone pattern cannot be referenced more than twice
		 within the same gponToneSequenceProfile.

		 Default = 0 (null pointer).
		 VALIDATION:  Once a null value has been established for a pointer, all subsequent
			pattern pointers in this table must also be null.

		 Modification is NOT permitted.  "
	::= { gponToneSequenceProfileEntry  11 }

gponToneSequenceProfilePattern7Pointer  OBJECT-TYPE
	SYNTAX 	AsamProfilePointer
	ACCESS	read-write
	STATUS	mandatory
	DESCRIPTION 
		"This attribute points to a row in gponTonePatternProfileTable.  It
		 logically follows the previous tone pattern reference.

		 Value 0 is permitted - meaning that tone sequence STOPS.
		 If non-zero, must point to a tone pattern (defined in TonePatternProfileTable). 

		 If the pattern referenced here has already been previously referenced
		 within this profile - then it should be considered as a logical jump back to
		 that previous reference (and the sequence continues from that point forward).
		 This effectively allows the definition of a cyclical sequence of tone patterns.

		 Other than the zero value, the same tone pattern cannot be referenced more than twice
		 within the same gponToneSequenceProfile.

		 Default = 0 (null pointer).
		 VALIDATION:  Once a null value has been established for a pointer, all subsequent
			pattern pointers in this table must also be null.

		 Modification is NOT permitted.  "
	::= { gponToneSequenceProfileEntry  12 }

gponToneSequenceProfilePattern8Pointer  OBJECT-TYPE
	SYNTAX 	AsamProfilePointer
	ACCESS	read-write
	STATUS	mandatory
	DESCRIPTION 
		"This attribute points to a row in gponTonePatternProfileTable.  It
		 logically follows the previous tone pattern reference.

		 Value 0 is permitted - meaning that tone sequence STOPS.
		 If non-zero, must point to a tone pattern (defined in TonePatternProfileTable). 

		 If the pattern referenced here has already been previously referenced
		 within this profile - then it should be considered as a logical jump back to
		 that previous reference (and the sequence continues from that point forward).
		 This effectively allows the definition of a cyclical sequence of tone patterns.

		 Other than the zero value, the same tone pattern cannot be referenced more than twice
		 within the same gponToneSequenceProfile.

		 Default = 0 (null pointer).
		 VALIDATION:  Once a null value has been established for a pointer, all subsequent
			pattern pointers in this table must also be null.

		 Modification is NOT permitted.  "
	::= { gponToneSequenceProfileEntry  13 }


gponToneSequenceProfileIndexNext        OBJECT-TYPE
        	SYNTAX          AsamNextProfileIndex
        	ACCESS          read-only
        	STATUS          mandatory
        	DESCRIPTION     
        	"This object contains an appropriate value to be used for 
         		gponToneSequenceProfileIndex when creating entries in the
         		gponToneSequenceProfileTable. 
         		The value 0 indicates that no unassigned entries are available. To 
         		obtain the next index value for a new entry, the
        		 manager issues a management protocol retrieval operation to obtain the
         		current value of this object.  After each retrieval, the agent should
        		 modify the value to the next unassigned index. "
::= {gponProfilesGroup 46 }


  gponToneSequenceProfileMaxIndex        OBJECT-TYPE
      	SYNTAX            AsamMaxProfileIndex
      	ACCESS            read-only
     	 STATUS            mandatory
      	DESCRIPTION
            	"This object represents the maximum number of
            		 gponToneSequenceProfiles that can be created. The object
             		 gponToneSequenceProfileIndexNext will have values ranging
            		 from 0 to the value represented by this object. 
		 For ISAM4.2,  initially set to 50. "
::= {gponProfilesGroup 47 }


-- *********************************************
-- GPON TONE PATTERN SEQUENCE PROFILE MAPPING TABLE
--
-- This table was first introduced with ISAM4.2 MIB.
-- It is only SUPPORTED beginning with ISAM4.2.02 release.
--
-- For the gponToneSequenceProfileTable, this table provides a reverse mapping
-- (i.e. profile name to profile index number).
--
-- The system automatically creates an entry in this Table when a  corresponding entry
-- in gponToneSequenceProfile is created. 
-- The system automatically deletes an entry in this Table when a  corresponding entry
-- in gponToneSequenceProfile is deleted.
--
--	For GPON - SUPPORTED as of ISAM4.2.02
--	For XG-PON1 - SUPPORTED as of ISAM4.6.02
--  For NG-PON2 - SUPPORTED as of ISAM5.4.01
--   
--
-- *********************************************

 
gponToneSequenceProfileMappingTable OBJECT-TYPE
   SYNTAX   SEQUENCE OF GponToneSequenceProfileMappingEntry
   ACCESS   not-accessible
   STATUS   mandatory
   DESCRIPTION
   "This object contains a table for gponToneSequenceProfile
name to index mapping"
::= { gponProfilesGroup 48 }
 
gponToneSequenceProfileMappingEntry OBJECT-TYPE
   SYNTAX   GponToneSequenceProfileMappingEntry
   ACCESS   not-accessible
   STATUS mandatory
   DESCRIPTION
   " An entry (conceptual row) representing the gponToneSequenceProfile Name to Index mapping."
   INDEX {gponToneSequenceProfileMappingName }
   ::= {gponToneSequenceProfileMappingTable  1}
 
GponToneSequenceProfileMappingEntry ::=
   SEQUENCE { 
	gponToneSequenceProfileMappingName     AsamProfileName,
      	gponToneSequenceProfileMappingIndex      AsamProfileIndex
  }
 
gponToneSequenceProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponToneSequenceProfileMappingEntry 1}
 
gponToneSequenceProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponToneSequenceProfileMappingEntry 2}


-- *********************************************
-- GPON TONE EVENT PROFILE TABLE
--
-- This table was first introduced with ISAM4.2 MIB.
-- It is only SUPPORTED beginning with ISAM4.2.02 release.
--
-- This table contains information for associating call events with
-- desired tones.
-- From an OMCI standpoint, it maps primarily to the Tone Event Table
-- attribute in the Voice Service Profile ME.
--
--  Rows are created by the operator.
--
-- NOTE: Profile cannot be modified or deleted if associated with another table.
--
--	For GPON - SUPPORTED as of ISAM4.2.02
--	For XG-PON1 - SUPPORTED as of ISAM4.6.02
--  For NG-PON2 - SUPPORTED as of ISAM5.4.01
-- 
--
-- *********************************************

gponToneEventProfileTable OBJECT-TYPE
	SYNTAX	SEQUENCE OF GponToneEventProfileEntry
	ACCESS	not-accessible
	STATUS	mandatory
	DESCRIPTION
		"This object contains a table for creating and storing
		tone sequences.
		These profiles are normally associated with a Voice Service
		Profile "
::= { gponProfilesGroup 49 }

gponToneEventProfileEntry OBJECT-TYPE
	SYNTAX 	GponToneEventProfileEntry
	ACCESS	not-accessible
	STATUS	mandatory
	DESCRIPTION
		"Rows of this table contain Tone Event Profiles "
	INDEX {gponToneEventProfileIndex }
::= {gponToneEventProfileTable 1}

GponToneEventProfileEntry ::=
	SEQUENCE { 
		gponToneEventProfileIndex		AsamProfileIndex,
		gponToneEventProfileName		AsamProfileName,
		gponToneEventProfileRefCount		AsamProfileRefCount,
		gponToneEventProfileScope		AsamProfileScope,
		gponToneEventProfileRowStatus 		RowStatus,
		gponToneEventProfileBusyTonePointer		AsamProfilePointer,
		gponToneEventProfileBusyFilePointer		AsamProfilePointer,
		gponToneEventProfileBusyFileRepetitions	INTEGER,
		gponToneEventProfileConfTonePointer		AsamProfilePointer,
		gponToneEventProfileConfFilePointer		AsamProfilePointer,
		gponToneEventProfileConfFileRepetitions	INTEGER,
		gponToneEventProfileDialTonePointer		AsamProfilePointer,
		gponToneEventProfileDialFilePointer		AsamProfilePointer,
		gponToneEventProfileDialFileRepetitions	INTEGER,
		gponToneEventProfileMsgWaitTonePointer		AsamProfilePointer,
		gponToneEventProfileMsgWaitFilePointer		AsamProfilePointer,
		gponToneEventProfileMsgWaitFileRepetitions	INTEGER,
		gponToneEventProfileROHTonePointer		AsamProfilePointer,
		gponToneEventProfileROHFilePointer		AsamProfilePointer,
		gponToneEventProfileROHFileRepetitions	INTEGER,
		gponToneEventProfileRingbackTonePointer		AsamProfilePointer,
		gponToneEventProfileRingbackFilePointer		AsamProfilePointer,
		gponToneEventProfileRingbackFileRepetitions	INTEGER,
		gponToneEventProfileReorderTonePointer		AsamProfilePointer,
		gponToneEventProfileReorderFilePointer		AsamProfilePointer,
		gponToneEventProfileReorderFileRepetitions	INTEGER,
		gponToneEventProfileStutterDialTonePointer		AsamProfilePointer,
		gponToneEventProfileStutterDialFilePointer		AsamProfilePointer,
		gponToneEventProfileStutterDialFileRepetitions	INTEGER,
		gponToneEventProfileCallWait1TonePointer		AsamProfilePointer,
		gponToneEventProfileCallWait1FilePointer		AsamProfilePointer,
		gponToneEventProfileCallWait1FileRepetitions	INTEGER,
		gponToneEventProfileCallWait2TonePointer		AsamProfilePointer,
		gponToneEventProfileCallWait2FilePointer		AsamProfilePointer,
		gponToneEventProfileCallWait2FileRepetitions	INTEGER,
		gponToneEventProfileCallWait3TonePointer		AsamProfilePointer,
		gponToneEventProfileCallWait3FilePointer		AsamProfilePointer,
		gponToneEventProfileCallWait3FileRepetitions	INTEGER,
		gponToneEventProfileCallWait4TonePointer		AsamProfilePointer,
		gponToneEventProfileCallWait4FilePointer		AsamProfilePointer,
		gponToneEventProfileCallWait4FileRepetitions	INTEGER,
		gponToneEventProfileAlertSignalTonePointer		AsamProfilePointer,
		gponToneEventProfileAlertSignalFilePointer		AsamProfilePointer,
		gponToneEventProfileAlertSignalFileRepetitions	INTEGER,
		gponToneEventProfileSpecialDialTonePointer		AsamProfilePointer,
		gponToneEventProfileSpecialDialFilePointer		AsamProfilePointer,
		gponToneEventProfileSpecialDialFileRepetitions	INTEGER,
		gponToneEventProfileSpecialInfoTonePointer		AsamProfilePointer,
		gponToneEventProfileSpecialInfoFilePointer		AsamProfilePointer,
		gponToneEventProfileSpecialInfoFileRepetitions	INTEGER,
		gponToneEventProfileReleaseTonePointer		AsamProfilePointer,
		gponToneEventProfileReleaseFilePointer		AsamProfilePointer,
		gponToneEventProfileReleaseFileRepetitions	INTEGER,
		gponToneEventProfileCongestionTonePointer		AsamProfilePointer,
		gponToneEventProfileCongestionFilePointer		AsamProfilePointer,
		gponToneEventProfileCongestionFileRepetitions	INTEGER,
		gponToneEventProfileIntrusionTonePointer		AsamProfilePointer,
		gponToneEventProfileIntrusionFilePointer		AsamProfilePointer,
		gponToneEventProfileIntrusionFileRepetitions	INTEGER,
		gponToneEventProfileDeadToneTonePointer		AsamProfilePointer,
		gponToneEventProfileDeadToneFilePointer		AsamProfilePointer,
		gponToneEventProfileDeadToneFileRepetitions	INTEGER,
		gponToneEventProfileUserDef1TonePointer		AsamProfilePointer,
		gponToneEventProfileUserDef1FilePointer		AsamProfilePointer,
		gponToneEventProfileUserDef1FileRepetitions	INTEGER,
		gponToneEventProfileUserDef2TonePointer		AsamProfilePointer,
		gponToneEventProfileUserDef2FilePointer		AsamProfilePointer,
		gponToneEventProfileUserDef2FileRepetitions	INTEGER,
		gponToneEventProfileUserDef3TonePointer		AsamProfilePointer,
		gponToneEventProfileUserDef3FilePointer		AsamProfilePointer,
		gponToneEventProfileUserDef3FileRepetitions	INTEGER,
		gponToneEventProfileUserDef4TonePointer		AsamProfilePointer,
		gponToneEventProfileUserDef4FilePointer		AsamProfilePointer,
		gponToneEventProfileUserDef4FileRepetitions	INTEGER
}

gponToneEventProfileIndex OBJECT-TYPE 
	SYNTAX AsamProfileIndex
	ACCESS not-accessible
	STATUS mandatory
	DESCRIPTION
	    "This object is the index to the gponToneEventProfileTable. "
::= { gponToneEventProfileEntry 1}

gponToneEventProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponToneEventProfileEntry 2}

gponToneEventProfileRefCount OBJECT-TYPE
	SYNTAX	AsamProfileRefCount
	ACCESS read-only
	STATUS	mandatory
	DESCRIPTION
		" Indicates the number of entities using this profile. If the
          		reference count is greater than 0, then this profile is 'in use',
          		and may NOT be modified or deleted. If the value is 0, then this profile is
          		'not in use', and can be modified or deleted. "
::= { gponToneEventProfileEntry  3}


gponToneEventProfileScope OBJECT-TYPE
        	SYNTAX          AsamProfileScope
        	ACCESS          read-write
        	STATUS          mandatory
        	DESCRIPTION     
       		 "A  profile can be qualified as having a local scope or a network wide 
         		scope.

		Default = 1 = local scope. "
::= {gponToneEventProfileEntry  4}


gponToneEventProfileRowStatus OBJECT-TYPE 
	SYNTAX	RowStatus
	ACCESS	read-write
	STATUS  mandatory
	DESCRIPTION
		"This object is used to create a new row or modify or
         		delete an existing row in this table. 
       		     o The entry associated with a Profile that is being used may
             		 not be modified or deleted. "
::= { gponToneEventProfileEntry  5}

gponToneEventProfileBusyTonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 1 (Busy) in Tone Event Table attribute
		 of Voice Service Profile ME.

		 This attribute and alternative file pointer attribute (below) cannot both
		 be non-zero.

		 Modification is permitted only if profile is unassociated.  "
	::= { gponToneEventProfileEntry  6 }

gponToneEventProfileBusyFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 1 (Busy) in Tone Event Table attribute
		 of Voice Service Profile ME.

		 This attribute and alternative ToneSequence pointer attribute (above) cannot
		 both be non-zero.

		 Modification is permitted only if profile is unassociated.  "
	::= { gponToneEventProfileEntry  7 }

gponToneEventProfileBusyFileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  8 }

gponToneEventProfileConfTonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 2 (Confirmation) in Tone Event Table attribute
		 of Voice Service Profile ME.

		 This attribute and alternative file pointer attribute (below) cannot both
		 be non-zero.

		 Modification is permitted only if profile is unassociated.  "
	::= { gponToneEventProfileEntry  9 }

gponToneEventProfileConfFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 2 (Confirmation) in Tone Event Table attribute
		 of Voice Service Profile ME.

		 This attribute and alternative ToneSequence pointer attribute (above) cannot
		 both be non-zero.

		 Modification is permitted only if profile is unassociated.  "
	::= { gponToneEventProfileEntry  10 }

gponToneEventProfileConfFileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  11 }

gponToneEventProfileDialTonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 3 (Dial) in Tone Event Table attribute
		 of Voice Service Profile ME.

		 This attribute and alternative file pointer attribute (below) cannot both
		 be non-zero.

		 Modification is permitted only if profile is unassociated.  "
	::= { gponToneEventProfileEntry  12 }

gponToneEventProfileDialFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 3 (Dial) in Tone Event Table attribute
		 of Voice Service Profile ME.

		 This attribute and alternative ToneSequence pointer attribute (above) cannot
		 both be non-zero.

		 Modification is permitted only if profile is unassociated.  "
	::= { gponToneEventProfileEntry  13 }

gponToneEventProfileDialFileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  14 }

gponToneEventProfileMsgWaitTonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 4 (MsgWait) in Tone Event Table attribute
		 of Voice Service Profile ME.

		 This attribute and alternative file pointer attribute (below) cannot both
		 be non-zero.

		 Modification is permitted only if profile is unassociated.  "
	::= { gponToneEventProfileEntry  15 }

gponToneEventProfileMsgWaitFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 4 (MsgWait) in Tone Event Table attribute
		 of Voice Service Profile ME.

		 This attribute and alternative ToneSequence pointer attribute (above) cannot
		 both be non-zero.

		 Modification is permitted only if profile is unassociated.  "
	::= { gponToneEventProfileEntry  16 }

gponToneEventProfileMsgWaitFileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  17 }

gponToneEventProfileROHTonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 5 (ROH) in Tone Event Table attribute
		 of Voice Service Profile ME.

		 This attribute and alternative file pointer attribute (below) cannot both
		 be non-zero.

		 Modification is permitted only if profile is unassociated.  "
	::= { gponToneEventProfileEntry  18 }

gponToneEventProfileROHFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 5 (ROH) in Tone Event Table attribute
		 of Voice Service Profile ME.

		 This attribute and alternative ToneSequence pointer attribute (above) cannot
		 both be non-zero.

		 Modification is permitted only if profile is unassociated.  "
	::= { gponToneEventProfileEntry  19 }

gponToneEventProfileROHFileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  20 }

gponToneEventProfileRingbackTonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 6 (Ringback) in Tone Event Table attribute
		 of Voice Service Profile ME.

		 This attribute and alternative file pointer attribute (below) cannot both
		 be non-zero.

		 Modification is permitted only if profile is unassociated.  "
	::= { gponToneEventProfileEntry  21 }

gponToneEventProfileRingbackFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 6 (Ringback) in Tone Event Table attribute
		 of Voice Service Profile ME.

		 This attribute and alternative ToneSequence pointer attribute (above) cannot
		 both be non-zero.

		 Modification is permitted only if profile is unassociated.  "
	::= { gponToneEventProfileEntry  22 }

gponToneEventProfileRingbackFileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  23 }

gponToneEventProfileReorderTonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 7 (Reorder) in Tone Event Table attribute
		 of Voice Service Profile ME.

		 This attribute and alternative file pointer attribute (below) cannot both
		 be non-zero.

		 Modification is permitted only if profile is unassociated.  "
	::= { gponToneEventProfileEntry  24 }

gponToneEventProfileReorderFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 7 (Reorder) in Tone Event Table attribute
		 of Voice Service Profile ME.

		 This attribute and alternative ToneSequence pointer attribute (above) cannot
		 both be non-zero.

		 Modification is permitted only if profile is unassociated.  "
	::= { gponToneEventProfileEntry  25 }

gponToneEventProfileReorderFileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  26 }

gponToneEventProfileStutterDialTonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 8 (StutterDial) in Tone Event Table attribute
		 of Voice Service Profile ME.

		 This attribute and alternative file pointer attribute (below) cannot both
		 be non-zero.

		 Modification is permitted only if profile is unassociated.  "
	::= { gponToneEventProfileEntry  27 }

gponToneEventProfileStutterDialFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 8 (StutterDial) in Tone Event Table attribute
		 of Voice Service Profile ME.

		 This attribute and alternative ToneSequence pointer attribute (above) cannot
		 both be non-zero.

		 Modification is permitted only if profile is unassociated.  "
	::= { gponToneEventProfileEntry  28 }

gponToneEventProfileStutterDialFileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  29 }

gponToneEventProfileCallWait1TonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 9 (CallWait1) in Tone Event Table attribute
		 of Voice Service Profile ME.

		 This attribute and alternative file pointer attribute (below) cannot both
		 be non-zero.

		 Modification is permitted only if profile is unassociated.  "
	::= { gponToneEventProfileEntry  30 }

gponToneEventProfileCallWait1FilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 9 (CallWait1) in Tone Event Table attribute
		 of Voice Service Profile ME.

		 This attribute and alternative ToneSequence pointer attribute (above) cannot
		 both be non-zero.

		 Modification is permitted only if profile is unassociated.  "
	::= { gponToneEventProfileEntry  31 }

gponToneEventProfileCallWait1FileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  32 }

gponToneEventProfileCallWait2TonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 10 (CallWait2) in Tone Event Table attribute
		 of Voice Service Profile ME.

		 This attribute and alternative file pointer attribute (below) cannot both
		 be non-zero.

		 Modification is permitted only if profile is unassociated.  "
	::= { gponToneEventProfileEntry  33 }

gponToneEventProfileCallWait2FilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 10 (CallWait2) in Tone Event Table attribute
		 of Voice Service Profile ME.

		 This attribute and alternative ToneSequence pointer attribute (above) cannot
		 both be non-zero.

		 Modification is permitted only if profile is unassociated.  "
	::= { gponToneEventProfileEntry  34 }

gponToneEventProfileCallWait2FileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  35 }

gponToneEventProfileCallWait3TonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 11 (CallWait3) in Tone Event Table attribute
		 of Voice Service Profile ME.

		 This attribute and alternative file pointer attribute (below) cannot both
		 be non-zero.

		 Modification is permitted only if profile is unassociated.  "
	::= { gponToneEventProfileEntry  36 }

gponToneEventProfileCallWait3FilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 11 (CallWait3) in Tone Event Table attribute
		 of Voice Service Profile ME.

		 This attribute and alternative ToneSequence pointer attribute (above) cannot
		 both be non-zero.

		 Modification is permitted only if profile is unassociated.  "
	::= { gponToneEventProfileEntry  37 }

gponToneEventProfileCallWait3FileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  38 }

gponToneEventProfileCallWait4TonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 12 (CallWait4) in Tone Event Table attribute
		 of Voice Service Profile ME.

		 This attribute and alternative file pointer attribute (below) cannot both
		 be non-zero.

		 Modification is permitted only if profile is unassociated.  "
	::= { gponToneEventProfileEntry  39 }

gponToneEventProfileCallWait4FilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 12 (CallWait4) in Tone Event Table attribute
		 of Voice Service Profile ME.

		 This attribute and alternative ToneSequence pointer attribute (above) cannot
		 both be non-zero.

		 Modification is permitted only if profile is unassociated.  "
	::= { gponToneEventProfileEntry  40 }

gponToneEventProfileCallWait4FileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  41 }

gponToneEventProfileAlertSignalTonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 13 (AlertSignal) in Tone Event Table attribute
		 of Voice Service Profile ME.

		 This attribute and alternative file pointer attribute (below) cannot both
		 be non-zero.

		 Modification is permitted only if profile is unassociated.  "
	::= { gponToneEventProfileEntry  42 }

gponToneEventProfileAlertSignalFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 13 (AlertSignal) in Tone Event Table attribute
		 of Voice Service Profile ME.

		 This attribute and alternative ToneSequence pointer attribute (above) cannot
		 both be non-zero.

		 Modification is permitted only if profile is unassociated.  "
	::= { gponToneEventProfileEntry  43 }

gponToneEventProfileAlertSignalFileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  44 }

gponToneEventProfileSpecialDialTonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 14 (SpecialDial) in Tone Event Table attribute
		 of Voice Service Profile ME.

		 This attribute and alternative file pointer attribute (below) cannot both
		 be non-zero.

		 Modification is permitted only if profile is unassociated.  "
	::= { gponToneEventProfileEntry  45 }

gponToneEventProfileSpecialDialFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 14 (SpecialDial) in Tone Event Table attribute
		 of Voice Service Profile ME.

		 This attribute and alternative ToneSequence pointer attribute (above) cannot
		 both be non-zero.

		 Modification is permitted only if profile is unassociated.  "
	::= { gponToneEventProfileEntry  46 }

gponToneEventProfileSpecialDialFileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  47 }

gponToneEventProfileSpecialInfoTonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 15 (SpecialInfo) in Tone Event Table attribute
		 of Voice Service Profile ME.

		 This attribute and alternative file pointer attribute (below) cannot both
		 be non-zero.

		 Modification is permitted only if profile is unassociated.  "
	::= { gponToneEventProfileEntry  48 }

gponToneEventProfileSpecialInfoFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 15 (SpecialInfo) in Tone Event Table attribute
		 of Voice Service Profile ME.

		 This attribute and alternative ToneSequence pointer attribute (above) cannot
		 both be non-zero.

		 Modification is permitted only if profile is unassociated.  "
	::= { gponToneEventProfileEntry  49 }

gponToneEventProfileSpecialInfoFileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  50 }

gponToneEventProfileReleaseTonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 16 (Release) in Tone Event Table attribute
		 of Voice Service Profile ME.

		 This attribute and alternative file pointer attribute (below) cannot both
		 be non-zero.

		 Modification is permitted only if profile is unassociated.  "
	::= { gponToneEventProfileEntry  51 }

gponToneEventProfileReleaseFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 16 (Release) in Tone Event Table attribute
		 of Voice Service Profile ME.

		 This attribute and alternative ToneSequence pointer attribute (above) cannot
		 both be non-zero.

		 Modification is permitted only if profile is unassociated.  "
	::= { gponToneEventProfileEntry  52 }

gponToneEventProfileReleaseFileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  53 }

gponToneEventProfileCongestionTonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 17 (Congestion) in Tone Event Table attribute
		 of Voice Service Profile ME.

		 This attribute and alternative file pointer attribute (below) cannot both
		 be non-zero.

		 Modification is permitted only if profile is unassociated.  "
	::= { gponToneEventProfileEntry  54 }

gponToneEventProfileCongestionFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 17 (Congestion) in Tone Event Table attribute
		 of Voice Service Profile ME.

		 This attribute and alternative ToneSequence pointer attribute (above) cannot
		 both be non-zero.

		 Modification is permitted only if profile is unassociated.  "
	::= { gponToneEventProfileEntry  55 }

gponToneEventProfileCongestionFileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  56 }

gponToneEventProfileIntrusionTonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 33 (Intrusion) in Tone Event Table attribute
		 of Voice Service Profile ME.

		 This attribute and alternative file pointer attribute (below) cannot both
		 be non-zero.

		 Modification is permitted only if profile is unassociated.  "
	::= { gponToneEventProfileEntry  57 }

gponToneEventProfileIntrusionFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 33 (Intrusion) in Tone Event Table attribute
		 of Voice Service Profile ME.

		 This attribute and alternative ToneSequence pointer attribute (above) cannot
		 both be non-zero.

		 Modification is permitted only if profile is unassociated.  "
	::= { gponToneEventProfileEntry  58 }

gponToneEventProfileIntrusionFileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  59 }

gponToneEventProfileDeadToneTonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 34 (DeadTone) in Tone Event Table attribute
		 of Voice Service Profile ME.

		 This attribute and alternative file pointer attribute (below) cannot both
		 be non-zero.

		 Modification is permitted only if profile is unassociated.  "
	::= { gponToneEventProfileEntry  60 }

gponToneEventProfileDeadToneFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to Event 34 (DeadTone) in Tone Event Table attribute
		 of Voice Service Profile ME.

		 This attribute and alternative ToneSequence pointer attribute (above) cannot
		 both be non-zero.

		 Modification is permitted only if profile is unassociated.  "
	::= { gponToneEventProfileEntry  61 }

gponToneEventProfileDeadToneFileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  62 }

gponToneEventProfileUserDef1TonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 18 (User Defined 1) in Tone Event Table attribute
		 of Voice Service Profile ME.

		 This attribute and alternative file pointer attribute (below) cannot both
		 be non-zero.

		 Modification is permitted only if profile is unassociated.  "
	::= { gponToneEventProfileEntry  63 }

gponToneEventProfileUserDef1FilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to 18 (User Defined 1) in Tone Event Table attribute
		 of Voice Service Profile ME.

		 This attribute and alternative ToneSequence pointer attribute (above) cannot
		 both be non-zero.

		 Modification is permitted only if profile is unassociated.  "
	::= { gponToneEventProfileEntry  64 }

gponToneEventProfileUserDef1FileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  65 }

gponToneEventProfileUserDef2TonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 19 (User Defined 2) in Tone Event Table attribute
		 of Voice Service Profile ME.

		 This attribute and alternative file pointer attribute (below) cannot both
		 be non-zero.

		 Modification is permitted only if profile is unassociated.  "
	::= { gponToneEventProfileEntry  66 }

gponToneEventProfileUserDef2FilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to 19 (User Defined 2) in Tone Event Table attribute
		 of Voice Service Profile ME.

		 This attribute and alternative ToneSequence pointer attribute (above) cannot
		 both be non-zero.

		 Modification is permitted only if profile is unassociated.  "
	::= { gponToneEventProfileEntry  67 }

gponToneEventProfileUserDef2FileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  68 }

gponToneEventProfileUserDef3TonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 20 (User Defined 3) in Tone Event Table attribute
		 of Voice Service Profile ME.

		 This attribute and alternative file pointer attribute (below) cannot both
		 be non-zero.

		 Modification is permitted only if profile is unassociated.  "
	::= { gponToneEventProfileEntry  69 }

gponToneEventProfileUserDef3FilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to 20 (User Defined 3) in Tone Event Table attribute
		 of Voice Service Profile ME.

		 This attribute and alternative ToneSequence pointer attribute (above) cannot
		 both be non-zero.

		 Modification is permitted only if profile is unassociated.  "
	::= { gponToneEventProfileEntry  70 }

gponToneEventProfileUserDef3FileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  71 }

gponToneEventProfileUserDef4TonePointer  OBJECT-TYPE
	SYNTAX 	AsamProfilePointer
	ACCESS	read-write
	STATUS	mandatory
	DESCRIPTION 
		"This attribute points to a row in gponToneSequenceProfileTable

		 Value 0 (default) is permitted - meaning none defined via that profile.
		 In OMCI - this applies to Event 21 (User Defined 4) in Tone Event Table attribute
		 of Voice Service Profile ME.

		 This attribute and alternative file pointer attribute (below) cannot both
		 be non-zero.

		 Modification is permitted only if profile is unassociated.  "
	::= { gponToneEventProfileEntry  72 }

gponToneEventProfileUserDef4FilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no tone is played.

		 Value 0 (default) is permitted - meaning none defined for this event.
		 In OMCI - this applies to 21 (User Defined 4) in Tone Event Table attribute
		 of Voice Service Profile ME.

		 This attribute and alternative ToneSequence pointer attribute (above) cannot
		 both be non-zero.

		 Modification is permitted only if profile is unassociated.  "
	::= { gponToneEventProfileEntry  73 }

gponToneEventProfileUserDef4FileRepetitions  OBJECT-TYPE
	SYNTAX 	INTEGER
	ACCESS	read-write
	STATUS	mandatory
	DESCRIPTION 
		"This attribute specifies the number of times the tone file (see above) is 
		 repeated.

		 Range is 0..10.

		 Value 0 (default) -  means the tone file is repeated indefinitely
		 until terminated by some external event (such as a call).

		 Modification is permitted only if profile is unassociated.  "
	::= { gponToneEventProfileEntry  74 }


gponToneEventProfileIndexNext        OBJECT-TYPE
        	SYNTAX          AsamNextProfileIndex
        	ACCESS          read-only
        	STATUS          mandatory
        	DESCRIPTION     
        	"This object contains an appropriate value to be used for 
         		gponToneEventProfileIndex when creating entries in the
         		gponToneEventProfileTable. 
         		The value 0 indicates that no unassigned entries are available. To 
         		obtain the next index value for a new entry, the
        		 manager issues a management protocol retrieval operation to obtain the
         		current value of this object.  After each retrieval, the agent should
        		 modify the value to the next unassigned index. "
::= {gponProfilesGroup 50 }


  gponToneEventProfileMaxIndex        OBJECT-TYPE
      	SYNTAX            AsamMaxProfileIndex
      	ACCESS            read-only
     	 STATUS            mandatory
      	DESCRIPTION
            	"This object represents the maximum number of
            		 gponToneEventProfiles that can be created. The object
             		 gponToneEventProfileIndexNext will have values ranging
            		 from 0 to the value represented by this object. 
		 For ISAM4.2,  initially set to 5. "
::= {gponProfilesGroup 51 }

-- *********************************************
-- GPON TONE EVENT PROFILE MAPPING TABLE
--
-- This table was first introduced with ISAM4.2 MIB.
-- It is only SUPPORTED beginning with ISAM4.2.02 release.
--
-- For the gponToneEventProfileTable, this table provides a reverse mapping
-- (i.e. profile name to profile index number).
--
-- The system automatically creates an entry in this Table when a  corresponding entry
-- in gponToneEventProfile is created. 
-- The system automatically deletes an entry in this Table when a  corresponding entry
-- in gponToneEventProfile is deleted.
--
--	For GPON - SUPPORTED as of ISAM4.2.02
--	For XG-PON1 - SUPPORTED as of ISAM4.6.02
--  For NG-PON2 - SUPPORTED as of ISAM5.4.01
--   
--
-- *********************************************

 
gponToneEventProfileMappingTable OBJECT-TYPE
   SYNTAX   SEQUENCE OF GponToneEventProfileMappingEntry
   ACCESS   not-accessible
   STATUS   mandatory
   DESCRIPTION
   "This object contains a table for gponToneEventProfile
name to index mapping"
::= { gponProfilesGroup 52 }
 
gponToneEventProfileMappingEntry OBJECT-TYPE
   SYNTAX   GponToneEventProfileMappingEntry
   ACCESS   not-accessible
   STATUS mandatory
   DESCRIPTION
   " An entry (conceptual row) representing the gponToneEventProfile Name to Index mapping."
   INDEX {gponToneEventProfileMappingName }
   ::= {gponToneEventProfileMappingTable  1}
 
GponToneEventProfileMappingEntry ::=
   SEQUENCE { 
	gponToneEventProfileMappingName     AsamProfileName,
      	gponToneEventProfileMappingIndex      AsamProfileIndex
  }
 
gponToneEventProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponToneEventProfileMappingEntry 1}
 
gponToneEventProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponToneEventProfileMappingEntry 2}

-- *********************************************
-- GPON RING PATTERN PROFILE TABLE
--
-- This table was first introduced with ISAM4.2 MIB.
-- It is only SUPPORTED beginning with ISAM4.2.02 release.
--
-- This table contains information for defining a ring
-- (or silence) along with a duration.
-- From an OMCI standpoint, it maps primarily to the Ring Pattern Table
-- attribute in the Voice Service Profile ME.
--
--  Rows are created by the operator.
--
-- NOTE: Profile cannot be deleted if associated with another table.
--
--	For GPON - SUPPORTED as of ISAM4.2.02
--	For XG-PON1 - SUPPORTED as of ISAM4.6.02
--  For NG-PON2 - SUPPORTED as of ISAM5.4.01
-- 
--
-- *********************************************

gponRingPatternProfileTable OBJECT-TYPE
	SYNTAX	SEQUENCE OF GponRingPatternProfileEntry
	ACCESS	not-accessible
	STATUS	mandatory
	DESCRIPTION
		"This object contains a table for creating and storing
		Ring pattern definitions. 
		These profiles are normally associated with Ring Sequence
		Profiles.  "
::= { gponProfilesGroup 53 }

gponRingPatternProfileEntry OBJECT-TYPE
	SYNTAX 	GponRingPatternProfileEntry
	ACCESS	not-accessible
	STATUS	mandatory
	DESCRIPTION
		"Rows of this table contain Ring Pattern Profiles "
	INDEX {gponRingPatternProfileIndex }
::= {gponRingPatternProfileTable 1}

GponRingPatternProfileEntry ::=
	SEQUENCE { 
		gponRingPatternProfileIndex		AsamProfileIndex,
		gponRingPatternProfileName		AsamProfileName,
		gponRingPatternProfileRefCount		AsamProfileRefCount,
		gponRingPatternProfileScope		AsamProfileScope,
		gponRingPatternProfileRowStatus 	RowStatus,
		gponRingPatternProfileOnOffInd	INTEGER,
		gponRingPatternProfileDuration		INTEGER
}

gponRingPatternProfileIndex OBJECT-TYPE 
	SYNTAX AsamProfileIndex
	ACCESS not-accessible
	STATUS mandatory
	DESCRIPTION
	    "This object is the index to the gponRingPatternProfileTable. "
::= { gponRingPatternProfileEntry 1}

gponRingPatternProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponRingPatternProfileEntry 2}

gponRingPatternProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponRingPatternProfileEntry  3}


gponRingPatternProfileScope OBJECT-TYPE
        	SYNTAX          AsamProfileScope
        	ACCESS          read-write
        	STATUS          mandatory
        	DESCRIPTION     
       		 "A  profile can be qualified as having a local scope or a network wide 
         		scope.

		Default = 1 = local scope. "
::= {gponRingPatternProfileEntry  4}


gponRingPatternProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponRingPatternProfileEntry  5}

gponRingPatternProfileOnOffInd  OBJECT-TYPE
	SYNTAX 	INTEGER
	ACCESS	read-write
	STATUS	mandatory
	DESCRIPTION 
		"This attribute controls whether Ring is OFF or ON. 

		 0 = OFF
		 1 = ON (default)

		 Modification is NOT permitted.  "
	::= { gponRingPatternProfileEntry  6 }


gponRingPatternProfileDuration  OBJECT-TYPE
	SYNTAX 	INTEGER
	ACCESS	read-write
	STATUS	mandatory
	DESCRIPTION 
		"This attribute specifies the duration of the phase (in milliseconds).  The value 0 specifies that
		 the phase endures indefinitely (i.e. until terminated by other events such as call abandonment).

		 Range is 0 - 65535 (milliseconds)

		 Modification is NOT permitted.  "
	::= { gponRingPatternProfileEntry  7 }


gponRingPatternProfileIndexNext        OBJECT-TYPE
        	SYNTAX          AsamNextProfileIndex
        	ACCESS          read-only
        	STATUS          mandatory
        	DESCRIPTION     
        	"This object contains an appropriate value to be used for 
         		gponRingPatternProfileIndex when creating entries in the
         		gponRingPatternProfileTable. 
         		The value 0 indicates that no unassigned entries are available. To 
         		obtain the next index value for a new entry, the
        		 manager issues a management protocol retrieval operation to obtain the
         		current value of this object.  After each retrieval, the agent should
        		 modify the value to the next unassigned index. "
::= {gponProfilesGroup 54 }


  gponRingPatternProfileMaxIndex        OBJECT-TYPE
      	SYNTAX            AsamMaxProfileIndex
      	ACCESS            read-only
     	 STATUS            mandatory
      	DESCRIPTION
            	"This object represents the maximum number of
            		 gponRingPatternProfiles that can be created. The object
             		 gponRingPatternProfileIndexNext will have values ranging
            		 from 0 to the value represented by this object. 
		 For ISAM4.2,  initially set to 20. "
::= {gponProfilesGroup 55 }

-- *********************************************
-- GPON RING PATTERN PROFILE MAPPING TABLE
--
-- This table was first introduced with ISAM4.2 MIB.
-- It is only SUPPORTED beginning with ISAM4.2.02 release.
--
-- For the gponRingPatternProfileTable, this table provides a reverse mapping
-- (i.e. profile name to profile index number).
--
-- The system automatically creates an entry in this Table when a  corresponding entry
-- in gponRingPatternProfile is created. 
-- The system automatically deletes an entry in this Table when a  corresponding entry
-- in gponRingPatternProfile is deleted.
--
--	For GPON - SUPPORTED as of ISAM4.2.02
--	For XG-PON1 - SUPPORTED as of ISAM4.6.02
--  For NG-PON2 - SUPPORTED as of ISAM5.4.01
--   
--
-- *********************************************

 
gponRingPatternProfileMappingTable OBJECT-TYPE
   SYNTAX   SEQUENCE OF GponRingPatternProfileMappingEntry
   ACCESS   not-accessible
   STATUS   mandatory
   DESCRIPTION
   "This object contains a table for gponRingPatternProfile
name to index mapping"
::= { gponProfilesGroup 56 }
 
gponRingPatternProfileMappingEntry OBJECT-TYPE
   SYNTAX   GponRingPatternProfileMappingEntry
   ACCESS   not-accessible
   STATUS mandatory
   DESCRIPTION
   " An entry (conceptual row) representing the gponRingPatternProfile Name to Index mapping."
   INDEX {gponRingPatternProfileMappingName }
   ::= {gponRingPatternProfileMappingTable  1}
 
GponRingPatternProfileMappingEntry ::=
   SEQUENCE { 
	gponRingPatternProfileMappingName     AsamProfileName,
      	gponRingPatternProfileMappingIndex      AsamProfileIndex
  }
 
gponRingPatternProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponRingPatternProfileMappingEntry 1}
 
gponRingPatternProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponRingPatternProfileMappingEntry 2}


-- *********************************************
-- GPON RING PATTERN SEQUENCE PROFILE TABLE
--
-- This table was first introduced with ISAM4.2 MIB.
-- It is only SUPPORTED beginning with ISAM4.2.02 release.
--
-- This table contains information for defining a sequence of
-- ring patterns.
-- From an OMCI standpoint, it maps primarily to the Ring Pattern Table
-- attribute in the Voice Service Profile ME.
--
--  Rows are created by the operator.
--
-- NOTE: Profile cannot be deleted if associated with another table.
--
--	For GPON - SUPPORTED as of ISAM4.2.02
--	For XG-PON1 - SUPPORTED as of ISAM4.6.02
--  For NG-PON2 - SUPPORTED as of ISAM5.4.01
-- 
--
-- *********************************************

gponRingSequenceProfileTable OBJECT-TYPE
	SYNTAX	SEQUENCE OF GponRingSequenceProfileEntry
	ACCESS	not-accessible
	STATUS	mandatory
	DESCRIPTION
		"This object contains a table for creating and storing
		Ring sequences.
		These profiles are normally associated with a Ring Event
		Profile "
::= { gponProfilesGroup 57 }

gponRingSequenceProfileEntry OBJECT-TYPE
	SYNTAX 	GponRingSequenceProfileEntry
	ACCESS	not-accessible
	STATUS	mandatory
	DESCRIPTION
		"Rows of this table contain Ring Sequence Profiles "
	INDEX {gponRingSequenceProfileIndex }
::= {gponRingSequenceProfileTable 1}

GponRingSequenceProfileEntry ::=
	SEQUENCE { 
		gponRingSequenceProfileIndex		AsamProfileIndex,
		gponRingSequenceProfileName		AsamProfileName,
		gponRingSequenceProfileRefCount		AsamProfileRefCount,
		gponRingSequenceProfileScope		AsamProfileScope,
		gponRingSequenceProfileRowStatus 		RowStatus,
		gponRingSequenceProfilePattern1Pointer	AsamProfilePointer,
		gponRingSequenceProfilePattern2Pointer	AsamProfilePointer,
		gponRingSequenceProfilePattern3Pointer	AsamProfilePointer,
		gponRingSequenceProfilePattern4Pointer	AsamProfilePointer,
		gponRingSequenceProfilePattern5Pointer	AsamProfilePointer

}

gponRingSequenceProfileIndex OBJECT-TYPE 
	SYNTAX AsamProfileIndex
	ACCESS not-accessible
	STATUS mandatory
	DESCRIPTION
	    "This object is the index to the gponRingSequenceProfileTable. "
::= { gponRingSequenceProfileEntry 1}

gponRingSequenceProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponRingSequenceProfileEntry 2}

gponRingSequenceProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponRingSequenceProfileEntry  3}


gponRingSequenceProfileScope OBJECT-TYPE
        	SYNTAX          AsamProfileScope
        	ACCESS          read-write
        	STATUS          mandatory
        	DESCRIPTION     
       		 "A  profile can be qualified as having a local scope or a network wide 
         		scope.

		Default = 1 = local scope. "
::= {gponRingSequenceProfileEntry  4}


gponRingSequenceProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponRingSequenceProfileEntry  5}

gponRingSequenceProfilePattern1Pointer  OBJECT-TYPE
	SYNTAX 	AsamProfilePointer
	ACCESS	read-write
	STATUS	mandatory
	DESCRIPTION 
		"This attribute points to a row in gponRingPatternProfileTable

		 Value 0 is NOT permitted.
		 No default - must be supplied by manager.

		 Modification is NOT permitted.  "
	::= { gponRingSequenceProfileEntry  6 }

gponRingSequenceProfilePattern2Pointer  OBJECT-TYPE
	SYNTAX 	AsamProfilePointer
	ACCESS	read-write
	STATUS	mandatory
	DESCRIPTION 
		"This attribute points to a row in gponRingPatternProfileTable.  It
		 logically follows the previous Ring pattern reference.

		 Value 0 is permitted - meaning that Ring sequence STOPS.
		 If non-zero, must point to a Ring pattern (defined in RingPatternProfileTable). 

		 If the pattern referenced here has already been previously referenced
		 within this profile - then it should be considered as a logical jump back to
		 that previous reference (and the sequence continues from that point forward).
		 This effectively allows the definition of a cyclical sequence of Ring patterns.

		 Other than the zero value, the same Ring pattern cannot be referenced more than twice
		 within the same gponRingSequenceProfile.

		 Default = 0 (null pointer).
		 VALIDATION:  Once a null value has been established for a pointer, all subsequent
			pattern pointers in this table must also be null.

		 Modification is NOT permitted.  "
	::= { gponRingSequenceProfileEntry  7 }

gponRingSequenceProfilePattern3Pointer  OBJECT-TYPE
	SYNTAX 	AsamProfilePointer
	ACCESS	read-write
	STATUS	mandatory
	DESCRIPTION 
		"This attribute points to a row in gponRingPatternProfileTable.  It
		 logically follows the previous Ring pattern reference.

		 Value 0 is permitted - meaning that Ring sequence STOPS.
		 If non-zero, must point to a Ring pattern (defined in RingPatternProfileTable). 

		 If the pattern referenced here has already been previously referenced
		 within this profile - then it should be considered as a logical jump back to
		 that previous reference (and the sequence continues from that point forward).
		 This effectively allows the definition of a cyclical sequence of Ring patterns.

		 Other than the zero value, the same Ring pattern cannot be referenced more than twice
		 within the same gponRingSequenceProfile.

		 Default = 0 (null pointer).
		 VALIDATION:  Once a null value has been established for a pointer, all subsequent
			pattern pointers in this table must also be null.

		 Modification is NOT permitted.  "
	::= { gponRingSequenceProfileEntry  8 }

gponRingSequenceProfilePattern4Pointer  OBJECT-TYPE
	SYNTAX 	AsamProfilePointer
	ACCESS	read-write
	STATUS	mandatory
	DESCRIPTION 
		"This attribute points to a row in gponRingPatternProfileTable.  It
		 logically follows the previous Ring pattern reference.

		 Value 0 is permitted - meaning that Ring sequence STOPS.
		 If non-zero, must point to a Ring pattern (defined in RingPatternProfileTable). 

		 If the pattern referenced here has already been previously referenced
		 within this profile - then it should be considered as a logical jump back to
		 that previous reference (and the sequence continues from that point forward).
		 This effectively allows the definition of a cyclical sequence of Ring patterns.

		 Other than the zero value, the same Ring pattern cannot be referenced more than twice
		 within the same gponRingSequenceProfile.

		 Default = 0 (null pointer).
		 VALIDATION:  Once a null value has been established for a pointer, all subsequent
			pattern pointers in this table must also be null.

		 Modification is NOT permitted.  "
	::= { gponRingSequenceProfileEntry  9 }

gponRingSequenceProfilePattern5Pointer  OBJECT-TYPE
	SYNTAX 	AsamProfilePointer
	ACCESS	read-write
	STATUS	mandatory
	DESCRIPTION 
		"This attribute points to a row in gponRingPatternProfileTable.  It
		 logically follows the previous Ring pattern reference.

		 Value 0 is permitted - meaning that Ring sequence STOPS.
		 If non-zero, must point to a Ring pattern (defined in RingPatternProfileTable). 

		 If the pattern referenced here has already been previously referenced
		 within this profile - then it should be considered as a logical jump back to
		 that previous reference (and the sequence continues from that point forward).
		 This effectively allows the definition of a cyclical sequence of Ring patterns.

		 Other than the zero value, the same Ring pattern cannot be referenced more than twice
		 within the same gponRingSequenceProfile.

		 Default = 0 (null pointer).
		 VALIDATION:  Once a null value has been established for a pointer, all subsequent
			pattern pointers in this table must also be null.

		 Modification is NOT permitted.  "
	::= { gponRingSequenceProfileEntry  10 }



gponRingSequenceProfileIndexNext        OBJECT-TYPE
        	SYNTAX          AsamNextProfileIndex
        	ACCESS          read-only
        	STATUS          mandatory
        	DESCRIPTION     
        	"This object contains an appropriate value to be used for 
         		gponRingSequenceProfileIndex when creating entries in the
         		gponRingSequenceProfileTable. 
         		The value 0 indicates that no unassigned entries are available. To 
         		obtain the next index value for a new entry, the
        		 manager issues a management protocol retrieval operation to obtain the
         		current value of this object.  After each retrieval, the agent should
        		 modify the value to the next unassigned index. "
::= {gponProfilesGroup 58 }


  gponRingSequenceProfileMaxIndex        OBJECT-TYPE
      	SYNTAX            AsamMaxProfileIndex
      	ACCESS            read-only
     	 STATUS            mandatory
      	DESCRIPTION
            	"This object represents the maximum number of
            		 gponRingSequenceProfiles that can be created. The object
             		 gponRingSequenceProfileIndexNext will have values ranging
            		 from 0 to the value represented by this object. 
		 For ISAM4.2,  initially set to 20. "
::= {gponProfilesGroup 59 }

-- *********************************************
-- GPON RING SEQUENCE PROFILE MAPPING TABLE
--
-- This table was first introduced with ISAM4.2 MIB.
-- It is only SUPPORTED beginning with ISAM4.2.02 release.
--
-- For the gponRingSequenceProfileTable, this table provides a reverse mapping
-- (i.e. profile name to profile index number).
--
-- The system automatically creates an entry in this Table when a  corresponding entry
-- in gponRingSequenceProfile is created. 
-- The system automatically deletes an entry in this Table when a  corresponding entry
-- in gponRingSequenceProfile is deleted.
--
--	For GPON - SUPPORTED as of ISAM4.2.02
--	For XG-PON1 - SUPPORTED as of ISAM4.6.02
--  For NG-PON2 - SUPPORTED as of ISAM5.4.01
--   
--
-- *********************************************

 
gponRingSequenceProfileMappingTable OBJECT-TYPE
   SYNTAX   SEQUENCE OF GponRingSequenceProfileMappingEntry
   ACCESS   not-accessible
   STATUS   mandatory
   DESCRIPTION
   "This object contains a table for gponRingSequenceProfile
name to index mapping"
::= { gponProfilesGroup 60 }
 
gponRingSequenceProfileMappingEntry OBJECT-TYPE
   SYNTAX   GponRingSequenceProfileMappingEntry
   ACCESS   not-accessible
   STATUS mandatory
   DESCRIPTION
   " An entry (conceptual row) representing the gponRingSequenceProfile Name to Index mapping."
   INDEX {gponRingSequenceProfileMappingName }
   ::= {gponRingSequenceProfileMappingTable  1}
 
GponRingSequenceProfileMappingEntry ::=
   SEQUENCE { 
	gponRingSequenceProfileMappingName     AsamProfileName,
      	gponRingSequenceProfileMappingIndex      AsamProfileIndex
  }
 
gponRingSequenceProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponRingSequenceProfileMappingEntry 1}
 
gponRingSequenceProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponRingSequenceProfileMappingEntry 2}


-- *********************************************
-- GPON RING EVENT PROFILE TABLE
--
-- This table was first introduced with ISAM4.2 MIB.
-- It is only SUPPORTED beginning with ISAM4.2.02 release.
--
-- This table contains information for associating ring events with
-- desired ring sequences.
-- From an OMCI standpoint, it maps primarily to the Ring Event Table
-- attribute in the Voice Service Profile ME.
--
--  Rows are created by the operator.
--
-- NOTE: Profile cannot be deleted if associated with another table.
--
--	For GPON - SUPPORTED as of ISAM4.2.02
--	For XG-PON1 - SUPPORTED as of ISAM4.6.02
--  For NG-PON2 - SUPPORTED as of ISAM5.4.01
-- 
--
-- *********************************************

gponRingEventProfileTable OBJECT-TYPE
	SYNTAX	SEQUENCE OF GponRingEventProfileEntry
	ACCESS	not-accessible
	STATUS	mandatory
	DESCRIPTION
		"This object contains a table for creating and storing
		Ring sequences.
		These profiles are normally associated with a Voice Service
		Profile "
::= { gponProfilesGroup 61 }

gponRingEventProfileEntry OBJECT-TYPE
	SYNTAX 	GponRingEventProfileEntry
	ACCESS	not-accessible
	STATUS	mandatory
	DESCRIPTION
		"Rows of this table contain Ring Event Profiles "
	INDEX {gponRingEventProfileIndex }
::= {gponRingEventProfileTable 1}

GponRingEventProfileEntry ::=
	SEQUENCE { 
		gponRingEventProfileIndex		AsamProfileIndex,
		gponRingEventProfileName		AsamProfileName,
		gponRingEventProfileRefCount		AsamProfileRefCount,
		gponRingEventProfileScope		AsamProfileScope,
		gponRingEventProfileRowStatus 		RowStatus,
		gponRingEventProfileDefaultRingPointer		AsamProfilePointer,
		gponRingEventProfileDefaultFilePointer		AsamProfilePointer,
		gponRingEventProfileDefaultFileRepetitions	INTEGER,
		gponRingEventProfileDefaultTextPointer	AsamProfilePointer,
		gponRingEventProfileSplashRingPointer		AsamProfilePointer,
		gponRingEventProfileSplashFilePointer		AsamProfilePointer,
		gponRingEventProfileSplashFileRepetitions	INTEGER,
		gponRingEventProfileSplashTextPointer	AsamProfilePointer
}

gponRingEventProfileIndex OBJECT-TYPE 
	SYNTAX AsamProfileIndex
	ACCESS not-accessible
	STATUS mandatory
	DESCRIPTION
	    "This object is the index to the gponRingEventProfileTable. "
::= { gponRingEventProfileEntry 1}

gponRingEventProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponRingEventProfileEntry 2}

gponRingEventProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponRingEventProfileEntry  3}


gponRingEventProfileScope OBJECT-TYPE
        	SYNTAX          AsamProfileScope
        	ACCESS          read-write
        	STATUS          mandatory
        	DESCRIPTION     
       		 "A  profile can be qualified as having a local scope or a network wide 
         		scope.

		Default = 1 = local scope. "
::= {gponRingEventProfileEntry  4}


gponRingEventProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponRingEventProfileEntry  5}

gponRingEventProfileDefaultRingPointer  OBJECT-TYPE
	SYNTAX 	AsamProfilePointer
	ACCESS	read-write
	STATUS	mandatory
	DESCRIPTION 
		"This attribute points to a row in gponRingSequenceProfileTable

		 Value 0 (default) is permitted - meaning none defined via that profile.
		 In OMCI - this applies to Event 1 (Default) in Ring Event Table attribute
		 of Voice Service Profile ME.

		 If both this attribute and alternative file pointer attribute (below) are non-zero,
		 then this attribute overrides.

		 Modification is NOT permitted.  "
	::= { gponRingEventProfileEntry  6 }

gponRingEventProfileDefaultFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no Ring is played.

		 Value 0 (default) is permitted - meaning none defined for this event.
		 In OMCI - this applies to Event 1 (Default) in Ring Event Table attribute
		 of Voice Service Profile ME.

		 Modification is NOT permitted.  "
	::= { gponRingEventProfileEntry  7 }

gponRingEventProfileDefaultFileRepetitions  OBJECT-TYPE
	SYNTAX 	INTEGER
	ACCESS	read-write
	STATUS	mandatory
	DESCRIPTION 
		"This attribute specifies the number of times the Ring file (see above) is 
		 repeated.

		 Range is 0..10.

		 Value 0 (default) -  means the Ring file is repeated indefinitely
		 until terminated by some external event (such as a call).

		 Modification is NOT permitted.  "
	::= { gponRingEventProfileEntry  8 }

gponRingEventProfileDefaultTextPointer  OBJECT-TYPE
	SYNTAX 	AsamProfilePointer
	ACCESS	read-write
	STATUS	mandatory
	DESCRIPTION 
		"This attribute points to a row in gponTextMsgProfileTable that contains
		 a text string to be displayed on the CPE device in conjunction with this event.

		 Value 0 (default) is permitted - meaning no text is displayed.
		 In OMCI - this applies to Event 1 (Default) in Ring Event Table attribute
		 of Voice Service Profile ME.

		 Modification is NOT permitted.

		 NOT SUPPORTED  "
	::= { gponRingEventProfileEntry  9 }

gponRingEventProfileSplashRingPointer  OBJECT-TYPE
	SYNTAX 	AsamProfilePointer
	ACCESS	read-write
	STATUS	mandatory
	DESCRIPTION 
		"This attribute points to a row in gponRingSequenceProfileTable

		 Value 0 (default) is permitted - meaning none defined via that profile.
		 In OMCI - this applies to Event 2 (Splash) in Ring Event Table attribute
		 of Voice Service Profile ME.

		 If both this attribute and alternative file pointer attribute (below) are non-zero,
		 then this attribute overrides.

		 Modification is NOT permitted.  "
	::= { gponRingEventProfileEntry  10 }

gponRingEventProfileSplashFilePointer  OBJECT-TYPE
	SYNTAX 	AsamProfilePointer
	ACCESS	read-write
	STATUS	mandatory
	DESCRIPTION 
		"This attribute points to a row in gponUriProfileTable that contains
		 path and name of a file (recognizable by ONT) containing a codec sequence
		 to be played out.  If no file is found in ONT, then no Ring is played.

		 Value 0 (default) is permitted - meaning none defined for this event.
		 In OMCI - this applies to Event 2 (Splash) in Ring Event Table attribute
		 of Voice Service Profile ME.

		 Modification is NOT permitted.  "
	::= { gponRingEventProfileEntry  11 }

gponRingEventProfileSplashFileRepetitions  OBJECT-TYPE
	SYNTAX 	INTEGER
	ACCESS	read-write
	STATUS	mandatory
	DESCRIPTION 
		"This attribute specifies the number of times the Ring file (see above) is 
		 repeated.

		 Range is 0..10.

		 Value 0 (default) -  means the Ring file is repeated indefinitely
		 until terminated by some external event (such as a call).

		 Modification is NOT permitted.  "
	::= { gponRingEventProfileEntry  12 }

gponRingEventProfileSplashTextPointer  OBJECT-TYPE
	SYNTAX 	AsamProfilePointer
	ACCESS	read-write
	STATUS	mandatory
	DESCRIPTION 
		"This attribute points to a row in gponTextMsgProfileTable that contains
		 a text string to be displayed on the CPE device in conjunction with this event.

		 Value 0 (default) is permitted - meaning no text is displayed.
		 In OMCI - this applies to Event 2 (Splash) in Ring Event Table attribute
		 of Voice Service Profile ME.

		 Modification is NOT permitted.

		 NOT SUPPORTED  "
	::= { gponRingEventProfileEntry  13 }


gponRingEventProfileIndexNext        OBJECT-TYPE
        	SYNTAX          AsamNextProfileIndex
        	ACCESS          read-only
        	STATUS          mandatory
        	DESCRIPTION     
        	"This object contains an appropriate value to be used for 
         		gponRingEventProfileIndex when creating entries in the
         		gponRingEventProfileTable. 
         		The value 0 indicates that no unassigned entries are available. To 
         		obtain the next index value for a new entry, the
        		 manager issues a management protocol retrieval operation to obtain the
         		current value of this object.  After each retrieval, the agent should
        		 modify the value to the next unassigned index. "
::= {gponProfilesGroup 62 }


  gponRingEventProfileMaxIndex        OBJECT-TYPE
      	SYNTAX            AsamMaxProfileIndex
      	ACCESS            read-only
     	 STATUS            mandatory
      	DESCRIPTION
            	"This object represents the maximum number of
            		 gponRingEventProfiles that can be created. The object
             		 gponRingEventProfileIndexNext will have values ranging
            		 from 0 to the value represented by this object. 
		 For ISAM4.2,  initially set to 5. "
::= {gponProfilesGroup 63 }

-- *********************************************
-- GPON RING EVENT PROFILE MAPPING TABLE
--
-- This table was first introduced with ISAM4.2 MIB.
-- It is only SUPPORTED beginning with ISAM4.2.02 release.
--
-- For the gponRingEventProfileTable, this table provides a reverse mapping
-- (i.e. profile name to profile index number).
--
-- The system automatically creates an entry in this Table when a  corresponding entry
-- in gponRingEventProfile is created. 
-- The system automatically deletes an entry in this Table when a  corresponding entry
-- in gponRingEventProfile is deleted.
--
--	For GPON - SUPPORTED as of ISAM4.2.02
--	For XG-PON1 - SUPPORTED as of ISAM4.6.02
--  For NG-PON2 - SUPPORTED as of ISAM5.4.01
--   
--
-- *********************************************

 
gponRingEventProfileMappingTable OBJECT-TYPE
   SYNTAX   SEQUENCE OF GponRingEventProfileMappingEntry
   ACCESS   not-accessible
   STATUS   mandatory
   DESCRIPTION
   "This object contains a table for gponRingEventProfile
name to index mapping"
::= { gponProfilesGroup 64 }
 
gponRingEventProfileMappingEntry OBJECT-TYPE
   SYNTAX   GponRingEventProfileMappingEntry
   ACCESS   not-accessible
   STATUS mandatory
   DESCRIPTION
   " An entry (conceptual row) representing the gponRingEventProfile Name to Index mapping."
   INDEX {gponRingEventProfileMappingName }
   ::= {gponRingEventProfileMappingTable  1}
 
GponRingEventProfileMappingEntry ::=
   SEQUENCE { 
	gponRingEventProfileMappingName     AsamProfileName,
      	gponRingEventProfileMappingIndex      AsamProfileIndex
  }
 
gponRingEventProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponRingEventProfileMappingEntry 1}
 
gponRingEventProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponRingEventProfileMappingEntry 2}

-- *********************************************
-- GPON VOICE SERVICE  PROFILE TABLE
--
-- This table was first introduced with ISAM4.2 MIB.
-- It is only SUPPORTED beginning with ISAM4.2.02 release.
--
-- This table contains information regarding voice service functions
-- (ultimately regarding a specific POTS line).
-- From an OMCI standpoint, it maps primarily to the Voice Service Profile ME.
--
--  Rows are created by the operator.
--
-- NOTE: Profile cannot be deleted if associated with another table.
--
--	For GPON - SUPPORTED as of ISAM4.2.02
--	For XG-PON1 - SUPPORTED as of ISAM4.6.02
--  For NG-PON2 - SUPPORTED as of ISAM5.4.01
-- 
--
-- *********************************************

gponVoiceServiceProfileTable OBJECT-TYPE
	SYNTAX	SEQUENCE OF GponVoiceServiceProfileEntry
	ACCESS	not-accessible
	STATUS	mandatory
	DESCRIPTION
		"This object contains a table for creating and storing
		 voice service parameters..
		These profiles are normally associated with a VoIP Media
		Profile "
::= { gponProfilesGroup 65 }

gponVoiceServiceProfileEntry OBJECT-TYPE
	SYNTAX 	GponVoiceServiceProfileEntry
	ACCESS	not-accessible
	STATUS	mandatory
	DESCRIPTION
		"Rows of this table contain Voice Service Profiles "
	INDEX {gponVoiceServiceProfileIndex }
::= {gponVoiceServiceProfileTable 1}

GponVoiceServiceProfileEntry ::=
	SEQUENCE { 
		gponVoiceServiceProfileIndex		AsamProfileIndex,
		gponVoiceServiceProfileName		AsamProfileName,
		gponVoiceServiceProfileRefCount		AsamProfileRefCount,
		gponVoiceServiceProfileScope		AsamProfileScope,
		gponVoiceServiceProfileRowStatus 		RowStatus,
		gponVoiceServiceProfileAnnounceType	INTEGER,
		gponVoiceServiceProfileJitterTarget		INTEGER,
		gponVoiceServiceProfileJitterBufferMax		INTEGER,
		gponVoiceServiceProfileEchoCancelInd		INTEGER,
		gponVoiceServiceProfilePstnProtocolVariant		INTEGER,
		gponVoiceServiceProfileDtmfDigitLevels		INTEGER,
		gponVoiceServiceProfileDtmfDigitDuration		INTEGER,
		gponVoiceServiceProfileHookFlashMinTime		INTEGER,
		gponVoiceServiceProfileHookFlashMaxTime		INTEGER,
		gponVoiceServiceProfileToneEventPointer		AsamProfilePointer,
		gponVoiceServiceProfileRingEventPointer		AsamProfilePointer,
		gponVoiceServiceProfileNetSpecificExtensionsPointer	AsamProfilePointer
}

gponVoiceServiceProfileIndex OBJECT-TYPE 
	SYNTAX AsamProfileIndex
	ACCESS not-accessible
	STATUS mandatory
	DESCRIPTION
	    "This object is the index to the gponVoiceServiceProfileTable. "
::= { gponVoiceServiceProfileEntry 1}

gponVoiceServiceProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponVoiceServiceProfileEntry 2}

gponVoiceServiceProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponVoiceServiceProfileEntry  3}


gponVoiceServiceProfileScope OBJECT-TYPE
        	SYNTAX          AsamProfileScope
        	ACCESS          read-write
        	STATUS          mandatory
        	DESCRIPTION     
       		 "A  profile can be qualified as having a local scope or a network wide 
         		scope.

		Default = 1 = local scope. "
::= {gponVoiceServiceProfileEntry  4}


gponVoiceServiceProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponVoiceServiceProfileEntry  5}

gponVoiceServiceProfileAnnounceType  OBJECT-TYPE
	SYNTAX 	INTEGER
	ACCESS	read-write
	STATUS	mandatory
	DESCRIPTION 
		"This attribute specifies the treatment when a subscriber goes off-hook,
		  but does not attempt a call.

		  Valid values are:
		  1 = Silence
		  2 = Reorder Tone
		  3 = Fast Busy
		  4 = Voice Announcement
		  255 = Not Applicable (default) - means none specified and ONT can choose its own behavior.

		 Modification is NOT permitted.  "
	::= { gponVoiceServiceProfileEntry  6 }

gponVoiceServiceProfileJitterTarget  OBJECT-TYPE
	SYNTAX 	INTEGER
	ACCESS	read-write
	STATUS	mandatory
	DESCRIPTION 
		"This attribute specifies the target valueof the jitter buffer (in milliseconds).
		  The system tries to maintain the jitter buffer at the target value.

		  Range is 0..65535
		  Value 0 (default) - means ONT can dynamically size the jitter buffer.
		  
		 Modification is NOT permitted.  "
	::= { gponVoiceServiceProfileEntry  7 }

gponVoiceServiceProfileJitterBufferMax  OBJECT-TYPE
	SYNTAX 	INTEGER
	ACCESS	read-write
	STATUS	mandatory
	DESCRIPTION 
		"This attribute specifies the maximum depth of the jitter buffer (in milliseconds).

		  Range is 0..65535
		  Value 0 (default) - means ONT can dynamically size the jitter buffer.
		  
		 Modification is NOT permitted.  "
	::= { gponVoiceServiceProfileEntry  8 }

gponVoiceServiceProfileEchoCancelInd  OBJECT-TYPE
	SYNTAX 	INTEGER
	ACCESS	read-write
	STATUS	mandatory
	DESCRIPTION 
		"This attribute specifies whether echo cancellation is OFF or ON

		 0 = OFF
		 1 = ON (default)
		  
		 Modification is NOT permitted.  "
	::= { gponVoiceServiceProfileEntry  9 }

gponVoiceServiceProfilePstnProtocolVariant  OBJECT-TYPE
	SYNTAX 	INTEGER
	ACCESS	read-write
	STATUS	mandatory
	DESCRIPTION 
		"This attribute specifies which variant of POTS signalling is used on the
		  associated POTS UNIs.  Value is equal to E.164 country code.

		 Valid range is 0 - 999.

		 Value 1 indicates USA.  This value should be used when in MGC mode, with GENB softswitch, and
		 desired behavior is ANSI-303 mode. 
		 Any value other than 1 indicates non-USA - and should be used when in MGC mode, with GENB softswitch,
		 and desired behavior is ETSI-303 mode. 

		 The following are explicit country codes specifically supported by ALU ONTs:
		 1 = USA (territories)/Canada
		 61  = Australia
		 56  = Chile
		 86  = China
		 45  = Denmark
		 33  = France
		 49  = Germany
		 354 = Iceland
		 353 = Ireland
		 82  = Korea
		 965 = Kuwait
		 60  = Malaysis
		 356 = Malta
		 92 = Pakistan
		 48  = Poland
		 351 = Portugal
		 7  = Russia
		 966 = Saudi Arabia
		 65  = Singapore
		 34  = Spain
		 971 = United Arab Emirates
		 44  = United Kingdom
		 
		 Default = 0 - means none specified.
		  
		 Modification is NOT permitted.  "
	::= { gponVoiceServiceProfileEntry  10 }

gponVoiceServiceProfileDtmfDigitLevels  OBJECT-TYPE
	SYNTAX 	INTEGER
	ACCESS	read-write
	STATUS	mandatory
	DESCRIPTION 
		"This attribute specifies the power level of DTMF digits that may be generated
		 by the ONT towards the subscriber set.

		 Value is referred to 1 mW at 0 TLP (dBm0)

		  From this GPON MIB perspective, valid values are -25 dBm to -3 dBm, and special value 0.
		  This is represented by INTEGER range -25 to -3, and the value 0.

		  Value 0 (default) - see below - selects ONT's internal policy.  

		   From an OMCI perspective, the attribute is a 16-bit,  2s complement
	                 integer referred to 1 mW at 0 TLP (dBm0), with resolution 1 dB. The OMCI default
		   value 0x8000 selects the ONTs internal policy.	
		  
		 Modification is NOT permitted.  "
	::= { gponVoiceServiceProfileEntry  11 }

gponVoiceServiceProfileDtmfDigitDuration  OBJECT-TYPE
	SYNTAX 	INTEGER
	ACCESS	read-write
	STATUS	mandatory
	DESCRIPTION 
		"This attribute specifies the duration of DTMF digits that may be generated
		 by the ONT towards the subscriber set (in milliseconds).

		 Range is 0..65535

		 Value 0 (default) - selects ONT's internal policy.  	
		  
		 Modification is NOT permitted.  "
	::= { gponVoiceServiceProfileEntry  12 }

gponVoiceServiceProfileHookFlashMinTime  OBJECT-TYPE
	SYNTAX 	INTEGER
	ACCESS	read-write
	STATUS	mandatory
	DESCRIPTION 
		"This attribute specifies the minimum duration recognized by the ONT
		 as a switchhook flash (in milliseconds).

		 Range is 0..65535

		 Value 0 (default) - selects ONT's internal policy.  	
		  
		 Modification is NOT permitted.  "
	::= { gponVoiceServiceProfileEntry  13 }

gponVoiceServiceProfileHookFlashMaxTime  OBJECT-TYPE
	SYNTAX 	INTEGER
	ACCESS	read-write
	STATUS	mandatory
	DESCRIPTION 
		"This attribute specifies the maximum duration recognized by the ONT
		 as a switchhook flash (in milliseconds).

		 Range is 0..65535

		 Value 0 (default) - selects ONT's internal policy.  	
		  
		 Modification is NOT permitted.  "
	::= { gponVoiceServiceProfileEntry  14 }


gponVoiceServiceProfileToneEventPointer  OBJECT-TYPE
	SYNTAX 	AsamProfilePointer
	ACCESS	read-write
	STATUS	mandatory
	DESCRIPTION 
		"This attribute points to a row in gponToneEventProfileTable - which 
		 associates tone sequences with specific events.

		 Value 0 (default) is permitted - meaning event tones are defined via other means.

		 Modification is NOT permitted.  "
	::= { gponVoiceServiceProfileEntry  15 }

gponVoiceServiceProfileRingEventPointer  OBJECT-TYPE
	SYNTAX 	AsamProfilePointer
	ACCESS	read-write
	STATUS	mandatory
	DESCRIPTION 
		"This attribute points to a row in gponRingEventProfileTable - which 
		 associates ring sequences with specific events.

		 Value 0 (default) is permitted - meaning ring tones are defined via other means.

		 Modification is NOT permitted.  "
	::= { gponVoiceServiceProfileEntry  16 }

gponVoiceServiceProfileNetSpecificExtensionsPointer  OBJECT-TYPE
	SYNTAX 	AsamProfilePointer
	ACCESS	read-write
	STATUS	mandatory
	DESCRIPTION 
		"This attribute points to a row in SecureUriProfileTable - which 
		 contains the fully-qualified path and name of a file containing PSTN network specific 
		 extension parameters.

		 Value 0 (default) is permitted - meaning none specified.

		 Modification is NOT permitted.  "
	::= { gponVoiceServiceProfileEntry  17 }


gponVoiceServiceProfileIndexNext        OBJECT-TYPE
        	SYNTAX          AsamNextProfileIndex
        	ACCESS          read-only
        	STATUS          mandatory
        	DESCRIPTION     
        	"This object contains an appropriate value to be used for 
         		gponVoiceServiceProfileIndex when creating entries in the
         		gponVoiceServiceProfileTable. 
         		The value 0 indicates that no unassigned entries are available. To 
         		obtain the next index value for a new entry, the
        		 manager issues a management protocol retrieval operation to obtain the
         		current value of this object.  After each retrieval, the agent should
        		 modify the value to the next unassigned index. "
::= {gponProfilesGroup 66 }


  gponVoiceServiceProfileMaxIndex        OBJECT-TYPE
      	SYNTAX            AsamMaxProfileIndex
      	ACCESS            read-only
     	 STATUS            mandatory
      	DESCRIPTION
            	"This object represents the maximum number of
            		 gponVoiceServiceProfiles that can be created. The object
             		 gponVoiceServiceProfileIndexNext will have values ranging
            		 from 0 to the value represented by this object. 
		 For ISAM4.2,  initially set to 10. "
::= {gponProfilesGroup 67 }

-- *********************************************
-- GPON VOICE SERVICE PROFILE MAPPING TABLE
--
-- This table was first introduced with ISAM4.2 MIB.
-- It is only SUPPORTED beginning with ISAM4.2.02 release.
--
-- For the gponVoiceServiceProfileTable, this table provides a reverse mapping
-- (i.e. profile name to profile index number).
--
-- The system automatically creates an entry in this Table when a  corresponding entry
-- in gponVoiceServiceProfile is created. 
-- The system automatically deletes an entry in this Table when a  corresponding entry
-- in gponVoiceServiceProfile is deleted.
--
--	For GPON - SUPPORTED as of ISAM4.2.02
--	For XG-PON1 - SUPPORTED as of ISAM4.6.02
--  For NG-PON2 - SUPPORTED as of ISAM5.4.01
--   
--
-- *********************************************

 
gponVoiceServiceProfileMappingTable OBJECT-TYPE
   SYNTAX   SEQUENCE OF GponVoiceServiceProfileMappingEntry
   ACCESS   not-accessible
   STATUS   mandatory
   DESCRIPTION
   "This object contains a table for gponVoiceServiceProfile
name to index mapping"
::= { gponProfilesGroup 68 }
 
gponVoiceServiceProfileMappingEntry OBJECT-TYPE
   SYNTAX   GponVoiceServiceProfileMappingEntry
   ACCESS   not-accessible
   STATUS mandatory
   DESCRIPTION
   " An entry (conceptual row) representing the gponVoiceServiceProfile Name to Index mapping."
   INDEX {gponVoiceServiceProfileMappingName }
   ::= {gponVoiceServiceProfileMappingTable  1}
 
GponVoiceServiceProfileMappingEntry ::=
   SEQUENCE { 
	gponVoiceServiceProfileMappingName     AsamProfileName,
      	gponVoiceServiceProfileMappingIndex      AsamProfileIndex
  }
 
gponVoiceServiceProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponVoiceServiceProfileMappingEntry 1}
 
gponVoiceServiceProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponVoiceServiceProfileMappingEntry 2}


-- *********************************************
-- GPON SIP MESSAGE RESPONSE PROFILE TABLE
--
-- This table was first introduced with ISAM4.2 MIB.
--
-- This table contains information for associating SIP response message codes with
-- desired tones and text.
-- From an OMCI standpoint, it maps primarily to the SIP Response Table attribute
-- of the SIP Agent Config Data ME.
--
--  Rows are created by the operator.
--
-- NOTE: Profile cannot be deleted if associated with another table.
--
-- This entire table is NOT SUPPORTED.
--
--	For GPON - NOT SUPPORTED as of ISAM4.2.02
--	For XG-PON1 - NOT SUPPORTED as of ISAM4.6.02
--  For NG-PON2 - SUPPORTED as of ISAM5.4.01
-- 
--
-- *********************************************

gponSipMsgProfileTable OBJECT-TYPE
	SYNTAX	SEQUENCE OF GponSipMsgProfileEntry
	ACCESS	not-accessible
	STATUS	mandatory
	DESCRIPTION
		"This object contains a table for creating and storing
		 SIP message code tones and text..
		These profiles are normally associated with the gponOntSipConfigTable.

		This entire table is NOT SUPPORTED.   "
::= { gponProfilesGroup 69 }

gponSipMsgProfileEntry OBJECT-TYPE
	SYNTAX 	GponSipMsgProfileEntry
	ACCESS	not-accessible
	STATUS	mandatory
	DESCRIPTION
		"Rows of this table contain SIP Message Code Profiles "
	INDEX {gponSipMsgProfileIndex }
::= {gponSipMsgProfileTable 1}

GponSipMsgProfileEntry ::=
	SEQUENCE { 
		gponSipMsgProfileIndex		AsamProfileIndex,
		gponSipMsgProfileName		AsamProfileName,
		gponSipMsgProfileRefCount		AsamProfileRefCount,
		gponSipMsgProfileScope		AsamProfileScope,
		gponSipMsgProfileRowStatus 		RowStatus,
		gponSipMsgProfileCode1			INTEGER,
		gponSipMsgProfileCode1TonePointer		AsamProfilePointer,
		gponSipMsgProfileCode1TextPointer		AsamProfilePointer,
		gponSipMsgProfileCode2			INTEGER,
		gponSipMsgProfileCode2TonePointer		AsamProfilePointer,
		gponSipMsgProfileCode2TextPointer		AsamProfilePointer,
		gponSipMsgProfileCode3			INTEGER,
		gponSipMsgProfileCode3TonePointer		AsamProfilePointer,
		gponSipMsgProfileCode3TextPointer		AsamProfilePointer,
		gponSipMsgProfileCode4			INTEGER,
		gponSipMsgProfileCode4TonePointer		AsamProfilePointer,
		gponSipMsgProfileCode4TextPointer		AsamProfilePointer,
		gponSipMsgProfileCode5			INTEGER,
		gponSipMsgProfileCode5TonePointer		AsamProfilePointer,
		gponSipMsgProfileCode5TextPointer		AsamProfilePointer
}

gponSipMsgProfileIndex OBJECT-TYPE 
	SYNTAX AsamProfileIndex
	ACCESS not-accessible
	STATUS mandatory
	DESCRIPTION
	    "This object is the index to the gponSipMsgProfileTable. "
::= { gponSipMsgProfileEntry 1}

gponSipMsgProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponSipMsgProfileEntry 2}

gponSipMsgProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponSipMsgProfileEntry  3}


gponSipMsgProfileScope OBJECT-TYPE
        	SYNTAX          AsamProfileScope
        	ACCESS          read-write
        	STATUS          mandatory
        	DESCRIPTION     
       		 "A  profile can be qualified as having a local scope or a network wide 
         		scope.

		Default = 1 = local scope. "
::= {gponSipMsgProfileEntry  4}


gponSipMsgProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponSipMsgProfileEntry  5}

gponSipMsgProfileCode1  OBJECT-TYPE
	SYNTAX 	INTEGER
	ACCESS	read-write
	STATUS	mandatory
	DESCRIPTION 
		"This attribute specifies the code value for a SIP message (normally 4xx,
		  5xx, and 6xx message codes. 

		 Range is 400..699.

		 The same SIP code cannot be used more than once in same profile.

		 No default - must be supplied by manager.

		 Modification is NOT permitted.  "
	::= { gponSipMsgProfileEntry  6 }

gponSipMsgProfileCode1TonePointer  OBJECT-TYPE
	SYNTAX 	AsamProfilePointer
	ACCESS	read-write
	STATUS	mandatory
	DESCRIPTION 
		"This attribute points to a row in gponToneSequenceProfileTable

		 Value 0 (default) is permitted - meaning no tone associated for this SIP code.

		 Modification is NOT permitted.  "
	::= { gponSipMsgProfileEntry  7 }

gponSipMsgProfileCode1TextPointer  OBJECT-TYPE
	SYNTAX 	AsamProfilePointer
	ACCESS	read-write
	STATUS	mandatory
	DESCRIPTION 
		"This attribute points to a row in gponTextMsgProfileTable that contains
		 a text string to be displayed to the subscriber for this SIP code.

		 Value 0 (default) is permitted - meaning none defined for this SIP code.

		 Modification is NOT permitted.  "
	::= { gponSipMsgProfileEntry  8 }

gponSipMsgProfileCode2  OBJECT-TYPE
	SYNTAX 	INTEGER
	ACCESS	read-write
	STATUS	mandatory
	DESCRIPTION 
		"This attribute specifies the code value for a SIP message (normally 4xx,
		  5xx, and 6xx message codes. 

		 Range is 400..699.

		 The same SIP code cannot be used more than once in same profile.

		 No default - must be supplied by manager.

		 Modification is NOT permitted.  "
	::= { gponSipMsgProfileEntry  9 }

gponSipMsgProfileCode2TonePointer  OBJECT-TYPE
	SYNTAX 	AsamProfilePointer
	ACCESS	read-write
	STATUS	mandatory
	DESCRIPTION 
		"This attribute points to a row in gponToneSequenceProfileTable

		 Value 0 (default) is permitted - meaning no tone associated for this SIP code.

		 Modification is NOT permitted.  "
	::= { gponSipMsgProfileEntry  10 }

gponSipMsgProfileCode2TextPointer  OBJECT-TYPE
	SYNTAX 	AsamProfilePointer
	ACCESS	read-write
	STATUS	mandatory
	DESCRIPTION 
		"This attribute points to a row in gponTextMsgProfileTable that contains
		 a text string to be displayed to the subscriber for this SIP code.

		 Value 0 (default) is permitted - meaning none defined for this SIP code.

		 Modification is NOT permitted.  "
	::= { gponSipMsgProfileEntry  11 }

gponSipMsgProfileCode3  OBJECT-TYPE
	SYNTAX 	INTEGER
	ACCESS	read-write
	STATUS	mandatory
	DESCRIPTION 
		"This attribute specifies the code value for a SIP message (normally 4xx,
		  5xx, and 6xx message codes. 

		 Range is 400..699.

		 The same SIP code cannot be used more than once in same profile.

		 No default - must be supplied by manager.

		 Modification is NOT permitted.  "
	::= { gponSipMsgProfileEntry  12 }

gponSipMsgProfileCode3TonePointer  OBJECT-TYPE
	SYNTAX 	AsamProfilePointer
	ACCESS	read-write
	STATUS	mandatory
	DESCRIPTION 
		"This attribute points to a row in gponToneSequenceProfileTable

		 Value 0 (default) is permitted - meaning no tone associated for this SIP code.

		 Modification is NOT permitted.  "
	::= { gponSipMsgProfileEntry  13 }

gponSipMsgProfileCode3TextPointer  OBJECT-TYPE
	SYNTAX 	AsamProfilePointer
	ACCESS	read-write
	STATUS	mandatory
	DESCRIPTION 
		"This attribute points to a row in gponTextMsgProfileTable that contains
		 a text string to be displayed to the subscriber for this SIP code.

		 Value 0 (default) is permitted - meaning none defined for this SIP code.

		 Modification is NOT permitted.  "
	::= { gponSipMsgProfileEntry  14 }

gponSipMsgProfileCode4  OBJECT-TYPE
	SYNTAX 	INTEGER
	ACCESS	read-write
	STATUS	mandatory
	DESCRIPTION 
		"This attribute specifies the code value for a SIP message (normally 4xx,
		  5xx, and 6xx message codes. 

		 Range is 400..699.

		 The same SIP code cannot be used more than once in same profile.

		 No default - must be supplied by manager.

		 Modification is NOT permitted.  "
	::= { gponSipMsgProfileEntry  15 }

gponSipMsgProfileCode4TonePointer  OBJECT-TYPE
	SYNTAX 	AsamProfilePointer
	ACCESS	read-write
	STATUS	mandatory
	DESCRIPTION 
		"This attribute points to a row in gponToneSequenceProfileTable

		 Value 0 (default) is permitted - meaning no tone associated for this SIP code.

		 Modification is NOT permitted.  "
	::= { gponSipMsgProfileEntry  16 }

gponSipMsgProfileCode4TextPointer  OBJECT-TYPE
	SYNTAX 	AsamProfilePointer
	ACCESS	read-write
	STATUS	mandatory
	DESCRIPTION 
		"This attribute points to a row in gponTextMsgProfileTable that contains
		 a text string to be displayed to the subscriber for this SIP code.

		 Value 0 (default) is permitted - meaning none defined for this SIP code.

		 Modification is NOT permitted.  "
	::= { gponSipMsgProfileEntry  17 }

gponSipMsgProfileCode5  OBJECT-TYPE
	SYNTAX 	INTEGER
	ACCESS	read-write
	STATUS	mandatory
	DESCRIPTION 
		"This attribute specifies the code value for a SIP message (normally 4xx,
		  5xx, and 6xx message codes. 

		 Range is 400..699.

		 The same SIP code cannot be used more than once in same profile.

		 No default - must be supplied by manager.

		 Modification is NOT permitted.  "
	::= { gponSipMsgProfileEntry  18 }

gponSipMsgProfileCode5TonePointer  OBJECT-TYPE
	SYNTAX 	AsamProfilePointer
	ACCESS	read-write
	STATUS	mandatory
	DESCRIPTION 
		"This attribute points to a row in gponToneSequenceProfileTable

		 Value 0 (default) is permitted - meaning no tone associated for this SIP code.

		 Modification is NOT permitted.  "
	::= { gponSipMsgProfileEntry  19 }

gponSipMsgProfileCode5TextPointer  OBJECT-TYPE
	SYNTAX 	AsamProfilePointer
	ACCESS	read-write
	STATUS	mandatory
	DESCRIPTION 
		"This attribute points to a row in gponTextMsgProfileTable that contains
		 a text string to be displayed to the subscriber for this SIP code.

		 Value 0 (default) is permitted - meaning none defined for this SIP code.

		 Modification is NOT permitted.  "
	::= { gponSipMsgProfileEntry  20 }


gponSipMsgProfileIndexNext        OBJECT-TYPE
        	SYNTAX          AsamNextProfileIndex
        	ACCESS          read-only
        	STATUS          mandatory
        	DESCRIPTION     
        	"This object contains an appropriate value to be used for 
         		gponSipMsgProfileIndex when creating entries in the
         		gponSipMsgProfileTable. 
         		The value 0 indicates that no unassigned entries are available. To 
         		obtain the next index value for a new entry, the
        		 manager issues a management protocol retrieval operation to obtain the
         		current value of this object.  After each retrieval, the agent should
        		 modify the value to the next unassigned index.

		NOT SUPPORTED "
::= {gponProfilesGroup 70 }


  gponSipMsgProfileMaxIndex        OBJECT-TYPE
      	SYNTAX            AsamMaxProfileIndex
      	ACCESS            read-only
     	 STATUS            mandatory
      	DESCRIPTION
            	"This object represents the maximum number of
            		 gponSipMsgProfiles that can be created. The object
             		 gponSipMsgProfileIndexNext will have values ranging
            		 from 0 to the value represented by this object. 
		 For ISAM4.2,  initially set to 20.

		NOT SUPPORTED "
::= {gponProfilesGroup 71 }

-- *********************************************
-- GPON SIP MESSAGE PROFILE MAPPING TABLE
--
-- This table was first introduced with ISAM4.2 MIB.
--
-- For the gponSipMsgProfileTable, this table provides a reverse mapping
-- (i.e. profile name to profile index number).
--
-- The system automatically creates an entry in this Table when a  corresponding entry
-- in gponSipMsgProfile is created. 
-- The system automatically deletes an entry in this Table when a  corresponding entry
-- in gponSipMsgProfile is deleted. 
--
--  This entire table is NOT SUPPORTED.
--
--	For GPON - NOT SUPPORTED as of ISAM4.2.02
--	For XG-PON1 - NOT SUPPORTED as of ISAM4.6.02
--  For NG-PON2 - SUPPORTED as of ISAM5.4.01
--  
--
-- *********************************************

 
gponSipMsgProfileMappingTable OBJECT-TYPE
   SYNTAX   SEQUENCE OF GponSipMsgProfileMappingEntry
   ACCESS   not-accessible
   STATUS   mandatory
   DESCRIPTION
   "This object contains a table for gponSipMsgProfile
name to index mapping"
::= { gponProfilesGroup 72 }
 
gponSipMsgProfileMappingEntry OBJECT-TYPE
   SYNTAX   GponSipMsgProfileMappingEntry
   ACCESS   not-accessible
   STATUS mandatory
   DESCRIPTION
   " An entry (conceptual row) representing the gponSipMsgProfile Name to Index mapping."
   INDEX {gponSipMsgProfileMappingName }
   ::= {gponSipMsgProfileMappingTable  1}
 
GponSipMsgProfileMappingEntry ::=
   SEQUENCE { 
	gponSipMsgProfileMappingName     AsamProfileName,
      	gponSipMsgProfileMappingIndex      AsamProfileIndex
  }
 
gponSipMsgProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponSipMsgProfileMappingEntry 1}
 
gponSipMsgProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponSipMsgProfileMappingEntry 2}

-- *********************************************
-- GPON NETWORK DIAL PLAN  PROFILE TABLE
--
-- This table was first introduced with ISAM4.2 MIB.
-- It is only SUPPORTED beginning with ISAM4.2.02 release.
--
-- This table contains information regarding network dial plans (i.e. digit maps)
-- (ultimately regarding a specific POTS line - when used with SIP).
-- From an OMCI standpoint, it maps primarily to the Network Dial Plan Table ME.

--  Rows are created by the operator.
--
-- NOTE: Profile cannot be deleted if associated with another table.
--
--	For GPON - SUPPORTED as of ISAM4.2.02
--	For XG-PON1 - SUPPORTED as of ISAM4.6.02
--  For NG-PON2 - SUPPORTED as of ISAM5.4.01
-- 
--
-- *********************************************

gponNetDialPlanProfileTable OBJECT-TYPE
	SYNTAX	SEQUENCE OF GponNetDialPlanProfileEntry
	ACCESS	not-accessible
	STATUS	mandatory
	DESCRIPTION
		"This object contains a table for creating and storing
		 network dial plan parameters.
		These profiles are normally associated with a POTS line - for SIP. "
::= { gponProfilesGroup 73 }

gponNetDialPlanProfileEntry OBJECT-TYPE
	SYNTAX 	GponNetDialPlanProfileEntry
	ACCESS	not-accessible
	STATUS	mandatory
	DESCRIPTION
		"Rows of this table contain Network Dial Plan Profiles "
	INDEX {gponNetDialPlanProfileIndex }
::= {gponNetDialPlanProfileTable 1}

GponNetDialPlanProfileEntry ::=
	SEQUENCE { 
		gponNetDialPlanProfileIndex		AsamProfileIndex,
		gponNetDialPlanProfileName		AsamProfileName,
		gponNetDialPlanProfileRefCount		AsamProfileRefCount,
		gponNetDialPlanProfileScope		AsamProfileScope,
		gponNetDialPlanProfileRowStatus 		RowStatus,
		gponNetDialPlanProfileCriticalDialTimeout	INTEGER,
		gponNetDialPlanProfilePartialDialTimeout	INTEGER,
		gponNetDialPlanProfileFormat		INTEGER,
		gponNetDialPlanProfileDigitMapPart1		DisplayString,
		gponNetDialPlanProfileDigitMapPart2		DisplayString,
		gponNetDialPlanProfileDigitMapPart3		DisplayString,
		gponNetDialPlanProfileDigitMapPart4		DisplayString
}

gponNetDialPlanProfileIndex OBJECT-TYPE 
	SYNTAX AsamProfileIndex
	ACCESS not-accessible
	STATUS mandatory
	DESCRIPTION
	    "This object is the index to the gponNetDialPlanProfileTable. "
::= { gponNetDialPlanProfileEntry 1}

gponNetDialPlanProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponNetDialPlanProfileEntry 2}

gponNetDialPlanProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponNetDialPlanProfileEntry  3}


gponNetDialPlanProfileScope OBJECT-TYPE
        	SYNTAX          AsamProfileScope
        	ACCESS          read-write
        	STATUS          mandatory
        	DESCRIPTION     
       		 "A  profile can be qualified as having a local scope or a network wide 
         		scope.

		Default = 1 = local scope. "
::= {gponNetDialPlanProfileEntry  4}


gponNetDialPlanProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponNetDialPlanProfileEntry  5}

gponNetDialPlanProfileCriticalDialTimeout  OBJECT-TYPE
	SYNTAX 	INTEGER
	ACCESS	read-write
	STATUS	mandatory
	DESCRIPTION 
		"This attribute specifies the critical dial timeout for digit map
		  processing (in milliseconds).

		 Range is 1000 (1 second) TO 40,000 (40 seconds).
		 OLT should only accept input on 1000 millisecond (i.e. 1 second) boundaries.		

		 Default = 4000 (4 seconds).

		 Modification is NOT permitted.  "
	::= { gponNetDialPlanProfileEntry  6 }

gponNetDialPlanProfilePartialDialTimeout  OBJECT-TYPE
	SYNTAX 	INTEGER
	ACCESS	read-write
	STATUS	mandatory
	DESCRIPTION 
		"This attribute specifies the partial dial timeout for digit map
		  processing (in milliseconds).

		 Range is 1000 (1 second) TO 40,000 (40 seconds).
		 OLT should only accept input on 1000 millisecond (i.e. 1 second) boundaries.	

		 Default = 16,000 (16 seconds).

		 Modification is NOT permitted.  "
	::= { gponNetDialPlanProfileEntry  7 }

gponNetDialPlanProfileFormat  OBJECT-TYPE
	SYNTAX 	INTEGER
	ACCESS	read-write
	STATUS	mandatory
	DESCRIPTION 
		"This attribute specifies the dial plan format that should be used.

		 0 = Not Defined
		 1 = H248 Format (using dial plan tokens - see below) - Default
		 2 = NSC Format

		 Modification is NOT permitted.  "
	::= { gponNetDialPlanProfileEntry  8 }

gponNetDialPlanProfileDigitMapPart1  OBJECT-TYPE
	SYNTAX 	DisplayString
	ACCESS	read-write
	STATUS	mandatory
	DESCRIPTION 
		"This attribute specifies Part 1 of the actual digit map ASCII symbols.
		  The symbol ' | ' should be used as the delimiter between the tokens.

		 Maximum string size is 256 characters - null terminated.
		 DigitMap Parts 1 through 4 should be considered as a continuous concatenated string
		 (with the first null terminator considered as the end of the concatenated string).

		 Modification is NOT permitted.  "
	::= { gponNetDialPlanProfileEntry  9 }

gponNetDialPlanProfileDigitMapPart2  OBJECT-TYPE
	SYNTAX 	DisplayString
	ACCESS	read-write
	STATUS	mandatory
	DESCRIPTION 
		"This attribute specifies Part 2 of the actual digit map ASCII symbols.
		  The symbol ' | ' should be used as the delimiter between the tokens.

		 Maximum string size is 256 characters - null terminated.
		 DigitMap Parts 1 through 4 should be considered as a continuous concatenated string
		 (with the first null terminator considered as the end of the concatenated string).

		 Modification is NOT permitted.  "
	::= { gponNetDialPlanProfileEntry  10 }

gponNetDialPlanProfileDigitMapPart3  OBJECT-TYPE
	SYNTAX 	DisplayString
	ACCESS	read-write
	STATUS	mandatory
	DESCRIPTION 
		"This attribute specifies Part 3 of the actual digit map ASCII symbols.
		  The symbol ' | ' should be used as the delimiter between the tokens.

		 Maximum string size is 256 characters - null terminated.
		 DigitMap Parts 1 through 4 should be considered as a continuous concatenated string
		 (with the first null terminator considered as the end of the concatenated string).

		 Modification is NOT permitted.  "
	::= { gponNetDialPlanProfileEntry  11 }

gponNetDialPlanProfileDigitMapPart4  OBJECT-TYPE
	SYNTAX 	DisplayString
	ACCESS	read-write
	STATUS	mandatory
	DESCRIPTION 
		"This attribute specifies Part 4 of the actual digit map ASCII symbols.
		  The symbol ' | ' should be used as the delimiter between the tokens.

		 Maximum string size is 256 characters - null terminated.
		 DigitMap Parts 1 through 4 should be considered as a continuous concatenated string
		 (with the first null terminator considered as the end of the concatenated string).

		 Modification is NOT permitted.  "
	::= { gponNetDialPlanProfileEntry  12 }


gponNetDialPlanProfileIndexNext        OBJECT-TYPE
        	SYNTAX          AsamNextProfileIndex
        	ACCESS          read-only
        	STATUS          mandatory
        	DESCRIPTION     
        	"This object contains an appropriate value to be used for 
         		gponNetDialPlanProfileIndex when creating entries in the
         		gponNetDialPlanProfileTable. 
         		The value 0 indicates that no unassigned entries are available. To 
         		obtain the next index value for a new entry, the
        		 manager issues a management protocol retrieval operation to obtain the
         		current value of this object.  After each retrieval, the agent should
        		 modify the value to the next unassigned index. "
::= {gponProfilesGroup 74 }


  gponNetDialPlanProfileMaxIndex        OBJECT-TYPE
      	SYNTAX            AsamMaxProfileIndex
      	ACCESS            read-only
     	 STATUS            mandatory
      	DESCRIPTION
            	"This object represents the maximum number of
            		 gponNetDialPlanProfiles that can be created. The object
             		 gponNetDialPlanProfileIndexNext will have values ranging
            		 from 0 to the value represented by this object. 
		 For ISAM4.2,  initially set to 20. "
::= {gponProfilesGroup 75 }

-- *********************************************
-- GPON NETWORK DIAL PLAN PROFILE MAPPING TABLE
--
-- This table was first introduced with ISAM4.2 MIB.
-- It is only SUPPORTED beginning with ISAM4.2.02 release.
--
-- For the gponNetDialPlanProfileTable, this table provides a reverse mapping
-- (i.e. profile name to profile index number).
--
-- The system automatically creates an entry in this Table when a  corresponding entry
-- in gponNetDialPlanProfile is created. 
-- The system automatically deletes an entry in this Table when a  corresponding entry
-- in gponNetDialPlanProfile is deleted.
--
--	For GPON - SUPPORTED as of ISAM4.2.02
--	For XG-PON1 - SUPPORTED as of ISAM4.6.02
--  For NG-PON2 - SUPPORTED as of ISAM5.4.01
--   
--
-- *********************************************

 
gponNetDialPlanProfileMappingTable OBJECT-TYPE
   SYNTAX   SEQUENCE OF GponNetDialPlanProfileMappingEntry
   ACCESS   not-accessible
   STATUS   mandatory
   DESCRIPTION
   "This object contains a table for gponNetDialPlanProfile
name to index mapping"
::= { gponProfilesGroup 76 }
 
gponNetDialPlanProfileMappingEntry OBJECT-TYPE
   SYNTAX   GponNetDialPlanProfileMappingEntry
   ACCESS   not-accessible
   STATUS mandatory
   DESCRIPTION
   " An entry (conceptual row) representing the gponNetDialPlanProfile Name to Index mapping."
   INDEX {gponNetDialPlanProfileMappingName }
   ::= {gponNetDialPlanProfileMappingTable  1}
 
GponNetDialPlanProfileMappingEntry ::=
   SEQUENCE { 
	gponNetDialPlanProfileMappingName     AsamProfileName,
      	gponNetDialPlanProfileMappingIndex      AsamProfileIndex
  }
 
gponNetDialPlanProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponNetDialPlanProfileMappingEntry 1}
 
gponNetDialPlanProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponNetDialPlanProfileMappingEntry 2}

-- *********************************************
-- GPON VOIP APPLICATION SERVICE  PROFILE TABLE
--
-- This table was first introduced with ISAM4.2 MIB.
-- It is only SUPPORTED beginning with ISAM4.2.02 release.
--
-- This table contains information regarding calling features used in conjunction
-- with a VoIP line service (ultimately regarding a specific POTS line - when used with SIP).
-- From an OMCI standpoint, it maps primarily to the VoIP Application Service Profile ME.
--
--  Rows are created by the operator.
--
-- NOTE: Profile cannot be deleted if associated with another table.
--
--	For GPON - SUPPORTED as of ISAM4.2.02
--	For XG-PON1 - SUPPORTED as of ISAM4.6.02
--  For NG-PON2 - SUPPORTED as of ISAM5.4.01
-- 
--
-- *********************************************

gponVoipAppServProfileTable OBJECT-TYPE
	SYNTAX	SEQUENCE OF GponVoipAppServProfileEntry
	ACCESS	not-accessible
	STATUS	mandatory
	DESCRIPTION
		"This object contains a table for creating and storing
		 VoIP application service parameters.
		These profiles are normally associated with a POTS line - for SIP. "
::= { gponProfilesGroup 77 }

gponVoipAppServProfileEntry OBJECT-TYPE
	SYNTAX 	GponVoipAppServProfileEntry
	ACCESS	not-accessible
	STATUS	mandatory
	DESCRIPTION
		"Rows of this table contain VoIP Application Service Profiles "
	INDEX {gponVoipAppServProfileIndex }
::= {gponVoipAppServProfileTable 1}

GponVoipAppServProfileEntry ::=
	SEQUENCE { 
		gponVoipAppServProfileIndex		AsamProfileIndex,
		gponVoipAppServProfileName		AsamProfileName,
		gponVoipAppServProfileRefCount		AsamProfileRefCount,
		gponVoipAppServProfileScope		AsamProfileScope,
		gponVoipAppServProfileRowStatus 		RowStatus,
		gponVoipAppServProfileCidFeatures		OCTET STRING,
		gponVoipAppServProfileCallWaitFeatures	OCTET STRING,
		gponVoipAppServProfileCallProgTranFeatures	OCTET STRING,
		gponVoipAppServProfileCallPresentFeatures	OCTET STRING,
		gponVoipAppServProfileDirectConnectFeatures	OCTET STRING,
		gponVoipAppServProfileDirectConnectUri	AsamProfilePointer,
		gponVoipAppServProfileBridgedLineAgentUri	AsamProfilePointer,
		gponVoipAppServProfileConfFactoryUri	AsamProfilePointer
}

gponVoipAppServProfileIndex OBJECT-TYPE 
	SYNTAX AsamProfileIndex
	ACCESS not-accessible
	STATUS mandatory
	DESCRIPTION
	    "This object is the index to the gponVoipAppServProfileTable. "
::= { gponVoipAppServProfileEntry 1}

gponVoipAppServProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponVoipAppServProfileEntry 2}

gponVoipAppServProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponVoipAppServProfileEntry  3}


gponVoipAppServProfileScope OBJECT-TYPE
        	SYNTAX          AsamProfileScope
        	ACCESS          read-write
        	STATUS          mandatory
        	DESCRIPTION     
       		 "A  profile can be qualified as having a local scope or a network wide 
         		scope.

		Default = 1 = local scope. "
::= {gponVoipAppServProfileEntry  4}


gponVoipAppServProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponVoipAppServProfileEntry  5}

gponVoipAppServProfileCidFeatures  OBJECT-TYPE
	SYNTAX 	OCTET STRING (SIZE(1))
	ACCESS	read-write
	STATUS	mandatory
	DESCRIPTION 
		"This attribute contains a bitmap of Caller ID features.  Except as noted,
		 value 0 = Disable and value 1 = Enable.

		 Interpret as follows:  Bit 1 = LSB and Bit 8 = MSB.

		 Bit 1 - Calling Number
		 Bit 2 - Calling Name
		 Bit 3 - CID Block (both Name and Number)
		 Bit 4 - CID Number - Permanent presentation status for number
			0 = public, 1 = private)
		 Bit 5 - CID Name - Permanent presentation status for name
			0 = public, 1 = private)
		 Bit 6 - Anonymous CID blocking (ACR) - may not be possible in ONT.
		 Bits 7 - 8 - Not used

		 Default = all zeroes.

		 Modification is NOT permitted.  "
	::= { gponVoipAppServProfileEntry  6 }

gponVoipAppServProfileCallWaitFeatures  OBJECT-TYPE
	SYNTAX 	OCTET STRING (SIZE(1))
	ACCESS	read-write
	STATUS	mandatory
	DESCRIPTION 
		"This attribute contains a bitmap of Call Waiting features.  Except as noted,
		 value 0 = Disable and value 1 = Enable.

		 Interpret as follows:  Bit 1 = LSB and Bit 8 = MSB.

		 Bit 1 - Call waiting
		 Bit 2 - Caller ID announcement
		 Bits 3 - 8 - Not used

		 Default = all zeroes.

		 Modification is NOT permitted.  "
	::= { gponVoipAppServProfileEntry  7 }

gponVoipAppServProfileCallProgTranFeatures  OBJECT-TYPE
	SYNTAX 	OCTET STRING (SIZE(2))
	ACCESS	read-write
	STATUS	mandatory
	DESCRIPTION 
		"This attribute contains a bitmap of Call Processing features.  Except as noted,
		 value 0 = Disable and value 1 = Enable.

		 Interpret as follows:  Bit 1 = LSB and Bit 16 = MSB.

		 Bit 1 - 3way
		 Bit 2 - Call transfer
		 Bit 3 - Call hold
		 Bit 4 - Call park
		 Bit 5 - Do not disturb
		 Bit 6 - Flash on emergency call 
			(flash is to be processed during an emergencyservice call).
		 Bit 7 - Emergency service originating hold 
			(determines whether call clearing is to be performed on on-hook
			 during an emergency service call).
		 Bit 8 - 6way
		 Bits 9 - 16 - Not used

		 Default = all zeroes.

		 Modification is NOT permitted.  "
	::= { gponVoipAppServProfileEntry  8 }

gponVoipAppServProfileCallPresentFeatures  OBJECT-TYPE
	SYNTAX 	OCTET STRING (SIZE(2))
	ACCESS	read-write
	STATUS	mandatory
	DESCRIPTION 
		"This attribute contains a bitmap of Call Presentation features.  Except as noted,
		 value 0 = Disable and value 1 = Enable.

		 Interpret as follows:  Bit 1 = LSB and Bit 16 = MSB.

		 Bit 1 - Message waiting indication splash ring
		 Bit 2 - Message waiting indication special dial tone
		 Bit 3 - Message waiting indication visual indication
		 Bit 4 - Call forwarding indication
		 Bits 5 - 16 - Not used

		 Default = all zeroes.

		 Modification is NOT permitted.  "
	::= { gponVoipAppServProfileEntry  9 }

gponVoipAppServProfileDirectConnectFeatures  OBJECT-TYPE
	SYNTAX 	OCTET STRING (SIZE(1))
	ACCESS	read-write
	STATUS	mandatory
	DESCRIPTION 
		"This attribute contains a bitmap of characteristics associated with direct
		  connect features.  Except as noted, value 0 = Disable and value 1 = Enable.

		 Interpret as follows:  Bit 1 = LSB and Bit 8 = MSB.

		 Bit 1 - Direct connect feature enabled
		 Bit 2 - Dial tone feature delay option
		 Bits 3 - 8 - Not used

		 Default = all zeroes.

		 Modification is NOT permitted.  "
	::= { gponVoipAppServProfileEntry  10 }

gponVoipAppServProfileDirectConnectUri  OBJECT-TYPE
	SYNTAX 	AsamProfilePointer
	ACCESS	read-write
	STATUS	mandatory
	DESCRIPTION 
		"This attribute points to a row in gponSecureUriProfileTable
		 the specifies the URI of the direct connect.

		 Value 0 (default) - i.e. null pointer means none specified.

		 Modification is NOT permitted.  "
	::= { gponVoipAppServProfileEntry  11 }

gponVoipAppServProfileBridgedLineAgentUri  OBJECT-TYPE
	SYNTAX 	AsamProfilePointer
	ACCESS	read-write
	STATUS	mandatory
	DESCRIPTION 
		"This attribute points to a row in gponSecureUriProfileTable
		 the specifies the URI of the bridged line agent.

		 Value 0 (default) - i.e. null pointer means none specified.

		 Modification is NOT permitted.  "
	::= { gponVoipAppServProfileEntry  12 }

gponVoipAppServProfileConfFactoryUri  OBJECT-TYPE
	SYNTAX 	AsamProfilePointer
	ACCESS	read-write
	STATUS	mandatory
	DESCRIPTION 
		"This attribute points to a row in gponSecureUriProfileTable
		 the specifies the URI of the conference factory.

		 Value 0 (default) - i.e. null pointer means none specified.

		 Modification is NOT permitted.  "
	::= { gponVoipAppServProfileEntry  13 }


gponVoipAppServProfileIndexNext        OBJECT-TYPE
        	SYNTAX          AsamNextProfileIndex
        	ACCESS          read-only
        	STATUS          mandatory
        	DESCRIPTION     
        	"This object contains an appropriate value to be used for 
         		gponVoipAppServProfileIndex when creating entries in the
         		gponVoipAppServProfileTable. 
         		The value 0 indicates that no unassigned entries are available. To 
         		obtain the next index value for a new entry, the
        		 manager issues a management protocol retrieval operation to obtain the
         		current value of this object.  After each retrieval, the agent should
        		 modify the value to the next unassigned index. "
::= {gponProfilesGroup 78 }


  gponVoipAppServProfileMaxIndex        OBJECT-TYPE
      	SYNTAX            AsamMaxProfileIndex
      	ACCESS            read-only
     	 STATUS            mandatory
      	DESCRIPTION
            	"This object represents the maximum number of
            		 gponVoipAppServProfiles that can be created. The object
             		 gponVoipAppServProfileIndexNext will have values ranging
            		 from 0 to the value represented by this object. 
		 For ISAM4.2,  initially set to 20. "
::= {gponProfilesGroup 79 }

-- *********************************************
-- GPON VOIP APPLICATION SERVICE PROFILE MAPPING TABLE
--
-- This table was first introduced with ISAM4.2 MIB.
-- It is only SUPPORTED beginning with ISAM4.2.02 release.
--
-- For the gponVoipAppServProfileTable, this table provides a reverse mapping
-- (i.e. profile name to profile index number).
--
-- The system automatically creates an entry in this Table when a  corresponding entry
-- in gponVoipAppServProfile is created. 
-- The system automatically deletes an entry in this Table when a  corresponding entry
-- in gponVoipAppServProfile is deleted.
--
--	For GPON - SUPPORTED as of ISAM4.2.02
--	For XG-PON1 - SUPPORTED as of ISAM4.6.02
--  For NG-PON2 - SUPPORTED as of ISAM5.4.01
--   
--
-- *********************************************

 
gponVoipAppServProfileMappingTable OBJECT-TYPE
   SYNTAX   SEQUENCE OF GponVoipAppServProfileMappingEntry
   ACCESS   not-accessible
   STATUS   mandatory
   DESCRIPTION
   "This object contains a table for gponVoipAppServProfile
name to index mapping"
::= { gponProfilesGroup 80 }
 
gponVoipAppServProfileMappingEntry OBJECT-TYPE
   SYNTAX   GponVoipAppServProfileMappingEntry
   ACCESS   not-accessible
   STATUS mandatory
   DESCRIPTION
   " An entry (conceptual row) representing the gponVoipAppServProfile Name to Index mapping."
   INDEX {gponVoipAppServProfileMappingName }
   ::= {gponVoipAppServProfileMappingTable  1}
 
GponVoipAppServProfileMappingEntry ::=
   SEQUENCE { 
	gponVoipAppServProfileMappingName     AsamProfileName,
      	gponVoipAppServProfileMappingIndex      AsamProfileIndex
  }
 
gponVoipAppServProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponVoipAppServProfileMappingEntry 1}
 
gponVoipAppServProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponVoipAppServProfileMappingEntry 2}

-- *********************************************
-- GPON VOIP FEATURE ACCESS CODES PROFILE TABLE
--
-- This table was first introduced with ISAM4.2 MIB.
-- It is only SUPPORTED beginning with ISAM4.2.02 release.
--
-- This table contains information regarding administrative feature access codes used in conjunction
-- with a VoIP line service (ultimately regarding a specific POTS line - when used with SIP).
-- From an OMCI standpoint, it maps primarily to the VoIp Feature Access Codes ME.
--
--  Rows are created by the operator.
--
-- NOTE: Profile cannot be deleted if associated with another table.
--
--	For GPON - SUPPORTED as of ISAM4.2.02
--	For XG-PON1 - SUPPORTED as of ISAM4.6.02
--  For NG-PON2 - SUPPORTED as of ISAM5.4.01
-- 
--
-- *********************************************

gponVoipFeatAccessCodeProfileTable OBJECT-TYPE
	SYNTAX	SEQUENCE OF GponVoipFeatAccessCodeProfileEntry
	ACCESS	not-accessible
	STATUS	mandatory
	DESCRIPTION
		"This object contains a table for creating and storing
		 VoIP feature access code parameters.
		These profiles are normally associated with a POTS line - for SIP. "
::= { gponProfilesGroup 81 }

gponVoipFeatAccessCodeProfileEntry OBJECT-TYPE
	SYNTAX 	GponVoipFeatAccessCodeProfileEntry
	ACCESS	not-accessible
	STATUS	mandatory
	DESCRIPTION
		"Rows of this table contain VoIP Feature Access Code Profiles "
	INDEX {gponVoipFeatAccessCodeProfileIndex }
::= {gponVoipFeatAccessCodeProfileTable 1}

GponVoipFeatAccessCodeProfileEntry ::=
	SEQUENCE { 
		gponVoipFeatAccessCodeProfileIndex		AsamProfileIndex,
		gponVoipFeatAccessCodeProfileName		AsamProfileName,
		gponVoipFeatAccessCodeProfileRefCount		AsamProfileRefCount,
		gponVoipFeatAccessCodeProfileScope		AsamProfileScope,
		gponVoipFeatAccessCodeProfileRowStatus 		RowStatus,
		gponVoipFeatAccessCodeProfileCancelCallWait		DisplayString,
		gponVoipFeatAccessCodeProfileCallHold		DisplayString,
		gponVoipFeatAccessCodeProfileCallPark		DisplayString,
		gponVoipFeatAccessCodeProfileCidActivate		DisplayString,
		gponVoipFeatAccessCodeProfileCidDeactivate		DisplayString,
		gponVoipFeatAccessCodeProfileDndActivate		DisplayString,
		gponVoipFeatAccessCodeProfileDndDeactivate		DisplayString,
		gponVoipFeatAccessCodeProfileDndPinChange		DisplayString,
		gponVoipFeatAccessCodeProfileEmergServiceNum	DisplayString,
		gponVoipFeatAccessCodeProfileIntercomService	DisplayString,
		gponVoipFeatAccessCodeProfileUnattendedCallTransfer	DisplayString,
		gponVoipFeatAccessCodeProfileAttendedCallTransfer	DisplayString
}

gponVoipFeatAccessCodeProfileIndex OBJECT-TYPE 
	SYNTAX AsamProfileIndex
	ACCESS not-accessible
	STATUS mandatory
	DESCRIPTION
	    "This object is the index to the gponVoipFeatAccessCodeProfileTable. "
::= { gponVoipFeatAccessCodeProfileEntry 1}

gponVoipFeatAccessCodeProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponVoipFeatAccessCodeProfileEntry 2}

gponVoipFeatAccessCodeProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponVoipFeatAccessCodeProfileEntry  3}


gponVoipFeatAccessCodeProfileScope OBJECT-TYPE
        	SYNTAX          AsamProfileScope
        	ACCESS          read-write
        	STATUS          mandatory
        	DESCRIPTION     
       		 "A  profile can be qualified as having a local scope or a network wide 
         		scope.

		Default = 1 = local scope. "
::= {gponVoipFeatAccessCodeProfileEntry  4}


gponVoipFeatAccessCodeProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponVoipFeatAccessCodeProfileEntry  5}

gponVoipFeatAccessCodeProfileCancelCallWait  OBJECT-TYPE
	SYNTAX 	DisplayString
	ACCESS	read-write
	STATUS	mandatory
	DESCRIPTION 
		"This attribute contains the access code to cancel call waiting.
		 Format is a string (maximum 5 characters) from the set (0..9, *, #),
		 with trailing nulls in any unused bytes.

		 Default = null string.

		 Modification is NOT permitted.  "
	::= { gponVoipFeatAccessCodeProfileEntry  6 }

gponVoipFeatAccessCodeProfileCallHold  OBJECT-TYPE
	SYNTAX 	DisplayString
	ACCESS	read-write
	STATUS	mandatory
	DESCRIPTION 
		"This attribute contains the access code to hold call.
		 Format is a string (maximum 5 characters) from the set (0..9, *, #),
		 with trailing nulls in any unused bytes.

		 Default = null string.

		 Modification is NOT permitted.  "
	::= { gponVoipFeatAccessCodeProfileEntry  7 }

gponVoipFeatAccessCodeProfileCallPark  OBJECT-TYPE
	SYNTAX 	DisplayString
	ACCESS	read-write
	STATUS	mandatory
	DESCRIPTION 
		"This attribute contains the access code to park call.
		 Format is a string (maximum 5 characters) from the set (0..9, *, #),
		 with trailing nulls in any unused bytes.

		 Default = null string.

		 Modification is NOT permitted.  "
	::= { gponVoipFeatAccessCodeProfileEntry  8 }

gponVoipFeatAccessCodeProfileCidActivate  OBJECT-TYPE
	SYNTAX 	DisplayString
	ACCESS	read-write
	STATUS	mandatory
	DESCRIPTION 
		"This attribute contains the access code to activate caller ID.
		 Format is a string (maximum 5 characters) from the set (0..9, *, #),
		 with trailing nulls in any unused bytes.

		 Default = null string.

		 Modification is NOT permitted.  "
	::= { gponVoipFeatAccessCodeProfileEntry  9 }

gponVoipFeatAccessCodeProfileCidDeactivate  OBJECT-TYPE
	SYNTAX 	DisplayString
	ACCESS	read-write
	STATUS	mandatory
	DESCRIPTION 
		"This attribute contains the access code to deactivate caller ID.
		 Format is a string (maximum 5 characters) from the set (0..9, *, #),
		 with trailing nulls in any unused bytes.

		 Default = null string.

		 Modification is NOT permitted.  "
	::= { gponVoipFeatAccessCodeProfileEntry  10 }

gponVoipFeatAccessCodeProfileDndActivate  OBJECT-TYPE
	SYNTAX 	DisplayString
	ACCESS	read-write
	STATUS	mandatory
	DESCRIPTION 
		"This attribute contains the access code to activate do not disturb.
		 Format is a string (maximum 5 characters) from the set (0..9, *, #),
		 with trailing nulls in any unused bytes.

		 Default = null string.

		 Modification is NOT permitted.  "
	::= { gponVoipFeatAccessCodeProfileEntry  11 }

gponVoipFeatAccessCodeProfileDndDeactivate  OBJECT-TYPE
	SYNTAX 	DisplayString
	ACCESS	read-write
	STATUS	mandatory
	DESCRIPTION 
		"This attribute contains the access code to deactivate do not disturb.
		 Format is a string (maximum 5 characters) from the set (0..9, *, #),
		 with trailing nulls in any unused bytes.

		 Default = null string.

		 Modification is NOT permitted.  "
	::= { gponVoipFeatAccessCodeProfileEntry  12 }

gponVoipFeatAccessCodeProfileDndPinChange  OBJECT-TYPE
	SYNTAX 	DisplayString
	ACCESS	read-write
	STATUS	mandatory
	DESCRIPTION 
		"This attribute contains the access code to change do not disturb PIN.
		 Format is a string (maximum 5 characters) from the set (0..9, *, #),
		 with trailing nulls in any unused bytes.

		 Default = null string.

		 Modification is NOT permitted.  "
	::= { gponVoipFeatAccessCodeProfileEntry  13 }

gponVoipFeatAccessCodeProfileEmergServiceNum  OBJECT-TYPE
	SYNTAX 	DisplayString
	ACCESS	read-write
	STATUS	mandatory
	DESCRIPTION 
		"This attribute contains the access code to set emergency service number.
		 Format is a string (maximum 5 characters) from the set (0..9, *, #),
		 with trailing nulls in any unused bytes.

		 Default = null string.

		 Modification is NOT permitted.  "
	::= { gponVoipFeatAccessCodeProfileEntry  14 }

gponVoipFeatAccessCodeProfileIntercomService  OBJECT-TYPE
	SYNTAX 	DisplayString
	ACCESS	read-write
	STATUS	mandatory
	DESCRIPTION 
		"This attribute contains the access code to enable intercom service.
		 Format is a string (maximum 5 characters) from the set (0..9, *, #),
		 with trailing nulls in any unused bytes.

		 Default = null string.

		 Modification is NOT permitted.  "
	::= { gponVoipFeatAccessCodeProfileEntry  15 }

gponVoipFeatAccessCodeProfileUnattendedCallTransfer  OBJECT-TYPE
	SYNTAX 	DisplayString
	ACCESS	read-write
	STATUS	mandatory
	DESCRIPTION 
		"This attribute contains the access code to enable unattended/blind call transfer.
		 Format is a string (maximum 5 characters) from the set (0..9, *, #),
		 with trailing nulls in any unused bytes.

		 Default = null string.

		 Modification is NOT permitted.  "
	::= { gponVoipFeatAccessCodeProfileEntry  16 }

gponVoipFeatAccessCodeProfileAttendedCallTransfer  OBJECT-TYPE
	SYNTAX 	DisplayString
	ACCESS	read-write
	STATUS	mandatory
	DESCRIPTION 
		"This attribute contains the access code to enable attended call transfer.
		 Format is a string (maximum 5 characters) from the set (0..9, *, #),
		 with trailing nulls in any unused bytes.

		 Default = null string.

		 Modification is NOT permitted.  "
	::= { gponVoipFeatAccessCodeProfileEntry  17 }


gponVoipFeatAccessCodeProfileIndexNext        OBJECT-TYPE
        	SYNTAX          AsamNextProfileIndex
        	ACCESS          read-only
        	STATUS          mandatory
        	DESCRIPTION     
        	"This object contains an appropriate value to be used for 
         		gponVoipFeatAccessCodeProfileIndex when creating entries in the
         		gponVoipFeatAccessCodeProfileTable. 
         		The value 0 indicates that no unassigned entries are available. To 
         		obtain the next index value for a new entry, the
        		 manager issues a management protocol retrieval operation to obtain the
         		current value of this object.  After each retrieval, the agent should
        		 modify the value to the next unassigned index. "
::= {gponProfilesGroup 82 }


  gponVoipFeatAccessCodeProfileMaxIndex        OBJECT-TYPE
      	SYNTAX            AsamMaxProfileIndex
      	ACCESS            read-only
     	 STATUS            mandatory
      	DESCRIPTION
            	"This object represents the maximum number of
            		 gponVoipFeatAccessCodeProfiles that can be created. The object
             		 gponVoipFeatAccessCodeProfileIndexNext will have values ranging
            		 from 0 to the value represented by this object. 
		 For ISAM4.2,  initially set to 20. "
::= {gponProfilesGroup 83 }

-- *********************************************
-- GPON VOIP FEATURE ACCESS CODE PROFILE MAPPING TABLE
--
-- This table was first introduced with ISAM4.2 MIB.
-- It is only SUPPORTED beginning with ISAM4.2.02 release.
--
-- For the gponVoipFeatAccessCodeProfileTable, this table provides a reverse mapping
-- (i.e. profile name to profile index number).
--
-- The system automatically creates an entry in this Table when a  corresponding entry
-- in gponVoipFeatAccessCodeProfile is created. 
-- The system automatically deletes an entry in this Table when a  corresponding entry
-- in gponVoipFeatAccessCodeProfile is deleted.
--
--	For GPON - SUPPORTED as of ISAM4.2.02
--	For XG-PON1 - SUPPORTED as of ISAM4.6.02
--  For NG-PON2 - SUPPORTED as of ISAM5.4.01
--   
--
-- *********************************************

 
gponVoipFeatAccessCodeProfileMappingTable OBJECT-TYPE
   SYNTAX   SEQUENCE OF GponVoipFeatAccessCodeProfileMappingEntry
   ACCESS   not-accessible
   STATUS   mandatory
   DESCRIPTION
   "This object contains a table for gponVoipFeatAccessCodeProfile
name to index mapping"
::= { gponProfilesGroup 84 }
 
gponVoipFeatAccessCodeProfileMappingEntry OBJECT-TYPE
   SYNTAX   GponVoipFeatAccessCodeProfileMappingEntry
   ACCESS   not-accessible
   STATUS mandatory
   DESCRIPTION
   " An entry (conceptual row) representing the gponVoipFeatAccessCodeProfile Name to Index mapping."
   INDEX {gponVoipFeatAccessCodeProfileMappingName }
   ::= {gponVoipFeatAccessCodeProfileMappingTable  1}
 
GponVoipFeatAccessCodeProfileMappingEntry ::=
   SEQUENCE { 
	gponVoipFeatAccessCodeProfileMappingName     AsamProfileName,
      	gponVoipFeatAccessCodeProfileMappingIndex      AsamProfileIndex
  }
 
gponVoipFeatAccessCodeProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponVoipFeatAccessCodeProfileMappingEntry 1}
 
gponVoipFeatAccessCodeProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponVoipFeatAccessCodeProfileMappingEntry 2}

-- *********************************************
-- GPON UNIFORM RESOURCE IDENTIFIER PROFILE TABLE
--
-- This table was first introduced with ISAM4.2 MIB.
-- It is only SUPPORTED beginning with ISAM4.2.02 release.
--
-- This table contains ASCII strings that represent Uniform Resource Information regarding
-- a remote network address, a remote/local file, a specific IP address using dot notation, etc.
-- From an OMCI standpoint, it maps primarily to the Large String ME.
--
--  Rows are created by the operator.
--
-- NOTE: Profile cannot be deleted if associated with another table.
--
--	For GPON - SUPPORTED as of ISAM4.2.02
--	For XG-PON1 - SUPPORTED as of ISAM4.6.02
--  For NG-PON2 - SUPPORTED as of ISAM5.4.01
-- 
--
-- *********************************************

gponUriProfileTable OBJECT-TYPE
	SYNTAX	SEQUENCE OF GponUriProfileEntry
	ACCESS	not-accessible
	STATUS	mandatory
	DESCRIPTION
		"This object contains a table for creating and storing
		 URI  profiles "
::= { gponProfilesGroup 85 }

gponUriProfileEntry OBJECT-TYPE
	SYNTAX 	GponUriProfileEntry
	ACCESS	not-accessible
	STATUS	mandatory
	DESCRIPTION
		"Rows of this table contain URI Profiles"
	INDEX {gponUriProfileIndex }
::= {gponUriProfileTable 1}

GponUriProfileEntry ::=
	SEQUENCE { 
		gponUriProfileIndex		AsamProfileIndex,
		gponUriProfileName		AsamProfileName,
		gponUriProfileRefCount	AsamProfileRefCount,
		gponUriProfileScope	AsamProfileScope,
		gponUriProfileRowStatus 	RowStatus,
		gponUriProfileAddress	DisplayString,
		gponUriProfileVersionNbr INTEGER
}

gponUriProfileIndex OBJECT-TYPE 
	SYNTAX AsamProfileIndex
	ACCESS not-accessible
	STATUS mandatory
	DESCRIPTION
	    "This object is the index to the gponUriProfileTable. "
::= { gponUriProfileEntry 1}

gponUriProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponUriProfileEntry 2}

gponUriProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponUriProfileEntry  3}


gponUriProfileScope OBJECT-TYPE
        	SYNTAX          AsamProfileScope
        	ACCESS          read-write
        	STATUS          mandatory
        	DESCRIPTION     
       		 "A  profile can be qualified as having a local scope or a network wide 
         		scope.

		Default = 1 = local scope. "
::= {gponUriProfileEntry  4}


gponUriProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponUriProfileEntry  5}


gponUriProfileAddress OBJECT-TYPE 
	SYNTAX 	DisplayString (SIZE(0..100))
	ACCESS	read-write
	STATUS	mandatory
	DESCRIPTION 
		"This is a textual string that contains a URI.
		 This string can represent a Fully Qualified Domain
		 Name (FQDN), or an IP Address (in dot notation), or a file name
		 useable by FTP protocol, or a local file name or other formats parseable
		 by the ONT.

		 Default - null string. "
::= { gponUriProfileEntry  6}

gponUriProfileVersionNbr OBJECT-TYPE
        SYNTAX INTEGER
        ACCESS read-write
        STATUS mandatory
        DESCRIPTION
                "The manager can associate a version number to the profile. It is usually set
                 to 1 when the profile is first created and can be incremented by the manager 
                 when the profile is modified.

                 Default = 1
                 Range is 1..2147483647."
::= { gponUriProfileEntry  7}


gponUriProfileIndexNext        OBJECT-TYPE
        	SYNTAX          AsamNextProfileIndex
        	ACCESS          read-only
        	STATUS          mandatory
        	DESCRIPTION     
        	"This object contains an appropriate value to be used for 
         		gponUriProfileIndex when creating entries in the
         		gponUriProfileTable. 
         		The value 0 indicates that no unassigned entries are available. To 
         		obtain the next index value for a new entry, the
        		 manager issues a management protocol retrieval operation to obtain the
         		current value of this object.  After each retrieval, the agent should
        		 modify the value to the next unassigned index. "
::= {gponProfilesGroup 86 }


  gponUriProfileMaxIndex        OBJECT-TYPE
      	SYNTAX            AsamMaxProfileIndex
      	ACCESS            read-only
     	 STATUS            mandatory
      	DESCRIPTION
            	"This object represents the maximum number of
            		 gponUriProfiles that can be created. The object
             		 gponUriProfileIndexNext will have values ranging
            		 from 0 to the value represented by this object. 
		 For ISAM4.2, initially set to 100. "
::= {gponProfilesGroup 87 }

-- *********************************************
-- GPON URI  PROFILE MAPPING TABLE
--
-- This table was first introduced with ISAM4.2 MIB.
-- It is only SUPPORTED beginning with ISAM4.2.02 release.
--
-- For the gponUriProfileTable, this table provides a reverse mapping
-- (i.e. profile name to profile index number).
--
-- The system automatically creates an entry in this Table when a  corresponding entry
-- in gponUriProfile is created. 
-- The system automatically deletes an entry in this Table when a  corresponding entry
-- in gponUriProfile is deleted.
--
--	For GPON - SUPPORTED as of ISAM4.2.02
--	For XG-PON1 - SUPPORTED as of ISAM4.6.02
--  For NG-PON2 - SUPPORTED as of ISAM5.4.01
--   
--
-- *********************************************

 
gponUriProfileMappingTable OBJECT-TYPE
   SYNTAX   SEQUENCE OF GponUriProfileMappingEntry
   ACCESS   not-accessible
   STATUS   mandatory
   DESCRIPTION
   "This object contains a table for gponUriProfile
name to index mapping"
::= { gponProfilesGroup 88 }
 
gponUriProfileMappingEntry OBJECT-TYPE
   SYNTAX   GponUriProfileMappingEntry
   ACCESS   not-accessible
   STATUS mandatory
   DESCRIPTION
   " An entry (conceptual row) representing the gponUriProfile Name to Index mapping."
   INDEX {gponUriProfileMappingName }
   ::= {gponUriProfileMappingTable  1}
 
GponUriProfileMappingEntry ::=
   SEQUENCE { 
	gponUriProfileMappingName     AsamProfileName,
      	gponUriProfileMappingIndex      AsamProfileIndex
  }
 
gponUriProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponUriProfileMappingEntry 1}
 
gponUriProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponUriProfileMappingEntry 2}


-- *********************************************
-- GPON TEXT MESSAGE PROFILE TABLE
--
-- This table was first introduced with ISAM4.2 MIB.
--
-- This table contains ASCII strings that represent common display text.  It is typically used
-- to represent textual data associated with a VoIP telephony event that is displayed on a
-- VoIP subscriber set.
-- From an OMCI standpoint, it maps primarily to the Large String ME.
--
--  Rows are created by the operator.
--
-- NOTE: Profile cannot be deleted if associated with another table.
--
-- This entire table is NOT SUPPORTED.
--
--	For GPON - NOT SUPPORTED as of ISAM4.2.02
--	For XG-PON1 - NOT SUPPORTED as of ISAM4.6.02
--	For NG-PON2 - NOT SUPPORTED as of ISAM5.2 
-- 
--
-- *********************************************

gponTextMsgProfileTable OBJECT-TYPE
	SYNTAX	SEQUENCE OF GponTextMsgProfileEntry
	ACCESS	not-accessible
	STATUS	mandatory
	DESCRIPTION
		"This object contains a table for creating and storing
		 text message  profiles.

		Entire table is NOT SUPPORTED. "
::= { gponProfilesGroup 89 }

gponTextMsgProfileEntry OBJECT-TYPE
	SYNTAX 	GponTextMsgProfileEntry
	ACCESS	not-accessible
	STATUS	mandatory
	DESCRIPTION
		"Rows of this table contain Text Message Profiles"
	INDEX {gponTextMsgProfileIndex }
::= {gponTextMsgProfileTable 1}

GponTextMsgProfileEntry ::=
	SEQUENCE { 
		gponTextMsgProfileIndex		AsamProfileIndex,
		gponTextMsgProfileName		AsamProfileName,
		gponTextMsgProfileRefCount	AsamProfileRefCount,
		gponTextMsgProfileScope	AsamProfileScope,
		gponTextMsgProfileRowStatus 	RowStatus,
		gponTextMsgProfileText	DisplayString
}

gponTextMsgProfileIndex OBJECT-TYPE 
	SYNTAX AsamProfileIndex
	ACCESS not-accessible
	STATUS mandatory
	DESCRIPTION
	    "This object is the index to the gponTextMsgProfileTable. "
::= { gponTextMsgProfileEntry 1}

gponTextMsgProfileName 	OBJECT-TYPE 
	SYNTAX	AsamProfileName
	ACCESS read-write
	STATUS mandatory
	DESCRIPTION
	    "Octet string storing the operator-given name of the profile.

	     Must be supplied by management system.
	     Cannot be null.
	     Must be unique accross other profile names within this profile table. "
::= {gponTextMsgProfileEntry 2}

gponTextMsgProfileRefCount OBJECT-TYPE
	SYNTAX	AsamProfileRefCount
	ACCESS read-only
	STATUS	mandatory
	DESCRIPTION
		" Indicates the number of entities using this profile. If the
          		reference count is greater than 0, then this profile is 'in use',
          		and may NOT be deleted. If the value is 0, then this profile is
          		'not in use', and can be deleted. "
::= { gponTextMsgProfileEntry  3}


gponTextMsgProfileScope OBJECT-TYPE
        	SYNTAX          AsamProfileScope
        	ACCESS          read-write
        	STATUS          mandatory
        	DESCRIPTION     
       		 "A  profile can be qualified as having a local scope or a network wide 
         		scope.

		Default = 1 = local scope. "
::= {gponTextMsgProfileEntry  4}


gponTextMsgProfileRowStatus OBJECT-TYPE 
	SYNTAX	RowStatus
	ACCESS	read-write
	STATUS  mandatory
	DESCRIPTION
		"This object is used to create a new row or modify or
         		delete an existing row in this table. 
       		     o The entry associated with a Profile that is being used may
             		 not be deleted. "
::= { gponTextMsgProfileEntry  5}


gponTextMsgProfileText OBJECT-TYPE 
	SYNTAX 	DisplayString (SIZE(0..100))
	ACCESS	read-write
	STATUS	mandatory
	DESCRIPTION 
		"This is a textual string that contains the actual display message.

		 Default - null string. 

		 Modification is not permitted.  "
::= { gponTextMsgProfileEntry  6}


gponTextMsgProfileIndexNext        OBJECT-TYPE
        	SYNTAX          AsamNextProfileIndex
        	ACCESS          read-only
        	STATUS          mandatory
        	DESCRIPTION     
        	"This object contains an appropriate value to be used for 
         		gponTextMsgProfileIndex when creating entries in the
         		gponTextMsgProfileTable. 
         		The value 0 indicates that no unassigned entries are available. To 
         		obtain the next index value for a new entry, the
        		 manager issues a management protocol retrieval operation to obtain the
         		current value of this object.  After each retrieval, the agent should
        		 modify the value to the next unassigned index.

		NOT SUPPORTED.  "
::= {gponProfilesGroup 90 }


  gponTextMsgProfileMaxIndex        OBJECT-TYPE
      	SYNTAX            AsamMaxProfileIndex
      	ACCESS            read-only
     	 STATUS            mandatory
      	DESCRIPTION
            	"This object represents the maximum number of
            		 gponTextMsgProfiles that can be created. The object
             		 gponTextMsgProfileIndexNext will have values ranging
            		 from 0 to the value represented by this object. 
		 For ISAM4.2, initially set to 20.

		NOT SUPPORTED. "
::= {gponProfilesGroup 91 }


-- *********************************************
-- GPON TEXT MESSAGE PROFILE MAPPING TABLE
--
-- This table was first introduced with ISAM4.2 MIB.
--
-- For the gponTextMsgProfileTable, this table provides a reverse mapping
-- (i.e. profile name to profile index number).
--
-- The system automatically creates an entry in this Table when a  corresponding entry
-- in gponTextMsgProfile is created. 
-- The system automatically deletes an entry in this Table when a  corresponding entry
-- in gponTextMsgProfile is deleted.  
--
-- This entire table is NOT SUPPORTED.
--
--	For GPON - NOT SUPPORTED as of ISAM4.2.02
--	For XG-PON1 - NOT SUPPORTED as of ISAM4.6.02
--	For NG-PON2 - NOT SUPPORTED as of ISAM5.2 
-- 
--
-- *********************************************

 
gponTextMsgProfileMappingTable OBJECT-TYPE
   SYNTAX   SEQUENCE OF GponTextMsgProfileMappingEntry
   ACCESS   not-accessible
   STATUS   mandatory
   DESCRIPTION
   "This object contains a table for gponTextMsgProfile
name to index mapping"
::= { gponProfilesGroup 92 }
 
gponTextMsgProfileMappingEntry OBJECT-TYPE
   SYNTAX   GponTextMsgProfileMappingEntry
   ACCESS   not-accessible
   STATUS mandatory
   DESCRIPTION
   " An entry (conceptual row) representing the gponTextMsgProfile Name to Index mapping."
   INDEX {gponTextMsgProfileMappingName }
   ::= {gponTextMsgProfileMappingTable  1}
 
GponTextMsgProfileMappingEntry ::=
   SEQUENCE { 
	gponTextMsgProfileMappingName     AsamProfileName,
      	gponTextMsgProfileMappingIndex      AsamProfileIndex
  }
 
gponTextMsgProfileMappingName OBJECT-TYPE
   SYNTAX   AsamProfileName
   ACCESS   not-accessible
   STATUS  mandatory
   DESCRIPTION
      "A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { gponTextMsgProfileMappingEntry 1}
 
gponTextMsgProfileMappingIndex OBJECT-TYPE
   SYNTAX   AsamProfileIndex
   ACCESS   read-only
   STATUS mandatory
   DESCRIPTION
      "This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { gponTextMsgProfileMappingEntry 2}



-- *********************************************
-- GPON VOICE OVER IP (VoIP) SERVICE TABLE
--
--This table is only used for GPON.
--
-- This table contains information regarding a VoIP service for
-- a specific ONT.  These individual services are referred to as
-- VoIP Clients.  Multiple physical POTS port UNIs can be associated
-- with a single VoIP service.   
-- Rows are created by the operator.
--
-- For ISAM4.0.10, this table is being re-used.  
-- Noted which attributes are relevant for ISAM4.0.10
--
-- For ISAM4.2, this table is being reused.
-- Noted which attributes are relevant for ISAM4.2.
--
-- VALIDATION:  For a specific ONT, creation of a row in this table must be MUTUALLY EXCLUSIVE
-- 	with creation of a row in gponOntIpHostTable that would use same ifIndex in Interface MIB (i.e. either legacy Voip or
--	standard Voip - but not both). For a specific ONT, creation of a row in this table is only permitted
--	if bponOntVoipCapability attribute is set to 1 (which implies legacy mode).
-- NOTE: To clarify terms used in other sections of this MIB, creation of a row in
--	this table means that the user has decided to provision VoIP for this ONT using legacy style
--	(i.e.NOT standard style).
--
--	For GPON - SUPPORTED as of ISAM4.0.10
--	For XG-PON1 - SUPPORTED as of ISAM4.6.02
--  For NG-PON2 - NOT SUPPORTED as of ISAM5.2 (POTS Card Type NOT SUPPORTED)
--   
--
-- *********************************************



gponVoipServiceTable OBJECT-TYPE
	SYNTAX	SEQUENCE OF GponVoipServiceEntry
	ACCESS	not-accessible
	STATUS	mandatory
	DESCRIPTION
		"This object contains a table for creating and storing
		information regarding a Voip service for an ONT  "
::= { gponServicesGroup 2 }

gponVoipServiceEntry OBJECT-TYPE
	SYNTAX 	GponVoipServiceEntry
	ACCESS	not-accessible
	STATUS	mandatory
	DESCRIPTION
		"Rows of this table contain Voip service information. "
	INDEX {gponVoipServiceUniIndex }
::= {gponVoipServiceTable 1}

GponVoipServiceEntry ::=
	SEQUENCE { 
		gponVoipServiceUniIndex		IfIndex,
		gponVoipServiceUpBwProfile		AsamProfilePointer,
		gponVoipServiceDownBwProfile	AsamProfilePointer,
		gponVoipServicePQProfile		AsamProfilePointer,
		gponVoipServiceRowStatus 		RowStatus,
		gponVoipServiceVlanId		INTEGER,
		gponVoipServiceAesEnableInd		INTEGER,
		gponVoipServiceLabel		OCTET STRING,
		gponVoipServiceAdminState		AdminState,
		gponVoipServiceOperState		OperState,
		gponVoipServiceGwyOption		INTEGER,
		gponVoipServiceNetGwyIpAddr	IpAddress,
		gponVoipServiceDefaltNextHopAddr	IpAddress,
		gponVoipServiceGwySigPort		INTEGER,
		gponVoipServiceGwySigEncoding	INTEGER,
		gponVoipServiceGwySigProtocol	INTEGER,
		gponVoipServiceRtpBasePort	INTEGER,
		gponVoipServiceDhcpEnable		INTEGER,
		gponVoipServiceClientIpAddr		IpAddress,
		gponVoipServiceClientSubnetMask	IpAddress,
		gponVoipServiceFtpServerIpAddr	IpAddress,
		gponVoipServiceDscpSetting		INTEGER,
		gponVoipServiceConfigFileName	OCTET STRING,
		gponVoipServiceClientIdentifier	OCTET STRING,
		gponVoipServiceCustomerId		DisplayString,
		gponVoipServiceGemPmCollectInd	INTEGER,
		gponVoipServiceGemPmNumPMIntervals	INTEGER,
		gponVoipServiceSecretId		OCTET STRING,
		gponVoipServiceSecretK		OCTET STRING,
		gponVoipServiceSourceVlanId	INTEGER,
		gponVoipServiceConfigMethod		INTEGER,
		gponVoipServiceSippingServerIpAddr	IpAddress,
		gponVoipServiceSippingAuthUsername		DisplayString,
		gponVoipServiceSippingAuthPassword		DisplayString,
		gponVoipServiceSippingAuthRealm		DisplayString,
		gponVoipServiceIpsecEnable		INTEGER,
		gponVoipServiceSippingServerAddress		AsamProfilePointer,
		gponVoipServiceSecondaryNetGwyIpAddr	IpAddress,
		gponVoipServiceDsRateSchedProfile	AsamProfilePointer,
		gponVoipServiceFtpAuthUsername	DisplayString,
		gponVoipServiceFtpAuthPassword	DisplayString,
		gponVoipServiceSignalVlanId	INTEGER,
		gponVoipServiceVlanPointer		VlanIndex,
		gponVoipServiceForceOmciXmlDownload	INTEGER
}

gponVoipServiceUniIndex OBJECT-TYPE 
	SYNTAX IfIndex
	ACCESS read-only
	STATUS mandatory
	DESCRIPTION
	    "This index is the ifIndex of the VoIP UNI.

	     For ISAM 4.0.10 -> this is an ONT UNI ifIndex 
 	     with the ontSlot/ontPort fields = 15/15.

	     For ISAM4.2, this stays the same as previous ISAM. "
::= { gponVoipServiceEntry 1}


gponVoipServiceUpBwProfile OBJECT-TYPE
	SYNTAX	AsamProfilePointer
	ACCESS read-write
	STATUS	mandatory
	DESCRIPTION
		" The value of this object identifies the row in the GPON
          		 Bandwidth Profile Table that applies for the upstream side
		 of this particular service.

		 Modification is permitted (without having to ADMIN DOWN the service).

		 For ISAM 4.0.10 --> this attribute is NOT SUPPORTED.
	     	 For ISAM4.2, this stays the same as previous ISAM.  "
::= { gponVoipServiceEntry  2}


gponVoipServiceDownBwProfile OBJECT-TYPE
	SYNTAX	AsamProfilePointer
	ACCESS read-write
	STATUS	mandatory
	DESCRIPTION
		" The value of this object identifies the row in the GPON
          		 Bandwidth Profile Table that applies for the downstream side
		 of this particular service.

		 Modification is permitted (without having to ADMIN DOWN the service).

		 For ISAM 4.0.10 --> this attribute is NOT SUPPORTED. 
	     	 For ISAM4.2, this stays the same as previous ISAM.  "
::= { gponVoipServiceEntry  3}


gponVoipServicePQProfile OBJECT-TYPE
	SYNTAX	AsamProfilePointer
	ACCESS read-write
	STATUS	mandatory
	DESCRIPTION
		" The value of this object identifies the row in the GPON
          		 Priority Queue Profile Table that applies for the upstream
		 aspects of this particular service. 

		 For all ONTs (other that older M300),  the referenced PQ Profile should
		 specify exactly 2 queues (GEM ports).  But the OLT will will not
		 enforce this check.  If the particular ONT does not support the 
		 the number of specified queues (GEM ports) for this VoIP service,
		 it will reject via OMCI and OLT will raise a 'service mismatch alarm'.

		 For ISAM 4.0.10 --> this attribute is NOT SUPPORTED. 
	     	 For ISAM4.2, this stays the same as previous ISAM.  "
::= { gponVoipServiceEntry  4}

gponVoipServiceRowStatus OBJECT-TYPE 
	SYNTAX	RowStatus
	ACCESS	read-write
	STATUS  mandatory
	DESCRIPTION
		"This object is used to create a new row or modify or
         		delete an existing row in this table.


	     	For ISAM 4.0.10 -> stays the same as latest FGU4.x. 
	     	 For ISAM4.2, this stays the same as previous ISAM.  "
::= { gponVoipServiceEntry  5}

gponVoipServiceVlanId OBJECT-TYPE 
	SYNTAX	INTEGER
	ACCESS	read-write
	STATUS  mandatory
	DESCRIPTION
		"This object is used to reference the S-VLAN ID (in the 
		 L2 subsystem) with which this service is associated. 

		 Range is 2 - 4094.
		
		 No default since value must be supplied by manager.

		 For ISAM 4.0.10 --> this attribute is NOT SUPPORTED.
	     	 For ISAM4.2, this stays the same as previous ISAM.  "
::= { gponVoipServiceEntry  6}

gponVoipServiceAesEnableInd OBJECT-TYPE 
	SYNTAX	INTEGER
	ACCESS	read-write
	STATUS  mandatory
	DESCRIPTION 
		" Used to designate whether AES encryption is enabled
  		or disabled for this service. This encryption decision applies
		to all GEM ports that ultimately get associated with the
		service. 

 		1 = enabled
  		2 = disabled
   
 		 Default = 2 = disabled

	    	 For ISAM 4.0.10 -> this attribute is NOT SUPPORTED.
	     	 For ISAM4.2, this stays the same as previous ISAM.  "
::= { gponVoipServiceEntry  7}


gponVoipServiceLabel  OBJECT-TYPE
	SYNTAX 	OCTET STRING (SIZE(0..80))
	ACCESS	read-write
	STATUS	mandatory
	DESCRIPTION 
		"This is a 80 byte free-form textual field that the
		  operator can use to label this particular service.
 
		 Default - null string.  

		 Modification is permitted.

	     	For ISAM 4.0.10 -> stays the same as latest FGU4.x
	     	 For ISAM4.2, this stays the same as previous ISAM.  "
::= { gponVoipServiceEntry  8 }


gponVoipServiceAdminState  OBJECT-TYPE
	SYNTAX 	AdminState
	ACCESS	read-write
	STATUS	mandatory
	DESCRIPTION 
		" Setting it to 'locked' causes OLT to stop
		  sending upstream allocation grants 
		  associated with this service.
		 
		 Default = 0 = unlocked.

		 Modification is permitted.

		 For ISAM 4.0.10, this attribute is still SUPPORTED.
 
		 NOTE: VoIP has a logical UNI represented in Interface MIB (and has
		 an Admin State attribute in that MIB that controls the logical UNI-aspect of VoIP).
		 This Admin State attribute (in this GPON MIB) controls the service-aspect of the VoIP service. 

	     	 For ISAM4.2, this stays the same as previous ISAM.  "
::= { gponVoipServiceEntry  9 }

gponVoipServiceOperState  OBJECT-TYPE
	SYNTAX 	OperState
	ACCESS	read-only
	STATUS	mandatory
	DESCRIPTION 
		"Indicates operational state of the
		  service. State is related to ability of service
		  to perform its function (e.g. whether service
		  affecting alarm is present).

		  Default = 0 = Enabled 

		  For ISAM 4.0.10, this attribute is still SUPPORTED.
 
		  NOTE: VoIP has a logical UNI represented in Interface MIB (and has
		  an Oper State attribute in that MIB that represents the logical UNI-aspect of VoIP).
		  This Oper State attribute (in this GPON MIB) represents the service-aspect of the VoIP service.

	     	 For ISAM4.2, this stays the same as previous ISAM.  "
::= { gponVoipServiceEntry  10  }


gponVoipServiceGwyOption  OBJECT-TYPE
	SYNTAX 	INTEGER
	ACCESS	read-write
	STATUS	mandatory
	DESCRIPTION 
		"Used to set Voice Gateway signalling mode.
		  As of FGU4.6.4, options are as follows:

		1 = GR303-H248
		2 = V5.x-H248
		3 = Softswitch-H248
		4 = SIP 1 = Mode 1 SIP - thin client - (compatible with Broadsoft softswitch)
		5 = SIP 2 = Mode 2 SIP - thick client (compatible with Nortel softswitch)
		6 = PPPoE SIP 1 = Mode 1 PPPoE SIP - thin client
		7 = PPPoE SIP 2  = Mode 2 PPPoE SIP - thick client
		8 = Future 1
		9 = Future 2

		Default = 4 (NOTE: For ISAM 4.0.10, changed default from 1 to 4)

	     For ISAM 4.0.10 -> only support following options: 4 and 5.
	     For ISAM 4.2 -> only support following options: 1, 2, 3, 4 and 5. "
::= { gponVoipServiceEntry  11 }


gponVoipServiceNetGwyIpAddr  OBJECT-TYPE
	SYNTAX 	IpAddress
	ACCESS	read-write
	STATUS	mandatory
	DESCRIPTION 
		" The manually provisioned IP Address of the
		  Network Media Gateway. NOTE: If DHCP option
		  is enabled, this provisioned attribute will be overriden
		  by the one obtained by the ONT from the DHCP server.
		  In either case, the value of the attribute actually used by
		  the ONT can be obtained from the 
		  gponVoipServiceOpInfoTable.

		  VALIDATION:  The OLT should prohibit entry of the 
		  following range of IP addresses:
		  224.0.0.0 to 239.255.255.255   (multicast)
    		  127.0.0.0 to 127.255.255.255   (loopback)

		  Default = 0.0.0.0

	     	For ISAM 4.0.10 -> stays the same as latest FGU4.x. 
	     	 For ISAM4.2, this stays the same as previous ISAM.  "
::= { gponVoipServiceEntry  12 }


gponVoipServiceDefaltNextHopAddr  OBJECT-TYPE
	SYNTAX 	IpAddress
	ACCESS	read-write
	STATUS	mandatory
	DESCRIPTION 
		" The manually provisioned default next hop 
		   IP Address used by the VoIP Client. NOTE: If DHCP
		  option is enabled, this provisioned attribute will be overriden
		  by the one obtained by the ONT from the DHCP server.
		  In either case, the value of the attribute actually used by
		  the ONT can be obtained from the 
		  gponVoipServiceOpInfoTable.

		  VALIDATION:  The OLT should prohibit entry of the 
		  following range of IP addresses:
		  224.0.0.0 to 239.255.255.255   (multicast)
    		  127.0.0.0 to 127.255.255.255   (loopback)

	     	For ISAM 4.0.10 -> stays the same as latest FGU4.x.
	     	 For ISAM4.2, this stays the same as previous ISAM.  "
::= { gponVoipServiceEntry  13 }


gponVoipServiceGwySigPort  OBJECT-TYPE
	SYNTAX 	INTEGER
	ACCESS	read-write
	STATUS	mandatory
	DESCRIPTION 
		"The TCP/UDP Port used for signalling.

		Default = 2944

	     For ISAM 4.0.10 -> this attribute is NOT SUPPORTED.
	     For ISAM 4.2, this attribute is SUPPORTED. "
::= { gponVoipServiceEntry  14 }


gponVoipServiceGwySigEncoding  OBJECT-TYPE
	SYNTAX 	INTEGER
	ACCESS	read-write
	STATUS	mandatory
	DESCRIPTION 
		"The encoding scheme used for H248 signalling.

		1 = Text
		2 = Binary
		3 = SCTP

		Default = 1 = Text - and that is the only value supported
		for FGU4.0

	     	For ISAM 4.0.10 -> stays the same as latest FGU4.x.
	     	 For ISAM4.2, this stays the same as previous ISAM.  "
::= { gponVoipServiceEntry  15 }


gponVoipServiceGwySigProtocol  OBJECT-TYPE
	SYNTAX 	INTEGER
	ACCESS	read-write
	STATUS	mandatory
	DESCRIPTION 
		"The protocol used for H248 signalling.

		1 = TCP
		2 = UDP
		3 = SCTP

		Default = 2 = UDP - and that is the only value supported
		for FGU4.0

	     	For ISAM 4.0.10 -> stays the same as latest FGU4.x.
	     	 For ISAM4.2, this stays the same as previous ISAM.  "
::= { gponVoipServiceEntry  16 }


gponVoipServiceRtpBasePort  OBJECT-TYPE
	SYNTAX 	INTEGER
	ACCESS	read-write
	STATUS	mandatory
	DESCRIPTION 
		"The UDP Base Port used for Bearer RTP
		 (RTCP port will be RTP port + 1).  Parameter 
		 specifies the first RTP port (for subscriber 1 on
		 this client). Subsequent subscribers will use 2 
		 greater than the previous.

		Default = 5004 - and that is the only value supported
		for FGU4.0

	     	For ISAM 4.0.10 -> stays the same as latest FGU4.x 
	     	 For ISAM4.2, this stays the same as previous ISAM.  "
::= { gponVoipServiceEntry  17 }

gponVoipServiceDhcpEnable OBJECT-TYPE 
	SYNTAX	INTEGER
	ACCESS	read-write
	STATUS  mandatory
	DESCRIPTION 
		" Used to designate whether DHCP is enabled as the 
  		method by which the ONT obtains IP Address, subnet
		mask, etc.  Enabling DHCP overrides any manual
		provisioning.

 		1 = enabled
  		2 = disabled
   
 		 Default = 2 = disabled

	     For ISAM 4.0.10 -> stays the same as latest FGU4.x
	     For ISAM4.2, this stays the same as previous ISAM.  "
::= { gponVoipServiceEntry  18}


gponVoipServiceClientIpAddr  OBJECT-TYPE
	SYNTAX 	IpAddress
	ACCESS	read-write
	STATUS	mandatory
	DESCRIPTION 
		" The manually provisioned local common IP Address of the
		  ONT VoIP Client. NOTE: If common DHCP option
		  is enabled, this provisioned attribute will be overriden
		  by the one obtained by the ONT from the DHCP server.
		  In either case, the value of the attribute actually used by
		  the ONT can be obtained from the 
		  gponVoipServiceOpInfoTable.

		  NOTE: As a minimum, this local IP address is associated with the signalling
		  flow. Depending on the explicit settings of gponVoipServiceBearerSVlanId
		  and gponVoipServiceFtpSVlanId, this IP address may also be associated
		  with the bearer and/or FTP flows.  This IP address may be described as
		  the 'common local IP address'  in other parts of this MIB.

		  VALIDATION:  The OLT should prohibit entry of the 
		  following range of IP addresses:
		  224.0.0.0 to 239.255.255.255   (multicast)
    		  127.0.0.0 to 127.255.255.255   (loopback)

	     For ISAM 4.0.10 -> stays the same as latest FGU4.x  
	     For ISAM4.2, this stays the same as previous ISAM.  "
::= { gponVoipServiceEntry  19 }


gponVoipServiceClientSubnetMask  OBJECT-TYPE
	SYNTAX 	IpAddress
	ACCESS	read-write
	STATUS	mandatory
	DESCRIPTION 
		" The manually provisioned subnet mask for
		   the VoIP client's subnet. NOTE: If DHCP option
		  is enabled, this provisioned attribute will be overriden
		  by the one obtained by the ONT from the DHCP server.
		  In either case, the value of the attribute actually used by
		  the ONT can be obtained from the 
		  gponVoipServiceOpInfoTable.

	     For ISAM 4.0.10 -> stays the same as latest FGU4.x 
	     For ISAM4.2, this stays the same as previous ISAM.  "
::= { gponVoipServiceEntry  20 }


gponVoipServiceFtpServerIpAddr  OBJECT-TYPE
	SYNTAX 	IpAddress
	ACCESS	read-write
	STATUS	mandatory
	DESCRIPTION 
		" The manually provisioned IP Address of the
		   FTP Server that contains the VoIP configuration files
		  that the ONT needs to download.  NOTE: If DHCP option
		  is enabled, this provisioned attribute will be overriden
		  by the one obtained by the ONT from the DHCP server.
		  In either case, the value of the attribute actually used by
		  the ONT can be obtained from the 
		  gponVoipServiceOpInfoTable. 

		  VALIDATION:  The OLT should prohibit entry of the 
		  following range of IP addresses:
		  224.0.0.0 to 239.255.255.255   (multicast)
    		  127.0.0.0 to 127.255.255.255   (loopback)

	     For ISAM 4.0.10 -> stays the same as latest FGU4.x 
	     For ISAM4.2, this stays the same as previous ISAM.  "
::= { gponVoipServiceEntry  21 }


gponVoipServiceDscpSetting OBJECT-TYPE 
	SYNTAX	INTEGER
	ACCESS	read-write
	STATUS  mandatory
	DESCRIPTION 
		" Used to set the DSCP value that the Voip Client
		  will use to tag signalling and management voice packets.
		  Only the low order 6 bits are relevant - since that is
		  the size of the DSCP field in IP packets.

		 Default = 24 (decimal) = 0x0018 (hex) = 011000 (binary) - Class Selector 3.

	     For ISAM 4.0.10 -> stays the same as latest FGU4.x.
	     For ISAM4.2, this stays the same as previous ISAM.  "
   
::= { gponVoipServiceEntry  22}


gponVoipServiceConfigFileName  OBJECT-TYPE 
	SYNTAX	OCTET STRING (SIZE(0..49))
	ACCESS	read-write
	STATUS  mandatory
	DESCRIPTION 
		" Used to identify the name of the Planned Configuration File
		  that the VoIP Client must use for VoIP configuration.
		  This file needs to either be embedded in the ONT's
		  default file system, or must be obtained
		  from an external FTP file server.  The name may include
		  both path and file name info, and is case sensitive.

		  First encountered binary 0 (i.e. null terminator) indicates
		  string terminator and remainder will be padded with binary 0's.
		  50th byte is always a null terminator.
   
 		 There is no default value, since this information must be
		 provided by the manager. 

		 Modification is permitted. 

		NOTE: The following attributes are tightly related:
		gponVoipServiceConfigFileName, gponVoipServiceFtpAuthUsername,
		and gponVoipServiceFtpAuthPassword.  From and OMCI standpoint,
		all 3 must be sent to the ONT in that order. This applies to initial VoIP
		Client creation, and subsequently if any one or more of these attributes
		are edited.

	     For ISAM 4.0.10 -> stays the same as latest FGU4.x 
	     For ISAM4.2, this stays the same as previous ISAM.  "
::= { gponVoipServiceEntry  23}

gponVoipServiceClientIdentifier OBJECT-TYPE 
	SYNTAX	OCTET STRING (SIZE(0..25))
	ACCESS	read-write
	STATUS  mandatory
	DESCRIPTION 
		" Used to uniquely identify the VoIP Client.  The ONT uses
		  this field in constructing Option 61 fields in DHCP request.
		  Other than the null value, this field must be unique across all
		  ONTs in the network - so a specific OLT must ensure that it is
		  unique across all ONTs in its domain.

		  From an OMCI standpoint, the OLT will as necessary pad out
		  the OMCI message field to fill in the 25 byte field.

		  NOTE:  The ONT also uses this field when acquiring a SIPPING Server.

		  RULE: If gponVoipServiceConfigMethod = 2 = SIPPING Server AND 
		  gponVoipServiceGwyOption is NOT a PPPoE variety (6, 7), then
		  this attribute cannot be null (i.e. it must be SET by the manager).
   
 		  Default is null value (meaning the ONT should not use Option 61
		  in DHCP requests nor acquire a SIPPING Server).

	     For ISAM 4.0.10 -> stays the same as latest FGU4.x  
	     For ISAM4.2, this stays the same as previous ISAM. 

	As of ISAM5.0, in-service modification of this attribute is SUPPORTED. "
::= { gponVoipServiceEntry  24}


gponVoipServiceCustomerId  OBJECT-TYPE
	SYNTAX 	DisplayString (SIZE(0..64))
	ACCESS	read-write
	STATUS	mandatory
	DESCRIPTION 
		"This is a textual string that the operator can use to
		 identify the customer associated with this service.
 
		 This field is used by the DHCP relay function in the OLT,
		 construct the DHCP Option 82 field.

		 Default - null string. 

		 Modification is permitted.

	     For ISAM 4.0.10 -> this attribute is NOT SUPPORTED. 
	     For ISAM4.2, this stays the same as previous ISAM.  "
	::= { gponVoipServiceEntry  25 }


gponVoipServiceGemPmCollectInd  OBJECT-TYPE
	SYNTAX 	INTEGER
	ACCESS	read-write
	STATUS	mandatory
	DESCRIPTION 
		" This indicates whether GEM Port Performance Monitors
		   should be collected for this VOIP Service (accounts for
		   both ONT-side and OLT-side).
	
		  1 = PM collection enabled
		  2 = PM collection disabled

		 Default = 2 = disabled.

	     For ISAM 4.0.10 -> stays the same as latest FGU4.x  
	     For ISAM4.2, this stays the same as previous ISAM.  "
	::= { gponVoipServiceEntry  26 }

gponVoipServiceGemPmNumPMIntervals  OBJECT-TYPE
	SYNTAX 	INTEGER
	ACCESS	read-only
	STATUS	mandatory
	DESCRIPTION 
		" Indicates the number of rows currently present
		  in the gponVoipServiceGemIntervalTables (both
		  ONT-side and OLT-side).  This
		  is for convenience of the EMS, so that it can
		  quickly determine how many rows should be 
		  uploaded.

	     For ISAM 4.0.10 -> stays the same as latest FGU4.x  
	     For ISAM4.2, this stays the same as previous ISAM.  "
	::= { gponVoipServiceEntry  27 }

gponVoipServiceSecretId OBJECT-TYPE 
	SYNTAX	OCTET STRING (SIZE(0..4))
	ACCESS	read-write
	STATUS  mandatory
	DESCRIPTION 
		" Used to specify the Secret ID.  The ONT uses
		  this field in constructing Option 90 fields in DHCP request.

		  From an OMCI standpoint, the OLT will as necessary pad out
		  the OMCI message field to fill in the 4 byte field.
   
 		  Default is null value (meaning the ONT should not use Option 90
		  in DHCP requests).

	     For ISAM 4.0.10 -> this attribute is NOT SUPPORTED.  
	     For ISAM4.2, this stays the same as previous ISAM. 

	As of ISAM5.0, this attribute is SUPPORTED (because SIPPING config method is SUPPORTED),
	but Modification is NOT permitted. "
::= { gponVoipServiceEntry  28}

gponVoipServiceSecretK OBJECT-TYPE 
	SYNTAX	OCTET STRING (SIZE(0..16))
	ACCESS	read-write
	STATUS  mandatory
	DESCRIPTION 
		" Used to specify the Secret K.  The ONT uses
		  this field in constructing Option 90 fields in DHCP request.

		  From an OMCI standpoint, the OLT will as necessary pad out
		  the OMCI message field to fill in the 16 byte field.  From an OMCI
		  standpoint, the OLT must send an OMCI SET for this attribute
		  after sending any OMCI CREATE or SET message that affects
		  the Secret ID attribute.
   
 		  Default is null value.

	     For ISAM 4.0.10 -> this attribute is NOT SUPPORTED. 
	     For ISAM4.2, this stays the same as previous ISAM. 

	As of ISAM5.0, this attribute is SUPPORTED (because SIPPING config method is SUPPORTED),
	but Modification is NOT permitted. "
::= { gponVoipServiceEntry  29}


gponVoipServiceSourceVlanId  OBJECT-TYPE 
	SYNTAX	INTEGER
	ACCESS	read-write
	STATUS  mandatory
	DESCRIPTION 
		" This attribute specifies the VLAN ID that the ONT should use in the VLAN ID 
		   portion of the tag (for upstream bearer and signalling packets).

		  Range is 0 - 4094.

		  Default = 0 

		  NOTE:  SUPPORTED as of  FGU4.4

		 For ISAM 4.0.10, this attribute is NOT SUPPORTED. 
	     	For ISAM4.2, this stays the same as previous ISAM.  "
::= { gponVoipServiceEntry  30}


gponVoipServiceConfigMethod  OBJECT-TYPE
	SYNTAX 	INTEGER
	ACCESS	read-write
	STATUS	mandatory
	DESCRIPTION 
		"Used to determine the primary method the ONT uses to
		 obtain VoIP configuration information.

		1 = FTP Server (NOTE: With this setting, ONT fetches configuration file from external FTP server
		      and pulls file from outside the OMCI channel).
		2 = SIPPING Server (NOTE: With this setting, the ONT may still access an FTP server for analog 
		      data set info associated with POTS lines, but the primary SIP information is obtained from a
		      SIPPING Server).
		3 = OMCI FTP (NOTE: With this setting, OLT fetches configuration file from external FTP server
		      and pushes file to ONT using the OMCI channel.
		      This codepoint value was introduced in ISAM4.4.02.
		4 = As of ISAM4.4.02, the description for this attribute says following:
			OMCI FTP Complete (NOTE: This method describes the results of the OMCI FTP download,
                             	system will auto change it to 4 after OMCI FTP success, this value is using in
                             	system, user can not get the value (OMCI FTP Complete), if the value is OMCI FTP 
                             	Complete, the system will auto change it to 3 to show for the user).
		      As of ISAM4.5, implementation remains the same as previous ISAM release.

		4 = OMCI FTP Complete.  This codepoint value is used only in conjunction with setting 3 above (i.e. OMCI FTP).
		      It is used to internally to convey that necessary OMCI FTP method download activity is completed.
		      This value is read-only. This value CANNOT be SET by manager, and such attempt should be rejected by OLT.
		      It may be the case that for a manager read operation, the agent may mask the value 4 and instead return a value of 3.
		      This codepoint value was introduced in ISAM4.4.02.
		      As of FTTU 4.8.30, this codepoint is also SUPPORTED.


		NOTE: If gponVoipServiceGwyOption is a PPPoE variety (6, 7), then
		           this attribute is not relevant (can be set to any value).

		Default = 1

	     For ISAM 4.0.10 -> the only supported option is 1 = FTP Server.
	     For ISAM4.2, this stays the same as previous ISAM.
	     As of ISAM4.4.02, codepoint 3 supported. 

	      As of ISAM4.6.01, Modification between method 1 and 3 is permitted.

	As of ISAM5.0, codepoint 2 (SIPPING Server Method)  is SUPPORTED,
	but Modification FROM or TO Sipping method 2 is NOT permitted. "
::= { gponVoipServiceEntry  31 }


gponVoipServiceSippingServerIpAddr  OBJECT-TYPE
	SYNTAX 	IpAddress
	ACCESS	read-write
	STATUS	mandatory
	DESCRIPTION 
		" The manually provisioned IP Address of the
		   SIPPING Server that contains the VoIP configuration info
		  that the ONT needs to acquire.  

		  NOTE:  This attribute is only relevant if gponVoipServiceConfigMethod
		  attribute is set to 2 = SIPPING Server.

		  VALIDATION:  The OLT should prohibit entry of the 
		  following range of IP addresses:
		  224.0.0.0 to 239.255.255.255   (multicast)
    		  127.0.0.0 to 127.255.255.255   (loopback)

		  Default = 0.0.0.0 

		 NOTE:  As of FGU4.4, this attribute is NOT SUPPORTED.

	     	For ISAM 4.0.10 -> stays the same as latest FGU4.x
	     	For ISAM4.2, this stays the same as previous ISAM - NOT SUPPORTED.  "
::= { gponVoipServiceEntry  32 }


gponVoipServiceSippingAuthUsername  OBJECT-TYPE
	SYNTAX 	DisplayString (SIZE(0..25))
	ACCESS	read-write
	STATUS	mandatory
	DESCRIPTION 
		"This is a textual string that contains the Username required for authentication with the
		 SIPPING Server OR for PPPoE authentication.
 
		 NOTE:  This attribute is only relevant if gponVoipServiceConfigMethod
		 attribute is set to 2 = SIPPING Server OR gponVoipServiceGwyOption is a
		 PPPoE variety (6, 7). 

		 Default - null string. 

		 Modification is permitted.

	     For ISAM 4.0.10 -> this attribute is NOT SUPPORTED.
	     For ISAM4.2, this stays the same as previous ISAM.

	As of ISAM5.0, this attribute is SUPPORTED (because SIPPING config method is SUPPORTED)
	As of ISAM5.0, in-service modification of this attribute is SUPPORTED.  "
	::= { gponVoipServiceEntry  33 }


gponVoipServiceSippingAuthPassword  OBJECT-TYPE
	SYNTAX 	DisplayString (SIZE(0..25))
	ACCESS	read-write
	STATUS	mandatory
	DESCRIPTION 
		"This is a textual string that contains the Password required for authentication with the
		 SIPPING Server OR for PPPoE authentication.
 
		 NOTE:  This attribute is only relevant if gponVoipServiceConfigMethod
		 attribute is set to 2 = SIPPING Server OR gponVoipServiceGwyOption is a
		 PPPoE variety (6, 7). 

		 Default - null string. 

		 Modification is permitted.

	     For ISAM 4.0.10 -> this attribute is NOT SUPPORTED. 
	     For ISAM4.2, this stays the same as previous ISAM.

	As of ISAM5.0, this attribute is SUPPORTED (because SIPPING config method is SUPPORTED)
	As of ISAM5.0, in-service modification of this attribute is SUPPORTED.  "
	::= { gponVoipServiceEntry  34 }


gponVoipServiceSippingAuthRealm  OBJECT-TYPE
	SYNTAX 	DisplayString (SIZE(0..25))
	ACCESS	read-write
	STATUS	mandatory
	DESCRIPTION 
		"This is a textual string that contains the Realm for authentication with the
		 SIPPING Server OR for the PPPoE access concentrator name.

 
		 NOTE:  This attribute is only relevant if gponVoipServiceConfigMethod
		 attribute is set to 2 = SIPPING Server OR gponVoipServiceGwyOption is a
		 PPPoE variety (6, 7). 

		 Default - null string. 

		 Modification is permitted.

	     For ISAM 4.0.10 -> this attribute is NOT SUPPORTED. 
	     For ISAM4.2, this stays the same as previous ISAM.

	As of ISAM5.0, this attribute is SUPPORTED (because SIPPING config method is SUPPORTED)
	As of ISAM5.0, in-service modification of this attribute is SUPPORTED.  "
	::= { gponVoipServiceEntry  35 }


gponVoipServiceIpsecEnable OBJECT-TYPE 
	SYNTAX	INTEGER
	ACCESS	read-write
	STATUS  mandatory
	DESCRIPTION 
		" Used to designate whether IPSEC is enabled or 
  		disabled.

 		0 = disabled
  		1 = enabled
   
 		Default = 0 = disabled 

		Modification is NOT permitted.

	     For ISAM 4.0.10 -> this attribute is NOT SUPPORTED.
	     For ISAM4.2, this stays the same as previous ISAM.

	As of ISAM5.0, this attribute is SUPPORTED, but only relevant for SIPPING and FTP config methods.
	Modification is NOT permitted.  "
::= { gponVoipServiceEntry  36}


gponVoipServiceSippingServerAddress	  OBJECT-TYPE
	SYNTAX	AsamProfilePointer
	ACCESS read-write
	STATUS	mandatory
	DESCRIPTION
		"The value of this object identifies the row in the GPON
          		 Large String Profile Table that contains a textual string that contains 
		 the address for acquiring the SIPPING Server. This string can represent
		 a Fully Qualified Domain Name (FQDN), or an IP Address (in dot notation), 
		 or other formats parseable by the ONT.
 
		 NOTE:  This attribute is only relevant if gponVoipServiceConfigMethod
		 attribute is set to 2 = SIPPING Server.

		 Default - null pointer. 

		 Modification is permitted (without having to ADMIN DOWN the service).

	     For ISAM 4.0.10 -> this attribute is NOT SUPPORTED. 
	     For ISAM4.2, this stays the same as previous ISAM. 

	As of ISAM5.0, this attribute is SUPPORTED (along with in-service modification).  But unlike FTTU, this attribute points to a row in
	the gponUriProfileTable. "
	::= { gponVoipServiceEntry  37 }


gponVoipServiceSecondaryNetGwyIpAddr  OBJECT-TYPE
	SYNTAX 	IpAddress
	ACCESS	read-write
	STATUS	mandatory
	DESCRIPTION 
		" The manually provisioned IP Address of the
		  secondary Network Media Gateway. NOTE: If DHCP option
		  is enabled, this provisioned attribute will be overriden
		  by the one obtained by the ONT from the DHCP server.
		  In either case, the value of the attribute actually used by
		  the ONT can be obtained from the 
		  gponVoipServiceOpInfoTable.

		  VALIDATION:  The OLT should prohibit entry of the 
		  following range of IP addresses:
		  224.0.0.0 to 239.255.255.255   (multicast)
    		  127.0.0.0 to 127.255.255.255   (loopback) 

		 SUPPORTED as of FGU4.5.5 

	     For ISAM 4.0.10 -> this attribute is NOT SUPPORTED.
	     For ISAM 4.2 -> this attribute is SUPPORTED, but Modification is NOT supported "
::= { gponVoipServiceEntry  38 }



gponVoipServiceDsRateSchedProfile OBJECT-TYPE
	SYNTAX	AsamProfilePointer
	ACCESS read-write
	STATUS	mandatory
	DESCRIPTION
		" This object is used to reference the appropriate service-based
		 downstream rate limiting profile (in the QOS MIB) -> for
		 service-based downstream rate limiting.

		 Must reference an existing profile.

		 Modification is permitted.

		 This attribute must be set to 1 (i.e. the default) if either of the following:
			- gponOltVoipDownstreamSchedMode scalar attribute is NOT
			  set to 1 = ONT-based.
		    	- bponOntDownstreamRateLimitOption attribute is NOT set to
		    	  1 = Service-based. 

		 Range is 1 - 32.

		 Default = 1 (represents a default profile delivered with the system).

	     	For ISAM 4.0.10, this attribute is NOT SUPPORTED. 
	     	For ISAM4.2, this stays the same as previous ISAM.  "
::= { gponVoipServiceEntry  39 }


gponVoipServiceFtpAuthUsername  OBJECT-TYPE
	SYNTAX 	DisplayString (SIZE(0..25))
	ACCESS	read-write
	STATUS	mandatory
	DESCRIPTION 
		"This is a textual string that contains the Username
		 required for authentication with the FTP Server.

		 Default - null string (meaning ONT should use anonymous)

		 Modification is permitted.

		NOTE: The following attributes are tightly related:
		gponVoipServiceConfigFileName, gponVoipServiceFtpAuthUsername,
		and gponVoipServiceFtpAuthPassword.  From and OMCI standpoint,
		all 3 must be sent to the ONT in that order. This applies to initial VoIP
		Client creation, and subsequently if any one or more of these attributes
		are edited.

	    	For ISAM 4.0.10 -> stays the same as latest FGU4.x  
	     	For ISAM4.2, this stays the same as previous ISAM.  "
	::= { gponVoipServiceEntry  40 }


gponVoipServiceFtpAuthPassword  OBJECT-TYPE
	SYNTAX 	DisplayString (SIZE(0..25))
	ACCESS	read-write
	STATUS	mandatory
	DESCRIPTION 
		"This is a textual string that contains the Password
		 required for authentication with the FTP Server.

		 Default - null string (meaning ONT should use anonymous)

		 Modification is permitted.

		NOTE: The following attributes are tightly related:
		gponVoipServiceConfigFileName, gponVoipServiceFtpAuthUsername,
		and gponVoipServiceFtpAuthPassword.  From and OMCI standpoint,
		all 3 must be sent to the ONT in that order. This applies to initial VoIP
		Client creation, and subsequently if any one or more of these attributes
		are edited.

	    	For ISAM 4.0.10 -> stays the same as latest FGU4.x 
	     	For ISAM4.2, this stays the same as previous ISAM.  "
	::= { gponVoipServiceEntry  41 }


gponVoipServiceSignalVlanId OBJECT-TYPE 
	SYNTAX	INTEGER
	ACCESS	read-write
	STATUS  mandatory
	DESCRIPTION
		"This object is used to reference the S-VLAN ID (in the 
		 L2 subsystem) that carries non-bearer traffic (i.e. signalling
		 and all else other than bearer). 

		 Range is 2 - 4094 and 4096.

		 The value 4096 is treated as null - and means that this separate S-VLAN
		 is not configured for the VoIP service.  Value 4096 means that service 
		 behaves like prior to FGU4.6 (i.e. bearer, signalling and all else carried
		 on the single S-VLAN specified in gponVoipServiceVlanId attribute.
		 NOTE:  This same pre-4.6 behavior (i.e. all traffic VoIP traffic on single VLAN)
		 can also be accomplished by setting this attribute to the same value as
		 the gponVoipServiceVlanId attribute above.

		 VALIDATION: If this value is NOT 4096 AND NOT equal to the value in  
		 gponVoipServiceVlanId attribute, then the associated PQ Profile
		 must specify exactly 2 GEM ports for this VoIP service. 

		 Modification is NOT permitted.
		
		 Default = 4096 (meaning no separate signalling VLAN)

		 Attribute is NOT SUPPORTED.  Was originally added for FGU4.6, and then
		 descoped.

	    	For ISAM 4.0.10 -> stays the same as latest FGU4.x
	     	For ISAM4.2, this stays the same as previous ISAM - NOT SUPPORTED.   "
::= { gponVoipServiceEntry  42 }


gponVoipServiceVlanPointer OBJECT-TYPE 
	SYNTAX	VlanIndex
	ACCESS	read-write
	STATUS  mandatory
	DESCRIPTION
		" This attribute was introduced for ISAM4.0.10.

		This object is used to reference the CVLAN and SVLAN association (in the 
		L2 subsystem) with which this service is associated. 

		 See other ALU proprietary MIBs and documentation for definition of VlanIndex structure.
		
		 No default since value must be supplied by manager.

		 Modification is NOT permitted.
	     	For ISAM4.2, this stays the same as previous ISAM.  "
::= { gponVoipServiceEntry  43}


gponVoipServiceForceOmciXmlDownload OBJECT-TYPE 
	SYNTAX	INTEGER
	ACCESS	read-write
	STATUS  mandatory
	DESCRIPTION
		" This attribute only has relevance if gponVoipServiceConfigMethod = 3
		  (i.e. only if XML download method is via the OMCI channel). 

		 The only valid SET (other than row creation) for this attribute is the value = 1 (meaning a trigger to force unconditional download).
		 For GET, the agent can return value 0 (which is meaningless, since this attribute is really intended to 
			be a trigger, and manager obtains no useful information from a GET).
		 For row creation, the only legitimate value is 0. 


		 When gponVoipServiceConfigMethod = 3 AND this attribute is SET to value = 1,
		 the OLT will force OMCI download of the XML file specified in gponVoipServiceConfigFileName,
		 regardless of whether the ONT already has a file with same name.

		 Modification is SUPPORTED (meaning that SET of the attribute forces the download action).
		
		 Default = 0

		Introduced in ISAM4.6 for MIB readiness.
		As of ISAM4.6.01, attribute is SUPPORTED.   "
::= { gponVoipServiceEntry  44 }




-- *********************************************
-- GPON VOICE OVER IP (VoIP) SERVICE OPINFO TABLE
--
--This table is only used for GPON.
--
-- This table contains operational information regarding a VoIP service
-- for a specific ONT.  These individual services are referred to as
-- VoIP Clients.  The operational information is significant in that
-- each time it is requested, the OLT issues OMCI GET messages   
-- to obtain the latest information directly from the ONT.
-- A table row is created/deleted automatically by the OLT upon  
-- creation/deletion of a Voip Service.
--
-- For ISAM4.0.10, this table is being re-used.  
-- Noted which attributes are relevant for ISAM4.0.10
--
--
-- For ISAM4.2, this table is being reused.
-- Noted which attributes are relevant for ISAM4.2.
--
--	For GPON - SUPPORTED as of ISAM4.0.10
--	For XG-PON1 - SUPPORTED as of ISAM4.6.02
--  For NG-PON2 - SUPPORTED as of ISAM5.4.01
--  
--
-- *********************************************

gponVoipServiceOpInfoTable OBJECT-TYPE
	SYNTAX	SEQUENCE OF GponVoipServiceOpInfoEntry
	ACCESS	not-accessible
	STATUS	mandatory
	DESCRIPTION
		"This object contains a table that contains Voip
		information for a specific Voip Service obtained 
		directly from a specific ONT.  "
::= { gponServicesGroup 3 }

gponVoipServiceOpInfoEntry OBJECT-TYPE
	SYNTAX 	GponVoipServiceOpInfoEntry
	ACCESS	not-accessible
	STATUS	mandatory
	DESCRIPTION
		"Rows of this table contain Voip service information. "
	INDEX {gponVoipServiceOpInfoUniIndex }
::= {gponVoipServiceOpInfoTable 1}

GponVoipServiceOpInfoEntry ::=
	SEQUENCE { 
		gponVoipServiceOpInfoUniIndex		IfIndex,
		gponVoipServiceOpInfoNetGwyIpAddr		IpAddress,
		gponVoipServiceOpInfoDefaltNextHopAddr	IpAddress,
		gponVoipServiceOpInfoClientIpAddr		IpAddress,
		gponVoipServiceOpInfoClientSubnetMask	IpAddress,
		gponVoipServiceOpInfoFtpServerIpAddr	IpAddress,
		gponVoipServiceOpInfoActualConfigFileName	OCTET STRING,
		gponVoipServiceOpInfoActualConfigFileVersion	OCTET STRING,
		gponVoipServiceOpInfoVoipSwVersion		OCTET STRING,
		gponVoipServiceOpInfoProfileDownloadStatus	DisplayString
}

gponVoipServiceOpInfoUniIndex OBJECT-TYPE 
	SYNTAX IfIndex
	ACCESS read-only
	STATUS mandatory
	DESCRIPTION
	    "This index is the ifIndex of the VoIP UNI.

	     For ISAM 4.0.10 -> this is an ONT UNI ifIndex 
 	     with the ontSlot/ontPort fields = 15/15.
	     For ISAM4.2, this stays the same as previous ISAM.  "
::= { gponVoipServiceOpInfoEntry  1 }


gponVoipServiceOpInfoNetGwyIpAddr  OBJECT-TYPE
	SYNTAX 	IpAddress
	ACCESS	read-only
	STATUS	mandatory
	DESCRIPTION 
		" The IP Address of the
		    Network Media Gateway. 
		   Default = 0.0.0.0

	    	For ISAM 4.0.10 -> stays the same as latest FGU4.x 
	     	For ISAM4.2, this stays the same as previous ISAM.  "
::= { gponVoipServiceOpInfoEntry  2 }


gponVoipServiceOpInfoDefaltNextHopAddr  OBJECT-TYPE
	SYNTAX 	IpAddress
	ACCESS	read-only
	STATUS	mandatory
	DESCRIPTION 
		" The default next hop 
		   IP Address used by the VoIP Client.
		   Default = 0.0.0.0

	    	For ISAM 4.0.10 -> stays the same as latest FGU4.x 
	     	For ISAM4.2, this stays the same as previous ISAM.   "
::= { gponVoipServiceOpInfoEntry  3 }


gponVoipServiceOpInfoClientIpAddr  OBJECT-TYPE
	SYNTAX 	IpAddress
	ACCESS	read-only
	STATUS	mandatory
	DESCRIPTION 
		" The IP Address of the
		   ONT VoIP Client. 
		   Default = 0.0.0.0

	    	For ISAM 4.0.10 -> stays the same as latest FGU4.x 
	     	For ISAM4.2, this stays the same as previous ISAM.  "
::= { gponVoipServiceOpInfoEntry  4 }


gponVoipServiceOpInfoClientSubnetMask  OBJECT-TYPE
	SYNTAX 	IpAddress
	ACCESS	read-only
	STATUS	mandatory
	DESCRIPTION 
		" The subnet mask for
		   the VoIP client's subnet.
		   Default = 0.0.0.0

	    	For ISAM 4.0.10 -> stays the same as latest FGU4.x 
	     	For ISAM4.2, this stays the same as previous ISAM.  "
::= { gponVoipServiceOpInfoEntry  5 }


gponVoipServiceOpInfoFtpServerIpAddr  OBJECT-TYPE
	SYNTAX 	IpAddress
	ACCESS	read-only
	STATUS	mandatory
	DESCRIPTION 
		" The IP Address of the
		   FTP Server that contains the VoIP configuration files
		   that the ONT needs to download. 
		   Default = 0.0.0.0 

	    	For ISAM 4.0.10 -> stays the same as latest FGU4.x 
	     	For ISAM4.2, this stays the same as previous ISAM.   "
::= { gponVoipServiceOpInfoEntry  6 }


gponVoipServiceOpInfoActualConfigFileName  OBJECT-TYPE 
	SYNTAX	OCTET STRING (SIZE(0..49))
	ACCESS	read-only
	STATUS  mandatory
	DESCRIPTION 
		" Used to identify the name of the Actual Configuration File
		  that the VoIP Client is using for VoIP configuration.
		  The name includes both path and file name info, and is 
		  case sensitive.

		  When requested by the manager, the OLT must use OMCI 
		  get commands to retrieve this directly from the ONT.

		  Default = null 

	    	For ISAM 4.0.10 -> stays the same as latest FGU4.x 
	     	For ISAM4.2, this stays the same as previous ISAM.  "
::= { gponVoipServiceOpInfoEntry  7 }


gponVoipServiceOpInfoActualConfigFileVersion  OBJECT-TYPE 
	SYNTAX	OCTET STRING (SIZE (4))
	ACCESS	read-only
	STATUS  mandatory
	DESCRIPTION 
		" Used to identify the XML file (i.e. Config file) version
		  currently being used by this ONT's VoIP Client. 

		  This attribute consists of 4 octets (32 bits) as follows
		  (consider 1st octet as high-order and 4th octet as low-order):
		  1st - Major Version (version number ranges 1 - 254, and special values - see below)
		  2nd - Minor version (version number ranges 0 - 254, and special values - see below)
		  3rd - Reserved (not used except for special values - see below)
		  4th - Reserved (not used except for special values - see below)

		  Following special values have following special meanings:

		  All 0's =  (32 binary zeros) means UNKNOWN because OLT cannot
		  	  communicate with ONT.  This value can also be reported
			  directly from ONT if no XML file was downloaded.

		  All 1's =  (32 binary ones) means ONT does not support this attribute.
		  	  OLT can deduce this either because ONT reported this value
			  directly via OMCI, or because ONT rejected the OMCI GET
		  	  request for this attribute.

		  When requested by the manager, the OLT must use OMCI 
		  get commands to retrieve this directly from the ONT.

		  Default = All 0's (see above)

	    	For ISAM 4.0.10 -> stays the same as latest FGU4.x 
	     	For ISAM4.2, this stays the same as previous ISAM.  "
::= { gponVoipServiceOpInfoEntry  8 }


gponVoipServiceOpInfoVoipSwVersion  OBJECT-TYPE 
	SYNTAX	OCTET STRING (SIZE (4))
	ACCESS	read-only
	STATUS  mandatory
	DESCRIPTION 
		" Used to identify the VoIP software version
		  currently running for this ONT's VoIP Client. 

		  This attribute consists of 4 octets (32 bits) as follows
		  (consider 1st octet as high-order and 4th octet as low-order):
		  1st - Major Version (version number ranges 1 - 254, and special values - see below)
		  2nd - Minor version (version number ranges 0 - 254, and special values - see below)
		  3rd - Reserved (not used except for special values - see below)
		  4th - Reserved (not used except for special values - see below)

		  Following special values have following special meanings:

		  All 0's =  (32 binary zeros) means UNKNOWN because OLT cannot
		  	  communicate with ONT.  

		  All 1's =  (32 binary ones) means ONT does not support this attribute.
		  	  OLT can deduce this either because ONT reported this value
			  directly via OMCI, or because ONT rejected the OMCI GET
		  	  request for this attribute.

		  When requested by the manager, the OLT must use OMCI 
		  get commands to retrieve this directly from the ONT.

		  Default = All 0's (see above) 

	    	For ISAM 4.0.10 -> stays the same as latest FGU4.x 
	     	For ISAM4.2, this stays the same as previous ISAM. "
::= { gponVoipServiceOpInfoEntry  9 }


gponVoipServiceOpInfoProfileDownloadStatus  OBJECT-TYPE 
	SYNTAX	DisplayString
	ACCESS	read-only
	STATUS  mandatory
	DESCRIPTION 
		" Used to retrieve the profile download status of VOIP Client profiles such as
         Trust Anchor and Local Network Profiles. The status can be OKAY, PENDING or FAILED
         in ASCII format for each profile separated by delimiters of '\n'. The order of the
         profiles is always Trust Anchor followed by Local Network. The size is defined as 
         255 chars so that we may add other profile statuses in future  without changing the MIB."
::= { gponVoipServiceOpInfoEntry  10 }


-- *********************************************
--
-- VOIP SERVICE ONT-SIDE GEM PERFORMANCE MONITOR CURRENT INTERVAL TABLE
--
-- This is a new table beginning with FGU4.2.
-- This current interval table contains various statistics collected for 
-- ONT GEM ports (ONT-side) during the current 15 minute interval 
-- of operation.  
--
-- An instance of this table is auto-created/deleted in accordance with the 
-- 'PM Collect Indicator' setting of the VOIP Service.
--
-- For GETs of table attributes, the OLT must go directly to the ONT (via OMCI)
-- in order to acquire fresh current counts. 
--
-- NOTE: The ONT itself doesn't have knowledge about the individual GEM
-- ports that comprise a VOIP Service - this is known only by the OLT.  But 
-- the ONT keeps the GEM PM counts on a GEM port basis.  Therefore, the
-- OLT must collect and sum the individual GEM port PMs for each of the 
-- GEM ports associated with the VOIP service.  The GEM port PM summations
-- are recorded in this table.
--
-- For ISAM4.0.10, this table is being re-used. 
-- Noted which attributes are relevant for ISAM4.0.10.
--
-- For ISAM4.2, this table is being re-used. 
-- Noted which attributes are relevant for ISAM4.2.
--
--	For GPON - SUPPORTED as of ISAM4.0.10
--	For XG-PON1 - SUPPORTED as of ISAM4.6.02
--  For NG-PON2 - SUPPORTED as of ISAM5.4.01
--  
-- 
-- *********************************************


gponVoipServiceOntsideGemCurrentIntervalTable  OBJECT-TYPE
	SYNTAX SEQUENCE OF GponVoipServiceOntsideGemCurrentIntervalEntry
	ACCESS	not-accessible
	STATUS	mandatory
	::= { gponServicesGroup 6 }


gponVoipServiceOntsideGemCurrentIntervalEntry  OBJECT-TYPE
	SYNTAX 	GponVoipServiceOntsideGemCurrentIntervalEntry
	ACCESS	not-accessible
	STATUS	mandatory
	DESCRIPTION 
		"An entry in the GPON Voip Service GEM PM
		 CurrentInterval Table. "
	INDEX	{ gponVoipServiceOntsideGemCurrentIntervalUniIndex }
	::= { gponVoipServiceOntsideGemCurrentIntervalTable 1 }

GponVoipServiceOntsideGemCurrentIntervalEntry ::= SEQUENCE {
	gponVoipServiceOntsideGemCurrentIntervalUniIndex			IfIndex,
	gponVoipServiceOntsideGemCurrentIntervalValidInd			Boolean,
	gponVoipServiceOntsideGemCurrentIntervalLostFragsDown			Counter,
	gponVoipServiceOntsideGemCurrentIntervalLostFragsUp			Counter,
	gponVoipServiceOntsideGemCurrentIntervalReceiveFrags		Counter,
	gponVoipServiceOntsideGemCurrentIntervalReceiveBlocks		Counter,
	gponVoipServiceOntsideGemCurrentIntervalTransmitBlocks		Counter,
	gponVoipServiceOntsideGemCurrentIntervalTransmitFrags		Counter
}


gponVoipServiceOntsideGemCurrentIntervalUniIndex  OBJECT-TYPE
	SYNTAX 	IfIndex
	ACCESS	read-only
	STATUS	mandatory
	DESCRIPTION 
		"This index is the ifIndex of the VoIP UNI.

	     For ISAM 4.0.10 ->  this is an ONT UNI ifIndex 
 	     with the ontSlot/ontPort fields = 15/15.
	     For ISAM4.2, this stays the same as previous ISAM.  "
	::= { gponVoipServiceOntsideGemCurrentIntervalEntry 1 }


gponVoipServiceOntsideGemCurrentIntervalValidInd  OBJECT-TYPE
	SYNTAX 	Boolean
	ACCESS	read-only
	STATUS	mandatory
	DESCRIPTION 
		"Indicates whether or not this CurrentInterval contains
		 valid PM counts.

		 As of FGU4.2, NOT SUPPORTED

		For ISAM 4.0.10 -> stays the same as latest FGU4.x
	     	For ISAM4.2, this stays the same as previous ISAM.   "
	::= { gponVoipServiceOntsideGemCurrentIntervalEntry 2 }


gponVoipServiceOntsideGemCurrentIntervalLostFragsDown  OBJECT-TYPE
	SYNTAX 	Counter
	ACCESS	read-only
	STATUS	mandatory
	DESCRIPTION 
		"A count of Lost GEM Fragments (downstream).

		For ISAM 4.0.10 -> stays the same as latest FGU4.x
	     	For ISAM4.2, this stays the same as previous ISAM.  "
	::= { gponVoipServiceOntsideGemCurrentIntervalEntry 3 }

gponVoipServiceOntsideGemCurrentIntervalLostFragsUp  OBJECT-TYPE
	SYNTAX 	Counter
	ACCESS	read-only
	STATUS	mandatory
	DESCRIPTION 
		"A count of Lost GEM Fragments (upstream).

		For ISAM 4.0.10 -> stays the same as latest FGU4.x
	     	For ISAM4.2, this stays the same as previous ISAM.  "
	::= { gponVoipServiceOntsideGemCurrentIntervalEntry 4 }

gponVoipServiceOntsideGemCurrentIntervalReceiveFrags  OBJECT-TYPE
	SYNTAX 	Counter
	ACCESS	read-only
	STATUS	mandatory
	DESCRIPTION 
		"A count of Received GEM Fragments.

		For ISAM 4.0.10 -> stays the same as latest FGU4.x
	     	For ISAM4.2, this stays the same as previous ISAM.  "
	::= { gponVoipServiceOntsideGemCurrentIntervalEntry 5 }


gponVoipServiceOntsideGemCurrentIntervalReceiveBlocks  OBJECT-TYPE
	SYNTAX 	Counter
	ACCESS	read-only
	STATUS	mandatory
	DESCRIPTION 
		"A count of Received GEM Blocks.

		For ISAM 4.0.10 -> stays the same as latest FGU4.x
	     	For ISAM4.2, this stays the same as previous ISAM.  "
	::= { gponVoipServiceOntsideGemCurrentIntervalEntry 6 }


gponVoipServiceOntsideGemCurrentIntervalTransmitBlocks  OBJECT-TYPE
	SYNTAX 	Counter
	ACCESS	read-only
	STATUS	mandatory
	DESCRIPTION 
		"A count of Transmitted GEM Blocks.

		For ISAM 4.0.10 -> stays the same as latest FGU4.x
	     	For ISAM4.2, this stays the same as previous ISAM.  "
	::= { gponVoipServiceOntsideGemCurrentIntervalEntry 7 }


gponVoipServiceOntsideGemCurrentIntervalTransmitFrags  OBJECT-TYPE
	SYNTAX 	Counter
	ACCESS	read-only
	STATUS	mandatory
	DESCRIPTION 
		"A count of Transmitted GEM Fragments.

		For ISAM 4.0.10 -> stays the same as latest FGU4.x
	     	For ISAM4.2, this stays the same as previous ISAM.  "
	::= { gponVoipServiceOntsideGemCurrentIntervalEntry 8 }

-- *********************************************
--
-- VOIP SERVICE ONT-SIDE GEM PERFORMANCE MONITOR INTERVAL TABLE
--
-- This is a new table beginning with FGU4.2.
-- This interval table contains various GEM port statistics collected
-- at an ONT over the previous 8 hours of operation.  The past 8 hours are
-- broken into 32 completed 15 minute intervals.  Each row in this table
-- represents one such interval associated with a VoIP service.
--
-- An instance of this table is auto-created/deleted in accordance with the 
-- 'PM Collect Indicator' setting of the VOIP Service.
--
-- NOTE: The ONT itself doesn't have knowledge about the individual GEM
-- ports that comprise a VoIP Service - this is known only by the OLT.  But 
-- the ONT keeps the GEM PM counts on a GEM port basis.  Therefore, the
-- OLT must collect and sum the individual GEM port PMs for each of the 
-- GEM ports associated with the VoIP service.  The GEM port PM summations
-- are recorded in this table.
--
-- For ISAM4.0.10, this table is being re-used. 
-- Noted which attributes are relevant for ISAM4.0.10.
--
-- For ISAM4.2, this table is being re-used. 
-- Noted which attributes are relevant for ISAM4.2.
--
--	For GPON - SUPPORTED as of ISAM4.0.10
--	For XG-PON1 - SUPPORTED as of ISAM4.6.02
--  For NG-PON2 - SUPPORTED as of ISAM5.4.01
--  
-- 
-- *********************************************


gponVoipServiceOntsideGemIntervalTable  OBJECT-TYPE
	SYNTAX SEQUENCE OF GponVoipServiceOntsideGemIntervalEntry
	ACCESS	not-accessible
	STATUS	mandatory
	::= { gponServicesGroup 7 }


gponVoipServiceOntsideGemIntervalEntry  OBJECT-TYPE
	SYNTAX 	GponVoipServiceOntsideGemIntervalEntry
	ACCESS	not-accessible
	STATUS	mandatory
	DESCRIPTION 
		"An entry in the GPON Voip Service GEM PM
		 Interval Table. "
	INDEX	{ gponVoipServiceOntsideGemIntervalUniIndex, 
		  gponVoipServiceOntsideGemIntervalNumber }
	::= { gponVoipServiceOntsideGemIntervalTable 1 }

GponVoipServiceOntsideGemIntervalEntry ::= SEQUENCE {
	gponVoipServiceOntsideGemIntervalUniIndex			IfIndex,
	gponVoipServiceOntsideGemIntervalNumber			INTEGER,
	gponVoipServiceOntsideGemIntervalValidInd			Boolean,
	gponVoipServiceOntsideGemIntervalLostFragsDown			Counter,
	gponVoipServiceOntsideGemIntervalLostFragsUp			Counter,
	gponVoipServiceOntsideGemIntervalReceiveFrags		Counter,
	gponVoipServiceOntsideGemIntervalReceiveBlocks		Counter,
	gponVoipServiceOntsideGemIntervalTransmitBlocks		Counter,
	gponVoipServiceOntsideGemIntervalTransmitFrags		Counter
}


gponVoipServiceOntsideGemIntervalUniIndex  OBJECT-TYPE
	SYNTAX 	IfIndex
	ACCESS	read-only
	STATUS	mandatory
	DESCRIPTION 
		"This index is the ifIndex of the VoIP UNI.

	     For ISAM 4.0.10 -> this is an ONT UNI ifIndex 
 	     with the ontSlot/ontPort fields = 15/15.
	     For ISAM4.2, this stays the same as previous ISAM. "
	::= { gponVoipServiceOntsideGemIntervalEntry 1 }


gponVoipServiceOntsideGemIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.

		For ISAM 4.0.10 -> stays the same as latest FGU4.x
	     	For ISAM4.2, this stays the same as previous ISAM.  "
	::= { gponVoipServiceOntsideGemIntervalEntry 2 }

gponVoipServiceOntsideGemIntervalValidInd  OBJECT-TYPE
	SYNTAX 	Boolean
	ACCESS	read-only
	STATUS	mandatory
	DESCRIPTION 
		"Indicates whether or not this interval contains
		 valid PM counts. 

		 As of FGU4.2, NOT SUPPORTED

		For ISAM 4.0.10 -> stays the same as latest FGU4.x
	     	For ISAM4.2, this stays the same as previous ISAM. "
	::= { gponVoipServiceOntsideGemIntervalEntry 3 }


gponVoipServiceOntsideGemIntervalLostFragsDown  OBJECT-TYPE
	SYNTAX 	Counter
	ACCESS	read-only
	STATUS	mandatory
	DESCRIPTION 
		"A count of Lost GEM Fragments (downstream).

		For ISAM 4.0.10 -> stays the same as latest FGU4.x
	     	For ISAM4.2, this stays the same as previous ISAM. "
	::= { gponVoipServiceOntsideGemIntervalEntry 4 }

gponVoipServiceOntsideGemIntervalLostFragsUp  OBJECT-TYPE
	SYNTAX 	Counter
	ACCESS	read-only
	STATUS	mandatory
	DESCRIPTION 
		"A count of Lost GEM Fragments (upstream).

		For ISAM 4.0.10 -> stays the same as latest FGU4.x
	     	For ISAM4.2, this stays the same as previous ISAM. "
	::= { gponVoipServiceOntsideGemIntervalEntry 5 }

gponVoipServiceOntsideGemIntervalReceiveFrags  OBJECT-TYPE
	SYNTAX 	Counter
	ACCESS	read-only
	STATUS	mandatory
	DESCRIPTION 
		"A count of Received GEM Fragments.

		For ISAM 4.0.10 -> stays the same as latest FGU4.x
	     	For ISAM4.2, this stays the same as previous ISAM. "
	::= { gponVoipServiceOntsideGemIntervalEntry 6 }


gponVoipServiceOntsideGemIntervalReceiveBlocks  OBJECT-TYPE
	SYNTAX 	Counter
	ACCESS	read-only
	STATUS	mandatory
	DESCRIPTION 
		"A count of Received GEM Blocks.

		For ISAM 4.0.10 -> stays the same as latest FGU4.x
	     	For ISAM4.2, this stays the same as previous ISAM. "
	::= { gponVoipServiceOntsideGemIntervalEntry 7 }


gponVoipServiceOntsideGemIntervalTransmitBlocks  OBJECT-TYPE
	SYNTAX 	Counter
	ACCESS	read-only
	STATUS	mandatory
	DESCRIPTION 
		"A count of Transmitted GEM Blocks.

		For ISAM 4.0.10 -> stays the same as latest FGU4.x
	     	For ISAM4.2, this stays the same as previous ISAM. "
	::= { gponVoipServiceOntsideGemIntervalEntry 8 }


gponVoipServiceOntsideGemIntervalTransmitFrags  OBJECT-TYPE
	SYNTAX 	Counter
	ACCESS	read-only
	STATUS	mandatory
	DESCRIPTION 
		"A count of Transmitted GEM Fragments.

		For ISAM 4.0.10 -> stays the same as latest FGU4.x
	     	For ISAM4.2, this stays the same as previous ISAM. "
	::= { gponVoipServiceOntsideGemIntervalEntry 9 }

-- *********************************************
--
-- VOIP SERVICE OLT-SIDE GEM PERFORMANCE MONITOR CURRENT INTERVAL TABLE
--
-- This is a new table beginning with FGU4.2.
-- This current interval table contains various statistics collected for 
-- ONT GEM ports (OLT-side) during the current 15 minute interval 
-- of operation.  
--
-- An instance of this table is auto-created/deleted in accordance with the 
-- 'PM Collect Indicator' setting of the VOIP Service.
--
--
-- NOTE: The OLT must collect and sum the individual GEM port PMs for each of the 
-- GEM ports associated with the VOIP service.  The GEM port PM summations
-- are recorded in this table.
--
-- For ISAM4.0.10, this table is being re-used. 
-- Noted which attributes are relevant for ISAM4.0.10.
--
-- For ISAM4.2, this table is being re-used. 
-- Noted which attributes are relevant for ISAM4.2.
--
--	For GPON - SUPPORTED as of ISAM4.0.10
--	For XG-PON1 - SUPPORTED as of ISAM4.6.02
--  For NG-PON2 - SUPPORTED as of ISAM5.4.01
--  
-- 
-- *********************************************


gponVoipServiceOltsideGemCurrentIntervalTable  OBJECT-TYPE
	SYNTAX SEQUENCE OF GponVoipServiceOltsideGemCurrentIntervalEntry
	ACCESS	not-accessible
	STATUS	mandatory
	::= { gponServicesGroup 10 }


gponVoipServiceOltsideGemCurrentIntervalEntry  OBJECT-TYPE
	SYNTAX 	GponVoipServiceOltsideGemCurrentIntervalEntry
	ACCESS	not-accessible
	STATUS	mandatory
	DESCRIPTION 
		"An entry in the GPON Voip Service GEM PM
		 CurrentInterval Table. "
	INDEX	{ gponVoipServiceOltsideGemCurrentIntervalUniIndex }
	::= { gponVoipServiceOltsideGemCurrentIntervalTable 1 }

GponVoipServiceOltsideGemCurrentIntervalEntry ::= SEQUENCE {
	gponVoipServiceOltsideGemCurrentIntervalUniIndex			IfIndex,
	gponVoipServiceOltsideGemCurrentIntervalValidInd			Boolean,
	gponVoipServiceOltsideGemCurrentIntervalLostFragsDown			Counter,
	gponVoipServiceOltsideGemCurrentIntervalLostFragsUp			Counter,
	gponVoipServiceOltsideGemCurrentIntervalReceiveFrags		Counter,
	gponVoipServiceOltsideGemCurrentIntervalReceiveBlocks		Counter,
	gponVoipServiceOltsideGemCurrentIntervalTransmitBlocks		Counter,
	gponVoipServiceOltsideGemCurrentIntervalTransmitFrags		Counter
}


gponVoipServiceOltsideGemCurrentIntervalUniIndex  OBJECT-TYPE
	SYNTAX 	IfIndex
	ACCESS	read-only
	STATUS	mandatory
	DESCRIPTION 
		"This index is the ifIndex of the VoIP UNI.

	     For ISAM 4.0.10 -> this is an ONT UNI ifIndex 
 	     with the ontSlot/ontPort fields = 15/15.
	     For ISAM4.2, this stays the same as previous ISAM. "
	::= { gponVoipServiceOltsideGemCurrentIntervalEntry 1 }


gponVoipServiceOltsideGemCurrentIntervalValidInd  OBJECT-TYPE
	SYNTAX 	Boolean
	ACCESS	read-only
	STATUS	mandatory
	DESCRIPTION 
		"Indicates whether or not this CurrentInterval contains
		 valid PM counts. 

		 As of FGU4.2, NOT SUPPORTED

		For ISAM 4.0.10 -> stays the same as latest FGU4.x
	     	For ISAM4.2, this stays the same as previous ISAM.  "
	::= { gponVoipServiceOltsideGemCurrentIntervalEntry 2 }


gponVoipServiceOltsideGemCurrentIntervalLostFragsDown  OBJECT-TYPE
	SYNTAX 	Counter
	ACCESS	read-only
	STATUS	mandatory
	DESCRIPTION 
		"A count of Lost GEM Fragments (downstream).

		 As of FGU4.2, NOT SUPPORTED

		For ISAM 4.0.10 -> stays the same as latest FGU4.x
	     	For ISAM4.2, this stays the same as previous ISAM. "
	::= { gponVoipServiceOltsideGemCurrentIntervalEntry 3 }

gponVoipServiceOltsideGemCurrentIntervalLostFragsUp  OBJECT-TYPE
	SYNTAX 	Counter
	ACCESS	read-only
	STATUS	mandatory
	DESCRIPTION 
		"A count of Lost GEM Fragments (upstream).

		For ISAM 4.0.10 -> stays the same as latest FGU4.x
	     	For ISAM4.2, this stays the same as previous ISAM. "
	::= { gponVoipServiceOltsideGemCurrentIntervalEntry 4 }

gponVoipServiceOltsideGemCurrentIntervalReceiveFrags  OBJECT-TYPE
	SYNTAX 	Counter
	ACCESS	read-only
	STATUS	mandatory
	DESCRIPTION 
		"A count of Received GEM Fragments.

		For ISAM 4.0.10 -> stays the same as latest FGU4.x
	     	For ISAM4.2, this stays the same as previous ISAM. "
	::= { gponVoipServiceOltsideGemCurrentIntervalEntry 5 }


gponVoipServiceOltsideGemCurrentIntervalReceiveBlocks  OBJECT-TYPE
	SYNTAX 	Counter
	ACCESS	read-only
	STATUS	mandatory
	DESCRIPTION 
		"A count of Received GEM Blocks.

		For ISAM 4.0.10 -> stays the same as latest FGU4.x
	     	For ISAM4.2, this stays the same as previous ISAM. "
	::= { gponVoipServiceOltsideGemCurrentIntervalEntry 6 }


gponVoipServiceOltsideGemCurrentIntervalTransmitBlocks  OBJECT-TYPE
	SYNTAX 	Counter
	ACCESS	read-only
	STATUS	mandatory
	DESCRIPTION 
		"A count of Transmitted GEM Blocks.

		For ISAM 4.0.10 -> stays the same as latest FGU4.x
	     	For ISAM4.2, this stays the same as previous ISAM. "
	::= { gponVoipServiceOltsideGemCurrentIntervalEntry 7 }


gponVoipServiceOltsideGemCurrentIntervalTransmitFrags  OBJECT-TYPE
	SYNTAX 	Counter
	ACCESS	read-only
	STATUS	mandatory
	DESCRIPTION 
		"A count of Transmitted GEM Fragments.

		For ISAM 4.0.10 -> stays the same as latest FGU4.x
	     	For ISAM4.2, this stays the same as previous ISAM. "
	::= { gponVoipServiceOltsideGemCurrentIntervalEntry 8 }

-- *********************************************
--
-- VOIP SERVICE OLT-SIDE GEM PERFORMANCE MONITOR INTERVAL TABLE
--
-- This is a new table beginning with FGU4.2.
-- This interval table contains various GEM port statistics collected
-- for a VoIP Service over the previous 8 hours of operation.  The past 8 hours are
-- broken into 32 completed 15 minute intervals.  Each row in this table
-- represents one such interval associated with a VoIP service.
--
-- An instance of this table is auto-created/deleted in accordance with the 
-- 'PM Collect Indicator' setting of the VOIP Service.
--
-- NOTE: The OLT must collect and sum the individual GEM port PMs for each of the 
-- GEM ports associated with the VoIP service.  The GEM port PM summations
-- are recorded in this table.
--
-- For ISAM4.0.10, this table is being re-used. 
-- Noted which attributes are relevant for ISAM4.0.10.
--
-- For ISAM4.2, this table is being re-used. 
-- Noted which attributes are relevant for ISAM4.2.
--
--	For GPON - SUPPORTED as of ISAM4.0.10
--	For XG-PON1 - SUPPORTED as of ISAM4.6.02
--  For NG-PON2 - SUPPORTED as of ISAM5.4.01
--  
-- 
-- *********************************************


gponVoipServiceOltsideGemIntervalTable  OBJECT-TYPE
	SYNTAX SEQUENCE OF GponVoipServiceOltsideGemIntervalEntry
	ACCESS	not-accessible
	STATUS	mandatory
	::= { gponServicesGroup 11 }


gponVoipServiceOltsideGemIntervalEntry  OBJECT-TYPE
	SYNTAX 	GponVoipServiceOltsideGemIntervalEntry
	ACCESS	not-accessible
	STATUS	mandatory
	DESCRIPTION 
		"An entry in the GPON Voip Service GEM PM
		 Interval Table. "
	INDEX	{ gponVoipServiceOltsideGemIntervalUniIndex, 
		  gponVoipServiceOltsideGemIntervalNumber }
	::= { gponVoipServiceOltsideGemIntervalTable 1 }

GponVoipServiceOltsideGemIntervalEntry ::= SEQUENCE {
	gponVoipServiceOltsideGemIntervalUniIndex			IfIndex,
	gponVoipServiceOltsideGemIntervalNumber			INTEGER,
	gponVoipServiceOltsideGemIntervalValidInd			Boolean,
	gponVoipServiceOltsideGemIntervalLostFragsDown			Counter,
	gponVoipServiceOltsideGemIntervalLostFragsUp			Counter,
	gponVoipServiceOltsideGemIntervalReceiveFrags		Counter,
	gponVoipServiceOltsideGemIntervalReceiveBlocks		Counter,
	gponVoipServiceOltsideGemIntervalTransmitBlocks		Counter,
	gponVoipServiceOltsideGemIntervalTransmitFrags		Counter
}


gponVoipServiceOltsideGemIntervalUniIndex  OBJECT-TYPE
	SYNTAX 	IfIndex
	ACCESS	read-only
	STATUS	mandatory
	DESCRIPTION 
		"This index is the ifIndex of the VoIP UNI.

	     For ISAM 4.0.10 -> this is an ONT UNI ifIndex 
 	     with the ontSlot/ontPort fields = 15/15.
	     For ISAM4.2, this stays the same as previous ISAM. "
	::= { gponVoipServiceOltsideGemIntervalEntry 1 }


gponVoipServiceOltsideGemIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.

		For ISAM 4.0.10 -> stays the same as latest FGU4.x
	     	For ISAM4.2, this stays the same as previous ISAM.  "
	::= { gponVoipServiceOltsideGemIntervalEntry 2 }

gponVoipServiceOltsideGemIntervalValidInd  OBJECT-TYPE
	SYNTAX 	Boolean
	ACCESS	read-only
	STATUS	mandatory
	DESCRIPTION 
		"Indicates whether or not this interval contains
		 valid PM counts. 

		 As of FGU4.2, NOT SUPPORTED

		For ISAM 4.0.10 -> stays the same as latest FGU4.x
	     	For ISAM4.2, this stays the same as previous ISAM.  "
	::= { gponVoipServiceOltsideGemIntervalEntry 3 }


gponVoipServiceOltsideGemIntervalLostFragsDown  OBJECT-TYPE
	SYNTAX 	Counter
	ACCESS	read-only
	STATUS	mandatory
	DESCRIPTION 
		"A count of Lost GEM Fragments (downstream).

		 As of FGU4.2, NOT SUPPORTED

		For ISAM 4.0.10 -> stays the same as latest FGU4.x
	     	For ISAM4.2, this stays the same as previous ISAM. "
	::= { gponVoipServiceOltsideGemIntervalEntry 4 }

gponVoipServiceOltsideGemIntervalLostFragsUp  OBJECT-TYPE
	SYNTAX 	Counter
	ACCESS	read-only
	STATUS	mandatory
	DESCRIPTION 
		"A count of Lost GEM Fragments (upstream).

		For ISAM 4.0.10 -> stays the same as latest FGU4.x
	     	For ISAM4.2, this stays the same as previous ISAM. "
	::= { gponVoipServiceOltsideGemIntervalEntry 5 }

gponVoipServiceOltsideGemIntervalReceiveFrags  OBJECT-TYPE
	SYNTAX 	Counter
	ACCESS	read-only
	STATUS	mandatory
	DESCRIPTION 
		"A count of Received GEM Fragments.

		For ISAM 4.0.10 -> stays the same as latest FGU4.x
	     	For ISAM4.2, this stays the same as previous ISAM. "
	::= { gponVoipServiceOltsideGemIntervalEntry 6 }


gponVoipServiceOltsideGemIntervalReceiveBlocks  OBJECT-TYPE
	SYNTAX 	Counter
	ACCESS	read-only
	STATUS	mandatory
	DESCRIPTION 
		"A count of Received GEM Blocks.

		For ISAM 4.0.10 -> stays the same as latest FGU4.x
	     	For ISAM4.2, this stays the same as previous ISAM. "
	::= { gponVoipServiceOltsideGemIntervalEntry 7 }


gponVoipServiceOltsideGemIntervalTransmitBlocks  OBJECT-TYPE
	SYNTAX 	Counter
	ACCESS	read-only
	STATUS	mandatory
	DESCRIPTION 
		"A count of Transmitted GEM Blocks.

		For ISAM 4.0.10 -> stays the same as latest FGU4.x
	     	For ISAM4.2, this stays the same as previous ISAM. "
	::= { gponVoipServiceOltsideGemIntervalEntry 8 }


gponVoipServiceOltsideGemIntervalTransmitFrags  OBJECT-TYPE
	SYNTAX 	Counter
	ACCESS	read-only
	STATUS	mandatory
	DESCRIPTION 
		"A count of Transmitted GEM Fragments.

		For ISAM 4.0.10 -> stays the same as latest FGU4.x
	     	For ISAM4.2, this stays the same as previous ISAM. "
	::= { gponVoipServiceOltsideGemIntervalEntry 9 }


-- *********************************************
-- GPON CES SERVICE TABLE
--
--This table is only used for GPON.
--
-- This table contains information regarding a CES service for
-- a specific ONT CES UNI.  If fractional DS1/E1 is supported, there can be
-- up to 24 services (for DS1) or 31 services (for E1).  
--
-- FGU4.3 only supports a single fractional service per CES UNI.
-- Therefore, for FGU4.3, only a single service per UNI is supported.
-- Rows are created by the operator.
--
-- For ISAM4.0.10, this table is being re-used. 
-- Noted which attributes are relevant for ISAM4.0.10.
--
-- For ISAM4.2, support of this table remains the same as ISAM4.0.10.
--
-- Prior to ISAM4.6.01, this table was used ONLY to provision CES Pseudowire service
-- (over Ethernet - L2).  As of ISAM4.6.01, this table is ALSO used to provision CES
-- Pseudowire service (over IP - L3).  Descriptions with individual table attributes (below)
-- indicate whether attribute is relevant:
--	only for L2
--	only for L3
--	for both L2 and L3
--
--	For GPON - SUPPORTED as of ISAM4.0.10
--	For XG-PON1 - SUPPORTED as of ISAM4.6.02
--	For NG-PON2 - NOT SUPPORTED as of ISAM5.2 (CES Card Type NOT SUPPORTED)
--  
--
-- *********************************************

gponCesServiceTable OBJECT-TYPE
	SYNTAX	SEQUENCE OF GponCesServiceEntry
	ACCESS	not-accessible
	STATUS	mandatory
	DESCRIPTION
		"This object contains a table for creating and storing
		information regarding a CES service for an ONT
		physical UNI. 

		Relevant for both L2 and L3. "
::= { gponServicesGroup 12 }

gponCesServiceEntry OBJECT-TYPE
	SYNTAX 	GponCesServiceEntry
	ACCESS	not-accessible
	STATUS	mandatory
	DESCRIPTION
		"Rows of this table contain Ces service information. "
	INDEX {gponCesServiceUniIndex ,
		gponCesServiceNumber }
::= {gponCesServiceTable 1}

GponCesServiceEntry ::=
	SEQUENCE { 
		gponCesServiceUniIndex		IfIndex,
		gponCesServiceNumber		INTEGER,
		gponCesServiceUpBwProfile		AsamProfilePointer,
		gponCesServiceDownBwProfile	AsamProfilePointer,
		gponCesServicePQProfile		AsamProfilePointer,
		gponCesServiceRowStatus 		RowStatus,
		gponCesServiceVlanId		INTEGER,
		gponCesServiceAesEnableInd		INTEGER,
		gponCesServiceLabel		OCTET STRING,
		gponCesServiceAdminState		AdminState,
		gponCesServiceOperState		OperState,
		gponCesServiceGemPmCollectInd	INTEGER,
		gponCesServiceGemPmNumPMIntervals	INTEGER,
		gponCesServiceSignalling			INTEGER,
		gponCesServiceDs0TimeslotMap		OCTET STRING,
		gponCesServicePayloadSize		INTEGER,
		gponCesServicePayloadEncapDelay	INTEGER,
		gponCesServiceTimingMode		INTEGER,
		gponCesServiceTransmitCircuitId	OCTET STRING,
		gponCesServiceExpectedCircuitId	OCTET STRING,
		gponCesServiceMaintenanceProfile	AsamProfilePointer,
		gponCesServiceDestinationMacAddress	OCTET STRING,
		gponCesServiceSourceVlanId	INTEGER,
		gponCesServicePWPmCollectInd	INTEGER,
		gponCesServicePWPmNumPMIntervals	INTEGER,
		gponCesServiceLoopback		INTEGER,
		gponCesServiceRtpEnableInd	INTEGER,
		gponCesServiceDsRateSchedProfile	AsamProfilePointer,
		gponCesServiceVlanPointer		VlanIndex,
		gponCesServiceUnderlyingTransportInd	INTEGER,
		gponCesServiceTcpUdpPortNum	INTEGER,
		gponCesServiceDscpSetting		INTEGER,
		gponCesServiceFarEndIpInfo		DisplayString,
		gponCesServiceRtpClockReference	INTEGER,
		gponCesServiceRtpTimeStampMode	INTEGER,
		gponCesServiceRtpPtypePayloadChannel	INTEGER,
		gponCesServiceRtpPtypeSignalChannel	INTEGER,
		gponCesServiceRtpSyncSourcePayloadChannel		INTEGER,
		gponCesServiceRtpSyncSourceSignalChannel	INTEGER,
		gponCesServiceRtpExpectedPtypePayloadChannel	INTEGER,
		gponCesServiceRtpExpectedPtypeSignalChannel	INTEGER,
		gponCesServiceRtpExpectedSyncSourcePayloadChannel		INTEGER,
		gponCesServiceRtpExpectedSyncSourceSignalChannel	INTEGER
}

gponCesServiceUniIndex OBJECT-TYPE 
	SYNTAX IfIndex
	ACCESS read-only
	STATUS mandatory
	DESCRIPTION
	    "This index is the ifIndex of the ONT CES UNI.

	     For ISAM 4.0.10 -> stays the same as latest FGU4.x

	As of ISAM4.6.01, relevant for both L2 and L3. "
::= { gponCesServiceEntry 1}

gponCesServiceNumber 	OBJECT-TYPE 
	SYNTAX	INTEGER
	ACCESS read-only
	STATUS mandatory
	DESCRIPTION
	    "This table index is the number of the service on the CES UNI.
		
		For FGU4.3, this value must be 1 (i.e. only a single service per CES UNI).

	     For ISAM 4.0.10 -> stays the same as latest FGU4.x

	As of ISAM4.6.01, relevant for both L2 and L3.  "
::= {gponCesServiceEntry 2}

gponCesServiceUpBwProfile OBJECT-TYPE
	SYNTAX	AsamProfilePointer
	ACCESS read-write
	STATUS	mandatory
	DESCRIPTION
		" The value of this object identifies the row in the GPON
          		 Bandwidth Profile Table that applies for the upstream side
		 of this particular service.

		 Modification is permitted (without having to ADMIN DOWN the service).

		As of ISAM 4.0.10, this attribute is NOT SUPPORTED.  "
::= { gponCesServiceEntry  3}


gponCesServiceDownBwProfile OBJECT-TYPE
	SYNTAX	AsamProfilePointer
	ACCESS read-write
	STATUS	mandatory
	DESCRIPTION
		" The value of this object identifies the row in the GPON
          		 Bandwidth Profile Table that applies for the downstream side
		 of this particular service.

		 Modification is permitted (without having to ADMIN DOWN the service).

		As of ISAM 4.0.10, this attribute is NOT SUPPORTED. "
::= { gponCesServiceEntry  4}


gponCesServicePQProfile OBJECT-TYPE
	SYNTAX	AsamProfilePointer
	ACCESS read-write
	STATUS	mandatory
	DESCRIPTION
		" The value of this object identifies the row in the GPON
          		 Priority Queue Profile Table that applies for the upstream
		 aspects of this particular service. 

		 NOTE: PQ Profile can only specify a single GEM port.

		As of ISAM 4.0.10, this attribute is NOT SUPPORTED.  "
::= { gponCesServiceEntry  5}

gponCesServiceRowStatus OBJECT-TYPE 
	SYNTAX	RowStatus
	ACCESS	read-write
	STATUS  mandatory
	DESCRIPTION
		"This object is used to create a new row or modify or
         		delete an existing row in this table.

	     For ISAM 4.0.10 -> stays the same as latest FGU4.x

	As of ISAM4.6.01, relevant for both L2 and L3. "
::= { gponCesServiceEntry  6}

gponCesServiceVlanId OBJECT-TYPE 
	SYNTAX	INTEGER
	ACCESS	read-write
	STATUS  mandatory
	DESCRIPTION
		"This object is used to reference the S-VLAN ID (in the 
		 L2 subsystem) with which this service is associated.
 
		 Range is 2 - 4090.
		
		 No default since value must be supplied by manager.

		As of ISAM 4.0.10, this attribute is NOT SUPPORTED. "
::= { gponCesServiceEntry  7}

gponCesServiceAesEnableInd OBJECT-TYPE 
	SYNTAX	INTEGER
	ACCESS	read-write
	STATUS  mandatory
	DESCRIPTION 
		" Used to designate whether AES encryption is enabled
  		or disabled for this service. This encryption decision applies
		to the GEM port that ultimately get associated with the
		service. 

 		1 = enabled
  		2 = disabled
   
 		 Default = 2 = disabled

		As of ISAM 4.0.10, this attribute is NOT SUPPORTED. "
::= { gponCesServiceEntry  8}


gponCesServiceLabel  OBJECT-TYPE
	SYNTAX 	OCTET STRING (SIZE(0..20))
	ACCESS	read-write
	STATUS	mandatory
	DESCRIPTION 
		"This is a 20 byte free-form textual field that the
		  operator can use to label this particular service.
 
		 Default - null string. 

		 Modification is permitted.

	     For ISAM 4.0.10 -> stays the same as latest FGU4.x

	As of ISAM4.6.01, relevant for both L2 and L3.  "
	::= { gponCesServiceEntry  9 }


gponCesServiceAdminState  OBJECT-TYPE
	SYNTAX 	AdminState
	ACCESS	read-write
	STATUS	mandatory
	DESCRIPTION 
		" For L2, setting it to 'locked' causes OLT to stop
		  sending upstream allocation grants 
		  associated with this service.

		  For L3, setting it to 'locked' merely causes OLT
		  to temporarily clear any alarm associated with the 
		  service (e.g. service mismatch alarm). 
		 
		 Default = 0 = unlocked.

		 Modification is permitted.

	     For ISAM 4.0.10 -> stays the same as latest FGU4.x

	As of ISAM4.6.01, relevant for both L2 and L3.  "
	::= {  gponCesServiceEntry  10 }

gponCesServiceOperState  OBJECT-TYPE
	SYNTAX 	OperState
	ACCESS	read-only
	STATUS	mandatory
	DESCRIPTION 
		"Indicates operational state of the
		  service. State is related to ability of service
		  to perform its function (e.g. whether service
		  affecting alarm is present).

		  Default = 0 = Enabled 

	     For ISAM 4.0.10 -> stays the same as latest FGU4.x

	As of ISAM4.6.01, relevant for both L2 and L3. "
	::= { gponCesServiceEntry  11  }


gponCesServiceGemPmCollectInd  OBJECT-TYPE
	SYNTAX 	INTEGER
	ACCESS	read-write
	STATUS	mandatory
	DESCRIPTION 
		" This indicates whether GEM Port performance Monitors
		  should be collected for this Ces Service (accounts for both
		  ONT-side and OLT-side).
	
		  1 = PM collection enabled
		  2 = PM collection disabled

		 Default = 2 = disabled. 


		For ISAM 4.0.10 -> stays the same as latest FGU4.x

	As of ISAM4.6.01, relevant only for L2.  "
	::= { gponCesServiceEntry  12 }

gponCesServiceGemPmNumPMIntervals  OBJECT-TYPE
	SYNTAX 	INTEGER
	ACCESS	read-only
	STATUS	mandatory
	DESCRIPTION 
		" Indicates the number of rows currently present
		  in the gponCesServiceGemIntervalTable (both 
		  ONT-side and OLT-side).  This
		  is for convenience of the EMS, so that it can
		  quickly determine how many rows should be 
		  uploaded. 


		For ISAM 4.0.10 -> stays the same as latest FGU4.x

	As of ISAM4.6.01, relevant only for L2.  "
	::= { gponCesServiceEntry  13 }

gponCesServiceSignalling OBJECT-TYPE 
	SYNTAX	INTEGER
	ACCESS	read-write
	STATUS  mandatory
	DESCRIPTION 
		" Optionas are as follows:

		0 - no signalling visible at this layer (Default) - permitted for both L2 and L3
		1 - CAS, to be carried in the same packet stream as the payload - permitted only for L3
		2 - CAS, to be carried in a separate signalling channel - permitted only for L2
 
		FGU4.3 only uses options 0 and 2.

		 Modification is NOT PERMITTED.

	     For ISAM 4.0.10 -> stays the same as latest FGU4.x

	As of ISAM4.6.01, relevant for both L2 and L3. "
::= { gponCesServiceEntry  14}


gponCesServiceDs0TimeslotMap  OBJECT-TYPE
	SYNTAX 	OCTET STRING (SIZE(4))
	ACCESS	read-write
	STATUS	mandatory
	DESCRIPTION 
		"This is a bitmap that represents the DS0s
		 that will be transported from the associated
		 DS1/E1.  This bitmap corresponds to the first
		 4 bytes in Table 8 of G983.2 for the Logical
		 Nx64kbit/s Sub-port Connection Termination
		 Point ME.  

		 VALIDITY RULE: This bitmap is only relevant and
		 only required if the CES port has been designated
		 to operate in Structured mode.

		 For a DS1, only the first 3 bytes
		 (i.e. 24 DS0 timeslots) of the bitmap are
		 relevant. The 4th byte must be coded as zeroes.
		 The 4th byte becomes relevant when the CES port
		 operates in E1 mode (i.e. 32 DS0 timeslots). 

		 VALIDITY RULE: If the line is configured as E1 (structured)
		 with PCM30 Framing, then timeslots 0 and 16 cannot be
		 specified for usage.

		 VALIDITY RULE: If the line is configured as E1 (structured)
		 with PCM31 Framing, then timeslot 0 cannot be
		 specified for usage.

		 Default = 0xFFFFFF00 (meaning all 24 DS0s
		 are transported.

		 Supported for FGU4.3 - since fractionals are supported.

		 NOTE: Any edit of this parameter is service-affecting.

	     For ISAM 4.0.10 -> stays the same as latest FGU4.x

	As of ISAM4.6.01, relevant for both L2 and L3. "
	::= { gponCesServiceEntry  15 }

gponCesServicePayloadSize OBJECT-TYPE 
	SYNTAX	INTEGER
	ACCESS	read-write
	STATUS  mandatory
	DESCRIPTION 
		" Number of payload bytes per packet. Valid only if service type = unstructured. 
		  Valid choices depend on the TDM service, but must include the following. 
		  Other choices are at the vendor's discretion.

		  DS1 ->192
		  DS1 ->	200 required only if unstructured octet aligned service is supported - NOT SUPPORTED
		  E1   ->	256

		  FGU4.3 only uses DS1 (192) and E1 (256).

		  Modification is NOT PERMITTED.

	     For ISAM 4.0.10 -> stays the same as latest FGU4.x

	As of ISAM4.6.01, relevant for both L2 and L3. "
::= { gponCesServiceEntry  16}

gponCesServicePayloadEncapDelay OBJECT-TYPE 
	SYNTAX	INTEGER
	ACCESS	read-write
	STATUS  mandatory
	DESCRIPTION 
		" Number of 125 microsecond frames to be encapsulated in each pseudowire packet. 
		  Valid only if service type = structured. Valid choices for various TDM services are listed below,
		  and are affected by the possible presence of in-band signalling. 

		  For NxDS0, no signalling, N = 1 -> use 64 (8 ms) 
		  For NxDS0, no signalling, N = 2..4 -> use 32 (4 ms)
		  For NxDS0, no signalling, N = >4 -> use 8 (1 ms)
		  For NxDS0 with DS1 CAS -> use 16 (2 ms) or 24 (3 ms)
		  For NxDS0 with E1 CAS -> use 16 (2 ms) 

		  Prior to ISAM4.6.01T -  valid values are limited to 8, 16, 24, 32 and 64.
		  As of ISAM4.6.01 - valid range is 8 to 64.

		  NOTE: OLT should enforce the following VALIDITY RULE:
		  Max Jitter Delay in msec > 1.5 * (payload length in frames) * 0.125

		  No default - must be provided by operator.

		  NOTE: Any edit of this parameter is service-affecting.

	     For ISAM 4.0.10 -> stays the same as latest FGU4.x

	As of ISAM4.6.01, relevant for both L2 and L3. "
::= { gponCesServiceEntry  17}


gponCesServiceTimingMode OBJECT-TYPE 
	SYNTAX	INTEGER
	ACCESS	read-write
	STATUS  mandatory
	DESCRIPTION 
		" This attribute selects the timing mode of the TDM service. 

		  0 - network timing
		  1 - differential timing
		  2 - adaptive timing (Default)
		  3 - loop timing: local TDM transmit clock derived from local TDM receive stream

		 NOTE:  Timing mode selection must be the same for every CES Service in a single ONT.

		 NOTE: If timing mode selection is differential timing, then gponCesServiceRtpEnableInd
		           must be set to enabled. 

		 NOTE: Any edit of this parameter is service-affecting. 

	     For ISAM 4.0.10 -> stays the same as latest FGU4.x

	As of ISAM4.6.01, relevant for both L2 and L3. "
::= { gponCesServiceEntry  18}


gponCesServiceTransmitCircuitId OBJECT-TYPE 
	SYNTAX	OCTET STRING (SIZE(8))
	ACCESS	read-write
	STATUS  mandatory
	DESCRIPTION 
		" This attribute is a pair of ECID (Ethernet circuit ID) values that the ONT transmits in the
		  direction from the TDM termination toward the packet-switched network. Legal MEF8 ECIDs 
		  lie in the range 1-1048575 (2^20 -1). To allow for the possibility of other transport (L2TP) in the future,
		  each ECID is allocated 4 bytes.  The first value is used for the payload ECID; the second is used 
		  for the optional separate signalling ECID. The first ECID is required for all MEF8 pseudowires; 
		  the second is required only if signalling is to be carried in a distinct channel. If signalling is not 
		  present, or is carried in the same channel as the payload, the second ECID should be set to the
		  special value 0.

		  NOTE: For L2, the payload ECID part cannot be 0. Other than the zero value for the signalling ECID part, all
		  ECID parts (payload and signalling) must be unique across all Transmit ECID parts across all CES 
		  Services within a single ONT. 

		  NOTE: For L2, any edit of this parameter is service-affecting.

		  For L2, No Default - must be provided by operator.
		  For L3, Default = all zeroes (since attribute is irrelevant)

	     For ISAM 4.0.10 -> stays the same as latest FGU4.x

	As of ISAM4.6.01, relevant only for L2. "
::= { gponCesServiceEntry  19 }

gponCesServiceExpectedCircuitId OBJECT-TYPE 
	SYNTAX	OCTET STRING (SIZE(8))
	ACCESS	read-write
	STATUS  mandatory
	DESCRIPTION 
		" This attribute is a pair of ECID (Ethernet circuit ID) values that the ONT can expect in the direction
		  from the packet-switched network toward the TDM termination. Checking ECIDs may be a way to 
		  detect circuit misconnection. MEF8 ECIDs lie in the range 1-1048575 (2^20 -1). To allow for the 
		  possibility of other transport (L2TP) in the future, each ECID is allocated 4 bytes.
		  The first value is used for the payload ECID; the second is used for the optional separate signalling 
		  ECID. For both payload and signalling ECID parts, the special value 0 indicates that no ECID checking
		  is expected. 

		  NOTE:  Other than the special zero value for either payload or signalling ECID parts, all
		  ECID parts (payload and signalling) must be unique across all Expected ECID parts across all CES 
		  Services within a single ONT. 

		  NOTE: Any edit of this parameter is service-affecting.

		  Default = all zeroes.

	     For ISAM 4.0.10 -> stays the same as latest FGU4.x

	As of ISAM4.6.01, relevant only for L2. "
::= { gponCesServiceEntry  20 }

gponCesServiceMaintenanceProfile OBJECT-TYPE
	SYNTAX	AsamProfilePointer
	ACCESS read-write
	STATUS	mandatory
	DESCRIPTION
		" The value of this object identifies the row in the GPON
          		 CES Maintenance Profile Table that applies for this CES Service.

		 If the pointer has its default value 0, the ONT's internal defaults apply.

		 Modification is permitted.

		 NOTE: Some attributes of Maintenance Profile must be the same across
		            all CES Services for the same ONT.  Check Maintenance Profile
		            for attributes that fall in that category.

		 Default = 0 = null pointer

		 NOTE: Any edit of this parameter is service-affecting.

	     For ISAM 4.0.10 -> stays the same as latest FGU4.x

	As of ISAM4.6.01, relevant for both L2 and L3. "
::= {gponCesServiceEntry  21 }


gponCesServiceDestinationMacAddress  OBJECT-TYPE 
	SYNTAX	OCTET STRING (SIZE(6))
	ACCESS	read-write
	STATUS  mandatory
	DESCRIPTION 
		" This attribute specifies the MAC address of the destination Ethernet frames.

		  Default = all zeroes.

		  NOTE: Any edit of this parameter is service-affecting.

	     For ISAM 4.0.10 -> stays the same as latest FGU4.x

	As of ISAM4.6.01, relevant only for L2. "
::= { gponCesServiceEntry  22 }


gponCesServiceSourceVlanId  OBJECT-TYPE 
	SYNTAX	INTEGER
	ACCESS	read-write
	STATUS  mandatory
	DESCRIPTION 
		" This attribute specifies the VLAN ID that the ONT should use in the VLAN ID 
		   portion of the tag (for upstream frames).

		   Range is 0 - 4095.

		  Default = 0

		   NOTE: Any edit of this parameter is service-affecting.

		 As of  ISAM 4.0.10, this attribute is NOT SUPPORTED.  "
::= { gponCesServiceEntry  23 }


gponCesServicePWPmCollectInd  OBJECT-TYPE
	SYNTAX 	INTEGER
	ACCESS	read-write
	STATUS	mandatory
	DESCRIPTION 
		" This indicates whether CES pseudowire performance monitors
		  should be collected for this CES Service.
	
		  1 = PM collection enabled
		  2 = PM collection disabled

		 Default = 2 = disabled.

	     For ISAM 4.0.10 -> stays the same as latest FGU4.x

	As of ISAM4.6.01, relevant for both L2 and L3.   "
	::= { gponCesServiceEntry  24 }

gponCesServicePWPmNumPMIntervals  OBJECT-TYPE
	SYNTAX 	INTEGER
	ACCESS	read-only
	STATUS	mandatory
	DESCRIPTION 
		" Indicates the number of rows currently present
		  in the gponCesServicePWIntervalTable.  This
		  is for convenience of the EMS, so that it can
		  quickly determine how many rows should be 
		  uploaded. 

	     For ISAM 4.0.10 -> stays the same as latest FGU4.x

	As of ISAM4.6.01, relevant for both L2 and L3.  "
	::= { gponCesServiceEntry  25 }


gponCesServiceLoopback  OBJECT-TYPE
	SYNTAX 	INTEGER
	ACCESS	read-write
	STATUS	mandatory
	DESCRIPTION 
		" This attribute is used to set the loopback configuration as follows:  
		  0 = No loopback  Loopback
		  1 = Loopback of downstream traffic at MAC client.  
		  uploaded.  

		  Default = 0 (no loopback)
		
		  NOT SUPPORTED for FGU4.3.

	     As of  ISAM 4.0.10 -> stays the same as latest FGU4.x - NOT SUPPORTED.  "
	::= { gponCesServiceEntry  26 }


gponCesServiceRtpEnableInd OBJECT-TYPE 
	SYNTAX	INTEGER
	ACCESS	read-write
	STATUS  mandatory
	DESCRIPTION 
		" Used to designate whether RTP is enabled
  		or disabled for this service. 

 		1 = enabled
  		2 = disabled
   
 		Default = 2 = disabled 

		NOTE: If timing mode selection is differential timing, then this attribute must be set to
		           enabled. 

		NOTE: Any edit of this parameter is service-affecting.

		From an OMCI perspective, the enable setting implies creation of the 
		RTP Pseudowires Parameters ME.

	     For ISAM 4.0.10 -> stays the same as latest FGU4.x

	As of ISAM4.6.01, relevant for both L2 and L3. "
::= { gponCesServiceEntry  27}


gponCesServiceDsRateSchedProfile OBJECT-TYPE
	SYNTAX	AsamProfilePointer
	ACCESS read-write
	STATUS	mandatory
	DESCRIPTION
		" This object is used to reference the appropriate service-based
		 downstream rate limiting profile (in the QOS MIB) -> for
		 service-based downstream rate limiting.

		 Must reference an existing profile.

		 Modification is permitted. 

		 NOTE: This attribute must be set to 1 (i.e. the default) if bponOntDownstreamRateLimitOption
		 attribute is NOT set to 1 = Service-based.

		 Range is 1 - 32.

		 Default = 1 (represents a default profile delivered with system).

		 As of ISAM 4.0.10, this attribute is NOT SUPPORTED.   "
::= { gponCesServiceEntry  28}


gponCesServiceVlanPointer OBJECT-TYPE 
	SYNTAX	VlanIndex
	ACCESS	read-write
	STATUS  mandatory
	DESCRIPTION
		" This attribute was introduced for ISAM4.0.10.

		This object is used to reference the CVLAN and SVLAN association (in the 
		VLAN subsystem) with which this service is associated. 

		NOTE: 	For L2 CES service, this referenced VLAN is associated with physical CES UNI port.
			For L3 CES service, this referenced VLAN is associated with an IpHost virtual UNI.

		 See other ALU proprietary MIBs and documentation for definition of VlanIndex structure.
		
		 No default since value must be supplied by manager.

		 Modification is NOT permitted.

	As of ISAM4.6.01, relevant for both L2 and L3. "
::= { gponCesServiceEntry  29 }


gponCesServiceUnderlyingTransportInd OBJECT-TYPE 
	SYNTAX	INTEGER
	ACCESS	read-write
	STATUS  mandatory
	DESCRIPTION 
		" Used to designate the type of underlying transport used for this CES pseudowire service. 

 		0 = Etherent - (herein referred to as L2)
  		1 = UDP/IP - (herein referred to as L3)
   
 		Default = 0 = Etherent - (herein referred to as L2)

		 Modification is NOT permitted.
 
	Introduced in ISAM4.6 for MIB readiness.
	As of ISAM4.6.0, relevant for both L2 and L3. "
::= { gponCesServiceEntry  30 }


gponCesServiceTcpUdpPortNum OBJECT-TYPE
	SYNTAX 	INTEGER
	ACCESS	read-write
	STATUS	mandatory
	DESCRIPTION 
		" Specifies the source UDP Port number to be used for this L3 CES service.

		  Valid range is 49152 thru 65535 and the value 2142.

		  VALIDATION:  For L3, CES IP services that share the same source IP address
				(i.e. same row in IpHostConfigTable) must have different source UDP port numbers.

		If L2, Default = 2142 (and attribute is irrelavant)
		If L3, No Default - must be provided by operator.

		 Modification is NOT SUPPORTED.

	Introduced in ISAM4.6 for MIB readiness.
	As of ISAM4.6.01, relevant only for L3. "
::= { gponCesServiceEntry  31 }

gponCesServiceDscpSetting  OBJECT-TYPE
	SYNTAX 	INTEGER
	ACCESS	read-write
	STATUS	mandatory
	DESCRIPTION 
		" Specifies the value of the DSCP field of the IP header for pseudowire packets associated
		  with this L3 CES service..

		  Only the low order 6 bits are relevant - since that is
		  the size of the DSCP field in IP packets.

 		 Default = 46 (decimal) = 0x002E (hex) = 101110 (binary) - Expedited Forwarding.

		  Modification is SUPPORTED.

	Introduced in ISAM4.6 for MIB readiness.
	As of ISAM4.6.01, relevant only for L3. "
::= { gponCesServiceEntry  32  }

gponCesServiceFarEndIpInfo OBJECT-TYPE 
	SYNTAX  DisplayString
	ACCESS	read-write
	STATUS	mandatory
	DESCRIPTION 
		" This is a textual string that represents the URI of the far-end termination point.

		  Maximum string size is 50 bytes.

		  NOTE:  From an OMCI standpoint, the OLT must create a Large String ME with this information.

		  The following are examples of the required format
		  (i.e must have udp:// part, resolvable IP address part, colon and UDP port number part). 
		  udp://192.168.100.221:5000
		  udp://pwe3srvr.int.example.net:2222

		If L2, Default = null string (and attribute is irrelavant)
		If L3, No Default - must be provided by operator.

		  Modification is SUPPORTED.

	Introduced in ISAM4.6 for MIB readiness.
	As of ISAM4.6.01, relevant only for L3.   "
::= { gponCesServiceEntry  33 }


gponCesServiceRtpClockReference OBJECT-TYPE 
	SYNTAX	INTEGER
	ACCESS	read-write
	STATUS  mandatory
	DESCRIPTION 
		" Used to specify the frequency of the common timing reference (in multiples of 8 kHz).
  		or disabled for this service. 

 		This attribute is only relevant if both of the following:
			1) gponCesServiceRtpEnableInd attribute is set to 1 = enabled.
			2) the CES service is type L3

		Range is 0 - 1000 (8 mHz)
   
 		Value 0 means ONT can choose it's internal policy 

		Default = 0. 

		NOTE: Any edit of this parameter is service-affecting.

	Introduced in ISAM4.6 for MIB readiness.
	As of ISAM4.6.01, relevant only for L3. "
::= { gponCesServiceEntry  34 }


gponCesServiceRtpTimeStampMode OBJECT-TYPE 
	SYNTAX	INTEGER
	ACCESS	read-write
	STATUS  mandatory
	DESCRIPTION 
		" Used to specify the mode in which RTP timestamps are generated in the TDM to PSN direction.
  		or disabled for this service. 

 		This attribute is only relevant if both of the following:
			1) gponCesServiceRtpEnableInd attribute is set to 1 = enabled.
			2) the CES service is type L3

 		0 = Unknown or Not Applicable (default)
		1 = Absolute - meaning timestamps are based on the timing of the incoming TDM signal.
		2 = Differential - meaning timestamps are based on the ONT's reference clock, which is understood to be 
		      stratum-traceable along with the reference clock at the far-end.

		NOTE: Any edit of this parameter is service-affecting.

	Introduced in ISAM4.6 for MIB readiness.
	As of ISAM4.6.01, relevant only for L3. "
::= { gponCesServiceEntry  35 }

gponCesServiceRtpPtypePayloadChannel OBJECT-TYPE 
	SYNTAX	INTEGER
	ACCESS	read-write
	STATUS  mandatory
	DESCRIPTION 
		" This attribute specifies the RTP payload type (PTYPE) for the payload channel in the TDM to PSN direction. 

 		This attribute is only relevant if both of the following:
			1) gponCesServiceRtpEnableInd attribute is set to 1 = enabled.
			2) the CES service is type L3

		NOTE: Any edit of this parameter is service-affecting.

		Range is 96..127 (Default = 96)

	Introduced in ISAM4.6 for MIB readiness.
	As of ISAM4.6.01, relevant only for L3. "
::= { gponCesServiceEntry  36 }

gponCesServiceRtpPtypeSignalChannel OBJECT-TYPE 
	SYNTAX	INTEGER
	ACCESS	read-write
	STATUS  mandatory
	DESCRIPTION 
		" This attribute specifies the RTP payload type (PTYPE) for the optional signalling channel in the TDM to PSN direction. 
		  If signalling is not transported in its own channel, this value should be set to 0.

 		This attribute is only relevant if both of the following:
			1) gponCesServiceRtpEnableInd attribute is set to 1 = enabled.
			2) the CES service is type L3

		NOTE: Any edit of this parameter is service-affecting.

		As of ISAM4.6.01, zero (0) is the only supported value.
		Default = 0.

	Introduced in ISAM4.6 for MIB readiness.
	As of ISAM4.6.01, relevant only for L3. "
::= { gponCesServiceEntry  37 }

gponCesServiceRtpSyncSourcePayloadChannel OBJECT-TYPE 
	SYNTAX	INTEGER
	ACCESS	read-write
	STATUS  mandatory
	DESCRIPTION 
		" This attribute specifies the RTP synchronization source for the payload channel in the TDM to PSN direction.  

 		This attribute is only relevant if both of the following:
			1) gponCesServiceRtpEnableInd attribute is set to 1 = enabled.
			2) the CES service is type L3

		 Range is 0..65535 (Default = 0)

		NOTE: Any edit of this parameter is service-affecting.

	Introduced in ISAM4.6 for MIB readiness.
	As of ISAM4.6.01, relevant only for L3. "
::= { gponCesServiceEntry  38 }

gponCesServiceRtpSyncSourceSignalChannel OBJECT-TYPE 
	SYNTAX	INTEGER
	ACCESS	read-write
	STATUS  mandatory
	DESCRIPTION 
		" This attribute specifies the RTP synchronization source for the optional signalling channel in the TDM to PSN direction.  
		  If signalling is not transported in its own channel, this value should be set to 0.

 		This attribute is only relevant if both of the following:
			1) gponCesServiceRtpEnableInd attribute is set to 1 = enabled.
			2) the CES service is type L3

		NOTE: Any edit of this parameter is service-affecting.

		As of ISAM4.6.01, zero (0) is the only supported value.
		Default = 0.

	Introduced in ISAM4.6 for MIB readiness.
	As of ISAM4.6.01, relevant only for L3. "
::= { gponCesServiceEntry  39 }


gponCesServiceRtpExpectedPtypePayloadChannel OBJECT-TYPE 
	SYNTAX	INTEGER
	ACCESS	read-write
	STATUS  mandatory
	DESCRIPTION 
		" This attribute specifies the RTP payload type (PTYPE) for the payload channel in the PSN to TDM direction. 
		 The received payload type may be used to detect malformed packets.  
		 To disable the check function, set the corresponding value to its default value 0.  

			1) gponCesServiceRtpEnableInd attribute is set to 1 = enabled.
			2) the CES service is type L3

		NOTE: Any edit of this parameter is service-affecting.

		Range is 0..127 (Default = 0)

	Introduced in ISAM4.6 for MIB readiness.
	As of ISAM4.6.01, relevant only for L3. "
::= { gponCesServiceEntry  40 }

gponCesServiceRtpExpectedPtypeSignalChannel OBJECT-TYPE 
	SYNTAX	INTEGER
	ACCESS	read-write
	STATUS  mandatory
	DESCRIPTION 
		" This attribute specifies the RTP payload type (PTYPE) for the optional signalling in the PSN to TDM direction. 
		 The received payload type may be used to detect malformed packets.  
		 To disable the check function, set the corresponding value to its default value 0.  

			1) gponCesServiceRtpEnableInd attribute is set to 1 = enabled.
			2) the CES service is type L3

		NOTE: Any edit of this parameter is service-affecting.

		As of ISAM4.6.01, zero (0) is the only supported value.
		Default = 0.

	Introduced in ISAM4.6 for MIB readiness.
	As of ISAM4.6.01, relevant only for L3. "
::= { gponCesServiceEntry  41 }



gponCesServiceRtpExpectedSyncSourcePayloadChannel OBJECT-TYPE 
	SYNTAX	INTEGER
	ACCESS	read-write
	STATUS  mandatory
	DESCRIPTION 
		" This attribute specifies the RTP synchronization source for the payload channel in the PSN to TDM direction.
		 The received SSRC may be used to detect misconnection (stray packets).  
		 To disable the check function, set the corresponding value to its default value 0.  

			1) gponCesServiceRtpEnableInd attribute is set to 1 = enabled.
			2) the CES service is type L3

		 Range is 0..65535 (Default = 0)

		NOTE: Any edit of this parameter is service-affecting.

	Introduced in ISAM4.6 for MIB readiness.
	As of ISAM4.6.01, relevant only for L3. "
::= { gponCesServiceEntry  42 }


gponCesServiceRtpExpectedSyncSourceSignalChannel OBJECT-TYPE 
	SYNTAX	INTEGER
	ACCESS	read-write
	STATUS  mandatory
	DESCRIPTION 
		" This attribute specifies the RTP synchronization source for the optional signalling channel in the PSN to TDM direction.
		 The received SSRC may be used to detect misconnection (stray packets).   
		 To disable the check function, set the corresponding value to its default value 0.  

			1) gponCesServiceRtpEnableInd attribute is set to 1 = enabled.
			2) the CES service is type L3

		As of ISAM4.6.01, zero (0) is the only supported value.
		Default = 0.

		NOTE: Any edit of this parameter is service-affecting.

	Introduced in ISAM4.6 for MIB readiness.
	As of ISAM4.6.01, relevant only for L3. "
::= { gponCesServiceEntry  43 }

-- *********************************************
--
-- GPON CES SERVICE PERFORMANCE MONITOR CURRENT INTERVAL TABLE
--
-- This is a new table beginning with FGU4.3.
-- This current interval table contains various statistics collected for 
-- a CES Service (pseudowire) during the current 15 minute interval 
-- of operation.  
--
-- An instance of this table is auto-created/deleted in accordance with the 
-- 'PM Collect Indicator' setting of the CES Service. 
--
-- For GETs of table attributes, the OLT must go directly to the ONT (via OMCI)
-- in order to acquire fresh current counts.
--
-- Most of the parameters monitor packets received from the PSN, and may
-- therefore be considered egress PM. For the most part, ingress PM is collected at
-- the CES UNI. 
--
-- For FGU4.3, this table is supported (for pseudowires).
--
-- For ISAM4.0.10, this table is being re-used. 
-- Noted which attributes are relevant for ISAM4.0.10
--
-- As of ISAM4.6.01, this table is relevant for both L2 and L3 CES pseudowire service.
--
--	For GPON - SUPPORTED as of ISAM4.0.10
--	For XG-PON1 - SUPPORTED as of ISAM4.6.02
--	For NG-PON2 - NOT SUPPORTED as of ISAM5.2 (CES Card Type NOT SUPPORTED)
--  
-- 
-- *********************************************

gponCesServicePWCurrentIntervalTable  OBJECT-TYPE
	SYNTAX SEQUENCE OF GponCesServicePWCurrentIntervalEntry
	ACCESS	not-accessible
	STATUS	mandatory
	::= { gponServicesGroup 13 }


gponCesServicePWCurrentIntervalEntry  OBJECT-TYPE
	SYNTAX 	GponCesServicePWCurrentIntervalEntry
	ACCESS	not-accessible
	STATUS	mandatory
	DESCRIPTION 
		"An entry in the GPON Ces Service PW
		 CurrentInterval Table. "
	INDEX	{ gponCesServicePWCurrentIntervalUniIndex, 
		   gponCesServicePWCurrentIntervalServiceNumber }
	::= { gponCesServicePWCurrentIntervalTable 1 }

GponCesServicePWCurrentIntervalEntry ::= SEQUENCE {
	gponCesServicePWCurrentIntervalUniIndex			IfIndex,
	gponCesServicePWCurrentIntervalServiceNumber			INTEGER,
	gponCesServicePWCurrentIntervalValidInd			Boolean,
	gponCesServicePWCurrentIntervalReceivePkts			Counter,
	gponCesServicePWCurrentIntervalTransmitPkts			Counter,
	gponCesServicePWCurrentIntervalMissingPkts		Counter,
	gponCesServicePWCurrentIntervalMisorderPktsUsable		Counter,
	gponCesServicePWCurrentIntervalMisorderPktsDropped		Counter,
	gponCesServicePWCurrentIntervalPlayoutBuffOverUnderRuns	Counter,
	gponCesServicePWCurrentIntervalMalformedPkts		Counter,
	gponCesServicePWCurrentIntervalStrayPkts			Counter,
	gponCesServicePWCurrentIntervalRemotePktsLost		Counter,
	gponCesServicePWCurrentIntervalTdmLbitPktsTransmitted	Counter,
	gponCesServicePWCurrentIntervalES				Counter,
	gponCesServicePWCurrentIntervalSES			Counter,
	gponCesServicePWCurrentIntervalUAS			Counter
}


gponCesServicePWCurrentIntervalUniIndex  OBJECT-TYPE
	SYNTAX 	IfIndex
	ACCESS	read-only
	STATUS	mandatory
	DESCRIPTION 
		"This index is the ifIndex of the physical CES UNI. 

		For ISAM 4.0.10 -> stays the same as latest FGU4.x "
	::= { gponCesServicePWCurrentIntervalEntry 1 }

gponCesServicePWCurrentIntervalServiceNumber  OBJECT-TYPE
	SYNTAX 	INTEGER
	ACCESS	read-only
	STATUS	mandatory
	DESCRIPTION 
		"This table index is the number of the service
		 on the physical CES UNI.

 		 For FGU4.3, this value must be 1 (i.e. only a single service per CES UNI).

		For ISAM 4.0.10 -> stays the same as latest FGU4.x  "
	::= { gponCesServicePWCurrentIntervalEntry 2 }


gponCesServicePWCurrentIntervalValidInd  OBJECT-TYPE
	SYNTAX 	Boolean
	ACCESS	read-only
	STATUS	mandatory
	DESCRIPTION 
		"Indicates whether or not this CurrentInterval contains
		 valid PM counts.

		 As of FGU4.3, NOT SUPPORTED

		For ISAM 4.0.10 -> stays the same as latest FGU4.x  "
	::= { gponCesServicePWCurrentIntervalEntry 3 }


gponCesServicePWCurrentIntervalReceivePkts  OBJECT-TYPE
	SYNTAX 	Counter
	ACCESS	read-only
	STATUS	mandatory
	DESCRIPTION 
		" This attribute is a count of the total number of packets, both payload
		  and signalling, received in the PSN to TDM direction.

		For ISAM 4.0.10 -> stays the same as latest FGU4.x  "
	::= { gponCesServicePWCurrentIntervalEntry 4 }

gponCesServicePWCurrentIntervalTransmitPkts  OBJECT-TYPE
	SYNTAX 	Counter
	ACCESS	read-only
	STATUS	mandatory
	DESCRIPTION 
		" This attribute is a count of the total number of packets, both payload and signalling,
		   transmitted from the TDM to the PSN. The count includes packets whose L bit is set
		   and which may therefore contain no payload. 
	
 		   For FGU4.3 NOT SUPPORTED by Resolute chip.

		For ISAM 4.0.10 -> stays the same as latest FGU4.x

		As of ISAM5.0, attribute is SUPPORTED.  "
	::= { gponCesServicePWCurrentIntervalEntry 5 }

gponCesServicePWCurrentIntervalMissingPkts  OBJECT-TYPE
	SYNTAX 	Counter
	ACCESS	read-only
	STATUS	mandatory
	DESCRIPTION 
		" This attribute is a count of the number of lost packets, as indicated by gaps in the control
		   word numbering sequence. Both payload and signalling packets, if any, contribute to this count.

		For ISAM 4.0.10 -> stays the same as latest FGU4.x  "
	::= { gponCesServicePWCurrentIntervalEntry 6 }


gponCesServicePWCurrentIntervalMisorderPktsUsable  OBJECT-TYPE
	SYNTAX 	Counter
	ACCESS	read-only
	STATUS	mandatory
	DESCRIPTION 
		" This attribute is a count of the number of packets received out of order, but which were able to be
		  successfully re-ordered and played out. Both payload and signalling packets, if any, contribute to
		   this count.

		For ISAM 4.0.10 -> stays the same as latest FGU4.x  "
	::= { gponCesServicePWCurrentIntervalEntry 7 }


gponCesServicePWCurrentIntervalMisorderPktsDropped  OBJECT-TYPE
	SYNTAX 	Counter
	ACCESS	read-only
	STATUS	mandatory
	DESCRIPTION 
		" This attribute is a count of the number of packets received out of sequence that were discarded, 
		   either because the ONT did not support reordering or because it was too late to reorder them. 
		   Both payload and signalling packets, if any, contribute to this count. 
		   
		   For FGU4.3 NOT SUPPORTED by Resolute chip.

		For ISAM 4.0.10 -> stays the same as latest FGU4.x

		As of ISAM5.0, attribute is SUPPORTED. "
	::= { gponCesServicePWCurrentIntervalEntry 8 }


gponCesServicePWCurrentIntervalPlayoutBuffOverUnderRuns  OBJECT-TYPE
	SYNTAX 	Counter
	ACCESS	read-only
	STATUS	mandatory
	DESCRIPTION 
		" This attribute is a count of the number of packets that were discarded because they arrived too late
		  or too early to be played out. Both payload and signalling packets, if any, contribute to this count.

		For ISAM 4.0.10 -> stays the same as latest FGU4.x "
	::= { gponCesServicePWCurrentIntervalEntry 9 }

gponCesServicePWCurrentIntervalMalformedPkts  OBJECT-TYPE
	SYNTAX 	Counter
	ACCESS	read-only
	STATUS	mandatory
	DESCRIPTION 
		" This attribute is a count of the number of malformed packets, for example because the packet
		   length was not as expected or because of unexpected RTP payload type. Both payload and 
		   signalling packets, if any, contribute to this count. 

		For ISAM 4.0.10 -> stays the same as latest FGU4.x  "
	::= { gponCesServicePWCurrentIntervalEntry 10 }

gponCesServicePWCurrentIntervalStrayPkts  OBJECT-TYPE
	SYNTAX 	Counter
	ACCESS	read-only
	STATUS	mandatory
	DESCRIPTION 
		" This attribute is a count of the number of packets whose ECID or RTP SSRC failed to match
		   the expected value, or which are otherwise known to have been misdelivered. Stray packets 
		   are discarded without affecting any of the other PM counters. Both payload and signalling 
		   packets, if any, contribute to this count. 

		   For FGU4.3 NOT SUPPORTED by Resolute chip.

		For ISAM 4.0.10 -> stays the same as latest FGU4.x "
	::= { gponCesServicePWCurrentIntervalEntry 11 }


gponCesServicePWCurrentIntervalRemotePktsLost  OBJECT-TYPE
	SYNTAX 	Counter
	ACCESS	read-only
	STATUS	mandatory
	DESCRIPTION 
		" This attribute is a count of received packets whose R bit is set, indicating the loss of packets
		  at the far end. Both payload and signalling packets, if any, contribute to this count.

		For ISAM 4.0.10 -> stays the same as latest FGU4.x "
	::= { gponCesServicePWCurrentIntervalEntry 12 }

gponCesServicePWCurrentIntervalTdmLbitPktsTransmitted  OBJECT-TYPE
	SYNTAX 	Counter
	ACCESS	read-only
	STATUS	mandatory
	DESCRIPTION 
		" This attribute is a count of the number of packets transmitted with the L bit set, indicating
		  a near-end TDM fault. Both payload and signalling packets, if any, contribute to this count.

		For ISAM 4.0.10 -> stays the same as latest FGU4.x  "
	::= { gponCesServicePWCurrentIntervalEntry 13 }

gponCesServicePWCurrentIntervalES  OBJECT-TYPE
	SYNTAX 	Counter
	ACCESS	read-only
	STATUS	mandatory
	DESCRIPTION 
		" This attribute counts errored seconds. Any discarded, lost, malformed or unusable packet
		  received from the PSN during a given second causes this counter to increment. Both payload
		  and signalling packets, if any, contribute to this count. 

		  For FGU4.3 NOT SUPPORTED by Resolute chip.

		For ISAM 4.0.10 -> stays the same as latest FGU4.x "
	::= { gponCesServicePWCurrentIntervalEntry 14 }

gponCesServicePWCurrentIntervalSES  OBJECT-TYPE
	SYNTAX 	Counter
	ACCESS	read-only
	STATUS	mandatory
	DESCRIPTION 
		" This attribute counts severely errored seconds. The criterion for a SES may be configured 
		   through the pseudowire maintenance profile managed entity. Both payload and signalling packets,
		   if any, contribute to this count.  

		  For FGU4.3 NOT SUPPORTED by Resolute chip.

		For ISAM 4.0.10 -> stays the same as latest FGU4.x "
	::= { gponCesServicePWCurrentIntervalEntry 15 }

gponCesServicePWCurrentIntervalUAS  OBJECT-TYPE
	SYNTAX 	Counter
	ACCESS	read-only
	STATUS	mandatory
	DESCRIPTION 
		" This attribute counts unavailable seconds. An unavailable second begins at the onset of ten consecutive
		  SESs and ends at the onset of ten consecutive seconds that are not severely errored. A service is 
		  unavailable if either its payload or its signalling, if any, are unavailable. During unavailable time, 
		  only SES and UAS should be counted; other anomalies should not be counted.   

		  For FGU4.3 NOT SUPPORTED by Resolute chip.

		For ISAM 4.0.10 -> stays the same as latest FGU4.x "
	::= { gponCesServicePWCurrentIntervalEntry 16 }


-- *********************************************
--
-- GPON CES SERVICE PERFORMANCE MONITOR INTERVAL TABLE
--
-- This is a new table beginning with FGU4.3.
-- This interval table contains CES psuedowire service statistics collected
-- at an ONT over the previous 8 hours of operation.  The past 8 hours are
-- broken into 32 completed 15 minute intervals.  Each row in this table
-- represents one such interval associated with a CES pseudowire service.  
--
-- An instance of this table is auto-created/deleted in accordance with the 
-- 'PM Collect Indicator' setting of the CES Service. 
--
-- Most of the parameters monitor packets received from the PSN, and may
-- therefore be considered egress PM. For the most part, ingress PM is collected at
-- the CES UNI. 
--
-- For FGU4.3, this table is supported (for pseudowires).
--
-- For ISAM4.0.10, this table is being re-used. 
-- Noted which attributes are relevant for ISAM4.0.10
--
-- As of ISAM4.6.01, this table is relevant for both L2 and L3 CES pseudowire service.
--
--	For GPON - SUPPORTED as of ISAM4.0.10
--	For XG-PON1 - SUPPORTED as of ISAM4.6.02
--	For NG-PON2 - NOT SUPPORTED as of ISAM5.2 (CES Card Type NOT SUPPORTED)
--  
-- 
-- *********************************************

gponCesServicePWIntervalTable  OBJECT-TYPE
	SYNTAX SEQUENCE OF GponCesServicePWIntervalEntry
	ACCESS	not-accessible
	STATUS	mandatory
	::= { gponServicesGroup 14 }


gponCesServicePWIntervalEntry  OBJECT-TYPE
	SYNTAX 	GponCesServicePWIntervalEntry
	ACCESS	not-accessible
	STATUS	mandatory
	DESCRIPTION 
		"An entry in the GPON Ces Service PW
		 Interval Table. "
	INDEX	{ gponCesServicePWIntervalUniIndex, 
		   gponCesServicePWIntervalServiceNumber,
		   gponCesServicePWIntervalNumber }
	::= { gponCesServicePWIntervalTable 1 }

GponCesServicePWIntervalEntry ::= SEQUENCE {
	gponCesServicePWIntervalUniIndex			IfIndex,
	gponCesServicePWIntervalServiceNumber			INTEGER,
	gponCesServicePWIntervalNumber		INTEGER,
	gponCesServicePWIntervalValidInd			Boolean,
	gponCesServicePWIntervalReceivePkts			Counter,
	gponCesServicePWIntervalTransmitPkts			Counter,
	gponCesServicePWIntervalMissingPkts		Counter,
	gponCesServicePWIntervalMisorderPktsUsable		Counter,
	gponCesServicePWIntervalMisorderPktsDropped		Counter,
	gponCesServicePWIntervalPlayoutBuffOverUnderRuns		Counter,
	gponCesServicePWIntervalMalformedPkts		Counter,
	gponCesServicePWIntervalStrayPkts			Counter,
	gponCesServicePWIntervalRemotePktsLost		Counter,
	gponCesServicePWIntervalTdmLbitPktsTransmitted	Counter,
	gponCesServicePWIntervalES				Counter,
	gponCesServicePWIntervalSES			Counter,
	gponCesServicePWIntervalUAS			Counter
}


gponCesServicePWIntervalUniIndex  OBJECT-TYPE
	SYNTAX 	IfIndex
	ACCESS	read-only
	STATUS	mandatory
	DESCRIPTION 
		"This index is the ifIndex of the physical CES UNI.

		For ISAM 4.0.10 -> stays the same as latest FGU4.x  "
	::= { gponCesServicePWIntervalEntry 1 }

gponCesServicePWIntervalServiceNumber  OBJECT-TYPE
	SYNTAX 	INTEGER
	ACCESS	read-only
	STATUS	mandatory
	DESCRIPTION 
		"This table index is the number of the service
		 on the physical CES UNI.

 		 For FGU4.3, this value must be 1 (i.e. only a single service per CES UNI).

		For ISAM 4.0.10 -> stays the same as latest FGU4.x  "
	::= { gponCesServicePWIntervalEntry 2 }

gponCesServicePWIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.

		For ISAM 4.0.10 -> stays the same as latest FGU4.x  "
	::= { gponCesServicePWIntervalEntry 3 }

gponCesServicePWIntervalValidInd  OBJECT-TYPE
	SYNTAX 	Boolean
	ACCESS	read-only
	STATUS	mandatory
	DESCRIPTION 
		"Indicates whether or not this Interval contains
		 valid PM counts.

		 As of FGU4.3, NOT SUPPORTED

		For ISAM 4.0.10 -> stays the same as latest FGU4.x  "
	::= { gponCesServicePWIntervalEntry 4 }


gponCesServicePWIntervalReceivePkts  OBJECT-TYPE
	SYNTAX 	Counter
	ACCESS	read-only
	STATUS	mandatory
	DESCRIPTION 
		" This attribute is a count of the total number of packets, both payload
		  and signalling, received in the PSN to TDM direction.

		For ISAM 4.0.10 -> stays the same as latest FGU4.x  "
	::= { gponCesServicePWIntervalEntry 5 }

gponCesServicePWIntervalTransmitPkts  OBJECT-TYPE
	SYNTAX 	Counter
	ACCESS	read-only
	STATUS	mandatory
	DESCRIPTION 
		" This attribute is a count of the total number of packets, both payload and signalling,
		   transmitted from the TDM to the PSN. The count includes packets whose L bit is set
		   and which may therefore contain no payload. 
	
 		   For FGU4.3 NOT SUPPORTED by Resolute chip.

		For ISAM 4.0.10 -> stays the same as latest FGU4.x

		As of ISAM5.0, attribute is SUPPORTED.  "
	::= { gponCesServicePWIntervalEntry 6 }

gponCesServicePWIntervalMissingPkts  OBJECT-TYPE
	SYNTAX 	Counter
	ACCESS	read-only
	STATUS	mandatory
	DESCRIPTION 
		" This attribute is a count of the number of lost packets, as indicated by gaps in the control
		   word numbering sequence. Both payload and signalling packets, if any, contribute to this count.

		For ISAM 4.0.10 -> stays the same as latest FGU4.x  "
	::= { gponCesServicePWIntervalEntry 7 }


gponCesServicePWIntervalMisorderPktsUsable  OBJECT-TYPE
	SYNTAX 	Counter
	ACCESS	read-only
	STATUS	mandatory
	DESCRIPTION 
		" This attribute is a count of the number of packets received out of order, but which were able to be
		  successfully re-ordered and played out. Both payload and signalling packets, if any, contribute to
		   this count.

		For ISAM 4.0.10 -> stays the same as latest FGU4.x  "
	::= { gponCesServicePWIntervalEntry 8 }


gponCesServicePWIntervalMisorderPktsDropped  OBJECT-TYPE
	SYNTAX 	Counter
	ACCESS	read-only
	STATUS	mandatory
	DESCRIPTION 
		" This attribute is a count of the number of packets received out of sequence that were discarded, 
		   either because the ONT did not support reordering or because it was too late to reorder them. 
		   Both payload and signalling packets, if any, contribute to this count. 
		   
		   For FGU4.3 NOT SUPPORTED by Resolute chip.

		For ISAM 4.0.10 -> stays the same as latest FGU4.x

		As of ISAM5.0, attribute is SUPPORTED. "
	::= { gponCesServicePWIntervalEntry 9 }


gponCesServicePWIntervalPlayoutBuffOverUnderRuns  OBJECT-TYPE
	SYNTAX 	Counter
	ACCESS	read-only
	STATUS	mandatory
	DESCRIPTION 
		" This attribute is a count of the number of packets that were discarded because they arrived too late
		  or too early to be played out. Both payload and signalling packets, if any, contribute to this count.

		For ISAM 4.0.10 -> stays the same as latest FGU4.x "
	::= { gponCesServicePWIntervalEntry 10 }

gponCesServicePWIntervalMalformedPkts  OBJECT-TYPE
	SYNTAX 	Counter
	ACCESS	read-only
	STATUS	mandatory
	DESCRIPTION 
		" This attribute is a count of the number of malformed packets, for example because the packet
		   length was not as expected or because of unexpected RTP payload type. Both payload and 
		   signalling packets, if any, contribute to this count. 

		For ISAM 4.0.10 -> stays the same as latest FGU4.x  "
	::= { gponCesServicePWIntervalEntry 11 }

gponCesServicePWIntervalStrayPkts  OBJECT-TYPE
	SYNTAX 	Counter
	ACCESS	read-only
	STATUS	mandatory
	DESCRIPTION 
		" This attribute is a count of the number of packets whose ECID or RTP SSRC failed to match
		   the expected value, or which are otherwise known to have been misdelivered. Stray packets 
		   are discarded without affecting any of the other PM counters. Both payload and signalling 
		   packets, if any, contribute to this count. 

		   For FGU4.3 NOT SUPPORTED by Resolute chip.

		For ISAM 4.0.10 -> stays the same as latest FGU4.x "
	::= { gponCesServicePWIntervalEntry 12 }


gponCesServicePWIntervalRemotePktsLost  OBJECT-TYPE
	SYNTAX 	Counter
	ACCESS	read-only
	STATUS	mandatory
	DESCRIPTION 
		" This attribute is a count of received packets whose R bit is set, indicating the loss of packets
		  at the far end. Both payload and signalling packets, if any, contribute to this count.

		For ISAM 4.0.10 -> stays the same as latest FGU4.x "
	::= { gponCesServicePWIntervalEntry 13 }

gponCesServicePWIntervalTdmLbitPktsTransmitted  OBJECT-TYPE
	SYNTAX 	Counter
	ACCESS	read-only
	STATUS	mandatory
	DESCRIPTION 
		" This attribute is a count of the number of packets transmitted with the L bit set, indicating
		  a near-end TDM fault. Both payload and signalling packets, if any, contribute to this count.

		For ISAM 4.0.10 -> stays the same as latest FGU4.x  "
	::= { gponCesServicePWIntervalEntry 14 }

gponCesServicePWIntervalES  OBJECT-TYPE
	SYNTAX 	Counter
	ACCESS	read-only
	STATUS	mandatory
	DESCRIPTION 
		" This attribute counts errored seconds. Any discarded, lost, malformed or unusable packet
		  received from the PSN during a given second causes this counter to increment. Both payload
		  and signalling packets, if any, contribute to this count. 

		  For FGU4.3 NOT SUPPORTED by Resolute chip.

		For ISAM 4.0.10 -> stays the same as latest FGU4.x "
	::= { gponCesServicePWIntervalEntry 15 }

gponCesServicePWIntervalSES  OBJECT-TYPE
	SYNTAX 	Counter
	ACCESS	read-only
	STATUS	mandatory
	DESCRIPTION 
		" This attribute counts severely errored seconds. The criterion for a SES may be configured 
		   through the pseudowire maintenance profile managed entity. Both payload and signalling packets,
		   if any, contribute to this count.  

		  For FGU4.3 NOT SUPPORTED by Resolute chip.

		For ISAM 4.0.10 -> stays the same as latest FGU4.x "
	::= { gponCesServicePWIntervalEntry 16 }

gponCesServicePWIntervalUAS  OBJECT-TYPE
	SYNTAX 	Counter
	ACCESS	read-only
	STATUS	mandatory
	DESCRIPTION 
		" This attribute counts unavailable seconds. An unavailable second begins at the onset of ten consecutive
		  SESs and ends at the onset of ten consecutive seconds that are not severely errored. A service is 
		  unavailable if either its payload or its signalling, if any, are unavailable. During unavailable time, 
		  only SES and UAS should be counted; other anomalies should not be counted.   

		  For FGU4.3 NOT SUPPORTED by Resolute chip.

		For ISAM 4.0.10 -> stays the same as latest FGU4.x "
	::= { gponCesServicePWIntervalEntry 17 }


-- *********************************************
--
-- CES SERVICE ONT-SIDE GEM PERFORMANCE MONITOR CURRENT INTERVAL TABLE
--
-- This is a new table beginning with FGU4.3.
-- This current interval table contains various statistics collected for 
-- ONT GEM ports (ONT-side) during the current 15 minute interval 
-- of operation.  
--
-- An instance of this table is auto-created/deleted in accordance with the 
-- 'PM Collect Indicator' setting of the CES Service.
--
-- For GETs of table attributes, the OLT must go directly to the ONT (via OMCI)
-- in order to acquire fresh current counts. 
--
-- NOTE: The ONT itself doesn't have knowledge about the individual GEM
-- ports that comprise an CES Service - this is known only by the OLT.  But 
-- the ONT keeps the GEM PM counts on a GEM port basis.  Therefore, the
-- OLT must collect and sum the individual GEM port PMs for each of the 
-- GEM ports associated with the CES service.  The GEM port PM summations
-- are recorded in this table.
--
-- For ISAM4.0.10, this table is being re-used. 
-- Noted which attributes are relevant for ISAM4.0.10.
--
-- As of ISAM4.6.01, this table is NOT supported for L3 CES pseudowire service.
--
--	For GPON - SUPPORTED as of ISAM4.0.10
--	For XG-PON1 - SUPPORTED as of ISAM4.6.02
--	For NG-PON2 - NOT SUPPORTED as of ISAM5.2 (CES Card Type NOT SUPPORTED)
--  
-- 
-- *********************************************


gponCesServiceOntsideGemCurrentIntervalTable  OBJECT-TYPE
	SYNTAX SEQUENCE OF GponCesServiceOntsideGemCurrentIntervalEntry
	ACCESS	not-accessible
	STATUS	mandatory
	::= { gponServicesGroup 15 }


gponCesServiceOntsideGemCurrentIntervalEntry  OBJECT-TYPE
	SYNTAX 	GponCesServiceOntsideGemCurrentIntervalEntry
	ACCESS	not-accessible
	STATUS	mandatory
	DESCRIPTION 
		"An entry in the GPON Ces Service GEM PM
		 CurrentInterval Table. "
	INDEX	{ gponCesServiceOntsideGemCurrentIntervalUniIndex, 
		   gponCesServiceOntsideGemCurrentIntervalServiceNumber }
	::= { gponCesServiceOntsideGemCurrentIntervalTable 1 }

GponCesServiceOntsideGemCurrentIntervalEntry ::= SEQUENCE {
	gponCesServiceOntsideGemCurrentIntervalUniIndex			IfIndex,
	gponCesServiceOntsideGemCurrentIntervalServiceNumber			INTEGER,
	gponCesServiceOntsideGemCurrentIntervalValidInd			Boolean,
	gponCesServiceOntsideGemCurrentIntervalLostFragsDown			Counter,
	gponCesServiceOntsideGemCurrentIntervalLostFragsUp			Counter,
	gponCesServiceOntsideGemCurrentIntervalReceiveFrags		Counter,
	gponCesServiceOntsideGemCurrentIntervalReceiveBlocks		Counter,
	gponCesServiceOntsideGemCurrentIntervalTransmitBlocks		Counter,
	gponCesServiceOntsideGemCurrentIntervalTransmitFrags		Counter
}


gponCesServiceOntsideGemCurrentIntervalUniIndex  OBJECT-TYPE
	SYNTAX 	IfIndex
	ACCESS	read-only
	STATUS	mandatory
	DESCRIPTION 
		"This index is the ifIndex of the physical UNI.

		For ISAM 4.0.10 -> stays the same as latest FGU4.x  "
	::= { gponCesServiceOntsideGemCurrentIntervalEntry 1 }

gponCesServiceOntsideGemCurrentIntervalServiceNumber  OBJECT-TYPE
	SYNTAX 	INTEGER
	ACCESS	read-only
	STATUS	mandatory
	DESCRIPTION 
		"This table index is the number of the service
		 on the physical UNI.

  		 For FGU4.3, this value must be 1 (i.e. only a single service per CES UNI).

		For ISAM 4.0.10 -> stays the same as latest FGU4.x "
	::= { gponCesServiceOntsideGemCurrentIntervalEntry 2 }


gponCesServiceOntsideGemCurrentIntervalValidInd  OBJECT-TYPE
	SYNTAX 	Boolean
	ACCESS	read-only
	STATUS	mandatory
	DESCRIPTION 
		"Indicates whether or not this CurrentInterval contains
		 valid PM counts.

		 As of FGU4.3, this is NOT SUPPORTED

		For ISAM 4.0.10 -> stays the same as latest FGU4.x  "
	::= { gponCesServiceOntsideGemCurrentIntervalEntry 3 }


gponCesServiceOntsideGemCurrentIntervalLostFragsDown  OBJECT-TYPE
	SYNTAX 	Counter
	ACCESS	read-only
	STATUS	mandatory
	DESCRIPTION 
		"A count of Lost GEM Fragments (downstream).

		For ISAM 4.0.10 -> stays the same as latest FGU4.x  "
	::= { gponCesServiceOntsideGemCurrentIntervalEntry 4 }

gponCesServiceOntsideGemCurrentIntervalLostFragsUp  OBJECT-TYPE
	SYNTAX 	Counter
	ACCESS	read-only
	STATUS	mandatory
	DESCRIPTION 
		"A count of Lost GEM Fragments (upstream).

		For ISAM 4.0.10 -> stays the same as latest FGU4.x "
	::= { gponCesServiceOntsideGemCurrentIntervalEntry 5 }

gponCesServiceOntsideGemCurrentIntervalReceiveFrags  OBJECT-TYPE
	SYNTAX 	Counter
	ACCESS	read-only
	STATUS	mandatory
	DESCRIPTION 
		"A count of Received GEM Fragments.

		For ISAM 4.0.10 -> stays the same as latest FGU4.x "
	::= { gponCesServiceOntsideGemCurrentIntervalEntry 6 }


gponCesServiceOntsideGemCurrentIntervalReceiveBlocks  OBJECT-TYPE
	SYNTAX 	Counter
	ACCESS	read-only
	STATUS	mandatory
	DESCRIPTION 
		"A count of Received GEM Blocks.

		For ISAM 4.0.10 -> stays the same as latest FGU4.x "
	::= { gponCesServiceOntsideGemCurrentIntervalEntry 7 }


gponCesServiceOntsideGemCurrentIntervalTransmitBlocks  OBJECT-TYPE
	SYNTAX 	Counter
	ACCESS	read-only
	STATUS	mandatory
	DESCRIPTION 
		"A count of Transmitted GEM Blocks.

		For ISAM 4.0.10 -> stays the same as latest FGU4.x "
	::= { gponCesServiceOntsideGemCurrentIntervalEntry 8 }


gponCesServiceOntsideGemCurrentIntervalTransmitFrags  OBJECT-TYPE
	SYNTAX 	Counter
	ACCESS	read-only
	STATUS	mandatory
	DESCRIPTION 
		"A count of Transmitted GEM Fragments.

		For ISAM 4.0.10 -> stays the same as latest FGU4.x "
	::= { gponCesServiceOntsideGemCurrentIntervalEntry 9 }

-- *********************************************
--
-- CES SERVICE ONT-SIDE GEM PERFORMANCE MONITOR INTERVAL TABLE
--
-- This is a new table beginning with FGU4.3.
-- This interval table contains various GEM port statistics collected
-- at an ONT over the previous 8 hours of operation.  The past 8 hours are
-- broken into 32 completed 15 minute intervals.  Each row in this table
-- represents one such interval associated with an CES service.
--
-- An instance of this table is auto-created/deleted in accordance with the 
-- 'PM Collect Indicator' setting of the CES Service.
--
-- NOTE: The ONT itself doesn't have knowledge about the individual GEM
-- ports that comprise an CES Service - this is known only by the OLT.  But 
-- the ONT keeps the GEM PM counts on a GEM port basis.  Therefore, the
-- OLT must collect and sum the individual GEM port PMs for each of the 
-- GEM ports associated with the CES service.  The GEM port PM summations
-- are recorded in this table.
--
-- For ISAM4.0.10, this table is being re-used. 
-- Noted which attributes are relevant for ISAM4.0.10.
--
-- As of ISAM4.6.01, this table is NOT supported for L3 CES pseudowire service.
--
--	For GPON - SUPPORTED as of ISAM4.0.10
--	For XG-PON1 - SUPPORTED as of ISAM4.6.02
--	For NG-PON2 - NOT SUPPORTED as of ISAM5.2 (CES Card Type NOT SUPPORTED)
--  
-- 
-- *********************************************


gponCesServiceOntsideGemIntervalTable  OBJECT-TYPE
	SYNTAX SEQUENCE OF GponCesServiceOntsideGemIntervalEntry
	ACCESS	not-accessible
	STATUS	mandatory
	::= { gponServicesGroup 16 }


gponCesServiceOntsideGemIntervalEntry  OBJECT-TYPE
	SYNTAX 	GponCesServiceOntsideGemIntervalEntry
	ACCESS	not-accessible
	STATUS	mandatory
	DESCRIPTION 
		"An entry in the GPON Ces Service GEM PM
		 Interval Table. "
	INDEX	{ gponCesServiceOntsideGemIntervalUniIndex, 
		   gponCesServiceOntsideGemIntervalServiceNumber,
		  gponCesServiceOntsideGemIntervalNumber }
	::= { gponCesServiceOntsideGemIntervalTable 1 }

GponCesServiceOntsideGemIntervalEntry ::= SEQUENCE {
	gponCesServiceOntsideGemIntervalUniIndex			IfIndex,
	gponCesServiceOntsideGemIntervalServiceNumber			INTEGER,
	gponCesServiceOntsideGemIntervalNumber			INTEGER,
	gponCesServiceOntsideGemIntervalValidInd			Boolean,
	gponCesServiceOntsideGemIntervalLostFragsDown			Counter,
	gponCesServiceOntsideGemIntervalLostFragsUp			Counter,
	gponCesServiceOntsideGemIntervalReceiveFrags		Counter,
	gponCesServiceOntsideGemIntervalReceiveBlocks		Counter,
	gponCesServiceOntsideGemIntervalTransmitBlocks		Counter,
	gponCesServiceOntsideGemIntervalTransmitFrags		Counter
}


gponCesServiceOntsideGemIntervalUniIndex  OBJECT-TYPE
	SYNTAX 	IfIndex
	ACCESS	read-only
	STATUS	mandatory
	DESCRIPTION 
		"This index is the ifIndex of the physical UNI.

		For ISAM 4.0.10 -> stays the same as latest FGU4.x  "
	::= { gponCesServiceOntsideGemIntervalEntry 1 }

gponCesServiceOntsideGemIntervalServiceNumber  OBJECT-TYPE
	SYNTAX 	INTEGER
	ACCESS	read-only
	STATUS	mandatory
	DESCRIPTION 
		"This table index is the number of the service
		 on the physical UNI.

   		 For FGU4.3, this value must be 1 (i.e. only a single service per CES UNI).

		For ISAM 4.0.10 -> stays the same as latest FGU4.x "
	::= { gponCesServiceOntsideGemIntervalEntry 2 }

gponCesServiceOntsideGemIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.

		For ISAM 4.0.10 -> stays the same as latest FGU4.x  "
	::= { gponCesServiceOntsideGemIntervalEntry 3 }

gponCesServiceOntsideGemIntervalValidInd  OBJECT-TYPE
	SYNTAX 	Boolean
	ACCESS	read-only
	STATUS	mandatory
	DESCRIPTION 
		"Indicates whether or not this interval contains
		 valid PM counts.  

		 As of FGU4.3, NOT SUPPORTED

		For ISAM 4.0.10 -> stays the same as latest FGU4.x "
	::= { gponCesServiceOntsideGemIntervalEntry 4 }


gponCesServiceOntsideGemIntervalLostFragsDown  OBJECT-TYPE
	SYNTAX 	Counter
	ACCESS	read-only
	STATUS	mandatory
	DESCRIPTION 
		"A count of Lost GEM Fragments (downstream).

		For ISAM 4.0.10 -> stays the same as latest FGU4.x "
	::= { gponCesServiceOntsideGemIntervalEntry 5 }

gponCesServiceOntsideGemIntervalLostFragsUp  OBJECT-TYPE
	SYNTAX 	Counter
	ACCESS	read-only
	STATUS	mandatory
	DESCRIPTION 
		"A count of Lost GEM Fragments (upstream).

		For ISAM 4.0.10 -> stays the same as latest FGU4.x "
	::= { gponCesServiceOntsideGemIntervalEntry 6 }

gponCesServiceOntsideGemIntervalReceiveFrags  OBJECT-TYPE
	SYNTAX 	Counter
	ACCESS	read-only
	STATUS	mandatory
	DESCRIPTION 
		"A count of Received GEM Fragments.

		For ISAM 4.0.10 -> stays the same as latest FGU4.x "
	::= { gponCesServiceOntsideGemIntervalEntry 7 }


gponCesServiceOntsideGemIntervalReceiveBlocks  OBJECT-TYPE
	SYNTAX 	Counter
	ACCESS	read-only
	STATUS	mandatory
	DESCRIPTION 
		"A count of Received GEM Blocks.

		For ISAM 4.0.10 -> stays the same as latest FGU4.x "
	::= { gponCesServiceOntsideGemIntervalEntry 8 }


gponCesServiceOntsideGemIntervalTransmitBlocks  OBJECT-TYPE
	SYNTAX 	Counter
	ACCESS	read-only
	STATUS	mandatory
	DESCRIPTION 
		"A count of Transmitted GEM Blocks.

		For ISAM 4.0.10 -> stays the same as latest FGU4.x "
	::= { gponCesServiceOntsideGemIntervalEntry 9 }


gponCesServiceOntsideGemIntervalTransmitFrags  OBJECT-TYPE
	SYNTAX 	Counter
	ACCESS	read-only
	STATUS	mandatory
	DESCRIPTION 
		"A count of Transmitted GEM Fragments.

		For ISAM 4.0.10 -> stays the same as latest FGU4.x "
	::= { gponCesServiceOntsideGemIntervalEntry 10 }


-- *********************************************
--
-- CES SERVICE OLT-SIDE GEM PERFORMANCE MONITOR CURRENT INTERVAL TABLE
--
-- This is a new table beginning with FGU4.3.
-- This current interval table contains various statistics collected for 
-- ONT GEM ports (OLT-side) during the current 15 minute interval 
-- of operation.  
--
-- An instance of this table is auto-created/deleted in accordance with the 
-- 'PM Collect Indicator' setting of the CES Service.
--
--
-- NOTE:  The OLT must collect and sum the individual GEM port PMs for each of the 
-- GEM ports associated with the CES service.  The GEM port PM summations
-- are recorded in this table.
--
-- For ISAM4.0.10, this table is being re-used. 
-- Noted which attributes are relevant for ISAM4.0.10.
--
-- As of ISAM4.6.01, this table is NOT supported for L3 CES pseudowire service.
--
--	For GPON - SUPPORTED as of ISAM4.0.10
--	For XG-PON1 - SUPPORTED as of ISAM4.6.02
--	For NG-PON2 - NOT SUPPORTED as of ISAM5.2 (CES Card Type NOT SUPPORTED)
--  
-- 
-- *********************************************


gponCesServiceOltsideGemCurrentIntervalTable  OBJECT-TYPE
	SYNTAX SEQUENCE OF GponCesServiceOltsideGemCurrentIntervalEntry
	ACCESS	not-accessible
	STATUS	mandatory
	::= { gponServicesGroup 17 }


gponCesServiceOltsideGemCurrentIntervalEntry  OBJECT-TYPE
	SYNTAX 	GponCesServiceOltsideGemCurrentIntervalEntry
	ACCESS	not-accessible
	STATUS	mandatory
	DESCRIPTION 
		"An entry in the GPON Ces Service GEM PM
		 CurrentInterval Table. "
	INDEX	{ gponCesServiceOltsideGemCurrentIntervalUniIndex, 
		   gponCesServiceOltsideGemCurrentIntervalServiceNumber }
	::= { gponCesServiceOltsideGemCurrentIntervalTable 1 }

GponCesServiceOltsideGemCurrentIntervalEntry ::= SEQUENCE {
	gponCesServiceOltsideGemCurrentIntervalUniIndex			IfIndex,
	gponCesServiceOltsideGemCurrentIntervalServiceNumber			INTEGER,
	gponCesServiceOltsideGemCurrentIntervalValidInd			Boolean,
	gponCesServiceOltsideGemCurrentIntervalLostFragsDown			Counter,
	gponCesServiceOltsideGemCurrentIntervalLostFragsUp			Counter,
	gponCesServiceOltsideGemCurrentIntervalReceiveFrags		Counter,
	gponCesServiceOltsideGemCurrentIntervalReceiveBlocks		Counter,
	gponCesServiceOltsideGemCurrentIntervalTransmitBlocks		Counter,
	gponCesServiceOltsideGemCurrentIntervalTransmitFrags		Counter
}


gponCesServiceOltsideGemCurrentIntervalUniIndex  OBJECT-TYPE
	SYNTAX 	IfIndex
	ACCESS	read-only
	STATUS	mandatory
	DESCRIPTION 
		"This index is the ifIndex of the physical UNI.

		For ISAM 4.0.10 -> stays the same as latest FGU4.x  "
	::= { gponCesServiceOltsideGemCurrentIntervalEntry 1 }

gponCesServiceOltsideGemCurrentIntervalServiceNumber  OBJECT-TYPE
	SYNTAX 	INTEGER
	ACCESS	read-only
	STATUS	mandatory
	DESCRIPTION 
		"This table index is the number of the service
		 on the physical UNI.

   		 For FGU4.3, this value must be 1 (i.e. only a single service per CES UNI).

		For ISAM 4.0.10 -> stays the same as latest FGU4.x "
	::= { gponCesServiceOltsideGemCurrentIntervalEntry 2 }


gponCesServiceOltsideGemCurrentIntervalValidInd  OBJECT-TYPE
	SYNTAX 	Boolean
	ACCESS	read-only
	STATUS	mandatory
	DESCRIPTION 
		"Indicates whether or not this CurrentInterval contains
		 valid PM counts.

		 As of FGU4.3, NOT SUPPORTED

		For ISAM 4.0.10 -> stays the same as latest FGU4.x  "
	::= { gponCesServiceOltsideGemCurrentIntervalEntry 3 }


gponCesServiceOltsideGemCurrentIntervalLostFragsDown  OBJECT-TYPE
	SYNTAX 	Counter
	ACCESS	read-only
	STATUS	mandatory
	DESCRIPTION 
		"A count of Lost GEM Fragments (downstream).

		 As of FGU4.3, NOT SUPPORTED

		For ISAM 4.0.10 -> stays the same as latest FGU4.x "
	::= { gponCesServiceOltsideGemCurrentIntervalEntry 4 }

gponCesServiceOltsideGemCurrentIntervalLostFragsUp  OBJECT-TYPE
	SYNTAX 	Counter
	ACCESS	read-only
	STATUS	mandatory
	DESCRIPTION 
		"A count of Lost GEM Fragments (upstream).

		For ISAM 4.0.10 -> stays the same as latest FGU4.x "
	::= { gponCesServiceOltsideGemCurrentIntervalEntry 5 }

gponCesServiceOltsideGemCurrentIntervalReceiveFrags  OBJECT-TYPE
	SYNTAX 	Counter
	ACCESS	read-only
	STATUS	mandatory
	DESCRIPTION 
		"A count of Received GEM Fragments.

		For ISAM 4.0.10 -> stays the same as latest FGU4.x "
	::= { gponCesServiceOltsideGemCurrentIntervalEntry 6 }


gponCesServiceOltsideGemCurrentIntervalReceiveBlocks  OBJECT-TYPE
	SYNTAX 	Counter
	ACCESS	read-only
	STATUS	mandatory
	DESCRIPTION 
		"A count of Received GEM Blocks.

		For ISAM 4.0.10 -> stays the same as latest FGU4.x "
	::= { gponCesServiceOltsideGemCurrentIntervalEntry 7 }


gponCesServiceOltsideGemCurrentIntervalTransmitBlocks  OBJECT-TYPE
	SYNTAX 	Counter
	ACCESS	read-only
	STATUS	mandatory
	DESCRIPTION 
		"A count of Transmitted GEM Blocks.

		For ISAM 4.0.10 -> stays the same as latest FGU4.x "
	::= { gponCesServiceOltsideGemCurrentIntervalEntry 8 }


gponCesServiceOltsideGemCurrentIntervalTransmitFrags  OBJECT-TYPE
	SYNTAX 	Counter
	ACCESS	read-only
	STATUS	mandatory
	DESCRIPTION 
		"A count of Transmitted GEM Fragments.

		For ISAM 4.0.10 -> stays the same as latest FGU4.x "
	::= { gponCesServiceOltsideGemCurrentIntervalEntry 9 }

-- *********************************************
--
-- CES SERVICE OLT-SIDE GEM PERFORMANCE MONITOR INTERVAL TABLE
--
-- This is a new table beginning with FGU4.3.
-- This interval table contains various GEM port statistics collected
-- for an CES Service (OLT-side) over the previous 8 hours of operation.  The past 8 hours are
-- broken into 32 completed 15 minute intervals.  Each row in this table
-- represents one such interval associated with an CES service.
--
-- An instance of this table is auto-created/deleted in accordance with the 
-- 'PM Collect Indicator' setting of the CES Service.
--
-- NOTE: The OLT must collect and sum the individual GEM port PMs for each of the 
-- GEM ports associated with the CES service.  The GEM port PM summations
-- are recorded in this table.
--
-- For ISAM4.0.10, this table is being re-used. 
-- Noted which attributes are relevant for ISAM4.0.10.
--
-- As of ISAM4.6.01, this table is NOT supported for L3 CES pseudowire service.
--
--	For GPON - SUPPORTED as of ISAM4.0.10
--	For XG-PON1 - SUPPORTED as of ISAM4.6.02
--	For NG-PON2 - NOT SUPPORTED as of ISAM5.2 (CES Card Type NOT SUPPORTED)
--  
-- 
-- *********************************************


gponCesServiceOltsideGemIntervalTable  OBJECT-TYPE
	SYNTAX SEQUENCE OF GponCesServiceOltsideGemIntervalEntry
	ACCESS	not-accessible
	STATUS	mandatory
	::= { gponServicesGroup 18 }


gponCesServiceOltsideGemIntervalEntry  OBJECT-TYPE
	SYNTAX 	GponCesServiceOltsideGemIntervalEntry
	ACCESS	not-accessible
	STATUS	mandatory
	DESCRIPTION 
		"An entry in the GPON Ces Service GEM PM
		 Interval Table. "
	INDEX	{ gponCesServiceOltsideGemIntervalUniIndex, 
		   gponCesServiceOltsideGemIntervalServiceNumber,
		  gponCesServiceOltsideGemIntervalNumber }
	::= { gponCesServiceOltsideGemIntervalTable 1 }

GponCesServiceOltsideGemIntervalEntry ::= SEQUENCE {
	gponCesServiceOltsideGemIntervalUniIndex			IfIndex,
	gponCesServiceOltsideGemIntervalServiceNumber			INTEGER,
	gponCesServiceOltsideGemIntervalNumber			INTEGER,
	gponCesServiceOltsideGemIntervalValidInd			Boolean,
	gponCesServiceOltsideGemIntervalLostFragsDown			Counter,
	gponCesServiceOltsideGemIntervalLostFragsUp			Counter,
	gponCesServiceOltsideGemIntervalReceiveFrags		Counter,
	gponCesServiceOltsideGemIntervalReceiveBlocks		Counter,
	gponCesServiceOltsideGemIntervalTransmitBlocks		Counter,
	gponCesServiceOltsideGemIntervalTransmitFrags		Counter
}


gponCesServiceOltsideGemIntervalUniIndex  OBJECT-TYPE
	SYNTAX 	IfIndex
	ACCESS	read-only
	STATUS	mandatory
	DESCRIPTION 
		"This index is the ifIndex of the physical UNI.  "
	::= { gponCesServiceOltsideGemIntervalEntry 1 }

gponCesServiceOltsideGemIntervalServiceNumber  OBJECT-TYPE
	SYNTAX 	INTEGER
	ACCESS	read-only
	STATUS	mandatory
	DESCRIPTION 
		"This table index is the number of the service
		 on the physical UNI.

   		 For FGU4.3, this value must be 1 (i.e. only a single service per CES UNI).

		For ISAM 4.0.10 -> stays the same as latest FGU4.x "
	::= { gponCesServiceOltsideGemIntervalEntry 2 }

gponCesServiceOltsideGemIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.

		For ISAM 4.0.10 -> stays the same as latest FGU4.x  "
	::= { gponCesServiceOltsideGemIntervalEntry 3 }

gponCesServiceOltsideGemIntervalValidInd  OBJECT-TYPE
	SYNTAX 	Boolean
	ACCESS	read-only
	STATUS	mandatory
	DESCRIPTION 
		"Indicates whether or not this interval contains
		 valid PM counts. 

		 As of FGU4.3, NOT SUPPORTED

		For ISAM 4.0.10 -> stays the same as latest FGU4.x  "
	::= { gponCesServiceOltsideGemIntervalEntry 4 }


gponCesServiceOltsideGemIntervalLostFragsDown  OBJECT-TYPE
	SYNTAX 	Counter
	ACCESS	read-only
	STATUS	mandatory
	DESCRIPTION 
		"A count of Lost GEM Fragments (downstream).

		 As of FGU4.3, NOT SUPPORTED

		For ISAM 4.0.10 -> stays the same as latest FGU4.x "
	::= { gponCesServiceOltsideGemIntervalEntry 5 }

gponCesServiceOltsideGemIntervalLostFragsUp  OBJECT-TYPE
	SYNTAX 	Counter
	ACCESS	read-only
	STATUS	mandatory
	DESCRIPTION 
		"A count of Lost GEM Fragments (upstream).

		For ISAM 4.0.10 -> stays the same as latest FGU4.x "
	::= { gponCesServiceOltsideGemIntervalEntry 6 }

gponCesServiceOltsideGemIntervalReceiveFrags  OBJECT-TYPE
	SYNTAX 	Counter
	ACCESS	read-only
	STATUS	mandatory
	DESCRIPTION 
		"A count of Received GEM Fragments.

		For ISAM 4.0.10 -> stays the same as latest FGU4.x "
	::= { gponCesServiceOltsideGemIntervalEntry 7 }


gponCesServiceOltsideGemIntervalReceiveBlocks  OBJECT-TYPE
	SYNTAX 	Counter
	ACCESS	read-only
	STATUS	mandatory
	DESCRIPTION 
		"A count of Received GEM Blocks.

		For ISAM 4.0.10 -> stays the same as latest FGU4.x "
	::= { gponCesServiceOltsideGemIntervalEntry 8 }


gponCesServiceOltsideGemIntervalTransmitBlocks  OBJECT-TYPE
	SYNTAX 	Counter
	ACCESS	read-only
	STATUS	mandatory
	DESCRIPTION 
		"A count of Transmitted GEM Blocks.

		For ISAM 4.0.10 -> stays the same as latest FGU4.x "
	::= { gponCesServiceOltsideGemIntervalEntry 9 }


gponCesServiceOltsideGemIntervalTransmitFrags  OBJECT-TYPE
	SYNTAX 	Counter
	ACCESS	read-only
	STATUS	mandatory
	DESCRIPTION 
		"A count of Transmitted GEM Fragments.

		For ISAM 4.0.10 -> stays the same as latest FGU4.x "
	::= { gponCesServiceOltsideGemIntervalEntry 10 }


-- *********************************************
-- GPON CES SERVICE OPINFO TABLE
--
--This table is only used for GPON.
--
-- This table contains operational information regarding a CES service
-- for a specific ONT.  The operational information is significant in that
-- each time it is requested, the OLT issues OMCI GET messages   
-- to obtain the latest information directly from the ONT.
-- A table row is created/deleted automatically by the OLT upon  
-- creation/deletion of a CES Service.
--
-- For ISAM4.0.10, this table is being re-used. 
-- Noted which attributes are relevant for ISAM4.0.10
--
--	For GPON - SUPPORTED as of ISAM4.0.10
--	For XG-PON1 - SUPPORTED as of ISAM4.6.02
--	For NG-PON2 - NOT SUPPORTED as of ISAM5.2 (CES Card Type NOT SUPPORTED)
--  
--
-- *********************************************

gponCesServiceOpInfoTable OBJECT-TYPE
	SYNTAX	SEQUENCE OF GponCesServiceOpInfoEntry
	ACCESS	not-accessible
	STATUS	mandatory
	DESCRIPTION
		"This object contains a table that contains Ces
		information for a specific Ces Service obtained 
		directly from a specific ONT.  "
::= { gponServicesGroup 19 }

gponCesServiceOpInfoEntry OBJECT-TYPE
	SYNTAX 	GponCesServiceOpInfoEntry
	ACCESS	not-accessible
	STATUS	mandatory
	DESCRIPTION
		"Rows of this table contain Ces service information. "
	INDEX {gponCesServiceOpInfoUniIndex,
	           gponCesServiceOpInfoServiceNumber }
::= {gponCesServiceOpInfoTable 1}

GponCesServiceOpInfoEntry ::=
	SEQUENCE { 
		gponCesServiceOpInfoUniIndex		IfIndex,
		gponCesServiceOpInfoServiceNumber		INTEGER,
		gponCesServiceOpInfoReceiveCircuitId		OCTET STRING,
		gponCesServiceOpInfoSourceMacAddress	OCTET STRING
}

gponCesServiceOpInfoUniIndex OBJECT-TYPE 
	SYNTAX IfIndex
	ACCESS read-only
	STATUS mandatory
	DESCRIPTION
	    "This index is the ifIndex of the Ces UNI

		For ISAM 4.0.10 -> stays the same as latest FGU4.x "
::= { gponCesServiceOpInfoEntry  1 }


gponCesServiceOpInfoServiceNumber  OBJECT-TYPE
	SYNTAX 	INTEGER
	ACCESS	read-only
	STATUS	mandatory
	DESCRIPTION 
		"This table index is the number of the service
		 on the physical UNI.

   		 For FGU4.3, this value must be 1 (i.e. only a single service per CES UNI).

		For ISAM 4.0.10 -> stays the same as latest FGU4.x "
::= { gponCesServiceOpInfoEntry  2 }


gponCesServiceOpInfoReceiveCircuitId  OBJECT-TYPE
	SYNTAX	OCTET STRING (SIZE(8))
	ACCESS	read-only
	STATUS  mandatory
	DESCRIPTION 
		" This attribute indicates the actual ECID(s) received on the payload and signalling channels, 
		  respectively. It may be used for diagnostic purposes.

 		 This attribute is a pair of ECID (Ethernet circuit ID) values that the ONT received in the direction
		  from the packet-switched network toward the TDM termination. Checking ECIDs may be a way to 
		  detect circuit misconnection. MEF8 ECIDs lie in the range 1-1048575 (2^20 -1). To allow for the 
		  possibility of other transport (L2TP) in the future, each ECID is allocated 4 bytes.
		  The first value is used for the payload ECID; the second is used for the optional separate signalling 
		  ECID.  

		  Default = all zeroes.

		  For FGU4.3, this attribute is NOT SUPPORTED by Resolute chip.

		For ISAM 4.0.10 -> stays the same as latest FGU4.x

		Although still NOT SUPPORTED as of ISAM4.6.01, this attribute would only be relevant for CES L2 pseudowire service.   "
::= { gponCesServiceOpInfoEntry  3 }


gponCesServiceOpInfoSourceMacAddress  OBJECT-TYPE
	SYNTAX	OCTET STRING (SIZE(6))
	ACCESS	read-only
	STATUS  mandatory
	DESCRIPTION 
		" This attribute specifies the near-end MAC address. It is established by other means
		   (eg factory programmed into ONT flash memory) and included here for information only.

		For ISAM 4.0.10 -> stays the same as latest FGU4.x

		As of ISAM4.6.01, this attribute is only relevant for L2 pseudowire service.  "
::= { gponCesServiceOpInfoEntry  4 }



-- *********************************************
--
-- GPON CES SERVICE (PSEUDOWIRE) PERFORMANCE MONITOR TCA
-- THRESHOLD TABLE
--
-- This is a new table beginning with FGU4.3.
-- This TCA Threshold table contains threshold settings
-- for various PMs at an ONT's CES pseudowire service interface during the current
-- 15 minute interval of operation.  
--
-- An instance of this table is auto-created/deleted in accordance with the 
-- CES Service PM Collect Indicator' setting of the particular CES Service.
--
-- 
-- NOTE: As of FGU4.3, this entire table is NOT SUPPORTED
--
-- As of ISAM 4.0.10, this table continues to be NOT SUPPORTED.
--
--	For GPON - NOT SUPPORTED as of ISAM4.0.10
--	For XG-PON1 - NOT SUPPORTED as of ISAM4.6.02
--	For NG-PON2 - NOT SUPPORTED as of ISAM5.2
--  
--
-- *********************************************


gponCesServicePwTCAThresholdTable  OBJECT-TYPE
	SYNTAX SEQUENCE OF GponCesServicePwTCAThresholdEntry
	ACCESS	not-accessible
	STATUS	mandatory
	::= { gponServicesGroup 20 }


gponCesServicePwTCAThresholdEntry  OBJECT-TYPE
	SYNTAX 	GponCesServicePwTCAThresholdEntry
	ACCESS	not-accessible
	STATUS	mandatory
	DESCRIPTION 
		"An entry in the Gpon Ethernet Traffic TCAThreshold 
		 Table. "
	INDEX	{ gponCesServicePwTCAThresholdUniIndex,
		  gponCesServicePwTCAThresholdServiceNumber  }
	::= { gponCesServicePwTCAThresholdTable 1 }

GponCesServicePwTCAThresholdEntry ::= SEQUENCE {
	gponCesServicePwTCAThresholdUniIndex			IfIndex,
	gponCesServicePwTCAThresholdServiceNumber			INTEGER,
	gponCesServicePwTCAEnable					INTEGER,
	gponCesServicePwTCAThresholdMissingPkts		Threshold,
	gponCesServicePwTCAThresholdMisorderPktsUsable		Threshold,
	gponCesServicePwTCAThresholdMisorderPktsDropped		Threshold,
	gponCesServicePwTCAThresholdPlayoutBuffOverUnderRuns	Threshold,
	gponCesServicePwTCAThresholdMalformedPkts		Threshold,
	gponCesServicePwTCAThresholdStrayPkts			Threshold,
	gponCesServicePwTCAThresholdRemotePktsLost		Threshold,
	gponCesServicePwTCAThresholdES				Threshold,
	gponCesServicePwTCAThresholdSES			Threshold,
	gponCesServicePwTCAThresholdUAS			Threshold
}


gponCesServicePwTCAThresholdUniIndex  OBJECT-TYPE
	SYNTAX 	IfIndex
	ACCESS	read-only
	STATUS	mandatory
	DESCRIPTION 
		" Each row is indexed by the ifIndex of the CES UNI.  "
	::= { gponCesServicePwTCAThresholdEntry 1 }

gponCesServicePwTCAThresholdServiceNumber  OBJECT-TYPE
	SYNTAX 	INTEGER
	ACCESS	read-only
	STATUS	mandatory
	DESCRIPTION 
		" This table index is the number of the service on the 
		CES UNI.
		
		For FGU4.3, this value must be 1 (i.e. only a single service per CES UNI).  "
	::= { gponCesServicePwTCAThresholdEntry 2 }


gponCesServicePwTCAEnable  OBJECT-TYPE
	SYNTAX 	INTEGER
	ACCESS	read-write
	STATUS	mandatory
	DESCRIPTION 
		"Allows the manager to enable/disable the reporting of
		 CES pseudowire service  TCAs for this physical UNI. 

	
		  1 = TCA's enabled
		  2 = TCA's disabled

		 Default = 2 = disabled. "
	::= { gponCesServicePwTCAThresholdEntry 3 }


gponCesServicePwTCAThresholdMissingPkts  OBJECT-TYPE
	SYNTAX 	Threshold
	ACCESS	read-write
	STATUS	mandatory
	DESCRIPTION 
		"TCA setting for Missing Packets.
		 A value of 4294967295 means that this threshold is disabled.

		 Default = 4294967295  "

	::= { gponCesServicePwTCAThresholdEntry 4 }


gponCesServicePwTCAThresholdMisorderPktsUsable  OBJECT-TYPE
	SYNTAX 	Threshold
	ACCESS	read-write
	STATUS	mandatory
	DESCRIPTION 
		"TCA setting for Misordered Packets (usable).
		 A value of 4294967295 means that this threshold is disabled.

		 Default = 4294967295  "

	::= { gponCesServicePwTCAThresholdEntry 5 }


gponCesServicePwTCAThresholdMisorderPktsDropped  OBJECT-TYPE
	SYNTAX 	Threshold
	ACCESS	read-write
	STATUS	mandatory
	DESCRIPTION 
		"TCA setting for Misordered Packets (dropped).
		 A value of 4294967295 means that this threshold is disabled.

		 Default = 4294967295

		 As of FGU4.3, this is NOT SUPPORTED  "

	::= { gponCesServicePwTCAThresholdEntry 6 }


gponCesServicePwTCAThresholdPlayoutBuffOverUnderRuns  OBJECT-TYPE
	SYNTAX 	Threshold
	ACCESS	read-write
	STATUS	mandatory
	DESCRIPTION 
		"TCA setting for Playout Buffer Overruns/Underruns.
		 A value of 4294967295 means that this threshold is disabled.

		 Default = 4294967295 "

	::= { gponCesServicePwTCAThresholdEntry 7 }

gponCesServicePwTCAThresholdMalformedPkts  OBJECT-TYPE
	SYNTAX 	Threshold
	ACCESS	read-write
	STATUS	mandatory
	DESCRIPTION 
		"TCA setting for Malformed Packets.
		 A value of 4294967295 means that this threshold is disabled.

		 Default = 4294967295  "

	::= { gponCesServicePwTCAThresholdEntry 8 }

gponCesServicePwTCAThresholdStrayPkts  OBJECT-TYPE
	SYNTAX 	Threshold
	ACCESS	read-write
	STATUS	mandatory
	DESCRIPTION 
		"TCA setting for Stray Packets.
		 A value of 4294967295 means that this threshold is disabled.

		 Default = 4294967295

		 As of FGU4.3, this is NOT SUPPORTED  "

	::= { gponCesServicePwTCAThresholdEntry 9 }

gponCesServicePwTCAThresholdRemotePktsLost  OBJECT-TYPE
	SYNTAX 	Threshold
	ACCESS	read-write
	STATUS	mandatory
	DESCRIPTION 
		"TCA setting for Remote Packets (lost).
		 A value of 4294967295 means that this threshold is disabled.

		 Default = 4294967295  "

	::= { gponCesServicePwTCAThresholdEntry 10 }

gponCesServicePwTCAThresholdES  OBJECT-TYPE
	SYNTAX 	Threshold
	ACCESS	read-write
	STATUS	mandatory
	DESCRIPTION 
		"TCA setting for Errored Seconds (ES).
		 A value of 4294967295 means that this threshold is disabled.

		 Default = 4294967295

		 As of FGU4.3, this is NOT SUPPORTED  "

	::= { gponCesServicePwTCAThresholdEntry 11 }

gponCesServicePwTCAThresholdSES  OBJECT-TYPE
	SYNTAX 	Threshold
	ACCESS	read-write
	STATUS	mandatory
	DESCRIPTION 
		"TCA setting for Severly Errored Seconds.
		 A value of 4294967295 means that this threshold is disabled.

		 Default = 4294967295

		 As of FGU4.3, this is NOT SUPPORTED  "

	::= { gponCesServicePwTCAThresholdEntry 12 }

gponCesServicePwTCAThresholdUAS  OBJECT-TYPE
	SYNTAX 	Threshold
	ACCESS	read-write
	STATUS	mandatory
	DESCRIPTION 
		"TCA setting for Unavailable Seconds.
		 A value of 4294967295 means that this threshold is disabled.

		 Default = 4294967295

		 As of FGU4.3, this is NOT SUPPORTED  "

	::= { gponCesServicePwTCAThresholdEntry 13 }


-- *********************************************
--
-- GPON TR069 MANAGEMENT SERVER TABLE
--
-- This is a new table beginning with isr4.4.
-- This TR069 Server table contains URI, VLAN, PBit settings
-- for creating TR069 management channel in ONT. 
--
--
-- An instance of this table is created/deleted by operator on NT and OLT. 
-- OMCI TR069 Management Server ME in ONT is auto-created/deleted.
--
--	For GPON - SUPPORTED as of ISAM4.4
--	For XG-PON1 - SUPPORTED as of ISAM4.6.02
--	For NG-PON2 - NOT SUPPORTED as of ISAM5.2 
--  
--
-- *********************************************

gponTR069ServerTable OBJECT-TYPE
	SYNTAX SEQUENCE OF GponTR069ServerEntry
	ACCESS	not-accessible
	STATUS	mandatory
	::= { gponServicesGroup 21 }

gponTR069ServerEntry  OBJECT-TYPE
	SYNTAX  GponTR069ServerEntry
	ACCESS	not-accessible
	STATUS	mandatory
	DESCRIPTION 
		"An entry in the gpon TR069 management server table. "
	INDEX	{ gponTR069ServerUniIndex  }
	::= { gponTR069ServerTable 1 }

GponTR069ServerEntry ::= SEQUENCE {
	gponTR069ServerUniIndex           IfIndex,
	gponTR069ServerAdminState         AdminState,
	gponTR069ServerAddressProfile     AsamProfilePointer,
	gponTR069ServerVLAN               VlanIndex,
	gponTR069ServerPbit               INTEGER,
	gponTR069ServerRowStatus          RowStatus
}


gponTR069ServerUniIndex  OBJECT-TYPE
	SYNTAX 	IfIndex
	ACCESS	not-accessible
	STATUS	mandatory
	DESCRIPTION 
		" Each row is indexed by the ifIndex of the associated VEIP UNI.   "
	::= { gponTR069ServerEntry 1 }

gponTR069ServerAdminState  OBJECT-TYPE
	SYNTAX 	AdminState
	ACCESS	read-write
	STATUS	mandatory
	DESCRIPTION 
		"For OMCI messaging, this attribute translates
		 into Admin State for the TR069 management server.  Setting it
		 to 'locked' deactivates the particular TR069 server.
		 Modification permitted even after row
		 becomes 'active'.
		 Default = 1 = locked

		 For ISAM4.4 - this attribute is  SUPPORTED "
	::= { gponTR069ServerEntry 2 }


gponTR069ServerAddressProfile  OBJECT-TYPE
	SYNTAX 	AsamProfilePointer
	ACCESS	read-write
	STATUS	mandatory
	DESCRIPTION 
		" This attribute points to a row in gponSecureUriProfileTable,
		  which contains the name (IP address or URI) of the TR069 server.

		  Value 0 (null pointer) is permitted - meaning this is determined via other means.

		  Default = 0.

		 For ISAM4.4 - this attribute is  SUPPORTED "
	::= { gponTR069ServerEntry 3 }


gponTR069ServerVLAN  OBJECT-TYPE
	SYNTAX 	VlanIndex
	ACCESS	read-write
	STATUS	mandatory
	DESCRIPTION 
		" This object is used to reference the C-VLAN pointing to one of 
		the user vlan.port created over the VEIP UNI or related virtual UNI.
		4097 is default VLAN id. If VLAN id is default value, 0xFFFF is set 
		to Associated tag in OMCI message of TR069 Server, and ONT will ignore 
		the configuration of Associated tag of TR069 Server.

		
		Default: 4097

		 For ISAM4.4 - this attribute is  SUPPORTED  "

	::= { gponTR069ServerEntry 4 }

gponTR069ServerPbit  OBJECT-TYPE
	SYNTAX 	INTEGER
	ACCESS	read-write
	STATUS	mandatory
	DESCRIPTION 
		" Pbit value for TR069 traffic, need NOT map with the port default Pbit. 
		The configured Pbit will be used for origin TR069 traffic and 
		will NOT be changed in OLT. If gponTR069ServerVLAN is default value 4097, 
		gponTR069ServerPbit will be ignored no matter what its real value is.

		
		Default: 0

		 For ISAM4.4 - this attribute is  SUPPORTED "
	::= { gponTR069ServerEntry 5 }

	
gponTR069ServerRowStatus  OBJECT-TYPE
	SYNTAX 	RowStatus
	ACCESS	read-write
	STATUS	mandatory
	DESCRIPTION 
		"This object is used to create a new row or modify or
	delete an existing row in this table. The usage is as per
	standard semantics of 'RowStatus' defined in SNMPv2-TC.

		 For ISAM4.4 - this attribute is  SUPPORTED "
	::= { gponTR069ServerEntry 6 }


-- *********************************************
--
-- Multicast ONT-SIDE GEM PERFORMANCE MONITOR CURRENT INTERVAL TABLE
--
-- This is a new table beginning with FGU4.7.4
-- This current interval table contains various statistics collected for
-- ONT GEM multicast port (ONT-side) during the current 15 minute interval
-- of operation.
--
-- An instance of this table is auto-created per ONT creation init and always
-- maintained.
--
-- For GETs of table attributes, the OLT must go directly to the ONT (via OMCI)
-- in order to acquire fresh current counts.
--
-- For ISAM4.2, this table is SUPPORTED (merged from FGU4.7.4).
--
--	For GPON - SUPPORTED as of ISAM4.2
--	For XG-PON1 - SUPPORTED as of ISAM4.6.02
--	For NG-PON2 - SUPPORTED as of ISAM5.2
--  
--
-- *********************************************

gponMulticastServiceOntsideGemCurrentIntervalTable  OBJECT-TYPE
   SYNTAX SEQUENCE OF GponMulticastServiceOntsideGemCurrentIntervalEntry
   ACCESS   not-accessible
   STATUS   mandatory
   ::= { gponServicesGroup 41 }


gponMulticastServiceOntsideGemCurrentIntervalEntry  OBJECT-TYPE
   SYNTAX   GponMulticastServiceOntsideGemCurrentIntervalEntry
   ACCESS   not-accessible
   STATUS   mandatory
   DESCRIPTION
      "An entry in the GPON Multicast Service GEM PM
       CurrentInterval Table. "
   INDEX { gponMulticastServiceOntsideGemCurrentIntervalOntIndex}
   ::= { gponMulticastServiceOntsideGemCurrentIntervalTable 1 }

GponMulticastServiceOntsideGemCurrentIntervalEntry ::= SEQUENCE {
   gponMulticastServiceOntsideGemCurrentIntervalOntIndex       IfIndex,
   gponMulticastServiceOntsideGemCurrentIntervalLostFragsDown        Counter,
   gponMulticastServiceOntsideGemCurrentIntervalReceiveFrags      Counter,
   gponMulticastServiceOntsideGemCurrentIntervalReceiveBlocks     Counter
}

gponMulticastServiceOntsideGemCurrentIntervalOntIndex  OBJECT-TYPE
   SYNTAX   IfIndex
   ACCESS   read-only
   STATUS   mandatory
   DESCRIPTION
      "This index is the ifIndex of the physical ONT.  "
   ::= { gponMulticastServiceOntsideGemCurrentIntervalEntry 1 }


gponMulticastServiceOntsideGemCurrentIntervalLostFragsDown  OBJECT-TYPE
   SYNTAX   Counter
   ACCESS   read-only
   STATUS   mandatory
   DESCRIPTION
      "A count of Lost GEM Fragments (downstream).  "
   ::= { gponMulticastServiceOntsideGemCurrentIntervalEntry 2 }


gponMulticastServiceOntsideGemCurrentIntervalReceiveFrags  OBJECT-TYPE
   SYNTAX   Counter
   ACCESS   read-only
   STATUS   mandatory
   DESCRIPTION
      "A count of Received GEM Fragments. "
   ::= { gponMulticastServiceOntsideGemCurrentIntervalEntry 3 }


gponMulticastServiceOntsideGemCurrentIntervalReceiveBlocks  OBJECT-TYPE
   SYNTAX   Counter
   ACCESS   read-only
   STATUS   mandatory
   DESCRIPTION
      "A count of Received GEM Blocks. "
   ::= { gponMulticastServiceOntsideGemCurrentIntervalEntry 4 }


-- *********************************************
--
-- Multicast GEM ONT-SIDE GEM PERFORMANCE MONITOR INTERVAL TABLE
--
-- This is a new table beginning with FGU4.7.4.
-- This interval table contains various GEM port statistics collected
-- at an ONT on multicast GEM port over the previous 8 hours of operation.
-- The past 8 hours are
-- broken into 32 completed 15 minute intervals.  Each row in this table
-- represents one such interval.
--
-- An instance of this table is auto-created upon creation of ONT.
--
-- For ISAM4.2, this table is SUPPORTED (merged from FGU4.7.4).
--
--	For GPON - SUPPORTED as of ISAM4.2
--	For XG-PON1 - SUPPORTED as of ISAM4.6.02
--	For NG-PON2 - SUPPORTED as of ISAM5.2
-- 
--
-- *********************************************


gponMulticastServiceOntsideGemIntervalTable  OBJECT-TYPE
   SYNTAX SEQUENCE OF GponMulticastServiceOntsideGemIntervalEntry
   ACCESS   not-accessible
   STATUS   mandatory
   ::= { gponServicesGroup 42 }


gponMulticastServiceOntsideGemIntervalEntry  OBJECT-TYPE
   SYNTAX   GponMulticastServiceOntsideGemIntervalEntry
   ACCESS   not-accessible
   STATUS   mandatory
   DESCRIPTION
      "An entry in the GPON Multicast Service GEM PM
       Interval Table. "
   INDEX { gponMulticastServiceOntsideGemIntervalOntIndex,
        gponMulticastServiceOntsideGemIntervalNumber }
   ::= { gponMulticastServiceOntsideGemIntervalTable 1 }

GponMulticastServiceOntsideGemIntervalEntry ::= SEQUENCE {
   gponMulticastServiceOntsideGemIntervalOntIndex        IfIndex,
   gponMulticastServiceOntsideGemIntervalNumber       INTEGER,
   gponMulticastServiceOntsideGemIntervalLostFragsDown         Counter,
   gponMulticastServiceOntsideGemIntervalReceiveFrags    Counter,
   gponMulticastServiceOntsideGemIntervalReceiveBlocks      Counter
}

gponMulticastServiceOntsideGemIntervalOntIndex  OBJECT-TYPE
   SYNTAX   IfIndex
   ACCESS   read-only
   STATUS   mandatory
   DESCRIPTION
      "This index is the ifIndex of the physical ONT.  "
   ::= { gponMulticastServiceOntsideGemIntervalEntry 1 }


gponMulticastServiceOntsideGemIntervalNumber  OBJECT-TYPE
   SYNTAX   INTEGER (1..32)
   ACCESS   read-only
   STATUS   mandatory
   DESCRIPTION
      "A number between 1 and 32, where 1 is the most
       recently completed 15 minute interval and 32
       is the 15 minute interval completed 7 hours
       and 45 minutes prior to interval 1.  "
   ::= { gponMulticastServiceOntsideGemIntervalEntry 2 }



gponMulticastServiceOntsideGemIntervalLostFragsDown  OBJECT-TYPE
   SYNTAX   Counter
   ACCESS   read-only
   STATUS   mandatory
   DESCRIPTION
      "A count of Lost GEM Fragments (downstream). "
   ::= { gponMulticastServiceOntsideGemIntervalEntry 3 }


gponMulticastServiceOntsideGemIntervalReceiveFrags  OBJECT-TYPE
   SYNTAX   Counter
   ACCESS   read-only
   STATUS   mandatory
   DESCRIPTION
      "A count of Received GEM Fragments. "
   ::= { gponMulticastServiceOntsideGemIntervalEntry 4 }

gponMulticastServiceOntsideGemIntervalReceiveBlocks  OBJECT-TYPE
   SYNTAX   Counter
   ACCESS   read-only
   STATUS   mandatory
   DESCRIPTION
      "A count of Received GEM Blocks. "
   ::= { gponMulticastServiceOntsideGemIntervalEntry 5 }


-- *********************************************
--
-- Multicast SERVICE OLT-SIDE GEM PERFORMANCE MONITOR CURRENT INTERVAL TABLE
--
-- This is a new table beginning with FGU4.7.4.
-- This current interval table contains various statistics collected for
-- OLT multicast GEM port during the current 15 minute interval
-- of operation.
--
-- An instance of this table is auto-created upon PON or channel pair creation.
--
-- For ISAM4.2, this table is SUPPORTED (merged from FGU4.7.4).
--
--	For GPON - SUPPORTED as of ISAM4.2
--	For XG-PON1 - SUPPORTED as of ISAM4.6.02
--	For NG-PON2 - SUPPORTED as of ISAM5.2 (for channel pairs)
-- 
--
-- *********************************************


gponMulticastServiceOltsideGemCurrentIntervalTable  OBJECT-TYPE
   SYNTAX SEQUENCE OF GponMulticastServiceOltsideGemCurrentIntervalEntry
   ACCESS   not-accessible
   STATUS   mandatory
   ::= { gponServicesGroup 43 }


gponMulticastServiceOltsideGemCurrentIntervalEntry  OBJECT-TYPE
   SYNTAX   GponMulticastServiceOltsideGemCurrentIntervalEntry
   ACCESS   not-accessible
   STATUS   mandatory
   DESCRIPTION
      "An entry in the GPON Multicast Service GEM PM
       CurrentInterval Table. "
   INDEX { gponMulticastServiceOltsideGemCurrentIntervalPonIndex}
   ::= { gponMulticastServiceOltsideGemCurrentIntervalTable 1 }

GponMulticastServiceOltsideGemCurrentIntervalEntry ::= SEQUENCE {
   gponMulticastServiceOltsideGemCurrentIntervalPonIndex       IfIndex,
   gponMulticastServiceOltsideGemCurrentIntervalTransmitBlocks    Counter,
   gponMulticastServiceOltsideGemCurrentIntervalTransmitFrags     Counter
}


gponMulticastServiceOltsideGemCurrentIntervalPonIndex  OBJECT-TYPE
   SYNTAX   IfIndex
   ACCESS   read-only
   STATUS   mandatory
   DESCRIPTION
      "This index is the ifIndex of the physical PON or channel pair.

		As of ISAM5.2, this table is also shared by GPON PONs and NG-PON2
		channel pairs. Therefore, this index can represent the following:
		- PON ifIndex (for PONs) - as of ISAM4.2
		- ChannelPair ifIndex (for channel pairs) - as of ISAM5.2.  "
   ::= { gponMulticastServiceOltsideGemCurrentIntervalEntry 1 }


gponMulticastServiceOltsideGemCurrentIntervalTransmitBlocks  OBJECT-TYPE
   SYNTAX   Counter
   ACCESS   read-only
   STATUS   mandatory
   DESCRIPTION
      "A count of Transmitted GEM Blocks on GEM 4095. "
   ::= { gponMulticastServiceOltsideGemCurrentIntervalEntry 2 }


gponMulticastServiceOltsideGemCurrentIntervalTransmitFrags  OBJECT-TYPE
   SYNTAX   Counter
   ACCESS   read-only
   STATUS   mandatory
   DESCRIPTION
      "A count of Transmitted GEM Fragments on GEM 4095. "
   ::= { gponMulticastServiceOltsideGemCurrentIntervalEntry 3 }


-- *********************************************
--
-- Multicast SERVICE OLT-SIDE GEM PERFORMANCE MONITOR INTERVAL TABLE
--
-- This is a new table beginning with FGU4.7.4.
-- This interval table contains various GEM port statistics collected
-- for the multicast GEM PORT over the previous 8 hours of operation.
-- The past 8 hours are
-- broken into 32 completed 15 minute intervals.
--
-- An instance of this table is auto-created upon PON or channel pair creation.
--
-- For ISAM4.2, this table is SUPPORTED (merged from FGU4.7.4).
--
--	For GPON - SUPPORTED as of ISAM4.2
--	For XG-PON1 - SUPPORTED as of ISAM4.6.02
--	For NG-PON2 - SUPPORTED as of ISAM5.2 (for channel pairs)
-- 
--
-- *********************************************


gponMulticastServiceOltsideGemIntervalTable  OBJECT-TYPE
   SYNTAX SEQUENCE OF GponMulticastServiceOltsideGemIntervalEntry
   ACCESS   not-accessible
   STATUS   mandatory
   ::= { gponServicesGroup 44 }


gponMulticastServiceOltsideGemIntervalEntry  OBJECT-TYPE
   SYNTAX   GponMulticastServiceOltsideGemIntervalEntry
   ACCESS   not-accessible
   STATUS   mandatory
   DESCRIPTION
      "An entry in the GPON Multicast Service GEM PM
       Interval Table. "
   INDEX { gponMulticastServiceOltsideGemIntervalPonIndex,
        gponMulticastServiceOltsideGemIntervalNumber }
   ::= { gponMulticastServiceOltsideGemIntervalTable 1 }

GponMulticastServiceOltsideGemIntervalEntry ::= SEQUENCE {
   gponMulticastServiceOltsideGemIntervalPonIndex        IfIndex,
   gponMulticastServiceOltsideGemIntervalNumber       INTEGER,
   gponMulticastServiceOltsideGemIntervalTransmitBlocks     Counter,
   gponMulticastServiceOltsideGemIntervalTransmitFrags      Counter
}

gponMulticastServiceOltsideGemIntervalPonIndex  OBJECT-TYPE
   SYNTAX   IfIndex
   ACCESS   read-only
   STATUS   mandatory
   DESCRIPTION
      "This index is the ifIndex of the physical PON or channel pair.

		As of ISAM5.2, this table is also shared by GPON PONs and NG-PON2
		channel pairs. Therefore, this index can represent the following:
		- PON ifIndex (for PONs) - as of ISAM4.2
		- ChannelPair ifIndex (for channel pairs) - as of ISAM5.2.  "
   ::= { gponMulticastServiceOltsideGemIntervalEntry 1 }


gponMulticastServiceOltsideGemIntervalNumber  OBJECT-TYPE
   SYNTAX   INTEGER (1..32)
   ACCESS   read-only
   STATUS   mandatory
   DESCRIPTION
      "A number between 1 and 32, where 1 is the most
       recently completed 15 minute interval and 32
       is the 15 minute interval completed 7 hours
       and 45 minutes prior to interval 1.  "
   ::= { gponMulticastServiceOltsideGemIntervalEntry 2 }



gponMulticastServiceOltsideGemIntervalTransmitBlocks  OBJECT-TYPE
   SYNTAX   Counter
   ACCESS   read-only
   STATUS   mandatory
   DESCRIPTION
      "A count of Transmitted GEM Blocks. "
   ::= { gponMulticastServiceOltsideGemIntervalEntry 3 }


gponMulticastServiceOltsideGemIntervalTransmitFrags  OBJECT-TYPE
   SYNTAX   Counter
   ACCESS   read-only
   STATUS   mandatory
   DESCRIPTION
      "A count of Transmitted GEM Fragments. "
   ::= { gponMulticastServiceOltsideGemIntervalEntry 4 }


-- **************************************************************************
--
-- GPON PON PORT LEVEL TROUBLESHOOTING COUNTERS TABLE
--
-- This is a new table beginning with ISAM4.2. For RCR ANTmt80984 - FDT1067
-- PT Counters and Statistics
-- 
-- The table consists of PON port or Channel Pair level counters for Unicast, Broadcast 
-- and Discarded packets in both upstream and downstream. Also includes
-- counters for Multicast traffic in the downstream
--
-- PON port level counters Enable/disable and reset operations are maintained in the 
-- TroubleShootingMgnt subsystem. 
--  
-- The PON port level counters can be enabled/disabled from the Troubleshooting
-- Management. As and when troubleshotting is enabled on the PON port level 
-- (through TROUBLESHOOTING-MIB), an entry in the 'gponOltsidePonPortTroubleshootCounterTable'
-- should be created for that PON port. Similarly the table entry will be destroyed 
-- after disabling. 
--
-- The PON port level counters can be reset to 0 by enabling a control variable
-- in the TROUBLESHOOTING-MIB.
--
--	For GPON - SUPPORTED as of ISAM4.2 (for PONs)
--	For XG-PON1 - SUPPORTED as of ISAM4.6.02
--	For NG-PON2 - SUPPORTED as of ISAM5.2 (for channel pairs)
--  
--
-- ***************************************************************************

gponOltsidePonPortTroubleshootCounterTable  OBJECT-TYPE
	SYNTAX SEQUENCE OF GponOltSidePonPortTroubleshootCounterEntry
	ACCESS	not-accessible
	STATUS	mandatory
::= { gponServicesGroup 45 }

gponOltsidePonPortTroubleshootCounterEntry  OBJECT-TYPE
	SYNTAX 	GponOltSidePonPortTroubleshootCounterEntry
	ACCESS	not-accessible
	STATUS	mandatory
	DESCRIPTION 
		"An entry in the GPON OLT-side PON port
		 Level troubleshooting counter Table. "
	INDEX	{ gponOltsidePonPortTroubleshootCounterponIndex }
::= { gponOltsidePonPortTroubleshootCounterTable 1 }

GponOltSidePonPortTroubleshootCounterEntry ::= SEQUENCE {
	gponOltsidePonPortTroubleshootCounterponIndex	IfIndex,
	gponOltsidePonPortUpBcastFwdFrameCounter		Counter,
	gponOltsidePonPortUpUcastFwdFrameCounter		Counter,
	gponOltsidePonPortDnBcastFwdFrameCounter		Counter,
	gponOltsidePonPortDnUcastFwdFrameCounter		Counter,
	gponOltsidePonPortUpDiscFrameCounter		Counter,
	gponOltsidePonPortDnDiscFrameCounter		Counter,
	gponOltsidePonPortDnMcastFwdFrameCounter		Counter,
	gponOltsidePonPortDnEthernetFrames	OCTET STRING,
	gponOltsidePonPortUpEthernetFrames	OCTET STRING,
	gponOltsidePonPortDnEthernetOctets		OCTET STRING,
	gponOltsidePonPortUpEthernetOctets		OCTET STRING,
	gponOltsidePonPortDnCRCErrorFrames	OCTET STRING,
	gponOltsidePonPortUpCRCErrorFrames	OCTET STRING,
	gponOltsidePonPortDnIllegalsizeFrames	OCTET STRING,
	gponOltsidePonPortUpIllegalsizeFrames	OCTET STRING,
	gponOltsidePonPortUpMcastFrames		OCTET STRING
}

gponOltsidePonPortTroubleshootCounterponIndex OBJECT-TYPE
	SYNTAX	IfIndex
	ACCESS	read-only
	STATUS   mandatory
	DESCRIPTION
		" Each row is indexed by the ifIndex of the
		PON (which is statically assigned based
		on slot/port on the OLT line card).

		As of ISAM5.2, this table is also shared by GPON PONs and NG-PON2
		channel pairs. Therefore, this index can represent the following:
		- PON ifIndex (for PONs) - as of ISAM4.2
		- ChannelPair ifIndex (for channel pairs) - as of ISAM5.2."
::= { gponOltsidePonPortTroubleshootCounterEntry 1 }

gponOltsidePonPortUpBcastFwdFrameCounter OBJECT-TYPE
	SYNTAX   Counter
	ACCESS   read-only
	STATUS   mandatory
	DESCRIPTION
		"The number of broadcast frames received from the user side that are successfully 
		 forwarded by the L2-forwarding engine on a PON port.
	ALCATEL NOTE:
	ACCESS:     NA       USAGE:      NA
	PERSIST:    NO       INSRVMOD:   NO
	RANGE:      NA       DEFVALUE:   NA
	UNITS:      frames   SPARSE:     NA
	DESCR:      NA"
::= { gponOltsidePonPortTroubleshootCounterEntry 2 }

gponOltsidePonPortUpUcastFwdFrameCounter OBJECT-TYPE
	SYNTAX   Counter
	ACCESS   read-only
	STATUS   mandatory
	DESCRIPTION
		"The number of unicast frames received from the user side that are successfully 
		 forwarded by the L2-forwarding engine on a PON port.
	ALCATEL NOTE:
	ACCESS:     NA       USAGE:      NA
	PERSIST:    NO       INSRVMOD:   NO
	RANGE:      NA       DEFVALUE:   NA
	UNITS:      frames   SPARSE:     NA
	DESCR:      NA"
::= { gponOltsidePonPortTroubleshootCounterEntry 3 }

gponOltsidePonPortDnBcastFwdFrameCounter OBJECT-TYPE
	SYNTAX   Counter
	ACCESS     read-only
	STATUS   mandatory
	DESCRIPTION
		"The number of broadcast frames received from the network side that are successfully 
		 forwarded by the L2-forwarding engine on a PON port.
	ALCATEL NOTE:
	ACCESS:     NA       USAGE:      NA
	PERSIST:    NO       INSRVMOD:   NO
	RANGE:      NA       DEFVALUE:   NA
	UNITS:      frames   SPARSE:     NA
	DESCR:      NA"
::= { gponOltsidePonPortTroubleshootCounterEntry 4 }

gponOltsidePonPortDnUcastFwdFrameCounter OBJECT-TYPE
	SYNTAX   Counter
	ACCESS     read-only
	STATUS   mandatory
	DESCRIPTION
		"The number of unicast frames received from the network side that are successfully 
		 forwarded by the L2-forwarding engine on a PON port.
	ALCATEL NOTE:
	ACCESS:     NA       USAGE:      NA
	PERSIST:    NO       INSRVMOD:   NO
	RANGE:      NA       DEFVALUE:   NA
	UNITS:      frames   SPARSE:     NA
	DESCR:      NA"
::= { gponOltsidePonPortTroubleshootCounterEntry 5 }

gponOltsidePonPortUpDiscFrameCounter OBJECT-TYPE
	SYNTAX   Counter
	ACCESS     read-only
	STATUS   mandatory
	DESCRIPTION
		"The number of frames received from the user side that are discarded for any reason 
		 related to the vlanport checks,including policing on a PON port.
	ALCATEL NOTE:
	ACCESS:     NA       USAGE:      NA
	PERSIST:    NO       INSRVMOD:   NO
	RANGE:      NA       DEFVALUE:   NA
	UNITS:      frames   SPARSE:     NA
	DESCR:      NA"
::= { gponOltsidePonPortTroubleshootCounterEntry 6 }

gponOltsidePonPortDnDiscFrameCounter OBJECT-TYPE
	SYNTAX   Counter
	ACCESS     read-only
	STATUS   mandatory
	DESCRIPTION
		"The number of frames received from the network side that are discarded on a PON port.
	ALCATEL NOTE:
	ACCESS:     NA       USAGE:      NA
	PERSIST:    NO       INSRVMOD:   NO
	RANGE:      NA       DEFVALUE:   NA
	UNITS:      frames   SPARSE:     NA
	DESCR:      NA"
::= { gponOltsidePonPortTroubleshootCounterEntry 7 }

gponOltsidePonPortDnMcastFwdFrameCounter OBJECT-TYPE
	SYNTAX   Counter
	ACCESS     read-only
	STATUS   mandatory
	DESCRIPTION
		"The number of multicast frames received from the network side and successfully 
		 forwarded by the L2-forwarding engine on a PON port.
	ALCATEL NOTE:
	ACCESS:     NA       USAGE:      NA
	PERSIST:    NO       INSRVMOD:   NO
	RANGE:      NA       DEFVALUE:   NA
	UNITS:      frames   SPARSE:     NA
	DESCR:      NA"
::= { gponOltsidePonPortTroubleshootCounterEntry  8 }


gponOltsidePonPortDnEthernetFrames  OBJECT-TYPE
    SYNTAX OCTET STRING (SIZE(8))
    ACCESS   read-only
    STATUS   mandatory
    DESCRIPTION
        "The number of transmitted Ethernet frames downstream on a PON port
    ALCATEL NOTE:
    ACCESS:     NA       USAGE:      NA
    PERSIST:    NO       INSRVMOD:   NO
    RANGE:      NA       DEFVALUE:   NA
    UNITS:      frames   SPARSE:     NA
    DESCR:      NA
 	64-BIT counters SUPPORTED as of ISAM4.6"
::= { gponOltsidePonPortTroubleshootCounterEntry  9 }

gponOltsidePonPortUpEthernetFrames  OBJECT-TYPE
    SYNTAX OCTET STRING (SIZE(8))
    ACCESS   read-only
    STATUS   mandatory
    DESCRIPTION
        "The number of received Ethernet frames upstream on a PON port
    ALCATEL NOTE:
    ACCESS:     NA       USAGE:      NA
    PERSIST:    NO       INSRVMOD:   NO
    RANGE:      NA       DEFVALUE:   NA
    UNITS:      frames   SPARSE:     NA
    DESCR:      NA
 	64-BIT counters SUPPORTED as of ISAM4.6"
::= { gponOltsidePonPortTroubleshootCounterEntry  10 }

gponOltsidePonPortDnEthernetOctets  OBJECT-TYPE
    SYNTAX OCTET STRING (SIZE(8))
    ACCESS     read-only
    STATUS   mandatory
    DESCRIPTION
        "The number of transmitted Ethernet bytes downstream on a PON port
    ALCATEL NOTE:
    ACCESS:     NA       USAGE:      NA
    PERSIST:    NO       INSRVMOD:   NO
    RANGE:      NA       DEFVALUE:   NA
    UNITS:      bytes   SPARSE:     NA
    DESCR:      NA
 	64-BIT counters SUPPORTED as of ISAM4.6"
::= { gponOltsidePonPortTroubleshootCounterEntry  11 }

gponOltsidePonPortUpEthernetOctets  OBJECT-TYPE
    SYNTAX OCTET STRING (SIZE(8))
    ACCESS   read-only
    STATUS   mandatory
    DESCRIPTION
        "The number of received Ethernet bytes upstream on a PON port
    ALCATEL NOTE:
    ACCESS:     NA       USAGE:      NA
    PERSIST:    NO       INSRVMOD:   NO
    RANGE:      NA       DEFVALUE:   NA
    UNITS:      bytes   SPARSE:     NA
    DESCR:      NA
 	64-BIT counters SUPPORTED as of ISAM4.6"
::= { gponOltsidePonPortTroubleshootCounterEntry  12 }

gponOltsidePonPortDnCRCErrorFrames  OBJECT-TYPE
    SYNTAX OCTET STRING (SIZE(8))
    ACCESS   read-only
    STATUS   mandatory
    DESCRIPTION
        "The number of transmitted Ethernet frames with CRC error downstream on a PON port
        Notes that this object will always be 0
    ALCATEL NOTE:
    ACCESS:     NA       USAGE:      NA
    PERSIST:    NO       INSRVMOD:   NO
    RANGE:      NA       DEFVALUE:   NA
    UNITS:      frames   SPARSE:     NA
    DESCR:      NA
 	64-BIT counters SUPPORTED as of ISAM4.6"
::= { gponOltsidePonPortTroubleshootCounterEntry  13 }

gponOltsidePonPortUpCRCErrorFrames  OBJECT-TYPE
    SYNTAX OCTET STRING (SIZE(8))
    ACCESS   read-only
    STATUS   mandatory
    DESCRIPTION
        "The number of received Ethernet frames with CRC error upstream on a PON port
    ALCATEL NOTE:
    ACCESS:     NA       USAGE:      NA
    PERSIST:    NO       INSRVMOD:   NO
    RANGE:      NA       DEFVALUE:   NA
    UNITS:      frames   SPARSE:     NA
    DESCR:      NA
 	64-BIT counters SUPPORTED as of ISAM4.6"
::= { gponOltsidePonPortTroubleshootCounterEntry  14 }

gponOltsidePonPortDnIllegalsizeFrames   OBJECT-TYPE
    SYNTAX OCTET STRING (SIZE(8))
    ACCESS   read-only
    STATUS   mandatory
    DESCRIPTION
        "The number of transmitted Ethernet frames with illegal size downstream on a PON port, including oversize and undersize packets
        Notes that this object will always be 0.

    ALCATEL NOTE:
    ACCESS:     NA       USAGE:      NA
    PERSIST:    NO       INSRVMOD:   NO
    RANGE:      NA       DEFVALUE:   NA
    UNITS:      frames   SPARSE:     NA
    DESCR:      NA
 	64-BIT counters SUPPORTED as of ISAM4.6"
::= { gponOltsidePonPortTroubleshootCounterEntry  15 }

gponOltsidePonPortUpIllegalsizeFrames   OBJECT-TYPE
    SYNTAX OCTET STRING (SIZE(8))
    ACCESS   read-only
    STATUS   mandatory
    DESCRIPTION
        "The number of received Ethernet frames with illegal size upstream on a PON port, including oversize and undersize packets
    ALCATEL NOTE:
    ACCESS:     NA       USAGE:      NA
    PERSIST:    NO       INSRVMOD:   NO
    RANGE:      NA       DEFVALUE:   NA
    UNITS:      frames   SPARSE:     NA
    DESCR:      NA
 	64-BIT counters SUPPORTED as of ISAM4.6"
::= { gponOltsidePonPortTroubleshootCounterEntry  16 }

gponOltsidePonPortUpMcastFrames OBJECT-TYPE
    SYNTAX OCTET STRING (SIZE(8))
    ACCESS   read-only
    STATUS   mandatory
    DESCRIPTION
        "The number of received multicat frames upstream on a PON port
    ALCATEL NOTE:
    ACCESS:     NA       USAGE:      NA
    PERSIST:    NO       INSRVMOD:   NO
    RANGE:      NA       DEFVALUE:   NA
    UNITS:      frames   SPARSE:     NA
    DESCR:      NA
 	64-BIT counters SUPPORTED as of ISAM4.6"
::= { gponOltsidePonPortTroubleshootCounterEntry  17 }



-- *********************************************
-- GPON SNMP OVER IP SERVICE TABLE
--
-- This table was first introduced in ISAM4.4
--
-- This table contains information regarding a SNMP over VEIP or IP service for
-- a specific vlan port. 
--
-- ISAM4.4 only supports a single SNMP service per VEIP or vlan port.
-- Therefore, for ISAM4.4, only a single service per VEIP or vlan port is supported.
-- Rows are created by the operator.
--
--	For GPON - SUPPORTED as of ISAM4.4
--	For XG-PON1 - SUPPORTED as of ISAM4.6.02
--	For NG-PON2 - NOT SUPPORTED as of ISAM5.2
-- 
--
-- *********************************************

gponSnmpIpServiceTable OBJECT-TYPE
	SYNTAX	SEQUENCE OF GponSnmpIpServiceEntry
	ACCESS	not-accessible
	STATUS	mandatory
	DESCRIPTION
		"This object contains a table for creating and storing
		information regarding a Snmp service.  "
::= { gponServicesGroup 53 }

gponSnmpIpServiceEntry OBJECT-TYPE
	SYNTAX 	GponSnmpIpServiceEntry
	ACCESS	not-accessible
	STATUS	mandatory
	DESCRIPTION
		"Rows of this table contain Snmp service information. "
	INDEX {gponSnmpIpServiceUniIndex}
::= {gponSnmpIpServiceTable 1}

GponSnmpIpServiceEntry ::=
	SEQUENCE { 
		gponSnmpIpServiceUniIndex		IfIndex,
--		gponSnmpIpServiceNumber		INTEGER,
		gponSnmpIpServiceRowStatus 		RowStatus,
--		gponSnmpIpServiceVersion		INTEGER,
--		gponSnmpIpServiceTcpUdpPortNum		INTEGER,
--		gponSnmpIpServiceDscpSetting		INTEGER,
--      		gponSnmpIpServiceServerIpv4Address	IpAddress,
--		gponSnmpIpServiceServerTcpUdpPortNum	INTEGER,
--		gponSnmpIpServiceSecurityName		DisplayString,
		gponSnmpIpServiceReadCommunity	DisplayString,
		gponSnmpIpServiceWriteCommunity	DisplayString,
--		gponSnmpIpServiceSystemName	DisplayString,
         		gponSnmpIpServiceIPHC	InterfaceIndexOrZero
}

gponSnmpIpServiceUniIndex OBJECT-TYPE 
	SYNTAX IfIndex
	ACCESS read-only
	STATUS mandatory
	DESCRIPTION
	    "This index is the ifIndex of a VEIP. "
::= { gponSnmpIpServiceEntry 1}

-- gponSnmpIpServiceNumber 	OBJECT-TYPE 
--	SYNTAX	INTEGER
--	ACCESS read-only
--	STATUS mandatory
--	DESCRIPTION
--	    "This table index is the number of the SNMP IP service on the Generic IP UNI.		
--		As of FTTU4.7.50+, this value must be 1 (i.e. only a single SNMP service per Generic IP UNI).  "
--  ::= {gponSnmpIpServiceEntry 2}


gponSnmpIpServiceRowStatus OBJECT-TYPE 
	SYNTAX	RowStatus
	ACCESS	read-write
	STATUS  mandatory
	DESCRIPTION
		"This object is used to create a new row or modify or
         		delete an existing row in this table. "
::= { gponSnmpIpServiceEntry  3}


-- gponSnmpIpServiceVersion OBJECT-TYPE 
--	SYNTAX	INTEGER
--	ACCESS	read-write
--	STATUS  mandatory
--	DESCRIPTION 
--		" Represents the SNMP protocol version to be supported.
--		  Options are as follows:
--
--		1 = Version 1 (default)
--		2 = Version 2
--		3 = Version 3
--
--		 Modification is NOT PERMITTED. "
--      ::= { gponSnmpIpServiceEntry  4}


-- gponSnmpIpServiceTcpUdpPortNum OBJECT-TYPE
--	SYNTAX 	INTEGER
--	ACCESS	read-write
--	STATUS	mandatory
--	DESCRIPTION 
--		" Specifies the source UDP Port number to be used for this SNMP service.
--
--		  Valid range is 0 thru 65535.
--		  No default - must be provided by operator.
--
--		  As of initial FTTU4.7.50+, the only supported value is 161.
--
--		  Modification is NOT SUPPORTED. "
--	::= { gponSnmpIpServiceEntry  5 }

-- gponSnmpIpServiceDscpSetting  OBJECT-TYPE
--	SYNTAX 	INTEGER
--	ACCESS	read-write
--	STATUS	mandatory
--	DESCRIPTION 
--		" Specifies the value of the DSCP field of the IP header for SNMP packets associated
--		  with this SNMP service.
--
--		  Only the low order 6 bits are relevant - since that is
--		  the size of the DSCP field in IP packets.
--
--	 	 Default = 46 (decimal) = 0x002E (hex) = 101110 (binary) - Expedited Forwarding.
--
--		  Modification is SUPPORTED. "
--	::= { gponSnmpIpServiceEntry  6  }

-- gponSnmpIpServiceServerIpv4Address OBJECT-TYPE 
--	SYNTAX  	IpAddress
--	ACCESS	read-write
--	STATUS	mandatory
--	DESCRIPTION 
--		" This represents the IPv4 address of the SNMP server.
--
--		  Default = 0.0.0.0
--
--		  Modification is SUPPORTED.  "
--	::= { gponSnmpIpServiceEntry  7 }


-- gponSnmpIpServiceServerTcpUdpPortNum OBJECT-TYPE 
--	SYNTAX  	INTEGER
--	ACCESS	read-write
--	STATUS	mandatory
--	DESCRIPTION 
--		" Specifies the UDP Port number of the SNMP server to be used for this SNMP service.
--
--		  Valid range is 0 thru 65535.
--		  No default - must be provided by operator.
--
--		  As of initial FTTU4.7.50+, the only supported value is 161.
--
--		  Modification is NOT SUPPORTED. "
--	::= { gponSnmpIpServiceEntry  8 }


-- gponSnmpIpServiceSecurityName OBJECT-TYPE 
--	SYNTAX  	DisplayString (SIZE(0..50))
--	ACCESS	read-write
--	STATUS	mandatory
--	DESCRIPTION 
--		" Specifies the Security name of this SNMP entity in the ONT.
--
--		  Relevant text from OMCI standard says the following:
--		  Represents the SNMP security name string in human-readable format
--		  that is independent of the security model.  SecurityName is defined in IETF RFC-2571.
--
--		  Default = null string.
--
--		  Modification is SUPPORTED. "
--	::= { gponSnmpIpServiceEntry  9 }


gponSnmpIpServiceReadCommunity OBJECT-TYPE 
	SYNTAX  	DisplayString (SIZE(0..50))
	ACCESS	read-write
	STATUS	mandatory
	DESCRIPTION 
		" Specifies the string for SNMP read community.

		  Default = 'public'.

		  Modification is SUPPORTED. "
	::= { gponSnmpIpServiceEntry  10 }


gponSnmpIpServiceWriteCommunity OBJECT-TYPE 
	SYNTAX  	DisplayString (SIZE(0..50))
	ACCESS	read-write
	STATUS	mandatory
	DESCRIPTION 
		" Specifies the string for SNMP write community.

		  Default = 'private'.

		  Modification is SUPPORTED. "
	::= { gponSnmpIpServiceEntry  11 }

-- gponSnmpIpServiceSystemName OBJECT-TYPE 
--	SYNTAX  	DisplayString (SIZE(0..50))
--	ACCESS	read-write
--	STATUS	mandatory
--	DESCRIPTION 
--		" Specifies the System name of this SNMP entity in the ONT.
--
--		  Relevant text from OMCI standard says the following:
--		  Represents the SNMP system name string in human-readable format.
--		  SysName is defined in IETF RFC-3418.
--
--		  Default = null string.
--
--		  Modification is SUPPORTED. "
--	::= { gponSnmpIpServiceEntry  12 }

gponSnmpIpServiceIPHC  OBJECT-TYPE
        SYNTAX  InterfaceIndexOrZero
        ACCESS  read-write
        STATUS  mandatory
        DESCRIPTION     
                "  This attribute was introduced with ISAM4.4.

                   When non-zero, this attribute must point to an appropriate row in gponOntIpHostTable. This would
	     be the situation when ONT SNMP agent uses IP service explicitly configured via this MIB.  When used
	     in this manner, the ifIndex format must be the appropriate VLAN.PORT ifIndex (for the corresponding row
	     in gponOntIpHostTable).

                   Zero means ONT SNMP agent uses IP service configured internally via VEIP mechanisms.
                   
                   Default = 0 = SNMP over VEIP.

	     Modification is SUPPORTED. "
        ::= { gponSnmpIpServiceEntry  13 }



-- *********************************************
--
-- Pon Utilization PERFORMANCE MONITOR CURRENT INTERVAL TABLE (5-minute cycle)
--
-- This is a new table beginning with ISAM 5.2 (copied and modified from FTTU4.9.20).
-- This current interval table contains various statistics collected for 
-- Pon Utilization collected during the current 5-minute interval of operation.  
--
-- An instance of this table is auto-created/deleted in accordance with the following:
-- 'Pon Utilization PM Collect Indicator' setting of the PON (in this MIB) 
-- 'Channel Pair Utilization PM Collector' setting of channel pair (in NG-PON2 MIB)
--
--	For GPON - SUPPORTED as of ISAM5.2 (for PONs)
--	For XG-PON1 - NOT SUPPORTED
--	For NG-PON2 - NOT SUPPORTED as of ISAM5.2.01 (for channel pairs) 
--
-- *********************************************


gponOltSidePonUtilPmCurrentIntervalTable  OBJECT-TYPE
	SYNTAX SEQUENCE OF GponOltSidePonUtilPmCurrentIntervalEntry
	ACCESS	not-accessible
	STATUS	mandatory
	::= { gponServicesGroup 57}


gponOltSidePonUtilPmCurrentIntervalEntry  OBJECT-TYPE
	SYNTAX 	GponOltSidePonUtilPmCurrentIntervalEntry
	ACCESS	not-accessible
	STATUS	mandatory
	DESCRIPTION 
		"An entry in the PON Utilization PM
		 CurrentInterval Table. "
	INDEX	{ gponOltSidePonUtilPmCurrentIntervalPonIndex}
	::= { gponOltSidePonUtilPmCurrentIntervalTable 1 }

GponOltSidePonUtilPmCurrentIntervalEntry ::= SEQUENCE {
        gponOltSidePonUtilPmCurrentIntervalPonIndex     IfIndex,
        gponOltSidePonUtilTxPmCurrentIntervalUcastUtil  Counter,
--        gponOltSidePonUtilRxPmCurrentIntervalUcastUtil  Counter,
        gponOltSidePonUtilTxPmCurrentIntervalMcastUtil  Counter,
        gponOltSidePonUtilTxPmCurrentIntervalBcastUtil  Counter,
        gponOltSidePonUtilTxPmCurrentIntervalTotalUtil  Counter,
        gponOltSidePonUtilRxPmCurrentIntervalTotalUtil  Counter,
        gponOltSidePonUtilTxPmCurrentIntervalUcastBytes     OCTET STRING,
--        gponOltSidePonUtilRxPmCurrentIntervalUcastBytes     OCTET STRING,
        gponOltSidePonUtilTxPmCurrentIntervalMcastBytes     OCTET STRING,
        gponOltSidePonUtilTxPmCurrentIntervalBcastBytes     OCTET STRING,
        gponOltSidePonUtilTxPmCurrentIntervalTotalBytes     OCTET STRING,
        gponOltSidePonUtilRxPmCurrentIntervalTotalBytes     OCTET STRING,
        gponOltSidePonUtilTxPmCurrentIntervalUcastDropBytes    OCTET STRING,
	gponOltSidePonUtilRxPmCurrentIntervalTotalDropBytes    OCTET STRING,
        gponOltSidePonUtilPmCurrentIntervalNumActiveOnts     INTEGER,
        gponOltSidePonUtilRxPmCurrentIntervalDBACongestionTime    INTEGER,
	gponOltSidePonUtilTxPmCurrentIntervalMcastDropBytes	OCTET STRING,
	gponOltSidePonUtilTxPmCurrentIntervalBcastDropBytes	OCTET STRING,
	gponOltSidePonUtilTxPmCurrentIntervalTotalDropBytes	OCTET STRING,	

        gponOltSidePonUtilTxPmCurrentIntervalUcastPackets     OCTET STRING,
--        gponOltSidePonUtilRxPmCurrentIntervalUcastPackets     OCTET STRING,
        gponOltSidePonUtilTxPmCurrentIntervalMcastPackets     OCTET STRING,
        gponOltSidePonUtilTxPmCurrentIntervalBcastPackets     OCTET STRING,
        gponOltSidePonUtilTxPmCurrentIntervalTotalPackets     OCTET STRING,
        gponOltSidePonUtilRxPmCurrentIntervalTotalPackets     OCTET STRING,
        gponOltSidePonUtilTxPmCurrentIntervalUcastDropPackets    OCTET STRING,
        gponOltSidePonUtilRxPmCurrentIntervalTotalDropPackets    OCTET STRING,
	gponOltSidePonUtilTxPmCurrentIntervalMcastDropPackets	OCTET STRING,
	gponOltSidePonUtilTxPmCurrentIntervalBcastDropPackets	OCTET STRING,
	gponOltSidePonUtilTxPmCurrentIntervalTotalDropPackets	OCTET STRING	
}
gponOltSidePonUtilPmCurrentIntervalPonIndex  OBJECT-TYPE
	SYNTAX 	IfIndex
	ACCESS	read-only
	STATUS	mandatory
	DESCRIPTION 
		"This index is the ifIndex of the physical PON (or channel-pair)

		As of ISAM5.2.01, this table is shared by GPON PONs and NG-PON2
		channel pairs. Therefore, this index can represent the following:
		- PON ifIndex (for PONs) - as of ISAM5.2
		- ChannelPair ifIndex (for channel pairs) - as of ISAM5.2.01  "
	::= { gponOltSidePonUtilPmCurrentIntervalEntry 1 }

gponOltSidePonUtilTxPmCurrentIntervalUcastUtil  OBJECT-TYPE
        SYNTAX  Counter
        ACCESS  read-only
        STATUS  mandatory
        DESCRIPTION
                "A count of unicast traffic PON Utilization on the pon port in
                 the downstream direction in percentage.

		 Range is 0..100000, represented in percentage as 0.00 to 1000.00

		Denominator is  non-multicast BW of the PON
		(calculated as the max PON BW less that reserved for multicast in the QOS cac-profile).

		The utilization percentage can exceed 100% because the denominator is the non-multicast BW of the PON
		(calculated as the max PON BW less that reserved for multicast in the QOS cac-profile), 
		yet the unicast (and broadcast) traffic can use the BW reserved for multicast if it is available.


		For GPON - SUPPORTED as of ISAM5.2
		For XG-PON1 - NOT SUPPORTED
		For NG-PON2 - NOT SUPPORTED as of ISAM5.2.01 (for channel pairs) "                    
        ::= { gponOltSidePonUtilPmCurrentIntervalEntry 2 }                    
               
   

-- gponOltSidePonUtilRxPmCurrentIntervalUcastUtil  OBJECT-TYPE
--        SYNTAX  Counter
--        ACCESS  read-only
--        STATUS  mandatory
--        DESCRIPTION
--                "A count of unicast traffic PON Utilization on the pon port in
--                 upstream direction in percentage.
--
--		 Range is 0..10000, represented in percentage as 0.00 to 100.00
--
--
--		 NOT SUPORTED as of ISAM5.2 "                          
--       ::= { gponOltSidePonUtilPmCurrentIntervalEntry 3}                    


gponOltSidePonUtilTxPmCurrentIntervalMcastUtil   OBJECT-TYPE
        SYNTAX  Counter
        ACCESS  read-only
        STATUS  mandatory
        DESCRIPTION
                "A count of Multicast traffic PON Utilization on the pon port in
                 the downstream direction in percentage.

		 Range is 0..10000, represented in percentage as 0.00 to 100.00

		Denominator is  reserved multicast BW of the PON (per QoS cac-profile).

		For GPON - SUPPORTED as of ISAM5.2
		For XG-PON1 - NOT SUPPORTED
		For NG-PON2 - NOT SUPPORTED as of ISAM5.2.01 (for channel pairs) "                    
        ::= { gponOltSidePonUtilPmCurrentIntervalEntry 4}                    

gponOltSidePonUtilTxPmCurrentIntervalBcastUtil   OBJECT-TYPE
        SYNTAX  Counter
        ACCESS  read-only
        STATUS  mandatory
        DESCRIPTION
                "A count of Broadcast traffic PON Utilization on the pon port in
                 the downstream direction in percentage.

		 Range is 0..100000, represented in percentage as 0.00 to 1000.00

		Denominator is  non-multicast BW of the PON
		(calculated as the max PON BW less that reserved for multicast in the QOS cac-profile).

		The utilization percentage can exceed 100% because the denominator is the non-multicast BW of the PON
		(calculated as the max PON BW less that reserved for multicast in the QOS cac-profile), 
		yet the unicast (and broadcast) traffic can use the BW reserved for multicast if it is available.

		For GPON - SUPPORTED as of ISAM5.2
		For XG-PON1 - NOT SUPPORTED
		For NG-PON2 - NOT SUPPORTED as of ISAM5.2.01 (for channel pairs) "                    
        ::= { gponOltSidePonUtilPmCurrentIntervalEntry 5}                    

gponOltSidePonUtilTxPmCurrentIntervalTotalUtil  OBJECT-TYPE
        SYNTAX  Counter
        ACCESS  read-only
        STATUS  mandatory
        DESCRIPTION
                "A count of total(unicast + multicast + broadcast) traffic PON 
                 Utilization on the pon port in the downstream direction in  
                 percentage.

		 Range is 0..10000, represented in percentage as 0.00 to 100.00

		Denominator is total downstream BW of the PON.

		For GPON - SUPPORTED as of ISAM5.2
		For XG-PON1 - NOT SUPPORTED
		For NG-PON2 - NOT SUPPORTED as of ISAM5.2.01 (for channel pairs) "
        ::= { gponOltSidePonUtilPmCurrentIntervalEntry 6 }
               
        
gponOltSidePonUtilRxPmCurrentIntervalTotalUtil  OBJECT-TYPE
        SYNTAX  Counter
        ACCESS  read-only
        STATUS  mandatory
        DESCRIPTION
                "A count of total(on unicast GEM ports) traffic PON 
                 Utilization on the pon port in the upstream direction in 
                 percentage.

		 Range is 0..10000, represented in percentage as 0.00 to 100.00

		Denominator is total upstream BW of the PON.

		For GPON - SUPPORTED as of ISAM5.2
		For XG-PON1 - NOT SUPPORTED
		For NG-PON2 - NOT SUPPORTED as of ISAM5.2.01 (for channel pairs) "
        ::= { gponOltSidePonUtilPmCurrentIntervalEntry 7 }


gponOltSidePonUtilTxPmCurrentIntervalUcastBytes     OBJECT-TYPE
        SYNTAX  OCTET STRING (SIZE(8))
        ACCESS  read-only
        STATUS  mandatory
        DESCRIPTION
                "A count of unicast traffic bytes transmitted on the pon port in
                 the downstream direction

		For GPON - SUPPORTED as of ISAM5.2
		For XG-PON1 - NOT SUPPORTED
		For NG-PON2 - NOT SUPPORTED as of ISAM5.2.01 (for channel pairs) "                    
        ::= { gponOltSidePonUtilPmCurrentIntervalEntry 8 }                    
               
   

-- gponOltSidePonUtilRxPmCurrentIntervalUcastBytes    OBJECT-TYPE
--        SYNTAX  OCTET STRING (SIZE(8))
--        ACCESS  read-only
--        STATUS  mandatory
--        DESCRIPTION
--                "A count of unicast traffic bytes received on the pon port in
--                 upstream direction
--
-- 		 NOT SUPORTED as of ISAM5.2 "                          
--        ::= { gponOltSidePonUtilPmCurrentIntervalEntry 9 }                    


gponOltSidePonUtilTxPmCurrentIntervalMcastBytes    OBJECT-TYPE
        SYNTAX  OCTET STRING (SIZE(8))
        ACCESS  read-only
        STATUS  mandatory        
		DESCRIPTION
                "A count of Multicast traffic bytes transmitted on the pon port in
                 the downstream direction

		For GPON - SUPPORTED as of ISAM5.2
		For XG-PON1 - NOT SUPPORTED
		For NG-PON2 - NOT SUPPORTED as of ISAM5.2.01 (for channel pairs) "                    
        ::= { gponOltSidePonUtilPmCurrentIntervalEntry 10 }                    

gponOltSidePonUtilTxPmCurrentIntervalBcastBytes    OBJECT-TYPE
        SYNTAX  OCTET STRING (SIZE(8))
        ACCESS  read-only
        STATUS  mandatory
        DESCRIPTION
                "A count of Broadcast traffic bytes transmitted on the pon port in
                 the downstream direction

		For GPON - SUPPORTED as of ISAM5.2
		For XG-PON1 - NOT SUPPORTED
		For NG-PON2 - NOT SUPPORTED as of ISAM5.2.01 (for channel pairs) "                    
        ::= { gponOltSidePonUtilPmCurrentIntervalEntry 11}                    

   
gponOltSidePonUtilTxPmCurrentIntervalTotalBytes     OBJECT-TYPE
        SYNTAX  OCTET STRING (SIZE(8))
        ACCESS  read-only
        STATUS  mandatory
        DESCRIPTION
                "A count of total(unicast+multicast+broadcast) traffic bytes 
                 transmitted on the pon port in the downstream direction

		For GPON - SUPPORTED as of ISAM5.2
		For XG-PON1 - NOT SUPPORTED
		For NG-PON2 - NOT SUPPORTED as of ISAM5.2.01 (for channel pairs) "          
        ::= { gponOltSidePonUtilPmCurrentIntervalEntry 12 }
               
        
gponOltSidePonUtilRxPmCurrentIntervalTotalBytes     OBJECT-TYPE
        SYNTAX  OCTET STRING (SIZE(8))
        ACCESS  read-only
        STATUS  mandatory
        DESCRIPTION
                "A count of total (on unicast GEM ports) traffic bytes 
                 on the pon port in the upstream direction.

		For GPON - SUPPORTED as of ISAM5.2
		For XG-PON1 - NOT SUPPORTED
		For NG-PON2 - NOT SUPPORTED as of ISAM5.2.01 (for channel pairs) "          
        ::= { gponOltSidePonUtilPmCurrentIntervalEntry 13 }
               
gponOltSidePonUtilTxPmCurrentIntervalUcastDropBytes    OBJECT-TYPE
        SYNTAX  OCTET STRING (SIZE(8))
        ACCESS  read-only
        STATUS  mandatory
        DESCRIPTION
                "A count of unicast traffic drop bytes on the pon port in
                 the downstream direction

		For GPON - SUPPORTED as of ISAM5.2
		For XG-PON1 - NOT SUPPORTED
		For NG-PON2 - NOT SUPPORTED as of ISAM5.2.01 (for channel pairs) "                    
        ::= { gponOltSidePonUtilPmCurrentIntervalEntry 14 }  
                  
               
gponOltSidePonUtilRxPmCurrentIntervalTotalDropBytes    OBJECT-TYPE
        SYNTAX  OCTET STRING (SIZE(8))
        ACCESS  read-only
        STATUS  mandatory
        DESCRIPTION
                "A count of unicast traffic drop bytes on the pon port in
                 upstream direction 

		For GPON - SUPPORTED as of ISAM5.2
		For XG-PON1 - NOT SUPPORTED
		For NG-PON2 - NOT SUPPORTED as of ISAM5.2.01 (for channel pairs) "                          
        ::= { gponOltSidePonUtilPmCurrentIntervalEntry 15 } 
                   

gponOltSidePonUtilPmCurrentIntervalNumActiveOnts     OBJECT-TYPE
        SYNTAX  INTEGER
        ACCESS  read-only
        STATUS  mandatory
        DESCRIPTION
                "A count of the number of active ONTs on the pon port.

		 Range is 0..256

		For GPON - SUPPORTED as of ISAM5.2
		For XG-PON1 - NOT SUPPORTED
		For NG-PON2 - NOT SUPPORTED as of ISAM5.2.01 (for channel pairs) "                          
        ::= { gponOltSidePonUtilPmCurrentIntervalEntry 16 }                    
               
gponOltSidePonUtilRxPmCurrentIntervalDBACongestionTime    OBJECT-TYPE
        SYNTAX  INTEGER
        ACCESS  read-only
        STATUS  mandatory
        DESCRIPTION
                "The percentage of the 5-minute time interval DBA engine
		 has allocated all of available bandwidth.
 
		 Range is 0..10000, represented in percentage as 0.00 to 100.00


		For GPON - SUPPORTED as of ISAM5.2
		For XG-PON1 - NOT SUPPORTED
		For NG-PON2 - NOT SUPPORTED as of ISAM5.2.01 (for channel pairs) "                          
        ::= { gponOltSidePonUtilPmCurrentIntervalEntry 17 }   


gponOltSidePonUtilTxPmCurrentIntervalMcastDropBytes    OBJECT-TYPE
        SYNTAX  OCTET STRING (SIZE(8))
        ACCESS  read-only
        STATUS  mandatory
        DESCRIPTION
                "A count of multicast traffic drop bytes on the pon port in
                 the downstream direction

		For GPON - SUPPORTED as of ISAM5.2
		For XG-PON1 - NOT SUPPORTED
		For NG-PON2 - NOT SUPPORTED as of ISAM5.2.01 (for channel pairs) "                    
        ::= { gponOltSidePonUtilPmCurrentIntervalEntry 18 }

gponOltSidePonUtilTxPmCurrentIntervalBcastDropBytes    OBJECT-TYPE
        SYNTAX  OCTET STRING (SIZE(8))
        ACCESS  read-only
        STATUS  mandatory
        DESCRIPTION
                "A count of broadcast traffic drop bytes on the pon port in
                 the downstream direction

		For GPON - SUPPORTED as of ISAM5.2
		For XG-PON1 - NOT SUPPORTED
		For NG-PON2 - NOT SUPPORTED as of ISAM5.2.01 (for channel pairs) "                    
        ::= { gponOltSidePonUtilPmCurrentIntervalEntry 19 } 


gponOltSidePonUtilTxPmCurrentIntervalTotalDropBytes    OBJECT-TYPE
        SYNTAX  OCTET STRING (SIZE(8))
        ACCESS  read-only
        STATUS  mandatory
        DESCRIPTION
                "A count of total traffic drop bytes on the pon port in
                 the downstream direction

		For GPON - SUPPORTED as of ISAM5.2
		For XG-PON1 - NOT SUPPORTED
		For NG-PON2 - NOT SUPPORTED as of ISAM5.2.01 (for channel pairs) "                    
        ::= { gponOltSidePonUtilPmCurrentIntervalEntry 20 } 



gponOltSidePonUtilTxPmCurrentIntervalUcastPackets     OBJECT-TYPE
        SYNTAX  OCTET STRING (SIZE(8))
        ACCESS  read-only
        STATUS  mandatory
        DESCRIPTION
                "A count of unicast traffic Packets transmitted on the pon port in
                 the downstream direction

		For GPON - SUPPORTED as of ISAM5.2
		For XG-PON1 - NOT SUPPORTED
		For NG-PON2 - NOT SUPPORTED as of ISAM5.2.01 (for channel pairs) "                    
        ::= { gponOltSidePonUtilPmCurrentIntervalEntry 21 }                    
               
   

-- gponOltSidePonUtilRxPmCurrentIntervalUcastPackets    OBJECT-TYPE
--        SYNTAX  OCTET STRING (SIZE(8))
--        ACCESS  read-only
--        STATUS  mandatory
--        DESCRIPTION
--                "A count of unicast traffic Packets received on the pon port in
--                 upstream direction
--
-- 		 NOT SUPORTED as of ISAM5.2 "                          
--        ::= { gponOltSidePonUtilPmCurrentIntervalEntry 22 }                    


gponOltSidePonUtilTxPmCurrentIntervalMcastPackets    OBJECT-TYPE
        SYNTAX  OCTET STRING (SIZE(8))
        ACCESS  read-only
        STATUS  mandatory        
		DESCRIPTION
                "A count of Multicast traffic Packets transmitted on the pon port in
                 the downstream direction

		For GPON - SUPPORTED as of ISAM5.2
		For XG-PON1 - NOT SUPPORTED
		For NG-PON2 - NOT SUPPORTED as of ISAM5.2.01 (for channel pairs) "                    
        ::= { gponOltSidePonUtilPmCurrentIntervalEntry 23 }                    

gponOltSidePonUtilTxPmCurrentIntervalBcastPackets    OBJECT-TYPE
        SYNTAX  OCTET STRING (SIZE(8))
        ACCESS  read-only
        STATUS  mandatory
        DESCRIPTION
                "A count of Broadcast traffic Packets transmitted on the pon port in
                 the downstream direction

		For GPON - SUPPORTED as of ISAM5.2
		For XG-PON1 - NOT SUPPORTED
		For NG-PON2 - NOT SUPPORTED as of ISAM5.2.01 (for channel pairs) "                    
        ::= { gponOltSidePonUtilPmCurrentIntervalEntry 24}                    

   
gponOltSidePonUtilTxPmCurrentIntervalTotalPackets     OBJECT-TYPE
        SYNTAX  OCTET STRING (SIZE(8))
        ACCESS  read-only
        STATUS  mandatory
        DESCRIPTION
                "A count of total(unicast+multicast+broadcast) traffic Packets 
                 transmitted on the pon port in the downstream direction

		For GPON - SUPPORTED as of ISAM5.2
		For XG-PON1 - NOT SUPPORTED
		For NG-PON2 - NOT SUPPORTED as of ISAM5.2.01 (for channel pairs) "          
        ::= { gponOltSidePonUtilPmCurrentIntervalEntry 25 }
               
        
gponOltSidePonUtilRxPmCurrentIntervalTotalPackets     OBJECT-TYPE
        SYNTAX  OCTET STRING (SIZE(8))
        ACCESS  read-only
        STATUS  mandatory
        DESCRIPTION
                "A count of total (on unicast GEM ports) traffic Packets 
                 on the pon port in the upstream direction

		For GPON - SUPPORTED as of ISAM5.2
		For XG-PON1 - NOT SUPPORTED
		For NG-PON2 - NOT SUPPORTED as of ISAM5.2.01 (for channel pairs) "          
        ::= { gponOltSidePonUtilPmCurrentIntervalEntry 26 }
               
gponOltSidePonUtilTxPmCurrentIntervalUcastDropPackets    OBJECT-TYPE
        SYNTAX  OCTET STRING (SIZE(8))
        ACCESS  read-only
        STATUS  mandatory
        DESCRIPTION
                "A count of unicast traffic drop Packets on the pon port in
                 the downstream direction

		For GPON - SUPPORTED as of ISAM5.2
		For XG-PON1 - NOT SUPPORTED
		For NG-PON2 - NOT SUPPORTED as of ISAM5.2.01 (for channel pairs) "                    
        ::= { gponOltSidePonUtilPmCurrentIntervalEntry 27 }                    
               
gponOltSidePonUtilRxPmCurrentIntervalTotalDropPackets    OBJECT-TYPE
        SYNTAX  OCTET STRING (SIZE(8))
        ACCESS  read-only
        STATUS  mandatory
        DESCRIPTION
                "A count of Total traffic drop Packets on the pon port in
                 upstream direction 

		For GPON - SUPPORTED as of ISAM5.2
		For XG-PON1 - NOT SUPPORTED
		For NG-PON2 - NOT SUPPORTED as of ISAM5.2.01 (for channel pairs) "                          
        ::= { gponOltSidePonUtilPmCurrentIntervalEntry 28 }  

gponOltSidePonUtilTxPmCurrentIntervalMcastDropPackets    OBJECT-TYPE
        SYNTAX  OCTET STRING (SIZE(8))
        ACCESS  read-only
        STATUS  mandatory
        DESCRIPTION
                "A count of multicast traffic drop Packets on the pon port in
                 the downstream direction

		For GPON - SUPPORTED as of ISAM5.2
		For XG-PON1 - NOT SUPPORTED
		For NG-PON2 - NOT SUPPORTED as of ISAM5.2.01 (for channel pairs) "                    
        ::= { gponOltSidePonUtilPmCurrentIntervalEntry 29 }

gponOltSidePonUtilTxPmCurrentIntervalBcastDropPackets    OBJECT-TYPE
        SYNTAX  OCTET STRING (SIZE(8))
        ACCESS  read-only
        STATUS  mandatory
        DESCRIPTION
                "A count of broadcast traffic drop Packets on the pon port in
                 the downstream direction

		For GPON - SUPPORTED as of ISAM5.2
		For XG-PON1 - NOT SUPPORTED
		For NG-PON2 - NOT SUPPORTED as of ISAM5.2.01 (for channel pairs) "                    
        ::= { gponOltSidePonUtilPmCurrentIntervalEntry 30 }   

gponOltSidePonUtilTxPmCurrentIntervalTotalDropPackets    OBJECT-TYPE
        SYNTAX  OCTET STRING (SIZE(8))
        ACCESS  read-only
        STATUS  mandatory
        DESCRIPTION
                "A count of total traffic drop Packets on the pon port in
                 the downstream direction

		For GPON - SUPPORTED as of ISAM5.2
		For XG-PON1 - NOT SUPPORTED
		For NG-PON2 - NOT SUPPORTED as of ISAM5.2.01 (for channel pairs) "                    
        ::= { gponOltSidePonUtilPmCurrentIntervalEntry 31 }                      


-- *********************************************
--
-- Pon Utilization PERFORMANCE MONITOR INTERVAL TABLE (5-minute cycle)
--
-- This is a new table beginning with ISAM5.2 (copied and modified from FTTU4.9.20).
-- This interval table contains the PON utilization statistics collected
-- at OLT-side for the the previous 5-minute intervals of operation.  
--
-- An instance of this table is auto-created/deleted in accordance with the setting of:
-- 'PON Util PM Collect Indicator' setting of the PON Table (in this GPON MIB).
-- 'Chan Pair Util PM Collect Indicator' setting of the ChannelPair Table (in NG-PON2 MIB).
--
--	For GPON - SUPPORTED as of ISAM5.2 (for PONs)
--	For XG-PON1 - NOT SUPPORTED
--	For NG-PON2 - NOT SUPPORTED as of ISAM5.2.01 (for channel pairs)
--
-- *********************************************


gponOltSidePonUtilPmIntervalTable  OBJECT-TYPE
	SYNTAX SEQUENCE OF GponOltSidePonUtilIntervalEntry
	ACCESS	not-accessible
	STATUS	mandatory
	::= { gponServicesGroup 58 }


gponOltSidePonUtilPmIntervalEntry  OBJECT-TYPE
	SYNTAX 	GponOltSidePonUtilIntervalEntry
	ACCESS	not-accessible
	STATUS	mandatory
	DESCRIPTION 
		"An entry in the GPON Multicast PON Utilization PM
		 Interval Table. "
	INDEX	{ gponOltSidePonUtilPmIntervalPonIndex, 
		       gponOltSidePonUtilPmIntervalNumber }
	::= { gponOltSidePonUtilPmIntervalTable 1 }

GponOltSidePonUtilIntervalEntry ::= SEQUENCE {
        gponOltSidePonUtilPmIntervalPonIndex     IfIndex,
        gponOltSidePonUtilPmIntervalNumber       INTEGER,
        gponOltSidePonUtilTxPmIntervalUcastUtil  Counter,
--        gponOltSidePonUtilRxPmIntervalUcastUtil  Counter,
        gponOltSidePonUtilTxPmIntervalMcastUtil  Counter,
        gponOltSidePonUtilTxPmIntervalBcastUtil  Counter,
        gponOltSidePonUtilTxPmIntervalTotalUtil  Counter,
        gponOltSidePonUtilRxPmIntervalTotalUtil  Counter,
        gponOltSidePonUtilTxPmIntervalUcastBytes     OCTET STRING,
--        gponOltSidePonUtilRxPmIntervalUcastBytes     OCTET STRING,
        gponOltSidePonUtilTxPmIntervalMcastBytes     OCTET STRING,
        gponOltSidePonUtilTxPmIntervalBcastBytes     OCTET STRING,
        gponOltSidePonUtilTxPmIntervalTotalBytes     OCTET STRING,
        gponOltSidePonUtilRxPmIntervalTotalBytes     OCTET STRING,
        gponOltSidePonUtilTxPmIntervalUcastDropBytes    OCTET STRING,
        gponOltSidePonUtilRxPmIntervalTotalDropBytes    OCTET STRING,

        gponOltSidePonUtilPmIntervalNumActiveOnts     INTEGER,
        gponOltSidePonUtilRxPmIntervalDBACongestionTime    INTEGER,
	gponOltSidePonUtilTxPmIntervalMcastDropBytes	OCTET STRING,
	gponOltSidePonUtilTxPmIntervalBcastDropBytes	OCTET STRING,
	gponOltSidePonUtilTxPmIntervalTotalDropBytes	OCTET STRING,
        gponOltSidePonUtilTxPmIntervalUcastPackets     OCTET STRING,
--        gponOltSidePonUtilRxPmIntervalUcastPackets     OCTET STRING,
        gponOltSidePonUtilTxPmIntervalMcastPackets     OCTET STRING,
        gponOltSidePonUtilTxPmIntervalBcastPackets     OCTET STRING,
        gponOltSidePonUtilTxPmIntervalTotalPackets     OCTET STRING,
        gponOltSidePonUtilRxPmIntervalTotalPackets     OCTET STRING,
        gponOltSidePonUtilTxPmIntervalUcastDropPackets    OCTET STRING,
        gponOltSidePonUtilRxPmIntervalTotalDropPackets    OCTET STRING,
	gponOltSidePonUtilTxPmIntervalMcastDropPackets	OCTET STRING,
	gponOltSidePonUtilTxPmIntervalBcastDropPackets	OCTET STRING,
	gponOltSidePonUtilTxPmIntervalTotalDropPackets	OCTET STRING	 
 }   

gponOltSidePonUtilPmIntervalPonIndex  OBJECT-TYPE
	SYNTAX 	IfIndex
	ACCESS	read-only
	STATUS	mandatory
	DESCRIPTION 
		"This index is the ifIndex of the physical PON or channel pair.


		As of ISAM5.2.01, this table is shared by GPON PONs and NG-PON2
		channel pairs. Therefore, this index can represent the following:
		- PON ifIndex (for PONs) - as of ISAM5.2
		- ChannelPair ifIndex (for channel pairs) - as of ISAM5.2.01  "
	::= { gponOltSidePonUtilPmIntervalEntry 1 }


gponOltSidePonUtilPmIntervalNumber   OBJECT-TYPE
	SYNTAX 	INTEGER (1..288)
	ACCESS	read-only
	STATUS	mandatory
	DESCRIPTION 
		"A number between 1 and 288, where 1 is the most
		 recently completed 5-minute interval. "

	::= { gponOltSidePonUtilPmIntervalEntry 2 }

gponOltSidePonUtilTxPmIntervalUcastUtil  OBJECT-TYPE
        SYNTAX  Counter
        ACCESS  read-only
        STATUS  mandatory
        DESCRIPTION
                "A count of unicast traffic PON Utilization on the pon port in
                 the downstream direction in percentage.

		 Range is 0..100000, represented in percentage as 0.00 to 1000.00

		Denominator is  non-multicast BW of the PON
		(calculated as the max PON BW less that reserved for multicast in the QOS cac-profile).

		The utilization percentage can exceed 100% because the denominator is the non-multicast BW of the PON
		(calculated as the max PON BW less that reserved for multicast in the QOS cac-profile), 
		yet the unicast (and broadcast) traffic can use the BW reserved for multicast if it is available.

		For GPON - SUPPORTED as of ISAM5.2
		For XG-PON1 - NOT SUPPORTED
		For NG-PON2 - NOT SUPPORTED as of ISAM5.2.01 (for channel pairs) "                    
        ::= { gponOltSidePonUtilPmIntervalEntry 3 }                    
               
   
-- gponOltSidePonUtilRxPmIntervalUcastUtil  OBJECT-TYPE
--        SYNTAX  Counter
--        ACCESS  read-only
--        STATUS  mandatory
--        DESCRIPTION
--                "A count of unicast traffic PON Utilization on the pon port in
--                 upstream direction in percentage.
--
--		 Range is 0..10000, represented in percentage as 0.00 to 100.00
--
--		 NOT SUPORTED as of ISAM5.2 "                          
--       ::= { gponOltSidePonUtilPmIntervalEntry 4 }  

gponOltSidePonUtilTxPmIntervalMcastUtil   OBJECT-TYPE
        SYNTAX  Counter
        ACCESS  read-only
        STATUS  mandatory
        DESCRIPTION
                "A count of Multicast traffic PON Utilization on the pon port in
                 the downstream direction in percentage.

		 Range is 0..10000, represented in percentage as 0.00 to 100.00

		Denominator is  reserved multicast BW of the PON (per QoS cac-profile).

		For GPON - SUPPORTED as of ISAM5.2
		For XG-PON1 - NOT SUPPORTED
		For NG-PON2 - NOT SUPPORTED as of ISAM5.2.01 (for channel pairs) "                    
        ::= { gponOltSidePonUtilPmIntervalEntry 5 }                    

gponOltSidePonUtilTxPmIntervalBcastUtil   OBJECT-TYPE
        SYNTAX  Counter
        ACCESS  read-only
        STATUS  mandatory
        DESCRIPTION
                "A count of Broadcast traffic PON Utilization on the pon port in
                 the downstream direction in percentage.

		 Range is 0..100000, represented in percentage as 0.00 to 1000.00

		Denominator is  non-multicast BW of the PON
		(calculated as the max PON BW less that reserved for multicast in the QOS cac-profile).

		The utilization percentage can exceed 100% because the denominator is the non-multicast BW of the PON
		(calculated as the max PON BW less that reserved for multicast in the QOS cac-profile), 
		yet the unicast (and broadcast) traffic can use the BW reserved for multicast if it is available.

		For GPON - SUPPORTED as of ISAM5.2
		For XG-PON1 - NOT SUPPORTED
		For NG-PON2 - NOT SUPPORTED as of ISAM5.2.01 (for channel pairs) "                    
        ::= { gponOltSidePonUtilPmIntervalEntry 6 }                    
                  

gponOltSidePonUtilTxPmIntervalTotalUtil  OBJECT-TYPE
        SYNTAX  Counter
        ACCESS  read-only
        STATUS  mandatory
        DESCRIPTION
                "A count of total(unicast + multicast + broadcast) traffic PON 
                 Utilization on the pon port in the downstream direction in 
                 percentage.

		 Range is 0..10000, represented in percentage as 0.00 to 100.00

		Denominator is total downstream BW of the PON.

		For GPON - SUPPORTED as of ISAM5.2
		For XG-PON1 - NOT SUPPORTED
		For NG-PON2 - NOT SUPPORTED as of ISAM5.2.01 (for channel pairs) "
        ::= { gponOltSidePonUtilPmIntervalEntry 7 }
               
        
gponOltSidePonUtilRxPmIntervalTotalUtil  OBJECT-TYPE
        SYNTAX  Counter
        ACCESS  read-only
        STATUS  mandatory
        DESCRIPTION
                "A count of total (on unicast GEM ports) traffic PON 
                 Utilization on the pon port in the upstream direction in 
                 percentage.

		 Range is 0..10000, represented in percentage as 0.00 to 100.00

		Denominator is total upstream BW of the PON.

		For GPON - SUPPORTED as of ISAM5.2
		For XG-PON1 - NOT SUPPORTED
		For NG-PON2 - NOT SUPPORTED as of ISAM5.2.01 (for channel pairs) "
        ::= { gponOltSidePonUtilPmIntervalEntry 8 }

gponOltSidePonUtilTxPmIntervalUcastBytes     OBJECT-TYPE
        SYNTAX  OCTET STRING (SIZE(8))
        ACCESS  read-only
        STATUS  mandatory
        DESCRIPTION
                "A count of unicast traffic bytes transmitted on the pon port in
                 the downstream direction

		For GPON - SUPPORTED as of ISAM5.2
		For XG-PON1 - NOT SUPPORTED
		For NG-PON2 - NOT SUPPORTED as of ISAM5.2.01 (for channel pairs) "                   
        ::= { gponOltSidePonUtilPmIntervalEntry 9 }                              
   
-- gponOltSidePonUtilRxPmIntervalUcastBytes    OBJECT-TYPE
--        SYNTAX  OCTET STRING (SIZE(8))
--        ACCESS  read-only
--        STATUS  mandatory
--        DESCRIPTION
--                "A count of unicast traffic bytes received on the pon port in
--                 upstream direction
--
--		 NOT SUPORTED as of ISAM5.2"                        
--        ::= { gponOltSidePonUtilPmIntervalEntry 10 }                    


gponOltSidePonUtilTxPmIntervalMcastBytes    OBJECT-TYPE
        SYNTAX  OCTET STRING (SIZE(8))
        ACCESS  read-only
        STATUS  mandatory
        DESCRIPTION
                "A count of Multicast traffic bytes transmitted on the pon port in
                 the downstream direction

		For GPON - SUPPORTED as of ISAM5.2
		For XG-PON1 - NOT SUPPORTED
		For NG-PON2 - NOT SUPPORTED as of ISAM5.2.01 (for channel pairs) "                   
        ::= { gponOltSidePonUtilPmIntervalEntry 11 }                    

gponOltSidePonUtilTxPmIntervalBcastBytes    OBJECT-TYPE
        SYNTAX  OCTET STRING (SIZE(8))
        ACCESS  read-only
        STATUS  mandatory
        DESCRIPTION
                "A count of Broadcast traffic bytes transmitted on the pon port in
                 the downstream direction

		For GPON - SUPPORTED as of ISAM5.2
		For XG-PON1 - NOT SUPPORTED
		For NG-PON2 - NOT SUPPORTED as of ISAM5.2.01 (for channel pairs) "                    
        ::= { gponOltSidePonUtilPmIntervalEntry 12 }                    


gponOltSidePonUtilTxPmIntervalTotalBytes     OBJECT-TYPE
        SYNTAX  OCTET STRING (SIZE(8))
        ACCESS  read-only
        STATUS  mandatory
        DESCRIPTION
                "A count of total(unicast+multicast+broadcast) traffic bytes 
                 transmitted on the pon port in the downstream direction

		For GPON - SUPPORTED as of ISAM5.2
		For XG-PON1 - NOT SUPPORTED
		For NG-PON2 - NOT SUPPORTED as of ISAM5.2.01 (for channel pairs) "         
        ::= { gponOltSidePonUtilPmIntervalEntry 13 }
               
        
gponOltSidePonUtilRxPmIntervalTotalBytes     OBJECT-TYPE
        SYNTAX  OCTET STRING (SIZE(8))
        ACCESS  read-only
        STATUS  mandatory
        DESCRIPTION
                "A count of total (on unicast GEM ports) traffic bytes 
                 on the pon port in the upstream direction
 
		For GPON - SUPPORTED as of ISAM5.2
		For XG-PON1 - NOT SUPPORTED
		For NG-PON2 - NOT SUPPORTED as of ISAM5.2.01 (for channel pairs) "        
        ::= { gponOltSidePonUtilPmIntervalEntry 14 }
               
gponOltSidePonUtilTxPmIntervalUcastDropBytes    OBJECT-TYPE
        SYNTAX  OCTET STRING (SIZE(8))
        ACCESS  read-only
        STATUS  mandatory
        DESCRIPTION
                "A count of unicast traffic drop bytes on the pon port in
                 the downstream direction

		For GPON - SUPPORTED as of ISAM5.2
		For XG-PON1 - NOT SUPPORTED
		For NG-PON2 - NOT SUPPORTED as of ISAM5.2.01 (for channel pairs) "                     
        ::= { gponOltSidePonUtilPmIntervalEntry 15 }                    
               
gponOltSidePonUtilRxPmIntervalTotalDropBytes    OBJECT-TYPE
        SYNTAX  OCTET STRING (SIZE(8))
        ACCESS  read-only
        STATUS  mandatory
        DESCRIPTION
                "A count of total traffic drop bytes on the pon port in
                 upstream direction

		For GPON - SUPPORTED as of ISAM5.2
		For XG-PON1 - NOT SUPPORTED
		For NG-PON2 - NOT SUPPORTED as of ISAM5.2.01 (for channel pairs) "                          
        ::= { gponOltSidePonUtilPmIntervalEntry 16 }                    

gponOltSidePonUtilPmIntervalNumActiveOnts     OBJECT-TYPE
        SYNTAX  INTEGER
        ACCESS  read-only
        STATUS  mandatory
        DESCRIPTION
                "A count of the maximum number of active ONTs on the pon port.

		 Range is 0..256

		For GPON - SUPPORTED as of ISAM5.2
		For XG-PON1 - NOT SUPPORTED
		For NG-PON2 - NOT SUPPORTED as of ISAM5.2.01 (for channel pairs) "                         
        ::= { gponOltSidePonUtilPmIntervalEntry 17 }                    
               
gponOltSidePonUtilRxPmIntervalDBACongestionTime    OBJECT-TYPE
        SYNTAX  INTEGER
        ACCESS  read-only
        STATUS  mandatory
        DESCRIPTION
                "The percentage of the 5-minute time interval DBA engine
		 has allocated all of available bandwidth.
 
		 Range is 0..10000, represented in percentage as 0.00 to 100.00

		For GPON - SUPPORTED as of ISAM5.2
		For XG-PON1 - NOT SUPPORTED
		For NG-PON2 - NOT SUPPORTED as of ISAM5.2.01 (for channel pairs) "                         
        ::= { gponOltSidePonUtilPmIntervalEntry 18 }                    


gponOltSidePonUtilTxPmIntervalMcastDropBytes    OBJECT-TYPE
        SYNTAX  OCTET STRING (SIZE(8))
        ACCESS  read-only
        STATUS  mandatory
        DESCRIPTION
                "A count of multicast traffic drop bytes on the pon port in
                 the downstream direction

		For GPON - SUPPORTED as of ISAM5.2
		For XG-PON1 - NOT SUPPORTED
		For NG-PON2 - NOT SUPPORTED as of ISAM5.2.01 (for channel pairs) "                    
        ::= { gponOltSidePonUtilPmIntervalEntry 19 }

gponOltSidePonUtilTxPmIntervalBcastDropBytes    OBJECT-TYPE
        SYNTAX  OCTET STRING (SIZE(8))
        ACCESS  read-only
        STATUS  mandatory
        DESCRIPTION
                "A count of broadcast traffic drop bytes on the pon port in
                 the downstream direction

		For GPON - SUPPORTED as of ISAM5.2
		For XG-PON1 - NOT SUPPORTED
		For NG-PON2 - NOT SUPPORTED as of ISAM5.2.01 (for channel pairs) "                    
        ::= { gponOltSidePonUtilPmIntervalEntry 20 } 


gponOltSidePonUtilTxPmIntervalTotalDropBytes    OBJECT-TYPE
        SYNTAX  OCTET STRING (SIZE(8))
        ACCESS  read-only
        STATUS  mandatory
        DESCRIPTION
                "A count of total traffic drop bytes on the pon port in
                 downstream direction

		For GPON - SUPPORTED as of ISAM5.2
		For XG-PON1 - NOT SUPPORTED
		For NG-PON2 - NOT SUPPORTED as of ISAM5.2.01 (for channel pairs) "                          
        ::= { gponOltSidePonUtilPmIntervalEntry 21 }         


gponOltSidePonUtilTxPmIntervalUcastPackets     OBJECT-TYPE
        SYNTAX  OCTET STRING (SIZE(8))
        ACCESS  read-only
        STATUS  mandatory
        DESCRIPTION
                "A count of unicast traffic Packets transmitted on the pon port in
                 the downstream direction

		For GPON - SUPPORTED as of ISAM5.2
		For XG-PON1 - NOT SUPPORTED
		For NG-PON2 - NOT SUPPORTED as of ISAM5.2.01 (for channel pairs) "                    
        ::= { gponOltSidePonUtilPmIntervalEntry 22 }                    
               
   

-- gponOltSidePonUtilRxPmIntervalUcastPackets    OBJECT-TYPE
--        SYNTAX  OCTET STRING (SIZE(8))
--        ACCESS  read-only
--        STATUS  mandatory
--        DESCRIPTION
--                "A count of unicast traffic Packets received on the pon port in
--                 upstream direction
--
-- 		 SUPORTED as of ISAM5.2 "                          
--        ::= { gponOltSidePonUtilPmIntervalEntry 23 }                    


gponOltSidePonUtilTxPmIntervalMcastPackets    OBJECT-TYPE
        SYNTAX  OCTET STRING (SIZE(8))
        ACCESS  read-only
        STATUS  mandatory        
		DESCRIPTION
                "A count of Multicast traffic Packets transmitted on the pon port in
                 the downstream direction

		For GPON - SUPPORTED as of ISAM5.2
		For XG-PON1 - NOT SUPPORTED
		NG-PON2 - NOT SUPPORTED as of ISAM5.2.01 (for channel pairs) "                    
        ::= { gponOltSidePonUtilPmIntervalEntry 24 }                    

gponOltSidePonUtilTxPmIntervalBcastPackets    OBJECT-TYPE
        SYNTAX  OCTET STRING (SIZE(8))
        ACCESS  read-only
        STATUS  mandatory
        DESCRIPTION
                "A count of Broadcast traffic Packets transmitted on the pon port in
                 the downstream direction

		For GPON - SUPPORTED as of ISAM5.2
		For XG-PON1 - NOT SUPPORTED
		NG-PON2 - NOT SUPPORTED as of ISAM5.2.01 (for channel pairs) "                    
        ::= { gponOltSidePonUtilPmIntervalEntry 25}                    

   
gponOltSidePonUtilTxPmIntervalTotalPackets     OBJECT-TYPE
        SYNTAX  OCTET STRING (SIZE(8))
        ACCESS  read-only
        STATUS  mandatory
        DESCRIPTION
                "A count of total(unicast+multicast+broadcast) traffic Packets 
                 transmitted on the pon port in the downstream direction

		For GPON - SUPPORTED as of ISAM5.2
		For XG-PON1 - NOT SUPPORTED
		NG-PON2 - NOT SUPPORTED as of ISAM5.2.01 (for channel pairs) "          
        ::= { gponOltSidePonUtilPmIntervalEntry 26 }
               
        
gponOltSidePonUtilRxPmIntervalTotalPackets     OBJECT-TYPE
        SYNTAX  OCTET STRING (SIZE(8))
        ACCESS  read-only
        STATUS  mandatory
        DESCRIPTION
                "A count of total (on unicast GEM ports) traffic Packets 
                 on the pon port in the upstream direction

		For GPON - SUPPORTED as of ISAM5.2
		For XG-PON1 - NOT SUPPORTED
		NG-PON2 - NOT SUPPORTED as of ISAM5.2.01 (for channel pairs) "          
        ::= { gponOltSidePonUtilPmIntervalEntry 27 }
               
gponOltSidePonUtilTxPmIntervalUcastDropPackets    OBJECT-TYPE
        SYNTAX  OCTET STRING (SIZE(8))
        ACCESS  read-only
        STATUS  mandatory
        DESCRIPTION
                "A count of unicast traffic drop Packets on the pon port in
                 the downstream direction

		For GPON - SUPPORTED as of ISAM5.2
		For XG-PON1 - NOT SUPPORTED
		NG-PON2 - NOT SUPPORTED as of ISAM5.2.01 (for channel pairs) "                    
        ::= { gponOltSidePonUtilPmIntervalEntry 28 }                    
               
gponOltSidePonUtilRxPmIntervalTotalDropPackets    OBJECT-TYPE
        SYNTAX  OCTET STRING (SIZE(8))
        ACCESS  read-only
        STATUS  mandatory
        DESCRIPTION
                "A count of total traffic drop Packets on the pon port in
                 upstream direction 

		For GPON - SUPPORTED as of ISAM5.2
		For XG-PON1 - NOT SUPPORTED
		NG-PON2 - NOT SUPPORTED as of ISAM5.2.01 (for channel pairs) "                          
        ::= { gponOltSidePonUtilPmIntervalEntry 29 }  

gponOltSidePonUtilTxPmIntervalMcastDropPackets    OBJECT-TYPE
        SYNTAX  OCTET STRING (SIZE(8))
        ACCESS  read-only
        STATUS  mandatory
        DESCRIPTION
                "A count of multicast traffic drop Packets on the pon port in
                 the downstream direction

		For GPON - SUPPORTED as of ISAM5.2
		For XG-PON1 - NOT SUPPORTED
		NG-PON2 - NOT SUPPORTED as of ISAM5.2.01 (for channel pairs) "                    
        ::= { gponOltSidePonUtilPmIntervalEntry 30 }

gponOltSidePonUtilTxPmIntervalBcastDropPackets    OBJECT-TYPE
        SYNTAX  OCTET STRING (SIZE(8))
        ACCESS  read-only
        STATUS  mandatory
        DESCRIPTION
                "A count of broadcast traffic drop Packets on the pon port in
                 the downstream direction

		For GPON - SUPPORTED as of ISAM5.2
		For XG-PON1 - NOT SUPPORTED
		NG-PON2 - NOT SUPPORTED as of ISAM5.2.01 (for channel pairs) "                    
        ::= { gponOltSidePonUtilPmIntervalEntry 31 } 

gponOltSidePonUtilTxPmIntervalTotalDropPackets    OBJECT-TYPE
        SYNTAX  OCTET STRING (SIZE(8))
        ACCESS  read-only
        STATUS  mandatory
        DESCRIPTION
                "A count of total traffic drop Packets on the pon port in
                 downstream direction 

		For GPON - SUPPORTED as of ISAM5.2
		For XG-PON1 - NOT SUPPORTED
		NG-PON2 - NOT SUPPORTED as of ISAM5.2.01 (for channel pairs) (for channel pairs) "                          
        ::= { gponOltSidePonUtilPmIntervalEntry 32 }  



-- *********************************************
--
-- Pon Utilization PERFORMANCE MONITOR ONT UNICAST-TRANSMIT(DOWNSTREAM) CURRENT 
--  INTERVAL TABLE (5-minute cycle)
--
-- This is a new table beginning with ISAM5.2 (copied from FTTU4.9.20). This interval  
-- table contains utilization and ranking for top 5 ONT Pon Utilizers collected  
-- during the current 5-minute interval of operation in downstream direction.  
--
-- An instance of this table is auto-created/deleted in accordance with the setting of:
-- 'PON Util PM Collect Indicator' setting of the PON Table (in this GPON MIB).
-- 'Chan Pair Util PM Collect Indicator' setting of the ChannelPair Table (in NG-PON2 MIB).
--
--	For GPON - SUPPORTED as of ISAM5.2 (for PONs)
--	For XG-PON1 - NOT SUPPORTED
--	For NG-PON2 - NOT SUPPORTED as of ISAM5.2.01 (for channel pairs)
-- *********************************************

gponOltSidePonUtilTxOntPmCurrentIntervalTable  OBJECT-TYPE
	SYNTAX SEQUENCE OF GponOltSidePonUtilTxOntPmCurrentIntervalEntry
	ACCESS	not-accessible
	STATUS	mandatory
	::= { gponServicesGroup 59}


gponOltSidePonUtilTxOntPmCurrentIntervalEntry  OBJECT-TYPE
	SYNTAX 	GponOltSidePonUtilTxOntPmCurrentIntervalEntry
	ACCESS	not-accessible
	STATUS	mandatory
	DESCRIPTION 
		"An entry in the gpon oltSide PON Utilization 
		 Transmit ONT PM current interval Table. "
	INDEX	{ gponOltSidePonUtilTxOntPmCurrentIntervalPonIndex,
               gponOltSidePonUtilTxOntPmCurrentIntervalRank
               }
	::= { gponOltSidePonUtilTxOntPmCurrentIntervalTable 1 }

GponOltSidePonUtilTxOntPmCurrentIntervalEntry ::= SEQUENCE {
	gponOltSidePonUtilTxOntPmCurrentIntervalPonIndex	IfIndex,
	gponOltSidePonUtilTxOntPmCurrentIntervalRank               INTEGER,
	gponOltSidePonUtilTxOntPmCurrentIntervalOntIndex           IfIndex,
	gponOltSidePonUtilTxOntPmCurrentIntervalUtil	             Counter
}

gponOltSidePonUtilTxOntPmCurrentIntervalPonIndex  OBJECT-TYPE
	SYNTAX 	IfIndex
	ACCESS	read-only
	STATUS	mandatory
	DESCRIPTION 
		"This index is the ifIndex of the physical PON.

		As of ISAM5.2.01, this table is shared by GPON PONs and NG-PON2
		channel pairs. Therefore, this index can represent the following:
		- PON ifIndex (for PONs) - as of ISAM5.2
		- ChannelPair ifIndex (for channel pairs) - as of ISAM5.2.01  "
	::= { gponOltSidePonUtilTxOntPmCurrentIntervalEntry 1 }


gponOltSidePonUtilTxOntPmCurrentIntervalRank  OBJECT-TYPE
	SYNTAX 	INTEGER (1..5)
	ACCESS	read-only
	STATUS	mandatory
	DESCRIPTION 
		"This attribute specifies the rank for ONT from 1 to 5 
		that utilized maximum unicast PON bandwidth in the downstream direction.

		For GPON - SUPPORTED as of ISAM5.2
		For XG-PON1 - NOT SUPPORTED
		NG-PON2 - NOT SUPPORTED as of ISAM5.2.01 (for channel pairs)  "
	::= { gponOltSidePonUtilTxOntPmCurrentIntervalEntry 2 }


gponOltSidePonUtilTxOntPmCurrentIntervalOntIndex  OBJECT-TYPE
	SYNTAX 	IfIndex
	ACCESS	read-only
	STATUS	mandatory
	DESCRIPTION 
		"This is the ifIndex of the physical ONT.

		For GPON - SUPPORTED as of ISAM5.2
		For XG-PON1 - NOT SUPPORTED
		NG-PON2 - NOT SUPPORTED as of ISAM5.2.01 (for channel pairs)  "
	::= { gponOltSidePonUtilTxOntPmCurrentIntervalEntry 3 }

gponOltSidePonUtilTxOntPmCurrentIntervalUtil  OBJECT-TYPE
	SYNTAX 	Counter
	ACCESS	read-only
	STATUS	mandatory
	DESCRIPTION 
		"A count of PON Utilization on the pon port for this ONT.

		 Range is 0..100000, represented in percentage as 0.00 to 1000.00

		Denominator is  non-multicast BW of the PON
		(calculated as the max PON BW less that reserved for multicast in the QOS cac-profile).


		The utilization percentage can exceed 100% because the denominator is the non-multicast BW of the PON
		(calculated as the max PON BW less that reserved for multicast in the QOS cac-profile), 
		yet the unicast (and broadcast) traffic can use the BW reserved for multicast if it is available.

		For GPON - SUPPORTED as of ISAM5.2
		For XG-PON1 - NOT SUPPORTED
		NG-PON2 - NOT SUPPORTED as of ISAM5.2.01 (for channel pairs) "
	::= { gponOltSidePonUtilTxOntPmCurrentIntervalEntry 4 }


-- *********************************************
--
-- Pon Utilization PERFORMANCE MONITOR ONT UNICAST-TRANSMIT(DOWNSTREAM) 
-- INTERVAL TABLE (5-minute cycle)
--
-- This is a new table beginning with ISAM5.2 (copied from FTTU4.9.20)
-- This interval table contains utilization and ranking for top 5 ONT Pon Utilizers
--  collected during the previous 5-minute intervals of operation in downstream direction.  
--
-- An instance of this table is auto-created/deleted in accordance with the setting of:
-- 'PON Util PM Collect Indicator' setting of the PON Table (in this GPON MIB).
-- 'Chan Pair Util PM Collect Indicator' setting of the ChannelPair Table (in NG-PON2 MIB).
--
--	For GPON - SUPPORTED as of ISAM5.2 (for PONs)
--	For XG-PON1 - NOT SUPPORTED
--	For NG-PON2 - NOT SUPPORTED as of ISAM5.2.01 (for channel pairs)

-- *********************************************

gponOltSidePonUtilTxOntPmIntervalTable  OBJECT-TYPE
	SYNTAX SEQUENCE OF GponOltSidePonUtilTxOntPmIntervalEntry
	ACCESS	not-accessible
	STATUS	mandatory
	::= { gponServicesGroup 60}


gponOltSidePonUtilTxOntPmIntervalEntry  OBJECT-TYPE
	SYNTAX 	GponOltSidePonUtilTxOntPmIntervalEntry
	ACCESS	not-accessible
	STATUS	mandatory
	DESCRIPTION 
		"An entry in the PON Utilization Transmit ONT PM 
		 Interval Table. "
	INDEX	{ gponOltSidePonUtilTxOntPmIntervalPonIndex,
               gponOltSidePonUtilTxOntPmIntervalRank,
               gponOltSidePonUtilTxOntPmIntervalNumber              
               }
	::= { gponOltSidePonUtilTxOntPmIntervalTable 1 }

GponOltSidePonUtilTxOntPmIntervalEntry ::= SEQUENCE {
	gponOltSidePonUtilTxOntPmIntervalPonIndex	IfIndex,
    gponOltSidePonUtilTxOntPmIntervalRank              INTEGER,
	gponOltSidePonUtilTxOntPmIntervalNumber		INTEGER,  
	gponOltSidePonUtilTxOntPmIntervalOntIndex 	IfIndex,
	gponOltSidePonUtilTxOntPmIntervalUtil		Counter
}

gponOltSidePonUtilTxOntPmIntervalPonIndex  OBJECT-TYPE
	SYNTAX 	IfIndex
	ACCESS	read-only
	STATUS	mandatory
	DESCRIPTION 
		"This index is the ifIndex of the physical PON.

		As of ISAM5.2.01, this table is shared by GPON PONs and NG-PON2
		channel pairs. Therefore, this index can represent the following:
		- PON ifIndex (for PONs) - as of ISAM5.2
		- ChannelPair ifIndex (for channel pairs) - as of ISAM5.2.01  "
	::= { gponOltSidePonUtilTxOntPmIntervalEntry 1 }



gponOltSidePonUtilTxOntPmIntervalRank  OBJECT-TYPE
	SYNTAX 	INTEGER (1..5)
	ACCESS	read-only
	STATUS	mandatory
	DESCRIPTION 
		"This attribute specifies the rank for ONTs from 1 to 5 that utilized 
		maximum PON bandwidth in the downstream direction.

		For GPON - SUPPORTED as of ISAM5.2
		For XG-PON1 - NOT SUPPORTED
		NG-PON2 - NOT SUPPORTED as of ISAM5.2.01 (for channel pairs) "
	::= { gponOltSidePonUtilTxOntPmIntervalEntry 2 }

gponOltSidePonUtilTxOntPmIntervalNumber  OBJECT-TYPE
	SYNTAX 	INTEGER (1..288)
	ACCESS	read-only
	STATUS	mandatory
	DESCRIPTION 
		"A number between 1 and 288, where 1 is the most
		 recently completed 5-minute interval.

		For GPON - SUPPORTED as of ISAM5.2
		For XG-PON1 - NOT SUPPORTED
		NG-PON2 - NOT SUPPORTED as of ISAM5.2.01 (for channel pairs) "
	::= { gponOltSidePonUtilTxOntPmIntervalEntry 3 }


gponOltSidePonUtilTxOntPmIntervalOntIndex  OBJECT-TYPE
	SYNTAX 	IfIndex
	ACCESS	read-only
	STATUS	mandatory
	DESCRIPTION 
		"This is the ifIndex of the physical ONT. "
	::= { gponOltSidePonUtilTxOntPmIntervalEntry 4 }

gponOltSidePonUtilTxOntPmIntervalUtil  OBJECT-TYPE
	SYNTAX 	Counter
	ACCESS	read-only
	STATUS	mandatory
	DESCRIPTION 
		"A count of PON Utilization on the pon port for this ONT.

		 Range is 0..100000, represented in percentage as 0.00 to 1000.00

		Denominator is  non-multicast BW of the PON
		(calculated as the max PON BW less that reserved for multicast in the QOS cac-profile).

		The utilization percentage can exceed 100% because the denominator is the non-multicast BW of the PON
		(calculated as the max PON BW less that reserved for multicast in the QOS cac-profile), 
		yet the unicast (and broadcast) traffic can use the BW reserved for multicast if it is available.

		For GPON - SUPPORTED as of ISAM5.2
		For XG-PON1 - NOT SUPPORTED
		NG-PON2 - NOT SUPPORTED as of ISAM5.2.01 (for channel pairs) "
	::= { gponOltSidePonUtilTxOntPmIntervalEntry 5 }


-- *********************************************
--
-- Pon Utilization PERFORMANCE MONITOR ONT UNICAST-RECEIVE(UPSTREAM) CURRENT INTERVAL 
-- TABLE (5-minute cycle)
--
-- This is a new table beginning with ISAM5.2 (copied from FTTU4.9.
-- This interval table contains various statistics collected for 
-- the top 5 Pon Utilization collected during the current 5-minute interval 
-- of operation in upstream direction.  
--
-- An instance of this table is auto-created/deleted in accordance with the setting of:
-- 'PON Util PM Collect Indicator' setting of the PON Table (in this GPON MIB).
-- 'Chan Pair Util PM Collect Indicator' setting of the ChannelPair Table (in NG-PON2 MIB).
--
--	For GPON - SUPPORTED as of ISAM5.2 (for PONs)
--	For XG-PON1 - NOT SUPPORTED
--	For NG-PON2 - NOT SUPPORTED as of ISAM5.2.01 (for channel pairs)
-- *********************************************


gponOltSidePonUtilRxOntPmCurrentIntervalTable  OBJECT-TYPE
	SYNTAX SEQUENCE OF GponOltSidePonUtilRxOntPmCurrentIntervalEntry
	ACCESS	not-accessible
	STATUS	mandatory
	::= { gponServicesGroup 61 }


gponOltSidePonUtilRxOntPmCurrentIntervalEntry  OBJECT-TYPE
	SYNTAX 	GponOltSidePonUtilRxOntPmCurrentIntervalEntry
	ACCESS	not-accessible
	STATUS	mandatory
	DESCRIPTION 
		"An entry in the PON Utilization receive direction current interval
		 Table. "
	INDEX	{ gponOltSidePonUtilRxOntPmCurrentIntervalPonIndex,
               gponOltSidePonUtilRxOntPmCurrentIntervalRank
}
	::= { gponOltSidePonUtilRxOntPmCurrentIntervalTable 1 }

GponOltSidePonUtilRxOntPmCurrentIntervalEntry ::= SEQUENCE {
	gponOltSidePonUtilRxOntPmCurrentIntervalPonIndex	IfIndex,
    gponOltSidePonUtilRxOntPmCurrentIntervalRank           INTEGER,
	gponOltSidePonUtilRxOntPmCurrentIntervalOntIndex	IfIndex,
	gponOltSidePonUtilRxOntPmCurrentIntervalUtil	Counter

}


gponOltSidePonUtilRxOntPmCurrentIntervalPonIndex  OBJECT-TYPE
	SYNTAX 	IfIndex
	ACCESS	read-only
	STATUS	mandatory
	DESCRIPTION 
		"This index is the ifIndex of the physical PON.

		As of ISAM5.2.01, this table is shared by GPON PONs and NG-PON2
		channel pairs. Therefore, this index can represent the following:
		- PON ifIndex (for PONs) - as of ISAM5.2
		- ChannelPair ifIndex (for channel pairs) - as of ISAM5.2.01  "
	::= { gponOltSidePonUtilRxOntPmCurrentIntervalEntry 1 }


gponOltSidePonUtilRxOntPmCurrentIntervalRank  OBJECT-TYPE
	SYNTAX 	INTEGER (1..5)
	ACCESS	read-only
	STATUS	mandatory
	DESCRIPTION 
		"This attribute specifies the rank for ONTs (1 to 5) that utilized 
		maximum PON bandwidth in the upstream direction.

		For GPON - SUPPORTED as of ISAM5.2
		For XG-PON1 - NOT SUPPORTED
		NG-PON2 - NOT SUPPORTED as of ISAM5.2.01 (for channel pairs) "
	::= { gponOltSidePonUtilRxOntPmCurrentIntervalEntry 2 }


gponOltSidePonUtilRxOntPmCurrentIntervalOntIndex  OBJECT-TYPE
	SYNTAX 	IfIndex
	ACCESS	read-only
	STATUS	mandatory
	DESCRIPTION 
		"This is the ifIndex of the physical ONT.

		For GPON - SUPPORTED as of ISAM5.2
		For XG-PON1 - NOT SUPPORTED
		NG-PON2 - NOT SUPPORTED as of ISAM5.2.01 (for channel pairs) "
	::= { gponOltSidePonUtilRxOntPmCurrentIntervalEntry 3 }


gponOltSidePonUtilRxOntPmCurrentIntervalUtil  OBJECT-TYPE
	SYNTAX 	Counter
	ACCESS	read-only
	STATUS	mandatory
	DESCRIPTION 
		"A count of PON Utilization on the pon port for this ONT.

		 Range is 0..10000, represented in percentage as 0.00 to 100.00

		 SUPORTED as of ISAM5.2

		For GPON - SUPPORTED as of ISAM5.2
		For XG-PON1 - NOT SUPPORTED
		NG-PON2 - NOT SUPPORTED as of ISAM5.2.01 (for channel pairs) "
	::= { gponOltSidePonUtilRxOntPmCurrentIntervalEntry 4 }


-- *********************************************
--
-- Pon Utilization PERFORMANCE MONITOR ONT UNICAST-RECEIVE(UPSTREAM) 
-- INTERVAL TABLE (5-minute cycle)
--
-- This is a new table beginning with ISAM5.2 (copied from FTTU4.9).
-- This interval table contains various statistics collected for 
-- the top 5 Pon Utilization ONTs collected during the previous 5-minute intervals 
-- of operation in upstream direction.  
--
-- An instance of this table is auto-created/deleted in accordance with the setting of:
-- 'PON Util PM Collect Indicator' setting of the PON Table (in this GPON MIB).
-- 'Chan Pair Util PM Collect Indicator' setting of the ChannelPair Table (in NG-PON2 MIB).
--
--	For GPON - SUPPORTED as of ISAM5.2 (for PONs)
--	For XG-PON1 - NOT SUPPORTED
--	For NG-PON2 - NOT SUPPORTED as of ISAM5.2.01 (for channel pairs)
-- *********************************************


gponOltSidePonUtilRxOntPmIntervalTable  OBJECT-TYPE
	SYNTAX SEQUENCE OF GponOltSidePonUtilRxOntPmIntervalEntry
	ACCESS	not-accessible
	STATUS	mandatory
	::= { gponServicesGroup 62 }


gponOltSidePonUtilRxOntPmIntervalEntry  OBJECT-TYPE
	SYNTAX 	GponOltSidePonUtilRxOntPmIntervalEntry
	ACCESS	not-accessible
	STATUS	mandatory
	DESCRIPTION 
		"An entry in the PON Utilization Receive ONT PM
		 Interval Table. "
	INDEX	{ gponOltSidePonUtilRxOntPmIntervalPonIndex,
               gponOltSidePonUtilRxOntPmIntervalRank,
               gponOltSidePonUtilRxOntPmIntervalNumber
               
}
	::= { gponOltSidePonUtilRxOntPmIntervalTable 1 }

GponOltSidePonUtilRxOntPmIntervalEntry ::= SEQUENCE {
	gponOltSidePonUtilRxOntPmIntervalPonIndex	IfIndex,
    gponOltSidePonUtilRxOntPmIntervalRank      INTEGER,
	gponOltSidePonUtilRxOntPmIntervalNumber		INTEGER,
    	gponOltSidePonUtilRxOntPmIntervalOntIndex	IfIndex,
	gponOltSidePonUtilRxOntPmIntervalUtil 	Counter }


gponOltSidePonUtilRxOntPmIntervalPonIndex  OBJECT-TYPE
	SYNTAX 	IfIndex
	ACCESS	read-only
	STATUS	mandatory
	DESCRIPTION 
		"This index is the ifIndex of the physical PON.

		As of ISAM5.2.01, this table is shared by GPON PONs and NG-PON2
		channel pairs. Therefore, this index can represent the following:
		- PON ifIndex (for PONs) - as of ISAM5.2
		- ChannelPair ifIndex (for channel pairs) - as of ISAM5.2.01  "
	::= { gponOltSidePonUtilRxOntPmIntervalEntry 1 }

gponOltSidePonUtilRxOntPmIntervalRank  OBJECT-TYPE
	SYNTAX 	INTEGER (1..5)
	ACCESS	read-only
	STATUS	mandatory
	DESCRIPTION 
		"This attribute specifies the rank for ONTs (1 to 5) that utilized
	  	maximum PON bandwidth in the upstream direction.

		For GPON - SUPPORTED as of ISAM5.2
		For XG-PON1 - NOT SUPPORTED
		NG-PON2 - NOT SUPPORTED as of ISAM5.2.01 (for channel pairs) "
	::= { gponOltSidePonUtilRxOntPmIntervalEntry 2 }


gponOltSidePonUtilRxOntPmIntervalNumber  OBJECT-TYPE
	SYNTAX 	INTEGER (1..288)
	ACCESS	read-only
	STATUS	mandatory
	DESCRIPTION 
		"A number between 1 and 288, where 1 is the most
		 recently completed 5-minute interval.

		For GPON - SUPPORTED as of ISAM5.2
		For XG-PON1 - NOT SUPPORTED
		NG-PON2 - NOT SUPPORTED as of ISAM5.2.01 (for channel pairs)  "
	::= { gponOltSidePonUtilRxOntPmIntervalEntry 3 }


gponOltSidePonUtilRxOntPmIntervalOntIndex  OBJECT-TYPE
	SYNTAX 	IfIndex
	ACCESS	read-only
	STATUS	mandatory
	DESCRIPTION 
		"This is the ifIndex of the physical ONT.

		For GPON - SUPPORTED as of ISAM5.2
		For XG-PON1 - NOT SUPPORTED
		NG-PON2 - NOT SUPPORTED as of ISAM5.2.01 (for channel pairs) "
	::= { gponOltSidePonUtilRxOntPmIntervalEntry 4 }

gponOltSidePonUtilRxOntPmIntervalUtil  OBJECT-TYPE
	SYNTAX 	Counter
	ACCESS	read-only
	STATUS	mandatory
	DESCRIPTION 
		"A count of PON Utilization on the pon port for this ONT.

		 Range is 0..10000, represented in percentage as 0.00 to 100.00

		For GPON - SUPPORTED as of ISAM5.2
		For XG-PON1 - NOT SUPPORTED
		NG-PON2 - NOT SUPPORTED as of ISAM5.2.01 (for channel pairs) "
	::= { gponOltSidePonUtilRxOntPmIntervalEntry 5 }


-- *********************************************
--
-- GPON OLTSIDE ONT UTILIZATION PERFORMANCE MONITOR CURRENT INTERVAL 
-- TABLE (5-minute cycle)
--
-- This is a new table beginning with ISAM5.2 (re-indexed from FTTU4.9).
-- This interval table contains various statistics collected for 
-- a number of ONTs on the PON during the current 5-minute interval of operation 
--
-- An instance of this table is auto-created/deleted in accordance with the 
-- ' bponPonConfigPonUtilOntDetailSelector' setting of PON (in this MIB).
-- ' ng2ChanPairConfigUtilOntDetailSelector setting of channel pair (in NG-PON2 MIB).
--
--	For GPON - SUPPORTED as of ISAM5.2 (for PONs)
--	For XG-PON1 - NOT SUPPORTED
--	For NG-PON2 - NOT SUPPORTED as of ISAM5.2.01 (for channel pairs)
-- *********************************************

gponOltSideOntUtilPmCurrentIntervalTable  OBJECT-TYPE
	SYNTAX SEQUENCE OF GponOltSideOntUtilPmCurrentIntervalEntry
	ACCESS	not-accessible
	STATUS	mandatory
	::= { gponServicesGroup 63 }


gponOltSideOntUtilPmCurrentIntervalEntry OBJECT-TYPE
	SYNTAX 	GponOltSideOntUtilPmCurrentIntervalEntry
	ACCESS	not-accessible
	STATUS	mandatory
	DESCRIPTION 
		"An entry in the Oltside ONT Utilization current interval
		 Table. "
	INDEX	{ ponIfIndex, ontIfIndex }	
-- First ifIndex is the ifIndex of either a PON (as of ISAM5.2) or 
--	a channel-pair (as of ISAM5.2.01)
-- Second ifIndex is the ifIndex of the ONT
::= { gponOltSideOntUtilPmCurrentIntervalTable  1 }

GponOltSideOntUtilPmCurrentIntervalEntry::= SEQUENCE {
               gponOltSideOntUtilPmCurrentIntervalTxUcastBytes  OCTET STRING,
               gponOltSideOntUtilPmCurrentIntervalRxUcastBytes  OCTET STRING,
               gponOltSideOntUtilPmCurrentIntervalTxUcastDropBytes  OCTET STRING,
               gponOltSideOntUtilPmCurrentIntervalRxUcastDropBytes OCTET STRING,
               gponOltSideOntUtilPmCurrentIntervalTxUcastPackets  OCTET STRING,
               gponOltSideOntUtilPmCurrentIntervalRxUcastPackets  OCTET STRING,
               gponOltSideOntUtilPmCurrentIntervalTxUcastDropPackets  OCTET STRING,
               gponOltSideOntUtilPmCurrentIntervalRxUcastDropPackets	 OCTET STRING
}


gponOltSideOntUtilPmCurrentIntervalTxUcastBytes OBJECT-TYPE
	SYNTAX 	OCTET STRING (SIZE(8))
	ACCESS	read-only
	STATUS	mandatory
	DESCRIPTION 
		"This attribute specifies the total unicast bytes transmitted on the PON 
          in the downstream direction to the specified ONT index

		For GPON - SUPPORTED as of ISAM5.2
		For XG-PON1 - NOT SUPPORTED
		NG-PON2 - NOT SUPPORTED as of ISAM5.2.01 (for channel pairs) "

	::= { gponOltSideOntUtilPmCurrentIntervalEntry 2 }

gponOltSideOntUtilPmCurrentIntervalRxUcastBytes OBJECT-TYPE
	SYNTAX 	OCTET STRING (SIZE(8))
	ACCESS	read-only
	STATUS	mandatory
	DESCRIPTION 
		"This attribute specifies the total unicast bytes on the PON 
          	in the upstream direction from the specified ONT index

		For GPON - SUPPORTED as of ISAM5.2
		For XG-PON1 - NOT SUPPORTED
		NG-PON2 - NOT SUPPORTED as of ISAM5.2.01 (for channel pairs) "
	::= { gponOltSideOntUtilPmCurrentIntervalEntry 3 }


gponOltSideOntUtilPmCurrentIntervalTxUcastDropBytes OBJECT-TYPE
	SYNTAX 	OCTET STRING (SIZE(8))
	ACCESS	read-only
	STATUS	mandatory
	DESCRIPTION 
		"This attribute specifies the total unicast bytes dropped on the PON 
          in the downstream direction for the specified ONT index

		For GPON - SUPPORTED as of ISAM5.2
		For XG-PON1 - NOT SUPPORTED
		NG-PON2 - NOT SUPPORTED as of ISAM5.2.01 (for channel pairs) "

	::= { gponOltSideOntUtilPmCurrentIntervalEntry 4 }

gponOltSideOntUtilPmCurrentIntervalRxUcastDropBytes OBJECT-TYPE
	SYNTAX 	OCTET STRING (SIZE(8))
	ACCESS	read-only
	STATUS	mandatory
	DESCRIPTION 
		"This attribute specifies the total unicast bytes dropped on the PON 
          in the upstream direction from the specified ONT index

		For GPON - SUPPORTED as of ISAM5.2
		For XG-PON1 - NOT SUPPORTED
		NG-PON2 - NOT SUPPORTED as of ISAM5.2.01 (for channel pairs) "
	::= { gponOltSideOntUtilPmCurrentIntervalEntry 5 }

gponOltSideOntUtilPmCurrentIntervalTxUcastPackets OBJECT-TYPE
	SYNTAX 	OCTET STRING (SIZE(8))
	ACCESS	read-only
	STATUS	mandatory
	DESCRIPTION 
		"This attribute specifies the total unicast Packets transmitted on the PON 
          in the downstream direction to the specified ONT index

		For GPON - SUPPORTED as of ISAM5.2
		For XG-PON1 - NOT SUPPORTED
		NG-PON2 - NOT SUPPORTED as of ISAM5.2.01 (for channel pairs) "

	::= { gponOltSideOntUtilPmCurrentIntervalEntry 6 }

gponOltSideOntUtilPmCurrentIntervalRxUcastPackets OBJECT-TYPE
	SYNTAX 	OCTET STRING (SIZE(8))
	ACCESS	read-only
	STATUS	mandatory
	DESCRIPTION 
		"This attribute specifies the total unicast Packets on the PON 
          	in the upstream direction from the specified ONT index

		For GPON - SUPPORTED as of ISAM5.2
		For XG-PON1 - NOT SUPPORTED
		NG-PON2 - NOT SUPPORTED as of ISAM5.2.01 (for channel pairs) "
	::= { gponOltSideOntUtilPmCurrentIntervalEntry 7 }


gponOltSideOntUtilPmCurrentIntervalTxUcastDropPackets OBJECT-TYPE
	SYNTAX 	OCTET STRING (SIZE(8))
	ACCESS	read-only
	STATUS	mandatory
	DESCRIPTION 
		"This attribute specifies the total unicast Packets dropped on the PON 
          in the downstream direction for the specified ONT index

		For GPON - SUPPORTED as of ISAM5.2
		For XG-PON1 - NOT SUPPORTED
		NG-PON2 - NOT SUPPORTED as of ISAM5.2.01 (for channel pairs) "

	::= { gponOltSideOntUtilPmCurrentIntervalEntry 8 }

gponOltSideOntUtilPmCurrentIntervalRxUcastDropPackets OBJECT-TYPE
	SYNTAX 	OCTET STRING (SIZE(8))
	ACCESS	read-only
	STATUS	mandatory
	DESCRIPTION 
		"This attribute specifies the total unicast Packets dropped on the PON 
          in the upstream direction from the specified ONT index

		For GPON - SUPPORTED as of ISAM5.2
		For XG-PON1 - NOT SUPPORTED
		NG-PON2 - NOT SUPPORTED as of ISAM5.2.01 (for channel pairs) "
	::= { gponOltSideOntUtilPmCurrentIntervalEntry 9 }


-- *********************************************
--
-- GPON OLTSIDE ONT UTILIZATION PERFORMANCE MONITOR INTERVAL TABLE (5-minute cycle)
--
-- This is a new table beginning with ISAM5.2 (re-indexed from FTTU4.9).
-- This interval table contains various statistics collected for 
-- the ONT on the PON during the previous 5-minute intervals of operation.
--
-- An instance of this table is auto-created/deleted in accordance with the 
-- ' bponPonConfigPonUtilOntDetailSelector' setting of PON (in this MIB).
-- ' ng2ChanPairConfigUtilOntDetailSelector' setting of channel pair (in NG-PON2 MIB).
--
--	For GPON - SUPPORTED as of ISAM5.2 (for PONs)
--	For XG-PON1 - NOT SUPPORTED
--	For NG-PON2 - NOT SUPPORTED as of ISAM5.2.01 (for channel pairs)
-- *********************************************

gponOltSideOntUtilPmIntervalTable  OBJECT-TYPE
	SYNTAX SEQUENCE OF GponOltSideOntUtilPmIntervalEntry
	ACCESS	not-accessible
	STATUS	mandatory
	::= { gponServicesGroup 64 }


gponOltSideOntUtilPmIntervalEntry OBJECT-TYPE
	SYNTAX 	GponOltSideOntUtilPmIntervalEntry
	ACCESS	not-accessible
	STATUS	mandatory
	DESCRIPTION 
		"An entry in the Oltside ONT Utilization interval
		 Table. "
	INDEX	{ ponIfIndex, ontIfIndex, pmIntervalNum }	
-- First ifIndex is the ifIndex of either a PON (as of ISAM5.2) or 
--	a channel-pair(as of ISAM5.2.01)
-- Second ifIndex is the ifIndex of the ONT
-- Third index pmIntervalNum range is 1..288

::= { gponOltSideOntUtilPmIntervalTable  1 }

GponOltSideOntUtilPmIntervalEntry::= SEQUENCE {
               gponOltSideOntUtilPmIntervalTxUcastBytes   OCTET STRING,
               gponOltSideOntUtilPmIntervalRxUcastBytes    OCTET STRING,
               gponOltSideOntUtilPmIntervalTxUcastDropBytes  OCTET STRING,
               gponOltSideOntUtilPmIntervalRxUcastDropBytes  OCTET STRING,
               gponOltSideOntUtilPmIntervalTxUcastPackets   OCTET STRING,
               gponOltSideOntUtilPmIntervalRxUcastPackets    OCTET STRING,
               gponOltSideOntUtilPmIntervalTxUcastDropPackets  OCTET STRING,
               gponOltSideOntUtilPmIntervalRxUcastDropPackets  OCTET STRING
}



gponOltSideOntUtilPmIntervalTxUcastBytes OBJECT-TYPE
	SYNTAX 	OCTET STRING (SIZE(8))
	ACCESS	read-only
	STATUS	mandatory
	DESCRIPTION 
		"This attribute specifies the total unicast bytes transmitted on the PON 
          in the downstream direction to the specified ONT index

		For GPON - SUPPORTED as of ISAM5.2
		For XG-PON1 - NOT SUPPORTED
		NG-PON2 - NOT SUPPORTED as of ISAM5.2.01 (for channel pairs) "

	::= { gponOltSideOntUtilPmIntervalEntry 3 }

gponOltSideOntUtilPmIntervalRxUcastBytes OBJECT-TYPE
	SYNTAX 	OCTET STRING (SIZE(8))
	ACCESS	read-only
	STATUS	mandatory
	DESCRIPTION 
		"This attribute specifies the total unicast bytes on the PON 
          	in the upstream direction from the specified ONT index

		For GPON - SUPPORTED as of ISAM5.2
		For XG-PON1 - NOT SUPPORTED
		NG-PON2 - NOT SUPPORTED as of ISAM5.2.01 (for channel pairs) "
	::= { gponOltSideOntUtilPmIntervalEntry 4 }


gponOltSideOntUtilPmIntervalTxUcastDropBytes OBJECT-TYPE
	SYNTAX 	OCTET STRING (SIZE(8))
	ACCESS	read-only
	STATUS	mandatory
	DESCRIPTION 
		"This attribute specifies the total unicast bytes dropped on the PON 
          in the downstream direction for the specified ONT index

		For GPON - SUPPORTED as of ISAM5.2
		For XG-PON1 - NOT SUPPORTED
		NG-PON2 - NOT SUPPORTED as of ISAM5.2.01 (for channel pairs) "

	::= { gponOltSideOntUtilPmIntervalEntry 5 }

gponOltSideOntUtilPmIntervalRxUcastDropBytes OBJECT-TYPE
	SYNTAX 	OCTET STRING (SIZE(8))
	ACCESS	read-only
	STATUS	mandatory
	DESCRIPTION 
		"This attribute specifies the total unicast bytes dropped on the PON 
          in the upstream direction from the specified ONT index

		For GPON - SUPPORTED as of ISAM5.2
		For XG-PON1 - NOT SUPPORTED
		NG-PON2 - NOT SUPPORTED as of ISAM5.2.01 (for channel pairs) "
	::= { gponOltSideOntUtilPmIntervalEntry 6 }


gponOltSideOntUtilPmIntervalTxUcastPackets OBJECT-TYPE
	SYNTAX 	OCTET STRING (SIZE(8))
	ACCESS	read-only
	STATUS	mandatory
	DESCRIPTION 
		"This attribute specifies the total unicast Packets transmitted on the PON 
          in the downstream direction to the specified ONT index

		For GPON - SUPPORTED as of ISAM5.2
		For XG-PON1 - NOT SUPPORTED
		NG-PON2 - NOT SUPPORTED as of ISAM5.2.01 (for channel pairs) "

	::= { gponOltSideOntUtilPmIntervalEntry 7 }

gponOltSideOntUtilPmIntervalRxUcastPackets OBJECT-TYPE
	SYNTAX 	OCTET STRING (SIZE(8))
	ACCESS	read-only
	STATUS	mandatory
	DESCRIPTION 
		"This attribute specifies the total unicast Packets on the PON 
          	in the upstream direction from the specified ONT index

		For GPON - SUPPORTED as of ISAM5.2
		For XG-PON1 - NOT SUPPORTED
		NG-PON2 - NOT SUPPORTED as of ISAM5.2.01 (for channel pairs) "
	::= { gponOltSideOntUtilPmIntervalEntry 8 }


gponOltSideOntUtilPmIntervalTxUcastDropPackets OBJECT-TYPE
	SYNTAX 	OCTET STRING (SIZE(8))
	ACCESS	read-only
	STATUS	mandatory
	DESCRIPTION 
		"This attribute specifies the total unicast Packets dropped on the PON 
          in the downstream direction for the specified ONT index

		For GPON - SUPPORTED as of ISAM5.2
		For XG-PON1 - NOT SUPPORTED
		NG-PON2 - NOT SUPPORTED as of ISAM5.2.01 (for channel pairs) "

	::= { gponOltSideOntUtilPmIntervalEntry 9 }

gponOltSideOntUtilPmIntervalRxUcastDropPackets OBJECT-TYPE
	SYNTAX 	OCTET STRING (SIZE(8))
	ACCESS	read-only
	STATUS	mandatory
	DESCRIPTION 
		"This attribute specifies the total unicast Packets dropped on the PON 
          in the upstream direction from the specified ONT index

		For GPON - SUPPORTED as of ISAM5.2
		For XG-PON1 - NOT SUPPORTED
		NG-PON2 - NOT SUPPORTED as of ISAM5.2.01 (for channel pairs) "
	::= { gponOltSideOntUtilPmIntervalEntry 10 }


-- *********************************************
--
-- GPON OLTSIDE ONT UTILIZATION BULK PERFORMANCE MONITOR 
-- INTERVAL TABLE (5-minute cycle)
--
-- This is a new table beginning with ISAM5.2.
-- This interval table contains various statistics collected for 
-- the ONT on the PON during the previous three 5-minute intervals of operation.
--
-- This table is used by the ALU EMS in order to prepare a 'ConfigFile'
-- for the BFMU.
--
-- An instance of this table is auto-created/deleted in accordance with the 
-- 'bponPonConfigPonUtilOntBulkDetailSelector' setting of the PON (in this MIB).
-- ' ng2ChanPairConfigUtilOntBulkDetailSelector' setting of channel pair (in NG-PON2 MIB).
--
--	For GPON - SUPPORTED as of ISAM5.2 (for PONs)
--	For XG-PON1 - NOT SUPPORTED
--	For NG-PON2 - NOT SUPPORTED as of ISAM5.2.01 (for channel pairs)
-- *********************************************

gponOltSideOntUtilBulkPmIntervalTable  OBJECT-TYPE
	SYNTAX SEQUENCE OF GponOltSideOntUtilBulkPmIntervalEntry
	ACCESS	not-accessible
	STATUS	mandatory
	::= { gponServicesGroup 66 }


gponOltSideOntUtilBulkPmIntervalEntry OBJECT-TYPE
	SYNTAX 	GponOltSideOntUtilBulkPmIntervalEntry
	ACCESS	not-accessible
	STATUS	mandatory
	DESCRIPTION 
		"An entry in the Oltside ONT Utilization Bulk interval
		 Table. "
	INDEX	{ ponIfIndex, ontIfIndex, pmIntervalNum }
	
-- First ifIndex is the ifIndex of either a PON (as of ISAM5.2) or
--	 a channel-pair (as of ISAM5.2.01)
-- Second ifIndex is the ifIndex of the ONT
-- Third index pmIntervalNum range is 1..3

::= { gponOltSideOntUtilBulkPmIntervalTable  1 }

GponOltSideOntUtilBulkPmIntervalEntry::= SEQUENCE {
               gponOltSideOntUtilBulkPmIntervalTxUcastBytes   OCTET STRING,
               gponOltSideOntUtilBulkPmIntervalRxUcastBytes    OCTET STRING,
               gponOltSideOntUtilBulkPmIntervalTxUcastDropBytes  OCTET STRING,
               gponOltSideOntUtilBulkPmIntervalRxUcastDropBytes  OCTET STRING,
               gponOltSideOntUtilBulkPmIntervalTxUcastPackets   OCTET STRING,
               gponOltSideOntUtilBulkPmIntervalRxUcastPackets    OCTET STRING,
               gponOltSideOntUtilBulkPmIntervalTxUcastDropPackets  OCTET STRING,
               gponOltSideOntUtilBulkPmIntervalRxUcastDropPackets  OCTET STRING
}



gponOltSideOntUtilBulkPmIntervalTxUcastBytes OBJECT-TYPE
	SYNTAX 	OCTET STRING (SIZE(8))
	ACCESS	read-only
	STATUS	mandatory
	DESCRIPTION 
		"This attribute specifies the total unicast bytes transmitted on the PON 
          in the downstream direction to the specified ONT index

		For GPON - SUPPORTED as of ISAM5.2
		For XG-PON1 - NOT SUPPORTED
		NG-PON2 - NOT SUPPORTED as of ISAM5.2.01 (for channel pairs) "

	::= { gponOltSideOntUtilBulkPmIntervalEntry 3 }

gponOltSideOntUtilBulkPmIntervalRxUcastBytes OBJECT-TYPE
	SYNTAX 	OCTET STRING (SIZE(8))
	ACCESS	read-only
	STATUS	mandatory
	DESCRIPTION 
		"This attribute specifies the total unicast bytes on the PON 
          	in the upstream direction from the specified ONT index

		For GPON - SUPPORTED as of ISAM5.2
		For XG-PON1 - NOT SUPPORTED
		NG-PON2 - NOT SUPPORTED as of ISAM5.2.01 (for channel pairs) "
	::= { gponOltSideOntUtilBulkPmIntervalEntry 4 }


gponOltSideOntUtilBulkPmIntervalTxUcastDropBytes OBJECT-TYPE
	SYNTAX 	OCTET STRING (SIZE(8))
	ACCESS	read-only
	STATUS	mandatory
	DESCRIPTION 
		"This attribute specifies the total unicast bytes dropped on the PON 
          in the downstream direction for the specified ONT index

		For GPON - SUPPORTED as of ISAM5.2
		For XG-PON1 - NOT SUPPORTED
		NG-PON2 - NOT SUPPORTED as of ISAM5.2.01 (for channel pairs) "

	::= { gponOltSideOntUtilBulkPmIntervalEntry 5 }

gponOltSideOntUtilBulkPmIntervalRxUcastDropBytes OBJECT-TYPE
	SYNTAX 	OCTET STRING (SIZE(8))
	ACCESS	read-only
	STATUS	mandatory
	DESCRIPTION 
		"This attribute specifies the total unicast bytes dropped on the PON 
          in the upstream direction from the specified ONT index

		For GPON - SUPPORTED as of ISAM5.2
		For XG-PON1 - NOT SUPPORTED
		NG-PON2 - NOT SUPPORTED as of ISAM5.2.01 (for channel pairs) "
	::= { gponOltSideOntUtilBulkPmIntervalEntry 6 }


gponOltSideOntUtilBulkPmIntervalTxUcastPackets OBJECT-TYPE
	SYNTAX 	OCTET STRING (SIZE(8))
	ACCESS	read-only
	STATUS	mandatory
	DESCRIPTION 
		"This attribute specifies the total unicast Packets transmitted on the PON 
          in the downstream direction to the specified ONT index

		For GPON - SUPPORTED as of ISAM5.2
		For XG-PON1 - NOT SUPPORTED
		NG-PON2 - NOT SUPPORTED as of ISAM5.2.01 (for channel pairs) "

	::= { gponOltSideOntUtilBulkPmIntervalEntry 7 }

gponOltSideOntUtilBulkPmIntervalRxUcastPackets OBJECT-TYPE
	SYNTAX 	OCTET STRING (SIZE(8))
	ACCESS	read-only
	STATUS	mandatory
	DESCRIPTION 
		"This attribute specifies the total unicast Packets on the PON 
          	in the upstream direction from the specified ONT index

		For GPON - SUPPORTED as of ISAM5.2
		For XG-PON1 - NOT SUPPORTED
		NG-PON2 - NOT SUPPORTED as of ISAM5.2.01 (for channel pairs) "
	::= { gponOltSideOntUtilBulkPmIntervalEntry 8 }


gponOltSideOntUtilBulkPmIntervalTxUcastDropPackets OBJECT-TYPE
	SYNTAX 	OCTET STRING (SIZE(8))
	ACCESS	read-only
	STATUS	mandatory
	DESCRIPTION 
		"This attribute specifies the total unicast Packets dropped on the PON 
          in the downstream direction for the specified ONT index

		For GPON - SUPPORTED as of ISAM5.2
		For XG-PON1 - NOT SUPPORTED
		NG-PON2 - NOT SUPPORTED as of ISAM5.2.01 (for channel pairs) "

	::= { gponOltSideOntUtilBulkPmIntervalEntry 9 }

gponOltSideOntUtilBulkPmIntervalRxUcastDropPackets OBJECT-TYPE
	SYNTAX 	OCTET STRING (SIZE(8))
	ACCESS	read-only
	STATUS	mandatory
	DESCRIPTION 
		"This attribute specifies the total unicast Packets dropped on the PON 
          in the upstream direction from the specified ONT index

		For GPON - SUPPORTED as of ISAM5.2
		For XG-PON1 - NOT SUPPORTED
		NG-PON2 - NOT SUPPORTED as of ISAM5.2.01 (for channel pairs) "
	::= { gponOltSideOntUtilBulkPmIntervalEntry 10 }

-- *********************************************
--
-- GPON ETHERNET TRAFFIC PERFORMANCE MONITOR CURRENT INTERVAL TABLE
--
-- This is a new table beginning with FGU4.2.
-- This current interval table contains Ethernet traffic statistics collected
-- at an ONT's data interface during the current 15 minute interval 
-- of operation.  The physical data interface could be any of the following:
-- Ethernet, XDSL, HPNA or MoCA.
--
-- An instance of this table is auto-created/deleted in accordance with the 
-- 'Ethernet Traffic PM Collect Indicator' setting of the particular data UNI.
--
-- For GETs of table attributes, the OLT must go directly to the ONT (via OMCI)
-- in order to acquire fresh current counts. 
--
-- For ISAM4.0.10, this table is being re-used. 
-- Noted which attributes are relevant for ISAM4.0.10
--
-- For ISAM4.2, extended the table with additional attributes (noted within).
--
--	For GPON - SUPPORTED as of ISAM4.2
--	For XG-PON1 - SUPPORTED as of ISAM4.6.02
--	For NG-PON2 - SUPPORTED as of ISAM5.2 (For Ethernet UNI only)
-- 
-- 
-- *********************************************


gponEtherTrafficCurrentIntervalTable  OBJECT-TYPE
	SYNTAX SEQUENCE OF GponEtherTrafficCurrentIntervalEntry
	ACCESS	not-accessible
	STATUS	mandatory
	::= { gponEthernetGroup 1 }


gponEtherTrafficCurrentIntervalEntry  OBJECT-TYPE
	SYNTAX 	GponEtherTrafficCurrentIntervalEntry
	ACCESS	not-accessible
	STATUS	mandatory
	DESCRIPTION 
		"An entry in the Gpon Ethernet Traffic CurrentInterval 
		 Table. "
	INDEX	{ gponEtherTrafficCurrentIntervalOntIndex,
		  gponEtherTrafficCurrentIntervalSpIndex }
	::= { gponEtherTrafficCurrentIntervalTable 1 }

GponEtherTrafficCurrentIntervalEntry ::= SEQUENCE {
	gponEtherTrafficCurrentIntervalOntIndex			IfIndex,
	gponEtherTrafficCurrentIntervalSpIndex			SpIndex,
	gponEtherTrafficCurrentIntervalValidInd			Boolean,
	gponEtherTrafficCurrentIntervalTxFrames		Counter,
	gponEtherTrafficCurrentIntervalRxFrames		Counter,
	gponEtherTrafficCurrentIntervalTxBytes			Counter,
	gponEtherTrafficCurrentIntervalRxBytes		Counter,
	gponEtherTrafficCurrentIntervalDroppedFramesUp		Counter,
	gponEtherTrafficCurrentIntervalDroppedBytesUp		Counter,
	gponEtherTrafficCurrentIntervalDroppedFramesDown		Counter,
	gponEtherTrafficCurrentIntervalTxFramesMulticast	Counter,
	gponEtherTrafficCurrentIntervalRxFramesMulticast	Counter,
gponEtherTrafficCurrentIntervalRxDropEvents		Counter,
	gponEtherTrafficCurrentIntervalRxFramesBroadcast	Counter,
	gponEtherTrafficCurrentIntervalRxCRCErrorFrames	Counter,
	gponEtherTrafficCurrentIntervalRxUndersizeFrames	Counter,
	gponEtherTrafficCurrentIntervalRxOversizeFrames	Counter,
	gponEtherTrafficCurrentIntervalRx64octets			Counter,
	gponEtherTrafficCurrentIntervalRx65to127octets		Counter,
	gponEtherTrafficCurrentIntervalRx128to255octets		Counter,
	gponEtherTrafficCurrentIntervalRx256to511octets		Counter,
	gponEtherTrafficCurrentIntervalRx512to1023octets	Counter,
	gponEtherTrafficCurrentIntervalRx1024to1518octets	Counter,
	gponEtherTrafficCurrentIntervalTxDropEvents		Counter,
	gponEtherTrafficCurrentIntervalTxFramesBroadcast	Counter,
	gponEtherTrafficCurrentIntervalTxCRCErrorFrames	Counter,
	gponEtherTrafficCurrentIntervalTxUndersizeFrames	Counter,
	gponEtherTrafficCurrentIntervalTxOversizeFrames	Counter,
	gponEtherTrafficCurrentIntervalTx64octets			Counter,
	gponEtherTrafficCurrentIntervalTx65to127octets		Counter,
	gponEtherTrafficCurrentIntervalTx128to255octets		Counter,
	gponEtherTrafficCurrentIntervalTx256to511octets		Counter,
	gponEtherTrafficCurrentIntervalTx512to1023octets	Counter,
	gponEtherTrafficCurrentIntervalTx1024to1518octets	Counter,
	gponEtherTrafficCurrentIntervalRxPackets		Counter,
	gponEtherTrafficCurrentIntervalTxPackets		Counter,
	gponEtherTrafficCurrentIntervalTxBytesCounter64	   OCTET STRING,
	gponEtherTrafficCurrentIntervalRxBytesCounter64	   OCTET STRING,
	gponEtherTrafficCurrentIntervalTxPacketsCounter64	OCTET STRING,
	gponEtherTrafficCurrentIntervalRxPacketsCounter64	OCTET STRING

}


gponEtherTrafficCurrentIntervalOntIndex  OBJECT-TYPE
	SYNTAX 	IfIndex
	ACCESS	read-only
	STATUS	mandatory
	DESCRIPTION 
		"Each row is indexed by the ifIndex of the ONT.

		For ISAM 4.0.10 -> stays the same as latest FGU4.x  "
	::= { gponEtherTrafficCurrentIntervalEntry 1 }


gponEtherTrafficCurrentIntervalSpIndex  OBJECT-TYPE
	SYNTAX 	SpIndex
	ACCESS	read-only
	STATUS	mandatory
	DESCRIPTION 
		"Each row is also indexed by the slot/port of the physical UNI.

		For ISAM 4.0.10 -> stays the same as latest FGU4.x   "
	::= { gponEtherTrafficCurrentIntervalEntry 2 }


gponEtherTrafficCurrentIntervalValidInd  OBJECT-TYPE
	SYNTAX 	Boolean
	ACCESS	read-only
	STATUS	mandatory
	DESCRIPTION 
		"Indicates whether or not this CurrentInterval contains
		 valid PM counts. 

		 As of FGU4.2, NOT SUPPORTED

		For ISAM 4.0.10 -> stays the same as latest FGU4.x   "
	::= { gponEtherTrafficCurrentIntervalEntry 3 }


gponEtherTrafficCurrentIntervalTxFrames  OBJECT-TYPE
	SYNTAX 	Counter
	ACCESS	read-only
	STATUS	mandatory
	DESCRIPTION 
		"A count of Transmitted Ethernet Frames.

		For ISAM 4.0.10 -> stays the same as latest FGU4.x  "
	::= { gponEtherTrafficCurrentIntervalEntry 4 }


gponEtherTrafficCurrentIntervalRxFrames  OBJECT-TYPE
	SYNTAX 	Counter
	ACCESS	read-only
	STATUS	mandatory
	DESCRIPTION 
		"A count of Received Ethernet Frames.

		For ISAM 4.0.10 -> stays the same as latest FGU4.x  "
	::= { gponEtherTrafficCurrentIntervalEntry 5 }


gponEtherTrafficCurrentIntervalTxBytes  OBJECT-TYPE
	SYNTAX 	Counter
	ACCESS	read-only
	STATUS	mandatory
	DESCRIPTION 
		"A count of Transmitted Ethernet Bytes.

		For ISAM 4.0.10 -> stays the same as latest FGU4.x


		 As of ISAM4.5, the plan is to effectively DEPRECATE this attribute.  Manager should instead use equivalent 
		 64-bit counter attribute gponEtherTrafficCurrentIntervalTxBytesCounter64.  "
	::= { gponEtherTrafficCurrentIntervalEntry 6 }


gponEtherTrafficCurrentIntervalRxBytes  OBJECT-TYPE
	SYNTAX 	Counter
	ACCESS	read-only
	STATUS	mandatory
	DESCRIPTION 
		"A count of Received Ethernet Bytes.

		For ISAM 4.0.10 -> stays the same as latest FGU4.x

		 As of ISAM4.5, the plan is to effectively DEPRECATE this attribute.  Manager should instead use equivalent 
		 64-bit counter attribute gponEtherTrafficCurrentIntervalRxBytesCounter64. " 
	::= { gponEtherTrafficCurrentIntervalEntry 7 }


gponEtherTrafficCurrentIntervalDroppedFramesUp  OBJECT-TYPE
	SYNTAX 	Counter
	ACCESS	read-only
	STATUS	mandatory
	DESCRIPTION 
		"A count of Dropped Frames Upstream.

		For ISAM 4.0.10 -> stays the same as latest FGU4.x  "
	::= { gponEtherTrafficCurrentIntervalEntry 8 }


gponEtherTrafficCurrentIntervalDroppedBytesUp  OBJECT-TYPE
	SYNTAX 	Counter
	ACCESS	read-only
	STATUS	mandatory
	DESCRIPTION 
		"A count of Dropped Bytes Upstream.

		 As of FGU4.2, this is NOT SUPPORTED 

		For ISAM 4.0.10 -> stays the same as latest FGU4.x  "
	::= { gponEtherTrafficCurrentIntervalEntry 9 }


gponEtherTrafficCurrentIntervalDroppedFramesDown  OBJECT-TYPE
	SYNTAX 	Counter
	ACCESS	read-only
	STATUS	mandatory
	DESCRIPTION 
		"A count of Dropped Frames Downstream.

		For ISAM 4.0.10 -> stays the same as latest FGU4.x  "
	::= { gponEtherTrafficCurrentIntervalEntry 10 }


gponEtherTrafficCurrentIntervalTxFramesMulticast  OBJECT-TYPE
	SYNTAX 	Counter
	ACCESS	read-only
	STATUS	mandatory
	DESCRIPTION 
		"A count of Transmitted Multicast Ethernet Frames.

		For ISAM 4.0.10 -> stays the same as latest FGU4.x  "
	::= { gponEtherTrafficCurrentIntervalEntry 11 }


gponEtherTrafficCurrentIntervalRxFramesMulticast  OBJECT-TYPE
	SYNTAX 	Counter
	ACCESS	read-only
	STATUS	mandatory
	DESCRIPTION 
		"A count of Received Multicast Ethernet Frames.

		For ISAM 4.0.10 -> stays the same as latest FGU4.x  "
	::= { gponEtherTrafficCurrentIntervalEntry 12 }


gponEtherTrafficCurrentIntervalRxDropEvents	  OBJECT-TYPE
	SYNTAX 	Counter
	ACCESS	read-only
	STATUS	mandatory
	DESCRIPTION 
		"The total number of events in which packets were dropped due to lack of
resources. This is not necessarily the number of packets dropped; it is the number of times this event was detected.

		 As of ISAM4.2 -> SUPPORTED. "
	::= { gponEtherTrafficCurrentIntervalEntry 13 }

	gponEtherTrafficCurrentIntervalRxFramesBroadcast	  OBJECT-TYPE
	SYNTAX 	Counter
	ACCESS	read-only
	STATUS	mandatory
	DESCRIPTION 
		"The total number of received good packets directed to the broadcast
address. This does not include multicast packets.

		 As of ISAM4.2 -> SUPPORTED. "
	::= { gponEtherTrafficCurrentIntervalEntry 14 }

	gponEtherTrafficCurrentIntervalRxCRCErrorFrames	  OBJECT-TYPE
	SYNTAX 	Counter
	ACCESS	read-only
	STATUS	mandatory
	DESCRIPTION 
		"The total number of packets received that had a length (excluding
framing bits, but including FCS octets) of between 64 and 1518 octets,
inclusive, but had either a bad frame check sequence (FCS) with an integral
number of octets (FCS error) or a bad FCS with a non-integral number of
octets (alignment error).

		 As of ISAM4.2 -> SUPPORTED. "
	::= { gponEtherTrafficCurrentIntervalEntry 15 }

	gponEtherTrafficCurrentIntervalRxUndersizeFrames	  OBJECT-TYPE
	SYNTAX 	Counter
	ACCESS	read-only
	STATUS	mandatory
	DESCRIPTION 
		"The total number of packets received that were less than 64 octets long
but were otherwise well formed (excluding framing bits, but including FCS
octets).

		 As of ISAM4.2 -> SUPPORTED. "
	::= { gponEtherTrafficCurrentIntervalEntry 16 }

	gponEtherTrafficCurrentIntervalRxOversizeFrames	  OBJECT-TYPE
	SYNTAX 	Counter
	ACCESS	read-only
	STATUS	mandatory
	DESCRIPTION 
		"The total number of packets received that were longer than 1518 octets
(excluding framing bits, but including FCS octets) and were otherwise well
formed.

		 As of ISAM4.2 -> SUPPORTED. "
	::= { gponEtherTrafficCurrentIntervalEntry 17 }

	gponEtherTrafficCurrentIntervalRx64octets	  OBJECT-TYPE
	SYNTAX 	Counter
	ACCESS	read-only
	STATUS	mandatory
	DESCRIPTION 
		"The total number of received packets (including bad packets) that were
64 octets long, excluding framing bits but including FCS.

		 As of ISAM4.2 -> SUPPORTED. "
	::= { gponEtherTrafficCurrentIntervalEntry 18 }

gponEtherTrafficCurrentIntervalRx65to127octets	  OBJECT-TYPE
	SYNTAX 	Counter
	ACCESS	read-only
	STATUS	mandatory
	DESCRIPTION 
		"The total number of received packets (including bad packets) that
were 65..127 octets long, excluding framing bits but including FCS.

		 As of ISAM4.2 -> SUPPORTED. "
::= { gponEtherTrafficCurrentIntervalEntry 19 }

gponEtherTrafficCurrentIntervalRx128to255octets	  OBJECT-TYPE
	SYNTAX 	Counter
	ACCESS	read-only
	STATUS	mandatory
	DESCRIPTION 
		"The total number of packets (including bad packets) received
that were 128..255 octets long, excluding framing bits but including FCS.

		 As of ISAM4.2 -> SUPPORTED. "
::= { gponEtherTrafficCurrentIntervalEntry 20 }

gponEtherTrafficCurrentIntervalRx256to511octets	  OBJECT-TYPE
	SYNTAX 	Counter
	ACCESS	read-only
	STATUS	mandatory
	DESCRIPTION 
"The total number of packets (including bad packets) received that were 256..511 octets long, excluding framing bits but including FCS.

		 As of ISAM4.2 -> SUPPORTED. "
::= { gponEtherTrafficCurrentIntervalEntry 21 }

gponEtherTrafficCurrentIntervalRx512to1023octets	  OBJECT-TYPE
	SYNTAX 	Counter
	ACCESS	read-only
	STATUS	mandatory
	DESCRIPTION 
		"The total number of packets (including bad packets) received
that were 512..1023 octets long, excluding framing bits but including FCS.

		 As of ISAM4.2 -> SUPPORTED. "
::= { gponEtherTrafficCurrentIntervalEntry 22 }

gponEtherTrafficCurrentIntervalRx1024to1518octets	  OBJECT-TYPE
	SYNTAX 	Counter
	ACCESS	read-only
	STATUS	mandatory
	DESCRIPTION 
		"The total number of packets (including bad packets) received
that were 1024..1518 octets long, excluding framing bits but including FCS.

		 As of ISAM4.2 -> SUPPORTED. "
::= { gponEtherTrafficCurrentIntervalEntry 23 }

gponEtherTrafficCurrentIntervalTxDropEvents	  OBJECT-TYPE
	SYNTAX 	Counter
	ACCESS	read-only
	STATUS	mandatory
	DESCRIPTION 
		" The total number of events in which packets were dropped due to lack of
resources. This is not necessarily the number of packets dropped; it is the number of times this event was detected

		 As of ISAM4.2 -> SUPPORTED.  "
::= { gponEtherTrafficCurrentIntervalEntry 24 }

	gponEtherTrafficCurrentIntervalTxFramesBroadcast	  OBJECT-TYPE
	SYNTAX 	Counter
	ACCESS	read-only
	STATUS	mandatory
	DESCRIPTION 
		" The total number of transmitted good packets directed to the broadcast
address. This does not include multicast packets

		 As of ISAM4.2 -> SUPPORTED. "
	::= { gponEtherTrafficCurrentIntervalEntry 25 }

	gponEtherTrafficCurrentIntervalTxCRCErrorFrames	  OBJECT-TYPE
	SYNTAX 	Counter
	ACCESS	read-only
	STATUS	mandatory
	DESCRIPTION 
		" The total number of packets transmitted that had a length (excluding
framing bits, but including FCS octets) of between 64 and 1518 octets,
inclusive, but had either a bad frame check sequence (FCS) with an integral
number of octets (FCS error) or a bad FCS with a non-integral number of
octets (alignment error).

		 As of ISAM4.2 -> SUPPORTED. "
	::= { gponEtherTrafficCurrentIntervalEntry 26 }

	gponEtherTrafficCurrentIntervalTxUndersizeFrames	  OBJECT-TYPE
	SYNTAX 	Counter
	ACCESS	read-only
	STATUS	mandatory
	DESCRIPTION 
		" The total number of packets transmitted that were less than 64 octets long
but were otherwise well formed (excluding framing bits, but including FCS
octets).

		 As of ISAM4.2 -> SUPPORTED.  "
	::= { gponEtherTrafficCurrentIntervalEntry 27 }

	gponEtherTrafficCurrentIntervalTxOversizeFrames	  OBJECT-TYPE
	SYNTAX 	Counter
	ACCESS	read-only
	STATUS	mandatory
	DESCRIPTION 
		" The total number of packets transmitted that were longer than 1518 octets
(excluding framing bits, but including FCS octets) and were otherwise well
formed

		 As of ISAM4.2 -> SUPPORTED.  "
	::= { gponEtherTrafficCurrentIntervalEntry 28 }

	gponEtherTrafficCurrentIntervalTx64octets	  OBJECT-TYPE
	SYNTAX 	Counter
	ACCESS	read-only
	STATUS	mandatory
	DESCRIPTION 
		"A The total number of transmitted packets (including bad packets) that were
64 octets long, excluding framing bits but including FCS

		 As of ISAM4.2 -> SUPPORTED.  "
	::= { gponEtherTrafficCurrentIntervalEntry 29 }

gponEtherTrafficCurrentIntervalTx65to127octets	  OBJECT-TYPE
	SYNTAX 	Counter
	ACCESS	read-only
	STATUS	mandatory
	DESCRIPTION 
		" The total number of transmitted packets (including bad packets) that
were 65..127 octets long, excluding framing bits but including FCS.

		 As of ISAM4.2 -> SUPPORTED. "
	::= { gponEtherTrafficCurrentIntervalEntry 30 }

gponEtherTrafficCurrentIntervalTx128to255octets	  OBJECT-TYPE
	SYNTAX 	Counter
	ACCESS	read-only
	STATUS	mandatory
	DESCRIPTION 
		" The total number of packets (including bad packets) transmitted
that were 128..255 octets long, excluding framing bits but including FCS.

		 As of ISAM4.2 -> SUPPORTED. "
::= { gponEtherTrafficCurrentIntervalEntry 31 }

gponEtherTrafficCurrentIntervalTx256to511octets	  OBJECT-TYPE
	SYNTAX 	Counter
	ACCESS	read-only
	STATUS	mandatory
	DESCRIPTION 
" The total number of packets (including bad packets) transmitted that were 256..511 octets long, excluding framing bits but including FCS.

		 As of ISAM4.2 -> SUPPORTED. "
::= { gponEtherTrafficCurrentIntervalEntry 32 }

gponEtherTrafficCurrentIntervalTx512to1023octets	  OBJECT-TYPE
	SYNTAX 	Counter
	ACCESS	read-only
	STATUS	mandatory
	DESCRIPTION 
		" The total number of packets (including bad packets) transmitted
that were 512..1023 octets long, excluding framing bits but including FCS.

		 As of ISAM4.2 -> SUPPORTED. "
::= { gponEtherTrafficCurrentIntervalEntry 33 }

gponEtherTrafficCurrentIntervalTx1024to1518octets	  OBJECT-TYPE
	SYNTAX 	Counter
	ACCESS	read-only
	STATUS	mandatory
	DESCRIPTION 
		" The total number of packets (including bad packets) transmitted
that were 1024..1518 octets long, excluding framing bits but including FCS

		 As of ISAM4.2 -> SUPPORTED.  "
::= { gponEtherTrafficCurrentIntervalEntry 34 }


gponEtherTrafficCurrentIntervalRxPackets	  OBJECT-TYPE
	SYNTAX 	Counter
	ACCESS	read-only
	STATUS	mandatory
	DESCRIPTION 
		"The total number of upstream packets received, including bad packets,
		broadcast packets and multicast packets. 

		 As of ISAM4.2 -> SUPPORTED. 

		 As of ISAM4.5, the plan is to effectively DEPRECATE this attribute.  Manager should instead use equivalent 
		 64-bit counter attribute gponEtherTrafficCurrentIntervalRxPacketsCounter64. "
	::= { gponEtherTrafficCurrentIntervalEntry 35 }

gponEtherTrafficCurrentIntervalTxPackets	  OBJECT-TYPE
	SYNTAX 	Counter
	ACCESS	read-only
	STATUS	mandatory
	DESCRIPTION 
		"The total number of downstream packets transmitted, including bad packets,
		broadcast packets and multicast packets. 

		 As of ISAM4.2 -> SUPPORTED.

		 As of ISAM4.5, the plan is to effectively DEPRECATE this attribute.  Manager should instead use equivalent 
		 64-bit counter attribute gponEtherTrafficCurrentIntervalTxPacketsCounter64. "
	::= { gponEtherTrafficCurrentIntervalEntry 36 }

gponEtherTrafficCurrentIntervalTxBytesCounter64  OBJECT-TYPE
	SYNTAX 	OCTET STRING (SIZE(8))
	ACCESS	read-only
	STATUS	mandatory
	DESCRIPTION 
		" This represents the equivalent of a 64-bit count of Transmitted Ethernet Bytes.

		 Introduced for readiness in ISAM 4.5 MIB.  Plan to support 32-bit counts in this attribute with ISAM4.5
		 with target implementation of 64-bit counts in ISAM4.5.01. "
	::= { gponEtherTrafficCurrentIntervalEntry 37 }


gponEtherTrafficCurrentIntervalRxBytesCounter64  OBJECT-TYPE
	SYNTAX 	OCTET STRING (SIZE(8))
	ACCESS	read-only
	STATUS	mandatory
	DESCRIPTION 
		" This represents the equivalent of a 64-bit count of Received Ethernet Bytes.

		 Introduced for readiness in ISAM 4.5 MIB.  Plan to support 32-bit counts in this attribute with ISAM4.5
		 with target implementation of 64-bit counts in ISAM4.5.01. "
	::= { gponEtherTrafficCurrentIntervalEntry 38 }

gponEtherTrafficCurrentIntervalTxPacketsCounter64  OBJECT-TYPE
	SYNTAX 	OCTET STRING (SIZE(8))
	ACCESS	read-only
	STATUS	mandatory
	DESCRIPTION 
		" This represents the equivalent of a 64-bit count of downstream Ethernet packets similar
		   to gponEtherTrafficCurrentIntervalTxPackets.

		 Introduced for readiness in ISAM 4.5 MIB.  Plan to support 32-bit counts in this attribute with ISAM4.5
		 with target implementation of 64-bit counts in ISAM4.5.01. "
	::= { gponEtherTrafficCurrentIntervalEntry 39 }


gponEtherTrafficCurrentIntervalRxPacketsCounter64  OBJECT-TYPE
	SYNTAX 	OCTET STRING (SIZE(8))
	ACCESS	read-only
	STATUS	mandatory
	DESCRIPTION 
		" This represents the equivalent of a 64-bit count of upstream Ethernet packets similar
		   to gponEtherTrafficCurrentIntervalRxPackets.

		 Introduced for readiness in ISAM 4.5 MIB.  Plan to support 32-bit counts in this attribute with ISAM4.5
		 with target implementation of 64-bit counts in ISAM4.5.01. "
	::= { gponEtherTrafficCurrentIntervalEntry 40 }


-- *********************************************
--
-- GPON ETHERNET TRAFFIC PERFORMANCE MONITOR  INTERVAL TABLE
--
-- This is a new table beginning with FGU4.2.
-- This interval table contains Ethernet traffic statistics collected
-- at an ONT's data interface over the previous 8 hours of operation.  The past 8 hours are
-- broken into 32 completed 15 minute intervals.  Each row in this table
-- represents one such interval associated with a physical data interface.  
-- The physical data interface could be any of the following:
-- Ethernet, XDSL, HPNA or MoCA.
--
-- An instance of this table is auto-created/deleted in accordance with the 
-- 'Ethernet Traffic PM Collect Indicator' setting of the particular data UNI.
--
-- For ISAM4.0.10, this table is being re-used. 
-- Noted which attributes are relevant for ISAM4.0.10
--
-- For ISAM4.2, extended the table and noted which new attributes are supported.
--
--	For GPON - SUPPORTED as of ISAM4.2
--	For XG-PON1 - SUPPORTED as of ISAM4.6.02
--	For NG-PON2 - SUPPORTED as of ISAM5.2 (For Ethernet UNI only)
--  
-- 
-- *********************************************


gponEtherTrafficIntervalTable  OBJECT-TYPE
	SYNTAX SEQUENCE OF GponEtherTrafficIntervalEntry
	ACCESS	not-accessible
	STATUS	mandatory
	::= { gponEthernetGroup 2 }


gponEtherTrafficIntervalEntry  OBJECT-TYPE
	SYNTAX 	GponEtherTrafficIntervalEntry
	ACCESS	not-accessible
	STATUS	mandatory
	DESCRIPTION 
		"An entry in the Gpon Ethernet Traffic CurrentInterval 
		 Table. "
	INDEX	{ gponEtherTrafficIntervalOntIndex,
		  gponEtherTrafficIntervalSpIndex,
		  gponEtherTrafficIntervalNumber  }
	::= { gponEtherTrafficIntervalTable 1 }

GponEtherTrafficIntervalEntry ::= SEQUENCE {
	gponEtherTrafficIntervalOntIndex			IfIndex,
	gponEtherTrafficIntervalSpIndex			SpIndex,
	gponEtherTrafficIntervalNumber		INTEGER,
	gponEtherTrafficIntervalValidInd			Boolean,
	gponEtherTrafficIntervalTxFrames		Counter,
	gponEtherTrafficIntervalRxFrames		Counter,
	gponEtherTrafficIntervalTxBytes			Counter,
	gponEtherTrafficIntervalRxBytes		Counter,
	gponEtherTrafficIntervalDroppedFramesUp		Counter,
	gponEtherTrafficIntervalDroppedBytesUp		Counter,
	gponEtherTrafficIntervalDroppedFramesDown		Counter,
	gponEtherTrafficIntervalTxFramesMulticast	Counter,
	gponEtherTrafficIntervalRxFramesMulticast	Counter,
	gponEtherTrafficIntervalRxDropEvents		Counter,
	gponEtherTrafficIntervalRxFramesBroadcast	Counter,
	gponEtherTrafficIntervalRxCRCErrorFrames	Counter,
	gponEtherTrafficIntervalRxUndersizeFrames	Counter,
	gponEtherTrafficIntervalRxOversizeFrames	Counter,
	gponEtherTrafficIntervalRx64octets		Counter,
	gponEtherTrafficIntervalRx65to127octets	Counter,
	gponEtherTrafficIntervalRx128to255octets	Counter,
	gponEtherTrafficIntervalRx256to511octets	Counter,
	gponEtherTrafficIntervalRx512to1023octets	Counter,
	gponEtherTrafficIntervalRx1024to1518octets	Counter,
	gponEtherTrafficIntervalTxDropEvents		Counter,
	gponEtherTrafficIntervalTxFramesBroadcast	Counter,
	gponEtherTrafficIntervalTxCRCErrorFrames	Counter,
	gponEtherTrafficIntervalTxUndersizeFrames	Counter,
	gponEtherTrafficIntervalTxOversizeFrames	Counter,
	gponEtherTrafficIntervalTx64octets		Counter,
	gponEtherTrafficIntervalTx65to127octets	Counter,
	gponEtherTrafficIntervalTx128to255octets	Counter,
	gponEtherTrafficIntervalTx256to511octets	Counter,
	gponEtherTrafficIntervalTx512to1023octets	Counter,
	gponEtherTrafficIntervalTx1024to1518octets	Counter,
	gponEtherTrafficIntervalRxPackets		Counter,
	gponEtherTrafficIntervalTxPackets		Counter,
	gponEtherTrafficIntervalTxBytesCounter64	OCTET STRING,
	gponEtherTrafficIntervalRxBytesCounter64	OCTET STRING,
	gponEtherTrafficIntervalTxPacketsCounter64	OCTET STRING,
	gponEtherTrafficIntervalRxPacketsCounter64	OCTET STRING
}


gponEtherTrafficIntervalOntIndex  OBJECT-TYPE
	SYNTAX 	IfIndex
	ACCESS	read-only
	STATUS	mandatory
	DESCRIPTION 
		"Each row is indexed by the ifIndex of the ONT.

		For ISAM 4.0.10 -> stays the same as latest FGU4.x  "
	::= { gponEtherTrafficIntervalEntry 1 }

gponEtherTrafficIntervalSpIndex  OBJECT-TYPE
	SYNTAX 	SpIndex
	ACCESS	read-only
	STATUS	mandatory
	DESCRIPTION 
		"Each row is also indexed by the slot/port of the physical UNI.

		For ISAM 4.0.10 -> stays the same as latest FGU4.x  "
	::= { gponEtherTrafficIntervalEntry 2 }

gponEtherTrafficIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.

		For ISAM 4.0.10 -> stays the same as latest FGU4.x  "
	::= { gponEtherTrafficIntervalEntry  3 }


gponEtherTrafficIntervalValidInd  OBJECT-TYPE
	SYNTAX 	Boolean
	ACCESS	read-only
	STATUS	mandatory
	DESCRIPTION 
		"Indicates whether or not this Interval contains
		 valid PM counts. 

		 As of FGU4.2, NOT SUPPORTED

		For ISAM 4.0.10 -> stays the same as latest FGU4.x  "
	::= { gponEtherTrafficIntervalEntry 4 }


gponEtherTrafficIntervalTxFrames  OBJECT-TYPE
	SYNTAX 	Counter
	ACCESS	read-only
	STATUS	mandatory
	DESCRIPTION 
		"A count of Transmitted Ethernet Frames.

		For ISAM 4.0.10 -> stays the same as latest FGU4.x "
	::= { gponEtherTrafficIntervalEntry 5 }


gponEtherTrafficIntervalRxFrames  OBJECT-TYPE
	SYNTAX 	Counter
	ACCESS	read-only
	STATUS	mandatory
	DESCRIPTION 
		"A count of Received Ethernet Frames.

		For ISAM 4.0.10 -> stays the same as latest FGU4.x "
	::= { gponEtherTrafficIntervalEntry 6 }


gponEtherTrafficIntervalTxBytes  OBJECT-TYPE
	SYNTAX 	Counter
	ACCESS	read-only
	STATUS	mandatory
	DESCRIPTION 
		"A count of Transmitted Ethernet Bytes.

		For ISAM 4.0.10 -> stays the same as latest FGU4.x

		 As of ISAM4.5, the plan is to effectively DEPRECATE this attribute.  Manager should instead use equivalent 
		 64-bit counter attribute gponEtherTrafficIntervalTxBytesCounter64. "
	::= { gponEtherTrafficIntervalEntry 7 }


gponEtherTrafficIntervalRxBytes  OBJECT-TYPE
	SYNTAX 	Counter
	ACCESS	read-only
	STATUS	mandatory
	DESCRIPTION 
		"A count of Received Ethernet Bytes.

		For ISAM 4.0.10 -> stays the same as latest FGU4.x

		 As of ISAM4.5, the plan is to effectively DEPRECATE this attribute.  Manager should instead use equivalent 
		 64-bit counter attribute gponEtherTrafficIntervalRxBytesCounter64. "
	::= { gponEtherTrafficIntervalEntry 8 }


gponEtherTrafficIntervalDroppedFramesUp  OBJECT-TYPE
	SYNTAX 	Counter
	ACCESS	read-only
	STATUS	mandatory
	DESCRIPTION 
		"A count of Dropped Frames Upstream.

		For ISAM 4.0.10 -> stays the same as latest FGU4.x "
	::= { gponEtherTrafficIntervalEntry 9 }


gponEtherTrafficIntervalDroppedBytesUp  OBJECT-TYPE
	SYNTAX 	Counter
	ACCESS	read-only
	STATUS	mandatory
	DESCRIPTION 
		"A count of Dropped Bytes Upstream.

		 As of FGU4.2, this is NOT SUPPORTED

		For ISAM 4.0.10 -> stays the same as latest FGU4.x "
	::= { gponEtherTrafficIntervalEntry 10 }


gponEtherTrafficIntervalDroppedFramesDown  OBJECT-TYPE
	SYNTAX 	Counter
	ACCESS	read-only
	STATUS	mandatory
	DESCRIPTION 
		"A count of Dropped Frames Downstream.

		For ISAM 4.0.10 -> stays the same as latest FGU4.x "
	::= { gponEtherTrafficIntervalEntry 11 }


gponEtherTrafficIntervalTxFramesMulticast  OBJECT-TYPE
	SYNTAX 	Counter
	ACCESS	read-only
	STATUS	mandatory
	DESCRIPTION 
		"A count of Transmitted Multicast Ethernet Frames.

		For ISAM 4.0.10 -> stays the same as latest FGU4.x "
	::= { gponEtherTrafficIntervalEntry 12 }


gponEtherTrafficIntervalRxFramesMulticast  OBJECT-TYPE
	SYNTAX 	Counter
	ACCESS	read-only
	STATUS	mandatory
	DESCRIPTION 
		"A count of Received Multicast Ethernet Frames.

		For ISAM 4.0.10 -> stays the same as latest FGU4.x "
	::= { gponEtherTrafficIntervalEntry 13 }


gponEtherTrafficIntervalRxDropEvents	  OBJECT-TYPE
	SYNTAX 	Counter
	ACCESS	read-only
	STATUS	mandatory
	DESCRIPTION 
		"The total number of events in which packets were dropped due to lack of
resources. This is not necessarily the number of packets dropped; it is the number of times this event was detected.

		 As of ISAM4.2 -> SUPPORTED. "
	::= { gponEtherTrafficIntervalEntry 14 }

	gponEtherTrafficIntervalRxFramesBroadcast	  OBJECT-TYPE
	SYNTAX 	Counter
	ACCESS	read-only
	STATUS	mandatory
	DESCRIPTION 
		"The total number of received good packets directed to the broadcast
address. This does not include multicast packets.

		 As of ISAM4.2 -> SUPPORTED. "
	::= { gponEtherTrafficIntervalEntry 15 }

	gponEtherTrafficIntervalRxCRCErrorFrames	  OBJECT-TYPE
	SYNTAX 	Counter
	ACCESS	read-only
	STATUS	mandatory
	DESCRIPTION 
		"The total number of packets received that had a length (excluding
framing bits, but including FCS octets) of between 64 and 1518 octets,
inclusive, but had either a bad frame check sequence (FCS) with an integral
number of octets (FCS error) or a bad FCS with a non-integral number of
octets (alignment error).

		 As of ISAM4.2 -> SUPPORTED. "
	::= { gponEtherTrafficIntervalEntry 16 }

	gponEtherTrafficIntervalRxUndersizeFrames	  OBJECT-TYPE
	SYNTAX 	Counter
	ACCESS	read-only
	STATUS	mandatory
	DESCRIPTION 
		"The total number of packets received that were less than 64 octets long
but were otherwise well formed (excluding framing bits, but including FCS
octets).

		 As of ISAM4.2 -> SUPPORTED. "
	::= { gponEtherTrafficIntervalEntry 17 }

	gponEtherTrafficIntervalRxOversizeFrames	  OBJECT-TYPE
	SYNTAX 	Counter
	ACCESS	read-only
	STATUS	mandatory
	DESCRIPTION 
		"The total number of packets received that were longer than 1518 octets
(excluding framing bits, but including FCS octets) and were otherwise well
formed.

		 As of ISAM4.2 -> SUPPORTED. "
	::= { gponEtherTrafficIntervalEntry 18 }

	gponEtherTrafficIntervalRx64octets	  OBJECT-TYPE
	SYNTAX 	Counter
	ACCESS	read-only
	STATUS	mandatory
	DESCRIPTION 
		"The total number of received packets (including bad packets) that were
64 octets long, excluding framing bits but including FCS.

		 As of ISAM4.2 -> SUPPORTED. "
	::= { gponEtherTrafficIntervalEntry 19 }

gponEtherTrafficIntervalRx65to127octets	  OBJECT-TYPE
	SYNTAX 	Counter
	ACCESS	read-only
	STATUS	mandatory
	DESCRIPTION 
		"The total number of received packets (including bad packets) that
were 65..127 octets long, excluding framing bits but including FCS.

		 As of ISAM4.2 -> SUPPORTED. "
::= { gponEtherTrafficIntervalEntry 20 }

gponEtherTrafficIntervalRx128to255octets	  OBJECT-TYPE
	SYNTAX 	Counter
	ACCESS	read-only
	STATUS	mandatory
	DESCRIPTION 
		"The total number of packets (including bad packets) received
that were 128..255 octets long, excluding framing bits but including FCS.

		 As of ISAM4.2 -> SUPPORTED. "
::= { gponEtherTrafficIntervalEntry 21 }

gponEtherTrafficIntervalRx256to511octets	  OBJECT-TYPE
	SYNTAX 	Counter
	ACCESS	read-only
	STATUS	mandatory
	DESCRIPTION 
"The total number of packets (including bad packets) received that were 256..511 octets long, excluding framing bits but including FCS.

		 As of ISAM4.2 -> SUPPORTED. "
::= { gponEtherTrafficIntervalEntry 22 }

gponEtherTrafficIntervalRx512to1023octets	  OBJECT-TYPE
	SYNTAX 	Counter
	ACCESS	read-only
	STATUS	mandatory
	DESCRIPTION 
		"The total number of packets (including bad packets) received
that were 512..1023 octets long, excluding framing bits but including FCS.

		 As of ISAM4.2 -> SUPPORTED. "
::= { gponEtherTrafficIntervalEntry 23 }

gponEtherTrafficIntervalRx1024to1518octets	  OBJECT-TYPE
	SYNTAX 	Counter
	ACCESS	read-only
	STATUS	mandatory
	DESCRIPTION 
		"The total number of packets (including bad packets) received
that were 1024..1518 octets long, excluding framing bits but including FCS.

		 As of ISAM4.2 -> SUPPORTED. "
::= { gponEtherTrafficIntervalEntry 24 }

gponEtherTrafficIntervalTxDropEvents	  OBJECT-TYPE
	SYNTAX 	Counter
	ACCESS	read-only
	STATUS	mandatory
	DESCRIPTION 
		" The total number of events in which packets were dropped due to lack of
resources. This is not necessarily the number of packets dropped; it is the number of times this event was detected

		 As of ISAM4.2 -> SUPPORTED.  "
::= { gponEtherTrafficIntervalEntry 25 }

	gponEtherTrafficIntervalTxFramesBroadcast	  OBJECT-TYPE
	SYNTAX 	Counter
	ACCESS	read-only
	STATUS	mandatory
	DESCRIPTION 
		" The total number of transmitted good packets directed to the broadcast
address. This does not include multicast packets

		 As of ISAM4.2 -> SUPPORTED. "
	::= { gponEtherTrafficIntervalEntry 26 }

	gponEtherTrafficIntervalTxCRCErrorFrames	  OBJECT-TYPE
	SYNTAX 	Counter
	ACCESS	read-only
	STATUS	mandatory
	DESCRIPTION 
		" The total number of packets transmitted that had a length (excluding
framing bits, but including FCS octets) of between 64 and 1518 octets,
inclusive, but had either a bad frame check sequence (FCS) with an integral
number of octets (FCS error) or a bad FCS with a non-integral number of
octets (alignment error).

		 As of ISAM4.2 -> SUPPORTED.  "
	::= { gponEtherTrafficIntervalEntry 27 }

	gponEtherTrafficIntervalTxUndersizeFrames	  OBJECT-TYPE
	SYNTAX 	Counter
	ACCESS	read-only
	STATUS	mandatory
	DESCRIPTION 
		" The total number of packets transmitted that were less than 64 octets long
but were otherwise well formed (excluding framing bits, but including FCS
octets).

		 As of ISAM4.2 -> SUPPORTED.  "
	::= { gponEtherTrafficIntervalEntry 28 }

	gponEtherTrafficIntervalTxOversizeFrames	  OBJECT-TYPE
	SYNTAX 	Counter
	ACCESS	read-only
	STATUS	mandatory
	DESCRIPTION 
		" The total number of packets transmitted that were longer than 1518 octets
(excluding framing bits, but including FCS octets) and were otherwise well
formed

		 As of ISAM4.2 -> SUPPORTED.  "
	::= { gponEtherTrafficIntervalEntry 29 }

	gponEtherTrafficIntervalTx64octets	  OBJECT-TYPE
	SYNTAX 	Counter
	ACCESS	read-only
	STATUS	mandatory
	DESCRIPTION 
		"A The total number of transmitted packets (including bad packets) that were
64 octets long, excluding framing bits but including FCS

		 As of ISAM4.2 -> SUPPORTED.  "
	::= { gponEtherTrafficIntervalEntry 30 }

gponEtherTrafficIntervalTx65to127octets	  OBJECT-TYPE
	SYNTAX 	Counter
	ACCESS	read-only
	STATUS	mandatory
	DESCRIPTION 
		" The total number of transmitted packets (including bad packets) that
were 65..127 octets long, excluding framing bits but including FCS.

		 As of ISAM4.2 -> SUPPORTED. "
	::= { gponEtherTrafficIntervalEntry 31 }

gponEtherTrafficIntervalTx128to255octets	  OBJECT-TYPE
	SYNTAX 	Counter
	ACCESS	read-only
	STATUS	mandatory
	DESCRIPTION 
		" The total number of packets (including bad packets) transmitted
that were 128..255 octets long, excluding framing bits but including FCS.

		 As of ISAM4.2 -> SUPPORTED.  "
::= { gponEtherTrafficIntervalEntry 32 }

gponEtherTrafficIntervalTx256to511octets	  OBJECT-TYPE
	SYNTAX 	Counter
	ACCESS	read-only
	STATUS	mandatory
	DESCRIPTION 
" The total number of packets (including bad packets) transmitted that were 256..511 octets long, excluding framing bits but including FCS.

		 As of ISAM4.2 -> SUPPORTED. "
::= { gponEtherTrafficIntervalEntry 33 }

gponEtherTrafficIntervalTx512to1023octets	  OBJECT-TYPE
	SYNTAX 	Counter
	ACCESS	read-only
	STATUS	mandatory
	DESCRIPTION 
		" The total number of packets (including bad packets) transmitted
that were 512..1023 octets long, excluding framing bits but including FCS.

		 As of ISAM4.2 -> SUPPORTED. "
::= { gponEtherTrafficIntervalEntry 34 }

gponEtherTrafficIntervalTx1024to1518octets	  OBJECT-TYPE
	SYNTAX 	Counter
	ACCESS	read-only
	STATUS	mandatory
	DESCRIPTION 
		" The total number of packets (including bad packets) transmitted
that were 1024..1518 octets long, excluding framing bits but including FCS

		 As of ISAM4.2 -> SUPPORTED.  "
::= { gponEtherTrafficIntervalEntry 35 }

gponEtherTrafficIntervalRxPackets	  OBJECT-TYPE
	SYNTAX 	Counter
	ACCESS	read-only
	STATUS	mandatory
	DESCRIPTION 
		"The total number of upstream packets received, including bad packets,
		broadcast packets and multicast packets. 

		 As of ISAM4.2 -> SUPPORTED.


		 As of ISAM4.5, the plan is to effectively DEPRECATE this attribute.  Manager should instead use equivalent 
		 64-bit counter attribute gponEtherTrafficIntervalRxPacketsCounter64. "
	::= { gponEtherTrafficIntervalEntry 36 }

gponEtherTrafficIntervalTxPackets	  OBJECT-TYPE
	SYNTAX 	Counter
	ACCESS	read-only
	STATUS	mandatory
	DESCRIPTION 
		"The total number of downstream packets transmitted, including bad packets,
		broadcast packets and multicast packets. 

		 As of ISAM4.2 -> SUPPORTED.


		 As of ISAM4.5, the plan is to effectively DEPRECATE this attribute.  Manager should instead use equivalent 
		 64-bit counter attribute gponEtherTrafficIntervalTxPacketsCounter64. "
	::= { gponEtherTrafficIntervalEntry 37 }

gponEtherTrafficIntervalTxBytesCounter64  OBJECT-TYPE
	SYNTAX 	OCTET STRING (SIZE(8))
	ACCESS	read-only
	STATUS	mandatory
	DESCRIPTION 
		" This represents the equivalent of a 64-bit count of Transmitted Ethernet Bytes.

		 Introduced for readiness in ISAM 4.5 MIB.  Plan to support 32-bit counts in this attribute with ISAM4.5
		 with target implementation of 64-bit counts in ISAM4.5.01. "
	::= { gponEtherTrafficIntervalEntry 38 }


gponEtherTrafficIntervalRxBytesCounter64  OBJECT-TYPE
	SYNTAX 	OCTET STRING (SIZE(8))
	ACCESS	read-only
	STATUS	mandatory
	DESCRIPTION 
		" This represents the equivalent of a 64-bit count of Received Ethernet Bytes.

		 Introduced for readiness in ISAM 4.5 MIB.  Plan to support 32-bit counts in this attribute with ISAM4.5
		 with target implementation of 64-bit counts in ISAM4.5.01. "
	::= { gponEtherTrafficIntervalEntry 39 }

gponEtherTrafficIntervalTxPacketsCounter64  OBJECT-TYPE
	SYNTAX 	OCTET STRING (SIZE(8))
	ACCESS	read-only
	STATUS	mandatory
	DESCRIPTION 
		" This represents the equivalent of a 64-bit count of downstream Ethernet packets similar
		   to gponEtherTrafficIntervalTxPackets.

		 Introduced for readiness in ISAM 4.5 MIB.  Plan to support 32-bit counts in this attribute with ISAM4.5
		 with target implementation of 64-bit counts in ISAM4.5.01. "
	::= { gponEtherTrafficIntervalEntry 40 }


gponEtherTrafficIntervalRxPacketsCounter64  OBJECT-TYPE
	SYNTAX 	OCTET STRING (SIZE(8))
	ACCESS	read-only
	STATUS	mandatory
	DESCRIPTION 
		" This represents the equivalent of a 64-bit count of upstream Ethernet packets similar
		   to gponEtherTrafficIntervalRxPackets.

		 Introduced for readiness in ISAM 4.5 MIB.  Plan to support 32-bit counts in this attribute with ISAM4.5
		 with target implementation of 64-bit counts in ISAM4.5.01. "
	::= { gponEtherTrafficIntervalEntry 41 }


-- *********************************************
--
-- GPON ETHERNET TRAFFIC PERFORMANCE MONITOR TCA THRESHOLD TABLE
--
-- This is a new table beginning with FGU4.2.
-- This TCA Threshold table contains Ethernet traffic threshold settings
-- for various PMs at an ONT's data interface during the current 15 minute interval 
-- of operation.  The physical data interface could be any of the following:
-- Ethernet, VDSL or MoCA.
--
-- An instance of this table is auto-created/deleted in accordance with the 
-- 'Ethernet Traffic PM Collect Indicator' setting of the particular data UNI.
--
-- As of  ISAM4.0.10, this table is being re-used. 
-- Noted which attributes are relevant for ISAM4.0.10
--
--	For GPON - SUPPORTED as of ISAM4.2
--	For XG-PON1 - SUPPORTED as of ISAM4.6.02
--	For NG-PON2 - SUPPORTED as of ISAM5.2 (For Ethernet UNI only)
-- 
--
-- 
-- *********************************************


gponEtherTrafficTCAThresholdTable  OBJECT-TYPE
	SYNTAX SEQUENCE OF GponEtherTrafficTCAThresholdEntry
	ACCESS	not-accessible
	STATUS	mandatory
	::= { gponEthernetGroup 3 }


gponEtherTrafficTCAThresholdEntry  OBJECT-TYPE
	SYNTAX 	GponEtherTrafficTCAThresholdEntry
	ACCESS	not-accessible
	STATUS	mandatory
	DESCRIPTION 
		"An entry in the Gpon Ethernet Traffic TCAThreshold 
		 Table. "
	INDEX	{ gponEtherTrafficTCAThresholdOntIndex,
		  gponEtherTrafficTCAThresholdSpIndex  }
	::= { gponEtherTrafficTCAThresholdTable 1 }

GponEtherTrafficTCAThresholdEntry ::= SEQUENCE {
	gponEtherTrafficTCAThresholdOntIndex			IfIndex,
	gponEtherTrafficTCAThresholdSpIndex			SpIndex,
	gponEtherTrafficTCAEnable					INTEGER,
	gponEtherTrafficTCAThresholdDroppedFramesUp		Threshold,
	gponEtherTrafficTCAThresholdDroppedBytesUp		Threshold,
	gponEtherTrafficTCAThresholdDroppedFramesDown		Threshold
}


gponEtherTrafficTCAThresholdOntIndex  OBJECT-TYPE
	SYNTAX 	IfIndex
	ACCESS	read-only
	STATUS	mandatory
	DESCRIPTION 
		"Each row is indexed by the ifIndex of the ONT.

		For ISAM 4.0.10 -> stays the same as latest FGU4.x  "
	::= { gponEtherTrafficTCAThresholdEntry 1 }

gponEtherTrafficTCAThresholdSpIndex  OBJECT-TYPE
	SYNTAX 	SpIndex
	ACCESS	read-only
	STATUS	mandatory
	DESCRIPTION 
		"Each row is also indexed by the slot/port of the physical UNI.

		For ISAM 4.0.10 -> stays the same as latest FGU4.x  "
	::= { gponEtherTrafficTCAThresholdEntry 2 }


gponEtherTrafficTCAEnable  OBJECT-TYPE
	SYNTAX 	INTEGER
	ACCESS	read-write
	STATUS	mandatory
	DESCRIPTION 
		"Allows the manager to enable/disable the reporting of
		 Ethernet traffic TCAs for this physical UNI. 

	
		  1 = TCA's enabled
		  2 = TCA's disabled

		 Default = 2 = disabled.

		For ISAM 4.0.10 -> stays the same as latest FGU4.x "
	::= { gponEtherTrafficTCAThresholdEntry 3 }


gponEtherTrafficTCAThresholdDroppedFramesUp  OBJECT-TYPE
	SYNTAX 	Threshold
	ACCESS	read-write
	STATUS	mandatory
	DESCRIPTION 
		"TCA setting for Dropped Frames (upstream).
		 A value of 4294967295 means that this threshold is disabled.

		 Default = 4294967295 

		For ISAM 4.0.10 -> stays the same as latest FGU4.x "

	::= { gponEtherTrafficTCAThresholdEntry 4 }


gponEtherTrafficTCAThresholdDroppedBytesUp  OBJECT-TYPE
	SYNTAX 	Threshold
	ACCESS	read-write
	STATUS	mandatory
	DESCRIPTION 
		"TCA setting for Dropped Bytes (upstream).
		 A value of 4294967295 means that this threshold is disabled.

		 Default = 4294967295 

		 As of FGU4.2, this is NOT SUPPORTED

		For ISAM 4.0.10 -> stays the same as latest FGU4.x "

	::= { gponEtherTrafficTCAThresholdEntry 5 }


gponEtherTrafficTCAThresholdDroppedFramesDown  OBJECT-TYPE
	SYNTAX 	Threshold
	ACCESS	read-write
	STATUS	mandatory
	DESCRIPTION 
		"TCA setting for Dropped Frames (downstream).
		 A value of 4294967295 means that this threshold is disabled.

		 Default = 4294967295

		For ISAM 4.0.10 -> stays the same as latest FGU4.x  "

	::= { gponEtherTrafficTCAThresholdEntry 6 }


-- *********************************************
--
-- GPON UNI GEM PM COLLECT ENABLE TABLE
--
-- This is a new table beginning with ISAM4.0.10.  Rows
-- are automatically created by agent when a corresponding
-- UNI port is auto-created.
--
-- Prior to ISAM5.0, this table was only SUPPORTED for following:
-- Ethernet and XDSL UNI types
--
-- As of ISAM5.0, this table is SUPPORTED for following:
-- Ethernet, XDSL,HPNA, MOCA and VEIP UNI types.
--
--	For GPON - SUPPORTED as of ISAM4.0.10
--	For XG-PON1 - SUPPORTED as of ISAM4.6.02
--	For NG-PON2 - SUPPORTED as of ISAM5.2 (For Ethernet UNI only)
--   
--
--
-- *********************************************

gponUniGemPmTable  OBJECT-TYPE
	SYNTAX SEQUENCE OF GponUniGemPmEntry
	ACCESS	not-accessible
	STATUS	mandatory
	::= { gponGenericUniGroup 1 }

gponUniGemPmEntry  OBJECT-TYPE
	SYNTAX 	GponUniGemPmEntry
	ACCESS	not-accessible
	STATUS	mandatory
	INDEX	{ gponUniGemPmOntIndex,
		  gponUniGemPmSpIndex }
	::= { gponUniGemPmTable 1 }

GponUniGemPmEntry ::= SEQUENCE {
	gponUniGemPmOntIndex				IfIndex,
	gponUniGemPmSpIndex				SpIndex,
	gponUniGemPmCollectInd				INTEGER,
	gponUniGemPmNumPMIntervals			INTEGER
}

gponUniGemPmOntIndex  OBJECT-TYPE
	SYNTAX 	IfIndex
	ACCESS	read-only
	STATUS	mandatory
	DESCRIPTION 
		"Each row is indexed by the ifIndex of the ONT.   "
	::= { gponUniGemPmEntry 1 }

gponUniGemPmSpIndex  OBJECT-TYPE
	SYNTAX 	SpIndex
	ACCESS	read-only
	STATUS	mandatory
	DESCRIPTION 
		"Each row is also indexed by slot/port of the UNI..  "
	::= { gponUniGemPmEntry 2 }

gponUniGemPmCollectInd  OBJECT-TYPE
	SYNTAX 	INTEGER
	ACCESS	read-write
	STATUS	mandatory
	DESCRIPTION 
		" This indicates whether GEM Port Performance Monitors
		   should be collected for this UNI (accounts for
		   both ONT-side and OLT-side).
	
		  1 = PM collection enabled
		  2 = PM collection disabled

		 Default = 2 = disabled.   "
	::= { gponUniGemPmEntry  3 }

gponUniGemPmNumPMIntervals  OBJECT-TYPE
	SYNTAX 	INTEGER
	ACCESS	read-only
	STATUS	mandatory
	DESCRIPTION 
		" Indicates the number of rows currently present
		  in the gponUniGemIntervalTables (both
		  ONT-side and OLT-side).  This
		  is for convenience of the EMS, so that it can
		  quickly determine how many rows should be 
		  uploaded.   "
	::= { gponUniGemPmEntry  4 }


-- *********************************************
--
-- UNI ONT-SIDE GEM PERFORMANCE MONITOR CURRENT INTERVAL TABLE
--
-- This is a new table beginning with ISAM4.0.10.
-- This current interval table contains various statistics collected for 
-- ONT GEM ports (ONT-side) during the current 15 minute interval 
-- of operation.  
--
-- An instance of this table is auto-created/deleted in accordance with the 
-- 'PM Collect Indicator' setting (for this UNI) in the UNI Gem PM Table.
--
--
-- For GETs of table attributes, the OLT must go directly to the ONT (via OMCI)
-- in order to acquire fresh current counts. 
--
-- NOTE: The ONT itself doesn't have knowledge about the individual GEM
-- ports associated with a UNI - this is known only by the OLT.  But 
-- the ONT keeps the GEM PM counts on a GEM port basis.  Therefore, the
-- OLT must collect and sum the individual GEM port PMs for each of the 
-- GEM ports associated with the UNI.  The GEM port PM summations
-- are recorded in this table.
--
-- Prior to ISAM5.0, this table was only SUPPORTED for following:
-- Ethernet and XDSL UNI types
--
-- As of ISAM5.0, this table is SUPPORTED for following:
-- Ethernet, XDSL,HPNA, MOCA and VEIP UNI types.
--
--	For GPON - SUPPORTED as of ISAM4.0.10
--	For XG-PON1 - SUPPORTED as of ISAM4.6.02
--	For NG-PON2 - SUPPORTED as of ISAM5.2 (For Ethernet UNI only)
--  
--
--
-- 
-- *********************************************


gponUniOntsideGemCurrentIntervalTable  OBJECT-TYPE
	SYNTAX SEQUENCE OF GponUniOntsideGemCurrentIntervalEntry
	ACCESS	not-accessible
	STATUS	mandatory
	::= { gponGenericUniGroup 2 }


gponUniOntsideGemCurrentIntervalEntry  OBJECT-TYPE
	SYNTAX 	GponUniOntsideGemCurrentIntervalEntry
	ACCESS	not-accessible
	STATUS	mandatory
	DESCRIPTION 
		"An entry in the GPON UNI GEM PM
		 CurrentInterval Table. "
	INDEX	{ gponUniOntsideGemCurrentIntervalOntIndex, 
		   gponUniOntsideGemCurrentIntervalSpIndex }
	::= { gponUniOntsideGemCurrentIntervalTable 1 }

GponUniOntsideGemCurrentIntervalEntry ::= SEQUENCE {
	gponUniOntsideGemCurrentIntervalOntIndex			IfIndex,
	gponUniOntsideGemCurrentIntervalSpIndex			SpIndex,
	gponUniOntsideGemCurrentIntervalValidInd			Boolean,
	gponUniOntsideGemCurrentIntervalLostFragsDown			Counter,
	gponUniOntsideGemCurrentIntervalLostFragsUp			Counter,
	gponUniOntsideGemCurrentIntervalReceiveFrags		Counter,
	gponUniOntsideGemCurrentIntervalReceiveBlocks		Counter,
	gponUniOntsideGemCurrentIntervalTransmitBlocks		Counter,
	gponUniOntsideGemCurrentIntervalTransmitFrags		Counter
}


gponUniOntsideGemCurrentIntervalOntIndex  OBJECT-TYPE
	SYNTAX 	IfIndex
	ACCESS	read-only
	STATUS	mandatory
	DESCRIPTION 
		"This index is the ifIndex of the ONT.  "
	::= { gponUniOntsideGemCurrentIntervalEntry 1 }

gponUniOntsideGemCurrentIntervalSpIndex  OBJECT-TYPE
	SYNTAX 	SpIndex
	ACCESS	read-only
	STATUS	mandatory
	DESCRIPTION 
		"This index is the slot/port of the physical UNI. "
	::= { gponUniOntsideGemCurrentIntervalEntry 2 }


gponUniOntsideGemCurrentIntervalValidInd  OBJECT-TYPE
	SYNTAX 	Boolean
	ACCESS	read-only
	STATUS	mandatory
	DESCRIPTION 
		"Indicates whether or not this CurrentInterval contains
		 valid PM counts.

		 As of ISAM4.0.10, this is NOT SUPPORTED  "
	::= { gponUniOntsideGemCurrentIntervalEntry 3 }


gponUniOntsideGemCurrentIntervalLostFragsDown  OBJECT-TYPE
	SYNTAX 	Counter
	ACCESS	read-only
	STATUS	mandatory
	DESCRIPTION 
		"A count of Lost GEM Fragments (downstream).  "
	::= { gponUniOntsideGemCurrentIntervalEntry 4 }

gponUniOntsideGemCurrentIntervalLostFragsUp  OBJECT-TYPE
	SYNTAX 	Counter
	ACCESS	read-only
	STATUS	mandatory
	DESCRIPTION 
		"A count of Lost GEM Fragments (upstream). "
	::= { gponUniOntsideGemCurrentIntervalEntry 5 }

gponUniOntsideGemCurrentIntervalReceiveFrags  OBJECT-TYPE
	SYNTAX 	Counter
	ACCESS	read-only
	STATUS	mandatory
	DESCRIPTION 
		"A count of Received GEM Fragments. "
	::= { gponUniOntsideGemCurrentIntervalEntry 6 }


gponUniOntsideGemCurrentIntervalReceiveBlocks  OBJECT-TYPE
	SYNTAX 	Counter
	ACCESS	read-only
	STATUS	mandatory
	DESCRIPTION 
		"A count of Received GEM Blocks. "
	::= { gponUniOntsideGemCurrentIntervalEntry 7 }


gponUniOntsideGemCurrentIntervalTransmitBlocks  OBJECT-TYPE
	SYNTAX 	Counter
	ACCESS	read-only
	STATUS	mandatory
	DESCRIPTION 
		"A count of Transmitted GEM Blocks. "
	::= { gponUniOntsideGemCurrentIntervalEntry 8 }


gponUniOntsideGemCurrentIntervalTransmitFrags  OBJECT-TYPE
	SYNTAX 	Counter
	ACCESS	read-only
	STATUS	mandatory
	DESCRIPTION 
		"A count of Transmitted GEM Fragments. "
	::= { gponUniOntsideGemCurrentIntervalEntry 9 }

-- *********************************************
--
-- UNI ONT-SIDE GEM PERFORMANCE MONITOR INTERVAL TABLE
--
-- This is a new table beginning with ISAM4.0.10.
-- This interval table contains various GEM port statistics collected
-- at an ONT over the previous 8 hours of operation.  The past 8 hours are
-- broken into 32 completed 15 minute intervals.  Each row in this table
-- represents one such interval associated with a service flow.
--
-- An instance of this table is auto-created/deleted in accordance with the 
-- 'PM Collect Indicator' setting (for this UNI) in the UNI Gem PM Table.
--
--
-- NOTE: The ONT itself doesn't have knowledge about the individual GEM
-- ports associated with a UNI - this is known only by the OLT.  But 
-- the ONT keeps the GEM PM counts on a GEM port basis.  Therefore, the
-- OLT must collect and sum the individual GEM port PMs for each of the 
-- GEM ports associated with the UNI.  The GEM port PM summations
-- are recorded in this table.
--
-- Prior to ISAM5.0, this table was only SUPPORTED for following:
-- Ethernet and XDSL UNI types
--
-- As of ISAM5.0, this table is SUPPORTED for following:
-- Ethernet, XDSL,HPNA, MOCA and VEIP UNI types. 
--
--	For GPON - SUPPORTED as of ISAM4.0.10
--	For XG-PON1 - SUPPORTED as of ISAM4.6.02
--	For NG-PON2 - SUPPORTED as of ISAM5.2 (For Ethernet UNI only)
-- 
--
--
-- 
-- *********************************************


gponUniOntsideGemIntervalTable  OBJECT-TYPE
	SYNTAX SEQUENCE OF GponUniOntsideGemIntervalEntry
	ACCESS	not-accessible
	STATUS	mandatory
	::= { gponGenericUniGroup 3 }


gponUniOntsideGemIntervalEntry  OBJECT-TYPE
	SYNTAX 	GponUniOntsideGemIntervalEntry
	ACCESS	not-accessible
	STATUS	mandatory
	DESCRIPTION 
		"An entry in the GPON UNI GEM PM
		 Interval Table. "
	INDEX	{ gponUniOntsideGemIntervalOntIndex, 
		   gponUniOntsideGemIntervalSpIndex,
		  gponUniOntsideGemIntervalNumber }
	::= { gponUniOntsideGemIntervalTable 1 }

GponUniOntsideGemIntervalEntry ::= SEQUENCE {
	gponUniOntsideGemIntervalOntIndex			IfIndex,
	gponUniOntsideGemIntervalSpIndex			SpIndex,
	gponUniOntsideGemIntervalNumber			INTEGER,
	gponUniOntsideGemIntervalValidInd			Boolean,
	gponUniOntsideGemIntervalLostFragsDown			Counter,
	gponUniOntsideGemIntervalLostFragsUp			Counter,
	gponUniOntsideGemIntervalReceiveFrags		Counter,
	gponUniOntsideGemIntervalReceiveBlocks		Counter,
	gponUniOntsideGemIntervalTransmitBlocks		Counter,
	gponUniOntsideGemIntervalTransmitFrags		Counter
}


gponUniOntsideGemIntervalOntIndex  OBJECT-TYPE
	SYNTAX 	IfIndex
	ACCESS	read-only
	STATUS	mandatory
	DESCRIPTION 
		"This index is the ifIndex of the ONT.  "
	::= { gponUniOntsideGemIntervalEntry 1 }

gponUniOntsideGemIntervalSpIndex  OBJECT-TYPE
	SYNTAX 	SpIndex
	ACCESS	read-only
	STATUS	mandatory
	DESCRIPTION 
		"This index is the slot/port of the physical UNI. "
	::= { gponUniOntsideGemIntervalEntry 2 }

gponUniOntsideGemIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.  "
	::= { gponUniOntsideGemIntervalEntry 3 }

gponUniOntsideGemIntervalValidInd  OBJECT-TYPE
	SYNTAX 	Boolean
	ACCESS	read-only
	STATUS	mandatory
	DESCRIPTION 
		"Indicates whether or not this interval contains
		 valid PM counts.  

		 As of ISAM4.0.10, NOT SUPPORTED "
	::= { gponUniOntsideGemIntervalEntry 4 }


gponUniOntsideGemIntervalLostFragsDown  OBJECT-TYPE
	SYNTAX 	Counter
	ACCESS	read-only
	STATUS	mandatory
	DESCRIPTION 
		"A count of Lost GEM Fragments (downstream). "
	::= { gponUniOntsideGemIntervalEntry 5 }

gponUniOntsideGemIntervalLostFragsUp  OBJECT-TYPE
	SYNTAX 	Counter
	ACCESS	read-only
	STATUS	mandatory
	DESCRIPTION 
		"A count of Lost GEM Fragments (upstream). "
	::= { gponUniOntsideGemIntervalEntry 6 }

gponUniOntsideGemIntervalReceiveFrags  OBJECT-TYPE
	SYNTAX 	Counter
	ACCESS	read-only
	STATUS	mandatory
	DESCRIPTION 
		"A count of Received GEM Fragments. "
	::= { gponUniOntsideGemIntervalEntry 7 }


gponUniOntsideGemIntervalReceiveBlocks  OBJECT-TYPE
	SYNTAX 	Counter
	ACCESS	read-only
	STATUS	mandatory
	DESCRIPTION 
		"A count of Received GEM Blocks. "
	::= { gponUniOntsideGemIntervalEntry 8 }


gponUniOntsideGemIntervalTransmitBlocks  OBJECT-TYPE
	SYNTAX 	Counter
	ACCESS	read-only
	STATUS	mandatory
	DESCRIPTION 
		"A count of Transmitted GEM Blocks. "
	::= { gponUniOntsideGemIntervalEntry 9 }


gponUniOntsideGemIntervalTransmitFrags  OBJECT-TYPE
	SYNTAX 	Counter
	ACCESS	read-only
	STATUS	mandatory
	DESCRIPTION 
		"A count of Transmitted GEM Fragments. "
	::= { gponUniOntsideGemIntervalEntry 10 }


-- *********************************************
--
-- UNI OLT-SIDE GEM PERFORMANCE MONITOR CURRENT INTERVAL TABLE
--
-- This is a new table beginning with ISAM4.0.10.
-- This current interval table contains various statistics collected for 
-- ONT GEM ports (OLT-side) during the current 15 minute interval 
-- of operation.  
--
-- An instance of this table is auto-created/deleted in accordance with the 
-- 'PM Collect Indicator' setting (for this UNI) in the UNI Gem PM Table.
--
--
-- NOTE:  The OLT must collect and sum the individual GEM port PMs for each of the 
-- GEM ports associated with the UNI.  The GEM port PM summations
-- are recorded in this table.
--
-- Prior to ISAM5.0, this table was only SUPPORTED for following:
-- Ethernet and XDSL UNI types
--
-- As of ISAM5.0, this table is SUPPORTED for following:
-- Ethernet, XDSL,HPNA, MOCA and VEIP UNI types.
--
--	For GPON - SUPPORTED as of ISAM4.0.10
--	For XG-PON1 - SUPPORTED as of ISAM4.6.02
--	For NG-PON2 - SUPPORTED as of ISAM5.2 (For Ethernet UNI only)
--  
--
--
-- 
-- *********************************************


gponUniOltsideGemCurrentIntervalTable  OBJECT-TYPE
	SYNTAX SEQUENCE OF GponUniOltsideGemCurrentIntervalEntry
	ACCESS	not-accessible
	STATUS	mandatory
	::= { gponGenericUniGroup 4 }


gponUniOltsideGemCurrentIntervalEntry  OBJECT-TYPE
	SYNTAX 	GponUniOltsideGemCurrentIntervalEntry
	ACCESS	not-accessible
	STATUS	mandatory
	DESCRIPTION 
		"An entry in the GPON UNI GEM PM
		 CurrentInterval Table. "
	INDEX	{ gponUniOltsideGemCurrentIntervalOntIndex, 
		   gponUniOltsideGemCurrentIntervalSpIndex }
	::= { gponUniOltsideGemCurrentIntervalTable 1 }

GponUniOltsideGemCurrentIntervalEntry ::= SEQUENCE {
	gponUniOltsideGemCurrentIntervalOntIndex			IfIndex,
	gponUniOltsideGemCurrentIntervalSpIndex			SpIndex,
	gponUniOltsideGemCurrentIntervalValidInd			Boolean,
	gponUniOltsideGemCurrentIntervalLostFragsDown			Counter,
	gponUniOltsideGemCurrentIntervalLostFragsUp			Counter,
	gponUniOltsideGemCurrentIntervalReceiveFrags		Counter,
	gponUniOltsideGemCurrentIntervalReceiveBlocks		Counter,
	gponUniOltsideGemCurrentIntervalTransmitBlocks		Counter,
	gponUniOltsideGemCurrentIntervalTransmitFrags		Counter
}


gponUniOltsideGemCurrentIntervalOntIndex  OBJECT-TYPE
	SYNTAX 	IfIndex
	ACCESS	read-only
	STATUS	mandatory
	DESCRIPTION 
		"This index is the ifIndex of the ONT.  "
	::= { gponUniOltsideGemCurrentIntervalEntry 1 }

gponUniOltsideGemCurrentIntervalSpIndex  OBJECT-TYPE
	SYNTAX 	SpIndex
	ACCESS	read-only
	STATUS	mandatory
	DESCRIPTION 
		"This index is the slot/port of the physical UNI. "
	::= { gponUniOltsideGemCurrentIntervalEntry 2 }


gponUniOltsideGemCurrentIntervalValidInd  OBJECT-TYPE
	SYNTAX 	Boolean
	ACCESS	read-only
	STATUS	mandatory
	DESCRIPTION 
		"Indicates whether or not this CurrentInterval contains
		 valid PM counts.

		 As of ISAM4.0.10, NOT SUPPORTED  "
	::= { gponUniOltsideGemCurrentIntervalEntry 3 }


gponUniOltsideGemCurrentIntervalLostFragsDown  OBJECT-TYPE
	SYNTAX 	Counter
	ACCESS	read-only
	STATUS	mandatory
	DESCRIPTION 
		"A count of Lost GEM Fragments (downstream).

		 As of ISAM4.0.10, NOT SUPPORTED "
	::= { gponUniOltsideGemCurrentIntervalEntry 4 }

gponUniOltsideGemCurrentIntervalLostFragsUp  OBJECT-TYPE
	SYNTAX 	Counter
	ACCESS	read-only
	STATUS	mandatory
	DESCRIPTION 
		"A count of Lost GEM Fragments (upstream). "
	::= { gponUniOltsideGemCurrentIntervalEntry 5 }

gponUniOltsideGemCurrentIntervalReceiveFrags  OBJECT-TYPE
	SYNTAX 	Counter
	ACCESS	read-only
	STATUS	mandatory
	DESCRIPTION 
		"A count of Received GEM Fragments. "
	::= { gponUniOltsideGemCurrentIntervalEntry 6 }


gponUniOltsideGemCurrentIntervalReceiveBlocks  OBJECT-TYPE
	SYNTAX 	Counter
	ACCESS	read-only
	STATUS	mandatory
	DESCRIPTION 
		"A count of Received GEM Blocks. "
	::= { gponUniOltsideGemCurrentIntervalEntry 7 }


gponUniOltsideGemCurrentIntervalTransmitBlocks  OBJECT-TYPE
	SYNTAX 	Counter
	ACCESS	read-only
	STATUS	mandatory
	DESCRIPTION 
		"A count of Transmitted GEM Blocks. "
	::= { gponUniOltsideGemCurrentIntervalEntry 8 }


gponUniOltsideGemCurrentIntervalTransmitFrags  OBJECT-TYPE
	SYNTAX 	Counter
	ACCESS	read-only
	STATUS	mandatory
	DESCRIPTION 
		"A count of Transmitted GEM Fragments. "
	::= { gponUniOltsideGemCurrentIntervalEntry 9 }

-- *********************************************
--
-- UNI OLT-SIDE GEM PERFORMANCE MONITOR INTERVAL TABLE
--
-- This is a new table beginning with ISAM4.0.10.
-- This interval table contains various GEM port statistics collected
-- for a Service Flow (OLT-side) over the previous 8 hours of operation.  The past 8 hours are
-- broken into 32 completed 15 minute intervals.  Each row in this table
-- represents one such interval associated with a service flow.
--
-- An instance of this table is auto-created/deleted in accordance with the 
-- 'PM Collect Indicator' setting (for this UNI) in the UNI Gem PM Table.
--
--
-- NOTE: The OLT must collect and sum the individual GEM port PMs for each of the 
-- GEM ports associated with the UNI.  The GEM port PM summations
-- are recorded in this table.
--
-- Prior to ISAM5.0, this table was only SUPPORTED for following:
-- Ethernet and XDSL UNI types
--
-- As of ISAM5.0, this table is SUPPORTED for following:
-- Ethernet, XDSL,HPNA, MOCA and VEIP UNI types.
--
--	For GPON - SUPPORTED as of ISAM4.0.10
--	For XG-PON1 - SUPPORTED as of ISAM4.6.02
--	For NG-PON2 - SUPPORTED as of ISAM5.2 (For Ethernet UNI only)
--  
--
--
-- 
-- *********************************************


gponUniOltsideGemIntervalTable  OBJECT-TYPE
	SYNTAX SEQUENCE OF GponUniOltsideGemIntervalEntry
	ACCESS	not-accessible
	STATUS	mandatory
	::= { gponGenericUniGroup 5 }


gponUniOltsideGemIntervalEntry  OBJECT-TYPE
	SYNTAX 	GponUniOltsideGemIntervalEntry
	ACCESS	not-accessible
	STATUS	mandatory
	DESCRIPTION 
		"An entry in the GPON UNI GEM PM
		 Interval Table. "
	INDEX	{ gponUniOltsideGemIntervalOntIndex, 
		   gponUniOltsideGemIntervalSpIndex,
		  gponUniOltsideGemIntervalNumber }
	::= { gponUniOltsideGemIntervalTable 1 }

GponUniOltsideGemIntervalEntry ::= SEQUENCE {
	gponUniOltsideGemIntervalOntIndex			IfIndex,
	gponUniOltsideGemIntervalSpIndex			SpIndex,
	gponUniOltsideGemIntervalNumber			INTEGER,
	gponUniOltsideGemIntervalValidInd			Boolean,
	gponUniOltsideGemIntervalLostFragsDown			Counter,
	gponUniOltsideGemIntervalLostFragsUp			Counter,
	gponUniOltsideGemIntervalReceiveFrags		Counter,
	gponUniOltsideGemIntervalReceiveBlocks		Counter,
	gponUniOltsideGemIntervalTransmitBlocks		Counter,
	gponUniOltsideGemIntervalTransmitFrags		Counter
}


gponUniOltsideGemIntervalOntIndex  OBJECT-TYPE
	SYNTAX 	IfIndex
	ACCESS	read-only
	STATUS	mandatory
	DESCRIPTION 
		"This index is the ifIndex of the ONT.  "
	::= { gponUniOltsideGemIntervalEntry 1 }

gponUniOltsideGemIntervalSpIndex  OBJECT-TYPE
	SYNTAX 	SpIndex
	ACCESS	read-only
	STATUS	mandatory
	DESCRIPTION 
		"This index is the slot/port of the physical UNI. "
	::= { gponUniOltsideGemIntervalEntry 2 }

gponUniOltsideGemIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.  "
	::= { gponUniOltsideGemIntervalEntry 3 }

gponUniOltsideGemIntervalValidInd  OBJECT-TYPE
	SYNTAX 	Boolean
	ACCESS	read-only
	STATUS	mandatory
	DESCRIPTION 
		"Indicates whether or not this interval contains
		 valid PM counts. 

		 As of ISAM4.0.10, NOT SUPPORTED  "
	::= { gponUniOltsideGemIntervalEntry 4 }


gponUniOltsideGemIntervalLostFragsDown  OBJECT-TYPE
	SYNTAX 	Counter
	ACCESS	read-only
	STATUS	mandatory
	DESCRIPTION 
		"A count of Lost GEM Fragments (downstream).

		 As of ISAM4.0.10, NOT SUPPORTED "
	::= { gponUniOltsideGemIntervalEntry 5 }

gponUniOltsideGemIntervalLostFragsUp  OBJECT-TYPE
	SYNTAX 	Counter
	ACCESS	read-only
	STATUS	mandatory
	DESCRIPTION 
		"A count of Lost GEM Fragments (upstream). "
	::= { gponUniOltsideGemIntervalEntry 6 }

gponUniOltsideGemIntervalReceiveFrags  OBJECT-TYPE
	SYNTAX 	Counter
	ACCESS	read-only
	STATUS	mandatory
	DESCRIPTION 
		"A count of Received GEM Fragments. "
	::= { gponUniOltsideGemIntervalEntry 7 }


gponUniOltsideGemIntervalReceiveBlocks  OBJECT-TYPE
	SYNTAX 	Counter
	ACCESS	read-only
	STATUS	mandatory
	DESCRIPTION 
		"A count of Received GEM Blocks. "
	::= { gponUniOltsideGemIntervalEntry 8 }


gponUniOltsideGemIntervalTransmitBlocks  OBJECT-TYPE
	SYNTAX 	Counter
	ACCESS	read-only
	STATUS	mandatory
	DESCRIPTION 
		"A count of Transmitted GEM Blocks. "
	::= { gponUniOltsideGemIntervalEntry 9 }


gponUniOltsideGemIntervalTransmitFrags  OBJECT-TYPE
	SYNTAX 	Counter
	ACCESS	read-only
	STATUS	mandatory
	DESCRIPTION 
		"A count of Transmitted GEM Fragments. "
	::= { gponUniOltsideGemIntervalEntry 10 }



-- *********************************************
--
-- GPON OLT GROUP
--
-- This MIB group contains parameters that are specified once, but apply to
-- all ONTs on all PONs in the entire shelf.  Typically, these MIB attributes
-- appear somewhere in the SET-NE-ALL TL1 command.
--
-- For ISAM4.0.10, this table is being re-used. 
-- Noted which attributes are relevant for ISAM4.0.10
--
-- These attributes are applicable for GPON, XG-PON1 and NG-PON2 
-- Noted which attributes are relevant for each flavor of each.
-- 
-- *********************************************


gponOltUpgradePotsPowerHoldTimer  OBJECT-TYPE
	SYNTAX 	INTEGER
	ACCESS	read-write
	STATUS	mandatory
	DESCRIPTION 
		" Used to specify the software upgrade situation timer that all ONTs use
		  to hold up POTS line power after losing communication with the OLT - 
		  Specified for all ONTs on the shelf.

		  Range is 0 - 1440 in minutes (i.e. up to 24 hours).

		  Default = 5 minutes

	For GPON - NOT SUPPORTED as of ISAM4.0.10
	For XG-PON1 - NOT SUPPORTED as of ISAM4.6.02
	For NG-PON2 - NOT SUPPORTED as of ISAM5.2  "
	::= { gponOltGroup 1 }

gponOltUpgradePotsPowerHoldTimerWindow  OBJECT-TYPE
	SYNTAX 	INTEGER
	ACCESS	read-write
	STATUS	mandatory
	DESCRIPTION 
		" Used to specify the window length during which the software upgrade 
		  situation timer (above) applies for holding up POTS line power - specified
		  for all ONTs on the shelf.

		  Range is 0 - 1440 in minutes (i.e. up to 24 hours).

		  Default = 5 minutes 

	For GPON - NOT SUPPORTED as of ISAM4.0.10
	For XG-PON1 - NOT SUPPORTED as of ISAM4.6.02
	For NG-PON2 - NOT SUPPORTED as of ISAM5.2  "
	::= { gponOltGroup 2 }


gponOltOntSwDownloadBehavior  OBJECT-TYPE
	SYNTAX 	INTEGER
	ACCESS	read-write
	STATUS	mandatory
	DESCRIPTION 
		" Used to specify (for the entire OLT) how ONT software download should
		  be handled for all ONT downloads.
		  
		  0 = Do NOT auto-activate image after download.
		  1 = Auto-activate image after download.

		  Default = 0 = Do NOT auto-activate.

		  As of FGU4.5, this attribute is NOT SUPPORTED

	For GPON - NOT SUPPORTED as of ISAM4.0.10
	For XG-PON1 - NOT SUPPORTED as of ISAM4.6.02
	For NG-PON2 - NOT SUPPORTED as of ISAM5.2   "
	::= { gponOltGroup 3 }

gponOltSlidInterpretationMode  OBJECT-TYPE
	SYNTAX 	INTEGER
	ACCESS	read-write
	STATUS	mandatory
	DESCRIPTION 
		" Used to specify (for the entire OLT) how to interpret
		  entry and display of the fields in the GPON MIB that
		  relate to GPON Subscriber Location ID (SLID) or the
		  NG-PON2 Registration ID. 
		  
		  0 = ASCII mode.
		  1 = Hexadecimal mode.

		  Default = 0 = ASCII mode. 

		  SUPPORTED  for FGU4.4.10.

	For GPON - SUPPORTED as of ISAM4.0.10
	For XG-PON1 - SUPPORTED as of ISAM4.6.02
	For NG-PON2 - SUPPORTED as of ISAM5.2  "
	::= { gponOltGroup 4 }

gponOltVoipDownstreamSchedMode  OBJECT-TYPE
	SYNTAX 	INTEGER
	ACCESS	read-write
	STATUS	mandatory
	DESCRIPTION 
		" Used to specify (for the entire OLT) how downstream
		  VoIP traffic is managed on the PONs.
		  
		  0 = ONT-based (queued and scheduled on a per-ONT or per-service basis).		  
		  1 = PON-based (all VoIP traffic is queued and scheduled via a common queue
		        on each PON).
		        As of FGU4.6, the value of 1 (PON-based) is only applicable for the GLT4 cards.
		        Such setting will be ignored for GLT2 cards and voip traffic will be queued on a per ONT-basis.

		  Default = 0 = ONT-based. 

		  Modification permitted only if NO Voip services exist (in entire system).

		  SUPPORTED for FGU4.6.

	For GPON - NOT SUPPORTED as of ISAM4.0.10
	For XG-PON1 - NOT SUPPORTED as of ISAM4.6.02
	For NG-PON2 - NOT SUPPORTED as of ISAM5.2   "
	::= { gponOltGroup 5 }


gponOltPowerBurstDetectMode OBJECT-TYPE
	SYNTAX 	INTEGER
	ACCESS	read-write
	STATUS	mandatory
	DESCRIPTION 
		" Used to specify whether 'special power burst detection mode'
		  is enabled or disabled for all PONs on the system.
		  
		  0 = Disabled	  
		  1 = Enabled

		  Default = 0 = Disabled. 

		  SUPPORTED as of FGU4.6.

	For GPON - SUPPORTED as of ISAM4.0.10
	For XG-PON1 - SUPPORTED as of ISAM4.6.02
	For NG-PON2 - NOT SUPPORTED as of ISAM5.2  "
	::= { gponOltGroup 6 }


-- *********************************************
-- GPON ONT SOFTWARE VERSION CONTROL TABLE
--
-- This table was introduced in FGU4.6
--
-- This table associates ONT HW Version/Variant with appropriate
-- ONT SW Version (download and planned).  The instructions in this table are used when
-- the following are TRUE: 
-- 1) Either Planned SW Version and/or Download SW Version (in ONT Table) are set to AUTO,
-- 2) Actual HW Version and specified SW Variant (in ONT Table) have a match in this table.
-- When such case is TRUE,  the logic behaves as if the appropriate AUTO selection (in ONT Table)
-- was instead replaced by the respective SW Version specified in this table.
-- 3) As of ISAM5.2, the same behavior applies for CfgFile1 and CfgFile2 configuration files.
--
--  Rows are created by the operator.
--
-- NOTE:  A row CANNOT be deleted if currently referenced by at least one ONT that has special
-- value AUTO in either SwPlannedVersion or SwDownloadVersion or similar attributes for either 
-- primary or secondary configuration files.  'Referenced' means that the
-- ONT has a matching HW version and SW Variant in the table.
--
-- For ISAM4.0.10, this table is being re-used. 
-- Noted which attributes are relevant for ISAM4.0.10
--
-- As of ISAM5.2, usage of this table was extended to include ability to control download/activation
-- of 2 distinct configuration files (CfgFile1 and CfgFile2). 
--
--	For GPON - SUPPORTED as of ISAM4.0.10 (CfgFile1 and CfgFile2 are SUPPORTED as of ISAM5.2)
--	For XG-PON1 - SUPPORTED as of ISAM4.6.02 (CfgFile1 and CfgFile2 are NOT SUPPORTED)
--	For NG-PON2 - NOT SUPPORTED as of ISAM5.2 
--
-- *********************************************

gponOntSwVerCtlTable OBJECT-TYPE
	SYNTAX	SEQUENCE OF GponOntSwVerCtlEntry
	ACCESS	not-accessible
	STATUS	mandatory
	DESCRIPTION
		"This object contains a table for automating the download
		and activation of ONT software (based on ONT HW version). "
::= { gponOntSwGroup 1 }

gponOntSwVerCtlEntry OBJECT-TYPE
	SYNTAX 	GponOntSwVerCtlEntry
	ACCESS	not-accessible
	STATUS	mandatory
	DESCRIPTION
		"Rows of this table contain ONT HW version keys and
		 associated ONT SW versions. "
	INDEX {gponOntSwVerCtlIndex }
::= {gponOntSwVerCtlTable 1}

GponOntSwVerCtlEntry ::=
	SEQUENCE { 
		gponOntSwVerCtlIndex		INTEGER,
		gponOntSwVerCtlRowStatus 	RowStatus,
		gponOntSwVerCtlHwVersion		OCTET STRING,
		gponOntSwVerCtlPlannedVariant	DisplayString,
		gponOntSwVerCtlPlannedSwVersion 	DisplayString,
		gponOntSwVerCtlPlannedSwVersionConf	DisplayString,
		gponOntSwVerCtlPreviousPlannedSwVersion	DisplayString,
		gponOntSwVerCtlPlannedSwVersionRevertCmd	INTEGER,
		gponOntSwVerCtlDownloadSwVersion 	DisplayString,
		gponOntSwVerCtlLastUpdateTime	INTEGER,
		gponOntSwVerCtlNumOntsReferenced		INTEGER,
		gponOntSwVerCtlPlannedCfgFile1	DisplayString,
		gponOntSwVerCtlDownloadCfgFile1	DisplayString,
		gponOntSwVerCtlPlannedCfgFile2	DisplayString,
		gponOntSwVerCtlDownloadCfgFile2	DisplayString
}

gponOntSwVerCtlIndex OBJECT-TYPE 
	SYNTAX INTEGER
	ACCESS not-accessible
	STATUS mandatory
	DESCRIPTION
	    "This object is the index to the gponOntSwVerCtlTable.
	     Range is 1 .. 250

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2 "
::= { gponOntSwVerCtlEntry 1}

gponOntSwVerCtlRowStatus OBJECT-TYPE 
	SYNTAX	RowStatus
	ACCESS	read-write
	STATUS  mandatory
	DESCRIPTION
		"This object is used to create a new row or modify or
         		delete an existing row in this table.

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2  "
::= { gponOntSwVerCtlEntry  2}

gponOntSwVerCtlHwVersion 	OBJECT-TYPE 
	SYNTAX 	OCTET STRING (SIZE(0..14))
	ACCESS	read-write
	STATUS	mandatory
	DESCRIPTION 
		" This is the ONT Hardware Version. Has same connotation as bponOntVersionNumber
		  attribute in bponOntTable.  This attribute is a key in this table.  The combination of this
		  attribute and the gponOntSwVerCtlPlannedVariant attribute MUST be unique, otherwise
		  it is rejected.

		  Special character * (asterisk) means that the * character (and all subsequent character
		  positions) are considered to be automatic 'matches' for values in same character positions
		  of bponOntVersionNumber attribute of bponOntTable.  NOTE:  The position of the * must also
		  be taken into consideration when determining 'uniqueness' of row keys in tables (per above).

		  Modification is NOT permitted (i.e. CANNOT modify a key field). 

		  No default - must be supplied by operator.

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2 "
::= {gponOntSwVerCtlEntry 3}

gponOntSwVerCtlPlannedVariant 	OBJECT-TYPE 
	SYNTAX 	DisplayString
	ACCESS	read-write
	STATUS	mandatory
	DESCRIPTION 
		" This attribute has same connotation as bponOntPlannedVariant attribute in bponOntTable.
		  This attribute is a key in this table.  The combination of this attribute and the
		  gponOntSwVerCtlHwVersion attribute MUST be unique, otherwise it is rejected.

		  Modification is permitted (i.e. CANNOT modify a key field). 

		  Maximum of 80 displayable characters.

		  Default = null string.

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2  "
::= {gponOntSwVerCtlEntry 4}

gponOntSwVerCtlPlannedSwVersion  OBJECT-TYPE
	SYNTAX 	DisplayString
	ACCESS	read-write
	STATUS	mandatory
	DESCRIPTION 
		" As of ISAM4.0.10, This attribute has same connotation as bponOntSwPlannedVersion attribute in bponOntTable.
		  When bponOntSwPlannedVersion is set to special value AUTO, and that ONT's hardware
		  version and planned variant have a match in this table, then this attribute is used in place
		  of the bponOntSwPlannedVersion.

		  The special string value UNPLANNED means that any download and activation processing 
		  associated with this attribute is inhibited.  UNPLANNED also means that the OLT will NOT provision this
		  ONT via OMCI with relevant information from the OLT MIB.

		  See rules below associated with gponOntSwVerCtlPlannedSwVersionConf attribute. Any attempt to 
		  SET this attribute (without a coincident SET on gponOntSwVerCtlPlannedSwVersionConf)
		  is rejected.

		  Modification is permitted.

		  Default = string value UNPLANNED

		As of ISAM4.3.01, the special string value DISABLED means that any download and activation processing
		associated with this attribute is inhibited.  However, unlike UNPLANNED string, the DISABLED string
		means that the OLT will provision this ONT via OMCI with relevant information from the OLT MIB.

		As of ISAM5.0, the special string value DELAYACTIVATE means that following the next ONT Out-of-Service (OOS)
		to In-Service (IS) transition, the OLT will activate the software version implied in bponOntSwDownloadVersion
		attribute.  

		As of ISAM5.0:
		RULE:  The following combination of values are prohibited:
			 gponOntSwVerCtlPlannedSwVersion = DELAYACTIVATE
			 gponOntSwVerCtlDownloadSwVersion = DISABLED

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2   "

::= {gponOntSwVerCtlEntry 5}

gponOntSwVerCtlPlannedSwVersionConf  OBJECT-TYPE
	SYNTAX 	DisplayString
	ACCESS	read-write
	STATUS	mandatory
	DESCRIPTION 
		" This attribute acts as a confirmation of the gponOntSwVerCtlPlannedSwVersion attribute (above).
		  Any time the gponOntSwVerCtlPlannedSwVersion attribute is SET (either due to creation
		  or edit), this attribute must be SET to the identical value.  Otherwise, the operation is rejected.
		  Any attempt to SET this attribute (without a coincident SET on gponOntSwVerCtlPlannedSwVersion)
		  is also rejected.

		  Modification is permitted.

		  Default = string value UNPLANNED

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2  "
::= {gponOntSwVerCtlEntry 6}

gponOntSwVerCtlPreviousPlannedSwVersion  OBJECT-TYPE
	SYNTAX 	DisplayString
	ACCESS	read-only
	STATUS	mandatory
	DESCRIPTION 
		" This attribute contains previous value of gponOntSwVerCtlPlannedSwVersion (prior to the
		  last edit of that attribute).  Upon receipt of a 'revert command', the OLT will copy this 
		  attribute into the gponOntSwVerCtlPlannedSwVersion attribute and then perform necessary
		  download/activation sequences. 

		  Default (upon row creation) = same value as gponOntSwVerCtlPlannedSwVersion

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2  "
::= {gponOntSwVerCtlEntry 7}

gponOntSwVerCtlPlannedSwVersionRevertCmd OBJECT-TYPE
	SYNTAX 	 INTEGER
	ACCESS	read-write
	STATUS	mandatory
	DESCRIPTION 
		" This attribute is used to command the OLT to copy the gponOntSwVerCtlPreviousPlannedSwVersion
		  attribute into the gponOntSwVerCtlPlannedSwVersion attribute and then perform necessary
		  download/activation sequences.  This is referred to as a 'revert command'.  It is typically used
		  to revert (i.e. rollback) the download/activation sequences that may have occurred due to a 
		  mistaken user entry for creation/edit of the gponOntSwVerCtlPlannedSwVersion attribute.
		  
		  Acceptable values are as follows:
		  0 = no reversion (default)
		  1 = execute reversion 

		  NOTE:  If 'execute reversion' command is received and gponOntSwVerCtlPlannedSwVersion 
		  already equals gponOntSwVerCtlPreviousPlannedSwVersion, this is effectively a no-op.

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2  "
::= {gponOntSwVerCtlEntry 8}

gponOntSwVerCtlDownloadSwVersion  OBJECT-TYPE
	SYNTAX 	DisplayString
	ACCESS	read-write
	STATUS	mandatory
	DESCRIPTION 
		" This attribute has same connotation as bponOntSwDownloadVersion attribute in bponOntTable.
		  When bponOntSwDownloadVersion is set to special value AUTO, and that ONT's hardware
		  version and planned variant have a match in this table, then this attribute is used in place
		  of the bponOntSwDownloadVersion.

		  The special string value DISABLED means that any download processing associated
		  with this attribute is inhibited.

		  Modification is permitted.

		  Default = string value DISABLED


		As of ISAM5.0:
		RULE:  The following combination of values are prohibited:
			 gponOntSwVerCtlPlannedSwVersion = DELAYACTIVATE
			 gponOntSwVerCtlDownloadSwVersion = DISABLED 

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2  "
::= {gponOntSwVerCtlEntry 9}


gponOntSwVerCtlLastUpdateTime OBJECT-TYPE
       	SYNTAX       INTEGER (0..4294967295)
       	ACCESS       read-only
       	STATUS       mandatory
       	DESCRIPTION
           		" This attribute should be interpreted as Unix time (seconds since midnight January 1,1970). 
		  This attributes represents the time that this row was created or the last time any field
		  in the row was edited by the user.

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2   "
::= {gponOntSwVerCtlEntry 10}


gponOntSwVerCtlNumOntsReferenced OBJECT-TYPE
       	SYNTAX       INTEGER 
       	ACCESS       read-only
       	STATUS       mandatory
       	DESCRIPTION
           		" This attribute contains the number of ONTs that are referenced by this row.

		  For FGU4.6, range is 0..8192.

		For ISAM 4.0.10 -> upper range was increased to 8192, 
		to handle increased number of ONTs per OLT.

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2  "
::= {gponOntSwVerCtlEntry 11}


gponOntSwVerCtlPlannedCfgFile1  OBJECT-TYPE
	SYNTAX 	DisplayString
	ACCESS	read-write
	STATUS	mandatory
	DESCRIPTION 
	"This attribute has same connotation as bponOntPlannedCfgFile1 attribute in bponOntTable.
	 When bponOntPlannedCfgFile1 is set to special value AUTO, and that ONT's hardware version 
	 and planned variant have a match in this table, then this attribute is used in place of the 
	 bponOntPlannedCfgFile1 .

	 The special string value DISABLED means that any download processing associated with this attribute is inhibited.

	Default = string value DISABLED

	For GPON - SUPPORTED as of ISAM5.2 
	For XG-PON1 - NOT SUPPORTED as of ISAM4.6.02 
	For NG-PON2 - NOT SUPPORTED as of ISAM5.2  "
::= {gponOntSwVerCtlEntry 12}


gponOntSwVerCtlDownloadCfgFile1  OBJECT-TYPE
	SYNTAX 	DisplayString
	ACCESS	read-write
	STATUS	mandatory
	DESCRIPTION 
	"This attribute has same connotation as bponOntDownloadCfgFile1 attribute in bponOntTable.
	 When bponOntDownloadCfgFile1 is set to special value AUTO, and that ONT's hardware version 
	 and planned variant have a match in this table, then this attribute is used in place of the 
	 bponOntDownloadCfgFile1 .

	 The special string value DISABLED means that any download processing associated with this attribute is inhibited.

	Default = string value DISABLED

	For GPON - SUPPORTED as of ISAM5.2 
	For XG-PON1 - NOT SUPPORTED as of ISAM4.6.02 
	For NG-PON2 - NOT SUPPORTED as of ISAM5.2  "
::= {gponOntSwVerCtlEntry 13}


gponOntSwVerCtlPlannedCfgFile2  OBJECT-TYPE
	SYNTAX 	DisplayString
	ACCESS	read-write
	STATUS	mandatory
	DESCRIPTION 
	"This attribute has same connotation as bponOntPlannedCfgFile2 attribute in bponOntTable.
	 When bponOntPlannedCfgFile2 is set to special value AUTO, and that ONT's hardware version 
	 and planned variant have a match in this table, then this attribute is used in place of the 
	 bponOntPlannedCfgFile2 .

	 The special string value DISABLED means that any download processing associated with this attribute is inhibited.

	Default = string value DISABLED

	For GPON - SUPPORTED as of ISAM5.2 
	For XG-PON1 - NOT SUPPORTED as of ISAM4.6.02 
	For NG-PON2 - NOT SUPPORTED as of ISAM5.2  "
::= {gponOntSwVerCtlEntry 14}


gponOntSwVerCtlDownloadCfgFile2  OBJECT-TYPE
	SYNTAX 	DisplayString
	ACCESS	read-write
	STATUS	mandatory
	DESCRIPTION 
	"This attribute has same connotation as bponOntDownloadCfgFile2 attribute in bponOntTable.
	 When bponOntDownloadCfgFile2 is set to special value AUTO, and that ONT's hardware version 
	 and planned variant have a match in this table, then this attribute is used in place of the 
	 bponOntPlannedCfgFile2 .

	 The special string value DISABLED means that any download processing associated with this attribute is inhibited.

	Default = string value DISABLED

	For GPON - SUPPORTED as of ISAM5.2 
	For XG-PON1 - NOT SUPPORTED as of ISAM4.6.02 
	For NG-PON2 - NOT SUPPORTED as of ISAM5.2  "
::= {gponOntSwVerCtlEntry 15}



gponOntSwVerCtlIndexNext        OBJECT-TYPE
        	SYNTAX          INTEGER
        	ACCESS          read-only
        	STATUS          mandatory
        	DESCRIPTION     
        	        	" This object contains an appropriate value to be used for gponOntSwVerCtlIndex 
		   when creating entries in the gponOntSwVerCtlTable. 
		   Range is 0 .. 250.
         		   The value 0 indicates that no unassigned entries are available. To 
         		   obtain the next avaialble index value for a new entry, the
        		   manager can issue a management protocol retrieval operation to obtain the
         		   current value of this object.  After each retrieval, the agent should
        		   modify the value to the next unassigned index.

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2  "
::= {gponOntSwGroup 7 }


-- ***********************************************************************************************************
-- GPON ONT SOFTWARE VERSION CONTROL REFERENCED ROW SCALAR
--
-- This scalar is used to identify a row in the gponOntSwVerCtlTable.  The manager SETs
-- this attribute in order to cause the NE to freshly construct all rows in the gponOntSwVerCtlRefOntTable.
-- 
--
--	For GPON - SUPPORTED as of ISAM4.0.10
--	For XG-PON1 - SUPPORTED as of ISAM4.6.02
--	For NG-PON2 - NOT SUPPORTED as of ISAM5.2
--
-- ***********************************************************************************************************

gponOntSwVerCtlReferencedRow        OBJECT-TYPE
        	SYNTAX          INTEGER
	ACCESS	read-write
	STATUS	mandatory
	DESCRIPTION 
		" This attribute is used to specify a row in the gponOntSwVerCtlTable.  The manager SETs
		   this attribute in order to cause the NE to freshly construct all rows in the 
		   gponOntSwVerCtlRefOntTable.  Other than the special value 0, the system should reject
		   attempt to set this attribute to a non-existent row. The value 0 will cause the NE to nullify
		   (e.g. depopulate) the entire gponOntSwVerCtlRefOntTable.  The manager (e.g. TL1 and EMS)
		   should not present this 0 (zero) option to the user - as it is typically reserved for Off Line Migration
		   Tool (OLMT) - so that a migrated database can start with a fresh value of 0.

		   For FGU4.6, range is 0..250.

		  Default = 0

	For GPON - SUPPORTED as of ISAM4.0.10
	For XG-PON1 - SUPPORTED as of ISAM4.6.02
	For NG-PON2 - NOT SUPPORTED as of ISAM5.2  "
::= { gponOntSwGroup 8 }


-- *********************************************
-- GPON ONT SOFTWARE VERSION CONTROL REFERENCED ONT TABLE
--
-- This table was introduced in FGU4.6.
--
-- This table contains a list of ONT ifIndexes for those ONTs that are referenced by the 
-- gponOntSwVerCtlTable row that was last SET in the gponOntSwVerCtlReferencedRow SCALAR.
-- The table entries are automatically created/re-created by the NE each time an appropriate SET
-- is accepted for the gponOntSwVerCtlReferencedRow SCALAR attribute.
-- 
--	For GPON - SUPPORTED as of ISAM4.0.10
--	For XG-PON1 - SUPPORTED as of ISAM4.6.02
--	For NG-PON2 - NOT SUPPORTED as of ISAM5.2
--
-- *********************************************

gponOntSwVerCtlRefOntTable OBJECT-TYPE
	SYNTAX	SEQUENCE OF GponOntSwVerCtlRefOntEntry
	ACCESS	not-accessible
	STATUS	mandatory
	DESCRIPTION
		"This object contains a table of ONT ifIndexes for those ONTs
		 that are referenced by the gponOntSwVerCtlTable row that was last
		 SET in the gponOntSwVerCtlReferencedRow SCALAR. "
::= { gponOntSwGroup 9 }

gponOntSwVerCtlRefOntEntry OBJECT-TYPE
	SYNTAX 	GponOntSwVerCtlRefOntEntry
	ACCESS	not-accessible
	STATUS	mandatory
	DESCRIPTION
		"Rows of this table contain the ifIndexes of ONTs that are referenced to
		 a specific row of the gponOntSwVerCtlTable. "
	INDEX {gponOntSwVerCtlRefOntIndex }
::= {gponOntSwVerCtlRefOntTable 1}

GponOntSwVerCtlRefOntEntry ::=
	SEQUENCE { 
		gponOntSwVerCtlRefOntIndex		INTEGER,
		gponOntSwVerCtlRefOntIfIndex		IfIndex
}

gponOntSwVerCtlRefOntIndex OBJECT-TYPE 
	SYNTAX INTEGER
	ACCESS not-accessible
	STATUS mandatory
	DESCRIPTION
	    "This object is the index to the gponOntSwVerCtlRefOntTable.
	     Range is 1 .. 8192

	For ISAM 4.0.10 -> upper range was increased to 8192, to handle increased 
	number of ONTs per OLT.

	For GPON - SUPPORTED as of ISAM4.0.10
	For XG-PON1 - SUPPORTED as of ISAM4.6.02
	For NG-PON2 - NOT SUPPORTED as of ISAM5.2  "
::= { gponOntSwVerCtlRefOntEntry 1}

gponOntSwVerCtlRefOntIfIndex OBJECT-TYPE 
	SYNTAX	IfIndex
	ACCESS	read-only
	STATUS  mandatory
	DESCRIPTION
		"This object contains the ifIndex of an ONT that is referenced by the
		 gponOntSwVerCtlTable row that was last SET in the 
		 gponOntSwVerCtlReferencedRow SCALAR 

	For GPON - SUPPORTED as of ISAM4.0.10
	For XG-PON1 - SUPPORTED as of ISAM4.6.02
	For NG-PON2 - NOT SUPPORTED as of ISAM5.2 "
::= { gponOntSwVerCtlRefOntEntry  2}



-- *********************************************
-- GPON ONT SOFTWARE VERSION INFO TABLE
--
-- This table was introduced in FGU4.6.
--
-- This table contains a listing of ONT Software Versions and config files that are currently
--  resident on the the NT file system.
--
-- For this initial GET of the 1st row, the OLT agent will delay
-- the GET-RESPONSE while it replenishes the entire
-- table with fresh information
--
-- For ISAM4.0.10, this table is being re-used. 
-- Noted which attributes are relevant for ISAM4.0.10
--
-- As of ISAM5.2, this table is also relevant for CfgFile1 and CfgFile2 files
--
--	For GPON - SUPPORTED as of ISAM4.0.10 (CfgFile1 and CfgFile2 are SUPPORTED as of ISAM5.2)
--	For XG-PON1 - SUPPORTED as of ISAM4.6.02 (CfgFile1 and CfgFile2 are NOT SUPPORTED)
--	For NG-PON2 - NOT SUPPORTED as of ISAM5.2 
--
-- *********************************************

gponOntSwVerInfoTable OBJECT-TYPE
	SYNTAX	SEQUENCE OF GponOntSwVerInfoEntry
	ACCESS	not-accessible
	STATUS	mandatory
	DESCRIPTION
		"This object contains a table for listing the ONT Software version
		 files and config files currently resident on the NT file system "
::= { gponOntSwGroup 2 }

gponOntSwVerInfoEntry OBJECT-TYPE
	SYNTAX 	GponOntSwVerInfoEntry
	ACCESS	not-accessible
	STATUS	mandatory
	DESCRIPTION
		"Rows of this table contain information about ONT SW version
		 files and config files resident on the NT file system. "
	INDEX {gponOntSwVerInfoIndex }
::= {gponOntSwVerInfoTable 1}

GponOntSwVerInfoEntry ::=
	SEQUENCE { 
		gponOntSwVerInfoIndex		INTEGER,
		gponOntSwVerInfoSwVersion	DisplayString,
		gponOntSwVerInfoSwVersionSize 	INTEGER,
		gponOntSwVerInfoSwVersionCrc 	INTEGER
}

gponOntSwVerInfoIndex OBJECT-TYPE 
	SYNTAX INTEGER
	ACCESS not-accessible
	STATUS mandatory
	DESCRIPTION
	    "This object is the index to the gponOntSwVerInfoTable.
	     Range is 1 .. 250

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2   "
::= { gponOntSwVerInfoEntry 1}

gponOntSwVerInfoSwVersion  OBJECT-TYPE
	SYNTAX 	DisplayString
	ACCESS	read-only
	STATUS	mandatory
	DESCRIPTION 
		" This attribute contains the ONT Software Version identifier.

		   If there are no ONT software version files on the NT system, or if the information
		   is unobtainable for any reason - then this attribute contains the null string.

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2 "
::= {gponOntSwVerInfoEntry 2}


gponOntSwVerInfoSwVersionSize	OBJECT-TYPE 
	SYNTAX 	INTEGER (0..4294967295)
	ACCESS	read-only
	STATUS	mandatory
	DESCRIPTION 
		" This attribute contains the ONT Software Version size (in bytes).

		   If there are no ONT software version files on the NT system, or if the information
		   is unobtainable for any reason - then this attribute contains the value 0.

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2 "
::= {gponOntSwVerInfoEntry 3}

gponOntSwVerInfoSwVersionCrc	OBJECT-TYPE 
	SYNTAX 	INTEGER (0..4294967295)
	ACCESS	read-only
	STATUS	mandatory
	DESCRIPTION 
		" This attribute contains the ONT Software Version CRC.

		   If there are no ONT software version files on the NT system, or if the information
		   is unobtainable for any reason - then this attribute contains the value 0.

		  As of FGU4.6, this attribute is NOT SUPPORTED

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2. "
::= {gponOntSwVerInfoEntry 4}


-- *********************************************
-- GPON ONT SOFTWARE VERSION DELETE COMMAND SCALAR
--
-- This scalar is used to identify an ONT Software Version or CfgFile1 or CfgFile2 
--	that manager wants deleted from the NT file system
--
-- For ISAM4.0.10, this table is being re-used. 
-- Noted which attributes are relevant for ISAM4.0.10
--
-- As of ISAM5.2, this SCALAR is also relevant for primary and secondary config files
--
--	For GPON - SUPPORTED as of ISAM4.0.10 (CfgFile1 and CfgFile2 are SUPPORTED as of ISAM5.2)
--	For XG-PON1 - SUPPORTED as of ISAM4.6.02 (CfgFile1 and CfgFile2 are NOT SUPPORTED)
--	For NG-PON2 - NOT SUPPORTED as of ISAM5.2 
--
--
-- *********************************************

gponOntSwVerDeleteCmd OBJECT-TYPE
	SYNTAX 	DisplayString
	ACCESS	read-write
	STATUS	mandatory
	DESCRIPTION 
		" This attribute is used to specify an ONT Software Version or CfgFile1 or CfgFile2
		  that manager wants deleted from the NT file system.

		  Default = null string

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2 "
::= { gponOntSwGroup 3 }


-- *********************************************
-- GPON ONT SOFTWARE VERSION DELETE COMMAND STATUS SCALAR
--
-- This scalar is used to post the status of the last ONT Software Version or CfgFile1 or CfgFile2
-- deletion command (i.e. the previous SET of gponOntSwVerDeleteCmd).
--
-- For ISAM4.0.10, this table is being re-used. 
-- Noted which attributes are relevant for ISAM4.0.10

-- As of ISAM5.2, this SCALAR is also relevant for primary and secondary config files
--
--	For GPON - SUPPORTED as of ISAM4.0.10 (CfgFile1 and CfgFile2 are SUPPORTED as of ISAM5.2)
--	For XG-PON1 - SUPPORTED as of ISAM4.6.02 (CfgFile1 and CfgFile2 are NOT SUPPORTED)
--	For NG-PON2 - NOT SUPPORTED as of ISAM5.2 
--
-- *********************************************

gponOntSwVerDeleteCmdStatus OBJECT-TYPE
	SYNTAX 	INTEGER
	ACCESS	read-only
	STATUS	mandatory
	DESCRIPTION 
		" This attribute is used to post the status of the last ONT Software Version
		  or primary/secondary config file deletion command
		  (i.e. the previous SET of gponOntSwVerDeleteCmd).

		  0 =  Command has never been issued (this is the DEFAULT)
		  1 =  In progress (agent will post this status until deletion request is determined to be 
		         successful or unsuccessful).
		  2 =  Success (file successfully deleted)
		  3 =  Failed (unable to delete file)

		  Default = 0

	For GPON - SUPPORTED as of ISAM4.0.10 (CfgFile1 and CfgFile2 are SUPPORTED as of ISAM5.2)
	For XG-PON1 - SUPPORTED as of ISAM4.6.02 (CfgFile1 and CfgFile2 are NOT SUPPORTED)
	For NG-PON2 - NOT SUPPORTED as of ISAM5.2  "
::= { gponOntSwGroup 4 }


-- *********************************************
--
-- GPON ONT SOFTWARE DOWNLOAD TABLE
--
-- This is a new table beginning with FGU4.6.
--
-- It is used to retrieve individual ONT fine-grain status 
-- asssociated with any 'SW download activity'.  This table is primarily
-- intended as a aide to a management system (EMS) that prefers polling
-- a status attribute (instead of using the legacy 'alarm processing' mechanism).
-- NOTE:  The term 'download activity' should be interpreted in the broad sense
-- of individual steps necessary to perform 'womb-to-tomb' ONT software 
-- management activity (e.g. retrieval of load from NT file system all the way
-- through ONT activation).
-- 
-- Rows are created/deleted automatically by OLT when the
-- parent PON or channel pair row is created/deleted .
--
-- For ISAM4.0.10, this table is being re-used. 
-- Noted which attributes are relevant for ISAM4.0.10

--	For GPON - SUPPORTED as of ISAM4.0.10 (CfgFile1 and CfgFile2 are SUPPORTED as of ISAM5.2)
--	For XG-PON1 - SUPPORTED as of ISAM4.6.02 (CfgFile1 and CfgFile2 are NOT SUPPORTED as of ISAM4.6.02)
--	For NG-PON2 - SUPPORTED as of ISAM5.3 (CfgFile1 and CfgFile2 are NOT SUPPORTED as of ISAM5.3)
--  
-- *********************************************

gponOntSwDownldStatusTable  OBJECT-TYPE
	SYNTAX SEQUENCE OF GponOntSwDownldStatusEntry
	ACCESS	not-accessible
	STATUS	mandatory
	::= { gponOntSwGroup 5 }

gponOntSwDownldStatusEntry  OBJECT-TYPE
	SYNTAX 	GponOntSwDownldStatusEntry
	ACCESS	not-accessible
	STATUS	mandatory
	INDEX	{ gponOntSwDownldStatusIndex }
	::= { gponOntSwDownldStatusTable 1 }

GponOntSwDownldStatusEntry ::= SEQUENCE {
	gponOntSwDownldStatusIndex			IfIndex,
	gponOntSwDownldStatus	OCTET STRING,
	gponOntCfgFile1DownldStatus	OCTET STRING,
	gponOntCfgFile2DownldStatus	OCTET STRING
}

gponOntSwDownldStatusIndex  OBJECT-TYPE
	SYNTAX 	IfIndex
	ACCESS	read-only
	STATUS	mandatory
	DESCRIPTION 
		"Each row is indexed by the ifIndex of the ONT.

	For GPON - SUPPORTED as of ISAM4.0.10 (CfgFile1 and CfgFile2 are NOT SUPPORTED as of ISAM5.2)
	For XG-PON1 - SUPPORTED as of ISAM4.6.02 (CfgFile1 and CfgFile2 are NOT SUPPORTED)
	For NG-PON2 - NOT SUPPORTED as of ISAM5.2 "
	::= { gponOntSwDownldStatusEntry 1 }


gponOntSwDownldStatus  OBJECT-TYPE
	SYNTAX 	OCTET STRING (SIZE(4))
	ACCESS	read-only
	STATUS	mandatory
	DESCRIPTION 
           		" Attribute construction is as follows: 
		  4 bytes (32 bits) per ONT.  

		  The 32-bit ONT chunk is a bit-map of current ONT download status conditions, and multiple
		  conditions can be simultaneously present.  For example, an ONT may have a Software Version
		  Mismatch condition concurrent with the File Not Found reason.

           		 In following descriptions, Bit 1 position is defined as the high-order left-most and Bit 32 position is 
		 defined as  the low-order, right-most. The bit positions and meanings are as follows:

           		 All Bits Zero (OFF) = ONT is Planned, OLT is in-contact with it, no download activity is pending or ongoing,
				    and system is not in some erroneous state due to download activity.
		 Bit 1 ON = ONT is NOT Planned.  All other bits are inconsequential when this bit is set (and if set, the 
		       	    NE should have all other bits set to 0).  
		 Bit 2 ON =  ONT is INACTIVE (mirrors INACT alarm condition, although OLT may be suppressing
			      an actual INACT alarm ). 
		 Bit 3 ON =  Last known Planned Software Version was NOT OK (i.e. Planned did not equal
			      Active).  This bit only has relevance when Bit 2 is ON (i.e. when ONT is inactive).
		 Bit 4 ON =  Last known Download Software Version was NOT OK (i.e. Download did not equal
			      Active or Passive).  This bit only has relevance when Bit 2 is ON (i.e. when ONT is inactive).
		 Bit 5 ON =  Download activity In-Progress (mirrors current SWDLIP alarm).  
		 Bit 6 ON =  NT/LT file transfer activity In-Progress. 
		 Bit 7 ON =  OMCI file transfer activity In-Progress. 
		 Bit 8 ON =  ONT flash-write activity In-Progress.
		 Bit 9 ON =  ONT software activation In-Progress.
		 Bit 10 ON =  NT/LT file transfer failure.
		 Bit 11 ON =  OMCI file transfer failure.
		 Bit 12 ON =  ONT flash-write failure.
		 Bit 13 ON =  ONT software activation failure (mirrors current SWACTFAIL alarm).
		 Bit 14 ON =  Download File-Not-Found (mirrors current SWDLFILE alarm).
		 Bit 15 ON =  Entry match not found in ONT Software Version Control Table
			      (mirrors SWVERCTLERR alarm introduced in FGU4.6).
		 Bit 16 ON =  Software Version Mismatch (mirrors current SWVER alarm).
		 Bit 17 ON =  Software Download Failure (mirrors current SWDLFAIL alarm).
		 Bit 18 ON = DELAYACTIVATE activity is Pending.
		 Bit 19 ON = Download activity is Pending. (Bit NOT SUPPORTED as of ISAM5.2)
		 Bits 20 thru 32  = Undefined - Not Supported - and should be zero (OFF).

		 Default = Bit 1 ON (and Bits 2 thru 32 OFF). Meaning that when PON is initially auto-created by NE,
		 there are effectively NO Planned ONTs on the PON.

		As of ISAM5.0, added SUPPORT for Bit 18.
		As of ISAM5.2, added SUPPORT for Bit 19.

	For GPON - SUPPORTED as of ISAM4.0.10 
	For XG-PON1 - SUPPORTED as of ISAM4.6.02
	For NG-PON2 - NOT SUPPORTED as of ISAM5.2 "
        ::= { gponOntSwDownldStatusEntry 2 }

gponOntCfgFile1DownldStatus  OBJECT-TYPE
	SYNTAX 	OCTET STRING (SIZE(4))
	ACCESS	read-only
	STATUS	mandatory
	DESCRIPTION 
      " Attribute construction is as follows: 
		  4 bytes (32 bits) per ONT.  

		  The 32-bit ONT chunk is a bit-map of current ONT download status conditions, and multiple
		  conditions can be simultaneously present.  For example, an ONT may have a CfgFile1 Version
		  Mismatch condition concurrent with the File Not Found reason.

      		In following descriptions, Bit 1 position is defined as the high-order left-most and Bit 32 position is 
		  defined as  the low-order, right-most. The bit positions and meanings are as follows:

      		All Bits Zero (OFF) = ONT is Planned, OLT is in-contact with it, no download activity is pending or ongoing,
		  and system is not in some erroneous state due to download activity.
		  Bit 1 ON = ONT is NOT Planned.  All other bits are inconsequential when this bit is set (and if set, the 
		       	    NE should have all other bits set to 0).  
		  Bit 2 ON =  ONT is INACTIVE (mirrors INACT alarm condition, although OLT may be suppressing
			          an actual INACT alarm ). 
		  Bit 3 ON =  Last known Planned CfgFile1 Version was NOT OK (i.e. Planned did not equal
			          Active).  This bit only has relevance when Bit 2 is ON (i.e. when ONT is inactive).
		  Bit 4 ON =  Last known Download CfgFile1 Version was NOT OK (i.e. Download did not equal
			          Active or Passive).  This bit only has relevance when Bit 2 is ON (i.e. when ONT is inactive).
		  Bit 5 ON =  Download activity In-Progress (mirrors current CFG1DLIP alarm).  
		  Bit 6 ON =  NT/LT file transfer activity In-Progress. 
		  Bit 7 ON =  OMCI file transfer activity In-Progress. 
		  Bit 8 ON =  ONT flash-write activity In-Progress.
		  Bit 9 ON =  ONT software activation In-Progress.
		  Bit 10 ON =  NT/LT file transfer failure.
		  Bit 11 ON =  OMCI file transfer failure.
		  Bit 12 ON =  ONT flash-write failure.
		  Bit 13 ON =  ONT Cfg1File1 activation failure (mirrors current CFG1ACTFAIL alarm).
		  Bit 14 ON =  Download File-Not-Found (mirrors current CFG1DLFILE alarm).
		  Bit 15 ON =  Entry match not found in ONT Software Version Control Table
			            (mirrors CFG1VERCTLERR alarm).
		  Bit 16 ON =  CfgFile1 Version Mismatch (mirrors current CFG1VER alarm).
		  Bit 17 ON =  CfgFile1 Download Failure (mirrors current CFG1DLFAIL alarm).
      		  Bit 18 ON =  DELAYACTIVATE activity is Pending. (Bit NOT SUPPORTED for this attribute - always 0).
		  Bit 19 ON =  Download activity is Pending. (Bit introduced and NOT SUPPORTED as of ISAM5.2)
		  Bits 20 thru 32  = Undefined - Not Supported - and should be zero (OFF).

		  Default = Bit 1 ON (and Bits 2 thru 32 OFF). Meaning that when PON is initially auto-created by NE,
		            there are effectively NO Planned ONTs on the PON.
    	Introduced in ISAM5.2 MIB

		For GPON - SUPPORTED as of ISAM5.2 
		For XG-PON1 - NOT SUPPORTED as of ISAM4.6.02
		For NG-PON2 - NOT SUPPORTED as of ISAM5.2 "

      ::= { gponOntSwDownldStatusEntry 3 }
      
gponOntCfgFile2DownldStatus  OBJECT-TYPE
	SYNTAX 	OCTET STRING (SIZE(4))
	ACCESS	read-only
	STATUS	mandatory
	DESCRIPTION 
      " Attribute construction is as follows: 
		  4 bytes (32 bits) per ONT.  
		  The 32-bit ONT chunk is a bit-map of current ONT download status conditions, and multiple
		  conditions can be simultaneously present.  For example, an ONT may have a CfgFile1 Version
		  Mismatch condition concurrent with the File Not Found reason.

      		In following descriptions, Bit 1 position is defined as the high-order left-most and Bit 32 position is 
		  defined as  the low-order, right-most. The bit positions and meanings are as follows:

      		All Bits Zero (OFF) = ONT is Planned, OLT is in-contact with it, no download activity is pending or ongoing,
		  and system is not in some erroneous state due to download activity.
		  Bit 1 ON = ONT is NOT Planned.  All other bits are inconsequential when this bit is set (and if set, the 
		       	    NE should have all other bits set to 0).  
		  Bit 2 ON =  ONT is INACTIVE (mirrors INACT alarm condition, although OLT may be suppressing
			          an actual INACT alarm ). 
		  Bit 3 ON =  Last known Planned CfgFile2 Version was NOT OK (i.e. Planned did not equal
			          Active).  This bit only has relevance when Bit 2 is ON (i.e. when ONT is inactive).
		  Bit 4 ON =  Last known Download CfgFile2 Version was NOT OK (i.e. Download did not equal
			          Active or Passive).  This bit only has relevance when Bit 2 is ON (i.e. when ONT is inactive).
		  Bit 5 ON =  Download activity In-Progress (mirrors current CFG2DLIP alarm).  
		  Bit 6 ON =  NT/LT file transfer activity In-Progress. 
		  Bit 7 ON =  OMCI file transfer activity In-Progress. 
		  Bit 8 ON =  ONT flash-write activity In-Progress.
		  Bit 9 ON =  ONT software activation In-Progress.
		  Bit 10 ON =  NT/LT file transfer failure.
		  Bit 11 ON =  OMCI file transfer failure.
		  Bit 12 ON =  ONT flash-write failure.
		  Bit 13 ON =  ONT Cfg2File1 activation failure (mirrors current CFG2ACTFAIL alarm).
		  Bit 14 ON =  Download File-Not-Found (mirrors current CFG2DLFILE alarm).
		  Bit 15 ON =  Entry match not found in ONT Software Version Control Table
			            (mirrors CFG2VERCTLERR alarm).
		  Bit 16 ON =  CfgFile1 Version Mismatch (mirrors current CFG2VER alarm).
		  Bit 17 ON =  CfgFile1 Download Failure (mirrors current CFG2DLFAIL alarm).
      		  Bit 18 ON =  DELAYACTIVATE activity is Pending. (Bit NOT SUPPORTED for this attribute - always 0).
		  Bit 19 ON =  Download activity is Pending. (Bit introduced and NOT SUPPORTED as of ISAM5.2)
		  Bits 20 thru 32  = Undefined - Not Supported - and should be zero (OFF).

		  Default = Bit 1 ON (and Bits 2 thru 32 OFF). Meaning that when PON is initially auto-created by NE,
		            there are effectively NO Planned ONTs on the PON.
    	Introduced in ISAM5.2 MIB

		For GPON - SUPPORTED as of ISAM5.2 
		For XG-PON1 - NOT SUPPORTED as of ISAM4.6.02
		For NG-PON2 - NOT SUPPORTED as of ISAM5.2 "

      ::= { gponOntSwDownldStatusEntry 4 }  


-- *********************************************
--
-- GPON PON ONT SOFTWARE DOWNLOAD TABLE
--
-- This is a new table beginning with FGU4.6.
--
-- It is used to retrieve (for PON lump-sum) individual ONT fine-grain status 
-- asssociated with any 'SW download activity'.  This table is primarily
-- intended as a aide to a management system (EMS) that prefers polling
-- a status attribute (instead of using the legacy 'alarm processing' mechanism).
-- NOTE:  The term 'download activity' should be interpreted in the broad sense
-- of individual steps necessary to perform 'womb-to-tomb' ONT software 
-- management activity (e.g. retrieval of load from NT file system all the way
-- through ONT activation).
-- 
-- Rows are created/deleted automatically by OLT when the
-- corresponding row is created/deleted in the bponPonConfigTable.
--
--	For GPON - SUPPORTED as of ISAM4.0.10 (CfgFile1 and CfgFile2 are SUPPORTED as of ISAM5.2)
--	For XG-PON1 - SUPPORTED as of ISAM4.6.02 (CfgFile1 and CfgFile2 are NOT SUPPORTED as of ISAM4.6.02)
--	For NG-PON2 - NOT SUPPORTED as of ISAM5.2
--  
-- *********************************************

gponPonOntSwDownldStatusTable  OBJECT-TYPE
	SYNTAX SEQUENCE OF GponPonOntSwDownldStatusEntry
	ACCESS	not-accessible
	STATUS	mandatory
	::= { gponOntSwGroup 6 }

gponPonOntSwDownldStatusEntry  OBJECT-TYPE
	SYNTAX 	GponPonOntSwDownldStatusEntry
	ACCESS	not-accessible
	STATUS	mandatory
	INDEX	{ gponPonOntSwDownldStatusIndex }
	::= { gponPonOntSwDownldStatusTable 1 }

GponPonOntSwDownldStatusEntry ::= SEQUENCE {
	gponPonOntSwDownldStatusIndex			IfIndex,
	gponPonOntSwDownldStatus	OCTET STRING,
	gponPonOntCfgFile1DownldStatus	OCTET STRING,
	gponPonOntCfgFile2DownldStatus	OCTET STRING
}

gponPonOntSwDownldStatusIndex  OBJECT-TYPE
	SYNTAX 	IfIndex
	ACCESS	read-only
	STATUS	mandatory
	DESCRIPTION 
		"Each row is indexed by the ifIndex of the PON.  "
	::= { gponPonOntSwDownldStatusEntry 1 }


gponPonOntSwDownldStatus  OBJECT-TYPE
	SYNTAX 	OCTET STRING (SIZE(512))
	ACCESS	read-only
	STATUS	mandatory
	DESCRIPTION 
           		" Attribute construction is as follows: 
		  4 bytes (32 bits) per planned (or potentially plan-able) ONT per PON.  So low-order
		  4 bytes represent ONT number 1 on PON, and high-order 4 bytes represent ONT number
		  128 on PON.

		  Each 32-bit ONT chunk is a bit-map of current ONT download status conditions, and multiple
		  conditions can be simultaneously present.  For example, an ONT may have a Software Version
		  Mismatch condition concurrent with the File Not Found reason.

           		 In following descriptions, Bit 1 position is defined as the high-order left-most and Bit 32 position is 
		 defined as  the low-order, right-most. The bit positions and meanings are as follows:

           		 All Bits Zero (OFF) = ONT is Planned, OLT is in-contact with it, no download activity is pending or ongoing,
				    and system is not in some erroneous state due to download activity.
		 Bit 1 ON = ONT is NOT Planned.  All other bits are inconsequential when this bit is set (and if set, the 
		       	    NE should have all other bits set to 0).  
		 Bit 2 ON =  ONT is INACTIVE (mirrors INACT alarm condition, although OLT may be suppressing
			      an actual INACT alarm ). 
		 Bit 3 ON =  Last known Planned Software Version was NOT OK (i.e. Planned did not equal
			      Active).  This bit only has relevance when Bit 2 is ON (i.e. when ONT is inactive).
		 Bit 4 ON =  Last known Download Software Version was NOT OK (i.e. Download did not equal
			      Active or Passive).  This bit only has relevance when Bit 2 is ON (i.e. when ONT is inactive).
		 Bit 5 ON =  Download activity In-Progress (mirrors current SWDLIP alarm).  
		 Bit 6 ON =  NT/LT file transfer activity In-Progress. 
		 Bit 7 ON =  OMCI file transfer activity In-Progress. 
		 Bit 8 ON =  ONT flash-write activity In-Progress.
		 Bit 9 ON =  ONT software activation In-Progress.
		 Bit 10 ON =  NT/LT file transfer failure.
		 Bit 11 ON =  OMCI file transfer failure.
		 Bit 12 ON =  ONT flash-write failure.
		 Bit 13 ON =  ONT software activation failure (mirrors current SWACTFAIL alarm).
		 Bit 14 ON =  Download File-Not-Found (mirrors current SWDLFILE alarm).
		 Bit 15 ON =  Entry match not found in ONT Software Version Control Table
			      (mirrors SWVERCTLERR alarm introduced in FGU4.6).
		 Bit 16 ON =  Software Version Mismatch (mirrors current SWVER alarm).
		 Bit 17 ON =  Software Download Failure (mirrors current SWDLFAIL alarm).
		 Bit 18 ON = DELAYACTIVATE activity is Pending. (Bit SUPPORTED as of ISAM5.0)
		 Bit 19 ON = Download activity is Pending. (Bit NOT SUPPORTED as of ISAM5.2)
		 Bits 20 thru 32  = Undefined - Not Supported - and should be zero (OFF).

		 Default = Bit 1 ON (and Bits 2 thru 32 OFF) for each of the 128 ONT 4-byte chunks. 
			 Meaning that when PON is initially auto-created by NE, there are effectively
			 NO Planned ONTs on the PON.

		For ISAM 4.0.10 -> stays the same as latest FGU4.x, except OCTET size was increased to 512 
					in order to handle up to 128 ONTs per PON.
		For ISAM5.0, added SUPPORT for Bit 18.
		For ISAM5.2, added SUPPORT for Bit 19.

		For GPON - SUPPORTED as of ISAM5.2 
		For XG-PON1 - SUPPORTED as of ISAM4.6.02
		For NG-PON2 - NOT SUPPORTED as of ISAM5.2  "
        ::= { gponPonOntSwDownldStatusEntry 2 }


gponPonOntCfgFile1DownldStatus  OBJECT-TYPE
	SYNTAX 	OCTET STRING (SIZE(512))
	ACCESS	read-only
	STATUS	mandatory
	DESCRIPTION 
   	 " Attribute construction is as follows: 
		 4 bytes (32 bits) per planned (or potentially plan-able) ONT per PON.  So low-order
		 4 bytes represent ONT number 1 on PON, and high-order 4 bytes represent ONT number
		 128 on PON.

		 Each 32-bit ONT chunk is a bit-map of current ONT download status conditions, and multiple
		 conditions can be simultaneously present.  For example, an ONT may have a CfgFile1 Version
		 Mismatch condition concurrent with the File Not Found reason.

     		In following descriptions, Bit 1 position is defined as the high-order left-most and Bit 32 position is 
		 defined as  the low-order, right-most. The bit positions and meanings are as follows:

      		All Bits Zero (OFF) = ONT is Planned, OLT is in-contact with it, no download activity is pending or ongoing,
		  and system is not in some erroneous state due to download activity.
		  Bit 1 ON = ONT is NOT Planned.  All other bits are inconsequential when this bit is set (and if set, the 
		       	    NE should have all other bits set to 0).  
		  Bit 2 ON =  ONT is INACTIVE (mirrors INACT alarm condition, although OLT may be suppressing
			          an actual INACT alarm ). 
		  Bit 3 ON =  Last known Planned CfgFile1 Version was NOT OK (i.e. Planned did not equal
			          Active).  This bit only has relevance when Bit 2 is ON (i.e. when ONT is inactive).
		  Bit 4 ON =  Last known Download CfgFile1 Version was NOT OK (i.e. Download did not equal
			          Active or Passive).  This bit only has relevance when Bit 2 is ON (i.e. when ONT is inactive).
		  Bit 5 ON =  Download activity In-Progress (mirrors current CFG1DLIP alarm).  
		  Bit 6 ON =  NT/LT file transfer activity In-Progress. 
		  Bit 7 ON =  OMCI file transfer activity In-Progress. 
		  Bit 8 ON =  ONT flash-write activity In-Progress.
		  Bit 9 ON =  ONT software activation In-Progress.
		  Bit 10 ON =  NT/LT file transfer failure.
		  Bit 11 ON =  OMCI file transfer failure.
		  Bit 12 ON =  ONT flash-write failure.
		  Bit 13 ON =  ONT Cfg1File1 activation failure (mirrors current CFG1ACTFAIL alarm).
		  Bit 14 ON =  Download File-Not-Found (mirrors current CFG1DLFILE alarm).
		  Bit 15 ON =  Entry match not found in ONT Software Version Control Table
			            (mirrors CFG1VERCTLERR alarm).
		  Bit 16 ON =  CfgFile1 Version Mismatch (mirrors current CFG1VER alarm).
		  Bit 17 ON =  CfgFile1 Download Failure (mirrors current CFG1DLFAIL alarm).
      		  Bit 18 ON =  DELAYACTIVATE activity is Pending. (Bit NOT SUPPORTED for this attribute - always 0).
		  Bit 19 ON =  Download activity is Pending. (Bit introduced and NOT SUPPORTED as of ISAM5.2)
		  Bits 20 thru 32  = Undefined - Not Supported - and should be zero (OFF).

		 Default = Bit 1 ON (and Bits 2 thru 32 OFF) for each of the 128 ONT 4-byte chunks. 
			 Meaning that when PON is initially auto-created by NE, there are effectively
			 NO Planned ONTs on the PON.

    		Introduced in ISAM5.2 MIB

	For GPON - SUPPORTED as of ISAM5.2 
	For XG-PON1 - NOT SUPPORTED as of ISAM4.6.02
	For NG-PON2 - NOT SUPPORTED as of ISAM5.2  "
    
    ::= { gponPonOntSwDownldStatusEntry 3 }
    
gponPonOntCfgFile2DownldStatus  OBJECT-TYPE
	SYNTAX 	OCTET STRING (SIZE(512))
	ACCESS	read-only
	STATUS	mandatory
	DESCRIPTION 
   	 " Attribute construction is as follows: 
		 4 bytes (32 bits) per planned (or potentially plan-able) ONT per PON.  So low-order
		 4 bytes represent ONT number 1 on PON, and high-order 4 bytes represent ONT number
		 128 on PON.

		 Each 32-bit ONT chunk is a bit-map of current ONT download status conditions, and multiple
		 conditions can be simultaneously present.  For example, an ONT may have a CfgFile2 Version
		 Mismatch condition concurrent with the File Not Found reason.

     In following descriptions, Bit 1 position is defined as the high-order left-most and Bit 32 position is 
		 defined as  the low-order, right-most. The bit positions and meanings are as follows:

      		All Bits Zero (OFF) = ONT is Planned, OLT is in-contact with it, no download activity is pending or ongoing,
		  and system is not in some erroneous state due to download activity.
		  Bit 1 ON = ONT is NOT Planned.  All other bits are inconsequential when this bit is set (and if set, the 
		       	    NE should have all other bits set to 0).  
		  Bit 2 ON =  ONT is INACTIVE (mirrors INACT alarm condition, although OLT may be suppressing
			          an actual INACT alarm ). 
		  Bit 3 ON =  Last known Planned CfgFile2 Version was NOT OK (i.e. Planned did not equal
			          Active).  This bit only has relevance when Bit 2 is ON (i.e. when ONT is inactive).
		  Bit 4 ON =  Last known Download CfgFile2 Version was NOT OK (i.e. Download did not equal
			          Active or Passive).  This bit only has relevance when Bit 2 is ON (i.e. when ONT is inactive).
		  Bit 5 ON =  Download activity In-Progress (mirrors current CFG2DLIP alarm).  
		  Bit 6 ON =  NT/LT file transfer activity In-Progress. 
		  Bit 7 ON =  OMCI file transfer activity In-Progress. 
		  Bit 8 ON =  ONT flash-write activity In-Progress.
		  Bit 9 ON =  ONT software activation In-Progress.
		  Bit 10 ON =  NT/LT file transfer failure.
		  Bit 11 ON =  OMCI file transfer failure.
		  Bit 12 ON =  ONT flash-write failure.
		  Bit 13 ON =  ONT Cfg2File1 activation failure (mirrors current CFG2ACTFAIL alarm).
		  Bit 14 ON =  Download File-Not-Found (mirrors current CFG2DLFILE alarm).
		  Bit 15 ON =  Entry match not found in ONT Software Version Control Table
			            (mirrors CFG2VERCTLERR alarm).
		  Bit 16 ON =  CfgFile1 Version Mismatch (mirrors current CFG2VER alarm).
		  Bit 17 ON =  CfgFile1 Download Failure (mirrors current CFG2DLFAIL alarm).
      		  Bit 18 ON =  DELAYACTIVATE activity is Pending. (Bit NOT SUPPORTED for this attribute - always 0).
		  Bit 19 ON =  Download activity is Pending. (Bit introduced and NOT SUPPORTED as of ISAM5.2)
		  Bits 20 thru 32  = Undefined - Not Supported - and should be zero (OFF).

		 Default = Bit 1 ON (and Bits 2 thru 32 OFF) for each of the 128 ONT 4-byte chunks. 
			 Meaning that when PON is initially auto-created by NE, there are effectively

			 NO Planned ONTs on the PON.
    		Introduced in ISAM5.2 MIB

	For GPON - SUPPORTED as of ISAM5.2 
	For XG-PON1 - NOT SUPPORTED as of ISAM4.6.02
	For NG-PON2 - NOT SUPPORTED as of ISAM5.2  "
    
    ::= { gponPonOntSwDownldStatusEntry 4 }    

-- *********************************************
--
-- GPON ONT PING TEST TABLE
--
-- This is a new table beginning with FG4.7.
-- This table contains a row for each provisioned IP stack on an ONT.
-- NOTE: As of FGU4.7, an ONT IP stack is tightly coupled with the VoIP service
-- (can't have one without the other).  So until we make management of IP stack
-- separable from VoIP, this ping table only applies to VoIP IP stack (i.e. uses VoIP
-- GEM ports, VoIP VLAN, VoIP PBits, etc). Rows are created/deleted automatically by the 
-- OLT agent in a one-to-one association with creation/deletion of a VoIP Service. 
--
--	For GPON - NOT SUPPORTED as of ISAM4.0.10
--	For XG-PON1 - NOT SUPPORTED as of ISAM4.6.02
--	For NG-PON2 - NOT SUPPORTED as of ISAM5.2
--
--
-- *********************************************

gponOntPingTestTable  OBJECT-TYPE
	SYNTAX SEQUENCE OF GponOntPingTestEntry
	ACCESS	not-accessible
	STATUS	mandatory
	::= { gponOntIpGroup 1 }


gponOntPingTestEntry  OBJECT-TYPE
	SYNTAX 	GponOntPingTestEntry
	ACCESS	not-accessible
	STATUS	mandatory
	INDEX	{ gponOntPingTestOntIndex,
		   gponOntPingTestIpStackIndex }
	::= { gponOntPingTestTable 1 }

GponOntPingTestEntry ::= SEQUENCE {
	gponOntPingTestOntIndex		IfIndex,
	gponOntPingTestIpStackIndex	IfIndex,
	gponOntPingTestMode		INTEGER,
	gponOntPingTestNumberToAttempt	INTEGER,
	gponOntPingTestExplicitIpAddress	IpAddress,
	gponOntPingTestNetworkAddress	DisplayString,
	gponOntPingTestCmd		INTEGER,
	gponOntPingTestNumberAttempted	INTEGER,
	gponOntPingTestNumberReplied	INTEGER,
	gponOntPingTestMaximumDelay	INTEGER,
	gponOntPingTestMinimumDelay	INTEGER,
	gponOntPingTestAddressPinged	IpAddress
}


gponOntPingTestOntIndex  OBJECT-TYPE
	SYNTAX 	IfIndex
	ACCESS	read-only
	STATUS	mandatory
	DESCRIPTION 
		"Each row is indexed by the ifIndex of the ONT

		For ISAM 4.0.10 -> this attribute is NOT SUPPORTED.  "
	::= { gponOntPingTestEntry 1 }


gponOntPingTestIpStackIndex  OBJECT-TYPE
	SYNTAX 	IfIndex
	ACCESS	read-only
	STATUS	mandatory
	DESCRIPTION 
		"Each row is also indexed by the number of the IP stack
		 on the ONT.  As of FGU4.7, this index is 1 and only 1.

		For ISAM 4.0.10 -> this attribute is NOT SUPPORTED.  "
	::= { gponOntPingTestEntry 2 }



gponOntPingTestMode  OBJECT-TYPE
	SYNTAX 	INTEGER
	ACCESS	read-write
	STATUS	mandatory
	DESCRIPTION 
		" Indicates whether ping is for explicit IP address or 
		  a network address that requires translation into an IP address.
		  actual test is requested):

		  0 = explicit IP address
		  1 = network address

		  Default = 0 = explicit IP address.

		For ISAM 4.0.10 -> this attribute is NOT SUPPORTED. "
	::= { gponOntPingTestEntry 3 }


gponOntPingTestNumberToAttempt  OBJECT-TYPE
	SYNTAX 	INTEGER 
	ACCESS	read-write
	STATUS	mandatory
	DESCRIPTION 
		" Indicates the number of ping attemps the manager desires.
		
		  For FGU4.7, the range is 0 to 5.
		  
		  The value 0 has the special meaning 'ONT vendor determined' - this value
		  is specifiable to be compatible with standard OMCI.  For ALU ONTs, this
		  value 0 is equavalent to the value 1 (i.e. a single ping attempt). 

		  No Default - value must be specified by manager.

		For ISAM 4.0.10 -> this attribute is NOT SUPPORTED.  "
	::= { gponOntPingTestEntry 4 }


gponOntPingTestExplicitIpAddress  OBJECT-TYPE
	SYNTAX 	IpAddress
	ACCESS	read-write
	STATUS	mandatory
	DESCRIPTION 
		" The explicit IP address to where the ping should be directed.

		  VALIDATION:  The OLT should prohibit entry of the 
		  following range of IP addresses:
		  224.0.0.0 to 239.255.255.255   (multicast)
    		  127.0.0.0 to 127.255.255.255   (loopback)
		  255.255.255.255 (broadcast)

		  This attribute only has relevance if gponOntPingTestMode = 0 = explicit IP address.

		  Default = 0.0.0.0

		For ISAM 4.0.10 -> this attribute is NOT SUPPORTED.   "
	::= { gponOntPingTestEntry 5 }

gponOntPingTestNetworkAddress OBJECT-TYPE 
	SYNTAX 	DisplayString (SIZE(0..100))
	ACCESS	read-write
	STATUS	mandatory
	DESCRIPTION 
		"This is a textual string that contains an address.
		 This string can represent a Fully Qualified Domain
		 Name (FQDN), or an IP Address (in dot notation), or other formats
		 parseable by the ONT.

		 Default - null string.

		For ISAM 4.0.10 -> this attribute is NOT SUPPORTED.   "
	::= { gponOntPingTestEntry 6 }


gponOntPingTestCmd  OBJECT-TYPE
	SYNTAX 	INTEGER 
	ACCESS	read-write
	STATUS	mandatory
	DESCRIPTION 
		" Manager is only permitted to SET this attribute
		 to (1), indicating desire to execute ONT ping test.
		 Thereafter, manager issues SNMP GET to determine
		 status/result of the ping test. Agent changes
		 attribute value accordingly as follows:
		 0 - This is the initial default value, meaning an ONT ping test
		          has never been executed on this ONT IP stack since initialization.
		 1 - Only value settable by manager (to initiate test)  
		 2 - meaning test is in progress.
		 3 - meaning test failed because ONT failed
		       to respond within reasonable time.
		 4 - meaning test has completed execution.
		 5 - meaning OLT didn't issue the command to ONT.
		 6 - meaning ONT rejected the test command for some reason
		      (e.g. OMCI reject because ONT doesn't implement this test).
		 7 - meaning test failed because ONT could NOT parse the network address.

		Manager must read results in 
  		gponOntPingTestNumberAttempted, gponOntPingTestNumberReplied, 
		gponOntPingTestMinimumDelay, gponOntPingTestMaximumDelay,
		and gponOntPingTestAddressPinged 
		attributes to discern the specifics of the actual ping test results.

		Default = 0 

		For ISAM 4.0.10 -> this attribute is NOT SUPPORTED. "
	::= { gponOntPingTestEntry 7 }

gponOntPingTestNumberAttempted  OBJECT-TYPE
	SYNTAX 	INTEGER 
	ACCESS	read-only
	STATUS	mandatory
	DESCRIPTION 
		" Indicates the number of pings attempted by ONT.
		
		  For FGU4.7, the range is 0 to 5.
		  
		  Default = 0 

		For ISAM 4.0.10 -> this attribute is NOT SUPPORTED. "
	::= { gponOntPingTestEntry 8 }

gponOntPingTestNumberReplied  OBJECT-TYPE
	SYNTAX 	INTEGER 
	ACCESS	read-only
	STATUS	mandatory
	DESCRIPTION 
		" Indicates the number of successful ping replies received by ONT.
		
		  For FGU4.7, the range is 0 to 5.
		  
		  Default = 0 

		For ISAM 4.0.10 -> this attribute is NOT SUPPORTED. "
	::= { gponOntPingTestEntry 9 }

gponOntPingTestMaximumDelay  OBJECT-TYPE
	SYNTAX 	INTEGER 
	ACCESS	read-only
	STATUS	mandatory
	DESCRIPTION 
		" In relation to all pings attempted for the ping test, this attribute indicates the maximum delay 
		  between a successful ping transmit/response exchange. 

		   From this GPON MIB perspective, valid values are 0 msecs to +65535 msecs
		   (in 1 msec increments).  This is represented by the INTEGER range:
		   0 to +65535.  

		   From an OMCI perspective, the attribute is a 16-bit measurement of response delay, 
		   expressed in ms.  And the special value 0xFFFF means a lost response.	   

		  NOTE: The 0xFFFF value (MIB value +65535) will be used by OLT for any test where not even a
		  single successful ping transmit/response could be exchanged.  This includes cases where 
		  OLT-to-ONT had communication issues or where ONT-to-ping-destination had communication
		  issues.

		  Default = 0xFFFF = 65535.

		For ISAM 4.0.10 -> this attribute is NOT SUPPORTED.  "
	::= { gponOntPingTestEntry 10 }

gponOntPingTestMinimumDelay  OBJECT-TYPE
	SYNTAX 	INTEGER 
	ACCESS	read-only
	STATUS	mandatory
	DESCRIPTION 
		" In relation to all pings attempted for the ping test, this attribute indicates the minimum delay 
		  between a successful ping transmit/response exchange. 

		   From this GPON MIB perspective, valid values are 0 msecs to +65535 msecs
		   (in 1 msec increments).  This is represented by the INTEGER range:
		   0 to +65535.  

		   From an OMCI perspective, the attribute is a 16-bit measurement of response delay, 
		   expressed in ms.  And the special value 0xFFFF means a lost response.	   

		  NOTE: The 0xFFFF value (MIB value +65535) will be used by OLT for any test where not even a
		  single successful ping transmit/response could be exchanged.  This includes cases where 
		  OLT-to-ONT had communication issues or where ONT-to-ping-destination had communication
		  issues.

		  Default = 0xFFFF = 65535.

		For ISAM 4.0.10 -> this attribute is NOT SUPPORTED.  "
	::= { gponOntPingTestEntry 11 }

gponOntPingTestAddressPinged  OBJECT-TYPE
	SYNTAX 	IpAddress
	ACCESS	read-only
	STATUS	mandatory
	DESCRIPTION 
		" The explicit IP address that was actually pinged during the test.

		  Default = 0.0.0.0 

		For ISAM 4.0.10 -> stays the same as latest FGU4.x  "
	::= { gponOntPingTestEntry 12 }

-- *********************************************
--
-- GPON ONT IP HOST TABLE
--
-- This is a new table beginning with ISAM4.2. 
-- It is only SUPPORTED beginning with ISAM4.2.02 release.
--
--
-- This table contains configuration information for an IP stack on the ONT.
-- From an OMCI standpoint, it maps primarily to the IP Host Config Data ME.
-- From an OMCI standpoint, it is implicit that creation of a row in this table also
-- causes creation of Tcp/Udp ME (designated as UDP port 68).
--
-- Prior to ISAM4.4, this table was only used for standard VoIP service. For standard VoIP service, rows in this table use the same ifIndex as the 
-- Virtual UNI that is auto-created in the IFM MIB (stemming from appropriate setting of bponOntVoipCapability attribute in bponOntTable).
--
-- As of ISAM4.4, if bponOntIPHCCapability attribute in bponOntTable is set to SUPPORTED then rows in this table
-- can also use the same ifIndex that corresponds to a VLAN.PORT in the IFM MIB.
--  
-- As of ISAM4.4, the only relevant usage in this manner (i.e. VLAN.PORT) is for ONT SNMP agent service that uses IP service explicitly
-- configured via this MIB,  Such association is conveyed via corresponding ifIndex value in gponSnmpIpServiceIPHC attribute in gponSnmpIpServiceTable.
--
-- As of ISAM4.6.01, the VLAN.PORT style usage is also relevant for L3 CES psuedowire service (since an IpHost instance is necessary for such service).
-- For such L3 CES service, this association is inferred between gponCesServiceVlanPointer attribute in gponCesServiceTable and VLAN.PORT ifIndex 
-- style usage in this gponOntIpHostTable.
--
-- VALIDATION:  As of ISAM4.4, a specific ONT can have at most a single row represented in this table.  Thus, for a specific ONT there
--	can be no conflict regarding the usage format of the ifIndex.
--
-- VALIDATION:  Regarding VoIP for a specific ONT, creation of a row in this table must be MUTUALLY EXCLUSIVE
-- 	with creation of a row in gponOntVoipServiceTable that would use same ifIndex in Interface MIB 
--	(i.e. either legacy Voip or standard Voip - but not both). 
--
-- VALIDATION:  As of ISAM4.4, for a specific ONT, cannot configure both legacy VoIP service and SNMP agent service that uses IP service 
--	explicitly configured in this MIB.
--
-- VALIDATION:  As of ISAM4.6.01, ALU is building an ONT that supports L3 CES pseudowire service.  This ONT does NOT support VoIP service of
--	of any type and does NOT support ONT SNMP agent service that uses an IpHost entry in this table.  So in the real world (so far), it is still
-- 	only necessary to support a single IpHost entry for a single ONT.  And it is also NOT necessary to support legacy VoIP along with
-- 	L3 CES pseudowire service in the same ONT.  But in theory, an ONT could support 'multiple IpHost instances' along with legacy VoIP, etc...
--	In order to step gradually:
--		As of ISAM4.6.01 sill can only configure a single entry in IpHost table for a single ONT.
--		As of ISAM4.6.01 cannot configure both legacy VoIP and any gponOntIpHostTable entry for the same ONT.
--
--
--
-- NOTE: To clarify terms used in other sections of this MIB, creation of a row in this table for VoIP
--	means that the user has decided to provision VoIP for this ONT using standard style
--	(i.e. NOT legacy style).  
--
--	For GPON - SUPPORTED as of ISAM4.2.02
--	For XG-PON1 - SUPPORTED as of ISAM4.6.02
--  For NG-PON2 - SUPPORTED as of ISAM5.4.01
--
-- *********************************************

gponOntIpHostTable  OBJECT-TYPE
	SYNTAX SEQUENCE OF GponOntIpHostEntry
	ACCESS	not-accessible
	STATUS	mandatory
	::= { gponOntIpGroup 2 }


gponOntIpHostEntry  OBJECT-TYPE
	SYNTAX 	GponOntIpHostEntry
	ACCESS	not-accessible
	STATUS	mandatory
	INDEX	{ ifIndex }
	::= { gponOntIpHostTable 1 }

GponOntIpHostEntry ::= SEQUENCE {
	gponOntIpHostRowStatus		RowStatus,
	gponOntIpHostDhcpInd		INTEGER,
	gponOntIpHostRespondToPingsInd	INTEGER,
	gponOntIpHostRespondToTraceRouteInd	INTEGER,
--	gponOntIpHostEnableStackInd	INTEGER,
	gponOntIpHostOntIdentifier		DisplayString,
	gponOntIpHostIpAddress		IpAddress,
	gponOntIpHostSubnetMask		IpAddress,
	gponOntIpHostDefaultGateway	IpAddress,
	gponOntIpHostPrimaryDns		IpAddress,
	gponOntIpHostSecondaryDns	IpAddress,
	gponOntIpHostVlanPointer		VlanIndex,
	gponOntIpHostDhcpDscpSetting	INTEGER,
	gponOntIpHostPmCollectInd		INTEGER,
	gponOntIpHostNumPMIntervals	INTEGER
}


gponOntIpHostRowStatus OBJECT-TYPE 
	SYNTAX	RowStatus
	ACCESS	read-write
	STATUS  mandatory
	DESCRIPTION
		"This object is used to create a new row or modify or
         		delete an existing row in this table.  "
::= {  gponOntIpHostEntry 2 }

gponOntIpHostDhcpInd  OBJECT-TYPE
	SYNTAX 	INTEGER
	ACCESS	read-write
	STATUS	mandatory
	DESCRIPTION 
		" Determines whether host should use DHCP to acquire IP address.

		  0 = Disable DHCP (default)
		  1 = Enable DHCP  

		  Modification is SUPPORTED - edit may be service-affecting. "
	::= { gponOntIpHostEntry 3 }

gponOntIpHostRespondToPingsInd  OBJECT-TYPE
	SYNTAX 	INTEGER
	ACCESS	read-write
	STATUS	mandatory
	DESCRIPTION 
		" Determines whether host should respond to pings.

		  0 = Disable (default)
		  1 = Enable 

		  Modification is SUPPORTED - edit may be service-affecting. "
	::= { gponOntIpHostEntry 4 }

gponOntIpHostRespondToTraceRouteInd  OBJECT-TYPE
	SYNTAX 	INTEGER
	ACCESS	read-write
	STATUS	mandatory
	DESCRIPTION 
		" Determines whether host should respond to traceroute messages.

		  0 = Disable (default)
		  1 = Enable 

		  Modification is SUPPORTED  - edit may be service-affecting. "
	::= { gponOntIpHostEntry 5 }

-- gponOntIpHostEnableStackInd  OBJECT-TYPE
--	SYNTAX 	INTEGER
--	ACCESS	read-write
--	STATUS	mandatory
--	DESCRIPTION 
--		" Determines whether host Ip stack should be enabled or disabled.
--
--		  NOTE:  Attribute not used - GPON will translate Admin State setting
--		  (from IFM MIB) into appropriate OMCI setting.
--
--		  0 = Disable (default)
--		  1 = Enable 
--
--		  Modification is SUPPORTED. "
--	::= { gponOntIpHostEntry 6 }

gponOntIpHostOntIdentifier  OBJECT-TYPE
	SYNTAX 	DisplayString
	ACCESS	read-write
	STATUS	mandatory
	DESCRIPTION 
		" Used to uniquely identify the ONT.  If set to a non-null value, this string
		  is used instead of the MAC Address in retrieving DHCP parameters.
		  Other than the null value, this field must be unique across all
		  ONTs in the network - so a specific OLT must ensure that it is
		  unique across all ONTs in its domain.

		  Maximum of 25 displayable characters.

		  Default = null string

		  Modification is SUPPORTED  - edit may be service-affecting. "
	::= { gponOntIpHostEntry 7 }

gponOntIpHostIpAddress  OBJECT-TYPE
	SYNTAX 	IpAddress
	ACCESS	read-write
	STATUS	mandatory
	DESCRIPTION 
		" Used to manually configure the address for IP host services
		  (when DHCP is disabled).

		  VALIDATION:  The OLT should prohibit entry of the 
		  following range of IP addresses:
		  224.0.0.0 to 239.255.255.255   (multicast)
    		  127.0.0.0 to 127.255.255.255   (loopback)
		  255.255.255.255 (broadcast)

		  Default = 0.0.0.0

		  Modification is SUPPORTED  - edit may be service-affecting. "
	::= { gponOntIpHostEntry 8 }

gponOntIpHostSubnetMask  OBJECT-TYPE
	SYNTAX 	IpAddress
	ACCESS	read-write
	STATUS	mandatory
	DESCRIPTION 
		" Used to manually configure the subnet mask for IP host services
		  (when DHCP is disabled).

		  VALIDATION:  The OLT should enforce following rules:
		  1) Non-contiguoius 1's are NOT permitted.
		  2) If there are any 1's at all, they must begin at the leftmost (i.e. most-significant) bit.
		  
		  Default = 0.0.0.0

		  Modification is SUPPORTED  - edit may be service-affecting. "
	::= { gponOntIpHostEntry 9 }

gponOntIpHostDefaultGateway  OBJECT-TYPE
	SYNTAX 	IpAddress
	ACCESS	read-write
	STATUS	mandatory
	DESCRIPTION 
		" Used to manually configure the default gateway address for IP host services
		  (when DHCP is disabled).

		  VALIDATION:  The OLT should prohibit entry of the 
		  following range of IP addresses:
		  224.0.0.0 to 239.255.255.255   (multicast)
    		  127.0.0.0 to 127.255.255.255   (loopback)
		  255.255.255.255 (broadcast)

		  Default = 0.0.0.0

		  Modification is SUPPORTED  - edit may be service-affecting. "
	::= { gponOntIpHostEntry 10 }

gponOntIpHostPrimaryDns  OBJECT-TYPE
	SYNTAX 	IpAddress
	ACCESS	read-write
	STATUS	mandatory
	DESCRIPTION 
		" Used to manually configure the address of the primary DNS server for IP host services
		  (when DHCP is disabled).

		  VALIDATION:  The OLT should prohibit entry of the 
		  following range of IP addresses:
		  224.0.0.0 to 239.255.255.255   (multicast)
    		  127.0.0.0 to 127.255.255.255   (loopback)
		  255.255.255.255 (broadcast)

		  Default = 0.0.0.0

		  Modification is SUPPORTED  - edit may be service-affecting. "
	::= { gponOntIpHostEntry 11 }

gponOntIpHostSecondaryDns  OBJECT-TYPE
	SYNTAX 	IpAddress
	ACCESS	read-write
	STATUS	mandatory
	DESCRIPTION 
		" Used to manually configure the address of the secondary DNS server for IP host services
		  (when DHCP is disabled).

		  VALIDATION:  The OLT should prohibit entry of the 
		  following range of IP addresses:
		  224.0.0.0 to 239.255.255.255   (multicast)
    		  127.0.0.0 to 127.255.255.255   (loopback)
		  255.255.255.255 (broadcast)

		  Default = 0.0.0.0

		  Modification is SUPPORTED  - edit may be service-affecting. "
	::= { gponOntIpHostEntry 12 }

gponOntIpHostVlanPointer OBJECT-TYPE 
	SYNTAX	VlanIndex
	ACCESS	read-write
	STATUS  mandatory
	DESCRIPTION

		"  This object is used to reference the CVLAN and SVLAN association (in the 
		    VLAN subsystem) with which this service is associated. 

		 See other ALU proprietary MIBs and documentation for definition of VlanIndex structure.
		
		 When ifIndex format for table row represents Virtual UNI, then no default is permitted. Legitimate value 
		 must be supplied by manager.

		 When ifIndex format for table row represents VLAN.PORT, then default is 0.  

		 Modification is NOT permitted. "
::= { gponOntIpHostEntry 13 }

gponOntIpHostDhcpDscpSetting  OBJECT-TYPE
	SYNTAX 	INTEGER
	ACCESS	read-write
	STATUS	mandatory
	DESCRIPTION 
		" Specifies the value of the DSCP field of the IP header for DHCP packets.

		  Only the low order 6 bits are relevant - since that is
		  the size of the DSCP field in IP packets.

		  No default - must be supplied by manager.
 
		  Modification is SUPPORTED  - edit may be service-affecting. "
	::= {  gponOntIpHostEntry 14 }

gponOntIpHostPmCollectInd  OBJECT-TYPE
	SYNTAX 	INTEGER
	ACCESS	read-write
	STATUS	mandatory
	DESCRIPTION 
		" This indicates whether IP Host Performance Monitors
		   should be collected for this IP Host instance.
	
		  1 = PM collection enabled
		  2 = PM collection disabled

		 Default = 2 = disabled.   "
	::= { gponOntIpHostEntry 15 }

gponOntIpHostNumPMIntervals  OBJECT-TYPE
	SYNTAX 	INTEGER
	ACCESS	read-only
	STATUS	mandatory
	DESCRIPTION 
		" Indicates the number of rows currently present
		  in the gponIpHostIntervalTable.  This
		  is for convenience of the EMS, so that it can
		 quickly determine how many rows should be 
		 uploaded.   "
	::= { gponOntIpHostEntry 16 }


-- *********************************************
-- GPON  ONT IP HOST OPINFO TABLE
--
-- This is a new table beginning with ISAM4.2. 
-- It is only SUPPORTED beginning with ISAM4.2.02 release.
--
-- This table contains operational information for an IP stack on the ONT.
-- From an OMCI standpoint, it maps primarily to the IP Host Config Data ME.
--
-- The operational information is significant in that
-- each time it is requested, the OLT issues OMCI GET messages   
-- to obtain the latest information directly from the ONT.
-- A table row is created/deleted automatically by the OLT upon  
-- creation/deletion of an associated row in gponOntIpHostTable.
--
--	For GPON - SUPPORTED as of ISAM4.2.02
--	For XG-PON1 - SUPPORTED as of ISAM4.6.02
--  For NG-PON2 - SUPPORTED as of ISAM5.4.01
--
-- *********************************************

gponOntIpHostOpInfoTable OBJECT-TYPE
	SYNTAX	SEQUENCE OF GponOntIpHostOpInfoEntry
	ACCESS	not-accessible
	STATUS	mandatory
	DESCRIPTION
		"This table contains operational information for a specific IP Host, 
		 obtained directly from a specific ONT.  "
::= { gponOntIpGroup 3 }

gponOntIpHostOpInfoEntry OBJECT-TYPE
	SYNTAX 	GponOntIpHostOpInfoEntry
	ACCESS	not-accessible
	STATUS	mandatory
	DESCRIPTION
		"Rows of this table contain IP host information. "
	INDEX { ifIndex }

::= {gponOntIpHostOpInfoTable 1}

GponOntIpHostOpInfoEntry ::=
	SEQUENCE { 
		gponOntIpHostOpInfoMacAddress	MacAddress,
		gponOntIpHostOpInfoIpAddress	IpAddress,
		gponOntIpHostOpInfoSubnetMask	IpAddress,
		gponOntIpHostOpInfoDefaultGateway	IpAddress,
		gponOntIpHostOpInfoPrimaryDns	IpAddress,
		gponOntIpHostOpInfoSecondaryDns	IpAddress,
		gponOntIpHostOpInfoDomainName	DisplayString,
		gponOntIpHostOpInfoHostName	DisplayString
}


gponOntIpHostOpInfoMacAddress OBJECT-TYPE
	SYNTAX 	MacAddress
	ACCESS	read-only
	STATUS	mandatory
	DESCRIPTION 
		" Indicates the current MAC address used by this IP node.

		  Following values have special meanings:
		  00.00.00.00.00.00 (default) - means UNKNOWN (because OLT cannot communicate with ONT for OMCI discovery purposes).
		  00.00.00.00.00.01 - means that ONT does not support GET of this attribute."
::= { gponOntIpHostOpInfoEntry  2 }

gponOntIpHostOpInfoIpAddress OBJECT-TYPE
	SYNTAX 	IpAddress
	ACCESS	read-only
	STATUS	mandatory
	DESCRIPTION 
		" Indicates the current address for the IP host service.

		  Following values have special meanings:
		  0.0.0.0 - ONT reports this value if undefined (e.g. configured to acquire via DHCP, but DHCP was unavailable). 
		  0.0.0.1(default) - means UNKNOWN (because OLT cannot communicate with ONT for OMCI discovery purposes).  
		  0.0.0.2 - means that ONT does not support GET of this attribute."
::= { gponOntIpHostOpInfoEntry  3 }

gponOntIpHostOpInfoSubnetMask OBJECT-TYPE
	SYNTAX 	IpAddress
	ACCESS	read-only
	STATUS	mandatory
	DESCRIPTION 
		" Indicates the current subnet mask for the IP host service.

		  Following values have special meanings:
		  0.0.0.0 - ONT reports this value if undefined (e.g. configured to acquire via DHCP, but DHCP was unavailable). 
		  0.0.0.1(default) - means UNKNOWN (because OLT cannot communicate with ONT for OMCI discovery purposes).  
		  0.0.0.2 - means that ONT does not support GET of this attribute."
::= { gponOntIpHostOpInfoEntry  4 }

gponOntIpHostOpInfoDefaultGateway OBJECT-TYPE
	SYNTAX 	IpAddress
	ACCESS	read-only
	STATUS	mandatory
	DESCRIPTION 
		" Indicates the current default gateway address for the IP host service.

		  Following values have special meanings:
		  0.0.0.0 - ONT reports this value if undefined (e.g. configured to acquire via DHCP, but DHCP was unavailable). 
		  0.0.0.1(default) - means UNKNOWN (because OLT cannot communicate with ONT for OMCI discovery purposes).  
		  0.0.0.2 - means that ONT does not support GET of this attribute."
::= { gponOntIpHostOpInfoEntry  5 }

gponOntIpHostOpInfoPrimaryDns OBJECT-TYPE
	SYNTAX 	IpAddress
	ACCESS	read-only
	STATUS	mandatory
	DESCRIPTION 
		" Indicates the current address of the primary DNS serverfor the IP host service.

		  Following values have special meanings:
		  0.0.0.0 - ONT reports this value if undefined (e.g. configured to acquire via DHCP, but DHCP was unavailable). 
		  0.0.0.1(default) - means UNKNOWN (because OLT cannot communicate with ONT for OMCI discovery purposes).  
		  0.0.0.2 - means that ONT does not support GET of this attribute."
::= { gponOntIpHostOpInfoEntry  6 }

gponOntIpHostOpInfoSecondaryDns OBJECT-TYPE
	SYNTAX 	IpAddress
	ACCESS	read-only
	STATUS	mandatory
	DESCRIPTION 
		" Indicates the current address for the IP host service.

		  Following values have special meanings:
		  0.0.0.0 - ONT reports this value if undefined (e.g. configured to acquire via DHCP, but DHCP was unavailable). 
		  0.0.0.1(default) - means UNKNOWN (because OLT cannot communicate with ONT for OMCI discovery purposes).  
		  0.0.0.2 - means that ONT does not support GET of this attribute."
::= { gponOntIpHostOpInfoEntry  7 }

gponOntIpHostOpInfoDomainName OBJECT-TYPE
	SYNTAX 	DisplayString
	ACCESS	read-only
	STATUS	mandatory
	DESCRIPTION 
		" If DHCP indicates a domain name, it is contained in this attribute.

		  Maximum of 25 displayable characters.

		  Following values have special meanings:
		  null string - means ONT reported that no domain name received via DHCP.
		  string UNKNOWN (default) - means UNKNOWN (because OLT cannot communicate with ONT for OMCI discovery purposes).
		  string NOSUPPORT - means that ONT does not support GET of this attribute."
::= { gponOntIpHostOpInfoEntry  8 }

gponOntIpHostOpInfoHostName OBJECT-TYPE
	SYNTAX 	DisplayString
	ACCESS	read-only
	STATUS	mandatory
	DESCRIPTION 
		" If DHCP indicates a host name, it is contained in this attribute.

		  Maximum of 25 displayable characters.

		  Following values have special meanings:
		  null string - means ONT reported that no host name received via DHCP.
		  string UNKNOWN (default) - means UNKNOWN (because OLT cannot communicate with ONT for OMCI discovery purposes).
		  string NOSUPPORT - means that ONT does not support GET of this attribute."
::= { gponOntIpHostOpInfoEntry  9 }


-- *********************************************
--
-- GPON ONT IP HOST PING TEST TABLE
--
-- As of ISAM5.0, this table is SUPPORTED
--
--  Rows are created/deleted by the manager.  Rows may also be deleted
--  automatically by the system for various reasons (e.g. if row existence exceeds
--  a system timer).
--
-- NOTE: This table is indexed using ifIindex.  The ifIndex can only be the same as associated with rows
-- in gponVoipServiceTable or gponOntIpHostTable.
--
-- For cases where bponOntVoipCapability attribute in bponOntTable indicates either legacy VoIP or Standard VoIP
-- (regardless of the setting of bponOntIPHCCapability attribute in bponOntTable), the format of the 
-- related ifIndex in this table uses the same Virtual UNI Index as that used on the related VoIP row in either
-- gponVoipServiceTable or gponOntIpHostTable.
--
-- Otherwise, for cases where bponOntIPHCCapability attribute in bponOntTable indicates IPHC is ENABLED,
-- the format of the related ifIndex in this table uses the same VLAN.PORT ifIndex as that used on the related
-- IP Host row in the gponOntIpHostTable.
--
--	For GPON - SUPPORTED as of ISAM5.0
--	For XG-PON1 - NOT SUPPORTED as of ISAM4.6.02
--  For NG-PON2 - SUPPORTED as of ISAM5.4.01
--
-- *********************************************

gponOntIpHostPingTestTable  OBJECT-TYPE
	SYNTAX SEQUENCE OF GponOntIpHostPingTestEntry
	ACCESS	not-accessible
	STATUS	mandatory
	::= { gponOntIpGroup 4 }


gponOntIpHostPingTestEntry  OBJECT-TYPE
	SYNTAX 	GponOntIpHostPingTestEntry
	ACCESS	not-accessible
	STATUS	mandatory
	INDEX	{ ifIndex }
	::= { gponOntIpHostPingTestTable 1 }

GponOntIpHostPingTestEntry ::= SEQUENCE {
	gponOntIpHostPingTestRowStatus		RowStatus,
	gponOntIpHostPingTestTargetIpAddressType	InetAddressType,
	gponOntIpHostPingTestTargetIpAddress	InetAddress,
	gponOntIpHostPingTestAddressPointer	AsamProfilePointer,
	gponOntIpHostPingTestNumberToAttempt	INTEGER,
	gponOntIpHostPingTestCmd			INTEGER,
	gponOntIpHostPingTestNumberAttempted	INTEGER,
	gponOntIpHostPingTestNumberReplied	INTEGER,
	gponOntIpHostPingTestMaximumDelay	INTEGER,
	gponOntIpHostPingTestMinimumDelay		INTEGER,
	gponOntIpHostPingTestPingedIpAddressType	InetAddressType,
	gponOntIpHostPingTestPingedIpAddress	InetAddress

}

gponOntIpHostPingTestRowStatus OBJECT-TYPE 
	SYNTAX	RowStatus
	ACCESS	read-write
	STATUS  mandatory
	DESCRIPTION
		"This object is used to create or delete an existing row in this table.

	As of ISAM5.0, this attribute is SUPPORTED.  "
::= { gponOntIpHostPingTestEntry 1 }


gponOntIpHostPingTestTargetIpAddressType  OBJECT-TYPE
	SYNTAX 	InetAddressType
	ACCESS	read-write
	STATUS	mandatory
	DESCRIPTION 
		" Indicates the type of IP address in gponOntIpHostPingTestTargetIpAddress
		  attribute:

		ipv4(1), -  As of ISAM5.0 - SUPPORTED  (for OMCI purposes, equates to IPv4 explicit ping method)
		ipv6(2), - As of ISAM5.0 - NOT SUPPORTED
		ipv4z(3), - As of ISAM5.0 - NOT SUPPORTED
		ipv6z(4), - As of ISAM5.0 - NOT SUPPORTED
		dns(16) - As of ISAM5.0 - SUPPORTED  (for OMCI purposes, equates to extended ping method)

		  No Default - must be supplied with row creation.

	As of ISAM5.0, this attribute is SUPPORTED. "
	::= { gponOntIpHostPingTestEntry 2 }


gponOntIpHostPingTestTargetIpAddress  OBJECT-TYPE
	SYNTAX 	InetAddress
	ACCESS	read-write
	STATUS	mandatory
	DESCRIPTION 
		" This contains the target IP address of the ping.

		  The format must be consistent with gponOntIpHostPingTestTargetIpAddressType
		  attribute:

		  If IPv4(1) - then 4 most significant bytes must have format of typical IpAddress type,
		  and remainder must be null padded.
		  If IPv4(1) - OLT should prohibit entry of the following range of IP addresses:
		  224.0.0.0 to 239.255.255.255   (multicast)
    		  127.0.0.0 to 127.255.255.255   (loopback)
		  255.255.255.255 (broadcast)

		  If DNS(16) - then format must equate to what logically is DisplayString (SIZE (1..254)),
		  with unused portion null terminated.
		  If DNS(16) - then one or the other of this attribute
		  and gponOntIpHostPingTestAddressPointer must be null and the other must be non-null.

		  No Default - must be supplied with row creation.

	As of ISAM5.0, this attribute is SUPPORTED. "
	::= { gponOntIpHostPingTestEntry 3 }


gponOntIpHostPingTestAddressPointer OBJECT-TYPE 
	SYNTAX 	AsamProfilePointer
	ACCESS	read-write
	STATUS	mandatory
	DESCRIPTION 
		"This is a pointer to a row in gponOntUriProfileTable
		 that can represent a Fully Qualified Domain or an IP Address (in dot notation),
		 or other formats parseable by the ONT.

		This attribute only has relevance if gponOntIpHostPingTestTargetIpAddressType = DNS(16). 

		 If DNS(16) - then one or the other of this attribute
		 and gponOntIpHostPingTestTargetIpAddress must be null and the other must be non-null.

		 No Default - must be supplied with row creation.

	As of ISAM5.0, this attribute is SUPPORTED.   "
	::= { gponOntIpHostPingTestEntry 4 }


gponOntIpHostPingTestNumberToAttempt  OBJECT-TYPE
	SYNTAX 	INTEGER 
	ACCESS	read-write
	STATUS	mandatory
	DESCRIPTION 
		" Indicates the number of ping attemps the manager desires.
		
		  The range is 0 to 5.
		  
		  The value 0 has the special meaning 'ONT vendor determined' - this value
		  is specifiable to be compatible with standard OMCI.  For ALU ONTs, this
		  value 0 is equavalent to the value 1 (i.e. a single ping attempt). 

		  No Default - must be supplied with row creation.

	As of ISAM5.0, this attribute is SUPPORTED. "
	::= { gponOntIpHostPingTestEntry 5 }


gponOntIpHostPingTestCmd  OBJECT-TYPE
	SYNTAX 	INTEGER 
	ACCESS	read-write
	STATUS	mandatory
	DESCRIPTION 
		" Manager is only permitted to SET this attribute
		 to (1), indicating desire to execute ONT ping test.
		 Thereafter, manager issues SNMP GET to determine
		 status/result of the ping test. Agent changes
		 attribute value accordingly as follows:

		 1 - Only value settable by manager (to initiate test)  
		 2 - meaning test is in progress.
		 3 - meaning test failed because ONT failed
		       to respond within reasonable time.
		 4 - meaning test has completed execution.
		 5 - meaning OLT didn't issue the command to ONT.
		 6 - meaning ONT rejected the test command for some reason
		      (e.g. OMCI reject because ONT doesn't implement this test).
		 7 - meaning test failed because ONT could NOT parse the network address.

		Manager must read results in 
  		gponOntIpHostPingTestNumberAttempted, gponOntIpHostPingTestNumberReplied, 
		gponOntIpHostPingTestMinimumDelay, gponOntIpHostPingTestMaximumDelay,
		and gponOntIpHostPingTestAddressPinged 
		attributes to discern the specifics of the actual ping test results.

		Default = 1

	As of ISAM5.0, this attribute is SUPPORTED.  "
	::= { gponOntIpHostPingTestEntry 6 }

gponOntIpHostPingTestNumberAttempted  OBJECT-TYPE
	SYNTAX 	INTEGER 
	ACCESS	read-only
	STATUS	mandatory
	DESCRIPTION 
		" Indicates the number of pings attempted by ONT.
		
		  The range is 0 to 5.
		  
		  Default = 0

	As of ISAM5.0, this attribute is SUPPORTED.  "
	::= { gponOntIpHostPingTestEntry 7 }

gponOntIpHostPingTestNumberReplied  OBJECT-TYPE
	SYNTAX 	INTEGER 
	ACCESS	read-only
	STATUS	mandatory
	DESCRIPTION 
		" Indicates the number of successful ping replies received by ONT.
		
		  The range is 0 to 5.
		  
		  Default = 0 

	As of ISAM5.0, this attribute is SUPPORTED. "
	::= { gponOntIpHostPingTestEntry 8 }

gponOntIpHostPingTestMaximumDelay  OBJECT-TYPE
	SYNTAX 	INTEGER 
	ACCESS	read-only
	STATUS	mandatory
	DESCRIPTION 
		" In relation to all pings attempted for the ping test, this attribute indicates the maximum delay 
		  between a successful ping transmit/response exchange. 

		   From this GPON MIB perspective, valid values are 0 msecs to +65535 msecs
		   (in 1 msec increments).  This is represented by the INTEGER range:
		   0 to +65535.  

		   From an OMCI perspective, the attribute is a 16-bit measurement of response delay, 
		   expressed in ms.  And the special value 0xFFFF means a lost response.	   

		  NOTE: The 0xFFFF value (MIB value +65535) will be used by OLT for any test where not even a
		  single successful ping transmit/response could be exchanged.  This includes cases where 
		  OLT-to-ONT had communication issues or where ONT-to-ping-destination had communication
		  issues.

		  Default = 0xFFFF = 65535.

	As of ISAM5.0, this attribute is SUPPORTED.  "
	::= { gponOntIpHostPingTestEntry 9 }

gponOntIpHostPingTestMinimumDelay  OBJECT-TYPE
	SYNTAX 	INTEGER 
	ACCESS	read-only
	STATUS	mandatory
	DESCRIPTION 
		" In relation to all pings attempted for the ping test, this attribute indicates the minimum delay 
		  between a successful ping transmit/response exchange. 

		   From this GPON MIB perspective, valid values are 0 msecs to +65535 msecs
		   (in 1 msec increments).  This is represented by the INTEGER range:
		   0 to +65535.  

		   From an OMCI perspective, the attribute is a 16-bit measurement of response delay, 
		   expressed in ms.  And the special value 0xFFFF means a lost response.	   

		  NOTE: The 0xFFFF value (MIB value +65535) will be used by OLT for any test where not even a
		  single successful ping transmit/response could be exchanged.  This includes cases where 
		  OLT-to-ONT had communication issues or where ONT-to-ping-destination had communication
		  issues.

		  Default = 0xFFFF = 65535.

	As of ISAM5.0, this attribute is SUPPORTED.  "
	::= { gponOntIpHostPingTestEntry 10 }

gponOntIpHostPingTestPingedIpAddressType  OBJECT-TYPE
	SYNTAX 	InetAddressType
	ACCESS	read-only
	STATUS	mandatory
	DESCRIPTION 
		" Indicates the type of IP address in gponOntIpHostPingTestPingedIpAddress attribute.

		  This attribute only has relevance if gponOntIpHostPingTestTargetIpAddressType = DNS(16). 

		  As of ISAM5.0, the only SUPPORTED value is 1 = IPv4

		ipv4(1), -  As of ISAM5.0 - SUPPORTED 
		ipv6(2), - As of ISAM5.0 - NOT SUPPORTED

		Default = 1


	As of ISAM5.0, this attribute is SUPPORTED. "
	::= { gponOntIpHostPingTestEntry 11 }



gponOntIpHostPingTestPingedIpAddress  OBJECT-TYPE
	SYNTAX 	InetAddress
	ACCESS	read-only
	STATUS	mandatory
	DESCRIPTION 
		" The IP address that was actually pinged during the test.

		  This attribute only has relevance if gponOntIpHostPingTestTargetIpAddressType = DNS(16). 

		   If an IPv4 address was pinged, then the 4 most significant bytes contain the IPv4 address and the remainder bytes are zeroes.

		   If an IPv6 address was pinged, then the 16 most significant bytes contain the IPv6 address.
		   NOTE: As of ISAM5.0, display of IPv6 address is NOT SUPPORTED

		   If network address was unresolvable, then all bytes are zeroes.

		  Default = all zeroes

	As of ISAM5.0, this attribute is SUPPORTED (only for IPv4 addressing).  "
	::= { gponOntIpHostPingTestEntry 12 }



-- *********************************************
--
-- GPON IP HOST PERFORMANCE MONITOR CURRENT INTERVAL TABLE
--
-- This is a new table beginning with ISAM4.2.
-- It is only SUPPORTED beginning with ISAM4.2.02 release.
--
-- This current interval table contains various IP Host data during the current 15 minute interval 
-- of operation.  
--
-- An instance of this table is auto-created/deleted in accordance with the 
-- 'IP Host PM Collect Indicator' setting of the IP Host table.
--
-- For GETs of table attributes, the OLT must go directly to the ONT (via OMCI)
-- in order to acquire fresh current counts. 
--
--	For GPON - SUPPORTED as of ISAM4.2.02
--	For XG-PON1 - SUPPORTED as of ISAM4.6.02
--  For NG-PON2 - SUPPORTED as of ISAM5.4.01
-- 
-- *********************************************


gponIpHostCurrentIntervalTable  OBJECT-TYPE
	SYNTAX SEQUENCE OF GponIpHostCurrentIntervalEntry
	ACCESS	not-accessible
	STATUS	mandatory
	::= { gponOntIpGroup 5 }


gponIpHostCurrentIntervalEntry  OBJECT-TYPE
	SYNTAX 	GponIpHostCurrentIntervalEntry
	ACCESS	not-accessible
	STATUS	mandatory
	DESCRIPTION 
		"An entry in the gponIpHostCurrentIntervalTable  "
	INDEX { ifIndex }
-- this is the ifIndex of the IP Host UNI.
	::= { gponIpHostCurrentIntervalTable 1 }

GponIpHostCurrentIntervalEntry ::= SEQUENCE {
	gponIpHostCurrentIntervalValidInd			Boolean,
	gponIpHostCurrentIntervalIcmpErrors			Counter,
	gponIpHostCurrentIntervalDnsErrors		Counter,
	gponIpHostCurrentIntervalDhcpTimeouts			Counter,
	gponIpHostCurrentIntervalIpAddressConflicts		Counter,
	gponIpHostCurrentIntervalOutOfMemory			Counter,
	gponIpHostCurrentIntervalInternalError		Counter

}


gponIpHostCurrentIntervalValidInd  OBJECT-TYPE
	SYNTAX 	Boolean
	ACCESS	read-only
	STATUS	mandatory
	DESCRIPTION 
		"Indicates whether or not this CurrentInterval contains
		 valid PM counts. 

		 NOT SUPPORTED "
	::= { gponIpHostCurrentIntervalEntry 1 }

gponIpHostCurrentIntervalIcmpErrors  OBJECT-TYPE
	SYNTAX 	Counter
	ACCESS	read-only
	STATUS	mandatory
	DESCRIPTION 
		"A count of number of ICMP errors received. "
	::= { gponIpHostCurrentIntervalEntry 2 }

gponIpHostCurrentIntervalDnsErrors  OBJECT-TYPE
	SYNTAX 	Counter
	ACCESS	read-only
	STATUS	mandatory
	DESCRIPTION 
		"A count of number of DNS errors received. "
	::= { gponIpHostCurrentIntervalEntry 3 }

gponIpHostCurrentIntervalDhcpTimeouts  OBJECT-TYPE
	SYNTAX 	Counter
	ACCESS	read-only
	STATUS	mandatory
	DESCRIPTION 
		"A count of number of DHCP timeouts. "
	::= { gponIpHostCurrentIntervalEntry 4 }

gponIpHostCurrentIntervalIpAddressConflicts  OBJECT-TYPE
	SYNTAX 	Counter
	ACCESS	read-only
	STATUS	mandatory
	DESCRIPTION 
		"Attribute is incremented whenever ONT detects a conflicting IP address on the network.
		 A conflicting IP address is one that has the same value as the one currently assigned to the ONT. "
	::= { gponIpHostCurrentIntervalEntry 5 }

gponIpHostCurrentIntervalOutOfMemory  OBJECT-TYPE
	SYNTAX 	Counter
	ACCESS	read-only
	STATUS	mandatory
	DESCRIPTION 
		"Attribute is incremented whenever ONT detects an out of memory condition in the IP stack. "
	::= { gponIpHostCurrentIntervalEntry 6 }

gponIpHostCurrentIntervalInternalError  OBJECT-TYPE
	SYNTAX 	Counter
	ACCESS	read-only
	STATUS	mandatory
	DESCRIPTION 
		"Attribute is incremented whenever ONT detects an internal error condition
		  (such as a driver interface failure in the IP stack).  "
	::= { gponIpHostCurrentIntervalEntry 7 }


-- *********************************************
--
-- GPON IP HOST PERFORMANCE MONITOR INTERVAL TABLE
--
-- This is a new table beginning with ISAM4.2.
-- It is NOT SUPPORTED as of  ISAM4.2.02 release.
--
-- This interval table contains various IP Host data collected
-- over the previous 8 hours of operation.  The past 8 hours are
-- broken into 32 completed 15 minute intervals.  Each row in this table
-- represents one such interval associated with an IP Host.  
--
-- An instance of this table is auto-created/deleted in accordance with the 
-- 'IP Host PM Collect Indicator' setting of the IP Host table.
--
--	For GPON - NOT SUPPORTED as of ISAM4.2.02
--	For XG-PON1 - NOT SUPPORTED as of ISAM4.6.02
--  For NG-PON2 - SUPPORTED as of ISAM5.4.01
-- 
-- *********************************************


gponIpHostIntervalTable  OBJECT-TYPE
	SYNTAX SEQUENCE OF GponIpHostIntervalEntry
	ACCESS	not-accessible
	STATUS	mandatory
	::= { gponOntIpGroup 6 }


gponIpHostIntervalEntry  OBJECT-TYPE
	SYNTAX 	GponIpHostIntervalEntry
	ACCESS	not-accessible
	STATUS	mandatory
	DESCRIPTION 
		"An entry in the gponIpHostIntervalTable  "
	INDEX { ifIndex,
		gponIpHostIntervalNumber }
-- this is the ifIndex of the IP Host UNI.
	::= { gponIpHostIntervalTable 1 }

GponIpHostIntervalEntry ::= SEQUENCE {
	gponIpHostIntervalNumber			INTEGER,	
	gponIpHostIntervalValidInd			Boolean,
	gponIpHostIntervalIcmpErrors			Counter,
	gponIpHostIntervalDnsErrors		Counter,
	gponIpHostIntervalDhcpTimeouts			Counter,
	gponIpHostIntervalIpAddressConflicts		Counter,
	gponIpHostIntervalOutOfMemory			Counter,
	gponIpHostIntervalInternalError		Counter

}


gponIpHostIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.  "
	::= { gponIpHostIntervalEntry 1 }

gponIpHostIntervalValidInd  OBJECT-TYPE
	SYNTAX 	Boolean
	ACCESS	read-only
	STATUS	mandatory
	DESCRIPTION 
		"Indicates whether or not this CurrentInterval contains
		 valid PM counts. 

		 NOT SUPPORTED "
	::= { gponIpHostIntervalEntry 2 }

gponIpHostIntervalIcmpErrors  OBJECT-TYPE
	SYNTAX 	Counter
	ACCESS	read-only
	STATUS	mandatory
	DESCRIPTION 
		"A count of number of ICMP errors received. "
	::= { gponIpHostIntervalEntry 3 }

gponIpHostIntervalDnsErrors  OBJECT-TYPE
	SYNTAX 	Counter
	ACCESS	read-only
	STATUS	mandatory
	DESCRIPTION 
		"A count of number of DNS errors received. "
	::= { gponIpHostIntervalEntry 4 }

gponIpHostIntervalDhcpTimeouts  OBJECT-TYPE
	SYNTAX 	Counter
	ACCESS	read-only
	STATUS	mandatory
	DESCRIPTION 
		"A count of number of DHCP timeouts. "
	::= { gponIpHostIntervalEntry 5 }

gponIpHostIntervalIpAddressConflicts  OBJECT-TYPE
	SYNTAX 	Counter
	ACCESS	read-only
	STATUS	mandatory
	DESCRIPTION 
		"Attribute is incremented whenever ONT detects a conflicting IP address on the network.
		 A conflicting IP address is one that has the same value as the one currently assigned to the ONT. "
	::= { gponIpHostIntervalEntry 6 }

gponIpHostIntervalOutOfMemory  OBJECT-TYPE
	SYNTAX 	Counter
	ACCESS	read-only
	STATUS	mandatory
	DESCRIPTION 
		"Attribute is incremented whenever ONT detects an out of memory condition in the IP stack. "
	::= { gponIpHostIntervalEntry 7 }

gponIpHostIntervalInternalError  OBJECT-TYPE
	SYNTAX 	Counter
	ACCESS	read-only
	STATUS	mandatory
	DESCRIPTION 
		"Attribute is incremented whenever ONT detects an internal error condition
		  (such as a driver interface failure in the IP stack).  "
	::= { gponIpHostIntervalEntry 8 }



-- *********************************************
--
-- GPON VOIP CONFIGURATION TABLE
--
-- This is a new table beginning with ISAM4.2. 
-- It is only SUPPORTED beginning with ISAM4.2.02 release, when
-- VoIP provisioning style is standard (not legacy)
--
--
-- This table contains information regarding the method the ONT should use to configure VoIP.
-- From an OMCI standpoint, it maps primarily to the VoIP Configuration ME.
-- Rows are created/deleted by the manager, and use the same ifIndex as the IP Host UNI.
--
-- VALIDATION:  A row can only be created if  VoIP provisioning style is standard (not legacy).
-- VALIDATION: A row cannot be deleted if a corresponding row in gponOntMgcConfigTable or
--	gponOntSipConfigTable is provisioned for this ONT.
--
--	For GPON - SUPPORTED as of ISAM4.2.02
--	For XG-PON1 - SUPPORTED as of ISAM4.6.02
--  For NG-PON2 - SUPPORTED as of ISAM5.4.01
--
-- *********************************************

gponOntVoipConfigTable  OBJECT-TYPE
	SYNTAX SEQUENCE OF GponOntVoipConfigEntry
	ACCESS	not-accessible
	STATUS	mandatory
	::= { gponVoipGroup 1 }


gponOntVoipConfigEntry  OBJECT-TYPE
	SYNTAX 	GponOntVoipConfigEntry
	ACCESS	not-accessible
	STATUS	mandatory
	INDEX	{ ifIndex }
-- this is the ifIndex of the IP Host UNI.
	::= { gponOntVoipConfigTable 1 }

GponOntVoipConfigEntry ::= SEQUENCE {
	gponOntVoipConfigRowStatus		RowStatus,
	gponOntVoipConfigSignallingProtocol		INTEGER,
	gponOntVoipConfigMethod			INTEGER,
	gponOntVoipConfigSecureUriPointer		AsamProfilePointer,
	gponOntVoipConfigRetrieveProfileCmd		INTEGER
}


gponOntVoipConfigRowStatus OBJECT-TYPE 
	SYNTAX	RowStatus
	ACCESS	read-write
	STATUS  mandatory
	DESCRIPTION
		"This object is used to create a new row or modify or
         		delete an existing row in this table.  "
::= {  gponOntVoipConfigEntry 1 }

gponOntVoipConfigSignallingProtocol  OBJECT-TYPE
	SYNTAX 	INTEGER
	ACCESS	read-write
	STATUS	mandatory
	DESCRIPTION 
		" Specifies the signalling protocol to be used for VoIP configuration.

		  1 = SIP
		  2 = H248 

		  No default - must be provided by manager.

		  Modification is SUPPORTED (but only if no actual VoIP service is provisioned). "
	::= { gponOntVoipConfigEntry 2 }

gponOntVoipConfigMethod  OBJECT-TYPE
	SYNTAX 	INTEGER
	ACCESS	read-write
	STATUS	mandatory
	DESCRIPTION 
		" Specifies the VoIP configuration method that should be used by ONT.

		  1 = OMCI (default)
		  2 = Configuration file retrieval
		  3 = TR69 (not supported as of ISAM4.2.02)
		  4 = SIPPING Framework (not supported as of ISAM4.2.02)

		  Modification is SUPPORTED (but only if no actual VoIP service is provisioned). "
	::= { gponOntVoipConfigEntry 3 }

gponOntVoipConfigSecureUriPointer  OBJECT-TYPE
	SYNTAX 	AsamProfilePointer
	ACCESS	read-write
	STATUS	mandatory
	DESCRIPTION 
		"This attribute points to a row in gponSecureUriProfileTable

		 Value 0 (meaning none specified) is permitted.  
		 This attribute is only relevant if VoipConfigMethod is NOT via OMCI.
		 If ConfigMethod is via OMCI, then this pointer must be 0.

		 NOTE:  If an actual file needs to be retrieved, the URI
		 component of the SecureUriProfile should contain full pathname of file.
		 Default = 0.

		Modification is permitted.- even after VoIP service has been provisioned.  "
	::= { gponOntVoipConfigEntry 4 }

gponOntVoipConfigRetrieveProfileCmd  OBJECT-TYPE
	SYNTAX 	INTEGER
	ACCESS	read-write
	STATUS	mandatory
	DESCRIPTION 
		" Attribute provides a means by which the ONT may be notified that a new VoIP profile 
		  should be retrieved. By setting this attribute, the OLT triggers the ONU to retrieve a new profile.

		  This command attribute is only relevant if VoipConfigMethod is NOT via OMCI.

		  This attribute allows the manager to force the ONT to retrieve a new VoIP config profile.
		  The only valid value is 1.  After the manager sets the value to 1, the OLT issues
		   the appropriate OMCI message to the ONT.  
		    
		   Attribute values are as follows:
		   1 - Retrieve new config profile

		   The GPON agent uses internal mechanisms to keep track
		   that a single command is implemented a single time. "
	::= { gponOntVoipConfigEntry 5 }


-- *********************************************
-- GPON  ONT VOIP CONFIGURATION OPINFO TABLE
--
-- This is a new table beginning with ISAM4.2. 
-- It is only SUPPORTED beginning with ISAM4.2.02 release, when
-- VoIP provisioning style is standard (not legacy)
--
--
-- This table contains operational information regarding VoIP configuration for an ONT.
-- From an OMCI standpoint, it maps primarily to the VoIP Configuration ME.
--
-- The operational information is significant in that
-- each time it is requested, the OLT issues OMCI GET messages   
-- to obtain the latest information directly from the ONT.
-- A table row is created/deleted automatically by the OLT upon  
-- creation/deletion of the IP Host UNI (i.e.a row in gponOntIpHostTable).
--
--	For GPON - SUPPORTED as of ISAM4.2.02
--	For XG-PON1 - SUPPORTED as of ISAM4.6.02
--  For NG-PON2 - SUPPORTED as of ISAM5.4.01
--
-- *********************************************

gponOntVoipConfigOpInfoTable OBJECT-TYPE
	SYNTAX	SEQUENCE OF GponOntVoipConfigOpInfoEntry
	ACCESS	not-accessible
	STATUS	mandatory
	DESCRIPTION
		"This table contains operational information for a specific ONT, 
		 obtained directly from a specific ONT.  "
::= { gponVoipGroup 2 }

gponOntVoipConfigOpInfoEntry OBJECT-TYPE
	SYNTAX 	GponOntVoipConfigOpInfoEntry
	ACCESS	not-accessible
	STATUS	mandatory
	DESCRIPTION
		"Rows of this table contain ONT VoIP config information. "
	INDEX { ifIndex }
-- this is the ifIndex of the IP Host UNI.

::= {gponOntVoipConfigOpInfoTable 1}

GponOntVoipConfigOpInfoEntry ::=
	SEQUENCE { 
		gponOntVoipConfigOpInfoAvailSigProtocols	OCTET STRING,
		gponOntVoipConfigOpInfoAvailConfigMethods	OCTET STRING,
		gponOntVoipConfigOpInfoStatus		INTEGER,
		gponOntVoipConfigOpInfoProfileVersion	DisplayString
}


gponOntVoipConfigOpInfoAvailSigProtocols OBJECT-TYPE
	SYNTAX 	OCTET STRING (SIZE(2))
	ACCESS	read-only
	STATUS	mandatory
	DESCRIPTION 
		" Indicates the available VoIP siganlling protocols supported by this ONT.
		  This is a bitmap where Bit 1 = LSB and Bit 16 = MSB.  The 8 least significant
		  bits map directly to OMCI attribute (i.e. available signalling protocols).  The 8
		  most significant bits are populated by the OLT agent to convey extra information
		  for the manager (for user interface).

		  Bit meanings are as follows:

		  Bit 1 -	0 means SIP NOT SUPPORTED.
			1 means SIP SUPPORTED.
		  Bit 2 -	0 means H248 NOT SUPPORTED.
			1 means H248 SUPPORTED.
		  Bit 3 -	0 means MGCP NOT SUPPORTED.
			1 means MGCP SUPPORTED.
		  Bits 4..8 - no meaning in ISAM4.2 (ignore)
		  Bit 9 -	0 means this response came directly from the ONT
			1 means UNKNOWN (because OLT cannot communicate with ONT for OMCI discovery purposes).
		  Bit 10 -	0 means ONT supports GET of this attribute
			1 means that ONT does NOT support GET of this attribute.
		  Bits 11..16 - no meaning in ISAM4.2 (ignore) 

		  Default = all bits zero except Bit 9 equals 1 (i.e. UNKNOWN). "
::= { gponOntVoipConfigOpInfoEntry  1 }

gponOntVoipConfigOpInfoAvailConfigMethods OBJECT-TYPE
	SYNTAX 	OCTET STRING (SIZE(5))
	ACCESS	read-only
	STATUS	mandatory
	DESCRIPTION 
		" Indicates the available VoIP configuration methods supported by this ONT.
		  This is a bitmap where Bit 1 = LSB and Bit 40 = MSB.  The 32 least significant
		  bits map directly to OMCI attribute (i.e. available VoIP configuration methods).  The 8
		  most significant bits are populated by the OLT agent to convey extra information
		  for the manager (for user interface).

		  Bit meanings are as follows:

		  Bit 1 -	0 means config via OMCI NOT SUPPORTED.
			1 means config via OMCI SUPPORTED.
		  Bit 2 -	0 means config via file retrieval NOT SUPPORTED.
			1 means config via file retrieval SUPPORTED.
		  Bit 3 -	0 means config via TR69 (DSL Forum) NOT SUPPORTED.
			1 means config via TR69 (DSL Forum) SUPPORTED.
		  Bit 4 -	0 means config via SIPPING (IETF) NOT SUPPORTED.
			1 means config via SIPPING (IETF) SUPPORTED.
		  Bits 5..24 - reserved for future standardization - no meaning in ISAM4.2 (ignore)
		  Bit 25 -	0 means ALU proprietary hybrid NOT SUPPORTED.
			1 means ALU proprietary hybrid SUPPORTED.
		  Bits 26..32 - no meaning in ISAM4.2 (ignore) 
		  Bit 33 -	0 means this response came directly from the ONT
			1 means UNKNOWN (because OLT cannot communicate with ONT for OMCI discovery purposes).
		  Bit 34 -	0 means ONT supports GET of this attribute
			1 means that ONT does NOT support GET of this attribute.
		  Bits 35..40 - no meaning in ISAM4.2 (ignore)  

		  Default = all bits zero except Bit 33 equals 1 (i.e. UNKNOWN). "
::= { gponOntVoipConfigOpInfoEntry  2 }

gponOntVoipConfigOpInfoStatus OBJECT-TYPE
	SYNTAX 	INTEGER
	ACCESS	read-only
	STATUS	mandatory
	DESCRIPTION 
		" Indicates the retrieval status of the VoIP service configuration.
		  This is a bitmap where Bit 1 = LSB and Bit 40 = MSB.  The 32 least significant
		  bits map directly to OMCI attribute (i.e. available VoIP configuration methods).  The 8
		  most significant bits are populated by the OLT agent to convey extra information
		  for the manager (for user interface).

		  0 = Inactive - ONT reported that configuration retrieval has not been attempted.
		  1 = Active - ONT reported that configuration has been retrieved.
		  2 = Initializing - ONT reported that configuration is now being retrieved.
		  3 = Fault - ONT reported that configuration retrieval process has failed.
		  254 = UNKNOWN - (because OLT cannot communicate with ONT for OMCI discovery purposes).
		  255 = NOSUPPORT - means that ONT does NOT support GET of this attribute.

		  Default = 254 = UNKNOWN - (because OLT cannot communicate with ONT for OMCI discovery purposes). "
::= { gponOntVoipConfigOpInfoEntry  3 }


gponOntVoipConfigOpInfoProfileVersion OBJECT-TYPE
	SYNTAX 	DisplayString
	ACCESS	read-only
	STATUS	mandatory
	DESCRIPTION 
		" Identifies the version of the last retrieved profile.

		  Maximum of 25 displayable characters.

		  Following values have special meanings:
		  null string - means ONT reported that no version was reported..
		  string UNKNOWN (default) - means UNKNOWN (because OLT cannot communicate with ONT for OMCI discovery purposes).
		  string NOSUPPORT - means that ONT does not support GET of this attribute."
::= { gponOntVoipConfigOpInfoEntry  4 }


-- *********************************************
--
-- GPON ONT MEDIA GATEWAY CONTROLLER CONFIG TABLE
--
-- This is a new table beginning with ISAM4.2. 
-- It is only SUPPORTED beginning with ISAM4.2.02 release, when 
-- VoIP provisioning style is standard (not legacy).
--
--
-- This table contains MGC configuration information for a VoIP service that
-- uses H248 signalling..
-- From an OMCI standpoint, it maps primarily to the MGC Config Data ME.
-- From an OMCI standpoint, it is implicit that creation of a row in this table also
-- causes creation of Tcp/Udp ME.
-- Rows are created by the manager. 
--
-- VALIDATION:  A row can only be created if VoIP provisioning style is standard (not legacy).
-- VALIDATION: A row can only be created if gponOntVoipConfigSignallingProtocol attribute 
--	in gponOntVoipConfigTable indicates H248.
-- VALIDATION:  A row cannot be deleted if has an associated POTS port.
--
--	For GPON - SUPPORTED as of ISAM4.2.02
--	For XG-PON1 - SUPPORTED as of ISAM4.6.02
--	For NG-PON2 - NOT SUPPORTED as of ISAM5.2
--
-- *********************************************

gponOntMgcConfigTable  OBJECT-TYPE
	SYNTAX SEQUENCE OF GponOntMgcConfigEntry
	ACCESS	not-accessible
	STATUS	mandatory
	::= { gponVoipGroup 3 }


gponOntMgcConfigEntry  OBJECT-TYPE
	SYNTAX 	GponOntMgcConfigEntry
	ACCESS	not-accessible
	STATUS	mandatory
	INDEX	{ ifIndex }
-- ifIndex of IP Host UNI
	::= { gponOntMgcConfigTable 1 }

GponOntMgcConfigEntry ::= SEQUENCE {
	gponOntMgcConfigRowStatus		RowStatus,
	gponOntMgcConfigPrimaryMgcAddress	AsamProfilePointer,
	gponOntMgcConfigSecondaryMgcAddress	AsamProfilePointer,
	gponOntMgcConfigProtocolVersion		INTEGER,
	gponOntMgcConfigMessageFormat		INTEGER,
	gponOntMgcConfigMaxRetryTime		INTEGER,
	gponOntMgcConfigMaxRetryAttempts		INTEGER,
	gponOntMgcConfigServiceChangeDelay	INTEGER,
	gponOntMgcConfigTerminationIdBase		DisplayString,
	gponOntMgcConfigSoftswitchVendor		DisplayString,
	gponOntMgcConfigDscpSetting		INTEGER,
	gponOntMgcConfigPmCollectInd		INTEGER,
	gponOntMgcConfigNumPMIntervals		INTEGER,
	gponOntMgcConfigMessageId		AsamProfilePointer,
	gponOntMgcConfigTcpUdpPortNum		INTEGER
--	gponOntMgcConfigMessageIdStr		DisplayString
}


gponOntMgcConfigRowStatus OBJECT-TYPE 
	SYNTAX	RowStatus
	ACCESS	read-write
	STATUS  mandatory
	DESCRIPTION
		"This object is used to create a new row or modify or
         		delete an existing row in this table.  "
	::= {  gponOntMgcConfigEntry 2 }


gponOntMgcConfigPrimaryMgcAddress  OBJECT-TYPE
	SYNTAX 	AsamProfilePointer
	ACCESS	read-write
	STATUS	mandatory
	DESCRIPTION 
		"This attribute points to a row in gponSecureUriProfileTable
		 which contains address of primary MGC that controls signalling.

		 Must point to an existing gponSecureUriProfileTable (i.e. value 0 is not permitted).
		 No Default - must be provided by manager.

		 Modification is permitted.  "
	::= { gponOntMgcConfigEntry 3 }


gponOntMgcConfigSecondaryMgcAddress  OBJECT-TYPE
	SYNTAX 	AsamProfilePointer
	ACCESS	read-write
	STATUS	mandatory
	DESCRIPTION 
		"This attribute points to a row in gponSecureUriProfileTable
		 which contains address of secondary MGC that controls signalling.

		 Must point to an existing gponSecureUriProfileTable (i.e. value 0 is not permitted).
		 No Default - must be provided by manager.
		 It is permitted to point to same UriProfile as used for PrimaryMgcAddress.

		 Modification is permitted.  "
	::= { gponOntMgcConfigEntry 4 }

gponOntMgcConfigProtocolVersion OBJECT-TYPE
	SYNTAX 	INTEGER
	ACCESS	read-write
	STATUS	mandatory
	DESCRIPTION 
		" Represents the version of the Megaco protocol that should be used.

		  Range of values is 0 (meaning don't care), 1, 2 and 3.

		  Default = 0 - meaning don't care.

		  Modification is permitted. "

	::= { gponOntMgcConfigEntry 5 }

gponOntMgcConfigMessageFormat OBJECT-TYPE
	SYNTAX 	INTEGER
	ACCESS	read-write
	STATUS	mandatory
	DESCRIPTION 
		" Represents the message format.

		  0 = Text Long
		  1 = Text Short
		  2 = Binary (not supported as of ISAM4.2)

		  Default = 0 

		  Modification is NOT permitted. "

	::= { gponOntMgcConfigEntry 6 }

gponOntMgcConfigMaxRetryTime OBJECT-TYPE
	SYNTAX 	INTEGER
	ACCESS	read-write
	STATUS	mandatory
	DESCRIPTION 
		" Specifies the maximum retry time (in seconds) for MGC transactions.

		  Range is 0 - 60.

		  Default = 0 (meaning vendor specific implementation)

		  Modification is permitted. "

	::= { gponOntMgcConfigEntry 7 }

gponOntMgcConfigMaxRetryAttempts OBJECT-TYPE
	SYNTAX 	INTEGER
	ACCESS	read-write
	STATUS	mandatory
	DESCRIPTION 
		" Specifies the maximum number of times a message is transmitted for MGC.

		  Range is 0 - 10.

		  Default = 0 (meaning vendor specific implementation)

		  Modification is permitted. "

	::= { gponOntMgcConfigEntry 8 }

gponOntMgcConfigServiceChangeDelay OBJECT-TYPE
	SYNTAX 	INTEGER
	ACCESS	read-write
	STATUS	mandatory
	DESCRIPTION 
		" Specifies the service status delay time (in seconds) for changes in line service status.

		  Range is 0 - 60.

		  Default = 0 (meaning no delay)

		  Modification is permitted. "

	::= { gponOntMgcConfigEntry 9 }


gponOntMgcConfigTerminationIdBase OBJECT-TYPE
	SYNTAX 	DisplayString
	ACCESS	read-write
	STATUS	mandatory
	DESCRIPTION 
		" Specifies the base string for the H248 physical termination Ids (for this ONT).  This string
		  is intended to uniquely identify an ONT for all ONTs on this shelf - otherwise OLT should reject.
		  The ONT internally adds POTs slot/port info to this base to uniquely identify POTS line terminations
		  on a specific ONT.

		  Maximum of 25 displayable characters.

		  No Default = must be supplied by manager.

		 For H248 modes, this field must be unique across
		 ONTs on the same shelf. Also - for this uniqueness check -
		 the field must be considered case insensitive.
		 Termination ID is a case insensitive string up to 25 characters
		 long. Only the following characters are allowed: 
		 ['a'..'z', 'A'..'Z', '0'..'9', '*', '/', '-', '_', '$', '@', or '.']. 
		 The first character must be alphabetic.
		 The string 'ROOT' is not allowed. 

		  Modification is permitted.  "

	::= { gponOntMgcConfigEntry 10 }

gponOntMgcConfigSoftswitchVendor OBJECT-TYPE
	SYNTAX 	DisplayString
	ACCESS	read-write
	STATUS	mandatory
	DESCRIPTION 
		" Specifies the gateway softswitch vendor.  The format is four ASCII coded alphabetic characters (A..Z),
		  as defined in ATIS-0322000. A value of 4 null characters indicates no particular vendor.

		  The setting of this attribute will signal to ONT to use various flavors of H248.  At the moment, we do not
		  have the official list of softswitch vendor IDs.

		  In the interim, ALU ONT will interpret some specific settings as follows:

		  GENB (along with country code of POTS line = 1)  = legacy GR303-H248 (assumes General Bandwidth G6).
		  GENB (along with country code of POTS line = NOT 1) = legacy V5.x-H248 (assumes General Bandwidth G6)
		  Any Other Setting = legacy Softswitch-H248 

		  Default = null string (ALU will interpret this as 'Any Other Setting' mentioned above).

		  Modification is permitted.  "

	::= { gponOntMgcConfigEntry 11 }

gponOntMgcConfigDscpSetting  OBJECT-TYPE
	SYNTAX 	INTEGER
	ACCESS	read-write
	STATUS	mandatory
	DESCRIPTION 
		" Specifies the value of the DSCP field of the IP header for H248 signalling packets.

		  Only the low order 6 bits are relevant - since that is
		  the size of the DSCP field in IP packets.

		  Default = 24 (decimal)
   
 		  NOTE: Typically, for VoIP signalling - user would be expected to supply following:
			24 (decimal) = 0x0018 (hex) = 011000 (binary) - Class Selector.

		  Modification is SUPPORTED. "
	::= { gponOntMgcConfigEntry 12 }

gponOntMgcConfigPmCollectInd  OBJECT-TYPE
	SYNTAX 	INTEGER
	ACCESS	read-write
	STATUS	mandatory
	DESCRIPTION 
		" This indicates whether MGC Performance Monitors
		   should be collected for this MGC Config instance.
	
		  1 = PM collection enabled
		  2 = PM collection disabled

		 Default = 2 = disabled.   "
	::= { gponOntMgcConfigEntry 13 }

gponOntMgcConfigNumPMIntervals  OBJECT-TYPE
	SYNTAX 	INTEGER
	ACCESS	read-only
	STATUS	mandatory
	DESCRIPTION 
		" Indicates the number of rows currently present
		  in the gponOntMgcIntervalTable.  This
		  is for convenience of the EMS, so that it can
		 quickly determine how many rows should be 
		 uploaded.   "
	::= { gponOntMgcConfigEntry 14 }

gponOntMgcConfigMessageId  OBJECT-TYPE
	SYNTAX 	AsamProfilePointer
	ACCESS	read-write
	STATUS	mandatory
	DESCRIPTION 
		"This attribute points to a row in gponUriProfileTable
		 which contains the Message Identifier string for H.248 messages that originate
		 from this MGC Config instance.

		 Value 0 (meaning none specified) is permitted.
		 Default = 0.

		 Modification is permitted.  "
	::= { gponOntMgcConfigEntry 15 }


gponOntMgcConfigTcpUdpPortNum OBJECT-TYPE
	SYNTAX 	INTEGER
	ACCESS	read-write
	STATUS	mandatory
	DESCRIPTION 
		" Specifies the UDP Port number to be used for MGC Signalling messages.

		  Valid range is 2000 through 3000
		  Default = 2944

		  Modification is NOT SUPPORTED. "

	::= { gponOntMgcConfigEntry 16 }


-- gponOntMgcConfigMessageIdStr OBJECT-TYPE 
--	SYNTAX DisplayString (SIZE(0..100)) 
--	ACCESS read-write 
--	STATUS mandatory 
--	DESCRIPTION 
--		" This is a textual string which contains the Message Identifier string for H.248 messages. 
--		It represents the same data as gponOntMgcConfigMessageId attribute (above), but instead
--		of using an existing profile, this attribute allows operator to specify unique message id 
--		for each ONT (without using the profile construct).
--
--		Default is NULL string. 
--
--		If gponOntMgcConfigMessageIdStr is Default value = null, the text in 
--		URI profile associated to gponOntMgcConfigMessageId will be used;
--		otherwise, the text in this attribute will be sent to ONT instead.
--
--		Modification is SUPPORTED.
--
--		This attribute was introduced in ISAM5.1 and is NOT SUPPORTED as of ISAM5.1 "
--							 
--	::= { gponOntMgcConfigEntry 17 } 


-- *********************************************
--
-- GPON ONT SIP CONFIG TABLE
--
-- This is a new table beginning with ISAM4.2. 
-- It is only SUPPORTED beginning with ISAM4.2.02 release, when
-- VoIP provisioning style is standard (not legacy).
--
--
-- This table contains SIP configuration information for a VoIP service that
-- uses SIP signalling..
-- From an OMCI standpoint, it maps primarily to the SIP Agent Config Data ME.
-- From an OMCI standpoint, it is implicit that creation of a row in this table also
-- causes creation of Tcp/Udp ME.
-- Rows are created by the manager. 
--
-- VALIDATION:  A row can only be created if VoIP provisioning style is standard (not legacy).
-- VALIDATION: A row can only be created if gponOntVoipConfigSignallingProtocol attribute 
--	in gponOntVoipConfigTable indicates SIP.
-- VALIDATION:  A row cannot be deleted if has an associated POTS port.
--
--	For GPON - SUPPORTED as of ISAM4.2.02
--	For XG-PON1 - SUPPORTED as of ISAM4.6.02
--  For NG-PON2 - SUPPORTED as of ISAM5.4.01
--
-- *********************************************

gponOntSipConfigTable  OBJECT-TYPE
	SYNTAX SEQUENCE OF GponOntSipConfigEntry
	ACCESS	not-accessible
	STATUS	mandatory
	::= { gponVoipGroup 4 }


gponOntSipConfigEntry  OBJECT-TYPE
	SYNTAX 	GponOntSipConfigEntry
	ACCESS	not-accessible
	STATUS	mandatory
	INDEX	{ ifIndex }
-- ifIndex of IP Host UNI
	::= { gponOntSipConfigTable 1 }

GponOntSipConfigEntry ::= SEQUENCE {
	gponOntSipConfigRowStatus			RowStatus,
	gponOntSipConfigProxyServerAddress		AsamProfilePointer,
	gponOntSipConfigOutboundProxyServerAddress 	AsamProfilePointer,
	gponOntSipConfigPrimaryDns		IpAddress,
	gponOntSipConfigSecondaryDns		IpAddress,
	gponOntSipConfigRegExpireTime		INTEGER,
	gponOntSipConfigReRegHeadStartTime	INTEGER,
	gponOntSipConfigAorHostPartUri		AsamProfilePointer,
	gponOntSipConfigRegistrar			AsamProfilePointer,
	gponOntSipConfigSoftswitchVendor		DisplayString,
	gponOntSipConfigMsgCodePointer		AsamProfilePointer,
	gponOntSipConfigOptionTxControl		INTEGER,
	gponOntSipConfigUriFormat			INTEGER,
	gponOntSipConfigDscpSetting		INTEGER,
	gponOntSipConfigTcpUdpPortNum		INTEGER,
	gponOntSipAgentPmCollectInd		INTEGER,
	gponOntSipAgentNumPMIntervals		INTEGER,
	gponOntSipAgentCallInitPmCollectInd		INTEGER,
	gponOntSipAgentCallInitNumPMIntervals	INTEGER
}



gponOntSipConfigRowStatus OBJECT-TYPE 
	SYNTAX	RowStatus
	ACCESS	read-write
	STATUS  mandatory
	DESCRIPTION
		"This object is used to create a new row or modify or
         		delete an existing row in this table.  "
	::= {  gponOntSipConfigEntry 2 }


gponOntSipConfigProxyServerAddress  OBJECT-TYPE
	SYNTAX 	AsamProfilePointer
	ACCESS	read-write
	STATUS	mandatory
	DESCRIPTION 
		"This attribute points to a row in gponUriProfileTable
		 which contains the name (IP address or URI) of the SIP proxy server for 
		 SIP signalling messages.

		 References a Large String, so there is no authentication associated with this address.
		 Authentication is performed through the Registrar attribute, which may or may not reference
		 this same address.

		 Value 0 (meaning address obtained via other means) is permitted.
		 Default = 0.

		 Modification is permitted.  "
	::= { gponOntSipConfigEntry 3 }

gponOntSipConfigOutboundProxyServerAddress  OBJECT-TYPE
	SYNTAX 	AsamProfilePointer
	ACCESS	read-write
	STATUS	mandatory
	DESCRIPTION 
		"This attribute points to a row in gponUriProfileTable
		 which contains the name (IP address or URI) of the outbound SIP proxy server for 
		 SIP signalling messages.

		 If an outbound proxy is required, then this attribute must point to a valid Large String.
		 Otherwise, it must contain a null pointer.

		 Value 0 (meaning null pointer) is permitted.
		 Default = 0.

		 Modification is permitted.  "
	::= { gponOntSipConfigEntry 4 }


gponOntSipConfigPrimaryDns  OBJECT-TYPE
	SYNTAX 	IpAddress
	ACCESS	read-write
	STATUS	mandatory
	DESCRIPTION 
		" Used to manually configure the address of the primary SIP DNS server.
		  Value 0 means no primary DNS is defined.

		  VALIDATION:  The OLT should prohibit entry of the 
		  following range of IP addresses:
		  224.0.0.0 to 239.255.255.255   (multicast)
    		  127.0.0.0 to 127.255.255.255   (loopback)
		  255.255.255.255 (broadcast)

		  Default = 0.0.0.0

		  Modification is SUPPORTED. "
	::= { gponOntSipConfigEntry 5 }

gponOntSipConfigSecondaryDns  OBJECT-TYPE
	SYNTAX 	IpAddress
	ACCESS	read-write
	STATUS	mandatory
	DESCRIPTION 
		" Used to manually configure the address of the primary SIP DNS server.
		  Value 0 means no primary DNS is defined.

		  VALIDATION:  The OLT should prohibit entry of the 
		  following range of IP addresses:
		  224.0.0.0 to 239.255.255.255   (multicast)
    		  127.0.0.0 to 127.255.255.255   (loopback)
		  255.255.255.255 (broadcast)

		  Default = 0.0.0.0

		  Modification is SUPPORTED. "
	::= { gponOntSipConfigEntry 6 }

gponOntSipConfigRegExpireTime OBJECT-TYPE
	SYNTAX 	INTEGER
	ACCESS	read-write
	STATUS	mandatory
	DESCRIPTION 
		" Represents the SIP registration expiration time (in seconds).

		  Range is 0..86400

		  Value 0 means the SIP agent does not add an expiration time to the
		  registration requests and does not perform re-registration.

		  Default = 3600.

		  Modification is permitted. "
	::= { gponOntSipConfigEntry 7 }

gponOntSipConfigReRegHeadStartTime OBJECT-TYPE
	SYNTAX 	INTEGER
	ACCESS	read-write
	STATUS	mandatory
	DESCRIPTION 
		" Represents the time (in seconds) prior to timeout that causes the SIP agent
		  to start the re-registration process.

		  Range is 0..600

		  Value 0 means the SIP agent does not implement this function.

		  Default = 360.

		  Modification is permitted. "

	::= { gponOntSipConfigEntry 8 }

gponOntSipConfigAorHostPartUri  OBJECT-TYPE
	SYNTAX 	AsamProfilePointer
	ACCESS	read-write
	STATUS	mandatory
	DESCRIPTION 
		"This attribute points to a row in gponUriProfileTable
		 which contains the host or domain part of the SIP Address of record (AOR) for
		 users connected to this ONT.

		 Value 0 (default) - i.e. null pointer means that the current address in the IP Host Config
		 is used instead.

		 Modification is permitted.  "
	::= { gponOntSipConfigEntry 9 }

gponOntSipConfigRegistrar  OBJECT-TYPE
	SYNTAX 	AsamProfilePointer
	ACCESS	read-write
	STATUS	mandatory
	DESCRIPTION 
		"This attribute points to a row in gponSecureUriProfileTable
		 which contains the name (IP address or resolved name) of the registrar server for
		 SIP signalling messages.

		 Value 0 (default) - i.e. null pointer means that this is determined via other means.

		 Modification is permitted.  "
	::= { gponOntSipConfigEntry 10 }

gponOntSipConfigSoftswitchVendor  OBJECT-TYPE
	SYNTAX 	DisplayString
	ACCESS	read-write
	STATUS	mandatory
	DESCRIPTION 
		" Specifies the SIP gateway softswitch vendor.  The format is four ASCII coded alphabetic characters (A..Z),
		  as defined in ATIS-0322000. A value of 4 null characters indicates no particular vendor.

		  The setting of this attribute will signal to ONT to use various flavors of SIP.  At the moment, we do not
		  have the official list of softswitch vendor IDs.

		  In the interim, ALU ONT will interpret some specific settings as follows:

		  THIN = legacy SIP 1 - Mode 1 SIP - thin client 
		  Any Other Setting = legacy SIP 2 - Mode 2 SIP - thick client

		  Default = null string (ALU will interpret this as 'Any Other Setting' mentioned above).

		  Modification is permitted.  "
	::= { gponOntSipConfigEntry 11 }

gponOntSipConfigMsgCodePointer  OBJECT-TYPE
	SYNTAX 	AsamProfilePointer
	ACCESS	read-write
	STATUS	mandatory
	DESCRIPTION 
		"This attribute points to a row in gponSipMsgProfileTable - which 
		 associates tones and text with SIP message codes.

		 Value 0 (default) is permitted - meaning tones and text are defined via other means.

		 Modification is permitted.

		NOT SUPPORTED.   "
	::= { gponOntSipConfigEntry 12 }

gponOntSipConfigOptionTxControl OBJECT-TYPE
	SYNTAX 	INTEGER
	ACCESS	read-write
	STATUS	mandatory
	DESCRIPTION 
		" Specifies whether ONT is enabled/disabled to transmit SIP options.

		  0 = Disabled (default)
		  1 = Enabled

		  Modification is permitted. "

	::= { gponOntSipConfigEntry 13 }

gponOntSipConfigUriFormat OBJECT-TYPE
	SYNTAX 	INTEGER
	ACCESS	read-write
	STATUS	mandatory
	DESCRIPTION 
		" Specifies the format of the URI in outgoing SIP messages.

		  0 = TEL URIs (default)
		  1 = SIP URIs

		  Modification is permitted. "

	::= { gponOntSipConfigEntry 14 }

gponOntSipConfigDscpSetting  OBJECT-TYPE
	SYNTAX 	INTEGER
	ACCESS	read-write
	STATUS	mandatory
	DESCRIPTION 
		" Specifies the value of the DSCP field of the IP header for SIP signalling packets.

		  Only the low order 6 bits are relevant - since that is
		  the size of the DSCP field in IP packets.

		  Default = 24 (decimal)
   
 		  NOTE: Typically, for VoIP signalling - user would be expected to supply following:
			24 (decimal) = 0x0018 (hex) = 011000 (binary) - Class Selector.

		  Modification is SUPPORTED. "
	::= { gponOntSipConfigEntry 15 }

gponOntSipConfigTcpUdpPortNum OBJECT-TYPE
	SYNTAX 	INTEGER
	ACCESS	read-write
	STATUS	mandatory
	DESCRIPTION 
		" Specifies the UDP Port number to be used for SIP Signalling messages.

		  Valid range is 5000 through 6000
		  Default = 5060

		  Modification is NOT SUPPORTED. "

	::= { gponOntSipConfigEntry 16 }

gponOntSipAgentPmCollectInd  OBJECT-TYPE
	SYNTAX 	INTEGER
	ACCESS	read-write
	STATUS	mandatory
	DESCRIPTION 
		" This indicates whether SIP Agent Performance Monitors
		   should be collected for this SIP Agent.
	
		  1 = PM collection enabled
		  2 = PM collection disabled

		 Default = 2 = disabled.   "
	::= { gponOntSipConfigEntry 17 }

gponOntSipAgentNumPMIntervals  OBJECT-TYPE
	SYNTAX 	INTEGER
	ACCESS	read-only
	STATUS	mandatory
	DESCRIPTION 
		" Indicates the number of rows currently present
		  in the gponOntSipIntervalTable.  This
		  is for convenience of the EMS, so that it can
		 quickly determine how many rows should be 
		 uploaded.   "
	::= { gponOntSipConfigEntry 18 }

gponOntSipAgentCallInitPmCollectInd  OBJECT-TYPE
	SYNTAX 	INTEGER
	ACCESS	read-write
	STATUS	mandatory
	DESCRIPTION 
		" This indicates whether SIP Agent Call Initiation Performance Monitors
		   should be collected for this SIP Agent.
	
		  1 = PM collection enabled
		  2 = PM collection disabled

		 Default = 2 = disabled.   "
	::= { gponOntSipConfigEntry 19 }

gponOntSipAgentCallInitNumPMIntervals  OBJECT-TYPE
	SYNTAX 	INTEGER
	ACCESS	read-only
	STATUS	mandatory
	DESCRIPTION 
		" Indicates the number of rows currently present
		  in the gponOntSipCallInitIntervalTable.  This
		  is for convenience of the EMS, so that it can
		 quickly determine how many rows should be 
		 uploaded.   "
	::= { gponOntSipConfigEntry 20 }

-- *********************************************
-- GPON  ONT SIP CONFIGURATION OPINFO TABLE
--
-- This is a new table beginning with ISAM4.2. 
-- It is only SUPPORTED beginning with ISAM4.2.02 release, when 
-- VoIP provisioning style is standard (not legacy).
--
--
-- This table contains operational information regarding SIP configuration for an ONT.
-- From an OMCI standpoint, it maps primarily to the SIP Agent Config Data ME.
--
-- The operational information is significant in that
-- each time it is requested, the OLT issues OMCI GET messages   
-- to obtain the latest information directly from the ONT.
-- A table row is created/deleted automatically by the OLT upon  
-- creation/deletion of the associated row in gponOntSipConfigTable.
--
--	For GPON - SUPPORTED as of ISAM4.2.02
--	For XG-PON1 - SUPPORTED as of ISAM4.6.02
--  For NG-PON2 - SUPPORTED as of ISAM5.4.01
--
-- *********************************************

gponOntSipConfigOpInfoTable OBJECT-TYPE
	SYNTAX	SEQUENCE OF GponOntSipConfigOpInfoEntry
	ACCESS	not-accessible
	STATUS	mandatory
	DESCRIPTION
		"This table contains operational information for a specific ONT, 
		 obtained directly from a specific ONT.  "
::= { gponVoipGroup 5 }

gponOntSipConfigOpInfoEntry OBJECT-TYPE
	SYNTAX 	GponOntSipConfigOpInfoEntry
	ACCESS	not-accessible
	STATUS	mandatory
	DESCRIPTION
		"Rows of this table contain ONT Sip config information. "
	INDEX { ifIndex }
-- this is the ifIndex of the IP Host UNI.

::= {gponOntSipConfigOpInfoTable 1}

GponOntSipConfigOpInfoEntry ::=
	SEQUENCE { 
		gponOntSipConfigOpInfoStatus		INTEGER
}


gponOntSipConfigOpInfoStatus OBJECT-TYPE
	SYNTAX 	INTEGER
	ACCESS	read-only
	STATUS	mandatory
	DESCRIPTION 
		" Indicates the current status of the SIP agent.
		  In OMCI, this maps to the SIP status attribute in the SIP Agent Config Data ME. 

		  0 = OK/Initial
		  1 = Connected
		  2 = Failed - ICMP Error
		  3 = Failed - Malformed Response
		  4 = Failed - Inadequate Info Response
		  5 = Failed - Timeout
		  6 through 255 = ONT reported non-standard value
		  256 = UNKNOWN - (because OLT cannot communicate with ONT for OMCI discovery purposes).
		  257 = NOSUPPORT - means that ONT does NOT support GET of this attribute.

		  Default = 256 = UNKNOWN - (because OLT cannot communicate with ONT for OMCI discovery purposes). "
::= { gponOntSipConfigOpInfoEntry  1 }


-- *********************************************
--
-- GPON SIP AGENT PERFORMANCE MONITOR CURRENT INTERVAL TABLE
--
-- This is a new table beginning with ISAM4.2.
-- It is only SUPPORTED beginning with ISAM4.2.02 release, when
-- VoIP provisioning style is standard (not legacy).
--
-- This current interval table contains various SIP agent data during the current 15 minute interval 
-- of operation.  
--
-- An instance of this table is auto-created/deleted in accordance with the 
-- 'SIP Agent PM Collect Indicator' setting of the SIP Config table.
--
-- For GETs of table attributes, the OLT must go directly to the ONT (via OMCI)
-- in order to acquire fresh current counts. 
-- 
--	For GPON - SUPPORTED as of ISAM4.2.02
--	For XG-PON1 - SUPPORTED as of ISAM4.6.02
--  For NG-PON2 - SUPPORTED as of ISAM5.4.01
--
-- *********************************************


gponOntSipCurrentIntervalTable  OBJECT-TYPE
	SYNTAX SEQUENCE OF GponOntSipCurrentIntervalEntry
	ACCESS	not-accessible
	STATUS	mandatory
	::= { gponVoipGroup 6 }


gponOntSipCurrentIntervalEntry  OBJECT-TYPE
	SYNTAX 	GponOntSipCurrentIntervalEntry
	ACCESS	not-accessible
	STATUS	mandatory
	DESCRIPTION 
		"An entry in the gponOntSipCurrentIntervalTable  "
	INDEX { ifIndex }
-- this is the ifIndex of the IP Host UNI.
	::= { gponOntSipCurrentIntervalTable 1 }

GponOntSipCurrentIntervalEntry ::= SEQUENCE {
	gponOntSipCurrentIntervalValidInd			Boolean,
	gponOntSipCurrentIntervalTransactions			Counter,
	gponOntSipCurrentIntervalRxInviteReqs		Counter,
	gponOntSipCurrentIntervalRxInviteRetrans			Counter,
	gponOntSipCurrentIntervalRxNonInviteReqs		Counter,
	gponOntSipCurrentIntervalRxNonInviteRetrans			Counter,
	gponOntSipCurrentIntervalRxResponses		Counter,
	gponOntSipCurrentIntervalRxResponseRetrans		Counter,
	gponOntSipCurrentIntervalTxInviteReqs		Counter,
	gponOntSipCurrentIntervalTxInviteRetrans			Counter,
	gponOntSipCurrentIntervalTxNonInviteReqs		Counter,
	gponOntSipCurrentIntervalTxNonInviteRetrans			Counter,
	gponOntSipCurrentIntervalTxResponses		Counter,
	gponOntSipCurrentIntervalTxResponseRetrans		Counter
}


gponOntSipCurrentIntervalValidInd  OBJECT-TYPE
	SYNTAX 	Boolean
	ACCESS	read-only
	STATUS	mandatory
	DESCRIPTION 
		"Indicates whether or not this CurrentInterval contains
		 valid PM counts. 

		 NOT SUPPORTED "
	::= { gponOntSipCurrentIntervalEntry 1 }

gponOntSipCurrentIntervalTransactions  OBJECT-TYPE
	SYNTAX 	Counter
	ACCESS	read-only
	STATUS	mandatory
	DESCRIPTION 
		"A count of number of new transactions that were initiated. "
	::= { gponOntSipCurrentIntervalEntry 2 }

gponOntSipCurrentIntervalRxInviteReqs  OBJECT-TYPE
	SYNTAX 	Counter
	ACCESS	read-only
	STATUS	mandatory
	DESCRIPTION 
		"A count of number of received invite messages, including retransmissions. "
	::= { gponOntSipCurrentIntervalEntry 3 }

gponOntSipCurrentIntervalRxInviteRetrans  OBJECT-TYPE
	SYNTAX 	Counter
	ACCESS	read-only
	STATUS	mandatory
	DESCRIPTION 
		"A count of number of received invite retransmission messages. "
	::= { gponOntSipCurrentIntervalEntry 4 }

gponOntSipCurrentIntervalRxNonInviteReqs  OBJECT-TYPE
	SYNTAX 	Counter
	ACCESS	read-only
	STATUS	mandatory
	DESCRIPTION 
		"A count of number of received non-invite messages, including retransmissions. "
	::= { gponOntSipCurrentIntervalEntry 5 }

gponOntSipCurrentIntervalRxNonInviteRetrans  OBJECT-TYPE
	SYNTAX 	Counter
	ACCESS	read-only
	STATUS	mandatory
	DESCRIPTION 
		"A count of number of received non-invite retransmission messages. "
	::= { gponOntSipCurrentIntervalEntry 6 }

gponOntSipCurrentIntervalRxResponses  OBJECT-TYPE
	SYNTAX 	Counter
	ACCESS	read-only
	STATUS	mandatory
	DESCRIPTION 
		"A count of number of total responses received. "
	::= { gponOntSipCurrentIntervalEntry 7 }

gponOntSipCurrentIntervalRxResponseRetrans  OBJECT-TYPE
	SYNTAX 	Counter
	ACCESS	read-only
	STATUS	mandatory
	DESCRIPTION 
		"A count of number of total response retransmissions received. "
	::= { gponOntSipCurrentIntervalEntry 8 }

gponOntSipCurrentIntervalTxInviteReqs  OBJECT-TYPE
	SYNTAX 	Counter
	ACCESS	read-only
	STATUS	mandatory
	DESCRIPTION 
		"A count of number of transmitted invite messages, including retransmissions. "
	::= { gponOntSipCurrentIntervalEntry 9 }

gponOntSipCurrentIntervalTxInviteRetrans  OBJECT-TYPE
	SYNTAX 	Counter
	ACCESS	read-only
	STATUS	mandatory
	DESCRIPTION 
		"A count of number of transmitted invite retransmission messages. "
	::= { gponOntSipCurrentIntervalEntry 10 }

gponOntSipCurrentIntervalTxNonInviteReqs  OBJECT-TYPE
	SYNTAX 	Counter
	ACCESS	read-only
	STATUS	mandatory
	DESCRIPTION 
		"A count of number of transmitted non-invite messages, including retransmissions. "
	::= { gponOntSipCurrentIntervalEntry 11 }

gponOntSipCurrentIntervalTxNonInviteRetrans  OBJECT-TYPE
	SYNTAX 	Counter
	ACCESS	read-only
	STATUS	mandatory
	DESCRIPTION 
		"A count of number of transmitted non-invite retransmission messages. "
	::= { gponOntSipCurrentIntervalEntry 12 }

gponOntSipCurrentIntervalTxResponses  OBJECT-TYPE
	SYNTAX 	Counter
	ACCESS	read-only
	STATUS	mandatory
	DESCRIPTION 
		"A count of number of total responses transmitted. "
	::= { gponOntSipCurrentIntervalEntry 13 }

gponOntSipCurrentIntervalTxResponseRetrans  OBJECT-TYPE
	SYNTAX 	Counter
	ACCESS	read-only
	STATUS	mandatory
	DESCRIPTION 
		"A count of number of total response retransmissions transmitted. "
	::= { gponOntSipCurrentIntervalEntry 14 }



-- *********************************************
--
-- GPON SIP AGENT PERFORMANCE MONITOR INTERVAL TABLE
--
-- This is a new table beginning with ISAM4.2.
-- It is NOT SUPPORTED as of  ISAM4.2.02 release.
-- Only relevant when VoIP provisioning style is standard (not legacy).
--
-- This interval table contains various SIP agent data collected
-- over the previous 8 hours of operation.  The past 8 hours are
-- broken into 32 completed 15 minute intervals.  Each row in this table
-- represents one such interval associated with a SIP Agent.  
--
-- An instance of this table is auto-created/deleted in accordance with the 
-- 'SIP Agent PM Collect Indicator' setting of the SIP Config table.
--
--	For GPON - NOT SUPPORTED as of ISAM4.2.02
--	For XG-PON1 - NOT SUPPORTED as of ISAM4.6.02
--  For NG-PON2 - SUPPORTED as of ISAM5.4.01
-- 
-- *********************************************


gponOntSipIntervalTable  OBJECT-TYPE
	SYNTAX SEQUENCE OF GponOntSipIntervalEntry
	ACCESS	not-accessible
	STATUS	mandatory
	::= { gponVoipGroup 7 }


gponOntSipIntervalEntry  OBJECT-TYPE
	SYNTAX 	GponOntSipIntervalEntry
	ACCESS	not-accessible
	STATUS	mandatory
	DESCRIPTION 
		"An entry in the gponOntSipIntervalTable  "
	INDEX { ifIndex,
		gponOntSipIntervalNumber }
-- this is the ifIndex of the IP Host UNI.
	::= { gponOntSipIntervalTable 1 }

GponOntSipIntervalEntry ::= SEQUENCE {
	gponOntSipIntervalNumber			INTEGER,
	gponOntSipIntervalValidInd			Boolean,
	gponOntSipIntervalTransactions			Counter,
	gponOntSipIntervalRxInviteReqs		Counter,
	gponOntSipIntervalRxInviteRetrans			Counter,
	gponOntSipIntervalRxNonInviteReqs		Counter,
	gponOntSipIntervalRxNonInviteRetrans			Counter,
	gponOntSipIntervalRxResponses		Counter,
	gponOntSipIntervalRxResponseRetrans		Counter,
	gponOntSipIntervalTxInviteReqs		Counter,
	gponOntSipIntervalTxInviteRetrans			Counter,
	gponOntSipIntervalTxNonInviteReqs		Counter,
	gponOntSipIntervalTxNonInviteRetrans			Counter,
	gponOntSipIntervalTxResponses		Counter,
	gponOntSipIntervalTxResponseRetrans		Counter
}

gponOntSipIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.  "
	::= { gponOntSipIntervalEntry 1 }

gponOntSipIntervalValidInd  OBJECT-TYPE
	SYNTAX 	Boolean
	ACCESS	read-only
	STATUS	mandatory
	DESCRIPTION 
		"Indicates whether or not this Interval contains
		 valid PM counts. 

		 NOT SUPPORTED "
	::= { gponOntSipIntervalEntry 2 }

gponOntSipIntervalTransactions  OBJECT-TYPE
	SYNTAX 	Counter
	ACCESS	read-only
	STATUS	mandatory
	DESCRIPTION 
		"A count of number of new transactions that were initiated. "
	::= { gponOntSipIntervalEntry 3 }

gponOntSipIntervalRxInviteReqs  OBJECT-TYPE
	SYNTAX 	Counter
	ACCESS	read-only
	STATUS	mandatory
	DESCRIPTION 
		"A count of number of received invite messages, including retransmissions. "
	::= { gponOntSipIntervalEntry 4 }

gponOntSipIntervalRxInviteRetrans  OBJECT-TYPE
	SYNTAX 	Counter
	ACCESS	read-only
	STATUS	mandatory
	DESCRIPTION 
		"A count of number of received invite retransmission messages. "
	::= { gponOntSipIntervalEntry 5 }

gponOntSipIntervalRxNonInviteReqs  OBJECT-TYPE
	SYNTAX 	Counter
	ACCESS	read-only
	STATUS	mandatory
	DESCRIPTION 
		"A count of number of received non-invite messages, including retransmissions. "
	::= { gponOntSipIntervalEntry 6 }

gponOntSipIntervalRxNonInviteRetrans  OBJECT-TYPE
	SYNTAX 	Counter
	ACCESS	read-only
	STATUS	mandatory
	DESCRIPTION 
		"A count of number of received non-invite retransmission messages. "
	::= { gponOntSipIntervalEntry 7 }

gponOntSipIntervalRxResponses  OBJECT-TYPE
	SYNTAX 	Counter
	ACCESS	read-only
	STATUS	mandatory
	DESCRIPTION 
		"A count of number of total responses received. "
	::= { gponOntSipIntervalEntry 8 }

gponOntSipIntervalRxResponseRetrans  OBJECT-TYPE
	SYNTAX 	Counter
	ACCESS	read-only
	STATUS	mandatory
	DESCRIPTION 
		"A count of number of total response retransmissions received. "
	::= { gponOntSipIntervalEntry 9 }

gponOntSipIntervalTxInviteReqs  OBJECT-TYPE
	SYNTAX 	Counter
	ACCESS	read-only
	STATUS	mandatory
	DESCRIPTION 
		"A count of number of transmitted invite messages, including retransmissions. "
	::= { gponOntSipIntervalEntry 10 }

gponOntSipIntervalTxInviteRetrans  OBJECT-TYPE
	SYNTAX 	Counter
	ACCESS	read-only
	STATUS	mandatory
	DESCRIPTION 
		"A count of number of transmitted invite retransmission messages. "
	::= { gponOntSipIntervalEntry 11 }

gponOntSipIntervalTxNonInviteReqs  OBJECT-TYPE
	SYNTAX 	Counter
	ACCESS	read-only
	STATUS	mandatory
	DESCRIPTION 
		"A count of number of transmitted non-invite messages, including retransmissions. "
	::= { gponOntSipIntervalEntry 12 }

gponOntSipIntervalTxNonInviteRetrans  OBJECT-TYPE
	SYNTAX 	Counter
	ACCESS	read-only
	STATUS	mandatory
	DESCRIPTION 
		"A count of number of transmitted non-invite retransmission messages. "
	::= { gponOntSipIntervalEntry 13 }

gponOntSipIntervalTxResponses  OBJECT-TYPE
	SYNTAX 	Counter
	ACCESS	read-only
	STATUS	mandatory
	DESCRIPTION 
		"A count of number of total responses transmitted. "
	::= { gponOntSipIntervalEntry 14 }

gponOntSipIntervalTxResponseRetrans  OBJECT-TYPE
	SYNTAX 	Counter
	ACCESS	read-only
	STATUS	mandatory
	DESCRIPTION 
		"A count of number of total response retransmissions transmitted. "
	::= { gponOntSipIntervalEntry 15 }


-- *********************************************
--
-- GPON SIP AGENT CALL INITIATION MONITOR CURRENT INTERVAL TABLE
--
-- This is a new table beginning with ISAM4.2.
-- It is only SUPPORTED beginning with ISAM4.2.02 release, when 
-- VoIP provisioning style is standard (not legacy).
--
-- This current interval table contains various SIP agent call initiation data during the 
-- current 15 minute interval of operation.  
--
-- An instance of this table is auto-created/deleted in accordance with the 
-- 'SIP Agent Call Init PM Collect Indicator' setting of the SIP Config table.
--
-- For GETs of table attributes, the OLT must go directly to the ONT (via OMCI)
-- in order to acquire fresh current counts. 
-- 
--	For GPON - SUPPORTED as of ISAM4.2.02
--	For XG-PON1 - SUPPORTED as of ISAM4.6.02
--  For NG-PON2 - SUPPORTED as of ISAM5.4.01
--
-- *********************************************


gponOntSipCallInitCurrentIntervalTable  OBJECT-TYPE
	SYNTAX SEQUENCE OF GponOntSipCallInitCurrentIntervalEntry
	ACCESS	not-accessible
	STATUS	mandatory
	::= { gponVoipGroup 8 }


gponOntSipCallInitCurrentIntervalEntry  OBJECT-TYPE
	SYNTAX 	GponOntSipCallInitCurrentIntervalEntry
	ACCESS	not-accessible
	STATUS	mandatory
	DESCRIPTION 
		"An entry in the gponOntSipCallInitCurrentIntervalTable  "
	INDEX { ifIndex }
-- this is the ifIndex of the IP Host UNI.
	::= { gponOntSipCallInitCurrentIntervalTable 1 }

GponOntSipCallInitCurrentIntervalEntry ::= SEQUENCE {
	gponOntSipCallInitCurrentIntervalValidInd			Boolean,
	gponOntSipCallInitCurrentIntervalConnectFails			Counter,
	gponOntSipCallInitCurrentIntervalValidateFails		Counter,
	gponOntSipCallInitCurrentIntervalTimeouts			Counter,
	gponOntSipCallInitCurrentIntervalReceivedFails		Counter,
	gponOntSipCallInitCurrentIntervalAuthenticateFails			Counter
}


gponOntSipCallInitCurrentIntervalValidInd  OBJECT-TYPE
	SYNTAX 	Boolean
	ACCESS	read-only
	STATUS	mandatory
	DESCRIPTION 
		"Indicates whether or not this CurrentInterval contains
		 valid PM counts. 

		 NOT SUPPORTED "
	::= { gponOntSipCallInitCurrentIntervalEntry 1 }

gponOntSipCallInitCurrentIntervalConnectFails  OBJECT-TYPE
	SYNTAX 	Counter
	ACCESS	read-only
	STATUS	mandatory
	DESCRIPTION 
		"A count of number of times the SIP User Agent failed to reach/connect
		 its TCP/UDP peer during SIP call initiation. "
	::= { gponOntSipCallInitCurrentIntervalEntry 2 }

gponOntSipCallInitCurrentIntervalValidateFails  OBJECT-TYPE
	SYNTAX 	Counter
	ACCESS	read-only
	STATUS	mandatory
	DESCRIPTION 
		"A count of number of times the SIP User Agent failed to validate
		 its peer during SIP call initiation. "
	::= { gponOntSipCallInitCurrentIntervalEntry 3 }

gponOntSipCallInitCurrentIntervalTimeouts  OBJECT-TYPE
	SYNTAX 	Counter
	ACCESS	read-only
	STATUS	mandatory
	DESCRIPTION 
		"A count of number of times the SIP User Agent timed out
		 during SIP call initiations. "
	::= { gponOntSipCallInitCurrentIntervalEntry 4 }

gponOntSipCallInitCurrentIntervalReceivedFails  OBJECT-TYPE
	SYNTAX 	Counter
	ACCESS	read-only
	STATUS	mandatory
	DESCRIPTION 
		"A count of number of times the SIP User Agent received a failure error code
		 during SIP call initiations. "
	::= { gponOntSipCallInitCurrentIntervalEntry 5 }

gponOntSipCallInitCurrentIntervalAuthenticateFails  OBJECT-TYPE
	SYNTAX 	Counter
	ACCESS	read-only
	STATUS	mandatory
	DESCRIPTION 
		"A count of number of times the SIP User Agent failed to authenticate itself
		 during SIP call initiations. "
	::= { gponOntSipCallInitCurrentIntervalEntry 6 }


-- *********************************************
--
-- GPON SIP AGENT CALL INITIATION PERFORMANCE MONITOR INTERVAL TABLE
--
-- This is a new table beginning with ISAM4.2.
-- It is NOT SUPPORTED as of  ISAM4.2.02 release.
-- Only relevant when VoIP provisioning style is standard (not legacy).
--
-- This interval table contains various SIP agent call initiation data collected
-- over the previous 8 hours of operation.  The past 8 hours are
-- broken into 32 completed 15 minute intervals.  Each row in this table
-- represents one such interval associated with a SIP Agent.  
--
-- An instance of this table is auto-created/deleted in accordance with the 
-- 'SIP Agent Call Init PM Collect Indicator' setting of the SIP Config table.
--
--	For GPON - NOT SUPPORTED as of ISAM4.2.02
--	For XG-PON1 - NOT SUPPORTED as of ISAM4.6.02
--  For NG-PON2 - SUPPORTED as of ISAM5.4.01
-- 
-- *********************************************


gponOntSipCallInitIntervalTable  OBJECT-TYPE
	SYNTAX SEQUENCE OF GponOntSipCallInitIntervalEntry
	ACCESS	not-accessible
	STATUS	mandatory
	::= { gponVoipGroup 9 }


gponOntSipCallInitIntervalEntry  OBJECT-TYPE
	SYNTAX 	GponOntSipCallInitIntervalEntry
	ACCESS	not-accessible
	STATUS	mandatory
	DESCRIPTION 
		"An entry in the gponOntSipCallInitIntervalTable  "
	INDEX { ifIndex,
		gponOntSipCallInitIntervalNumber }
-- this is the ifIndex of the IP Host UNI.
	::= { gponOntSipCallInitIntervalTable 1 }

GponOntSipCallInitIntervalEntry ::= SEQUENCE {
	gponOntSipCallInitIntervalNumber			INTEGER,
	gponOntSipCallInitIntervalValidInd			Boolean,
	gponOntSipCallInitIntervalConnectFails			Counter,
	gponOntSipCallInitIntervalValidateFails		Counter,
	gponOntSipCallInitIntervalTimeouts			Counter,
	gponOntSipCallInitIntervalReceivedFails		Counter,
	gponOntSipCallInitIntervalAuthenticateFails			Counter
}

gponOntSipCallInitIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.  "
	::= { gponOntSipCallInitIntervalEntry 1 }

gponOntSipCallInitIntervalValidInd  OBJECT-TYPE
	SYNTAX 	Boolean
	ACCESS	read-only
	STATUS	mandatory
	DESCRIPTION 
		"Indicates whether or not this Interval contains
		 valid PM counts. 

		 NOT SUPPORTED "
	::= { gponOntSipCallInitIntervalEntry 2 }

gponOntSipCallInitIntervalConnectFails  OBJECT-TYPE
	SYNTAX 	Counter
	ACCESS	read-only
	STATUS	mandatory
	DESCRIPTION 
		"A count of number of times the SIP User Agent failed to reach/connect
		 its TCP/UDP peer during SIP call initiation. "
	::= { gponOntSipCallInitIntervalEntry 3 }

gponOntSipCallInitIntervalValidateFails  OBJECT-TYPE
	SYNTAX 	Counter
	ACCESS	read-only
	STATUS	mandatory
	DESCRIPTION 
		"A count of number of times the SIP User Agent failed to validate
		 its peer during SIP call initiation. "
	::= { gponOntSipCallInitIntervalEntry 4 }

gponOntSipCallInitIntervalTimeouts  OBJECT-TYPE
	SYNTAX 	Counter
	ACCESS	read-only
	STATUS	mandatory
	DESCRIPTION 
		"A count of number of times the SIP User Agent timed out
		 during SIP call initiations. "
	::= { gponOntSipCallInitIntervalEntry 5 }

gponOntSipCallInitIntervalReceivedFails  OBJECT-TYPE
	SYNTAX 	Counter
	ACCESS	read-only
	STATUS	mandatory
	DESCRIPTION 
		"A count of number of times the SIP User Agent received a failure error code
		 during SIP call initiations. "
	::= { gponOntSipCallInitIntervalEntry 6 }

gponOntSipCallInitIntervalAuthenticateFails  OBJECT-TYPE
	SYNTAX 	Counter
	ACCESS	read-only
	STATUS	mandatory
	DESCRIPTION 
		"A count of number of times the SIP User Agent failed to authenticate itself
		 during SIP call initiations. "
	::= { gponOntSipCallInitIntervalEntry 7 }

-- *********************************************
--
-- GPON MGC PERFORMANCE MONITOR CURRENT INTERVAL TABLE
--
-- This is a new table beginning with ISAM4.2.
-- It is only SUPPORTED beginning with ISAM4.2.02 release, when
-- VoIP provisioning style is standard (not legacy).
--
-- This current interval table contains various run time statistics for an active MGC association 
-- during the current 15 minute interval of operation.  
--
-- An instance of this table is auto-created/deleted in accordance with the 
-- 'MGC PM Collect Indicator' setting of the MGC Config table.
--
-- For GETs of table attributes, the OLT must go directly to the ONT (via OMCI)
-- in order to acquire fresh current counts. 
-- 
--	For GPON - SUPPORTED as of ISAM4.2.02
--	For XG-PON1 - SUPPORTED as of ISAM4.6.02
--	For NG-PON2 - NOT SUPPORTED as of ISAM5.2
-- *********************************************


gponOntMgcCurrentIntervalTable  OBJECT-TYPE
	SYNTAX SEQUENCE OF GponOntMgcCurrentIntervalEntry
	ACCESS	not-accessible
	STATUS	mandatory
	::= { gponVoipGroup 10 }


gponOntMgcCurrentIntervalEntry  OBJECT-TYPE
	SYNTAX 	GponOntMgcCurrentIntervalEntry
	ACCESS	not-accessible
	STATUS	mandatory
	DESCRIPTION 
		"An entry in the gponOntMgcCurrentIntervalTable  "
	INDEX { ifIndex }
-- this is the ifIndex of the IP Host UNI.
	::= { gponOntMgcCurrentIntervalTable 1 }

GponOntMgcCurrentIntervalEntry ::= SEQUENCE {
	gponOntMgcCurrentIntervalValidInd			Boolean,
	gponOntMgcCurrentIntervalRxMsgs			Counter,
	gponOntMgcCurrentIntervalRxOctets			Counter,
	gponOntMgcCurrentIntervalTxMsgs			Counter,
	gponOntMgcCurrentIntervalTxOctets			Counter,
	gponOntMgcCurrentIntervalProtocolErrors		Counter,
	gponOntMgcCurrentIntervalTransportLosses		Counter,
	gponOntMgcCurrentIntervalLastDetectedEvent		Counter,
	gponOntMgcCurrentIntervalLastDetectedEventTime	Counter,
	gponOntMgcCurrentIntervalLastDetectedResetTime	Counter

}


gponOntMgcCurrentIntervalValidInd  OBJECT-TYPE
	SYNTAX 	Boolean
	ACCESS	read-only
	STATUS	mandatory
	DESCRIPTION 
		"Indicates whether or not this CurrentInterval contains
		 valid PM counts. 

		 NOT SUPPORTED "
	::= { gponOntMgcCurrentIntervalEntry 1 }

gponOntMgcCurrentIntervalRxMsgs  OBJECT-TYPE
	SYNTAX 	Counter
	ACCESS	read-only
	STATUS	mandatory
	DESCRIPTION 
		"A count of number of received Megaco messages on this association,
		 as defined by ITU-T H.341.  "
	::= { gponOntMgcCurrentIntervalEntry 2 }

gponOntMgcCurrentIntervalRxOctets  OBJECT-TYPE
	SYNTAX 	Counter
	ACCESS	read-only
	STATUS	mandatory
	DESCRIPTION 
		"A count of total number of octets received over this association,
		 as defined by ITU-T H.341.  "
	::= { gponOntMgcCurrentIntervalEntry 3 }

gponOntMgcCurrentIntervalTxMsgs  OBJECT-TYPE
	SYNTAX 	Counter
	ACCESS	read-only
	STATUS	mandatory
	DESCRIPTION 
		"A count of number of sent Megaco messages on this association,
		 as defined by ITU-T H.341.  "
	::= { gponOntMgcCurrentIntervalEntry 4 }

gponOntMgcCurrentIntervalTxOctets  OBJECT-TYPE
	SYNTAX 	Counter
	ACCESS	read-only
	STATUS	mandatory
	DESCRIPTION 
		"A count of total number of octets sent over this association,
		 as defined by ITU-T H.341.  "
	::= { gponOntMgcCurrentIntervalEntry 5 }

gponOntMgcCurrentIntervalProtocolErrors  OBJECT-TYPE
	SYNTAX 	Counter
	ACCESS	read-only
	STATUS	mandatory
	DESCRIPTION 
		"A count of total number of errors detected on this association,
		 as defined by ITU-T H.341. This includes:
		 - Syntax errors detected in a given received message.
		 - Outgoing transactions that failed for protocol reasons. "
	::= { gponOntMgcCurrentIntervalEntry 6 }

gponOntMgcCurrentIntervalTransportLosses  OBJECT-TYPE
	SYNTAX 	Counter
	ACCESS	read-only
	STATUS	mandatory
	DESCRIPTION 
		"A count of total number of transport losses (for example socket problems)
		 detected on this association. A link loss is defined as loss of communication
		 with the remote entity due to hardware/transient problems, or problems in
		 related software.  "
	::= { gponOntMgcCurrentIntervalEntry 7 }

gponOntMgcCurrentIntervalLastDetectedEvent  OBJECT-TYPE
	SYNTAX 	Counter
	ACCESS	read-only
	STATUS	mandatory
	DESCRIPTION 
		" This attribute reports the last detected event on this association.
		  This includes events such as link failing or being set up.  This attribute is
		  an enumeration as follows:

		  0 = No Event - No event has been detected as yet.
		  1 = Link Up - The transport link underpinning the association came up.
		  2 = Link Down - The transport link underpinning the association went down.
		  3 = Persistent Error - A persistent error was detected on the link (such as the socket
		        connection to the remote node could not be set up.
		  4 = Local Shutdown - The association was brought down intentionally by the 
		        local application.
		  5 = Failover Down - The association was brought down as part of failover processing.
		  255 = Other Event - The last event does not match any in the list.  "
	::= { gponOntMgcCurrentIntervalEntry 8 }

gponOntMgcCurrentIntervalLastDetectedEventTime  OBJECT-TYPE
	SYNTAX 	Counter
	ACCESS	read-only
	STATUS	mandatory
	DESCRIPTION 
		" This attribute reports the time in seconds since the last event on this association was 
		  detected, as defined by ITU-T H.341.  "
	::= { gponOntMgcCurrentIntervalEntry 9 }

gponOntMgcCurrentIntervalLastDetectedResetTime  OBJECT-TYPE
	SYNTAX 	Counter
	ACCESS	read-only
	STATUS	mandatory
	DESCRIPTION 
		" This attribute reports the time in seconds since these these statistics were last reset, 
		  as defined by ITU-T H.341.  "
	::= { gponOntMgcCurrentIntervalEntry 10 }


-- *********************************************
--
-- GPON MGC PERFORMANCE MONITOR INTERVAL TABLE
--
-- This is a new table beginning with ISAM4.2.
-- It is NOT SUPPORTED as of  ISAM4.2.02 release.
-- Only relevant when VoIP provisioning style is standard (not legacy).
--
-- This interval table run time statistics for an active MGC association collected
-- over the previous 8 hours of operation.  The past 8 hours are
-- broken into 32 completed 15 minute intervals.  Each row in this table
-- represents one such interval associated with a MGC Config instance.  
--
-- An instance of this table is auto-created/deleted in accordance with the 
-- 'MGC PM Collect Indicator' setting of the MCG Config table.
--
--	For GPON - NOT SUPPORTED as of ISAM4.2.02
--	For XG-PON1 - NOT SUPPORTED as of ISAM4.6.02
--	For NG-PON2 - NOT SUPPORTED as of ISAM5.2
-- 
-- *********************************************


gponOntMgcIntervalTable  OBJECT-TYPE
	SYNTAX SEQUENCE OF GponOntMgcIntervalEntry
	ACCESS	not-accessible
	STATUS	mandatory
	::= { gponVoipGroup 11 }


gponOntMgcIntervalEntry  OBJECT-TYPE
	SYNTAX 	GponOntMgcIntervalEntry
	ACCESS	not-accessible
	STATUS	mandatory
	DESCRIPTION 
		"An entry in the gponOntMgcIntervalTable  "
	INDEX { ifIndex, gponOntMgcIntervalNumber
		 }

-- this is the ifIndex of the IP Host UNI.
	::= { gponOntMgcIntervalTable 1 }

GponOntMgcIntervalEntry ::= SEQUENCE {
	gponOntMgcIntervalNumber			INTEGER,
	gponOntMgcIntervalValidInd			Boolean,
	gponOntMgcIntervalRxMsgs			Counter,
	gponOntMgcIntervalRxOctets			Counter,
	gponOntMgcIntervalTxMsgs			Counter,
	gponOntMgcIntervalTxOctets			Counter,
	gponOntMgcIntervalProtocolErrors		Counter,
	gponOntMgcIntervalTransportLosses		Counter,
	gponOntMgcIntervalLastDetectedEvent		Counter,
	gponOntMgcIntervalLastDetectedEventTime	Counter,
	gponOntMgcIntervalLastDetectedResetTime	Counter
}

gponOntMgcIntervalNumber  OBJECT-TYPE
	SYNTAX 	INTEGER (1..32)
	ACCESS	read-only
	STATUS	mandatory
	DESCRIPTION 
		"A number between 1 and 32, where 1 is the most
		 recently completed 15 minute interval and 32
		 is the 15 minute interval completed 7 hours 
		 and 45 minutes prior to interval 1.  "
	::= { gponOntMgcIntervalEntry 1 }

gponOntMgcIntervalValidInd  OBJECT-TYPE
	SYNTAX 	Boolean
	ACCESS	read-only
	STATUS	mandatory
	DESCRIPTION 
		"Indicates whether or not this Interval contains
		 valid PM counts. 

		 NOT SUPPORTED "
	::= { gponOntMgcIntervalEntry 2 }

gponOntMgcIntervalRxMsgs  OBJECT-TYPE
	SYNTAX 	Counter
	ACCESS	read-only
	STATUS	mandatory
	DESCRIPTION 
		"A count of number of received Megaco messages on this association,
		 as defined by ITU-T H.341.  "
	::= { gponOntMgcIntervalEntry 3 }

gponOntMgcIntervalRxOctets  OBJECT-TYPE
	SYNTAX 	Counter
	ACCESS	read-only
	STATUS	mandatory
	DESCRIPTION 
		"A count of total number of octets received over this association,
		 as defined by ITU-T H.341.  "
	::= { gponOntMgcIntervalEntry 4 }

gponOntMgcIntervalTxMsgs  OBJECT-TYPE
	SYNTAX 	Counter
	ACCESS	read-only
	STATUS	mandatory
	DESCRIPTION 
		"A count of number of sent Megaco messages on this association,
		 as defined by ITU-T H.341.  "
	::= { gponOntMgcIntervalEntry 5 }

gponOntMgcIntervalTxOctets  OBJECT-TYPE
	SYNTAX 	Counter
	ACCESS	read-only
	STATUS	mandatory
	DESCRIPTION 
		"A count of total number of octets sent over this association,
		 as defined by ITU-T H.341.  "
	::= { gponOntMgcIntervalEntry 6 }

gponOntMgcIntervalProtocolErrors  OBJECT-TYPE
	SYNTAX 	Counter
	ACCESS	read-only
	STATUS	mandatory
	DESCRIPTION 
		"A count of total number of errors detected on this association,
		 as defined by ITU-T H.341. This includes:
		 - Syntax errors detected in a given received message.
		 - Outgoing transactions that failed for protocol reasons. "
	::= { gponOntMgcIntervalEntry 7 }

gponOntMgcIntervalTransportLosses  OBJECT-TYPE
	SYNTAX 	Counter
	ACCESS	read-only
	STATUS	mandatory
	DESCRIPTION 
		"A count of total number of transport losses (for example socket problems)
		 detected on this association. A link loss is defined as loss of communication
		 with the remote entity due to hardware/transient problems, or problems in
		 related software.  "
	::= { gponOntMgcIntervalEntry 8 }

gponOntMgcIntervalLastDetectedEvent  OBJECT-TYPE
	SYNTAX 	Counter
	ACCESS	read-only
	STATUS	mandatory
	DESCRIPTION 
		" This attribute reports the last detected event on this association.
		  This includes events such as link failing or being set up.  This attribute is
		  an enumeration as follows:

		  0 = No Event - No event has been detected as yet.
		  1 = Link Up - The transport link underpinning the association came up.
		  2 = Link Down - The transport link underpinning the association went down.
		  3 = Persistent Error - A persistent error was detected on the link (such as the socket
		        connection to the remote node could not be set up.
		  4 = Local Shutdown - The association was brought down intentionally by the 
		        local application.
		  5 = Failover Down - The association was brought down as part of failover processing.
		  255 = Other Event - The last event does not match any in the list.  "
	::= { gponOntMgcIntervalEntry 9 }

gponOntMgcIntervalLastDetectedEventTime  OBJECT-TYPE
	SYNTAX 	Counter
	ACCESS	read-only
	STATUS	mandatory
	DESCRIPTION 
		" This attribute reports the time in seconds since the last event on this association was 
		  detected, as defined by ITU-T H.341.  "
	::= { gponOntMgcIntervalEntry 10 }

gponOntMgcIntervalLastDetectedResetTime  OBJECT-TYPE
	SYNTAX 	Counter
	ACCESS	read-only
	STATUS	mandatory
	DESCRIPTION 
		" This attribute reports the time in seconds since these these statistics were last reset, 
		  as defined by ITU-T H.341.  "
	::= { gponOntMgcIntervalEntry 11 }


-- ********************************************************************************************************************************
--  Following tables should be deleted one day as they are not used in ISAM4.2.  But they are added back to MIB
--  to ease the transition to ISAM4.2.
-- ********************************************************************************************************************************



-- *********************************************
--  GPON OLT PERIODIC INFO TABLE
--
-- This table is SUPPORTED as of FGU4.7.
--
-- This table contains assorted periodic information that spans the whole OLT.
-- The table contains a single row.  Data is initially populated at OLT startup. Thereafter,
-- all data is refreshed a 5-minute wall-clock boundaries.
--
-- A single table row is created at OLT startup.
--
-- For ISAM4.0.10, this entire table is NOT SUPPORTED.
-- For ISAM4.2, this entire table is NOT SUPPORTED.
--
--	For GPON - NOT SUPPORTED as of ISAM4.0.10
--	For XG-PON1 - NOT SUPPORTED as of ISAM4.6.02
--	For NG-PON2 - NOT SUPPORTED as of ISAM5.2
--
-- *********************************************

gponOltPeriodInfoTable  OBJECT-TYPE
	SYNTAX SEQUENCE OF GponOltPeriodInfoEntry
	ACCESS	not-accessible
	STATUS	mandatory
	::= { gponOltGroup 7 }

gponOltPeriodInfoEntry  OBJECT-TYPE
	SYNTAX 	GponOltPeriodInfoEntry
	ACCESS	not-accessible
	STATUS	mandatory
	INDEX	{ gponOltPeriodInfoNumber }
	::= { gponOltPeriodInfoTable 1 }

GponOltPeriodInfoEntry ::= SEQUENCE {
	gponOltPeriodInfoNumber			INTEGER,
	gponOltPeriodInfoPotsLinesIsNr		INTEGER,
	gponOltPeriodInfoXdslLinesIsNr		INTEGER,
	gponOltPeriodInfoEnetLinesIsNr		INTEGER,
	gponOltPeriodInfoMocaLinesIsNr		INTEGER,
	gponOltPeriodInfoCesLinesIsNr		INTEGER,
	gponOltPeriodInfoPotsLinesOosAuma	 	INTEGER,
	gponOltPeriodInfoXdslLinesOosAuma	 	INTEGER,
	gponOltPeriodInfoEnetLinesOosAuma	 	INTEGER,
	gponOltPeriodInfoMocaLinesOosAuma	 	INTEGER,
	gponOltPeriodInfoCesLinesOosAuma	 	INTEGER,
	gponOltPeriodInfoPotsLinesOosAu	 	INTEGER,
	gponOltPeriodInfoXdslLinesOosAu	 	INTEGER,
	gponOltPeriodInfoEnetLinesOosAu	 	INTEGER,
	gponOltPeriodInfoMocaLinesOosAu	 	INTEGER,
	gponOltPeriodInfoCesLinesOosAu	 	INTEGER,
	gponOltPeriodInfoPotsLinesPreProv	 	INTEGER,
	gponOltPeriodInfoXdslLinesPreProv	 	INTEGER,
	gponOltPeriodInfoEnetLinesPreProv	 	INTEGER,
	gponOltPeriodInfoMocaLinesPreProv	 	INTEGER,
	gponOltPeriodInfoCesLinesPreProv	 	INTEGER
}

gponOltPeriodInfoNumber  OBJECT-TYPE
	SYNTAX 	INTEGER
	ACCESS	read-only
	STATUS	mandatory
	DESCRIPTION 
		"There is only 1 row in this table, so this value is always 1.

		For ISAM 4.0.10 -> this attribute is NOT SUPPORTED.  "
	::= { gponOltPeriodInfoEntry 1 }

gponOltPeriodInfoPotsLinesIsNr  OBJECT-TYPE
	SYNTAX 	INTEGER
	ACCESS	read-only
	STATUS	mandatory
	DESCRIPTION 
		" Number of POTS lines In-Service - Normal (IS-NR) (operationally registered and  
		  able to provide subscriber service).  States are Admin UP and Operational UP.

		  Range is from 0 - max POTS possible POTS lines in system.

		For ISAM 4.0.10 -> this attribute is NOT SUPPORTED. "
	::= { gponOltPeriodInfoEntry 2 }

gponOltPeriodInfoXdslLinesIsNr  OBJECT-TYPE
	SYNTAX 	INTEGER
	ACCESS	read-only
	STATUS	mandatory
	DESCRIPTION 
		" Number of Xdsl lines In-Service - Normal (IS-NR) (operationally registered and  
		  able to provide subscriber service).  States are Admin UP and Operational UP.

		  Range is from 0 - max possible XDSL lines in system.

		For ISAM 4.0.10 -> this attribute is NOT SUPPORTED. "
	::= { gponOltPeriodInfoEntry 3 }

gponOltPeriodInfoEnetLinesIsNr  OBJECT-TYPE
	SYNTAX 	INTEGER
	ACCESS	read-only
	STATUS	mandatory
	DESCRIPTION 
		" Number of Ethernet lines In-Service - Normal (IS-NR) (operationally registered and  
		  able to provide subscriber service).  States are Admin UP and Operational UP.

		  Range is from 0 - max possible Ethernet lines in system.

		For ISAM 4.0.10 -> this attribute is NOT SUPPORTED. "
	::= { gponOltPeriodInfoEntry 4 }

gponOltPeriodInfoMocaLinesIsNr  OBJECT-TYPE
	SYNTAX 	INTEGER
	ACCESS	read-only
	STATUS	mandatory
	DESCRIPTION 
		" Number of Moca lines In-Service - Normal (IS-NR) (operationally registered and  
		  able to provide subscriber service).  States are Admin UP and Operational UP.

		  Range is from 0 - max possible MoCA lines in system.

		For ISAM 4.0.10 -> this attribute is NOT SUPPORTED. "
	::= { gponOltPeriodInfoEntry 5 }

gponOltPeriodInfoCesLinesIsNr  OBJECT-TYPE
	SYNTAX 	INTEGER
	ACCESS	read-only
	STATUS	mandatory
	DESCRIPTION 
		" Number of CES lines In-Service - Normal (IS-NR) (operationally registered and  
		  able to provide subscriber service).  States are Admin UP and Operational UP.

		  Range is from 0 - max possible CES lines in system.

		For ISAM 4.0.10 -> this attribute is NOT SUPPORTED. "
	::= { gponOltPeriodInfoEntry 6 }


gponOltPeriodInfoPotsLinesOosAuma  OBJECT-TYPE
	SYNTAX 	INTEGER
	ACCESS	read-only
	STATUS	mandatory
	DESCRIPTION 
		" Number of POTS lines Out-of-Service - via management manual action (OOS-AUMA).

		  Range is from 0 - max possible POTS lines in system.

		For ISAM 4.0.10 -> this attribute is NOT SUPPORTED. "
	::= { gponOltPeriodInfoEntry 7 }

gponOltPeriodInfoXdslLinesOosAuma  OBJECT-TYPE
	SYNTAX 	INTEGER
	ACCESS	read-only
	STATUS	mandatory
	DESCRIPTION 
		" Number of XDSL lines Out-of-Service - via management manual action (OOS-AUMA).

		  Range is from 0 - max possible XDSL lines in system.

		For ISAM 4.0.10 -> this attribute is NOT SUPPORTED. "
	::= { gponOltPeriodInfoEntry 8 }

gponOltPeriodInfoEnetLinesOosAuma  OBJECT-TYPE
	SYNTAX 	INTEGER
	ACCESS	read-only
	STATUS	mandatory
	DESCRIPTION 
		" Number of Ethernet lines Out-of-Service - via management manual action (OOS-AUMA).

		  Range is from 0 - max possible Ethernet lines in system.

		For ISAM 4.0.10 -> this attribute is NOT SUPPORTED. "
	::= { gponOltPeriodInfoEntry 9 }

gponOltPeriodInfoMocaLinesOosAuma  OBJECT-TYPE
	SYNTAX 	INTEGER
	ACCESS	read-only
	STATUS	mandatory
	DESCRIPTION 
		" Number of MoCA lines Out-of-Service - via management manual action (OOS-AUMA).

		  Range is from 0 - max possible MoCA lines in system.

		For ISAM 4.0.10 -> this attribute is NOT SUPPORTED. "
	::= { gponOltPeriodInfoEntry 10 }

gponOltPeriodInfoCesLinesOosAuma  OBJECT-TYPE
	SYNTAX 	INTEGER
	ACCESS	read-only
	STATUS	mandatory
	DESCRIPTION 
		" Number of CES lines Out-of-Service - via management manual action (OOS-AUMA).

		  Range is from 0 - max possible CES lines in system.

		For ISAM 4.0.10 -> this attribute is NOT SUPPORTED. "
	::= { gponOltPeriodInfoEntry 11 }

gponOltPeriodInfoPotsLinesOosAu  OBJECT-TYPE
	SYNTAX 	INTEGER
	ACCESS	read-only
	STATUS	mandatory
	DESCRIPTION 
		" Number of POTS lines Out-of-Service - due to some fault (OOS-AU).

		  Range is from 0 - max possible POTS lines in system.

		For ISAM 4.0.10 -> this attribute is NOT SUPPORTED. "
	::= { gponOltPeriodInfoEntry 12 }

gponOltPeriodInfoXdslLinesOosAu  OBJECT-TYPE
	SYNTAX 	INTEGER
	ACCESS	read-only
	STATUS	mandatory
	DESCRIPTION 
		" Number of XDSL lines Out-of-Service - due to some fault (OOS-AU).

		  Range is from 0 - max possible XDSL lines in system.

		For ISAM 4.0.10 -> this attribute is NOT SUPPORTED. "
	::= { gponOltPeriodInfoEntry 13 }

gponOltPeriodInfoEnetLinesOosAu  OBJECT-TYPE
	SYNTAX 	INTEGER
	ACCESS	read-only
	STATUS	mandatory
	DESCRIPTION 
		" Number of Ethernet lines Out-of-Service - due to some fault (OOS-AU).

		  Range is from 0 - max possible Ethernet lines in system.

		For ISAM 4.0.10 -> this attribute is NOT SUPPORTED. "
	::= { gponOltPeriodInfoEntry 14 }

gponOltPeriodInfoMocaLinesOosAu  OBJECT-TYPE
	SYNTAX 	INTEGER
	ACCESS	read-only
	STATUS	mandatory
	DESCRIPTION 
		" Number of MoCA lines Out-of-Service - due to some fault (OOS-AU).

		  Range is from 0 - max possible MoCA lines in system.

		For ISAM 4.0.10 -> this attribute is NOT SUPPORTED. "
	::= { gponOltPeriodInfoEntry 15 }

gponOltPeriodInfoCesLinesOosAu  OBJECT-TYPE
	SYNTAX 	INTEGER
	ACCESS	read-only
	STATUS	mandatory
	DESCRIPTION 
		" Number of CES lines Out-of-Service - due to some fault (OOS-AU).

		  Range is from 0 - max possible CES lines in system.

		For ISAM 4.0.10 -> this attribute is NOT SUPPORTED. "
	::= { gponOltPeriodInfoEntry 16 }

gponOltPeriodInfoPotsLinesPreProv  OBJECT-TYPE
	SYNTAX 	INTEGER
	ACCESS	read-only
	STATUS	mandatory
	DESCRIPTION 
		" Number of POTS lines that have been pre-provisioned (but whose ONT has never
		  been ranged).

		  Range is from 0 - max possible POTS lines in system.

		For ISAM 4.0.10 -> this attribute is NOT SUPPORTED. "
	::= { gponOltPeriodInfoEntry 17 }

gponOltPeriodInfoXdslLinesPreProv  OBJECT-TYPE
	SYNTAX 	INTEGER
	ACCESS	read-only
	STATUS	mandatory
	DESCRIPTION 
		" Number of XDSL lines that have been pre-provisioned (but whose ONT has never
		  been ranged).

		  Range is from 0 - max possible XDSL lines in system.

		For ISAM 4.0.10 -> this attribute is NOT SUPPORTED. "
	::= { gponOltPeriodInfoEntry 18 }

gponOltPeriodInfoEnetLinesPreProv  OBJECT-TYPE
	SYNTAX 	INTEGER
	ACCESS	read-only
	STATUS	mandatory
	DESCRIPTION 
		" Number of Ethernet lines that have been pre-provisioned (but whose ONT has never
		  been ranged).

		  Range is from 0 - max possible Ethernet lines in system.

		For ISAM 4.0.10 -> this attribute is NOT SUPPORTED. "
	::= { gponOltPeriodInfoEntry 19 }

gponOltPeriodInfoMocaLinesPreProv  OBJECT-TYPE
	SYNTAX 	INTEGER
	ACCESS	read-only
	STATUS	mandatory
	DESCRIPTION 
		" Number of MoCA lines that have been pre-provisioned (but whose ONT has never
		  been ranged).

		  Range is from 0 - max possible MoCA lines in system.

		For ISAM 4.0.10 -> this attribute is NOT SUPPORTED. "
	::= { gponOltPeriodInfoEntry 20 }

gponOltPeriodInfoCesLinesPreProv  OBJECT-TYPE
	SYNTAX 	INTEGER
	ACCESS	read-only
	STATUS	mandatory
	DESCRIPTION 
		" Number of CES lines that have been pre-provisioned (but whose ONT has never
		  been ranged).

		  Range is from 0 - max possible CES lines in system.

		For ISAM 4.0.10 -> this attribute is NOT SUPPORTED. "
	::= { gponOltPeriodInfoEntry 21 }



-- ***************************************************
-- GPON OLT PERIODIC INFO LAST ACCESS TIME
--
-- This SCALAR contains the time stamp that represents the last time any
-- attribute in the gponOltPeriodInfoTable was accessed from an external 
-- management system.
--
--	For GPON - NOT SUPPORTED as of ISAM4.0.10
--	For XG-PON1 - NOT SUPPORTED as of ISAM4.6.02
--	For NG-PON2 - NOT SUPPORTED as of ISAM5.2
-- ******************************************************

gponOltPeriodInfoLastAccessTime OBJECT-TYPE
	SYNTAX 	INTEGER (0..4294967295)
	ACCESS	read-only
	STATUS	mandatory
	DESCRIPTION 
		" This attribute contains the time stamp that represents the last time any
		   attribute in the gponOltPeriodInfoTable was accessed from an external 
		   management system.

		  This attribute should be interpreted as Unix time seconds since midnight January 1,1970). 

		  Default = 0

		  SUPPORTED as of FGU4.7.

		For ISAM 4.0.10 -> this attribute is NOT SUPPORTED.  "
	::= { gponOltGroup 8 }


gponOltIOPOntControlMode  OBJECT-TYPE
        SYNTAX  INTEGER
        ACCESS  read-write
        STATUS  mandatory
        DESCRIPTION
                " Used to specify ONT vendors allowed by OLT system.
                if the vendor is not allowed:
                the ONT will be authenticated, but OLT will NOT configure it with OMCI. 
                ONT will be kept in O5 PLOAM state. 

                0 = Allow all vendors.
                1 = Only ALCL vendor allowed.

                Default = 0 = Allow all verdors.

	For GPON - NOT SUPPORTED as of ISAM4.0.10
	For XG-PON1 - NOT SUPPORTED as of ISAM4.6.02
	For NG-PON2 - NOT SUPPORTED as of ISAM5.2 "
        ::= { gponOltGroup 14 }


gponPonTrafficTcaInterval OBJECT-TYPE 
	SYNTAX Gauge 
	ACCESS read-write 
	STATUS mandatory 
	DESCRIPTION 
	" Used to specify PON or channel-pair traffic threshold detection interval. 
	Unit is seconds, in range of 60 - 86400 (1 minute - 1 day) 
	Default = 300

		Attribute introduced in ISAM4.6 MIB.  


	For GPON - SUPPORTED as of ISAM4.6 (for PONs)
	For XG-PON1 - SUPPORTED as of ISAM4.6.02 
	For NG-PON2 - NOT SUPPORTED as of ISAM5.2 (for channel pairs) " 
::= { gponOltGroup 15 }




gponOltSnAutoBundleTimer	OBJECT-TYPE
	SYNTAX	INTEGER
	ACCESS	read-write
	STATUS	mandatory
	DESCRIPTION
	" Used to specify the system timer (in hours) for bundling SN (with LOID/SLID) when ONT is in auto-bundle mode.
	Range is 1 - 72 (hours).

	Default = 24 (hours)

		Attribute introduced in ISAM4.6 MIB. 
 
	For GPON - SUPPORTED as of ISAM4.6
	For XG-PON1 - SUPPORTED as of ISAM4.6.02
	For NG-PON2 - SUPPORTED as of ISAM5.2 "
::= { gponOltGroup 16 }


-- ============================================================================
-- PON/Channel-Pair BW Utilization System Objects. 
-- ============================================================================

gponSysOltSidePonUtilPmCollectInd  OBJECT-TYPE
        SYNTAX  INTEGER
        ACCESS  read-write
        STATUS  mandatory
        DESCRIPTION
                " This system level attribute indicates whether PON/Channel-Pair 
                  BW Utilization Performance Monitor collections should be 
                  enabled/disabled for all PON/Channel-Pair interfaces.
       
		1 = Enable PM collection 
		2 = Disable PM collection   
    
                  Default = 2 = disabled.
                           
           ALCATEL NOTE:
           ACCESS:    NA
           USAGE:     NA
           PERSIST:   YES
           INSRVMOD:  YES
           RANGE:     1..2
           DEFVALUE:  2
           UNITS:     NA
           SPARSE:    NA
           DESCR:     FTTU ISAM 7342

	For GPON - SUPPORTED as of ISAM5.2 (for PONs)
	For XG-PON1 - NOT SUPPORTED as of ISAM4.6.02
	For NG-PON2 - NOT SUPPORTED as of ISAM5.2.01 (for channel pairs)

		NOTE: This means that as of ISAM5.2.01, this attribute value is shared
		by all PONs and channel-pairs that have applicable INHERIT option set
		for BW Utilization PMs and TCA settings.  "

        DEFVAL { 2 }
        ::={ gponOltGroup 17}

gponSysOltSidePonUtilHighTcaEnable  OBJECT-TYPE
        SYNTAX  INTEGER
        ACCESS  read-write
        STATUS  mandatory
        DESCRIPTION
       
                " This system level attribute specifies whether the TCA alarms 
                  reporting are enabled or disabled for all PON/channel-pair interfaces.
 
                  1 = TCA reporting enabled
                  2 = TCA reporting disabled
       
                  Default = 2 = disabled.  
                  
           ALCATEL NOTE:
           ACCESS:    NA
           USAGE:     NA
           PERSIST:   YES
           INSRVMOD:  YES
           RANGE:     1..2
           DEFVALUE:  2
           UNITS:     NA
           SPARSE:    NA
           DESCR:     FTTU ISAM 7342

	For GPON - SUPPORTED as of ISAM5.2 (for PONs)
	For XG-PON1 - NOT SUPPORTED as of ISAM4.6.02
	For NG-PON2 - NOT SUPPORTED as of ISAM5.2.01 (for channel pairs)

		NOTE: This means that as of ISAM5.2.01, this attribute value is shared
		by all PONs and channel-pairs that have applicable INHERIT option set
		for BW Utilization PMs and TCA settings. "


        DEFVAL {2 }

        ::={ gponOltGroup 18}
       
gponSysOltSidePonUtilHighThresholdLevelDown  OBJECT-TYPE
        SYNTAX  Threshold
        ACCESS  read-write
        STATUS  mandatory
        DESCRIPTION
                " System-level High threshold TCA setting in percentage for downstream total traffic.

		 
		Range is 0..100, represented in percentage as 0 to 100.

		A value of 0 means that this threshold is disabled.    
       
          ALCATEL NOTE:
           ACCESS:    NA
           USAGE:     NA
           PERSIST:   YES
           INSRVMOD:  YES
           RANGE:     0..100
           DEFVALUE:  0
           UNITS:     percent
           SPARSE:    NA
           DESCR:     FTTU ISAM 7342

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "


        DEFVAL { 0 }
        ::={ gponOltGroup 19}


gponSysOltSidePonUtilHighThresholdLevelUp  OBJECT-TYPE
        SYNTAX  Threshold
        ACCESS  read-write
        STATUS  mandatory
        DESCRIPTION
                " System-level High threshold TCA setting in percentage for total upstream
		traffic.
		 
		Range is 0..100, represented in percentage

		A value of 0 means that this threshold is disabled.

           Default = 0
           ALCATEL NOTE:
           ACCESS:    NA
           USAGE:     NA
           PERSIST:   YES
           INSRVMOD:  YES
           RANGE:     0..100
           DEFVALUE:  0
           UNITS:     percent
           SPARSE:    NA
           DESCR:     FTTU ISAM 7342

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "


        DEFVAL { 0 }
        ::={ gponOltGroup 20}
       
    
gponSysOltSidePonMcastUtilHighThresholdLevelDown  OBJECT-TYPE
        SYNTAX  Threshold
        ACCESS  read-write
        STATUS  mandatory
        DESCRIPTION
                " System-level High threshold TCA setting in percentage for downstream multicast traffic.
		 
		Range is 0..100, represented in percentage

		A value of 0 means that this threshold is disabled.

           Default = 0

           ALCATEL NOTE:
           ACCESS:    NA
           USAGE:     NA
           PERSIST:   YES
           INSRVMOD:  YES
           RANGE:     0..100
           DEFVALUE:  0
           UNITS:     percent
           SPARSE:    NA
           DESCR:     FTTU ISAM 7342

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "

        DEFVAL { 0 }
        ::={ gponOltGroup 21}

gponSysOltSidePonUtilHighThresholdDBACongestionUp  OBJECT-TYPE
        SYNTAX  Threshold
        ACCESS  read-write
        STATUS  mandatory
	DESCRIPTION 
        " System-level High threshold TCA setting in percentage for DBA Congestion.
	  This percentage is in relationship to the 5-minute PM/TCA interval.

		Range is 0..100, represented in percentage

		A value of 0 means that this threshold is disabled.

           Default = 0


           ALCATEL NOTE:
           ACCESS:    NA
           USAGE:     NA
           PERSIST:   YES
           INSRVMOD:  YES
           RANGE:     0..100
           DEFVALUE:  0
           UNITS:     NA
           SPARSE:    NA
           DESCR:     FTTU ISAM 7342

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "

        DEFVAL { 0 }
        ::={ gponOltGroup 22}

gponSysOltSidePonUtilNumTcIntervals  OBJECT-TYPE
        SYNTAX  INTEGER
        ACCESS  read-write
        STATUS  mandatory
        DESCRIPTION
                " System-level: This attribute specifies the number of contiguous intervals out 
                  of the total 96 (history) for the non-DBA thresholds to be exceeded in order to raise
                  TCA alarms.
       
                  Valid values are from 1 to 96.
                  Default = 1

           ALCATEL NOTE:
           ACCESS:    NA
           USAGE:     NA
           PERSIST:   YES
           INSRVMOD:  YES
           RANGE:     1..96
           DEFVALUE:  1
           UNITS:     NA
           SPARSE:    NA
           DESCR:     FTTU ISAM 7342

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "

        DEFVAL { 1 }
        ::={ gponOltGroup 23}



gponSysOltSidePonUtilHighThresholdTxUcastDroppedPackets     OBJECT-TYPE
        SYNTAX  OCTET STRING (SIZE(8))
        ACCESS  read-write
        STATUS  mandatory
        DESCRIPTION
                "System-level High threshold for count of transmit downstream unicast dropped packets
		 within interval in order to declare TCA alarm. 

		Range is 0..1,000,000,000

		A value of 0 means that this threshold is disabled.

		Default = 0  

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "         
        ::= { gponOltGroup 24 }                    
               
   

gponSysOltSidePonUtilHighThresholdRxTotalDroppedPackets     OBJECT-TYPE
        SYNTAX  OCTET STRING (SIZE(8))
        ACCESS  read-write
        STATUS  mandatory
        DESCRIPTION
                "System-level High threshold for count of receive upstream total dropped packets
		 within interval in order to declare TCA alarm. 

		Range is 0..1,000,000,000

		A value of 0 means that this threshold is disabled.

		Default = 0  

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "            
        ::= { gponOltGroup 25 }                                       


gponSysOltSidePonUtilHighThresholdTxMcastDroppedPackets     OBJECT-TYPE
        SYNTAX  OCTET STRING (SIZE(8))
        ACCESS  read-write
        STATUS  mandatory
        DESCRIPTION
                "System-level High threshold for count of transmit downstream multicast dropped packets
		 within interval in order to declare TCA alarm. 

		Range is 0..1,000,000,000

		A value of 0 means that this threshold is disabled.

		Default = 0  
	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "            
        ::= { gponOltGroup 26 }                                       
                

gponSysOltSidePonUtilHighThresholdTxBcastDroppedPackets     OBJECT-TYPE
        SYNTAX  OCTET STRING (SIZE(8))
        ACCESS  read-write
        STATUS  mandatory
        DESCRIPTION
                "System-level High threshold for count of transmit downstream broadcast dropped packets
		 within interval in order to declare TCA alarm. 

		Range is 0..1,000,000,000

		A value of 0 means that this threshold is disabled.

		Default = 0  

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "               
        ::= { gponOltGroup 27 }


gponSysOltSidePonUtilMediumThresholdLevelDown  OBJECT-TYPE
        SYNTAX  Threshold
        ACCESS  read-write
        STATUS  mandatory
        DESCRIPTION
                " System-level Medium threshold TCA setting in percentage for total downstream  traffic.

		 
		Range is 0..100, represented in percentage

		A value of 0 means that this threshold is disabled.    
       
          ALCATEL NOTE:
           ACCESS:    NA
           USAGE:     NA
           PERSIST:   YES
           INSRVMOD:  YES
           RANGE:     0..100
           DEFVALUE:  0
           UNITS:     percent
           SPARSE:    NA
           DESCR:     

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "    

        DEFVAL { 0 }
        ::={ gponOltGroup 28 }



gponSysOltSidePonUtilMediumThresholdLevelUp  OBJECT-TYPE
	SYNTAX 	Threshold
	ACCESS	read-write
	STATUS	mandatory
	DESCRIPTION 
        " System-level Medium threshold TCA setting in percentage for total upstream traffic.

		 
		Range is 0..100, represented in percentage

		A value of 0 means that this threshold is disabled.

           Default = 0

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "    
        ::={ gponOltGroup 29 }


gponSysOltSidePonMcastUtilMediumThresholdLevelDown  OBJECT-TYPE
	SYNTAX 	Threshold
	ACCESS	read-write
	STATUS	mandatory
	DESCRIPTION 
         " System-level Medium threshold TCA setting in percentage for downstream multicast traffic.
		 
		Range is 0..100, represented in percentage

		A value of 0 means that this threshold is disabled.

           Default = 0

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "    
	::= { gponOltGroup 30 }


gponSysOltSidePonUtilMediumThresholdDBACongestionUp   OBJECT-TYPE
	SYNTAX 	Threshold
	ACCESS	read-write
	STATUS	mandatory
	DESCRIPTION 
        " System-level Medium threshold TCA setting in percentage for DBA Congestion.
	  This percentage is in relationship to the 5-minute PM/TCA interval.

		Range is 0..100, represented in percentage

		A value of 0 means that this threshold is disabled.

           Default = 0


	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "    
	::= { gponOltGroup 31 }


gponSysOltSidePonUtilMediumThresholdTxUcastDroppedPackets     OBJECT-TYPE
        SYNTAX  OCTET STRING (SIZE(8))
        ACCESS  read-write
        STATUS  mandatory
        DESCRIPTION
                "System-level Medium threshold for count of transmit downstream unicast dropped packets
		 within interval in order to declare TCA alarm. 

		Range is 0..1,000,000,000

		A value of 0 means that this threshold is disabled.

		Default = 0  

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "                 
        ::= { gponOltGroup 32 }                    
               
   

gponSysOltSidePonUtilMediumThresholdRxTotalDroppedPackets     OBJECT-TYPE
        SYNTAX  OCTET STRING (SIZE(8))
        ACCESS  read-write
        STATUS  mandatory
        DESCRIPTION
                "System-level Medium threshold for count of receive upstream total dropped packets
		 within interval in order to declare TCA alarm. 

		Range is 0..1,000,000,000

		A value of 0 means that this threshold is disabled.

		Default = 0  

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "             
        ::= { gponOltGroup 33 }                                       


gponSysOltSidePonUtilMediumThresholdTxMcastDroppedPackets     OBJECT-TYPE
        SYNTAX  OCTET STRING (SIZE(8))
        ACCESS  read-write
        STATUS  mandatory
        DESCRIPTION
                "System-level Medium threshold for count of transmit downstream multicast dropped packets
		 within interval in order to declare TCA alarm. 

		Range is 0..1,000,000,000

		A value of 0 means that this threshold is disabled.

		Default = 0  

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "                 
        ::= { gponOltGroup 34 }                                       
                

gponSysOltSidePonUtilMediumThresholdTxBcastDroppedPackets     OBJECT-TYPE
        SYNTAX  OCTET STRING (SIZE(8))
        ACCESS  read-write
        STATUS  mandatory
        DESCRIPTION
                "System-level Medium threshold for count of transmit downstream broadcast dropped packets
		 within interval in order to declare TCA alarm. 

		Range is 0..1,000,000,000

		A value of 0 means that this threshold is disabled.

		Default = 0  

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "                    
        ::= { gponOltGroup 35 }



gponSysOltSidePonUtilLowThresholdLevelDown  OBJECT-TYPE
	SYNTAX 	Threshold
	ACCESS	read-write
	STATUS	mandatory
	DESCRIPTION 
         " System-level Low threshold TCA setting in percentage for total downstream traffic.

		 
		Range is 0..100, represented in percentage

		A value of 0 means that this threshold is disabled.

           Default = 0

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "    
	::= { gponOltGroup 36 }


gponSysOltSidePonUtilLowThresholdLevelUp  OBJECT-TYPE
	SYNTAX 	Threshold
	ACCESS	read-write
	STATUS	mandatory
	DESCRIPTION 
        " System-level Low threshold TCA setting in percentage for total upstream traffic.

		 
		Range is 0..100, represented in percentage

		A value of 0 means that this threshold is disabled.

           Default = 0

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "    
	::= { gponOltGroup 37 }


gponSysOltSidePonMcastUtilLowThresholdLevelDown  OBJECT-TYPE
	SYNTAX 	Threshold
	ACCESS	read-write
	STATUS	mandatory
	DESCRIPTION 
         " System-level Low threshold TCA setting in percentage for downstream multicast traffic.
		 
		Range is 0..100, represented in percentage

		A value of 0 means that this threshold is disabled.

           Default = 0

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "    
	::= { gponOltGroup 38 }


gponSysOltSidePonUtilLowThresholdDBACongestionUp   OBJECT-TYPE
	SYNTAX 	Threshold
	ACCESS	read-write
	STATUS	mandatory
	DESCRIPTION 
        " System-level low threshold TCA setting in percentage for DBA Congestion.
	  This percentage is in relationship to the 5-minute PM/TCA interval.

		Range is 0..100, represented in percentage

		A value of 0 means that this threshold is disabled.

           Default = 0



	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "    
	::= { gponOltGroup 39 }

gponSysOltSidePonUtilLowThresholdTxUcastDroppedPackets     OBJECT-TYPE
        SYNTAX  OCTET STRING (SIZE(8))
        ACCESS  read-write
        STATUS  mandatory
        DESCRIPTION
                "System-level Low threshold for count of transmit downstream unicast dropped packets
		 within interval in order to declare TCA alarm. 

		Range is 0..1,000,000,000

		A value of 0 means that this threshold is disabled.

		Default = 0  

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "                     
        ::= { gponOltGroup 40 }                    
               
   

gponSysOltSidePonUtilLowThresholdRxTotalDroppedPackets     OBJECT-TYPE
        SYNTAX  OCTET STRING (SIZE(8))
        ACCESS  read-write
        STATUS  mandatory
        DESCRIPTION
                "System-level Low threshold for count of receive upstream total dropped packets
		 within interval in order to declare TCA alarm. 

		Range is 0..1,000,000,000

		A value of 0 means that this threshold is disabled.

		Default = 0  

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "                 
        ::= { gponOltGroup 41 }                                       


gponSysOltSidePonUtilLowThresholdTxMcastDroppedPackets     OBJECT-TYPE
        SYNTAX  OCTET STRING (SIZE(8))
        ACCESS  read-write
        STATUS  mandatory
        DESCRIPTION
                "System-level Low threshold for count of transmit downstream multicast dropped packets
		 within interval in order to declare TCA alarm. 

		Range is 0..1,000,000,000

		A value of 0 means that this threshold is disabled.

		Default = 0  

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "                     
        ::= { gponOltGroup 42 }                                       
                

gponSysOltSidePonUtilLowThresholdTxBcastDroppedPackets     OBJECT-TYPE
        SYNTAX  OCTET STRING (SIZE(8))
        ACCESS  read-write
        STATUS  mandatory
        DESCRIPTION
                "System-level Low threshold for count of transmit downstream broadcast dropped packets
		 within interval in order to declare TCA alarm. 

		Range is 0..1,000,000,000

		A value of 0 means that this threshold is disabled.

		Default = 0  

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "                      
        ::= { gponOltGroup 43 }

gponSysOltSidePonUtilDbaCongestionThreshold  OBJECT-TYPE
	SYNTAX 	Threshold
	ACCESS	read-write
	STATUS	mandatory
	DESCRIPTION
         " System-level percentage of actual congestion within a DBA grant window wherein
	   the system declares a congested window. NOTE:  This window is NOT the
	   same as the 5-minute PM/TCA periods.
		 
		Range is 0..100, represented in percentage

           Default = 90

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "    
	::= { gponOltGroup 44 }

gponSysOltSidePonUtilNumDbaTcIntervals   OBJECT-TYPE
	SYNTAX 	INTEGER (1..96)
	ACCESS	read-write
	STATUS	mandatory
	DESCRIPTION 
		" Number of contiguous intervals (history) necessary for the DBA 
          thresholds to be exceeded for TCA alarm generation.

		  Default = 1

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "    
	::= { gponOltGroup 45 }


gponSysOltsidePonUtilOntDetailSelector OBJECT-TYPE
	SYNTAX 	INTEGER
	ACCESS	read-write
	STATUS	mandatory
	DESCRIPTION 
		" This attribute was first introduced with ISAM5.2. 
           
	   System-level attribute that specifies weather following ONT tables are enabled
	   for PONs that have PON Utilization PM collection enabled:
		- gponOltSideOntUtilPmCurrentIntervalTable
		- gponOltSideOntUtilPmIntervalTable

		1 = Enable PM collection 
		2 = Disable PM collection 

		 Default = 2

	For GPON - SUPPORTED as of ISAM5.2 (for PONs)
	For XG-PON1 - NOT SUPPORTED as of ISAM4.6.02
	NG-PON2 - NOT SUPPORTED as of ISAM5.2.01 (for channel pairs)

		NOTE: This means that as of ISAM5.2.01, this attribute value is shared
		by all PONs and channel-pairs that have applicable INHERIT option set
		for BW Utilization PMs and TCA settings. "    
	::= { gponOltGroup 46 }

-- =====================================================================================================
-- =====================================================================================================

gponSysOntSwVerMismatchTrafficBlockSelector  OBJECT-TYPE
        SYNTAX  INTEGER
        ACCESS  read-write
        STATUS  mandatory
        DESCRIPTION
                " This attribute was first introduced with ISAM5.2.

		System-level attribute used to specify ONT user traffic control behavior 
		upon occurrence of Software Version Mismatch (i.e. planned not equal to active).

                1 = enable (meaning block user traffic when ONT software version mismatch).
                2 = disable (meaning do NOT block user traffic when ONT software version mismatch).

                Default = 1 

	For GPON - SUPPORTED as of ISAM5.2
	For XG-PON1 - NOT SUPPORTED as of ISAM4.6.02
	For NG-PON2 - SUPPORTED as of ISAM5.2 "
	::= { gponOltGroup 47 }



gponOltRangeMode  OBJECT-TYPE
        SYNTAX  INTEGER
        ACCESS  read-write
        STATUS  mandatory
        DESCRIPTION
                " This attribute allows the manager to configure the ranging mode of GPON interface. 
                   Attribute values are as follows:
                   0 - Normal:  GPON use normal ranging mode
                   1 - AlienTolerant:  GPON use alien tolerant range mode which allow ONTs to range 
		       in the presence of Alien ONUs

                 Default = 0 = Normal 
 
        For GPON - SUPPORTED as of ISAM5.3
        For XG-PON1 - NOT SUPPORTED as of ISAM4.6.02
        For NG-PON2 - NOT SUPPORTED as of ISAM5.3 "
 
        ::= { gponOltGroup 48 }


-- *********************************************
--
-- GPON HGU TR069 CUSTOMIZED ALARM TABLE
-- This is a new table beginning with ISAM R5.3.01
-- This table contains the customized alarm description of HGU TR069
--
-- For GETs of table attributes, OLT will return the values in memory without having to access ONT directly. 
--
--  For GPON - SUPPORTED as of ISAM5.3.01
--  For XG-PON1 - NOT SUPPORTED as of ISAM5.3.01
--  For NG-PON2 - NOT SUPPORTED as of ISAM5.3.01
--
-- *********************************************

gponHGUTR069CustomizedAlarmTable  OBJECT-TYPE
    SYNTAX SEQUENCE OF GponHGUTR069CustomizedAlarmEntry
    ACCESS  not-accessible
    STATUS  mandatory
    ::= { gponOltGroup 49 }

gponHGUTR069CustomizedAlarmEntry  OBJECT-TYPE
    SYNTAX  GponHGUTR069CustomizedAlarmEntry
    ACCESS  not-accessible
    STATUS  mandatory
    DESCRIPTION
        "An entry in the GPON HGU TR069 customized alarm Table. "
    INDEX   { gponHGUTR069CustomizedAlarmIndex}
    ::= { gponHGUTR069CustomizedAlarmTable 1 }

GponHGUTR069CustomizedAlarmEntry ::= SEQUENCE {
    gponHGUTR069CustomizedAlarmIndex           INTEGER,
    gponHGUTR069CustomizedAlarmDescription     DisplayString,
    gponHGUTR069CustomizedAlarmRowStatus       RowStatus
}
    
gponHGUTR069CustomizedAlarmIndex  OBJECT-TYPE
    SYNTAX  INTEGER (1..31)
    ACCESS  read-only
    STATUS  mandatory
    DESCRIPTION
        " Each row is indexed by a number that
         indicate the TR069 customized alarm index.
                 
         Introduced in ISAM5.3.01 MIB

        For GPON - SUPPORTED as of ISAM5.3.01
        For XG-PON1 - NOT SUPPORTED as of ISAM5.3.01
        For NG-PON2 - NOT SUPPORTED as of ISAM5.3.01  "
    ::= { gponHGUTR069CustomizedAlarmEntry 1 }

gponHGUTR069CustomizedAlarmDescription  OBJECT-TYPE
    SYNTAX  DisplayString (SIZE(0..64))
    ACCESS  read-write
    STATUS  mandatory
    DESCRIPTION 
        "Indicate the TR069 customized alarm description.
                 
         Introduced in ISAM5.3.01 MIB

        For GPON - SUPPORTED as of ISAM5.3.01
        For XG-PON1 - NOT SUPPORTED as of ISAM5.3.01
        For NG-PON2 - NOT SUPPORTED as of ISAM5.3.01 "
    ::= { gponHGUTR069CustomizedAlarmEntry 2 }
    
gponHGUTR069CustomizedAlarmRowStatus  OBJECT-TYPE
    SYNTAX  RowStatus
    ACCESS  read-write
    STATUS  mandatory
    DESCRIPTION
        " All rows instantiated using 'create-and-go' to
         provision a customized alarm. Set to 'destroy' to delete
         a customized alarm. 
                 
         Introduced in ISAM5.3.01 MIB

        For GPON - SUPPORTED as of ISAM5.3.01
        For XG-PON1 - NOT SUPPORTED as of ISAM5.3.01
        For NG-PON2 - NOT SUPPORTED as of ISAM5.3.01 "
    ::= { gponHGUTR069CustomizedAlarmEntry 3 }

-- *********************************************
--
-- GPON OLT GIS INFO Group
-- This is a new group beginning with ISAM R5.6
--
-- This MIB group contains OLT GIS parameters apply to
-- all ONTs on all PONs in the entire shelf. 
--
--- for gponOltGISDigest, gponOltGISAreaCode, gponOltGISCheck, hex values should be stored.
-- Following a specific algorithm, we could get a check value calculated by the first 8 parameters(from gponOltGISLng to gponOltGISDigest),
-- The check value is represented by h1h2h3h4, which is consist of 4 hex characters.
-- h1h2h3 = ((unsigned long)gponOltGISLng + (unsigned long)gponOltGISLat + (unsigned short)gponOltGISElev + gponOltGISHrzErr +  \
-- \ gponOltGISAltErr + gponOltGISAreaCode + gponOltGISTimeStamp + gponOltGISDigest) % 4093
-- h4 = sumOf16ASCII(gponOltGISDigest) % 15
-- If the gponOltGISCheck matches the check value(h1h2h3*16+h4), the configuration would be accepted.Otherwise, the configuration would be rejected.
--
--  For GPON - SUPPORTED as of ISAM5.6.01
--  For XG-PON1 - NOT SUPPORTED as of ISAM5.6.01
--  For NG-PON2 - NOT SUPPORTED as of ISAM5.6.01
--  For XGS-PON - NOT SUPPORTED as of ISAM5.6.01
-- 
-- *********************************************
gponOltGISInfoTable OBJECT-TYPE
    SYNTAX SEQUENCE OF GponOltGISInfoEntry
    ACCESS  not-accessible
    STATUS  mandatory
    ::= { gponGISInfoGroup 1 }

gponOltGISInfoEntry  OBJECT-TYPE
    SYNTAX  GponOltGISInfoEntry
    ACCESS  not-accessible
    STATUS  mandatory
    DESCRIPTION
        " An entry in Gpon Olt GIS Info Table 

          Introduced in ISAM5.6 MIB, with targeted implementation in ISAM5.6.01

          For GPON - SUPPORTED as of ISAM5.6.01
          For XG-PON1 - NOT SUPPORTED as of ISAM5.6.01
          For NG-PON2 - NOT SUPPORTED as of ISAM5.6.01 
          For XGS-PON - NOT SUPPORTED as of ISAM5.6.01"
    INDEX   { gponOltGISIndex }          
    ::= { gponOltGISInfoTable 1 }

GponOltGISInfoEntry ::= SEQUENCE {
    gponOltGISIndex            INTEGER,
    gponOltGISLng              INTEGER,
    gponOltGISLat              INTEGER,
    gponOltGISElev             INTEGER,
    gponOltGISHrzErr           INTEGER,
    gponOltGISAltErr           INTEGER,
    gponOltGISAreaCode         OCTET STRING,
    gponOltGISTimeStamp        INTEGER,
    gponOltGISDigest           OCTET STRING,
    gponOltGISCheck            OCTET STRING
}

gponOltGISIndex  OBJECT-TYPE
    SYNTAX  INTEGER (1..1)
    ACCESS  read-write
    STATUS  mandatory
    DESCRIPTION
        "Each row is indexed by a number that
         indicate the index of gponOltGISInfoTable. 
         
         ALCATEL NOTE:
           ACCESS:    NA
           USAGE:     NA
           PERSIST:   NO
           INSRVMOD:  NA
           RANGE:     1..1
           DEFVALUE:  NA
           UNITS:     NA
           SPARSE:    NA
           DESCR:     NA
         
         Introduced in ISAM5.6 MIB, with targeted implementation in ISAM5.6.01

        For GPON - SUPPORTED as of ISAM5.6.01
        For XG-PON1 - NOT SUPPORTED as of ISAM5.6.01
        For NG-PON2 - NOT SUPPORTED as of ISAM5.6.01 
        For XGS-PON - NOT SUPPORTED as of ISAM5.6.01"
    ::= { gponOltGISInfoEntry 1 }
    
gponOltGISLng  OBJECT-TYPE
    SYNTAX  INTEGER (-18000000..18000000)
    ACCESS  read-write
    STATUS  mandatory
    DESCRIPTION
        " This attribute indicates the longitude of the geographical location
          The allowable range is constrained to (-18000000..18000000).
          The actual value should be devided by 100000.
          eg, 11639147 represents east longitude 116.39147
          
	        Default = 0 
         
          ALCATEL NOTE:
           ACCESS:    NA
           USAGE:     NA
           PERSIST:   YES
           INSRVMOD:  YES
           RANGE:     -18000000..18000000
           DEFVALUE:  NA
           UNITS:     0.00001 degree
           SPARSE:    NA
           DESCR:     NA
           
          Introduced in ISAM5.6 MIB, with targeted implementation in ISAM5.6.01

          For GPON - SUPPORTED as of ISAM5.6.01
          For XG-PON1 - NOT SUPPORTED as of ISAM5.6.01
          For NG-PON2 - NOT SUPPORTED as of ISAM5.6.01
          For XGS-PON - NOT SUPPORTED as of ISAM5.6.01"
    ::= { gponOltGISInfoEntry 2 }

gponOltGISLat  OBJECT-TYPE
    SYNTAX  INTEGER (-9000000..9000000)
    ACCESS  read-write
    STATUS  mandatory
    DESCRIPTION
        " This object indicates the latitude of the geographical location
          The allowable range is constrained to (-9000000..9000000).
          The actual value should be devided by 100000.
          eg, 3990648 represents north latitude 39.90648
          
	        Default = 0
	         
	       ALCATEL NOTE:
           ACCESS:    NA
           USAGE:     NA
           PERSIST:   YES
           INSRVMOD:  YES
           RANGE:     -9000000..9000000
           DEFVALUE:  NA
           UNITS:     0.00001 degree
           SPARSE:    NA
           DESCR:     NA
           
          Introduced in ISAM5.6 MIB, with targeted implementation in ISAM5.6.01

         For GPON - SUPPORTED as of ISAM5.6.01
         For XG-PON1 - NOT SUPPORTED as of ISAM5.6.01
         For NG-PON2 - NOT SUPPORTED as of ISAM5.6.01 
	 For XGS-PON - NOT SUPPORTED as of ISAM5.6.01 "
    ::= { gponOltGISInfoEntry 3 }
 
gponOltGISElev  OBJECT-TYPE
    SYNTAX  INTEGER (-32768..32767)
    ACCESS  read-write
    STATUS  mandatory
    DESCRIPTION
        " This object indicates the elevation of the geographical location
          The allowable range is constrained to (-32768..32767).
          The unit is meter.
          eg, 15 represents 15m
          
	        Default = 0 
	        
	       	ALCATEL NOTE:
           ACCESS:    NA
           USAGE:     NA
           PERSIST:   YES
           INSRVMOD:  YES
           RANGE:     -32768..32767
           DEFVALUE:  NA
           UNITS:     m
           SPARSE:    NA
           DESCR:     NA
            
         Introduced in ISAM5.6 MIB, with targeted implementation in ISAM5.6.01

         For GPON - SUPPORTED as of ISAM5.6.01
         For XG-PON1 - NOT SUPPORTED as of ISAM5.6.01
         For NG-PON2 - NOT SUPPORTED as of ISAM5.6.01
	 For XGS-PON - NOT SUPPORTED as of ISAM5.6.01 "
    ::= { gponOltGISInfoEntry 4 }
 
gponOltGISHrzErr  OBJECT-TYPE
    SYNTAX  INTEGER (0..65535)
    ACCESS  read-write
    STATUS  mandatory
    DESCRIPTION
        " This object indicates the horizontal error of the geographical location
          The allowable range is constrained to (0..65535).
          The unit is meter.
          eg, 15 represents 15m
          
	        Default = 0 
	        
	       	ALCATEL NOTE:
           ACCESS:    NA
           USAGE:     NA
           PERSIST:   YES
           INSRVMOD:  YES
           RANGE:     0..65535
           DEFVALUE:  NA
           UNITS:     m
           SPARSE:    NA
           DESCR:     NA
            
         Introduced in ISAM5.6 MIB, with targeted implementation in ISAM5.6.01

         For GPON - SUPPORTED as of ISAM5.6.01
         For XG-PON1 - NOT SUPPORTED as of ISAM5.6.01
         For NG-PON2 - NOT SUPPORTED as of ISAM5.6.01
	 For XGS-PON - NOT SUPPORTED as of ISAM5.6.01 "
    ::= { gponOltGISInfoEntry 5 }
  
gponOltGISAltErr  OBJECT-TYPE
    SYNTAX  INTEGER (0..65535)
    ACCESS  read-write
    STATUS  mandatory
    DESCRIPTION
        " This object indicates the altitude error of the geographical location
          The allowable range is constrained to (0..65535).
          The unit is meter.
          eg, 15 represents 15m
          
	        Default = 0 
	       
	       ALCATEL NOTE:
           ACCESS:    NA
           USAGE:     NA
           PERSIST:   YES
           INSRVMOD:  YES
           RANGE:     0..65535
           DEFVALUE:  NA
           UNITS:     m
           SPARSE:    NA
           DESCR:     NA
            
         Introduced in ISAM5.6 MIB, with targeted implementation in ISAM5.6.01

         For GPON - SUPPORTED as of ISAM5.6.01
         For XG-PON1 - NOT SUPPORTED as of ISAM5.6.01
         For NG-PON2 - NOT SUPPORTED as of ISAM5.6.01
	 For XGS-PON - NOT SUPPORTED as of ISAM5.6.01 "
    ::= { gponOltGISInfoEntry 6 }
 
gponOltGISAreaCode  OBJECT-TYPE
    SYNTAX OCTET STRING (SIZE(6))
    ACCESS  read-write
    STATUS  mandatory
    DESCRIPTION
        " This object indicates the area code of the geographical location
                    
	        Default = all zeros. 
	        
	       	ALCATEL NOTE:
           ACCESS:    NA
           USAGE:     NA
           PERSIST:   YES
           INSRVMOD:  YES
           RANGE:     NA
           DEFVALUE:  0
           UNITS:     NA
           SPARSE:    NA
           DESCR:     NA
            
         Introduced in ISAM5.6 MIB, with targeted implementation in ISAM5.6.01

         For GPON - SUPPORTED as of ISAM5.6.01
         For XG-PON1 - NOT SUPPORTED as of ISAM5.6.01
         For NG-PON2 - NOT SUPPORTED as of ISAM5.6.01
	 For XGS-PON - NOT SUPPORTED as of ISAM5.6.01 "
    ::= { gponOltGISInfoEntry 7 }
    
gponOltGISTimeStamp  OBJECT-TYPE
    SYNTAX  INTEGER (0..4294967295)
    ACCESS  read-write
    STATUS  mandatory
    DESCRIPTION
        " This attribute should be interpreted as Unix time (seconds since midnight January 1,1970).
          This attributes represents the time that this geographical location information was generated.
          
	        Default = 0 
	       
	        ALCATEL NOTE:
           ACCESS:    NA
           USAGE:     NA
           PERSIST:   YES
           INSRVMOD:  YES
           RANGE:     0..4294967295
           DEFVALUE:  NA
           UNITS:     seconds
           SPARSE:    NA
           DESCR:     NA
           
         Introduced in ISAM5.6 MIB, with targeted implementation in ISAM5.6.01

         For GPON - SUPPORTED as of ISAM5.6.01
         For XG-PON1 - NOT SUPPORTED as of ISAM5.6.01
         For NG-PON2 - NOT SUPPORTED as of ISAM5.6.01
	 For XGS-PON - NOT SUPPORTED as of ISAM5.6.01 "
    ::= { gponOltGISInfoEntry 8 }
     
gponOltGISDigest  OBJECT-TYPE
    SYNTAX  OCTET STRING(SIZE(8))
    ACCESS  read-write
    STATUS  mandatory
    DESCRIPTION
        " This object indicates the gis digest of the geographical location
          		 
	        Default = all zeros. 
	        
	       ALCATEL NOTE:
           ACCESS:    NA
           USAGE:     NA
           PERSIST:   YES
           INSRVMOD:  YES
           RANGE:     NA
           DEFVALUE:  0
           UNITS:     NA
           SPARSE:    NA
           DESCR:     NA 
            
         Introduced in ISAM5.6 MIB, with targeted implementation in ISAM5.6.01

         For GPON - SUPPORTED as of ISAM5.6.01
         For XG-PON1 - NOT SUPPORTED as of ISAM5.6.01
         For NG-PON2 - NOT SUPPORTED as of ISAM5.6.01
	 For XGS-PON - NOT SUPPORTED as of ISAM5.6.01 "
    ::= { gponOltGISInfoEntry 9 }
    
gponOltGISCheck  OBJECT-TYPE
    SYNTAX  OCTET STRING(SIZE(2))
    ACCESS  read-write
    STATUS  mandatory
    DESCRIPTION
        " This object indicates the gis check of the geographical location
                   
	       Default =  all zeros. 
	        
	       ALCATEL NOTE:
           ACCESS:    NA
           USAGE:     NA
           PERSIST:   YES
           INSRVMOD:  YES
           RANGE:     NA
           DEFVALUE:  0
           UNITS:     NA
           SPARSE:    NA
           DESCR:     NA 
            
         Introduced in ISAM5.6 MIB, with targeted implementation in ISAM5.6.01

         For GPON - SUPPORTED as of ISAM5.6.01
         For XG-PON1 - NOT SUPPORTED as of ISAM5.6.01
         For NG-PON2 - NOT SUPPORTED as of ISAM5.6.01
	 For XGS-PON - NOT SUPPORTED as of ISAM5.6.01 "
    ::= { gponOltGISInfoEntry 10 } 
END
