--===================================================================
-- This specification is published by Alcatel-lucent under Non-Disclosure
-- Agreement(s) (NDA) with specific parties and has to be considered as
-- Confidential Information as defined in such NDA.
-- Alcatel-lucent reserves the right to revise this document for any reason,
-- including but not limited to conformity with standards promulgated by
-- various agencies, utilization of advances in the state of the technical
-- areas, or the reflection of changes in the design of any equipment,
-- techniques, or procedures described or referred to herein.
-- The product specifications and other technical or performance
-- information contained herein are subject to change without notice.
-- Updates of this document will be issued under the above NDA's.
-- Alcatel-lucent makes no representation or warranty, expressed or implied, with
-- respect to the sufficiency, accuracy, or utility of any information or
-- opinion contained herein. Alcatel-lucent expressly advises that any use of for
-- any purpose or reliance upon this technical reference is at the risk of
-- the user and that Alcatel-lucent shall not be liable for any damage or injury
-- incurred by any person arising out of the sufficiency, accuracy, or
-- utility of any information or opinion contained herein.
-- This document is not to be construed as a suggestion to any manufacturer
-- to modify or change any of its products, nor does this document
-- represent any commitment by Alcatel-lucent to sell or purchase any product.
-- Nothing contained herein shall be construed as conferring by implication,
-- estoppel, or otherwise any license or right under any patent, whether or
-- not the use of any information herein necessarily employs an invention
-- of any existing or later issued patent.
-- Alcatel-lucent reserves the right not to offer any or all of these products and
-- to withdraw any or all of them at any future time.
-- 
-- Copyright (C) 2003, Alcatel-lucent. All Rights Reserved.
--==============================================================================
-- HISTORY
--  REVISION     "201704140000z"
--  DESCRIPTION
--   "Version:  based on changeset ed75ab537baf
--    Editor: Rain Ding(rain.ding@alcatel-lucent.com)
--    Changes:
--    For FR ALU02348777 CLI/MIB mismatch for digit manipulation rule:
--    For FR ALU02358173 Misalignment between MIB and CLI
--    Update the description for sipRule in table sipRuleTable.
--    Change 'inc-add-country-code-for-national-number' to 'inc-add-phone-context-to-number'.
--==============================================================================

--==============================================================================
-- HISTORY
--  REVISION     "201703170000z"
--  DESCRIPTION
--   "Version:  based on changeset 5d7e9873f586
--    Editor: Joy Wang (joy.wang@alcatel-lucent.com)
--    Changes:
--    For RCR ALU02079243 ISAMV: SIP NPOTs to support shared lines:
--    Change 'internallyBlocked' to 'sharedCutoff' for callstatus in sipTerminationTable and sipSharedLineTermTable. 
--==============================================================================

--==============================================================================
-- HISTORY
--  REVISION     "201703020000z"
--  DESCRIPTION
--   "Version:  based on changeset 79ef82010846
--    Editor: Fred Zhou (F.Zhou@nokia.com)
--    Changes:
--    For RCR ALU02079243 ISAMV: SIP NPOTs to support shared lines:
--     Update sipSharedLineTermTable description due to maximum number terminations
--     supported by NPOT-B and NPOT-C is changed.
--==============================================================================
-- HISTORY
--  REVISION     "201612140000z"
--  DESCRIPTION
--   "Version:  based on changeset 58b8e9a4e190
--    Editor: Fred Zhou (F.Zhou@nokia.com)
--    Changes:
--    For RCR ALU02079243 ISAMV: SIP NPOTs to support shared lines:
--     Update some description according to MIB review.
--==============================================================================
-- HISTORY
--  REVISION     "201611110000z"
--  DESCRIPTION
--   "Version:  based on changeset 67ebea686ddc
--    Editor: Fred Zhou (F.Zhou@nokia.com)
--    Changes:
--    For RCR ALU02079243 ISAMV: SIP NPOTs to support shared lines:
--     Add 'internallyBlocked' for callstatus in sipTerminationTable and sipSharedLineTermTable.
--==============================================================================
--==============================================================================
-- HISTORY
--  REVISION     "201611010000z"
--  DESCRIPTION
--   "Version:  based on changeset ce5bb4a6f52b
--    Editor: Fred Zhou (F.Zhou@nokia.com)
--    Changes:
--    For RCR ALU02079243 ISAMV: SIP NPOTs to support shared lines:
--     Add objects sipSharedLineTermETSIClipDataMode, sipSharedLineTermEnableCallWaiting,
--     sipSharedLineTermEnableCallHold, sipSharedLineTermEnableCallConference and
--     sipSharedLineTermEnableCallTransfer for sipSharedLineTermTable
--==============================================================================
--==============================================================================
--HISTORY
--  REVISION    "201608310000z"
--  DESCRIPTION
--    "Version: based on changeset 3ef955da4c03 
--     Editor: Hanks Li (hanks.li@alcatel-lucent.com)
--     Changes:
--     For RCR ALU02079243 ISAMV: SIP NPOTs to support shared lines:
--       Add table sipSharedLineTermTable, entry SipSharedLineTermEntry, objects sipSharedLineTermDn, sipSharedLineTermUserName, sipSharedLineTermUri, sipSharedLineTermCallStatus, sipSharedLineTermAdminStatus, sipSharedLineTermOperStatus, sipSharedLineTermRowStatus, sipSharedLineTermContactUserInfo, sipSharedLineTermDisplayName."
--==============================================================================
-- =============================================================================
-- HISTORY
--  REVISION    "201608220000z"
--  DESCRIPTION
--   "Version:  based on changeset d387312ca22a
--    Editor: Dixon Wang (wang.dixon@alcatel-lucent.com.cn)
--    Changes:
--    For RCR ALU02046042:
--       Update description for objects: sipIsdnCasTerminationOperStatus, sipIsdnCasTerminationOpStatDownReason, sipIsdnCasTerminationNbrBChannelIdle, sipIsdnCasTerminationNbrBChannelUsed, sipIsdnCasTerminationPUIDlist, sipIsdnCasTerminationTestState.
-- =============================================================================
-- =============================================================================
-- HISTORY
--  REVISION    "201608170000z"
--  DESCRIPTION
--   "Version:  based on changeset c5514bfe6778
--    Editor: Dixon Wang (wang.dixon@alcatel-lucent.com.cn)
--    Changes:
--    For RCR ALU02046042:
--       Update bearerOperStatus of sipBChannelTable to bearerChannelOperStatus.
-- =============================================================================
-- =============================================================================
-- HISTORY
--  REVISION    "201608150000z"
--  DESCRIPTION
--   "Version:  based on changeset 9c70de93f01f
--    Editor: Dixon Wang (wang.dixon@alcatel-lucent.com.cn)
--    Changes:
--    For RCR ALU02046042:
--       Update all description of PRA ISDN SIP to PRA ISDN or R2 CAS SIP.
-- =============================================================================
-- =============================================================================
-- HISTORY
--  REVISION    "201608050000z"
--  DESCRIPTION
--   "Version:  based on changeset ea65b11e8d81
--    Editor: Dixon Wang (wang.dixon@alcatel-lucent.com.cn)
--    Changes:
--    For RCR ALU02046042:
--       Consider R2/CAS requirement, update sipIsdnTerminationTable name to sipIsdnCasTerminationTable.
-- =============================================================================
-- =============================================================================
-- HISTORY
--  REVISION    "201607130000z"
--  DESCRIPTION
--   "Version:  based on changeset d5840dc5133a
--    Editor: Candy Yin (yin.candy@alcatel-sbell.com.cn)
--    Changes:
--    For RCR ALU02244377:
--       1. remove some messy code like ? or >.
-- =============================================================================
-- =============================================================================
-- HISTORY
--  REVISION    "201606280000z"
--  DESCRIPTION
--   "Version:  based on changeset a7e677a1afda 
--    Editor: Rain Ding (rain.ding@alcatel-lucent.com)
--    Changes:
--    For RCR ALU02222057 
--       Update DESCRIPTION of SipTerminationImpedance in sipTerminationTable.
--       Update range of SipTerminationImpedance in sipTerminationTable.
--    For RCR ALU02231452 
--       Update the range of sipUserAgentVlanId:[1.4093]
--       Update the range of sipUserAgentRtpVlanId:[0.4093].
-- =============================================================================
-- =============================================================================
-- HISTORY
--  REVISION    "201605290000z"
--  DESCRIPTION
--   "Version:  based on changeset ac1972c36102
--    Editor: Jun Wang (Jun.AG.Wang@alcatel-lucent.com)
--    Changes:
--    For RCR ALU02114002
--          add new table sipSSPProfileMappingTable
-- =============================================================================
-- =============================================================================
-- HISTORY
--  REVISION    "201605190000z"
--  DESCRIPTION
--   "Version:  based on changeset 2357ee579017
--    Editor: Arthur Gu (arthur.gu@alcatel-lucent.com)
--    Changes:
--    For RCR ALU02114002
--          1. sipDNSServerTable
--              - enlarge TABLESIZE: 6->96
--              - change range of sipDNSServerId from (1...6) to (1...96)
--          2. sipDNSServerMappingTable
--              - enlarge TABLESIZE: 6->96
--              - change range of sipDNSServerMappingId from (1...6) to (1...96)
-- =============================================================================
-- CONTACT-INFO "liu Tao"  <Email#:tao.b.liu@alcatel-sbell.com.cn>
-- MODULE-IDENTITY
-- LAST-UPDATED "2009-11-13"
-- ORGANIZATION "Alcatel-lucent"
-- ORIGINATOR "Liu Tao"
-- 
-- Postal:
-- 6#-B502
-- Ningqiao Road No.388
-- 201206 ShangHai
-- China
-- ===================================================================
-- HISTORY
--  REVISION    "201605260000Z"
--  DESCRIPTION
--   "Version:  based on changeset 38f3f55c9484
--    Editor: Loren Zhang (zhang.loren@alcatel-lucent.com)
--     Changes:
--        1. change INSRVMOD to NO for sipUserAgentDHCPOptionReqList
-- ===================================================================
-- HISTORY
--  REVISION    "201605140000Z"
--  DESCRIPTION
--   "Version:  based on changeset 74ba99d6b3da
--    Editor: Loren Zhang (zhang.loren@alcatel-lucent.com)
--     Changes:
--        1. Update description of sipUserAgentTable for ALU02114002. 
--        2. Update description of sipUserAgentAccessPointTable for ALU02114002.
-- ===================================================================
-- HISTORY
--  REVISION    "201604180000Z"
--  DESCRIPTION
--   "Version:  based on changeset 2242baa92570 
--    Editor: Jason Chen (Jason.A.Chen@alcatel-lucent.com)
--     Changes:
--        1. For the counters sipTermStatsP15mOutFailLostSeiz,sipTermStatsP15mInFailLostSeiz and    
--           sipTermStatsP15mOutSuccInitInv will be implemented in R55, 
--           modified the mib description in the sipTermStatsP15mEntry.
--        2. For the counters sipTermStatsC15mOutFailLostSeiz,sipTermStatsC15mInFailLostSeiz and    
--           sipTermStatsC15mOutSuccInitInv will be implemented in R55, 
--           modified the mib description in the sipTermStatsC15mEntry.
--   
-- ===================================================================
-- HISTORY
-- REVISION     "201604160000z"a
-- DESCRIPTION
--  "Version:  based on changeset 5e1968c74f1e 
--  Editor: jun.ag.wang@alcatel-lucent.com
--  Changes:
--  For RCR ALU02114002
--      1. Add new table: sipDhcpSipServerTable
-- ===================================================================
-- HISTORY
--  REVISION    "201604120000Z"
--  DESCRIPTION
--   "Version:  based on changeset 8b48b4a87c96
--    Editor: Jason Chen (Jason.A.Chen@alcatel-lucent.com)
--     Requirment:
--      OID has already been used in the R54 MIB should not be re-used for the definition of other (different) objects in R5401.
--     Changes:
--         1. modified sipTermStatsP15mEntry
--              -change the current OID to be the OID used in the R54 mib
--         2. modified sipTermStatsC15mEntry
--              -change the current OID to be the OID used in the R54 mib
--     
-- ===================================================================
-- HISTORY
-- REVISION     "201603230000z"a
-- DESCRIPTION
--  "Version:  based on changeset eaef86a35160 
--  Editor: rain.ding@alcatel-lucent.com
--  Changes:
--  For RCR ALU02054042 
--       Add four objects to sipUserAgentTable
--         -new objects: sipUALSAVoiceDefaultGW
--                       sipUALSARTPVlanId
--                       sipUALSAMD5Realm 
--                       sipUALSAMD5Password 
--       Add two objects to sipUserAgentAccessPointTable 
--         -new objects: sipUaApLSARtpIpAddr 
--                       sipUaApLSARtpIpPrefixLength
--       extend the RANGE of sipServerRole
--         -RANGE:  4 | 16 | 20 | 32
-- ===================================================================
-- HISTORY
-- REVISION     "201603220000z"a
-- DESCRIPTION
--  "Version:  based on changeset f21298709aae
--  Editor: Jun.ag.Wang@alcatel-lucent.com
--  Changes:
--  For RCR ALU02114002
--       Change sipSSPProfileId range in table: sipSSPProfileTable.
-- ===================================================================
-- 
-- ===================================================================
-- HISTORY
-- REVISION     "201603220000z"a
-- DESCRIPTION
--  "Version:  based on changeset f21298709aae
--  Editor: Jun.ag.Wang@alcatel-lucent.com
--  Changes:
--  For RCR ALU02114002
--       Change sipSSPProfileId range in table: sipSSPProfileTable.
-- ===================================================================
-- 
-- ===================================================================
-- HISTORY
-- REVISION     "201603210000z"a
-- DESCRIPTION
--  "Version:  based on changeset 0936433ad1c9 
--  Editor: Jun.ag.Wang@alcatel-lucent.com
--  Changes:
--  For RCR ALU02114002
--       Remove object sipSSPProfileIndex in table: sipSSPProfileTable.
--       Change INDEX to sipSSPProfileId in table: sipSSPProfileTable.
--       Change sipSSPProfileId range in table: sipSSPProfileTable.
-- ===================================================================

-- ===================================================================
-- HISTORY
-- REVISION     "201603030000z"a
-- DESCRIPTION
--  "Version:  based on changeset 5ae867cfb445 
--  Editor: Xiaosheng.Jiang@alcatel-lucent.com
--  Changes:
--  For RCR ALU02114002
--       Add new object: sipSSPProfileIndex in table: sipSSPProfileTable.
-- ===================================================================

-- ===================================================================
-- HISTORY
-- REVISION     "201602040000z"a
-- DESCRIPTION
--  "Version:  based on changeset 454e14022583 
--  Editor: zhang.loren@alcatel-lucent.com
--  Changes:
--  For RCR ALU02114002
--      1. Add new table: sipSSPProfileTable
--      2. Add new object: sipVSPSSPProfileName in table: sipVSPTable.
-- ===================================================================
-- HISTORY
--  DESCRIPTION
--   "Version:  based on changeset 9a02b94ad45e
--    Editor: Phoebe Li (Phoebe.li@alcatel-lucent.com)
--    Changes: 
--    For RCR ALU02082604
--      Requirement changed for DTAG feature RCR ALU02137511, only define 15 conters in this RCR.
--          1. remove 2 tables and all their termination codec statistics counters (RCR ALU02137511)
--              - removed: sipTermCodecStatsP15mTable
--              - removed: sipTermCodecStatsC15mTable        
--          2. remove 2 tables and all their Board DSP statistics counters (RCR ALU02137511)
--              - removed: sipBoardDspStatsP15mTable 
--              - removed: sipBoardDspStatsC15mTable 
--          3. modified sipTermStatsP15mEntry (RCR ALU02137511)
--              - remove 5 objects 
--                OutgCallAttemptsWithRBT,OutgCallAttemptsWithRBTNoAns,OutgFailNoDialtoneFromServer,OutgSuccessInitialInvites,RTPJitterBufferDepthMax    
--          4. modified sipTermStatsC15mEntry (RCR ALU02137511)
--              - remove 5 objects
--                OutgCallAttemptsWithRBT,OutgCallAttemptsWithRBTNoAns,OutgFailNoDialtoneFromServer,OutgSuccessInitialInvites,RTPJitterBufferDepthMax
--
-- ===================================================================
-- HISTORY
-- REVISION  "201601210000z"
-- DESCRIPTION
--    Version: based on changeset 1d9ca84e52af
--    Editor: Squall Zhou (Squall.Zhou@Alcatel-lucent.com)
--    Changes:
--          1. Create sipIsdnTerminationTable and sipBChannelTable.
--          2. Change the default value sipLineIdIsdnSyntax in SipLineIdSyntaxProfileEntry
-- ==================================================================
-- HISTORY
--  REVISION     "201512010000z"
--  DESCRIPTION
--   "Version:  based on changeset ecc1a8dc0642
--    Editor: Dixon Wang (wang.dixon@alcatel-lucent.com)
--    Changes:
--    For RCR ALU02082604
--          1. removed sipMsanStatsP15mTable which has not been required by customer
--          2. created 2 tables for 36 termination codec statistics counters (RCR ALU02137511) 
--              - newly added: sipTermCodecStatsP15mTable
--              - newly added: sipTermCodecStatsC15mTable
--          3. created 2 tables for 16 board DSP statistics counters (RCR ALU02137511) 
--              - newly added: sipBoardDspStatsP15mTable
--              - newly added: sipBoardDspStatsC15mTable
--          4. modified sipBoardStatsP15mEntry (RCR ALU02137511) 
--              - added 4 new objects (availableDur, registerDur, activeConnections, brokenPorts)
--              - removed 16 board DSP statistics counters
--          5. modified sipBoardStatsC15mEntry (RCR ALU02137511) 
--              - added 4 new objects (availableDur, registerDur, activeConnections, brokenPorts)
--              - removed 16 board DSP statistics counters
--          6. modified sipTermStatsP15mEntry (RCR ALU02137511) 
--              - removed 36 term codec statistics counters
--          7. modified sipTermStatsC15mEntry (RCR ALU02137511) 
--              - removed 36 term codec statistics counters
--
-- ===================================================================
-- HISTORY
--  REVISION     "201511260000z"
--  DESCRIPTION
--   "Version:  based on changeset bad7935b9ad0
--    Editor: Dixon Wang (wang.dixon@alcatel-lucent.com)
--    Changes:
--    For RCR ALU02082604
--          1. modified sipTermStatsP15mEntry
--              - Add 56 new objects for voice SIP statistics counters
--          2. modified sipTermStatsC15mEntry
--              - Add 56 new objects for voice SIP statistics counters
--          3. modified sipBoardStatsP15mEntry
--              - Add 18 new objects for voice SIP statistics counters
--          4. modified sipBoardStatsC15mEntry
--              - Add 18 new objects for voice SIP statistics counters
--          5. add new table - sipMsanStatsP15mTable - for voice SIP MSAN shelf statistics functionality
-- ===================================================================
-- HISTORY
--  REVISION     "201506030000z"
--  DESCRIPTION
--   "Version:  based on changeset 8b3618effe0a
--    Editor: Lisa Zheng (Lisa.Zheng@alcatel-lucent.com)
--    Changes:
--     For RCR ALU02027707:
--    1. sipUserAgentTable
--       change tablesize from 4 to 16.
--    2. sipUserAgentId
--       change range from (1...4) to (1...16). 
--    3. update description forsipUserAgentTable, sipDialPlanTable, sipVSPTable, sipDialPlanDigitmapTable, sipTransportTable to declare that operator can manually create 16 entrys.
--    4. update description for sipRegisterTable, netwRedunTable to declare that operator can manually create 17 entrys.
-- ===================================================================
-- ===================================================================
-- HISTORY
--  REVISION     "201505180000z"
--  DESCRIPTION
--   "Version:  based on bde5a540d35b  
--    Editor: He Chunye (Chunye.He@alcatel-sbell.com.cn)
--    Changes:
--     RCR ALU01968111 7367-SX Sealed box Voice SIP Support: add description to support 7367 SX.
-- ===================================================================
-- HISTORY
--  REVISION     "201503110000z"
--  DESCRIPTION
--   "Version:  based on 
--    Editor: Bonnie Huang (Bonnie.Huang@alcatel-lucent.com)
--    Changes:
--    For RCR ALU02027707:
--          1. sipServerIdNext
--              - Keep RANGE: (1..128)
--          2. sipUserAgentIdNext
--              - Enlarge RANGE: (1..16)
--          3. sipDialPlanIdNext
--              - Enlarge RANGE: (1..16)
--          4. sipServerTable
--              - Keep TABLESIZE: 128 
--              - Keep range of sipServerId from (1...128) 
--          5. sipServerMappingTable
--              - Keep TABLESIZE: 128
--              - Keep range of sipServerMappingId from (1..128)
--              Persist:NA
--          6. sipUserAgentMappingTable
--              - enlarge TABLESIZE: 4->16
--              - change range of sipUaMappingId from (1...4) to (1...16)
--              -Persist: NA
--          7. sipDialPlanTable
--              - enlarge TABLESIZE: 4->16
--              - change range of sipDialPlanId from (1...4) to (1...16)
--          8. sipDialPlanMappingTable
--              - enlarge TABLESIZE: 4->16
--              - Persist: NA
--          9. sipDialPlanDigitmapTable
--              - enlarge TABLESIZE: DEP[4K * 4] The total size of the sipDialPlanDigitmapValue of ONE dial plan cannot exceed 4K 
--              -> DEP[4K * 16] The total size of the sipDialPlanDigitmapValue of ONE dial plan cannot exceed 4K
--          11. sipVSPTable
--              - enlarge TABLESIZE: 5->17
--              - change range of sipVSPId from (1...5)  to (1...17)
--          12. sipVSPMappingTable
--              - enlarge TABLESIZE: 5->17
--              - change range of sipVSPMappingId from (1...5) to (1...17)
--              - Persist: NA
--          13. sipUserAgentAccessPointTable
--              - enlarge TABLESIZE: DEP [max LT slot number of the shelf *4] -> DEP [max LT slot number of the shelf * 16]
--          14. sipTransportTable
--              - enlarge TABLESIZE: 4->16       
--          15. sipRegisterTable
--              - enlarge TABLESIZE: 5->17
--          16. sipDHCPAuthentParaTable
--              - Keep TABLESIZE: DEP [16 * 4] 
--          17. netwRedunTable
--              - enlarge TABLESIZE: 5->17
--          18. sipVSPIdNext
--              - change range of sipVSPIdNext from (1...5) to (1...17)
-- ===================================================================
-- HISTORY
--  REVISION     "201502110000z"
--  DESCRIPTION
--   "Version:  based on changeset 8b3618effe0a
--    Editor: Loren Zhang (Zhang.Loren@alcatel-lucent.com)
--    Changes:
--     FR ALU02049361: update USAGE for sipVSPDomainName.
-- ===================================================================
-- HISTORY
--  REVISION     "201501120000z"
--  DESCRIPTION
--   "Version:  based on changeset 94558ca5b843
--    Editor: Anny Zhong (Anny.A.Zhong@alcatel-lucent.com)
--    Changes:
--     Update description of sipTerminationEnableCallHold, sipTerminationEnableCallConference
--     and sipTerminationEnableCallTransfer to declare that the subscribe value is STILL NOT 
--     SUPPORTED for these three objects.
-- ===================================================================
-- HISTORY
--  REVISION     "201501050000z"
--  DESCRIPTION
--   "Version:  based on changeset b316b24f50df
--    Editor: Anny Zhong (Anny.A.Zhong@alcatel-lucent.com)
--    Changes:
--     (1) Update description for Multi-VAG
--     (2) Adding clarification to sipVSPName attribute (ref comment [825395])
-- ===================================================================
-- HISTORY
--  REVISION     "201412310000z"
--  DESCRIPTION 
--   "Version:  based on changeset d162f8fdbefe
--    Editor: Loren Zhang (Zhang.Loren@alcatel-lucent.com) 
--    Changes:
--     ALU02036893 [7363 NGVR][SIP]:The redundancy-cmd display empty after After we manual switch geo-red-site: 
--     Change ACCESS from not-accessible to read-only  for sipRedunCommandAdminDomName/ netwRedunStateSlotId.
-- ===================================================================
-- HISTORY
--  REVISION     "201412110000z"
--  DESCRIPTION 
--   "Version:  based on changeset f8e92bca0129
--    Editor: Brady Dou (Brady.Dou@alcatel-lucent.com) 
--    Changes:
--     1 Add some description in MIB object sipTerminationEnableCallWaiting.
--     "Options Disable(1) and Enable(2) were supported in SW from ISR4.5.01 onwards and Subscribe(3) is supported from ISR5.2."
-- ===================================================================
-- HISTORY
--  REVISION     "201412020000z"
--  DESCRIPTION 
--   "Version:  based on changeset 4c315b1232da
--    Editor: Loren Zhang 
--    Changes:
--     1 Change access for sipRegisterProviderName from read-write to read-only.  
--     2 Change change access for netwRedunAdminDomName to read-only.
-- ===================================================================
-- HISTORY
--  REVISION     "201412020000z"
--  DESCRIPTION 
--   "Version:  based on changeset 8c0f0344e380
--    Editor: Loren Zhang 
--    Changes:
--      Correct  description of sipUserAgentId: Now, up to 4 sip user agent supported for multiple VSP network.
-- ===================================================================
-- HISTORY
--  REVISION     "201411280000z"
--  DESCRIPTION 
--   "Version:  based on changeset d310b606d08a
--    Editor: Loren Zhang 
--    Changes:
--      Update description of sipPortStateTable
-- ===================================================================
-- HISTORY
--  REVISION     "201411130000z"
--  DESCRIPTION 
--   "Version: 
--    Editor: Loren Zhang 
--    Changes:
--      Update description of sipTerminationImpedance: change item 12 to 370NVLSASplitter.
-- ===================================================================
-- HISTORY
--  REVISION     "201411070000z"
--  DESCRIPTION 
--   "Version: base on changeset 136cf0eae504
--    Editor: Loren Zhang 
--    Changes:
--      Update description of sipDialPlanDigitMapTable and sipUserAgentAccessPointTable. 
-- ===================================================================
-- HISTORY
--  REVISION     "201410200000z"
--  DESCRIPTION 
--   "Version: base on changeset de09ad85ef4d
--    Editor:  Bill Feng
--    Changes:
--    For RCR ALU01962838:
--      Add time stamp object to following four statistic entries:
--          (1) sipTermStatsP15mEntry, add object  sipTermStatsP15mTimeStamp
--          (2) sipTermStatsP1dEntry, add object  sipTermStatsP1dTimeStamp
--          (3) sipBoardStatsP15mEntry, add object  sipBoardStatsP15mTimeStamp
--          (4) sipBoardStatsP1dEntry, add object  sipBoardStatsP1dTimeStamp
-- ===================================================================
-- HISTORY
--  REVISION     "201410130000z"
--  DESCRIPTION 
--   "Version: base on changeset aefc77d2074748ba248d690289853a674b6cfc89
--    Editor:  Bill Feng
--    Changes:
--    For RCR ALU01958523:
--       Add new MIB table: sipPortStateTable.
-- ===================================================================
-- HISTORY
--  REVISION     "201409180000z"
--  DESCRIPTION 
--   "Version: base on changeset 8b419e7bda0bba731f600632cbcb05b61d7e895f
--    Editor:  Loren Zhang
--    Changes:
--    For RCR ALU01864502 :
--          1. sipServerIdNext
--              - Enlarge RANGE: (1..128)
--          2. sipUserAgentIdNext
--              - Enlarge RANGE: (1..4)
--          3. sipDialPlanIdNext
--              - Enlarge RANGE: (1..4)
--          4. sipServerTable
--              - Enlarge TABLESIZE: 32 -> 128
--              - Change range of sipServerId from (1...32) to (1...128)
--              - Change default value of sipServerAdminDomName from null to vsp1
--          5. sipServerMappingTable
--              - enlarge TABLESIZE: 32->128
--              - change range of sipServerMappingId from (1...32) to (1...128)
--          6. sipUserAgentTable
--              - enlarge TABLESIZE: 1->4
--              - change range of sipUserAgentId from 1 to (1...4)
--              - add new object sipUserAgentProviderName
--          7. sipUserAgentMappingTable
--              - enlarge TABLESIZE: 1->4
--              - change range of sipUaMappingId from (1...1) to (1...4)
--          8. sipDialPlanTable
--              - enlarge TABLESIZE: 1->4
--              - change range of sipDialPlanId from (1...1) to (1...4)
--              - add new object sipDialPlanProviderName
--          9. sipDialPlanMappingTable
--              - enlarge TABLESIZE: 1->4
--          10. sipDialPlanDigitmapTable
--              - enlarge TABLESIZE: DEP [The total size of sipDialPlanDigitmapValue of the same type within one dial plan can not exceed 4K]  DEP[4K * 4] The total size of the sipDialPlanDigitmapValue of ONE dial plan cannot exceed 4K
--          11. sipTerminationTable
--              - add new object sipTerminationProviderName
--              - deprecated old object sipTerminationAssocVSPId
--          12. sipVSPTable
--              - enlarge TABLESIZE: 1->5
--              - change range of sipVSPId from (1...1)  to (1...5)
--              - change range of sipVSPRowStatus: 1 - active (1)  1 | 4 | 6  - active (1), createAndGo (4), destroy (6)
--          13. sipVSPMappingTable
--              - enlarge TABLESIZE: 1->5
--              - change range of sipVSPMappingId from (1...1) to (1...5)
--          14. sipUserAgentAccessPointTable
--              - enlarge TABLESIZE: DEP [max LT slot number of the shelf]  DEP [max LT slot number of the shelf * 4]
--          15. sipDNSServerMappingTable
--              - change TABLESIZE: 8->6
--              - change range of sipDNSServerMappingId from (1...8) to (1...6)
--          16. sipTransportTable
--              - enlarge TABLESIZE: 1->4
--              - change default value of sipTransportProviderName from null to vsp1        
--          17. sipRegisterTable
--              - enlarge TABLESIZE: 1->5
--          18. sipDHCPAuthentParaTable
--              - enlarge TABLESIZE: 16DEP [16 * 4]
--          19. netwRedunTable
--              - enlarge TABLESIZE: 1->5
--          20. sipVSPIdNext
--              - new added table and range is 5
-- ===================================================================
-- HISTORY
--  REVISION     "201408270000z"
--  DESCRIPTION 
--   "Version: base on changeset 89a63e42ccd2
--    Editor:  Anny Zhong
--    Changes:
--    For RCR ALU01958513:
--      1.Update mib object sipTermTestAccessTimeout in sipTerminationTable :
--        (1) Change object description: replace [0-300] with [0-900]
--        (2) Change Range of object from 0-300 to 0-900
--        (3) Change Default value of object from 120 to 900
-- ===================================================================
-- HISTORY
--  REVISION     "201405080000z"
--  DESCRIPTION 
--   "Version: base on changeset b14b26a75873 
--    Editor:   Dixon Wang  (Email# Wang.Dixon@alcatel-lucent.com)
--    Changes:
--    FR ALU01976217:
--    Modified the UNITs of sipTerminationTxGain and sipTerminationRxGain MIB objects from NA to dB.
-- ===================================================================
-- HISTORY
--  REVISION     "201403140000z"
--  DESCRIPTION 
--   "Version: base on c1f6906efdc5 
--    Editor:   Dennis Shao 
--    Changes:
--    RCR ALU01944197:
--     - MIB readiness for R5.1.x features.
--    RCR ALU01943990:
--     - Update value and range of SipTerminationImpedance. 
--   "
-- ===================================================================
-- HISTORY:
-- REVISION: "2014012201Z"
-- DESCRIPTION
--     "Version: 3FE25582EAAA_V4.4.0.2.11
--     Editor: Sunny Du (Email#Sunny.Du@alcatel-lucent.com) 
--     Changes:
--     Add new object sipTerminationLineId in sipTerminationTable for RCR ALU01865683 to support PANI (line-id) for DTAG
-- ===================================================================
-- HISTORY
-- REVISION "2012122500Z"
-- DESCRIPTION
--   "Version: 
--    Editor: Gavin Ren (Email# Gavin.Ren@alcatel-lucent.com)
--    Changes:
--    	- add netwDNSRedunMode object to netwRedunTable "
-- ===================================================================
-- HISTORY
-- REVISION "2012101700Z"
-- DESCRIPTION
--   "Version: 3FE25582EAAA_V4.4.0.2.5
--    Editor: Dixon Wang (Email# Wang.Dixon @alcatel-lucent.com)
--    Changes:
--      - Update the impedance description of MIB object sipTerminationImpedance. "
-- ===================================================================
-- HISTORY
-- REVISION "2012071000Z"
-- DESCRIPTION
--   "Version: 3FE25582EAAA_V4.4.0.2.3
--    Editor: Dixon Wang (Email# Wang.Dixon @alcatel-lucent.com)
--    Changes:
--      - Update some MIB tables for RCR ALU00782371. "
-- ====================================================================
-- HISTORY:
--  REVISION "2012090502Z"
--  DESCRIPTION
--     "Version: 3FE25582EAAA_V4.5.0.0.1
--      Editor: Li Haimei (Email#Haimei.Li@alcatel-sbell.com.cn)
--      Changes:
--      Update some table description for RCR ALU01812644.
-- ====================================================================
-- HISTORY:
--  REVISION "2011021002Z"
--  DESCRIPTION
--     "Version: 3FE25582EAAA_V4.3.0.0.2
--      Editor: GE Weimin (Email#Weimin.Ge@alcatel-sbell.com.cn)
--      Changes:
--      Update some table description for FR ALU00123102 according to latest comments #678032.
-- ====================================================================
-- HISTORY:
--  REVISION "2011013002Z"
--  DESCRIPTION
--     "Version: 3FE25582EAAA_V4.3.0.0.2
--      Editor: GE Weimin (Email#Weimin.Ge@alcatel-sbell.com.cn)
--      Changes:
--      Update some table description for FR ALU00123723 according to latest comments.
-- ====================================================================
-- HISTORY:
--  REVISION "2011012802Z"
--  DESCRIPTION
--     "Version: 3FE25582EAAA_V4.3.0.0.2
--      Editor: GE Weimin (Email#Weimin.Ge@alcatel-sbell.com.cn)
--      Changes:
--      Update the file for FR ALU00123723 according to the conclusion of the MIB 
--       PB review meeting.
-- ====================================================================
-- HISTORY:
--  REVISION "2011012702Z"
--  DESCRIPTION
--     "Version: 3FE25582EAAA_V4.3.0.0.2
--      Editor: GE Weimin (Email#Weimin.Ge@alcatel-sbell.com.cn)
--      Changes:
--      Update the file for FR ALU00123723 according to the review comments. The 
--         comments is listed as following: #677061, #677065, #677074, #677075, 
--          #677076, #677078, #677079, #677080, #677090, #677096.
-- ====================================================================
-- HISTORY:
--  REVISION "2011012701Z"
--  DESCRIPTION
--     "Version: 3FE25582EAAA_V4.3.0.0.2
--      Editor: GE Weimin (Email#Weimin.Ge@alcatel-sbell.com.cn)
--      Changes:
--      Update the file for FR ALU00123723.
--        1.Change the table description according to comments 676854,676882
--        2.Change the table description according to comments 676864
--        3.Change the AvgJBFL per Codec according to new conclusion, refer 673952
--        4.Change the description of CPULoad, refer the comments 676859,676878
-- ====================================================================
-- HISTORY:
--  REVISION "2011012401Z"
--  DESCRIPTION
--     "Version: 3FE25582EAAA_V4.3.0.0.2
--      Editor: GE Weimin (Email#Weimin.Ge@alcatel-sbell.com.cn)
--      Changes:
--      Update the file for FR ALU00123102.
--        1.Change sipTerminationGain object to sipTerminationRxGain.
--        2.Add a new object sipTerminationTxGain.
-- ====================================================================
-- HISTORY:
--  REVISION "2011011701Z"
--  DESCRIPTION
--     "Version: 3FE25582EAAA_V4.3.0.0.8
--      Editor: Zhao Xiaohui (Email#Xiaohui.Zhao@alcatel-sbell.com.cn)
--      Changes:
--      Update the file for FR ALU00941025.
--        Add 'sipSysObjectsAdminstatus' in SipSysObjectsTable.
-- ====================================================================
-- HISTORY:
--  REVISION "2011011301Z"
--  DESCRIPTION
--     "Version: 3FE25582EAAA_V4.3.0.0.3
--      Editor: Zhao Xiaohui (Email#Xiaohui.Zhao@alcatel-sbell.com.cn)
--      Changes:
--      Update the file for RCR ALU00122454.
--        1.Add 'ringback' for callstatus in SipTermination.
--        2.Add attribute sipTerminationOpStatDownReason in SipTermination.
-- ====================================================================
-- HISTORY:
--  REVISION "2011011202Z"
--  DESCRIPTION
--     "Version: 3FE25582EAAA_V4.3.0.0.0
--      Editor: Li Haimei (Email#Haimei.Li@alcatel-sbell.com.cn)
--      Changes:
--      Update for FR ALU01008336
-- ====================================================================
-- HISTORY:
--  REVISION "2010122601Z"
--  DESCRIPTION
--     "Version: 3FE25582EAAA_V4.3.0.0.2
--      Editor: GE Weimin (Email#Weimin.Ge@alcatel-sbell.com.cn)
--      Changes:
--      Update the file for the review comments.
--        1.Change the sipTerminationImpedance according to H.248 definition.
--        2.Remove the pmFileTransTable definition to FILE-TRANSFER-MIB definition.
-- ====================================================================
-- HISTORY:
--  REVISION "2010120801Z"
--  DESCRIPTION
--     "Version: 3FE25582EAAA_V4.3.0.0.1
--      Editor: GE Weimin (Email#Weimin.Ge@alcatel-sbell.com.cn)
--      Changes:
--      Update the file for the review comments.
-- ===================================================================
--  REVISION "2010120601Z"
--  DESCRIPTION
--     "Version: 3FE25582EAAA_V4.3.0.0.1
--      Editor: GE Weimin (Email#Weimin.Ge@alcatel-sbell.com.cn)
--      Changes:
--      Update for the following FRs MIB Ready:
--        ALU00503892: ISAM-V SIP: Collect statistics via FTP
--        ALU00747696: ISAM-V R430x MIB Ready in R43 for DTAG, It contain 2 RCRs
--        one is ALU00123102: SIP: Line Gain/impedance configurable
--        another is ALU00123723: SIP: POTS: Voice Statistics phase2: DT CDE
--      modified Tables:
--           sipTermStatsP15mEntry
--           sipTermStatsC15mEntry
--           sipTermStatsP1dEntry
--           sipTermStatsC1dEntry
--           sipTerminationEntry
--      new added Tables:
--           pmFileTransEntry
--           sipBoardStatsP15mEntry
--           sipBoardStatsC15mEntry
--           sipBoardStatsP1dEntry
--           sipBoardStatsC1dEntry
--           sipBoardStatsPerfInfoEntry
-- ===================================================================
--  REVISION "20100721200Z"
--  DESCRIPTION
--     "Version: 3FE25582EAAA_V4.3.0.0.0
--      Editor: Li Haimei (Email#Haimei.Li@alcatel-sbell.com.cn)
--      Changes:
--      *Create for fdt1120: Configure sip transport and register table"
-- ===================================================================
--  REVISION "20101021200Z"
--  DESCRIPTION
--     "Version: 3FE25582EAAA_V4.3.0.0.0
--      Editor: Li Haimei (Email#Haimei.Li@alcatel-sbell.com.cn)
--      Changes:
--      *Create for fdt1182: New changes for MIB"
-- ===================================================================
--  REVISION "20100721200Z"
--  DESCRIPTION
--     "Version: 3FE25582EAAA_V4.3.0.0.0
--      Editor: Li Haimei (Email#Haimei.Li@alcatel-sbell.com.cn)
--      Changes:
--      *Create for fdt1120: Configure sip transport and register table"
-- ===================================================================
--  REVISION "20091113200Z"
--  DESCRIPTION
--     "Version: 3FE25582EAAA_V4.2.0.0.0
--      Editor: Wu Xiuwen (Email#:Xiuwen.a.Wu@alcatel-sbell.com.cn)
--      Changes:
--      *Create for fdt993(ANTmt60010): Config external CDE parameter"
-- =============================================================================
--  REVISION "20090526200Z"
--  DESCRIPTION
--     "Version: 3FE25582EAAA_V4.1.0.0.0
--      Editor: He Chunye(Email#:chunye.he@alcatel-sbell.com.cn)
--      Changes:
--      * Update for FDT873(ANTms47684): SIP POTS Per-Call Statistics,
--      add sipCallStatsP15mTable under sipStatisticsAndData node.
-- =============================================================================
--  REVISION "20090306200Z"
--  DESCRIPTION
--     "Version: 3FE25582EAAA_V4.1.0.0.0
--      Editor: He Chunye(Email#:chunye.he@alcatel-sbell.com.cn)
--      Changes:
--      * Create for FDT873(ANTms03717): SIP POTS Statistics Collection&Report"
-- =============================================================================
--  REVISION "20081110200Z"
--  DESCRIPTION
--     "Version: 3FE25582EAAA_V4.0.0.0.0
--      Editor: Zhang Tinghui(Email#:tinghui.zhang@alcatel-sbell.com.cn)
--      Changes:
--      * add alcatel notes for MIB object sipLineIdIsdnSyntax, sipIsdnBasicRateExtTable and 
--  isdnBasicRateTable, they are not supported since R4.0. "
-- =============================================================================
-- REVISION "20080730200Z"
-- DESCRIPTION
--     "Version: 3FE25582EAAA_V4.0.0.0.0
--      Editor: He Chunye(Email#: chunye.he@alcatel-sbell.com.cn)
--      Changes:
--      * created for SIP POTS Integrated Line Test
-- =============================================================================
--  REVISION "20080217200Z"
--  DESCRIPTION
--     "Version: 3FE25582EAAA_V3.7.0.0.0
--      Editor: Liu Tao(Email#:tao.b.liu@alcatel-sbell.com.cn)
--      Changes:
--      * created for SIP Management Improvement and TermId provision"
--====================================================
--  REVISION "20070915200Z"
--  DESCRIPTION
--     "Version: 3FE25582EAAA_.V3.6.0.0.0
--      Editor: zhao yonggang(Email#:yonggang.zhao@alcatel-sbell.com.cn)
--      Changes:
--      * created for SIP Arch."
--=================================================================
--  REVISION "20070610200Z"
--  DESCRIPTION
--     "Version: 3FE25582EAAA_FDT035.V3.4.0.0.0
--      Editor: Liu Tao(Email#:tao.b.liu@alcatel-sbell.com.cn)
--      Changes:
--      * created for SIP Evolution."
--====================================================================
--
-- July 2006: Updated by Liu Tao(Email#:tao.b.liu@alcatel-sbell.com.cn)
-- 
-- Date: Oct 22, 2006 - Realease1 PROPOSAL 04, DNS support
-- Editor: Liu Tao
-- 
--==============================================================
-- 
-- July 2006: Updated by Zhang Yihui(Email#:yihui.zhang@alcatel-sbell.com.cn)
-- 
-- Date: July 18, 2006 - Realease1 PROPOSAL 03
-- Editor: Zhang Yihui
--	
-- ===============================================================
-- 
-- July 2006: Updated by Zhang Yihui(Email#:yihui.zhang@alcatel-sbell.com.cn)
-- 
-- Date: July 07, 2006 - Realease1 PROPOSAL 02
-- Editor: Zhang Yihui
-- 

-- 
-- January 2006: Created by Liu Tao(Email#:tao.b.liu@alcatel-sbell.com.cn)
-- 
-- Date: January 21, 2006 - Realease1 PROPOSAL 01
-- Editor: Liu Tao
--
-- Mar 2008: Updated by KANG Hai Tao
-- 
-- Changes: update for SIP : ISDN BA basic call & some suppl. services
--          introduce sipIsdnGroup and sipIsdnBasicRateExtTable
-- =============================================================================
 
SIP-MIB DEFINITIONS ::= BEGIN

		IMPORTS
			InetAddressType, InetAddress, InetAddressPrefixLength,InetPortNumber	
				FROM INET-ADDRESS-MIB			
			InterfaceIndex, ifIndex			
				FROM ITF-MIB			
			eqptSlotId   
				FROM  ASAM-EQUIP-MIB	
			VlanId			
				FROM Q-BRIDGE-MIB			
			Gauge, Counter, TimeTicks
				FROM RFC1155-SMI 	
			NetworkTimeInSeconds    
				FROM ASAM-TC-MIB
			OBJECT-TYPE			
				FROM RFC-1212
			SipTCEntityRole
			  FROM SIP-TC-MIB	
			DisplayString, RowStatus, TruthValue
      	FROM SNMPv2-TC			
			asam			
				FROM SYSTEM-MIB;
		
		IsdnBearerOperStatus ::= INTEGER {
				idle(1),
				connecting(2),
				connected(3),
				active(4),
				down(5),
				unknown(6)
				}
	
		IsdnLapdOperStatus ::= INTEGER {
				inactive(1),
				l1Active(2),
				l2Active(3)
				}
	
		SipTerminationImpedance ::= INTEGER {
				schmdefault(1),
				schmChina(2),
				schm220Ohm(3),
				schmTN12Splitter(4),
				schmETSI(5),
				schmBT(6),
				schmBT3(7),
				schm600(8),
				schm900(9),
				schmBT3Splitter(10),
				schm600Splitter(11),
				schm370NVLSASplitter(12),
				schm370SkinnySplitter(13),
				schm270DuratelSplitter(14),
				schm2703MSplitter(15),
                schm100Ohm(16),
                schm150Ohm(17),
                schm220OhmSplitter(18),
                schmReserved19(19),
                schmReserved20(20),
                schmReserved21(21),
                schmReserved32(32)
                }	
--
-- Node definitions
--
	
-- ****************************************************************************
-- GENERAL NOTES:
--   (1) There are NO trap definitions in this SIP MIB.
-- 
--   (2) There are NO alarm definitions in this SIP MIB.
--
--   (3) The R5.2 SIP MIB supports the multiple VAG feature. It does not support the multiple VSP feature.
-- 
-- ****************************************************************************
-- 
-- .iso.org.dod.internet.private.enterprises.alcatel.asd.asam.sipMIB
-- (.1.3.6.1.4.1.637.61.1.64)
--
-- =============================================================================

		sipMIB OBJECT IDENTIFIER ::= { asam 64 }

-- =============================================================================
-- Sip Scalar Objects Definition
-- =============================================================================

-- =============================================================================
-- NEXT FREE SIP APPLICATION SERVER ID 
-- =============================================================================
		sipServerIdNext OBJECT-TYPE
			SYNTAX INTEGER
			ACCESS read-only
			STATUS mandatory
			DESCRIPTION
					"The next free SIP Server index 
					Should a next free SIP server index be requested while no free sip server index is
					available anymore, the system will return a genErr response.
				ALCATEL-LUCENT NOTE:
				ACCESS:	READ-ONLY
				USAGE:	NA
				PERSIST:	NO 
				INSRVMOD: NA
				RANGE: (1..128)	
				DEFVALUE:	NA
				UNITS:	NA
				SPARSE: 	NO
				"
			::= { sipMIB 1 }


-- =============================================================================
-- NEXT FREE SIP USER AGNET ID 
-- =============================================================================
		sipUserAgentIdNext OBJECT-TYPE
			SYNTAX INTEGER
			ACCESS read-only
			STATUS mandatory
			DESCRIPTION
				"The next free SIP UserAgent identifier.
                Should an a next free SIP UserAgent index be requested while no free sip UserAgent index is
                found, the system will return a genErr response.
			ALCATEL-LUCENT NOTE:
			ACCESS:	READ-ONLY
			USAGE:	NA
			PERSIST:	NO
			INSRVMOD: NA
			RANGE:	(1..16)
			DEFVALUE: 	NA
			UNITS:	NA
			SPARSE:	NO
		"
		::= { sipMIB 2 }		
		

-- =============================================================================
-- NEXT FREE SIP DIAL PLAN ID 
-- =============================================================================
			sipDialPlanIdNext OBJECT-TYPE
				SYNTAX INTEGER
				ACCESS read-only
				STATUS mandatory
				DESCRIPTION
						"The next free SIP Dial Plan identifier.
                         Should an a next free SIP DialPlan identifier be requested while no free sip DialPlan identifier is
                         found, the system will return a genErr response.
					ALCATEL-LUCENT NOTE:
					ACCESS:	READ-ONLY
					USAGE:	NA
					PERSIST:	NO
					INSRVMOD: NA
					RANGE: (1..16)	
					DEFVALUE:	NA
					UNITS:	NA
					SPARSE:	NO
					"
			::= { sipMIB 3 }		
	

		
-- =============================================================================
-- Sip Server Table
-- =============================================================================
		sipServerTable OBJECT-TYPE
			SYNTAX SEQUENCE OF SipServerEntry
			ACCESS not-accessible
			STATUS mandatory
			DESCRIPTION
				"The sipServerTable allowing to create one or multiple SIP first hop servers.
                The sipServerTable might contain one or multiple SIP first hop servers for a particular Service Gateway.
                Maximum 128 SIP first hop servers can be created.

                7302/7330 ISAM FTTN : Supported
                7363 MX : Supported
		7367 SX : Supported
		
			ALCATEL NOTE: 
			TABLESIZE: 128
			DESCR:NA."
			::= { sipMIB 4 }

		sipServerEntry OBJECT-TYPE
			SYNTAX SipServerEntry
			ACCESS not-accessible
			STATUS mandatory
			DESCRIPTION
				"An entry in the sipServerTable."
			INDEX { sipServerId }
			::= { sipServerTable 1 }

		
		SipServerEntry ::=
			SEQUENCE { 
				sipServerId
					INTEGER,
				sipServerName
					OCTET STRING,
--				sipServerType
--					INTEGER,
				sipServerAddrType
					InetAddressType,
				sipServerAddr
					InetAddress,
				sipServerPort
					InetPortNumber,
				sipServerAdminStatus
					INTEGER,
				sipServerOperStatus
					INTEGER,
				sipServerRowStatus
					RowStatus,
				sipServerRole
					SipTCEntityRole,
				sipServerPriority
					INTEGER,
				sipServerWeight
					INTEGER,
				sipServerTransproto	
					INTEGER,
				sipServerDnsDomNameType
					INTEGER,
				sipServerRedunSite
					INTEGER,
				sipServerAdminDomName
					OCTET STRING
                            
			 }

		sipServerId OBJECT-TYPE
			SYNTAX INTEGER 
			ACCESS read-only 
			STATUS mandatory
			DESCRIPTION
					"The unique internal identifier of a SIP first hop server.
				ALCATEL-LUCENT NOTE:
				ACCESS: READ-ONLY	
				USAGE:	MANDATORY
				PERSIST:	YES
				INSRVMOD: NA
				RANGE:	(1..128)
				DEFVALUE: 	NA
				UNITS:	NA
				SPARSE:	NO
					"
			::= { sipServerEntry 1 }

	
		sipServerName OBJECT-TYPE
			SYNTAX OCTET STRING (SIZE (0..32))
			ACCESS read-write
			STATUS mandatory
			DESCRIPTION
					" The operator friendly name for the SIP first hop server. 
                    This name must be unique across all entries of the sipServerTable.
				ALCATEL-LUCENT NOTE:
				ACCESS:	NA
				USAGE:	MAND			
				PERSIST:	YES
				INSRVMOD:	YES
				RANGE:	SIZE (0..32)
				DEFVALUE:	NA
				UNITS:	NA	
				SPARSE:	NO
					"
			::= { sipServerEntry 2 }


--		sipServerType OBJECT-TYPE
--			SYNTAX INTEGER
--				{
--				broadworks (1),
--				nortel (2),
--				a5020 (3),
--				others (4) ,
--                                fs5000TispanCompliant (5),
--                                fs5000NonTispan (6)
--				}
--			ACCESS read-write
--			STATUS mandatory
--			DESCRIPTION
--				" The vendor type  of sip server.
--                                       In case loose couple mode is selected for supplementary service in the sip service profile, 
--                                       then the server type configuration in the MIB hasn't any influence.
--                                       In case tight couple mode is selected for supplementary service in the sip service profile, 
--                                       or there is no sip service profile available in CDE file, the server type configuration takes effect.
--			
--				ALCATEL-LUCENT NOTE:
--					ACCESS:     NA
--                                        USAGE:       OPT
--					PERSIST:  	YES
--					INSRVMOD: 	NO
--					RANGE:	1 | 2 | 3 | 4  | 5 | 6 
--					DEFVALUE: 	others (4)
--					UNITS:	NA	
--                                        SPARSE:    NO			
--				"
--			::= { sipServerEntry 3 }

		sipServerAddrType OBJECT-TYPE
			SYNTAX InetAddressType
			ACCESS read-write
			STATUS mandatory
			DESCRIPTION
					" The IP Address type of the sipServerAddr.
					Ipv4(1) : An Ipv4 address as defined by the InetAddressIPv4 textual convention
					Dns(16) : A DNS name as defined by the InetAddressDNS textual convention.
		
				ALCATEL-LUCENT NOTE:
				ACCESS:	NA
				USAGE:	OPT				
				PERSIST: 	YES
				INSRVMOD:	NO
				RANGE:	1 | 16 -- ipv4(1) or dns(16)
				DEFVALUE:	ipv4(1)
				UNITS:	NA
				SPARSE:	NO
					 "
			::= { sipServerEntry 4 }

		sipServerAddr OBJECT-TYPE
			SYNTAX InetAddress
			ACCESS read-write
			STATUS mandatory
			DESCRIPTION
					" IP Address or DNS name of the SIP first hop server. 
                    The Address type is defined by SipServerAddrType. 
					The  maximum length of this field = 64 Octets
		
				ALCATEL-LUCENT NOTE:
				ACCESS:	NA
				USAGE:	MAND		
				PERSIST:	YES
				INSRVMOD:	NO
				RANGE:	NA
				DEFVALUE: 	NA
				UNITS:	NA
				SPARSE:	NO		
					"
			::= { sipServerEntry 5 }

		sipServerPort OBJECT-TYPE
			SYNTAX InetPortNumber
			ACCESS read-write
			STATUS mandatory
			DESCRIPTION
					" Transport protocol port of the SIP first hop server.
				ALCATEL-LUCENT NOTE:
				ACCESS:	NA
				USAGE:	OPT		
				PERSIST:	YES
				INSRVMOD:	NO
				RANGE:	NA
				DEFVALUE:	5060
				UNITS:	NA
				SPARSE:	NO		
					"
			::= { sipServerEntry 6 }

		sipServerAdminStatus OBJECT-TYPE
			SYNTAX INTEGER
				{
				up(1),
				down(2)
				}
			ACCESS read-write
			STATUS mandatory
			DESCRIPTION
					" The administrative status of this SIP first hop server.
					When the administrative status of a SIP server is modified from 'up' to 'down', then the system will 
					de-register all SIP terminations (at all voice LT boards)  served by that SIP Server.
					Such configuration action will be rejected in case there is a call ongoing for one of the SIP terminations
					served by this SIP server.
		
					UP (1) : The SIP server reflected by this entry is addressable by the integrated voice service.
		   			The attributes of this entry that are indicated as INSRVMOD=YES can be modified.
					DOWN (2) : The SIP server reflected by this entry is not addressable by the integrated voice service.
		   			The attributes of this entry that are indicated as INSRVMOD=YES and the attributes that are
					indicated as INSRVMOD=NO can be modified.
					Note that the attributes that are indicated INSRVMOD=NA can not be modified after ceation.
		
				ALCATEL-LUCENT NOTE:
				ACCESS:	NA
				USAGE:	OPT		
				PERSIST:	YES
				INSRVMOD:	YES
				RANGE:	1 | 2
				DEFVALUE:	down(2)
				UNITS:	NA	
				SPARSE:	NO
					"
		::= { sipServerEntry 7 }


		sipServerOperStatus OBJECT-TYPE
			SYNTAX INTEGER
				{
				up(1),
				down(2)
				}
			ACCESS read-only
			STATUS mandatory
			DESCRIPTION
					"The operational status of this SIP first hop server.
					UP ( 1) : The server is in service.
					DOWN (2) : The server is out of service.
				ALCATEL-LUCENT NOTE:
				ACCESS:	NA
		                   USAGE:	NA		
				PERSIST:	NO
				INSRVMOD:	NA
				RANGE:	1 | 2
				DEFVALUE:	NA
				UNITS:	NA	
		                SPARSE:	NO	
					"
			::= { sipServerEntry 8 }

		sipServerRowStatus OBJECT-TYPE
			SYNTAX RowStatus
			ACCESS read-write
			STATUS mandatory
			DESCRIPTION
					"The status of this conceptual row.
					The RowStatus TC requires that this DESCRIPTION clause
					states under which circumstances other objects in this row
					can be modified.  The value of this object has no effect on
					whether other objects in this conceptual row can be
					modified.
					A conceptual row can always be made active.
				ALCATEL-LUCENT NOTE:
				ACCESS:	NA
				USAGE:	MAND
				PERSIST:	NO
				INSRVMOD:	YES
				RANGE:	1 | 4 | 6	-- active (1), createAndGo (4), destroy (6)
				DEFVALUE:	NA
				UNITS:	NA
				SPARSE:	NO
		         			"
			::= { sipServerEntry 9 }


		sipServerRole OBJECT-TYPE
			SYNTAX SipTCEntityRole
			ACCESS read-write
			STATUS mandatory
			DESCRIPTION
					" The role of this SIP first hop server. 
					The syntax is a bitmap : 
					SYNTAX BITS { 
					Reserved (0), 
					Reserved (1), 
					ProxyServer (2), 
					RedirectServer (3), (Not supported) 
					RegistrarServer (4), 
					LSAServer (5) 
					} 
					Different bits can be simultaneously set.
					The configured SIP server shall be included in the ROUTE header if the 'AllowRoute' parameter in the
					SIP Service Profile is provisioned with the value 'YES'.
					The configured SIP server shall NOT be included in the ROUTE header if the 'AllowRoute' parameter
					in the SIP Service Profile is provisioned with the value 'NO'.
					When redundancy is DISABLED, the operator can configure 4 different server roles : ProxyServer(value = 4),
					RegistrarServer(value = 16), ProxyServer AND RegistrarServer(value = 20) and LSAServer(value = 32) .
					When redundancy is ENABLED, the system always assumes role = ProxyServer AND RegistrarServer
					(value  = 20), irrespective of what has been configured by the operator. Or in other words, the system always behaves in accordance to the role = proxyAndRegistrarServer(20),  and does not take into account the value been configured by the operator
		
					7302 / 7330 ISAM FTTN R4.3 Only : 
					Only a single role can be defined for a SIP server. Only the role 'poxyAndRegistrarServer' (bits 2 & 4 set) is 
					supported.
		
				ALCATEL-LUCENT NOTE:
				ACCESS:	NA
		         	USAGE:	OPT		
				PERSIST:	YES
				INSRVMOD:	NO
				RANGE:	4 | 16 | 20 | 32
				DEFVALUE: 	proxyServer(4)
				UNITS:	NA	
				SPARSE:	NO
					"
			::= { sipServerEntry 10 }

		sipServerPriority OBJECT-TYPE
			SYNTAX INTEGER 
			ACCESS read-write
			STATUS mandatory
			DESCRIPTION
					"The priority of this SIP first hop server. The lower the value the higher the priority of the SIP first hop server.
                    Different SIP first hop servers may share the same priority. 
                    The SIP first hop server with the highest priority is considered the primary SIP server i..e the first SIP server to
                    be addressed (for a particular SIP server role).
                    Should several SIP servers with the same SIP server role share the same priority, then the SIP server with the
                    smallest server Id is considered the primary SIP server (First SIP server to be addressed)

				ALCATEL-LUCENT NOTE:
				ACCESS:	NA
				USAGE:	OPT		
				PERSIST:	YES
				INSRVMOD:	YES
				RANGE:	0..65535
				DEFVALUE:	100
				UNITS:	NA
		 		SPARSE:	NO
					"
			::= { sipServerEntry 11 }

		sipServerWeight OBJECT-TYPE
			SYNTAX INTEGER
			ACCESS read-write
			STATUS mandatory
			DESCRIPTION
			         "The weight of the SIP first hop server. The weight is actually not supported.
		                ALCATEL-LUCENT NOTE:
				ACCESS:	READ-WRITE
				USAGE:	OPT		
				PERSIST:	YES
				INSRVMOD:	YES
				RANGE:	0..65535
				DEFVALUE:	100
				UNITS:	NA
				SPARSE:	NO
					"
			::= { sipServerEntry 12 }

		sipServerTransproto OBJECT-TYPE
		         	SYNTAX INTEGER(1..4294967295)
		        	ACCESS read-write
		         	STATUS mandatory
					DESCRIPTION
					" The transport protocol to be used to address the sip server.
					Bit 0: a protocol other than those defined here
					Bit 1: User Datagram Protocol
					Bit 2: Transmission Control Protocol
					Bit 3: Stream Control Transmission Protocol
								Bit 4: Transport Layer Security Protocol over TCP
					Bit 5: Transport Layer Security Protocol over SCTP
					Bit 6 .. 31 : reserved for future extensions.
					Only UDP and TCP are supported.
				ALCATEL-LUCENT NOTE:
				ACCESS:	NA
				USAGE:	OPT		
				PERSIST:	YES
				INSRVMOD:	NO
				RANGE:	2 | 4 | 6
				DEFVALUE:	UDP (2)
				UNITS:	NA	
		 		SPARSE:	NO	
		                		"
			::= { sipServerEntry 13}

		sipServerDnsDomNameType OBJECT-TYPE
				SYNTAX INTEGER
					{
					none (1),
					dn (2),
					fqdn (3)
					}
				ACCESS read-write
				STATUS mandatory
				DESCRIPTION
					"Allows to clarify whether a Domain Name (dn) or a Fully Qualified Domain Name (fqdn) has been
					provisioned in the sipServerAddr object.
					This object is only relevant in case the value of the object sipServerAddrType has been provisioned with the
					value dns(16).
					In case the sipServerAddrType object is provisioned with value ipv4 (1) then this object must set to the value 
					'none'
					In case the sipServerAddrType object is provisioned with value dns(16) and this object is provisioned with the 
					value dn(2) , then the objects sipServerPort, sipServerPriority, sipServerWeight and sipServerProtocol are 
					irrelevant.
					In case the sipServerAddrType object is provisioned with value dns(16) and this object is provisioned with the 
					value fqdn(3), then the objects sipServerPort, sipServerPriority, sipServerWeight and sipServerProtocol are 
					mandatory.
					ALCATEL-LUCENT NOTE:
		                	ACCESS:	READ-WRITE
					USAGE:	MAND		
		                	PERSIST:	YES
		                	INSRVMOD:	NO
		                	RANGE:	1 | 2 | 3
		            		DEFVALUE:	1
		                	UNITS:	NA	
					SPARSE:	NO	
		                		"
		::= { sipServerEntry 14}

		sipServerRedunSite OBJECT-TYPE
			SYNTAX INTEGER
				{
				primary-site (1),	
				geo-backup-site (2),
				sos-backup-site (3)
				}
			ACCESS read-write
			STATUS mandatory
			DESCRIPTION
					"The redundancy site to which this (farm of) SIP first hop server(s) belong to.
				ALCATEL-LUCENT NOTE:
				ACCESS:	READ-WRITE
				USAGE:	MAND		
				PERSIST:	YES
				INSRVMOD:	YES
				RANGE:	1 | 2 | 3
				DEFVALUE:	primary-site (1)
				UNITS:	NA	
				SPARSE:	NO	
					"
		::= { sipServerEntry 15}


		sipServerAdminDomName OBJECT-TYPE
			SYNTAX OCTET STRING (SIZE (0..32))
			ACCESS read-write
			STATUS mandatory
			DESCRIPTION
				"The administrative domain name of the (farm of) SIP First hop server(s) i.e. the name of the parent 
                Service Gateway. This is the Service Gateway this SIP first hop server belongs to. 
				ALCATEL-LUCENT NOTE:
				ACCESS:	READ-WRITE
				USAGE:	NA		
				PERSIST:	YES
				INSRVMOD: NO
				RANGE:	SIZE (0..32))
				DEFVALUE: vsp1
				UNITS:	NA	
				SPARSE:	NO
					"				
			::= { sipServerEntry 16 }


-- =============================================================================
-- Sip Server Mapping Table
-- =============================================================================
		sipServerMappingTable OBJECT-TYPE
			SYNTAX SEQUENCE OF SipServerMappingEntry
			ACCESS not-accessible
			STATUS mandatory
			DESCRIPTION
				"The operator friendly SIP first hop server name to unique internal identifier mapping table.
                
                7302/7330 ISAM FTTN : Supported
                7363 MX : Supported
		7367 SX : Supported
		
				ALCATEL NOTE: 
				TABLESIZE: 128
				DESCR:NA."
			::= { sipMIB 5 }

		sipServerMappingEntry OBJECT-TYPE
			SYNTAX SipServerMappingEntry
			ACCESS not-accessible
			STATUS mandatory
			DESCRIPTION
				"An entry in the sipServerMappingTable.
                An entry is auto-created upon the creation of an entry in the sipServerTable.
                An entry is auto-deleted upon the deletion of an entry in the sipServerTable.
				"
			INDEX { sipServerMappingName }
			::= { sipServerMappingTable 1 }

		SipServerMappingEntry ::=
			SEQUENCE { 
			sipServerMappingName		OCTET STRING,
			sipServerMappingId		INTEGER	
			}

		sipServerMappingName OBJECT-TYPE
			SYNTAX OCTET STRING (SIZE (0..32))
			ACCESS not-accessible
			STATUS mandatory
			DESCRIPTION
					" The operator friendly name for this sip first hop server
				ALCATEL-LUCENT NOTE:
				ACCESS:	NOT-ACCESSIBLE
				USAGE:	MANDATORY
				PERSIST:	NA	
				INSRVMOD:	NA 
				RANGE:	SIZE (0..32)
				DEFVALUE:	NA
				UNITS:	NA	
				SPARSE:	NO			
					"
			::= { sipServerMappingEntry 1 }


		sipServerMappingId OBJECT-TYPE
			SYNTAX INTEGER
			ACCESS read-only
			STATUS mandatory
			DESCRIPTION
					"The unique internal identifier of this sip first hop server.
				ALCATEL-LUCENT NOTE:
				ACCESS:	NA
				USAGE:	NA
				PERSIST:	NA 
				INSRVMOD:	NA
				RANGE:	(1..128)
				DEFVALUE: 	NA
				UNITS:	NA
		                SPARSE:	NO
					"
			::= { sipServerMappingEntry 2 }

			
-- =============================================================================
-- Sip UserAgent Table
-- =============================================================================
		sipUserAgentTable OBJECT-TYPE
			SYNTAX SEQUENCE OF SipUserAgentEntry
			ACCESS not-accessible
			STATUS mandatory
			DESCRIPTION
				"The sipUserAgentTable allows to create a SIP User Agent instance. Such SIP User Agent instance is common to all voice LT boards in the node.
                A SIP User Agent instance needs to be created and administratively  enabled for each Service Gateway (VSP or VAG) that is administratively enable din the access node.
                Up to 16 SIP User Agent instances can be created. (only manual creation is supported).
                As the system supports different Service Gateways with different configuration settings, it is allowed to configure a different signaling/media VLAN per Service Gateway.
                However as the system also supports different Service Gateways sharing the same configuration settings, it is allowed to configured the same signaling/media VLAN for more than 1 Service Gateway.
                Maximum 5 DIFFERENT SIP User Agent contexts allowed (for both, MANUAL IP configuration mode and DHCP configuration mode ) amongst all configured SIP User Agent entries.
                It is allowed to configure the shared or distinct VLAN approach per configured Service Gateway. The system supports maximum 8 signaling VLANS for which flow control is enabled.
                Flow control needs to be enabled for the signaling VLAN as to protect system from SIP flooding.
                It is allowed to configure a different signaling stream p-bit value per Service Gateway.
                It is allowed to configure a different media stream p-bit value per Service Gateway.
                It is allowed to configure the IP address mode as 'manual' or 'DHCP' per Service Gateway.
                The DHCP address mode is only supported for the distributed IP address architecture (7363 MX : centralized IP address architecture) and the shared VLAN approach.
                DHCP options 82 and 120 are supported. For a maximum of 5 SIP User Agents instances the IP and  SIP server (option 120) configuration can be retrieved  via DHCP.
                It is allowed to configure a different IP address mode for each Service Gateway, if each Service Gateway owns a different VLAN.
                It is allowed to configure only 1 IP address mode, shared by all Service Gateways if the same VLAN is shared by all Service Gateways.
                The above mentioned limitations are checked upon changing the administrative state of a SIP User Agent instance from 'down' to 'up'.
                The system will check whether there are more than 5 SIP User Agent instances created for which the administrative status is set to 'UP' AND different configuration settings.
                A SIP User Agent instance is considered different from another previously configured SIP User Agent instance if the configured signaling part and/or the configured media part are different from what has been configured before.
                Signaling part : Signaling VlanId, Signaling Default Gw, Signaling Dscp Mark, Signaling Pbits, Signaling MTU.
                Media part : Media VlanId, Media Default GW, Media Dscp Mark, Media Pbits, Media MTU.
                A SIP User Agent instance is considered  not different from another previously configured SIP User Agent instance if both, the configured signaling part and the configured media part appear in one of the previously configured SIP UA entries.
                In case the number of SIP User Agent instances threshold is exceeded, the administrative 'UP' modification action is rejected. Upon the creation of a SIP User Agent instance with admin state = down, the configured  entry is stored within the NT DB.
                Upon the rejection of the admin state change the configured entry remains stored in the DB.

                7302/7330 ISAM FTTN : Supported
                7363 MX : Supported
                7367 SX : Supported

			ALCATEL NOTE: 
			TABLESIZE: 16
			DESCR:NA."
		::= { sipMIB 6 }

		sipUserAgentEntry OBJECT-TYPE
			SYNTAX SipUserAgentEntry
			ACCESS not-accessible
			STATUS mandatory
			DESCRIPTION
				" An entry in the sipUserAgentTable." 
			INDEX { sipUserAgentId }
		::= { sipUserAgentTable 1 }


		SipUserAgentEntry ::=
			SEQUENCE { 
				sipUserAgentId
					INTEGER,
				sipUserAgentName
					OCTET STRING,
--				sipUserAgentAssocProxyServerId
--					INTEGER,
--				sipUserAgentAssocRegServerId
--					INTEGER,
--				sipUserAgentAssocSlotId
--					INTEGER,
--				sipUserAgentAssocDialPlanId
--					INTEGER,
--				sipUserAgentUaDomain
--					OCTET STRING,
				sipUserAgentIpAddrType
					InetAddressType,
--				sipUserAgentIpAddr
--					InetAddress,
--				sipUserAgentIpPrefixLength
--					InetAddressPrefixLength,
				sipUserAgentDefaultGw
					InetAddress,
--				sipUserAgentDomainSrv
--					InetAddress,
--				sipUserAgentInUseSrvAddr
--					InetAddress,
-- 				sipUserAgentTransProto
--					INTEGER,              
--				sipUserAgentPort
--					InetPortNumber,
				sipUserAgentVlanId
                    INTEGER,
--				sipUserAgentSignallingVlanId
--					VlanId,
				sipUserAgentSignallingDscpMark
					INTEGER,
				sipUserAgentSignallingPBits
					INTEGER,
				sipUserAgentRtpVlanId
                    INTEGER,
				sipUserAgentRtpDscpMark
					INTEGER,
				sipUserAgentRtpPBits
					INTEGER,
				sipUserAgentGwConfigMode
					INTEGER,
				sipUserAgentAdminStatus
					INTEGER,
--				sipUserAgentOperStatus
--					INTEGER,
				sipUserAgentRowStatus
					RowStatus,
--				sipUAVoiceIpAddr
--					InetAddress,
--				sipUAVoiceIpAddrPrefixLength
--					InetAddressPrefixLength,
				sipUAVoiceDefaultGW
					InetAddress,
				sipUAIpAddrPolicy
					INTEGER,
				sipUASignalingLinkMTU
					INTEGER,
				sipUAVoiceLinkMTU
					INTEGER,
				sipUserAgentDHCPOptionReqList	
					DisplayString,
				sipUserAgentProviderName      
					OCTET STRING,
                sipUALSAVoiceDefaultGW
                    InetAddress,
                sipUALSARTPVlanId
                    INTEGER,
                sipUALSAMD5Realm
                    OCTET STRING,
                sipUALSAMD5Password
                    OCTET STRING
			}

		sipUserAgentId OBJECT-TYPE
			SYNTAX INTEGER 
			ACCESS read-only
			STATUS mandatory
			DESCRIPTION
				" Unique internal identifier of this SIP User Agent. 
			ALCATEL-LUCENT NOTE:
			ACCESS:     READ-ONLY
			USAGE:       NA
			PERSIST:  	YES
			INSRVMOD: 	NA
			RANGE:	(1..16)
			DEFVALUE: 	NA
			UNITS:	NA	
			SPARSE:    NO			
			"
			::= { sipUserAgentEntry 1 }

		sipUserAgentName OBJECT-TYPE
			SYNTAX OCTET STRING (SIZE (0..32))
			ACCESS read-write
			STATUS mandatory
			DESCRIPTION
				" The operator friendly name for this SIP User Agent.
				This name must be unique across the complete table.
			ALCATEL-LUCENT NOTE:
			ACCESS:	READ-WRITE
			USAGE:	MAND			
			PERSIST:	YES
			INSRVMOD:	YES
			RANGE:	SIZE (0..32)
			DEFVALUE:	NA
			UNITS:	NA
			SPARSE#:	NO								
			"
		::= { sipUserAgentEntry 2 }


		
--		sipUserAgentAssocProxyServerId OBJECT-TYPE
--			SYNTAX INTEGER (1..32)
--			ACCESS read-write
--			STATUS mandatory
--			DESCRIPTION
--				" Identifier of the associated sip server as outbound proxy.
--
--				ALCATEL-LUCENT NOTE:
--					SUPPORT:  	YES
--					PERSIST:  	YES
--					INSRVMOD: 	NO
--					RANGE:	(1..32)
--					DEFVALUE: 	NA
--					UNITS:	NA								
--				"
--			::= { sipUserAgentEntry 3 }

--		sipUserAgentAssocRegServerId OBJECT-TYPE
--			SYNTAX INTEGER (1..32)
--			ACCESS read-write
--			STATUS mandatory
--			DESCRIPTION
--				" Identifier of the associated sip register server.
--
--				ALCATEL-LUCENT NOTE:
--					SUPPORT:  	YES
--					PERSIST:  	YES
--					INSRVMOD: 	NO
--					RANGE:	(1..32)
--					DEFVALUE: 	NA
--					UNITS:	NA								
--				"
--			::= { sipUserAgentEntry 4 }

		
--		sipUserAgentAssocSlotId OBJECT-TYPE
--			SYNTAX	INTEGER (1..65535)
--			ACCESS read-write
--			STATUS mandatory
--			DESCRIPTION
--				" A unique identifier of the slot position of the associated
--				board of this sip ua. 
--
--				ALCATEL-LUCENT NOTE:
--					SUPPORT:  	YES
--					PERSIST:  	YES
--					INSRVMOD: 	NO
--					RANGE:	NA
--					DEFVALUE: 	NA
--					UNITS:	NA								
--				"
--			::= { sipUserAgentEntry 5 }

		
--		sipUserAgentAssocDialPlanId OBJECT-TYPE
--			SYNTAX INTEGER (1..255)
--			ACCESS read-write
--			STATUS mandatory
--			DESCRIPTION
--				" Identifier of the associated dial plan of this sip ua.
--
--				ALCATEL-LUCENT NOTE:
--					SUPPORT:  	YES
--					PERSIST:  	YES
--					INSRVMOD: 	NO
--					RANGE:	(1..255)
--					DEFVALUE: 	NA
--					UNITS:	NA								
--				"
--			::= { sipUserAgentEntry 6 }

		
--		sipUserAgentUaDomain OBJECT-TYPE
--			SYNTAX OCTET STRING (SIZE (0..64))
--			ACCESS read-write
--			STATUS mandatory
--			DESCRIPTION
--				" Domain of the sip user agent. 
--
--				ALCATEL-LUCENT NOTE:
--					SUPPORT:  	YES
--					PERSIST:  	YES
--					INSRVMOD: 	NO
--					RANGE:	SIZE (0..64)
--					DEFVALUE: 	null
--					UNITS:	NA								
--				"
--			DEFVAL { "" }
--			::= { sipUserAgentEntry 7 }

		

		
		sipUserAgentIpAddrType OBJECT-TYPE
			SYNTAX InetAddressType
			ACCESS read-only
			STATUS mandatory
			DESCRIPTION
				"The IP address type of SipUserAgentDefaultGw, SipUAVoiceDefaultGw and SipUserAgentDomainSrv.
			ALCATEL-LUCENT NOTE:
			ACCESS:	READ-ONLY
			USAGE:	OPT
			PERSIST:	NO
			INSRVMOD:	NO
			RANGE:	1	-- only ipv4(1)
			DEFVALUE:	1
			UNITS:	NA	
			SPARSE:	NO							
			"
		::= { sipUserAgentEntry 8 }

	
--		sipUserAgentIpAddr OBJECT-TYPE
--			SYNTAX InetAddress
--			ACCESS read-write
--			STATUS mandatory
--			DESCRIPTION
--				"IP address of this sip ua.
--
--				ALCATEL-LUCENT NOTE:
--					SUPPORT:  	YES
--					PERSIST:  	YES
--					INSRVMOD: 	NO
--					RANGE:	NA
--					DEFVALUE: 	NA
--					UNITS:	NA				
--				"
--			::= { sipUserAgentEntry 9 }

		
--		sipUserAgentIpPrefixLength OBJECT-TYPE
--			SYNTAX InetAddressPrefixLength
--			ACCESS read-write
--			STATUS mandatory
--			DESCRIPTION
--				"The IP address prefix which is basically the number
--				of '1' bits in the netmask.  The range of allowed
--				values of this object is derived from the address type
--				in sipUserAgentIpAddrType i.e. [1..30] for Ipv4 or
--				[1..126] for Ipv6.
--
--				ALCATEL-LUCENT NOTE:
--					SUPPORT:  	YES
--					PERSIST:  	YES
--					INSRVMOD: 	NO
--					RANGE:	NA
--					DEFVALUE: 	NA
--					UNITS:	NA
--				"
--			::= { sipUserAgentEntry 10 }

		sipUserAgentDefaultGw OBJECT-TYPE
			SYNTAX InetAddress
			ACCESS read-write
			STATUS mandatory
			DESCRIPTION
				" IP address of the default gateway.
				The IP context is defined by sipUserAgentIpAddrType.
			
				When the sipUserAgentGwConfigMode is configured as 'MANUAL' and the sipUAIpAddrPolicy is configured
				as 'DISTRIBUTED', then the sipUserAgentDefaultGw is a MANDATORY READ-WRITE object.
				When the sipUserAgentGwConfigMode is configured as 'MANUAL' and the sipUAIpAddrPolicy is configured
				as 'CENTRALISED', then the sipUserAgentDefaultGw is an OPTIONAL READ-WRITE object.
				When optional and no input received from the operator, the sipUserAgentDefaultGw is set to the  default value 0x00000000.
				When the sipUserAgentGwConfigMode is configured as 'DHCP', then the sipUserAgentDefaultGw is an OPTIONAL READ-ONLY object. It is set to the gateway value retrieved from the DHCP Server.

			ALCATEL-LUCENT NOTE:
			ACCESS:	READ-WRITE
			USAGE:	MAND		
			PERSIST:  	YES
			INSRVMOD:	NO
			RANGE:	NA
			DEFVALUE: 	NA
			UNITS:	NA		
			SPARSE:	NO						
			"
		::= { sipUserAgentEntry 11 }
		
--		sipUserAgentDomainSrv OBJECT-TYPE
--			SYNTAX InetAddress
--			ACCESS read-write
--			STATUS mandatory
--			DESCRIPTION
--				" IP address of the DNS server.
--                                  The IP context is defined by sipUserAgnetIpAddrType
--                                  If the sipUserAgentGwConfigMode is MANUAL, it is read-write and optional. 
--                                  If there is no DNS server is configured, only IP address could be supported, no URI would work. 
--                                   
--                                  If the sipUserAgentGwConfigMode is DHCP, it is read-write and optional. 
--                                  And if DHCP server does not assign DNS server to client, the configured DNS should be used.
--                                  If DHCP server does really assign DNS server, the configured DNS would be replaced by DHCP assigned one.
--                                  If DNS server is neither configured manually nor assigned by DHCP server, then only IP address could be supported, 
--                                  no URI would work.
--
--                                 If it's not configured or not assigned by DHCP server, it will be set to default value 0x00000000.
--
--				ALCATEL-LUCENT NOTE:
--					ACCESS:     NA
--                                        USAGE:       MAND		
--					PERSIST:  	YES
--					INSRVMOD: 	NO
--					RANGE:	NA
--					DEFVALUE: 	NA
--					UNITS:	NA	
--                                        SPARSE:    NO			
--				"
--			::= { sipUserAgentEntry 12 }

--		sipUserAgentInUseSrvAddr OBJECT-TYPE
--			SYNTAX InetAddress
--			ACCESS read-only
--			STATUS mandatory
--			DESCRIPTION
--				" IP address of the sip server currently used by the SIP user agent .
--
--				ALCATEL-LUCENT NOTE:
--					SUPPORT:  	YES
--					PERSIST:  	YES
--					INSRVMOD: 	NO
--					RANGE:	NA
--					DEFVALUE: 	NA
--					UNITS:	NA				
--				"
--			::= { sipUserAgentEntry 13 }
--

--		sipUserAgentTransProto OBJECT-TYPE
--			SYNTAX INTEGER
--				{
--				udp (1),
--				tcp (2)
--				}
--			ACCESS read-write
--			STATUS mandatory
--			DESCRIPTION
--				" The transport protocol type of the sip server.
--
--				ALCATEL-LUCENT NOTE:
--					SUPPORT:  	YES
--					PERSIST:  	YES
--					INSRVMOD: 	NO
--					RANGE:  1 -* only udp(1)
--					DEFVALUE: 	1
--					UNITS:	NA				
--				"
--			::= { sipUserAgentEntry 14 }

--		sipUserAgentPort OBJECT-TYPE
--			SYNTAX InetPortNumber
--			ACCESS read-write
--			STATUS mandatory
--			DESCRIPTION
--				" The transport layer port number of the SIP User Agent .
--				When sipUAIpPolicy o f SIP User Agent is configured to
--				 centralized, sipUserAgentPort configured by user  is 
--				 ignored, system set the value by itself.

--				ALCATEL-LUCENT NOTE:
--					SUPPORT:  	YES
--					PERSIST:  	YES
--					INSRVMOD: 	NO
--					RANGE:(1025!-49511)	
--					DEFVALUE: 	5060
--					UNITS:	NA				
--				"
--			DEFVAL { 5060 }
--			::= { sipUserAgentEntry 15 }
		

		sipUserAgentVlanId OBJECT-TYPE
            SYNTAX INTEGER (1..4093)
			ACCESS read-write
			STATUS mandatory
			DESCRIPTION
				" Vlan ID of the VLAN used for exchanging signaling traffic (SIP signaling packets)

                Multiple VAG : : the different SIP User Agent entries must be configured with the same 
                signaling VLAN (the same signaling VLAN is shared by all VAGs)
			ALCATEL-LUCENT NOTE:
			ACCESS:	READ-WRITE
			USAGE:	MAND			
			PERSIST:  	YES
			INSRVMOD:	NO
			RANGE:	NA
			DEFVALUE: 	NA
			UNITS:	NA	
			SPARSE:	NO			
			"
		::= { sipUserAgentEntry 16 }


		
--		sipUserAgentSignallingVlanId OBJECT-TYPE
--			SYNTAX VlanId
--			ACCESS read-write
--			STATUS mandatory
--			DESCRIPTION
--				" Vlan ID used for outgoing SIP signalling packets.
--
--				ALCATEL-LUCENT NOTE:
--					SUPPORT:  	YES
--					PERSIST:  	YES
--					INSRVMOD: 	NO
--					RANGE:	NA
--					DEFVALUE: 	NA
--					UNITS:	NA				
--				"
--			::= { sipUserAgentEntry 17 }

		sipUserAgentSignallingDscpMark OBJECT-TYPE
			SYNTAX INTEGER (0..63)
			ACCESS read-write
			STATUS mandatory
			DESCRIPTION
				" DSCP value assigned to outgoing SIP signalling traffic.
			ALCATEL-LUCENT NOTE:
			ACCESS:	READ-WRITE
			USAGE:	OPT
			PERSIST:	YES
			INSRVMOD:  NO 
			RANGE:	(0..63)
			DEFVALUE:	46 
			UNITS	:	NA	
			SPARSE:	NO			
			"
		::= { sipUserAgentEntry 18 }

		sipUserAgentSignallingPBits OBJECT-TYPE
			SYNTAX INTEGER (0..7)
			ACCESS read-write
			STATUS mandatory
			DESCRIPTION
				" 802.1p bits value assigned to outgoing SIP signalling traffic. 
			ALCATEL-LUCENT NOTE:
			ACCESS:	READ-WRITE
			USAGE:       OPT
			PERSIST:  	YES
			INSRVMOD: NO
			RANGE:	(0..7)
			DEFVALUE: 	6
			UNITS:	NA	
			SPARSE:	NO			
		"
		::= { sipUserAgentEntry 19 }

		sipUserAgentRtpVlanId OBJECT-TYPE
            SYNTAX INTEGER (0..4093)
			ACCESS read-write
			STATUS mandatory
			DESCRIPTION
				" Vlan ID of the VLAN used for exchanging media traffic (RTP/RTCP packets)
                Should the operator not configure this object, then the VLAN ID as configured in the sipUserAgentVlanId 
                object will be inherited. This means that the same VLAN ID is shared by signaling and voice traffic.
                                      
			ALCATEL-LUCENT NOTE:
			ACCESS:	READ-WRITE
			USAGE:       OPT
			PERSIST:  	YES
			INSRVMOD: NO
			RANGE:	NA
			DEFVALUE: 	sipUserAgentVlanId 
			UNITS:	NA			
 			SPARSE:    	NO			
			"
		::= { sipUserAgentEntry 20 }


		sipUserAgentRtpDscpMark OBJECT-TYPE
			SYNTAX INTEGER (0..63)
			ACCESS read-write
			STATUS mandatory
			DESCRIPTION
				" DSCP value assigned to outgoing media traffic.
			ALCATEL-LUCENT NOTE:
			ACCESS:	READ-WRITE
			USAGE:	OPT
			PERSIST:  	YES
			INSRVMOD: NO
			RANGE:	(0..63)
			DEFVALUE:	46	
			UNITS:	NA	
			SPARSE:	NO			
			"
		::= { sipUserAgentEntry 21 }

		sipUserAgentRtpPBits OBJECT-TYPE
			SYNTAX INTEGER (0..7)
			ACCESS read-write
			STATUS mandatory
			DESCRIPTION
				" 802.1p bits value assigned to outgoing media traffic.
			ALCATEL-LUCENT NOTE:
			ACCESS:	READ-WRITE
			USAGE:	OPT
			PERSIST:	YES
			INSRVMOD: NO
			RANGE:	(0..7)
			DEFVALUE: 	6	
			UNITS:	NA	
			SPARSE:	NO			
			"
		::= { sipUserAgentEntry 22 }

		sipUserAgentGwConfigMode OBJECT-TYPE
			SYNTAX INTEGER
			{
				dhcp(1),
				manual(2)
			}
			ACCESS read-write
			STATUS mandatory
			DESCRIPTION
				" The configuration mode of the L3 parameters for this SIP User Agent.

				7302/7330 ISAM FTTN :
				DHCP (1) : Can only be configured on the condition that the sipUAIpAddrPolicy is configured to 
					'distributed(1)' AND the same VLAN ID is shared by signaling and voice traffic i.e. 
					sipUserAgentRtpVlanId ='sipUserAgentVlanId'.
				MANUAL (2) : Can be configured in both cases , sipUAIpAddrPolicy ='distributed(1)' and 
					sipUAIpAddrPolicy ='centralized(2)' and this irrespective of whether signaling and voice traffic 
					share the same VLAN ID or do not share the same VLAN ID .

				7363 MX / 7367 SX:
				sipUAIpAddrPolicy can only be configured as 'centralized'.
				DHCP (1) : Can only be configured when the sipUAIpAddrPolicy is configured to 
                                         'centralised'  AND the same VLAN ID is shared by signaling and voice traffic.
				MANUAL (2) : Can be configured for sipUAIpAddrPolicy ='centralized' and this irrespective of whether 
				signaling and voice traffic share the same VLAN ID or do not share the same VLAN ID .

			ALCATEL-LUCENT NOTE:
			ACCESS:	READ-WRITE
			USAGE:	OPT
			PERSIST: 	YES
			INSRVMOD: NO
			RANGE:	1 | 2
			DEFVALUE: 	dhcp(1)
			UNITS:	NA	
			SPARSE:	NO			
			"
		::= { sipUserAgentEntry 23 }



		sipUserAgentAdminStatus OBJECT-TYPE
			SYNTAX INTEGER
			{
				up(1),
				down(2)
			}
			ACCESS read-write
			STATUS mandatory
			DESCRIPTION
				"The administrative status of this SIP User Agent.
				When the administrative status of the SIP User Agent is modified from 'up' to 'down', then following actions
				are taken by the system (at all voice LT boards) :
 				Active calls are immediately aborted;
 				SIP terminations are de-registered;
 				The operational status of the SIP terminations is modified to 'down'.
 				The physcial-lines of the SIP terminations are powered down.

				UP (1) : The attributes of this entry that are indicated as INSRVMOD=YES can be modified.
				DOWN (2) : The attributes of this entry that are indicated as INSRVMOD=YES and the attributes that are indicated as INSRVMOD=NO can be modified.
                             	Note that the attributes of this entry that are indicated INSRVMOD=NA can not be modified after creation..		ALCATEL-LUCENT NOTE:
			ACCESS:	READ-WRITE
			USAGE:	OPT
			PERSIST:  	YES
			INSRVMOD: YES
			RANGE:	1 | 2
			DEFVALUE:   down(2)	
			UNITS:	NA	
			SPARSE:	NO							
			"
		::= { sipUserAgentEntry 24 }


		
--		sipUserAgentOperStatus OBJECT-TYPE
--			SYNTAX INTEGER
--				{
--				up(1),
--				down(2)
--				}
--			ACCESS read-only
--			STATUS mandatory
--			DESCRIPTION
--				"The operational status of this sip ua. 
--					up(1)	- The sip ua is up and functional.
--					down(2)	- The sip ua is out of service.
--					
--				ALCATEL-LUCENT NOTE:
--					SUPPORT:  	YES
--					PERSIST:  	NO
--					INSRVMOD: 	NA
--					RANGE:	1 | 2
--					DEFVALUE: 	NA
--					UNITS:	NA								
--				"
--			::= { sipUserAgentEntry 25 }

		sipUserAgentRowStatus OBJECT-TYPE
			SYNTAX RowStatus
			ACCESS read-write
			STATUS mandatory
			DESCRIPTION
				"The status of this conceptual row.
				The RowStatus TC requires that this DESCRIPTION clause
				states under which circumstances other objects in this row
				can be modified.  The value of this object has no effect on
				whether other objects in this conceptual row can be
				modified.
				A conceptual row can always be made active.
			ALCATEL-LUCENT NOTE:
			ACCESS:	READ-WRITE
			USAGE:	MAND
			PERSIST:  	NO
			INSRVMOD: YES
			RANGE:	1 | 4 | 6	-- active (1), createAndGo (4), destroy (6)
			DEFVALUE: 	NA
			UNITS:	NA
                   	SPARSE#:	NO
         		"
		::= { sipUserAgentEntry 26 }


--		sipUAVoiceIpAddr OBJECT-TYPE
--			SYNTAX InetAddress
--			ACCESS read-write
--			STATUS mandatory
--			DESCRIPTION
--				"Public voice IP address of the voice traffic of this node.
--				that represents  voice ip address  uses the same value with sipUserAgentIpAddr
--
--				ALCATEL-LUCENT NOTE:
--					SUPPORT:  	YES
--					PERSIST:  	YES
--					INSRVMOD: 	NO
--					RANGE:	NA
--					UNITS:	NA				
--				"
--			::= { sipUserAgentEntry 27 }

		
--		sipUAVoiceIpAddrPrefixLength OBJECT-TYPE
--			SYNTAX InetAddressPrefixLength
--			ACCESS read-write
--			STATUS mandatory
--			DESCRIPTION
--				"The IP address prefix which is basically the number
--				of '1' bits in the netmask.  The range of allowed
--				values of this object is derived from the address type
--				in sipUserAgentIpAddrType i.e. [1..30] for Ipv4 or
--				[1..126] for Ipv6.

--				When User does not input this value, 
--				that represents  voice ip address prefix length  uses the 
--				same value with sipUAIpAddrPrefixLength
--
--				ALCATEL-LUCENT NOTE:
--					SUPPORT:  	YES
--					PERSIST:  	YES
--					INSRVMOD: 	NO
--					RANGE:	NA
--					DEFVALUE: 	NA
--					UNITS:	NA
--				"
--			::= { sipUserAgentEntry 28 }

		sipUAVoiceDefaultGW OBJECT-TYPE
			SYNTAX InetAddress
			ACCESS read-write
			STATUS mandatory
			DESCRIPTION
				" IP address of the associated default gateway for voice traffic.			
				The IP context is defined by sipUserAgentIpAddrType.

				The sipUAVoiceDefaultGW is an OPTIONAL READ-WRITE object, which, if no input received from the
				operator, by default inherets the value configured in the sipUserAgentGwConfigMode object.
				When the sipUserAgentGwConfigMode is configured as 'DHCP', then the sipUAVoiceDefaultGw is an
				OPTIONAL READ-ONLY object. It is set to the gateway value retrieved from the DHCP Server.
				When the sipUserAgentGwConfigMode is configured as 'MANUAL' and the sipUAIpAddrPolicy is configured
				as 'CENTRALISED', then the sipUAVoiceDefaultGw is an OPTIONAL READ-WRITE object.
				When optional and no input received from the operator, the sipUserAgentDefaultGw is set to the  default
				value 0x00000000.
				When the sipUserAgentGwConfigMode is configured as 'MANUAL' and the sipUAIpAddrPolicy is configured
				as 'DISTRIBUTED', then following rules apply 
 				When no configuration input received for the sipUserAgentRtpVlanId, the sipUAVoiceDefaultGw object inherets the value configured in the sipUserAgentGwConfigMode object.
 	 			When a configuration input is received for the sipUserAgentRtpVlanId and this configuration input is identical to the configuration input received for the sipUserAgentSignallingVlanId object, then the sipUAVoiceDefaultGw object inherets the value configured in the sipUserAgentGwConfigMode object.
 				When a configuration input is received for the sipUserAgentRtpVlanId and this configuration input is different from the configuration input received for the sipUserAgentSignallingVlanId object, then the sipUAVoiceDefaultGw is a MANDATORY READ-WRITE object.

			ALCATEL-LUCENT NOTE:
			ACCESS:	READ-WRITE
			USAGE:	OPT
			PERSIST:  	YES
			INSRVMOD: NO
			RANGE:	NA
			DEFVALUE: 	sipUserAgentDefaultGw
			UNITS:	NA	
			SPARSE#:	NO							
			"
		::= { sipUserAgentEntry 29 }

		sipUAIpAddrPolicy OBJECT-TYPE
			SYNTAX INTEGER
			{
				distributed (1),
				centralized (2) 
			}
			ACCESS read-write
			STATUS mandatory
			DESCRIPTION
				"The IP Address policy to be applied

				7302/7330 ISAM FTTN : BOTH IP address policies apply. 
				Distributed (1) : 
					- A SIP User Agent instance per Voice LT board. 
					- A signaling IP@ to be configured per Voice LT board
					- A Voice IP@ to be configured per Voice LT board
				Centralised (2) :
					- A SIP User Agent instance per Voice LT board.
					- A single signaling IP@ shared by all voice LT boards
					- A single voice IP@ shared by all voice LT boards
					- Signaling and voice IP@ are to be configured at the xHUB.

                SIP User Agent entries that share the same VLAN(s) must be configured with the same IP address policy.

	            7363 MX / 7367 SX: Only the CENTRALIZED IP address policy applies.
                The system will reject a management command that intends to configure the DISTRIBUTED IP address policy
                Centralised (2) :
                - A single SIP User Agent instance hosted at the NT board.
                - A single signaling IP@ shared by all voice LT boards
                - A single voice IP@ shared by all voice LT boards
                - Signaling and voice IP@ are to be configured at the NT board.

			ALCATEL-LUCENT NOTE:
			ACCESS:	READ-WRITE
     			USAGE:	OPT
			PERSIST:  	YES
			INSRVMOD: NO
			RANGE:	1 | 2 
			DEFVALUE: 	distributed (1)
			UNITS:	NA	
     			SPARSE:	NO			
			"
		::= { sipUserAgentEntry 30 }

		sipUASignalingLinkMTU OBJECT-TYPE
			SYNTAX INTEGER (576..1500)
			ACCESS read-write
			STATUS mandatory
			DESCRIPTION
				"The default MTU of the outgoing signalling traffic of the SIP user agent.

			ALCATEL-LUCENT NOTE:
			ACCESS:	READ-WRITE
			USAGE:	OPT
			PERSIST:  	YES
			INSRVMOD: NO
			RANGE:	(576..1500)
			DEFVALUE:  1500
			UNITS:	NA	
			SPARSE:	NO			
			"
		::= { sipUserAgentEntry 31 }

		sipUAVoiceLinkMTU OBJECT-TYPE
			SYNTAX INTEGER (576..1500)
			ACCESS read-write
			STATUS mandatory
			DESCRIPTION
				"LinkMTU value of the outgoing voice traffic of this sip user agent .

			ALCATEL-LUCENT NOTE:
			ACCESS:	READ-WRITE
			USAGE:	OPT
			PERSIST:	YES
			INSRVMOD: NO
			RANGE:	(576..1500)
			DEFVALUE: 	1500
			UNITS:	NA
			SPARSE:	NO				
			"
		::= { sipUserAgentEntry 32 }		
		
		sipUserAgentDHCPOptionReqList OBJECT-TYPE
			SYNTAX DisplayString (SIZE (0..63))
			ACCESS read-write
			STATUS mandatory
			DESCRIPTION 
			"This parameter lists the DHCP options the SIP User Agent wants the DHCP server to retur in option 55.
            Format : a series of DHCP options separated by a comma. Option index range is (1..255).
            The maximum number of options that can be specified = 16. 
            This object is only relevant in the case sipUAIpAddrPolicy = 'distributed(1)' and 
            sipUserAgentGwConfigMode = 'dhcp(1)'.

            SIP User Agent entries that share the same VLAN & that have the IP@ policy set to 'distributed' & that
            have the IP config mode set to 'DHCP', must have the same DHCP Option Request List configured.


			ALCATEL-LUCENT NOTE:
			ACCESS:	READ-WRITE
			USAGE:	OPT
			PERSIST:	YES
			INSRVMOD: NO
			RANGE:	SIZE (0..63)
			DEFVALUE: 	1,3,6,120
			UNITS:	NA
			SPARSE:	NO				
			"
      	 	::= {sipUserAgentEntry 33 }

        sipUserAgentProviderName OBJECT-TYPE
            SYNTAX OCTET STRING (SIZE (0..32))
            ACCESS read-write
            STATUS mandatory
            DESCRIPTION
	            "The name of the parent Service Gateway. 

            ALCATEL NOTE:
            ACCESS:read_write
            USAGE: NA              
            PERSIST:       YES
            INSRVMOD: NO
            RANGE: SIZE (0..32)
            DEFVALUE:      vsp1
            UNITS: NA      
            SPARSE:        NO
            "
            ::= { sipUserAgentEntry 34 }

           sipUALSAVoiceDefaultGW OBJECT-TYPE
           SYNTAX InetAddress
           ACCESS read-write
           STATUS mandatory
           DESCRIPTION
           "IP gateway IP address for the LSA media VLAN.
           This object is irrelevant in case the LSA server instance serves the local node only or
           in case the LSA server instance serves a clustered node topology whereby all nodes
           are connected via a L2 Network.

           ALCATEL-LUCENT NOTE:
           ACCESS: READ-WRITE
           USAGE: OPT
           PERSIST: YES
           INSRVMOD: NO
           RANGE: NA
           DEFVALUE: 0.0.0.0 
           UNITS: NA 
           SPARSE: NO 
           "
           ::= { sipUserAgentEntry 35 }

           sipUALSARTPVlanId OBJECT-TYPE
           SYNTAX INTEGER (0..4093)
           ACCESS read-write
           STATUS mandatory
           DESCRIPTION
           "The Vlan ID of the LSA Media VLAN.
            This object is associated with the sipUaApLSARTPIpAddr.
            Should the operator neither configure the sipUaApLSARTPIpAddr nor the
            sipUALSARTPVlanId then upon switching to LSA server mode the SIP UA will use the
            media VLAN ID and media IP address as configured in the sipUserAgentRtpVlanId  and
            sipUaApRtpIpAddr objects.
            Should only the sipUApLSARTPIpAddr or only the sipUALSARTPVlanId object be configured 
            then upon switching to LSA server mode the SIP UA will use the media VLAN ID and media
            IP address as configured in the sipUserAgentRtpVlanId and sipUaApRtpIpAddr objects.

            ALCATEL-LUCENT NOTE:
            ACCESS:	READ-WRITE
            USAGE: OPT
            PERSIST: YES
            INSRVMOD: NO
            RANGE: NA
            DEFVALUE: sipUserAgentRtpVlanId
            UNITS: NA
            SPARSE:	NO
            "
            ::= { sipUserAgentEntry 36 }

            sipUALSAMD5Realm OBJECT-TYPE
            SYNTAX OCTET STRING (SIZE (0..64))
            ACCESS read-write
            STATUS mandatory
            DESCRIPTION
            "The MD5 realm that allows a SIP termination to register to this LSA server instance.
             The same MD5 realm must be configured at the LSA server instance that has been assigned for the
             SIP terminations to be registered by this SIP User Agent.
             The LSA server instance uses the configured MD5 password together with a hard-coded string and
             the parameters [MD5 realm, Authentication scheme, Algorithm, QOP, Opaque Value and a Nonce Value
             generated by the LSA server instance) to generate the authentication key that is then compared with
             the Digest Authentication response in the SIP REGISTER request.
             In case the result is negative, the registration request is rejected with a 403 response.
             When the MD5 parameters are configured for the LSA server instance then the incoming register
             requests will be challenged. In order for the incoming register request to be successful,
             the MD5 parameters must also been correctly configured at the access node side.
             When the MD5 parameters are not configured for the LSA server instance then no challenge
             will be done for incoming register requests and this regardless of the MD5 parameters being
             configured at the access node side or not.
             In case this object hasn't been configured, the SIP User Agent uses the configured value of the
             sipTerminationMD5Realm object in the sipTerminationTable for the registration request to the
             LSA server.

             ALCATEL-LUCENT NOTE:
             ACCESS:	NA
             USAGE: OPT
             PERSIST: YES
             INSRVMOD: NO
             RANGE: SIZE (0..64)
             DEFVALUE: null
             UNITS: NA
             SPARSE: NO
             "
             ::= { sipUserAgentEntry 37 }

             sipUALSAMD5Password OBJECT-TYPE
             SYNTAX OCTET STRING (SIZE (0..64))
             ACCESS read-write
             STATUS mandatory
             DESCRIPTION
             "The MD5 password that allows a SIP termination to register to this LSA server instance.
              The MD5 password cannot be displayed via a CLI show command; Upon configuration it is
              encrypted based on the DES-CBC algorithm.
              As authentication intends to avoid DOS attacks as well as a SIP termination to register to the
              wrong LSA server instance i.e the LSA server instance that wasn't assigned to that SIP termination,
              it is preferred to configure a different MD5 Password for each LSA server instance.
              The same MD5 password must be configured at the LSA server instance that has been assigned
              for the SIP terminations to be registered by this SIP User Agent. 
              The LSA server instance uses the configured MD5 password together with a hard-coded string and
              the parameters [MD5 realm, Authentication scheme, Algorithm, QOP, Opaque Value and a Nonce Value
              generated by the LSA server instance) to generate the authentication key that is then compared with
              the Digest Authentication response in the SIP REGISTER request.
              In case the result is negative, the registration request is rejected with a 403 response.
              When the MD5 parameters are configured for the LSA server instance then the incoming register
              requests will be challenged. In order for the incoming register request to be successful,
              the MD5 parameters must also been correctly configured at the access node side.
              When the MD5 parameters are not configured for the LSA server instance then no challenge
              will be done for incoming register requests and this regardless of the MD5 parameters being
              configured at the access node side or not.
              In case this object hasn't been configured, the SIP User Agent uses the configured value of the
              sipTerminationMD5Password object in the sipTerminationTable for the registration request to
              the LSA server.

              ALCATEL-LUCENT NOTE:
              ACCESS:	NA
              USAGE: OPT
              PERSIST: YES
              INSRVMOD: NO
              RANGE: SIZE (0..64)
              DEFVALUE: null
              UNITS: NA
              SPARSE:	NO
              "
              ::= { sipUserAgentEntry 38 }

-- =============================================================================
-- Sip UserAgent Mapping Table
-- =============================================================================
		sipUserAgentMappingTable OBJECT-TYPE
			SYNTAX SEQUENCE OF SipUserAgentMappingEntry
			ACCESS not-accessible
			STATUS mandatory
			DESCRIPTION
				"The Sip User agent name to unique internal identifier mapping table.

                7302/7330 ISAM FTTN : Supported
                7363 MX : Supported
		7367 SX : Supported

			ALCATEL NOTE: 
 			TABLESIZE: 16
			DESCR:NA."
		::= { sipMIB 7 }
		
		sipUserAgentMappingEntry OBJECT-TYPE
			SYNTAX SipUserAgentMappingEntry
			ACCESS not-accessible
			STATUS mandatory
			DESCRIPTION
				"The SIP User Agent name to unique internal index mapping table.
                An entry is auto-created upon the creation of an entry in the sipUserAgentTable.
                An entry is auto-deleted upon the deletion of an entry in the sipUserAgentTable.
			"
		INDEX { sipUaMappingName }
		::= { sipUserAgentMappingTable 1 }

		SipUserAgentMappingEntry ::=
			SEQUENCE { 
				sipUaMappingName		OCTET STRING,
				sipUaMappingId			INTEGER	
			 }	

		sipUaMappingName OBJECT-TYPE
			SYNTAX OCTET STRING (SIZE (0..32))
			ACCESS not-accessible
			STATUS mandatory
			DESCRIPTION
				" The operator friendly name for this SIP User Agent.
			ALCATEL-LUCENT NOTE:
			ACCESS:	NOT-ACCESSIBLE
			USAGE:	MANDATORY
			PERSIST:	NA
			INSRVMOD: NA 
			RANGE:	SIZE (0..32)
			DEFVALUE: 	NA
			UNITS:	NA	
			SPARSE:	NO			
			"
		::= { sipUserAgentMappingEntry 1 }

		sipUaMappingId OBJECT-TYPE
			SYNTAX INTEGER
			ACCESS read-only
			STATUS mandatory
			DESCRIPTION
				"This index is the unique internal identifier of this SIP User Agent.
			ALCATEL-LUCENT NOTE:
			ACCESS:	READ-ONLY
			USAGE:	NA
			PERSIST:	NA 
			INSRVMOD: NA
			RANGE:	(1..16)
			DEFVALUE: 	NA
			UNITS:	NA
			SPARSE:	NO
			"
		::= { sipUserAgentMappingEntry 2 }	

			
-- =============================================================================
-- Sip Dial Plan Table.
-- =============================================================================
		sipDialPlanTable OBJECT-TYPE
			SYNTAX SEQUENCE OF SipDialPlanEntry
			ACCESS not-accessible
			STATUS mandatory
			DESCRIPTION
				"The sipDialPlanTable allowing to create a dial plan for a Service Gateway.
                The operator must create a dial plan for each of the Service Gateways created and activated in the 
                access node. (administrative state =  unlocked in the sipVSPTable).
                Maximum 16 entries can be created.
                The sipDialPlanProviderName attribute must be configured with the same value as the value configured in
                the sipVSPTable.sipVSPName of the parent Service Gateway.

                7302/7330 ISAM FTTN : Supported
                7363 MX : Supported
		7367 SX : Supported

				ALCATEL NOTE: 
				TABLESIZE: 16 
				DESCR:NA."
			::= { sipMIB 8 }

		sipDialPlanEntry OBJECT-TYPE
			SYNTAX SipDialPlanEntry
			ACCESS not-accessible
			STATUS mandatory
			DESCRIPTION
					"An entry in the sipDialPlanTable."
			INDEX { sipDialPlanId }
			::= { sipDialPlanTable 1 }
	
		SipDialPlanEntry ::=
			SEQUENCE { 
				sipDialPlanId			INTEGER,
				sipDialPlanName			OCTET STRING,
				sipDialPlanPrefixActivated		INTEGER,
				sipDialPlanStaticPrefix		OCTET STRING,
				sipDialPlanStaticSuffix		OCTET STRING,
		--		sipDialPlanUsedStatus 		INTEGER,
				sipDialPlanRowStatus		RowStatus,
				sipDialPlanDigitMapMode	INTEGER,
				sipDialPlanProviderName       OCTET STRING
				}

		sipDialPlanId OBJECT-TYPE
			SYNTAX INTEGER 
			ACCESS not-accessible
			STATUS mandatory
			DESCRIPTION
					" Unique internal identifier of a dial plan
				ALCATEL-LUCENT NOTE:
				ACCESS:	NOT-ACCESSIBLE
				USAGE:	MANDATORY
				PERSIST:  	YES
				INSRVMOD: NA
				RANGE:	(1..16)
				DEFVALUE: 	NA
				UNITS:	NA	
				SPARSE:	NO			
					"
			::= { sipDialPlanEntry 1 }


		sipDialPlanName OBJECT-TYPE
			SYNTAX OCTET STRING (SIZE (0..32))
			ACCESS read-write
			STATUS mandatory
			DESCRIPTION
					" The operator friendly name of the dial plan. 
                    The name must be unique accross all entries of the table.
				ALCATEL-LUCENT NOTE:
				ACCESS:	NA
				USAGE:	MAND
				PERSIST:  	YES
				INSRVMOD: YES
				RANGE:	SIZE(0..32)
				DEFVALUE: 	NA
				UNITS:	NA	
				SPARSE:	NO			
					"
			::= { sipDialPlanEntry 2 }

		sipDialPlanPrefixActivated OBJECT-TYPE
			SYNTAX INTEGER
				{
				on(1),
				off(2)
				}
			ACCESS read-write
			STATUS mandatory
			DESCRIPTION
					" ON (1) : Dial Plan activated.
					  OFF (2) : Dial Plan de-activated.
				ALCATEL-LUCENT NOTE:
				ACCESS:	NA
				USAGE:       OPT
				PERSIST:  	YES
				INSRVMOD: YES
				RANGE:	1 | 2
				DEFVALUE: 	off(2)
				UNITS:	NA	
				SPARSE:	NO			
				"
			::= { sipDialPlanEntry 3 }

		sipDialPlanStaticPrefix OBJECT-TYPE
			SYNTAX OCTET STRING (SIZE (0..32))
			ACCESS read-write
			STATUS mandatory
			DESCRIPTION
					" Static prefix including URI type and area code added to all valid DNs to form 'To' and 'Request URI' 
					headers. If this object is configured,the value of sipVSPURIType will not be used in 'To' and 'Request URI' 
					headers.
				ALCATEL-LUCENT NOTE:
				ACCESS:	NA
				USAGE:       OPT
				PERSIST:  	YES
				INSRVMOD: YES
				RANGE:	SIZE (0..32)
				DEFVALUE: 	null
				UNITS:	NA	
				SPARSE:	NO			
					"
			::= { sipDialPlanEntry 4 }

		sipDialPlanStaticSuffix OBJECT-TYPE
			SYNTAX OCTET STRING (SIZE (0..32))
			ACCESS read-write
			STATUS mandatory
			DESCRIPTION
					" Static suffix including domain name and port added to all valid DNs for form 'To' and 'Request URI' 
					headers. If this object is configured,the value of sipVSPDomainName will not be used in 'To' and 'Request 
					URI' headers.
				ALCATEL-LUCENT NOTE:
				ACCESS:	NA
				USAGE:	OPT
				PERSIST:  	YES
				INSRVMOD:	YES
				RANGE:	(SIZE (0..32)
				DEFVALUE: 	null
				UNITS:	NA		
		 		SPARSE:	NO		
					"
			::= { sipDialPlanEntry 5 }


--		sipDialPlanUsedStatus OBJECT-TYPE
--			SYNTAX INTEGER (0..65535)
--			ACCESS read-only	
--			STATUS mandatory
--			DESCRIPTION
--				" the number of terminations that are using this dial plan.
--
--				ALCATEL-LUCENT NOTE:
--					ACCESS:     NA
--                                        USAGE:       NA
--					PERSIST:  	NO
--					INSRVMOD: NA
--					RANGE:	(0..65535)
--					DEFVALUE: 	NA
--					UNITS:	NA	
--                                       SPARSE:    NO			
--				"
--			::= { sipDialPlanEntry 6 }

		sipDialPlanRowStatus OBJECT-TYPE
			SYNTAX RowStatus
			ACCESS read-write
			STATUS mandatory
			DESCRIPTION
				"The status of this conceptual row.
				The RowStatus TC requires that this DESCRIPTION clause
				states under which circumstances other objects in this row
				can be modified.  The value of this object has no effect on
				whether other objects in this conceptual row can be
				modified.
				A conceptual row can always be made active.
				ALCATEL-LUCENT NOTE:
				ACCESS:	NA
				USAGE:	MAND
				PERSIST:	NO
				INSRVMOD:	YES
				RANGE:  	1 | 4 | 5 | 6       -- active (1), createAndGo(4), createAndWait (5), destroy (6)
				DEFVALUE:	NA
				UNITS:	NA
				SPARSE: 	NO
			"
		::= { sipDialPlanEntry 7 }

		sipDialPlanDigitMapMode OBJECT-TYPE
			SYNTAX INTEGER
				{
				maximum(1),
				minimum(2)
				}
			ACCESS read-write
			STATUS mandatory
			DESCRIPTION
				" The digitmap match mode of this dial plan.
				Maximum: standard match mode.
				Minimum: System should send out INVITE immediately when an exact full match dial string is detected.    
				ALCATEL-LUCENT NOTE:
						ACCESS:	NA
				USAGE:	MAND
				PERSIST:	YES
				INSRVMOD: YES
				RANGE:  	1 | 2
				DEFVALUE: 	maximum(1)
				UNITS:  	NA
				SPARSE: 	NO
			"
		::= { sipDialPlanEntry 8 }

        sipDialPlanProviderName OBJECT-TYPE
            SYNTAX OCTET STRING (SIZE (0..32))
            ACCESS read-write
            STATUS mandatory
            DESCRIPTION
                "The name of the parent Service Gateway. 

                ALCATEL NOTE:
                ACCESS:read_write
                USAGE: NA              
                PERSIST:       YES
                INSRVMOD: NO
                RANGE: SIZE (0..32)
                DEFVALUE:     vsp1 
                UNITS: NA      
                SPARSE:        NO
            "
        ::= { sipDialPlanEntry 9 }

-- =============================================================================
-- Sip Dial Plan Mapping Table
-- =============================================================================
		sipDialPlanMappingTable OBJECT-TYPE
			SYNTAX SEQUENCE OF SipDialPlanMappingEntry
			ACCESS not-accessible
			STATUS mandatory
			DESCRIPTION
				"The operator friendly Dial Plan name to unique internal identifier mapping table.

                7302/7330 ISAM FTTN : Supported
                7363 MX : Supported
		7367 SX : Supported
		
				ALCATEL NOTE: 
				TABLESIZE: 16 
				DESCR:NA."
			::= { sipMIB 9 }

		sipDialPlanMappingEntry OBJECT-TYPE
			SYNTAX SipDialPlanMappingEntry
			ACCESS not-accessible
			STATUS mandatory
			DESCRIPTION
					"An entry in the sipDialPlanTable.
                    An entry is auto-created upon the creation of an entry in the sipDialPlanTable.
                    An entry is auto-deleted upon the deletion of an entry in the sipDialPlanTable.
					"
			INDEX { sipDialPlanMappingName }
			::= { sipDialPlanMappingTable 1 }

		SipDialPlanMappingEntry ::=
			SEQUENCE { 
				sipDialPlanMappingName
					OCTET STRING,
				sipDialPlanMappingId
					INTEGER	
			 }	

		sipDialPlanMappingName OBJECT-TYPE
			SYNTAX OCTET STRING (SIZE (0..32))
			ACCESS not-accessible
			STATUS mandatory
			DESCRIPTION
					" The operator friendly name of the dial plan.
				ALCATEL-LUCENT NOTE:
				ACCESS:	NOT-ACCESSIBLE
				USAGE:	MANDATORY
				PERSIST:	NA
				INSRVMOD: NA	
				RANGE:	SIZE (0..32)
				DEFVALUE: 	NA
				UNITS:	NA	
				SPARSE:	NO			
					"
			::= { sipDialPlanMappingEntry 1 }

		sipDialPlanMappingId OBJECT-TYPE
			SYNTAX INTEGER 
			ACCESS read-only
			STATUS mandatory
			DESCRIPTION
					"The unique internal identifier of the dial plan.
				ALCATEL-LUCENT NOTE:
				ACCESS:	NA
				USAGE:	NA
				PERSIST:	NA	
				INSRVMOD: NA
				RANGE:	(1..32)
				DEFVALUE: 	NA
				UNITS:	NA
				SPARSE:	NO
					"
			::= { sipDialPlanMappingEntry 2 }	


-- =============================================================================
-- Sip Dial Plan Digitmap Table.
-- =============================================================================
		sipDialPlanDigitmapTable OBJECT-TYPE
			SYNTAX SEQUENCE OF SipDialPlanDigitmapEntry
			ACCESS not-accessible
			STATUS mandatory
			DESCRIPTION
				"The SIP Dial Plan Digitmap table allows to configure the digit map patterns that are associated with a dial plan. (Actually 
                only 1 dial plan is supported per Service Gateway).
                The patterns are configured in the sipDialPlanDigitmapValue object.
                A sipDialPlanDigitmap table entry is often called a 'digit map rule'.
                A digit map rule may contain several patterns. Different patterns are separated by the '|' character.
                A pattern must NOT be split over different digit map rules.
                The maximum size of a configured sipDialPlanDigitmapValue object = 100 bytes. This size includes the configured patterns as well as
                the pattern separator(s).
                Once the digitmap configuration has completed, The NT passes the entire digitmap to the digitmap parser hosted at the voice LT board.
                Following restrictions will be checked by the digitmap parser :
                i. The total size of 'allowed' patterns ,of the same type, must NOT EXCEED 4 Kbytes.
                (Actually only the type 'digitmap' is supported.)
                ii. The total amount of patterns matching a dialled digit string must NOT EXCEED 50.

                Actually it is not possible to create sipDialPlanDigitmap table entries with sipDialPlanDigitmapAccessType = 'not-allowed'.

                The operator must create the entire digit map for the VSP or each of the VAGs that are created and activated in 
                the access node. (administrative state =  unlocked) in the sipVSPTable.
                Maximum 16 entire digit maps can be created.

	            7302/7330 ISAM FTTN : Supported
                7363 MX : Supported
		7367 SX : Supported

				ALCATEL NOTE: 
				TABLESIZE: DEP[4K * 16] The total size of the sipDialPlanDigitmapValue of ONE dial plan cannot exceed 4K
				DESCR:NA."
		::= { sipMIB 10 }

		sipDialPlanDigitmapEntry OBJECT-TYPE
			SYNTAX SipDialPlanDigitmapEntry
			ACCESS not-accessible
			STATUS mandatory
			DESCRIPTION
					"An entry in the sipDialPlanDigitmapTable."
			INDEX { sipDialPlanId, sipDialPlanDigitmapType, sipDialPlanDigitmapValue }
			::= { sipDialPlanDigitmapTable 1 }

		SipDialPlanDigitmapEntry ::=
			SEQUENCE { 
			sipDialPlanDigitmapType			INTEGER,
			sipDialPlanDigitmapValue		OCTET STRING,
			sipDialPlanDigitmapAccessType		INTEGER,	
			sipDialPlanDigitmapRowStatus		RowStatus
			}

		sipDialPlanDigitmapType OBJECT-TYPE
			SYNTAX INTEGER
				{
				prefixDigitmap(1),
				digitmap(2),
				emergencyDigitmap(3)
				}
			ACCESS not-accessible
			STATUS mandatory
			DESCRIPTION
					" 1 : Digitmap of all allowed DN prefixes (Actually NOT supported)
					  2 : Digitmap of all allowed DN  (Actually SUPPORTED)
					  3 : Digitmap including all DNs that must be considered as emergency numbers (Actually NOT supported)
				ALCATEL-LUCENT NOTE:
				ACCESS:	NOT-ACCESSIBLE
				USAGE:	MANDATORY
				PERSIST:  	YES
				INSRVMOD: NA	
				RANGE:	2 
				DEFVALUE: 	NA
				UNITS:	NA	
				SPARSE:	NO			
					"
		::= { sipDialPlanDigitmapEntry 1 }

		sipDialPlanDigitmapValue OBJECT-TYPE
			SYNTAX OCTET STRING (SIZE (1..100))
			ACCESS not-accessible
			STATUS mandatory
			DESCRIPTION
					" Allows to configure the digit map patterns.
				Several patterns may be concatenated in this object. The different patterns are separated by the  '|' character.
				A pattern must NOT be split over different digit map rules.
				The maximum size of a configured sipDialPlanDigitmapValue object = 100 bytes. This size includes the configured patterns as well as the pattern separator(s).
				Supported character set : 0123456789ABCDEIPRSTxXZ.,*?-|^[](){}#+
				                                                                                 
				ALCATEL-LUCENT NOTE:
				ACCESS:	NOT-ACCESSIBLE
				USAGE:	MANDATORY
				PERSIST:  	YES
				INSRVMOD: NA	
				RANGE: 	(SIZE (1..100))
				DEFVALUE: 	NA
				UNITS:	NA	
				SPARSE:	NO			
					"
		::= { sipDialPlanDigitmapEntry 2 }
		
		sipDialPlanDigitmapAccessType OBJECT-TYPE
			SYNTAX INTEGER
				{
				allowed(1),
				notallowed(2)
				}
			ACCESS read-write		
			STATUS mandatory
			DESCRIPTION
					" Status of digitmap rule being allowed.
					This object is actually NOT supported. So no matter what is configured for this object, the system considers a 
					digitmap value always as 'allowed'. 
				ALCATEL-LUCENT NOTE:
				ACCESS:	READ-WRITE
				USAGE:	OPT
				PERSIST:  	YES
				INSRVMOD: YES
				RANGE:	1..2
				DEFVALUE: 	1
				UNITS:	NA	
				SPARSE:	NO			
					"
			::= { sipDialPlanDigitmapEntry 3 }


		sipDialPlanDigitmapRowStatus OBJECT-TYPE
			SYNTAX RowStatus
			ACCESS read-write
			STATUS mandatory
			DESCRIPTION
				"The status of this conceptual row.
				The RowStatus TC requires that this DESCRIPTION clause
				states under which circumstances other objects in this row
				can be modified.  The value of this object has no effect on
				whether other objects in this conceptual row can be modified.
				A conceptual row can always be made active.
				ALCATEL-LUCENT NOTE:
				ACCESS:	READ-WRITE
				USAGE:	MAND
				PERSIST:	NO
				INSRVMOD: YES
				RANGE:  	1 | 4 | 6       -- active (1), createAndGo(4), destroy (6)
				DEFVALUE:	NA
				UNITS:	NA
				SPARSE:	NO
			"
		::= { sipDialPlanDigitmapEntry 4 }

		
-- =============================================================================
-- Sip Termination Table.
-- =============================================================================
		sipTerminationTable OBJECT-TYPE
			SYNTAX SEQUENCE OF SipTerminationEntry
			ACCESS not-accessible
			STATUS mandatory
			DESCRIPTION
				"The sipTerminationTable allowing to create SIP Terminations.
                SIP terminations are associated with a Service Gateway by means of the sipTerminationProviderName attribute.
                The sipTerminationProviderName attribute must be configured with the same value as the value configured in
                the sipVSPTable.sipVSPName of the parent Service Gateway.

                7302/7330 ISAM FTTN : Supported
                7363 MX : Supported
		7367 SX : Supported

			ALCATEL NOTE: 
			TABLESIZE: DEP [max slot of one shelf multiply max termination of one board]
			DESCR:NA."
		::= { sipMIB 11 }

		sipTerminationEntry OBJECT-TYPE
			SYNTAX SipTerminationEntry
			ACCESS not-accessible
			STATUS mandatory
			DESCRIPTION
				"An entry in the sipTerminationTable."
			INDEX { ifIndex }
		::= { sipTerminationTable 1 }

		SipTerminationEntry ::=
			SEQUENCE { 
--			sipTerminationAssocUserAgentId		INTEGER,
			sipTerminationDn					OCTET STRING,
			sipTerminationUserName				OCTET STRING,
			sipTerminationUri					OCTET STRING,
			sipTerminationDirectConnectUri			OCTET STRING,
			sipTerminationCallStatus				INTEGER,
--			sipTerminationStartLineTest			INTEGER,
--			sipTerminationLineTestStatus			INTEGER,
			sipTerminationCharacteristic			INTEGER,
			sipTerminationMD5Realm				OCTET STRING,
			sipTerminationMD5Password			OCTET STRING,
			sipTerminationAdminStatus			INTEGER,
			sipTerminationOperStatus				INTEGER,
			sipTerminationRowStatus 				RowStatus,
			sipTerminationTestStatus  				INTEGER,
			sipTermContactUserInfo  				OCTET STRING,
			sipTerminationAssocVSPId				INTEGER,
			sipTerminationETSIClipDataMode		INTEGER,
            sipTerminationTelcordiaClipDataMode INTEGER,
			sipTerminationDisplayName			OCTET STRING,
			sipTerminationImpedance				SipTerminationImpedance,
			sipTerminationRxGain    				INTEGER,
			sipTerminationAntiTapping			INTEGER,
			sipTerminationOpStatDownReason		INTEGER,
			sipTerminationTxGain				INTEGER,
			sipTermTestAccessState				INTEGER,
			sipTermTestAccessTimeout			INTEGER,
			sipTermTestAccessBusyOverwrite			TruthValue,
			sipTerminationWarmlineService			INTEGER,
			sipTerminationGroup 				INTEGER,
			sipTerminationSIPServerAddr 			InetAddress,
			sipTerminationEnableCallWaiting		INTEGER,
			sipTerminationEnableCallHold			INTEGER,
			sipTerminationEnableCallConference		INTEGER,
			sipTerminationEnableCallTransfer		INTEGER,
			sipTerminationEnableForceHold			INTEGER,
			sipTerminationLineSignalOnRemoteAnswer	INTEGER,	
			sipTerminationLineId				OCTET STRING,
			sipTerminationProviderName          OCTET STRING
			}

		
--		sipTerminationAssocUserAgentId OBJECT-TYPE
--			SYNTAX INTEGER (1..255)
--			ACCESS read-write
--			STATUS mandatory
--			DESCRIPTION
--				" Identifier of the associated sip ua of this 
--				sip termination.
--
--				ALCATEL-LUCENT NOTE:
--					SUPPORT:  	YES
--					PERSIST:  	YES
--					INSRVMOD: 	NO
--					RANGE:	(1..255)
--					DEFVALUE: 	NA
--					UNITS:	NA
--                                      SPARSE:    NO				
--				"
--			::= { sipTerminationEntry 1 }

		sipTerminationDn OBJECT-TYPE
			SYNTAX OCTET STRING (SIZE (0..32))
			ACCESS read-write
			STATUS mandatory
			DESCRIPTION
				" Directory number of this sip termination.
				Both, the sipTerminationDn and sipTerminationUri can not be configured with the null string.
				Should DN being configured and URI left empty then the register URI is composed by concatenating the
				configured DN together with the register URI configured in the sipRegisterTable.
				Should this object not been configured then the sipTerminationUri must be configured.
			ALCATEL-LUCENT NOTE:
			ACCESS:	NA
			USAGE:	OPT 
			PERSIST:  	YES
			INSRVMOD: NO
			RANGE:	SIZE (0..32)
			DEFVALUE: 	null
			UNITS:	NA	
			SPARSE:	NO			
			"
		::= { sipTerminationEntry 2 }
		
		sipTerminationUserName OBJECT-TYPE
			SYNTAX OCTET STRING (SIZE (0..64))
			ACCESS read-write
			STATUS mandatory
			DESCRIPTION
				" User name of this sip termination.
				Must be unique across all entries of this table.
			ALCATEL-LUCENT NOTE:
			ACCESS:	NA
			USAGE:	OPT
			PERSIST:  	YES
			INSRVMOD: NO
			RANGE:	SIZE (0..64)
			DEFVALUE: 	null
			UNITS:	NA	
			SPARSE:	NO			
			"
		::= { sipTerminationEntry 3 }

		sipTerminationUri OBJECT-TYPE
			SYNTAX OCTET STRING (SIZE (0..80))
			ACCESS read-write
			STATUS mandatory
			DESCRIPTION
				" SIP URI by which the user agent identifies this sip termination.
				Must be unique across all entries of this table.
				sipTerminationDn and sipTerminationUri can not be configured to the null string at the same time.
				The register URI in the sipRegisterTable must not be configured in case this object is configured as the URI
				configured in this object also includes the register domain.
			ALCATEL-LUCENT NOTE:
			ACCESS:	NA
			USAGE:	OPT
			PERSIST:  	YES
			INSRVMOD: NO
			RANGE:	SIZE (0..80)
			DEFVALUE: 	null
			UNITS:	NA	
			SPARSE:	NO			
			"
		::= { sipTerminationEntry 4 }


		sipTerminationDirectConnectUri OBJECT-TYPE
			SYNTAX OCTET STRING (SIZE (0..80))
			ACCESS read-write
			STATUS mandatory
			DESCRIPTION
				" SIP URI to be inserted as the TO address of an Invite send in response to the device going off-hook.
			ALCATEL-LUCENT NOTE:
			ACCESS:	NA
			USAGE:	OPT
			PERSIST:  	YES
			INSRVMOD: NO
			RANGE:	SIZE (0..80)
			DEFVALUE: 	null
			UNITS:	NA	
			SPARSE:	NO			
			"
		::= { sipTerminationEntry 5 }

		
		sipTerminationCallStatus OBJECT-TYPE
			SYNTAX INTEGER 
			{
				onhook(1),
				offhook(2),
				dialing(3),
				calling(4),
				connected(5),
				idleOffhook(6),
				busyTone(7),
				howlerTone(8),
				ringing(9),
				releasing(10),
				ringback(11),
                sharedCutoff(12)
			}
			ACCESS read-only
			STATUS mandatory
			DESCRIPTION
				"The status of call at this termination, The meaning of the status is list as following:
				onhook(1): hook on without any call
				offhook(2): hook off but user no dialing
				dialing(3): dial digit
				calling(4): send INVITE and wait response
				connected(5): call connect
				idleOffhook(6): parking
				busyTone(7): this status no used after R41
				howlerTone(8): this status no used after R41
				ringing(9): ring
				releasing(10): call have been terminated, but subscriber does not hook on, some tone maybe play in this 
						state, the line is in releasing state
				ringback(11): ringback tone to caller.
                sharedCutoff(12): term should be in cutoff status with following condition
                    Paired term is providing service (offhook, dialling, ringing, releasing, ringback), the other termination
                    will go to cutoff status and hear silence if hooks off it, and incoming call request for it will
                    be rejected
			ALCATEL-LUCENT NOTE:
			ACCESS:	NA
			USAGE:	NA
			PERSIST:  	NO
			INSRVMOD: NA
			RANGE:	1..11
			DEFVALUE: 	NA
			UNITS:	NA	
			SPARSE:	NO			
			"
		::= { sipTerminationEntry 6 }


		
--		sipTerminationStartLineTest OBJECT-TYPE
--			SYNTAX INTEGER
--				{
--				on(1),
--				off(2)
--				}
--			ACCESS read-write
--			STATUS mandatory
--			DESCRIPTION
--				" This parameter indicates the termination is in line-testing 
--				or not. This object is reserved for future use.
--
--				ALCATEL-LUCENT NOTE:
--					SUPPORT:  	YES
--					PERSIST:  	YES
--					INSRVMOD: 	YES
--					RANGE:	1 | 2
--					DEFVALUE: 	off(1)
--					UNITS:	NA	
			
--				"
--			DEFVAL { off }
--			::= { sipTerminationEntry 7 }

		
--		sipTerminationLineTestStatus OBJECT-TYPE
--			SYNTAX INTEGER
--			ACCESS read-only
--			STATUS mandatory
--			DESCRIPTION
--				" reserved for future usage, undefined yet
--
--				ALCATEL-LUCENT NOTE:
--					SUPPORT:  	NO
--					PERSIST:  	NO
--					INSRVMOD: 	NA
--					RANGE:	NA
--					DEFVALUE: 	NA
--					UNITS:	NA				
--				"
--			::= { sipTerminationEntry 8 }

			sipTerminationCharacteristic OBJECT-TYPE
				SYNTAX INTEGER
				ACCESS read-write
				STATUS mandatory
				DESCRIPTION
					"This parameter indicates the line feeding current.
					7302/7330 ISAM FTTN :
					NPOT-A (48p) : Up to 5 lines per LT board can be configured to work with enhanced feeding (40 mA). 
							There is no restriction wrt the line positioning on the board.
					NPOT-B (72p) : Up to 8 lines per LT board can be configured to work with enhanced feeding (40 mA). 
							There is no restriction wrt the line positioning on the board.
							NPOT-C (48p) : Up to 5 lines per LT board can be configured to work with enhanced feeding (40 mA). 
							There is no restriction wrt the line positioning on the board.
					7363 MX :
							RPOT-A (32p) : Up to 3 lines per LT board can be configured to work with enhanced feeding (40 mA). 
							There is no restriction wrt the line positioning on the board.
					7367 SX :
							SPOT-C (16p) : Up to 1 lines per LT board can be configured to work with enhanced feeding (40 mA). 
							There is no restriction wrt the line positioning on the board.
					ALCATEL-LUCENT NOTE:
					ACCESS:     NA
					USAGE:       OPT
					PERSIST:  	YES
					INSRVMOD: 	NO
					RANGE:	25 | 40
					DEFVALUE: 	25
					UNITS:	mA
					SPARSE:    NO				
			"
			::= { sipTerminationEntry 9 }

			sipTerminationMD5Realm OBJECT-TYPE
				SYNTAX OCTET STRING (SIZE (0..64))
				ACCESS read-write
				STATUS mandatory
				DESCRIPTION
					"The realm identifier that corresponds to the Service Gateway domain. 
				ALCATEL-LUCENT NOTE:
				ACCESS:	NA
				USAGE:	OPT
				PERSIST:  	YES
				INSRVMOD: NO
				RANGE:	SIZE (0..64)
				DEFVALUE: 	null
				UNITS:	NA		
				SPARSE:	NO		
				"
			::= { sipTerminationEntry 10 }

			sipTerminationMD5Password OBJECT-TYPE
				SYNTAX OCTET STRING (SIZE (0..64))
				ACCESS read-write
				STATUS mandatory
				DESCRIPTION
					"The password associated with the user 
					Not visible via CLI show command; returned as '******' string
					The content of the MIB is encrypted; the content of the DB is encrypted. 
					The encryption is basedon DES-CBC algorithm.
				ALCATEL-LUCENT NOTE:
				ACCESS:	NA
				USAGE:       OPT
				PERSIST:  	YES
				INSRVMOD: NO
				RANGE:	SIZE (0..64)
				DEFVALUE: 	null
				UNITS:	NA
				SPARSE:	NO				
				"
			::= { sipTerminationEntry 11 }

			sipTerminationAdminStatus OBJECT-TYPE
				SYNTAX INTEGER
				{
					up(1),
					down(2)
				}
				ACCESS read-write
				STATUS mandatory
				DESCRIPTION
					" The administrative status of this sip termination.
					When the administrative status of a SIP termination is modified from 'up' to 'down', then the system will
					de-register the SIP termination and power down the line.

                             		UP (1) : the attributes of this entry that are indicated as INSRVMOD=YES can be modified.
                             		DOWN (2) : the attributes of this entry that are indicated as INSRVMOD=YES and the attributes that are 
						indicated as INSRVMOD=NO can be modified.
						Note that the attributes of this entry that are indicated INSRVMOD=NA can not be modified after creation.

				ALCATEL-LUCENT NOTE:
				ACCESS:	NA
				USAGE:	OPT
				PERSIST:  	YES
				INSRVMOD: YES
				RANGE:	1 | 2
				DEFVALUE: 	down
				UNITS:	NA		
				SPARSE:	NO		
				"
			::= { sipTerminationEntry 12 }

			sipTerminationOperStatus OBJECT-TYPE
				SYNTAX INTEGER
				{
					up(1),
					down(2)
				}
				ACCESS read-only
				STATUS mandatory
				DESCRIPTION
					" The operational status of this sip termination. 
					up(1) :  The SIP Termination is up and able to make calls.
					down(2) : The SIP Termination is out of service.
				ALCATEL-LUCENT NOTE:
				ACCESS:	NA
				USAGE:	NA
				PERSIST:  	NO
				INSRVMOD: NA
				RANGE:	1 | 2
				DEFVALUE: 	NA
				UNITS:	NA	
				SPARSE:	NO					
				"
			::= { sipTerminationEntry 13 }

			sipTerminationRowStatus OBJECT-TYPE
				SYNTAX RowStatus
				ACCESS read-write
				STATUS mandatory
				DESCRIPTION
					"The status of this conceptual row.
					The RowStatus TC requires that this DESCRIPTION clause
					states under which circumstances other objects in this row
					can be modified.  The value of this object has no effect on
					whether other objects in this conceptual row can be
					modified.
					A conceptual row can always be made active.
				ALCATEL-LUCENT NOTE:
				ACCESS:	NA
				USAGE:	MAND
				PERSIST:  	NO
				INSRVMOD: YES
				RANGE:	1 | 4 | 6	-- active (1), createAndGo (4), destroy (6)
				DEFVALUE: 	NA
				UNITS:	NA
				SPARSE:	NO
         			"
			::= { sipTerminationEntry 14 }

			sipTerminationTestStatus OBJECT-TYPE
				SYNTAX INTEGER
				{
					noTesting(1),
					mtaTesting(2),
					intgLineTesting(3)
				}
				ACCESS read-only
				STATUS mandatory
				DESCRIPTION
					" The test status of this sip termination. 
					noTesting(1)	- The termination is not under testing.
					mtaTesting(2)	- The termination is under MTA testing.
					intgLineTesting(3) - The termination is under integrated line testing.
				ALCATEL-LUCENT NOTE:
				ACCESS:	NA
				USAGE:	NA
				PERSIST:  	NO
				INSRVMOD: NA
				RANGE:	1 | 2 | 3
				DEFVALUE: 	NA
				UNITS:	NA	
				SPARSE:	NO					
				"
			::= { sipTerminationEntry 15 }

			sipTermContactUserInfo OBJECT-TYPE
				SYNTAX OCTET STRING (SIZE (1..128))
				ACCESS read-only
				STATUS mandatory
				DESCRIPTION
					"The user-info of contact field in SIP message associated with the user 
					When the sipLineIdSyntaxPattern is configured as 'terminationUriOrDN (1)' and sipTerminationUri is NOT 
					empty, then this object contains the user part of sipTerminationUri as the user info; if sipTerminationUri
                    doesn't contain a '@', then this object contains the user part of sipTerminationDN as the user info.
					When the sipLineIdSyntaxPattern is configured as 'terminationUriOrDN (1)' and sipTerminationUri is  EMPTY, 
					then this object contains the user part of sipTerminationDN as the user info.
					When the sipLineIdSyntaxPattern is configured as 'PhysicalLineId (2)', then this object contains the physcial 
					lineId as the user info.
                    When the LT Board is not present Physically, then this object is empty.

				ALCATEL-LUCENT NOTE:
				ACCESS:	NA
				USAGE:	NA
				PERSIST:  	NO
				INSRVMOD: NA
				RANGE:	SIZE (1..128)
				DEFVALUE: 	NA
				UNITS:	NA	
				SPARSE:	NO			
				"
			::= { sipTerminationEntry 16 }

			sipTerminationAssocVSPId OBJECT-TYPE
				SYNTAX INTEGER
				ACCESS read-only
				STATUS deprecated
				DESCRIPTION
					"Identifier of the parent Service Gateway of this sip termination. 
                    Deprecated. Replaced by attribute sipTerminationProviderName.
				ALCATEL-LUCENT NOTE:
				ACCESS:	NA
				USAGE:	OPT
				PERSIST:  	YES
				INSRVMOD:  NA
				RANGE:	1 -Refer to sipVSPId
				DEFVALUE: 	1
				UNITS:	NA	
				SPARSE:	NO			
				"
			::= { sipTerminationEntry 17 }

			sipTerminationETSIClipDataMode OBJECT-TYPE
				SYNTAX INTEGER
				{
					cdevalue(1),
					fsk(2),
					dtmf(3)
				}
				ACCESS read-write
				STATUS mandatory
				DESCRIPTION
					" The ETSI clip data transmission protocol of this sip termination. 
					cdevalue(1)	- CDE configuration will be applied for ETSI CLIP.
					fsk(2)	- fsk will be applied for ETSI CLIP.
					dtmf(3) - dtmf will be applied for ETSI CLIP.
				ALCATEL-LUCENT NOTE:
				ACCESS:	NA
				USAGE:	OPT
				PERSIST:  	Yes
				INSRVMOD: NO
				RANGE:	1 | 2 | 3
				DEFVALUE: 	1
				UNITS:	NA	
				SPARSE:	NO
			"
			DEFVAL {cdevalue} 
			::= { sipTerminationEntry 18 }

            sipTerminationTelcordiaClipDataMode OBJECT-TYPE
                SYNTAX INTEGER
                {
                    cdevalue(1),
                    fsk(2)
                }
                ACCESS read-write
                STATUS mandatory
                DESCRIPTION
                    " The Telcordia clip data transmission protocol of this sip termination.
                    cdevalue(1) - CDE configuration will be applied for Telcordia CLIP.
                    fsk(2)  - fsk will be applied for Telcordia CLIP.
                ALCATEL-LUCENT NOTE:
                ACCESS: NA
                USAGE:  OPT
                PERSIST:    Yes
                INSRVMOD: NO
                RANGE:  1 | 2 
                DEFVALUE:   1
                UNITS:  NA  
                SPARSE: NO
            "
            DEFVAL {cdevalue} 
            ::= { sipTerminationEntry 19 }

			sipTerminationDisplayName OBJECT-TYPE
				SYNTAX OCTET STRING (SIZE (0..64))
				ACCESS read-write
				STATUS mandatory
				DESCRIPTION
					" Display name of this sip termination.
				ALCATEL-LUCENT NOTE:
				ACCESS:	NA
				USAGE:	OPT
				PERSIST:  	YES
				INSRVMOD: NO
				RANGE:	SIZE (0..64)
				DEFVALUE: 	null
				UNITS:	NA	
				SPARSE:	NO			
				"
			::= { sipTerminationEntry 20 }

			sipTerminationImpedance OBJECT-TYPE
				SYNTAX SipTerminationImpedance
				ACCESS read-write
				STATUS mandatory
				DESCRIPTION 
				"Impedance index (1-32), 1 means default value, 
                 only impedance values with a resistance value equal 
                 the pre-configured value in the CDE file can be chosen.

					1: default value. (default value of CDE profile)
					2: 200 Ohm+(680 Ohm//100nF)
					3: 220 Ohm+(820Ohm//120nF)
					4: 220 Ohm+(820 Ohm//120nF) miniSplitter
					5: 270 Ohm+(750 Ohm//150nF)
					6: 300 Ohm+(1000 Ohm//220nF)
					7: 370 Ohm+(620 Ohm//310nF)
					8: 600 Ohm
					9: 900 Ohm
					10: 370 Ohm+(620 Ohm//310nF) + Splitter
					11: 600 Ohm+ Splitter
					12: 370NVLSASplitter
					13: 370SkinnySplitter
					14: 270DuratelSplitter
					15: 2703MSplitter 
                    16: 100Ohm+(1650Ohm//5nF) 
                    17: 150Ohm+(510Ohm//47nF) 
                    18: 220Ohm+Splitter 
                    19: schmReserved19
                    20: schmReserved20
                    21: schmReserved21
                    22-32: schmReserved

				ALCATEL NOTE: 
				ACCESS:	READ-WRITE
				USAGE:	NA
				PERSIST:	YES
				INSRVMOD: NO
				RANGE:	(1..32)
				DEFVALUE:	1
				UNITS:	NA	
				SPARSE:	NO
				"
				DEFVAL {1}
			::= {sipTerminationEntry 21}
   
   			sipTerminationRxGain OBJECT-TYPE
				SYNTAX INTEGER(-14..6)
				ACCESS read-write
				STATUS mandatory
				DESCRIPTION 
					"The value of Line Receive Gain.
				ALCATEL NOTE: 
				ACCESS:	READ-WRITE
				USAGE:	NA
				PERSIST:	YES
				INSRVMOD: NO
				RANGE:	(-14..6)
				DEFVALUE:	0
				UNITS:	dB
				SPARSE:	NO
				"
				DEFVAL {0}
			::= {sipTerminationEntry 22}


    			sipTerminationAntiTapping OBJECT-TYPE
      				SYNTAX INTEGER
      				{
        			enable (1),
        			disable (2)
      				}
      				ACCESS read-write
      				STATUS mandatory
     				DESCRIPTION
        				"This parameter indicates anti-tapping action.
                        Enable anti-tapping will firstly validate and remove  a sequence of DTMF digits using a very specific 
                        timing,then normal dialing process.
                        Disable anti-tapping will use normal dialing process.

                        7302/7330 ISAM FTTN : This object only applies to SIP terminations connected to a NPOT-B/NPOT-C voice LT board.
                        A request to enable sipTerminationAntiTapping for a SIP termination connected to a NPOT-A voice LT board will be rejected.

        			ALCATEL-LUCENT NOTE:
          			ACCESS:     NA
         			USAGE:       OPT
          			PERSIST:        YES
          			INSRVMOD:       NO
          			RANGE:  enable(1) | disable(2)
          			DEFVALUE:       disable
          			UNITS:  NA
          			SPARSE:    NO
        			"
      			::= { sipTerminationEntry 23 }

			sipTerminationOpStatDownReason OBJECT-TYPE
				SYNTAX INTEGER
				{
					none(0),
					registering(1),
					registrationFailure(2),
					physicalFailure(3)
				}
				ACCESS read-only
				STATUS mandatory
				DESCRIPTION
					" The Oper status Down Reason of this sip termination. 
					none(0) : SIP Termination is operational
					registering(1) : The SIP Termination is registering.
					registrationFailure(2) : The SIP Termination registration has failed.
					physicalFailure(3) : The SIP Termination is out of service due to physical failure.
				ALCATEL-LUCENT NOTE:
				ACCESS:	NA
				USAGE:	NA
				PERSIST:  	NO
				INSRVMOD: NA
				RANGE:	0 |1 | 2 | 3
				DEFVALUE: 	NA
				UNITS:	NA	
				SPARSE:	NO					
				"
			::= { sipTerminationEntry 24 }

			sipTerminationTxGain OBJECT-TYPE
				SYNTAX INTEGER(-14..6)
				ACCESS read-write
				STATUS mandatory
				DESCRIPTION 
					"The value of Line Transmit Gain. 
				ALCATEL NOTE: 
				ACCESS:	READ-WRITE
				USAGE:	NA
				PERSIST:	YES
				INSRVMOD: NO
				RANGE:	(-14..6)
				DEFVALUE:   0
				UNITS:	dB
				SPARSE:	NO
				"
				DEFVAL {0}
			::= {sipTerminationEntry 25}

 			sipTermTestAccessState   OBJECT-TYPE
				SYNTAX    INTEGER
				{
					on (1),
					off (2)
				}
				ACCESS     read-write
				STATUS     mandatory
				DESCRIPTION 
					"The configured TestAccessState of a SIP termination.

                    ON (1) : The line of the SIP termination is exclusively reserved to run NBLT. Incoming and outgoing call attempts 
                    are blocked for this SIP termination for as long as the TestAccessState remains set to 'ON'.
                    OFF (2) : The line of the SIP termination can handle incoming and outgoing call attempts (On the condition that 
                    there is no other reason to block the SIP termination e.g. an ongoing NBLT) and can also handle NBLT requests.

                    The  actual administrative / operational / test status of the SIP termination does not have any influence on the 
                    setting of the TestAccessState, i.e. this object can be changed at any time from the moment the SIP termination has 
                    been created.
                                            
                    The receipt of a configuration command to switch the sipTermTestAccessState to 'ON(1)':

                    1. Only the MIB objects sipTermTestAccessBusyOverwrite and sipTermTestAccessTimeout can be included in the configuration 
                    command that intends to modify the sipTermTestAccessState to the value 'ON (1)'.

                    2. Should upon the receipt of the configuration command the sipTermTestAccessState value equals 'OFF (2)', then 
                    the sipTermTestAccessState is changed to 'ON (1)' and a timer with the default/configured value of 
                    sipTermTestAccessTimeout is started.
                                             
                    3. Should upon the receipt of the configuration command the sipTermTestAccessState value equals 'ON (1)', then the 
                    currently running sipTermTestAccessTimeout timer gets aborted and a new timer will be started with the default/newly 
                    configured  sipTermTestAccessTimeout timer.

                    4. Upon the expiry of the sipTermTestAccessTimeout timer, the sipTermTestAccessState value changes to 'OFF(2)'.
                                              
                    5. Should upon the expiry of the sipTermTestAccessTimeout timer, a NBLT test still be running, the 
                    sipTermTestAccessTimeout timer is re-started and the POTS NBLT test continues till completion. The sipTermTestAccessState 
                    remains set to 'ON' till the restarted timer expiry.

                    The receipt of a configuration command to switch the sipTermTestAccessState to 'OFF(2)':

                    1. No other MIB objects can be included in the configuration command that intends to modify the sipTermTestAccessState 
                    to the value 'OFF(2)'.

                    2. Should upon the receipt of the configuration command the sipTermTestAccessState value equals 'ON (1)' and no 
                    NBLT test being running then the sipTermTestAccessState is changed to 'OFF (2)' and the running timer gets aborted.

                    3. Should upon the receipt of the configuration command the sipTermTestAccessState value equals 'ON (1)' and a 
                    NBLT test still being running then the sipTermTestAccessState is changed to 'OFF (2)' and the running timer gets 
                    aborted. However, incoming and outgoing calls remain blocked till the running NBLT session has completed.

                    4. Should upon the receipt of the configuration command the sipTermTestAccessState value equals 'OFF (2)', then 
                    the configuration command is ignored.

                    The sipTermTestAccessState object is not persistent, which means that its value will be reset to the default value upon 
                    a board reset.

				ALCATEL-LUCENT NOTE:
				ACCESS:	RW
				USAGE:	OPT
				PERSIST:	NO
				INSRVMOD:  YES
				RANGE:	See above
				DEFVALUE:	off (2)
				UNITS:	NA
				SPARSE:	NO"
			::= {sipTerminationEntry 26} 

			sipTermTestAccessBusyOverwrite   OBJECT-TYPE
				SYNTAX    TruthValue
				ACCESS     read-write
				STATUS     mandatory
				DESCRIPTION 
					"This sipTermTestAccessBusyOverwrite object allows to forcibly turn on the sipTermTestAccessState of a SIP termination 
                    by dropping all active calls that are ongoing for that SIP termination at the moment the configuration command gets received.

                    1) Upon the receipt of a configuration command requesting the sipTermTestAccessState to be switched to 'ON (1)' and 
                    sipTermTestAccessBusyOverwrite set to 'TRUE (1)' : Should there still an active call be ongoing for this SIP termination, 
                    then this call is forcibly dropped and subsequently, the sipTermTestAccessState is switched to 'ON (1)'.

                    2) Upon the receipt of a configuration command requesting the sipTermTestAccessState to be switched to 'ON (1)' and 
                    sipTermTestAccessBusyOverwrite set to 'FALSE (2)' : Should there still an active call be ongoing for this SIP termination, 
                    then the request to switch on the sipTermTestAccessState gets rejected.

                    The sipTermTestAccessBusyOverwrite object can only be configured in the configuration command that intends to modify the 
                    sipTermTestAccessState to the value 'ON (1)'.

                    If not specified during the modification of the sipTermTestAccessState from 'OFF (2)' to 'ON(1)', the system assumes that 
                    the sipTermTestAccessBusyOverwrite object is set to the value 'False (2)' (which is the default value).

                    This object is not persistent, which means that its value will be reset to the default value upon a board reset. 
                          
                    When the sipTermTestAccessState value equals 'ON (1)', a read operation for the sipTermTestAccessBusyOverwrite object will 
                    result in the sipTermTestAccessBusyOverwrite value being returned that has been configured/adopted by the system during the 
                    last sipTermTestAccessState = 'ON(1)' modification request. 

                    Otherwise, should the sipTermTestAccessState value equals 'OFF (2)' a read operation for the sipTermTestAccessBusyOverwrite 
                    object will return the value 'FALSE(2)'.

				ALCATEL-LUCENT NOTE:
				ACCESS:	RW
				USAGE:	OPT
				PERSIST:	NO
				INSRVMOD: YES
				RANGE:       See above
				DEFVALUE:	false(2)
				UNITS:	NA
				SPARSE:	NO
				"
			::= {sipTerminationEntry 27} 

			sipTermTestAccessTimeout   OBJECT-TYPE
				SYNTAX    INTEGER
				ACCESS     read-write
				STATUS     mandatory
				DESCRIPTION 
					"This sipTermTestAccessTimeout object allows to configure the maximum elapse time that the sipTermTestAccessState 
                    object shall remain set to 'ON (1)'. 

                    Upon the expiry of the sipTermTestAccessTimeout timer, the system autonomously changes the sipTermTestAccessState 
                    value to 'OFF (2)'. 

                    1) Should upon the sipTermTestAccessTimeout timer expiry, still a NBLT session be running, then the 
                    sipTermTestAccessTimeout timer gets autonomously RESTARTED with the default/latest configured timer value. 
                    The sipTermTestAccessState remains set to 'ON(1)' till the restarted timer expiry. 

                    2) Should a NBLT session be completed prior to the sipTermTestAccessTimeout timer expiry, then the 
                    sipTermTestAccessTimeout timer gets autonomously RESTARTED with the default/latest configured timer value. 
                    The sipTermTestAccessState remains set to 'ON(1)' till the restarted timer expiry.

                    The sipTermTestAccessTimeout object can only be configured in the configuration command that intends to modify 
                    the sipTermTestAccessState to the value 'ON (1)'. 

                    The sipTermTestAccessTimeout object can be configured in the range [1.. 900] seconds. 
                    Should no configuration input be received for the sipTermTestAccessTimeout object, the default value (900 sec) 
                    gets assumed.

                    Upon the recipt of a configuration command to modify the sipTermTestAccessState to the value 'ON (1)' while the 
                    actual value of the sipTermTestAccessState equals 'ON (1)', then the current running sipTermTestAccessTimeout 
                    timer is aborted, and a new timer with the default /newly configured value for sipTermTestAccessTimeout is started.

                    This object is not persistent, which means that its value will be reset to the value '0' upon a board reset.

                    When the sipTermTestAccessState equals 'ON (1)', a read operation for the sipTermTestAccessTimeout object will 
                    return the time left before the sipTermTestAccessTimeout timer expires. 

                    When the sipTermTestAccessState equals 'OFF(2)', a read operation for the sipTermTestAccessTimeout object will 
                    return the value '0'.
				ALCATEL-LUCENT NOTE:
				ACCESS:	RW
				USAGE:	OPT
				PERSIST:	NO
				INSRVMOD: YES
				RANGE:       0-900
				DEFVALUE:  900
				UNITS:	Second
				SPARSE:	NO
				"
 			::= {sipTerminationEntry 28}

			sipTerminationWarmlineService OBJECT-TYPE
				SYNTAX INTEGER
				{ 
					disabled (1),
					activated (2), 
					subscribed (3)
				}  
				ACCESS read-write      
				STATUS mandatory       
 				DESCRIPTION 
					"This object specifies the value of the sipTerminationWarmlineService for this termination.
					Disabled(1) - When sipTerminationWarmLineService = disabled AND sipTerminationDirectConnectUri = null
					string, warmline service is controlled by SIP Service Profile. The SSP will tell whether this service is controlled
					by UA-Profile or the MIB disable value is applied (e.g. when the IMS core does not support the UA-profile
					approach).
					Activated(2) - warmline service is activated. Direct connect URI provisioned in sipTerminationDirectConnectUri
					is used for direct outgoing calls.
					Subscribed(3) - warmline service is subscribed and can be activated/deactivated by subscriber.
					Direct connect URI as dynamically provisioned by this termination is used for direct outgoing calls. 
				ALCATEL-LUCENT NOTE:
				ACCESS:	RW
				USAGE:	OPT     
				PERSIST:	YES
				INSRVMOD: NO
				RANGE: 	1|2|3
				DEFVALUE:   disabled (1)
				UNITS:	NA
				SPARSE:	NO
				"
			::= { sipTerminationEntry 29 }

			sipTerminationGroup OBJECT-TYPE
				SYNTAX INTEGER
				ACCESS read-only
				STATUS mandatory
				DESCRIPTION  
					"The SIP Termination Group this SIP termination actually belongs to.
					- Should the SIP Restoration feature be enabled then this object may be set to a value in the range 0..72
					whereby a value 0 means that the SIP termination has not been assigned yet to a SIP Termination Group.
					(not successfully registered yet)
					- Should the SIP Restoration feature be disabled then this object shall be set to the value 0 whereby a value 0
					means that the SIP termination Group approach doesn't apply.
				ALCATEL-LUCENT NOTE:
				ACCESS:	NA
				USAGE:	NA
				PERSIST:	NO
				INSRVMOD: NA
				RANGE:	0...72
				DEFVALUE:	NA
				UNITS:	NA
				SPARSE:	NO
				"
			::= { sipTerminationEntry 30 }

			sipTerminationSIPServerAddr OBJECT-TYPE
				SYNTAX InetAddress
				ACCESS read-only
				STATUS mandatory
				DESCRIPTION  
					"This object returns either the IP@ or the FQDN of the First Hop SIP server currently in use by the SIP
					Termination.
					Whether an IP@ or FQDN is going to be displayed depends on the mode been applied to configure the SIP
					Server Table.
					In case the IP@ mode is applied then an IP@ is going to be displayed. Otherwise, in case the DN / FQDN
					mode is applied then an FQDN is going to be displayed.
					An FQDN being displayed has only relevance and can only uniquely define a SIP First Hop server on the
					condition that the Domain Name Service being deployed in the customer's network offers a 1:1 mapping
					between FQDN and A Resource Record : should the DN / FQDN mode been applied to configure the SIP
					Server Table and should the Domain Name Service being deployed in the customer's network offer a 1:N
					mapping between FQDN and A Resource Record, then this object will return an FQDN value. However, due
					to the 1:N mapping between FQDN and A resource Record, this FQDN value will not uniquely identify the SIP
					First Hop server actually being in use by a SIP termination.

					1) SIP restoration disabled
					==> this object shall contain the SIP first hop address / FQDN to which all originating SIP requests are 
					addressed.
					==> this SIP first hop address / FQDN is filled in from the moment the SIP termination is successfully
					registered, otherwise no  value is shown

					2) SIP restoration enabled
					==> this object shall contain the SIP first hop address / FQDN to which all originating SIP requests are
					addressed.
					==> this SIP first hop address / FQDN is filled in from the moment the SIP termination is successfully
					registered i.e. belongs  to a SIP termination group, otherwise no value is shown.
				ALCATEL-LUCENT NOTE:
				ACCESS:	READ-ONLY
				USAGE:	NA
				PERSIST:	NO
				INSRVMOD:	NA
				RANGE:	NA
				DEFVALUE:	NA
				UNITS:	NA
				SPARSE:	NO
				"
			::= { sipTerminationEntry 31 }

			sipTerminationEnableCallWaiting OBJECT-TYPE
				SYNTAX INTEGER
				{ 
					disable (1),
					enable (2),
					subscribe (3)
				}  
				ACCESS read-write      
				STATUS mandatory       
				DESCRIPTION 
					"This object allows to configure the Call Waiting properties for this SIP termination.
					Disable(1) - call waiting service is controlled by SIP Service Profile. The SSP will tell whether this service is
					controlled by UA-Profile or the MIB disable value is applied (e.g. when the IMS core does not support the 
					UA-profile approach).
					Enable(2) - call waiting service is enabled.
					Subscribe(3) - call waiting service is subscribed and can be enabled/disabled by subscriber.
                    The configuration options Disable(1) and Enable(2) were supported in SW from ISR4.5.01 onwards.
                    The configuration option Subscribe(3) is supported from ISR5.2 onwards.
				ALCATEL-LUCENT NOTE:
				ACCESS:	READ-WRITE
				USAGE:	OPT     
				PERSIST:	YES
				INSRVMOD:	NO
				RANGE:	1|2|3
				DEFVALUE:	disable (1)
				UNITS:	NA
				SPARSE:	NO
				"
			::= { sipTerminationEntry 32 }

			sipTerminationEnableCallHold OBJECT-TYPE
				SYNTAX INTEGER
				{ 
					disable (1),
					enable (2),
					subscribe (3)
				}  
				ACCESS read-write      
				STATUS mandatory       
				DESCRIPTION 
					"This object allows to configure Call Hold properties for this termination.
					Disable(1) - call hold service is controlled by SIP Service Profile. The SSP will tell whether this service is
						controlled by UA-Profile or the MIB disable value is applied (e.g. when the IMS core does not support the 
						UA-profile approach).
					Enable(2) - call hold service is enabled.
					Subscribe(3) - call hold service is subscribed and can be enabled/disabled by subscriber. (This option is actually NOT supported)
				ALCATEL-LUCENT NOTE:
				ACCESS:	READ-WRITE
				USAGE:	OPT     
				PERSIST:	YES
				INSRVMOD:	NO
				RANGE:	1|2
				DEFVALUE:	disable (1)
				UNITS:	NA
				SPARSE:	NO
				"
			::= { sipTerminationEntry 33 }

			sipTerminationEnableCallConference OBJECT-TYPE
				SYNTAX INTEGER
				{ 
					disable (1),
					enable (2),
					subscribe (3)
				}  
				ACCESS read-write      
				STATUS mandatory       
				DESCRIPTION 
					"This object allows to configure Call Conference properties for this termination.
					Disable(1) - call conference service is controlled by SIP Service Profile. The SSP will tell whether this service is
						controlled by UA-Profile or the MIB disable value is applied (e.g. when the IMS core does not support the 
						UA-profile approach).
					Enable(2) - call conference service is enabled.
					Subscribe(3) - call conference service is subscribed and can be enabled/disabled by subscriber. (This option is actually NOT supported)
		 		ALCATEL-LUCENT NOTE:
				ACCESS:	READ-WRITE
				USAGE:	OPT     
				PERSIST:	YES
				INSRVMOD:	NO
				RANGE:	1|2
				DEFVALUE:	disable (1)
				UNITS:	NA
				SPARSE:	NO
			"
			::= { sipTerminationEntry 34 }

			sipTerminationEnableCallTransfer OBJECT-TYPE
				SYNTAX INTEGER
				{ 
					disable (1),
					enable (2),
					subscribe (3)
				}  
				ACCESS read-write      
				STATUS mandatory       
				DESCRIPTION 
					"This object allow sto configure Call Transfer properties for this termination.
					Disable(1) - call transfer service is controlled by SIP Service Profile. The SSP will tell whether this service is
						controlled by UA-Profile or the MIB disable value is applied (e.g. when the IMS core does not support the
						UA-profile approach).
					Enable(2) - call transfer service is enabled.
					Subscribe(3) - call transfer service is subscribed and can be enabled/disabled by subscriber. (This option is actually NOT supported) 
				ALCATEL-LUCENT NOTE:
				ACCESS:	READ-WRITE
				USAGE:	OPT     
				PERSIST:	YES
				INSRVMOD:	NO
				RANGE:	1|2
				DEFVALUE:	disable (1)
				UNITS:	NA
				SPARSE:	NO
			"
			::= { sipTerminationEntry 35 }

			sipTerminationEnableForceHold OBJECT-TYPE
				SYNTAX INTEGER
				{ 
					disable (1),
					enable (2)
				}  
				ACCESS read-write      
				STATUS mandatory       
				DESCRIPTION 
					"This object allow sto configure the Force Hold properties for this termination.
					If an outgoing call is an emergency call, if caller on hook, it should be in force hold state until force hold
					timer timeout which is hard coded as 45 minutes  or callee terminate the call, it is for both basic call and
					supplementary service.
				Disable(1) - call process is normal
				Enable(2) - force hold state is active.
				ALCATEL-LUCENT NOTE:
				ACCESS:	READ-WRITE
				USAGE:	OPT     
				PERSIST:	YES
				INSRVMOD:	NO
				RANGE:	1|2
				DEFVALUE:	disable (1)
				UNITS:	NA
				SPARSE:	NO
				"
			::= { sipTerminationEntry 36}

			sipTerminationLineSignalOnRemoteAnswer OBJECT-TYPE
			   	SYNTAX INTEGER
					{
					noSignal (1),
					lineReversal (2),
					singleMeteringPulse (3)
					}  
				ACCESS read-write      
				STATUS mandatory       
				DESCRIPTION 
					"This object specifies the value of the sipTerminationLineSignalOnRemoteAnswer for this termination.
					The MIB object is actually used to define what kind of line signal shall be applied to the line on receipt of 200
					OK INVITE. It is for basic call only.
					In case the line polarity becomes reversed upon the receipt of the 200 OK INVITE, that then the line polarity
					reversal remains kept till the call has completed.
					in case a single metering pulse is sent upon the receipt of the 200 OK INVITE, that the metring pulse
					characteristics are inherited from the CDE profile provisioning.
					noSignal(1) - do not send any signal to termination on receipt of 200 OK INVITE.
					lineReversal(2) - reverse line polarity on receipt of 200 OK INVITE.
					SingleMeteringPulse(3) - send single metering pulse to termination on receipt of 200 OK INVITE.
					ALCATEL-LUCENT NOTE:
					ACCESS:	READ-WRITE
					USAGE:	OPT     
					PERSIST:	YES
					INSRVMOD:	NO
					RANGE:	1|2|3
					DEFVALUE:	noSignal (1)
					UNITS:	NA
					SPARSE:	NO
			"
			::= { sipTerminationEntry 37}

			sipTerminationLineId OBJECT-TYPE
				SYNTAX OCTET STRING (SIZE (0..63))
				ACCESS read-write
				STATUS mandatory
				DESCRIPTION
					" Line ID of this sip termination.
					The line id configuration is not bounded to any format. It is the resonsibility of the customer to define the
					desired line ID format.
					There is no restriction on the character set being used to configure the line ID / line ID format.
			
					ALCATEL-LUCENT NOTE:
					ACCESS:	READ-WRITE
			                USAGE:	OPT
			                PERSIST:	YES
			                INSRVMOD:	NO
			                RANGE:	SIZE (0..63)
			                DEFVALUE:	null
			                UNITS:	NA
			                SPARSE:	NO
				"
			::= { sipTerminationEntry 38 }


            sipTerminationProviderName OBJECT-TYPE
                SYNTAX OCTET STRING (SIZE (0..32))
                ACCESS read-write
                STATUS mandatory
                DESCRIPTION
                    "The name of the parent Service Gateway.

                     ALCATEL NOTE:
                     ACCESS:read_write
                     USAGE: NA              
                     PERSIST:       YES
                     INSRVMOD: NO
                     RANGE: SIZE (0..32)
                     DEFVALUE:      vsp1
                     UNITS: NA      
                     SPARSE:        NO"
            ::= { sipTerminationEntry 39 }


-- =============================================================================
-- The Sip Sever - UserAgent Association Table
-- =============================================================================
--		sipServerUserAgentAssociationTable OBJECT-TYPE
--			SYNTAX SEQUENCE OF SipServerUserAgentAssociationEntry
--			ACCESS not-accessible
--			STATUS mandatory
--			DESCRIPTION
--				"This read-only table contains the sip 
--				server - sip ua associations, it is 
--				sorted per server"
--			::= { sipMIB 12 }

		
--		sipServerUserAgentAssociationEntry OBJECT-TYPE
--			SYNTAX SipServerUserAgentAssociationEntry
--			ACCESS not-accessible
--			STATUS mandatory
--			DESCRIPTION
--				"Each entry contains one sip server -
--				sip ua  association."
--			INDEX { sipServerId, sipServerAssocUserAgentId }
--			::= { sipServerUserAgentAssociationTable 1 }

		
--		SipServerUserAgentAssociationEntry ::=
--			SEQUENCE { 
--				sipServerAssocUserAgentId
--					INTEGER
--			 }

--		sipServerAssocUserAgentId OBJECT-TYPE
--			SYNTAX INTEGER (1..255)
--			ACCESS read-only
--			STATUS mandatory
--			DESCRIPTION
--				"Unique identifier of the sip ua which
--				is associated with the sip applciation server.

--				ALCATEL-LUCENT NOTE:
--					SUPPORT:  	YES
--					PERSIST:  	NO
--					INSRVMOD: 	NA
--					RANGE:	(1..255)
--					DEFVALUE: 	NA
--					UNITS:	NA								
--				"
--			::= { sipServerUserAgentAssociationEntry 1 }

		
-- =============================================================================
-- The Sip Dial Plan - UserAgent Association Table
-- =============================================================================
--		sipDialPlanUserAgentAssociationTable OBJECT-TYPE
--			SYNTAX SEQUENCE OF SipDialPlanUserAgentAssociationEntry
--			ACCESS not-accessible
--			STATUS mandatory
--			DESCRIPTION
--				"This read-only table contains the sip dial plan -
--				sip ua associations, it is sorted per
--				dial plan"
--			::= { sipMIB 13 }

		
--		sipDialPlanUserAgentAssociationEntry OBJECT-TYPE
--			SYNTAX SipDialPlanUserAgentAssociationEntry
--			ACCESS not-accessible
--			STATUS mandatory
--			DESCRIPTION
--				"Each entry contains one sip dial plan -
--				sip ua association."
--			INDEX { sipDialPlanId, sipDialPlanAssocUserAgentId }
--			::= { sipDialPlanUserAgentAssociationTable 1 }

		
--		SipDialPlanUserAgentAssociationEntry ::=
--			SEQUENCE { 
--				sipDialPlanAssocUserAgentId
--					INTEGER
--			 }

--		sipDialPlanAssocUserAgentId OBJECT-TYPE
--			SYNTAX INTEGER (1..255)
--			ACCESS read-only
--			STATUS mandatory
--			DESCRIPTION
--				"Unique identifier of the sip ua which
--				is associated with the sip dial plan.

--				ALCATEL-LUCENT NOTE:
--					SUPPORT:  	YES
--					PERSIST:  	NO
--					INSRVMOD: 	NA
--					RANGE:	(1..255)
--					DEFVALUE: 	NA
--					UNITS:	NA				
--				"
--			::= { sipDialPlanUserAgentAssociationEntry 1 }

		
-- =============================================================================
-- The Sip UserAgent - Sip Termination Association Table
-- =============================================================================
--		sipUserAgentTerminationAssociationTable OBJECT-TYPE
--			SYNTAX SEQUENCE OF SipUserAgentTerminationAssociationEntry
--			ACCESS not-accessible
--			STATUS mandatory
--			DESCRIPTION
--				"This read-only table contains the sip ua 
--				sip termination associations, it is sorted per dial plan"
--			::= { sipMIB 14 }

		
--		sipUserAgentTerminationAssociationEntry OBJECT-TYPE
--			SYNTAX SipUserAgentTerminationAssociationEntry
--			ACCESS not-accessible
--			STATUS mandatory
--			DESCRIPTION
--				"Each entry contains one sip ua -
--				sip termination association."
--			INDEX { sipUserAgentId, sipUserAgentAssocTerminationIfIndex }
--			::= { sipUserAgentTerminationAssociationTable 1 }

		
--		SipUserAgentTerminationAssociationEntry ::=
--			SEQUENCE { 
--				sipUserAgentAssocTerminationIfIndex InterfaceIndex
--			 }

--		sipUserAgentAssocTerminationIfIndex OBJECT-TYPE
--			SYNTAX InterfaceIndex
--			ACCESS read-only
--			STATUS mandatory
--			DESCRIPTION
--				"Unique identifier of the sip termination which
--				is associated with the sip ua

--				ALCATEL-LUCENT NOTE:
--					SUPPORT:  	YES
--					PERSIST:  	NO
--					INSRVMOD: 	NA
--					RANGE:	See Above
--					DEFVALUE: 	NA
--					UNITS:	NA				
--				"
--			::= { sipUserAgentTerminationAssociationEntry 1 }

		
-- =============================================================================
-- Sip System Objects Group Definition
-- =============================================================================
                 	sipSystemObjectsGroup OBJECT IDENTIFIER ::= { sipMIB 15 }	
		
		
-- =============================================================================
-- value of configuration if Session Timer is supported
-- =============================================================================

	
-- =============================================================================
-- 
-- Sip System Objects Table
--=============================================================================
		sipSysObjectsTable OBJECT-TYPE
			SYNTAX SEQUENCE OF SipSysObjectsEntry
			ACCESS not-accessible
			STATUS mandatory
			DESCRIPTION
                "The MIB table allowing to configure the SIP Sesstion Timer. 
                A single MIB table entry is auto-created at system start-up.
                Only 1 entry is created in this table. This single MIB table entry is common to all Service Gateways created and activated in the access node.

                7302/7330 ISAM FTTN : Supported
                7363 MX : Supported
		7367 SX : Supported

				ALCATEL NOTE: 
				TABLESIZE:  1
				DESCR:      NA"
			::= { sipSystemObjectsGroup 1 }

		sipSysObjectsEntry OBJECT-TYPE
			SYNTAX SipSysObjectsEntry
			ACCESS not-accessible
			STATUS mandatory
			DESCRIPTION
				"An entry in the sipSysObjectsTable."
			INDEX { sipSysObjectsIndex }
		::= { sipSysObjectsTable 1 }

		SipSysObjectsEntry ::=
			SEQUENCE { 
			sipSysObjectsIndex 			INTEGER,
			sipSysSessionTimerAdminState		INTEGER,					
			sipSysDefaultMinSE			INTEGER,	
			sipSysDefaultSessionExpires		INTEGER,
			sipSysObjectsAdminStatus		INTEGER
			}

		sipSysObjectsIndex OBJECT-TYPE
			SYNTAX INTEGER 
			ACCESS not-accessible
			STATUS mandatory
			DESCRIPTION
				" Unique internal identifier of this system object.
                ALCATEL-LUCENT NOTE:
				ACCESS:	NOT-ACCESSIBLE
				USAGE:	NA
				PERSIST:  	YES
				INSRVMOD:	NA
				RANGE:	(1..1)
				DEFVALUE: 	1
				UNITS:	NA	
				SPARSE:	NO			
				"
			::= { sipSysObjectsEntry 1 }

			sipSysSessionTimerAdminState OBJECT-TYPE
				SYNTAX INTEGER
					{
					enable (1),
					disable (2),
					enableAsUas(3)
					}		
				ACCESS read-write
				STATUS mandatory
				DESCRIPTION
					" The following SIP Session Timer behaviour is supported :
                    - Enable (1) : session expiration is requested in initial INVITE requests and 200 OK responses, and (In both cases) if an incoming initial INVITE request contains a session expiration header, but does not include the refresher value, then shall  use uac for the refresher parameter.
                    - Disable (2) : session expiration is not requested in initial INVITE requests and 200 OK responses 
                    - EnableAsUas (3) : session expiration shall be requested in initial INVITE request and 200 OK response.
                    And (in both cases) if an incoming initial INVITE request contains a session expiration header, but does not include the refresher value, then shall use uas for the refresher parameter.

					ALCATEL-LUCENT NOTE:
					ACCESS:	READ-WRITE
					USAGE:	OPT
					PERSIST:	YES
					INSRVMOD:	NO
					RANGE:	enable (1) | disable (2) | enableAsUas(3)
					DEFVALUE: 	disable (2)
					UNITS:	NA	
					SPARSE:	NO			
				"
			::= { sipSysObjectsEntry 2 }

			sipSysDefaultMinSE OBJECT-TYPE
				SYNTAX INTEGER (90..65535)
				ACCESS read-write
				STATUS mandatory
				DESCRIPTION
					"Value of Min-SE.			
					ALCATEL-LUCENT NOTE:
					ACCESS:	READ_WRITE
					USAGE:	OPT 
					PERSIST:  	YES
					INSRVMOD: NO
					RANGE:	(90..65535)
					DEFVALUE:	90
					UNITS:	Second
					SPARSE:	NO
						"
			::= { sipSysObjectsEntry 3 }	

			sipSysDefaultSessionExpires OBJECT-TYPE
				SYNTAX INTEGER (90..65535)
				ACCESS read-write
				STATUS mandatory
				DESCRIPTION
						"Value of Session-Expires.          
                        It must be equal or greater than sipSysDefaultMinSE value.

					ALCATEL-LUCENT NOTE:
					ACCESS:	READ-WRITE
					USAGE:	OPT
					PERSIST:  	YES
					INSRVMOD: NO
					RANGE:	(90..65535)
					DEFVALUE:  1800
					UNITS:	Second
					SPARSE:	NO
						"
				::= { sipSysObjectsEntry 4 }

			sipSysObjectsAdminStatus OBJECT-TYPE
				SYNTAX INTEGER
					{
					up(1),
					down(2)
					}
				ACCESS read-write
				STATUS mandatory
				DESCRIPTION
						" The administrative status of this sipSysObjects.
						UP (1) : the attributes of this entry that are indicated as INSRVMOD=YES can be modified.
						DOWN (2) : the attributes of this entry that are indicated as INSRVMOD=YES and the attributes that are
						indicated as INSRVMOD=NO can be modified.
						Note that the attributes of the same entry that are indicated INSRVMOD=NA can not be modified after
						creation.
			
				ALCATEL-LUCENT NOTE:
				ACCESS:	READ-WRITE
				USAGE:	OPT
				PERSIST:  	YES
				INSRVMOD: YES
				RANGE:	1 | 2
				DEFVALUE: 	down(2)
				UNITS:	NA	
				SPARSE:	NO			
				"
			::= { sipSysObjectsEntry 5 }

-- =============================================================================
-- Sip Voice Service Provider Table
-- =============================================================================
			sipVSPTable OBJECT-TYPE
				SYNTAX SEQUENCE OF SipVSPEntry
				ACCESS not-accessible
				STATUS mandatory
				DESCRIPTION
                "The MIB table allowing to configure the Service Gateway.
                The MIB table may contain a single entry (This is called the single Service Gateway approach and the Service Gateway entry is autonomously created by the System) or multiple Service Gateway entries ( This is called the multiple Service Gateway approach and the sipVSPTable contains a Service Gateway entry autonomously created by the system together with 1 or multiple Service Gateway entries manually created by the operator).
                The multiple Service Gateway concepts supports :
                - The multiple Voice Service Provider concept  : to support wholesale in a customer's network i.e.
                multiple voice service providers are connected to the same access network offering their voice service to the voice subscribers.
                - The multiple Virtual Access Gateway concept : to allow the customer to increase gradually the voice service capacity of its voice network by gradually installing additional access gateways (SIP servers) offering the voice service to the new voice service subscriptions. This must be entirely considered in the
  scope of a single voice service provider connected to the access network.
                In any case, upon system start-up, the system autonomously creates a sipVSPTable entry with sipVSPName = vsp1 and admin status = locked.
                The content of this entry (except the sipVSPName) can afterwards be modified by the operator.
                However, this autonomously created entry cannot be deleted by the operator.
                In addition to this autonomously created entry, up to 16 sipVSPTable entries can be manually created by the operator. (Thus the sipVSPTable can contain up to 17 entries)
                However, only maximum 16 service gateways entries can be simultaneously active (admin state = UP).

                The association between a sipVSPTable entry and its related data configured in an entry in the other MIB tables is to be made by means of the name configured in the sipVSPName.
                sipVSPTable.sipVSPName maps to :
                    ->sipUserAgentTable.sipUserAgentProviderName
                    ->sipTerminationTable.sipTerminationProviderName
                    ->sipDialPlanTable.sipDialPlanProviderName
                    ->sipServerTable.sipServerAdminDomName
                    ->sipDNSServerAdminDomName
                    ->sipTransportTable.sipTransportProviderName
                    ->sipRegisterTable.sipRegisterProviderName
                    ->netwRedunTable.netwRedunAdminDomName
                    ->netwRedunStateNewTable.netwRedunNewStateAdminDomName
                    ->sipRedunCommandTable.sipRedunCommandAdminDomName
                                  
                    7302/7330 ISAM FTTN : Supported
                    7363 MX : Supported
                    7367 SX : Supported, with the restriction that all Service Gateways must share the same VLAN ID and the same SIP Service Profile (single SIP Service Profile per access node)

			
				ALCATEL NOTE: 
				TABLESIZE:  17
				DESCR:      NA 
				"
			::= { sipMIB 16}

			sipVSPEntry OBJECT-TYPE
				SYNTAX SipVSPEntry
				ACCESS not-accessible
				STATUS mandatory
				DESCRIPTION
					"An entry in the sipVSPTable."
				INDEX { sipVSPId }
			::= { sipVSPTable 1 }

			SipVSPEntry ::=
				SEQUENCE { 
					sipVSPId					INTEGER,
					sipVSPName					OCTET STRING,
					sipVSPRowStatus				RowStatus,
					sipVSPAdminStatus			INTEGER,
					sipVSPDomainName			OCTET STRING,
					sipVSPTinfo				INTEGER,
					sipVSPTa4				INTEGER,
					sipVSPTtir1				INTEGER,
					sipVSPDigitSendingMode			INTEGER,
		--			sipVSPTransProto			INTEGER,	
					sipVSPTAcmDelta 			INTEGER,
					sipVSPAccessHeldTimer			INTEGER,
					sipVSPAwaitingTimer			INTEGER,
		--			sipVSPDnsPurgeTimer			INTEGER,
					sipVSPOverlap484Action			INTEGER,
					sipVSPDMPMIntDgtExpid			INTEGER,
					sipVSPDialingStartTimer			INTEGER,
					sipVSPDialingLongTimer			INTEGER,
					sipVSPDialingShortTimer			INTEGER,
					sipVSPURIType				INTEGER,
		--			sipVSPRegInterTimerAntiAlavanche	INTEGER,
					sipVSPRfc2833PayloadType		INTEGER,
					sipVSPRfc2833Processing			INTEGER,
					sipVSPMinDataJitterBuffer		INTEGER,
					sipVSPInitDataJitterBuffer		INTEGER,
					sipVSPMaxDataJitterBuffer		INTEGER,
					sipVSPReleaseMode			INTEGER, 
					sipVSPDynamicPTNegoType			INTEGER,
					sipVSPVbdG711APayloadType		INTEGER,
					sipVSPVbdG711UPayloadType		INTEGER,
					sipVSPVbdMode				INTEGER,
					sipVSPWarmlineDelayTimer		INTEGER,
					sipVSPDHCPOption82			INTEGER,
					sipVSPEnableRegisterSubscribe		INTEGER,
					sipVSPSubscribePeriod			INTEGER,
					sipVSPSubscribeHeadStart			INTEGER,
					sipVSPT38withSameUDP			INTEGER,
                    sipVSPSSPProfileName            OCTET STRING,
					sipVSPDtmfSipInfo               INTEGER
					}

			sipVSPId OBJECT-TYPE
				SYNTAX INTEGER 
				ACCESS not-accessible
				STATUS mandatory
				DESCRIPTION
					"The unique internal identifier of a Service Gateway. 
					ALCATEL-LUCENT NOTE:
					ACCESS:	NOT-ACCESSIBLE
					USAGE:	MANDATORY
					PERSIST:	YES
					INSRVMOD:	NA
					RANGE:	(1..17)
					DEFVALUE:	NA
					UNITS:	NA
					SPARSE:	NO
					"
				::= { sipVSPEntry 1 }

			sipVSPName OBJECT-TYPE
				SYNTAX OCTET STRING (SIZE (0..32))
				ACCESS read-write
				STATUS mandatory
				DESCRIPTION
					"The administrative domain name of a Service Gateway.
                    This name must be unique across all configured entries of the sipVSPTable.
                    As this name attribute is used as a link to other objects, this name attribute cannot be modified once the entry 
                    has been created.

					ALCATEL-LUCENT NOTE:
					ACCESS:	READ-WRITE
					USAGE:	NA
					PERSIST:  	YES
					INSRVMOD: NA
					RANGE:	SIZE (0..32)
					DEFVALUE:   vsp1
					UNITS:	NA	
					SPARSE:	NO			
					"
				::= { sipVSPEntry 2 }

			sipVSPRowStatus OBJECT-TYPE
				SYNTAX RowStatus
				ACCESS read-write
				STATUS mandatory
				DESCRIPTION
						"The status of this conceptual row.
						The RowStatus TC requires that this DESCRIPTION clause
						states under which circumstances other objects in this row
						can be modified.  The value of this object has no effect on
						whether other objects in this conceptual row can be
						modified.
						A conceptual row can always be made active.
					ALCATEL-LUCENT NOTE:
					ACCESS:	READ-WRITE
					USAGE:	MAND
					PERSIST:  NO
					INSRVMOD: YES
					RANGE:	1 | 4 | 6       -- active (1), createAndGo (4), destroy (6)
					DEFVALUE: 	NA
					UNITS:	NA
					SPARSE:	NO
			         			"
				::= { sipVSPEntry 3 }

			sipVSPAdminStatus OBJECT-TYPE
				SYNTAX INTEGER
					{
					up(1),
					down(2)
					}
				ACCESS read-write
				STATUS mandatory
				DESCRIPTION
						"The administrative status of a Service Gateway.
                        When the administrative status of a Service Gateway entry is modified from 'up' to 'down', then following actions are taken by the system (at all voice LT boards) :
			 			Active calls are immediately aborted;
			 			SIP terminations are de-registered;
			 			The operational status of the SIP terminations is modified to 'down'.
			 			The physcial-lines of the SIP terminations are powered down.
			
						UP (1) : the attributes of this entry that are indicated as INSRVMOD=YES can be modified.
						DOWN (2) : the attributes of this entry that are indicated as INSRVMOD=YES and the attributes that are 
								indicated as INSRVMOD=NO can be modified.
						Note that the attributes of the same entry that are indicated INSRVMOD=NA can not be modified after
						creation.
				ALCATEL-LUCENT NOTE:
				ACCESS:	READ-WRITE
				USAGE:	OPT
				PERSIST:  	YES
				INSRVMOD:	YES
				RANGE:	1 | 2
				DEFVALUE: 	down
				UNITS:	NA	
				SPARSE:	NO			
				"
			::= { sipVSPEntry 4 }

			sipVSPDomainName OBJECT-TYPE
				SYNTAX OCTET STRING (SIZE (1..64))
				ACCESS read-write
				STATUS mandatory
				DESCRIPTION
                " The SIP Domain Name of a Service Gateway. 
					ALCATEL-LUCENT NOTE:
					ACCESS:	READ-WRITE
					USAGE:	MAND
					PERSIST:  	YES
					INSRVMOD: NO
					RANGE:	SIZE (1..64)
					DEFVALUE: NA	
					UNITS:	NA	
					SPARSE:	NO							
						"
				::= { sipVSPEntry 5 }

			sipVSPTinfo OBJECT-TYPE
				SYNTAX INTEGER (1..3600000)
				ACCESS read-write
				STATUS mandatory
				DESCRIPTION
						"The timer to collect digits before an INVITE is sent. This to reduce the amount of INVITE requests sent (as
						defined in ETSI TS 183 036 V0.10.1).
					ALCATEL-LUCENT NOTE:
					ACCESS:	READ-WRITE
					USAGE:	OPT
					PERSIST:	YES
					INSRVMOD:	NO 
					RANGE:	(1..3600000)
					DEFVALUE:	1000
					UNITS:	milli-Second
					SPARSE:	NO
						"
			::= { sipVSPEntry 6 }

			sipVSPTtir1 OBJECT-TYPE
				SYNTAX INTEGER (1..3600000)
				ACCESS read-write
				STATUS mandatory
				DESCRIPTION
						"In the case 'from-change' is indicated, SIP UA has to wait for an UPDATE, the timer assures  that the call can
						continue if the UPDATE is missing (as defined in ETSI TS 183 036 V0.10.1)
					ALCATEL-LUCENT NOTE:
					ACCESS:	READ-WRITE
					USAGE:	OPT
					PERSIST:  	YES
					INSRVMOD: NO
					RANGE:	(0..3600000)
					DEFVALUE: 	100
					UNITS:	milli-Second
					SPARSE:	NO
						"
				::= { sipVSPEntry 7 }	

			sipVSPDigitSendingMode OBJECT-TYPE
				SYNTAX INTEGER
					{
					en-bloc(1),
					overlap-invite(2),
					overlap-indialog(3)
					}
				ACCESS read-write
				STATUS mandatory
				DESCRIPTION
						" The digit sending mode
					ALCATEL-LUCENT NOTE:
					ACCESS:	READ-WRITE
					USAGE:	OPT 
					PERSIST:	YES
					INSRVMOD: NO
					RANGE:	1 | 2 | 3
					DEFVALUE:	en-bloc
					UNITS:	NA
					SPARSE:	NO
						"
				::= { sipVSPEntry 8 }

	

--		sipVSPTransProto OBJECT-TYPE
--		  SYNTAX INTEGER (1..4294967295)
--                       ACCESS read-write
--                       STATUS mandatory
--                       DESCRIPTION
--                            " The transport protocol  bitmap of the sip server.
--				Bit 0: a protocol other than those defined here
--                         	Bit 1: User Datagram Protocol
--                         	Bit 2: Transmission Control Protocol
--                        	Bit 3: Stream Control Transmission Protocol
--                         	Bit 4: Transport Layer Security Protocol over TCP
--                         	Bit 5: Transport Layer Security Protocol over SCTP
--                          	Bit 6 .. 31 : reserved for future extensions.
--                          Only 2(udp), 4(tcp) and 6(udp_tcp) are supported now, others are reservered for future extensions.
--
--                    	ALCATEL-LUCENT NOTE:
--                       	        SUPPORT:    YES
--                            	PERSIST:    YES
--                            	INSRVMOD:   NO
--                            	RANGE:  [2|4|6]
--                            	DEFVALUE:  2
--                            	UNITS:  NA
--                                SPARSE:    NO
--                               "
--                       ::= { sipVSPEntry 9 }
  
			sipVSPTa4 OBJECT-TYPE
				SYNTAX INTEGER (1..3600000)
				ACCESS read-write
				STATUS mandatory
				DESCRIPTION
						"Timer which starts upon the receipt of the first dialed digit, if the dialed digits are not matched with digitmap,
						the expiry of Ta4 will trigger the sending of initial INVITE. This object is not applicable when the
			 			sipVSPDigitSendingMode is configured to en-bloc(1).
					ALCATEL-LUCENT NOTE:
					ACCESS:	READ-WRITE
					USAGE:	OPT
					PERSIST:	YES
					INSRVMOD:	NO 
					RANGE:	(1..3600000)
					DEFVALUE:	4000
					UNITS:	milli-Second
					SPARSE:	NO
						"
				::= { sipVSPEntry 10 }	

				
                sipVSPTAcmDelta OBJECT-TYPE
			SYNTAX INTEGER (1..3600000)
			ACCESS read-write
			STATUS mandatory
			DESCRIPTION
				"The timer T-acmdelta starts on the situation that T-interdigit timer expires and there is INVITE
				 transaction ongoing. The expiry of T-acmdelta will end the attemp of the call establishment.

				ALCATEL NOTE:
		                        ACCESS:	READ-WRITE
		                        USAGE:	OPT
					PERSIST:  	YES
					INSRVMOD:    NO 
					RANGE:	(1..3600000)
					DEFVALUE: 18000
					UNITS:	milli-second
				"
			::= { sipVSPEntry 11 }

                sipVSPAccessHeldTimer OBJECT-TYPE
                        SYNTAX INTEGER (1..65535)
                        ACCESS read-write
                        STATUS mandatory
                        DESCRIPTION
                                " When the sipVSPReleaseMode= normal, this value
                                  is used in the release control procedure. It
                                  is started when receiving INVITE with No Ring
                                  and no SDP and stopped when sending 200 OK
                                  (INVITE).
                                  When sipVSPReleaseMode= caller/callee/both,
                                  this value is the time that the system
                                  postpone to send BYE message after the local
                                  user onhook.

                                ALCATEL-LUCENT NOTE:
		                        ACCESS:	READ-WRITE
		                        USAGE:	OPT
                                        PERSIST:     YES
                                        INSRVMOD:    NO 
                                        RANGE:  (1..65535)
                                        DEFVALUE:  600
                                        UNITS:  Second
                                        SPARSE:	NO
                                "
                        ::= { sipVSPEntry 12 }

                sipVSPAwaitingTimer OBJECT-TYPE
                        SYNTAX INTEGER (1..65535)
                        ACCESS read-write
                        STATUS mandatory
                        DESCRIPTION
                               "This value is used in the release control procedure. It is started when receiving 200 OK (Bye) 
                                with X-Service-indicator and stopped when receiving INVITE with No Ring and No SDP.
		                ALCATEL-LUCENT NOTE:
		                ACCESS:	READ-WRITE
		                USAGE:	OPT
		                PERSIST:	YES
		                INSRVMOD:	NO 
		                RANGE:	(1..65535)
		                DEFVALUE:	60
		                UNITS:	Second
		                SPARSE:	NO

                                "
                        ::= { sipVSPEntry 13 }

 --               sipVSPDnsPurgeTimer OBJECT-TYPE
 --                    SYNTAX INTEGER (0..86400)
 --                     ACCESS read-write
 --                      STATUS mandatory
 --                       DESCRIPTION
 --                                "This is an interim measure to the support of SRV TTL in future ISAM-V releases. Where, the DNS purge timer will be complementary to future TTL support: i.e. use purge timer only if TTL is Not Available. Although the range is defined from 0 up to 86400, that currently for R4.1.x release only the range 10 up to 86400 is applicable.
 --
 --
--
--
--                                     ALCATEL NOTE:
--                                        SUPPORT:     YES
--                                       PERSIST:     YES
--                                       INSRVMOD:    NO
--                                      RANGE:  (0..86400)
 --                                       DEFVALUE:  1200
--                                        UNITS:  Second
--                                "
--                        ::= { sipVSPEntry 14 }

                sipVSPOverlap484Action OBJECT-TYPE
	                 SYNTAX INTEGER 
		         {
		          release-call(0),  
		          continue(1) 
		         }
	                 ACCESS read-write
	                  STATUS mandatory
	                 DESCRIPTION
			         "Allows to configure whether to release call or not when 484 received in ovelap dialing indialog method. 
                                 Release-call (0) : Terminate the call (default value),
                                 Continue (1) : Do not terminate the call.
		          ALCATEL-LUCENT NOTE:
		               ACCESS:	READ-WRITE
		               USAGE:	OPT
		               PERSIST:	YES
		               INSRVMOD:	NO 
		               RANGE:	0|1
		               DEFVALUE:	release-call (0)
		               UNITS:	NA
		               SPARSE:	NO
			"
	                ::= { sipVSPEntry 15 }


                  sipVSPDMPMIntDgtExpid OBJECT-TYPE
                        SYNTAX INTEGER
                        {
                            send-invite(0),
                            release-call(1)
                        }       
                        ACCESS read-write
                        STATUS mandatory
                        DESCRIPTION     
   			   "Allows to configure the action to be taken at the moment inter-digit timer expired with digitmap partial match.
                            Send-invite (0) : Send invite (default value),
                           Release-call (1) : Release call.
		           ALCATEL-LUCENT NOTE:
		               ACCESS:	READ-WRITE
		               USAGE:	OPT
		               PERSIST:	YES
		               INSRVMOD:	NO 
		               RANGE:	0|1
		               DEFVALUE:	send-invite (0)
		               UNITS:	NA
		               SPARSE:	NO
                                "
                        ::= { sipVSPEntry 16 } 

                  sipVSPDialingStartTimer OBJECT-TYPE
                        SYNTAX INTEGER (1..60)
                        ACCESS read-write
                        STATUS mandatory
                        DESCRIPTION
    			"Allows to configure the dialing start timer i.e. the maximum waiting time for dialing the first digit.
		             ALCATEL-LUCENT NOTE:
		             ACCESS:	READ-WRITE
		             USAGE:	OPT
		             PERSIST:	YES
		             INSRVMOD:	NO 
		             RANGE:	(1..60)
		             DEFVALUE:	10
		             UNITS:	Second
		             SPARSE:	NO
                                "
                        ::= { sipVSPEntry 17 }
                        
                  sipVSPDialingLongTimer OBJECT-TYPE
                        SYNTAX INTEGER (1..60)
                        ACCESS read-write
                        STATUS mandatory
                        DESCRIPTION
 			" Allows to configure the dialing long timer i.e. the maximum waiting time for dialing 
 			when no match found in the digitmap.
		             ALCATEL-LUCENT NOTE:
		             ACCESS:	READ-WRITE
		             USAGE:	OPT
		             PERSIST:	YES
		             INSRVMOD:	NO 
		             RANGE:	(1..60)
		             DEFVALUE:	20
		             UNITS:	Second
		             SPARSE:	NO
                                "
                        ::= { sipVSPEntry 18 }

                  sipVSPDialingShortTimer OBJECT-TYPE
                        SYNTAX INTEGER (1..60)
                        ACCESS read-write
                        STATUS mandatory
                        DESCRIPTION
   			" Allows to configure the dialing short timer i.e. the maximum waiting time for dialing when a match is found
            in the digitmap.
		              ALCATEL-LUCENT NOTE:
		              ACCESS:	READ-WRITE
		              USAGE:	OPT
		              PERSIST:	YES
		              INSRVMOD:	NO 
		              RANGE:	(1..60)
		              DEFVALUE:	5
		              UNITS:	Second
		              SPARSE:	NO
                                "
                        ::= { sipVSPEntry 19 }

             	   sipVSPURIType OBJECT-TYPE
                        SYNTAX INTEGER
                                {
                                sip-uri(1),
                                tel-uri(2)
                                }
                        ACCESS read-write
                        STATUS mandatory
                        DESCRIPTION
 			" The uri type.
		             ALCATEL-LUCENT NOTE:
		             ACCESS:	READ-WRITE
		             USAGE:	OPT
		             PERSIST:	YES
		             INSRVMOD:	NO 
		             RANGE:	1|2
		             DEFVALUE:	sip-uri (1)
		             UNITS:	NA
		             SPARSE:	NO
                                "
                        ::= { sipVSPEntry 20 }

--      		sipVSPRegInterTimerAntiAlavanche OBJECT-TYPE
--                        SYNTAX INTEGER (100..32000)
--                        ACCESS read-write
--                        STATUS mandatory
--                        DESCRIPTION
--                                " Register interval timer for anti-alavanche.
--                                ALCATEL NOTE:
--                                        SUPPORT:     YES
--                                        PERSIST:     YES
--                                        INSRVMOD:    NO
--                                        RANGE:  (100..32000)
--                                        DEFVALUE:  500
--                                        UNITS:  Milli-Second
--                                "
--                        ::= { sipVSPEntry 21 }


		 sipVSPRfc2833PayloadType OBJECT-TYPE
			SYNTAX INTEGER (96..127)
			ACCESS read-write
			STATUS mandatory
			DESCRIPTION
			" Payload type of RFC2833. 
		           ALCATEL-LUCENT NOTE:
		           ACCESS:	READ-WRITE
		           USAGE:	OPT
		           PERSIST:	YES
		           INSRVMOD:	NO 
		           RANGE:	(96..127)
		           DEFVALUE:	96
		           UNITS:	NA
		           SPARSE:	NO
		         "
		::= { sipVSPEntry 22 }


		sipVSPRfc2833Processing OBJECT-TYPE
			SYNTAX INTEGER
			{
			audio (1),
			rfc2833 (2),
			both (3),
			mandatory-audio(4) 
			}
			ACCESS read-write
			STATUS mandatory
			DESCRIPTION
		       " Allows to configure on how to process the DTMF and telephone event tones by rfc2833 or audio.
		           Audio (1) : No 2833 payload type will be included in SDP offer. If 2833 payload negotiation result does not
		                       support rfc2833, the access device will send  DTMF and telephone event tones by audio. 
                                       If 2833 payload negotiation result supports rfc2833, the access device will send  DTMF and telephone event
                                       tones both by audio and 2833.
		           Rfc2833 (2) : Configured 2833 payload type value will be included in SDP offer. If 2833 payload negotiation
                                         result does not support rfc2833, the access device will not send  DTMF and telephone event tones by 2833.
                                         If 2833 payload negotiation result supports rfc2833, ISAMV will send  DTMF and telephone event tones by 2833.
		           Both (3) : Configured 2833 payload type value will be included in SDP offer. If 2833 payload negotiation
                                      result does not support rfc2833, the access device will not send DTMF and telephone event tones by both audio and 2833.
                                      If 2833 payload negotiation result supports rfc2833, the access device will send  DTMF and telephone event
                                      tones both by audio and 2833.
                          Mandatory-audio (4) : no 2833 payload type will be included in SDP offer and answer. Always send  DTMF 
                                                and telephone event tones by audio.
		         ALCATEL-LUCENT NOTE:
		         ACCESS:	READ-WRITE
		         USAGE:	OPT
		         PERSIST:	YES
		         INSRVMOD:	NO 
		         RANGE:	1|2|3|4
		         DEFVALUE:	audio (1)
		         UNITS:	NA
		         SPARSE:	NO
			"
			::= { sipVSPEntry 23 }


			sipVSPMinDataJitterBuffer OBJECT-TYPE
				SYNTAX INTEGER (0..200)
				ACCESS read-write
				STATUS mandatory
				DESCRIPTION
				" The minimum data jitter buffer for data calls working in RTP mode.
		                ALCATEL-LUCENT NOTE:
		                ACCESS:	READ-WRITE
		                USAGE:	OPT
		                PERSIST:	YES
		                INSRVMOD:	NO 
		                RANGE:	(0..200)
		                DEFVALUE:	50
		                UNITS:	Milli-Second
		                SPARSE:	NO
				"
			::= { sipVSPEntry 24 }


			sipVSPInitDataJitterBuffer OBJECT-TYPE
				SYNTAX INTEGER (0..200)
				ACCESS read-write
				STATUS mandatory
				DESCRIPTION
				" The Initial data jitter buffer for data calls working in RTP mode.
		                ALCATEL-LUCENT NOTE:
		                ACCESS:	READ-WRITE
		                USAGE:	OPT
		                PERSIST:	YES
		                INSRVMOD:	NO 
		                RANGE:	(0..200)
		                DEFVALUE:	50
		                UNITS:	Milli-Second
		                SPARSE:	NO
				"
			::= { sipVSPEntry 25 }


			sipVSPMaxDataJitterBuffer OBJECT-TYPE
				SYNTAX INTEGER (0..200)
				ACCESS read-write
				STATUS mandatory
				DESCRIPTION
				" The maximum data jitter buffer for data calls working in RTP mode.
		                ALCATEL-LUCENT NOTE:
		                ACCESS:	READ-WRITE
		                USAGE:	OPT
		                PERSIST:	YES
		                INSRVMOD:	NO 
		                RANGE:	(0..200)
		                DEFVALUE:	50
		                UNITS:	Milli-Second
		                SPARSE:	NO
				"
			::= { sipVSPEntry 26 }

                        sipVSPReleaseMode OBJECT-TYPE
                                SYNTAX INTEGER
                                {
                                   normal (1),
                                   caller (2),
                                   callee (3),
                                   both (4)
                                }
                                ACCESS read-write
                                STATUS mandatory
                                DESCRIPTION
  			        "Allows to configure whether to send BYE immediately or not after caller/callee/both onhook:
			        Normal (1) : send BYE immediately. Applicable to the normal call release procedure.
			        Caller (2) : postpone BYE for caller. Only postpone BYE in case the local termination is the caller.
			        Callee (3) : postpone BYE for callee. Only postpone BYE in case the local termination is the callee.
			        Both (4) : postpone BYE for caller and callee. Postpone BYE in case the local termination is caller or callee.
		                ALCATEL-LUCENT NOTE:
		                ACCESS:	READ-WRITE
		                USAGE:	OPT
		                PERSIST:	YES
		                INSRVMOD:	NO 
		                RANGE:	1|2|3|4
		                DEFVALUE:	normal (1)
		                UNITS:	NA
		                SPARSE:	NO
                                "
                        ::= { sipVSPEntry 27 }   
						 

                        sipVSPDynamicPTNegoType OBJECT-TYPE
				SYNTAX INTEGER
				{
					far-end (1),
					asymmetric (2)
				}
				ACCESS read-write
				STATUS mandatory
				DESCRIPTION
  				"Allows to configure how to determine the dynamic payload type value in case the local system is the SDP
				offerer while this value answered by the SDP answerer is different from the one offered by the local system.
				These will apply on all with dynamic payload type value(i.e. RFC2833, G.711A/U with dynamic PT).
				If the local system is the SDP answerer, the local system will always use the same payload type value offered
				by the SDP offerer, irrespecting to which value is defined, unless that value is used for another payload type
				in the same stream.
				If the local system is the SDP offerer, and the payload type value answered by the SDP answerer is different
				from the one offered by the local system, the local system will determine the RTP payload type value
				according to the value of this object.

				Far-end (1) : the local system will apply the payload type value answered by the SDP answerer in both
						sending and receiving direction. 
				Asymmetric (2) : In sending direction, the local system will apply the payload type value answered by the SDP
						answerer; In receiving direction, the local system will apply the payload type value offered by
						the local system.
				ALCATEL-LUCENT NOTE:
				ACCESS:	READ-WRITE
				USAGE:	OPT
				PERSIST:	YES
				INSRVMOD:	NO 
				RANGE:	1|2
				DEFVALUE:	far-end (1)
				UNITS:	NA
				SPARSE:	NO
				"
			::= { sipVSPEntry 28 }

        		sipVSPVbdG711APayloadType OBJECT-TYPE
				SYNTAX INTEGER (96..127)
				ACCESS read-write
				STATUS mandatory
				DESCRIPTION
				"VBD Dynamic Payload type of G711A, only applied for V.152 . that is vbdmode is v152fallback-autoswitch
				or v152fallback-renegotiation.
				ALCATEL-LUCENT NOTE:
				ACCESS:	READ-WRITE
				USAGE:	OPT
				PERSIST:	YES
				INSRVMOD:	NO 
				RANGE:	(96..127)
				DEFVALUE:	97
				UNITS:	NA
				SPARSE:	NO
				"
			::= { sipVSPEntry 29 }

			sipVSPVbdG711UPayloadType OBJECT-TYPE
				SYNTAX INTEGER (96..127)
				ACCESS read-write
				STATUS mandatory
				DESCRIPTION
				" VBD Dynamic Payload type of G711U, only applied for V.152 . that is vbdmode is v152fallback-autoswitch 
				or v152fallback-renegotiation.
				ALCATEL-LUCENT NOTE:
				ACCESS:	READ-WRITE
				USAGE:	OPT
				PERSIST:	YES
				INSRVMOD:	NO 
				RANGE:	(96..127)
				DEFVALUE:	98
				UNITS:	NA
				SPARSE:	NO
				"
			::= { sipVSPEntry 30 }

			sipVSPVbdMode OBJECT-TYPE
				SYNTAX INTEGER
				{
				autoswitch (1),
				renegotiation (2),							 
				v152fallback-autoswitch (3),
                                v152fallback-renegotiation (4)
--				renegotiation-CT-mode (5)
                                } 
				ACCESS read-write
				STATUS mandatory
				DESCRIPTION
				" VBD mode :
				Autoswitch (1) : Use default codec without negotiation 
				Renegotiation (2) : Re-INVITE will be sent for VBD negotiation in case that fax/modem detect. 
				v152fallback-autoswitch (3) : Apply V.152 procedure, VBD codec (with dynamic payload type) will be
				negotiated at voice call setup.  If V152 neogtionation fails, act as autoswitch (1).
				v152fallback-renegotiation (4) : Apply V.152 procedure, VBD codec (with dynamic payload type) will be
							negotiated at voice call setup. If V152 neogtionation fails, act as renegotiation (2).
				ALCATEL-LUCENT NOTE:
				ACCESS:	READ-WRITE
				USAGE:	OPT
				PERSIST:	YES
				INSRVMOD:	NO 
				RANGE:	1|2|3|4
				DEFVALUE:	autoswitch (1)
				UNITS:	NA
				SPARSE:	NO
				"
			::= { sipVSPEntry 31 }

   			sipVSPWarmlineDelayTimer OBJECT-TYPE
				SYNTAX INTEGER
				ACCESS read-write
				STATUS mandatory
				DESCRIPTION
				"This object defines the duration of the Warm line Service delay. This timer starts when an off-hook condition
				is detected on the line of this termination.
				If it expires before any digits are received from the line, the Warm line Service is applied to the line.
				ALCATEL-LUCENT NOTE:
				ACCESS:	READ-WRITE
				USAGE:	OPT
				PERSIST:	YES
				INSRVMOD:	NO 
				RANGE:	(1..60)
				DEFVALUE:	4
				UNITS:	Second
				SPARSE:	NO
				"
			::= { sipVSPEntry 32 }

			sipVSPDHCPOption82 OBJECT-TYPE
                		SYNTAX INTEGER
                		{
                        		enable(1),
                       		 	disable(2)
                		}
                		ACCESS read-write
                		STATUS mandatory
                		DESCRIPTION
                 		"Allows to enable or disable the option 82 in the DHCP request. This object has only relevance  for a 
				distributed L2 architecture with shared VLAN approach and sipUserAgentGwConfigMode  = DHCP(1).
				ALCATEL-LUCENT NOTE:
				ACCESS:	READ-WRITE
				USAGE:	OPT
				PERSIST:	YES
				INSRVMOD:	NO 
				RANGE:	1|2
				DEFVALUE:	disable (2)
				UNITS:	NA
				SPARSE:	NO
                        	"
                	::= { sipVSPEntry 33 }
                                
                        sipVSPEnableRegisterSubscribe OBJECT-TYPE
                        	SYNTAX INTEGER
                        	{
                                disable (1),
                                enable (2)
                         	}
                                ACCESS read-write
                                STATUS mandatory
                                DESCRIPTION 
                         	"Allows to enable/disable the register SUBSCRIBE method.
				ALCATEL-LUCENT NOTE:
				ACCESS:	READ-WRITE
				USAGE:	OPT
				PERSIST:	YES
				INSRVMOD:	NO 
				RANGE:	1|2
				DEFVALUE:	disable (1)
				UNITS:	NA
				SPARSE:	NO
                                "
                        ::= { sipVSPEntry 34 }


                         sipVSPSubscribePeriod OBJECT-TYPE
                                SYNTAX INTEGER
                                ACCESS read-write
                                STATUS mandatory
                                DESCRIPTION 
				"VSP/ VAG level MIB object of subscription expiration time that the client will propose by including it in an 
                expires header of a SUBSCRIBE request. If this property is set to a value of zero, the client SHALL NOT 
                refresh a subscription even if the server specifies an expiration interval.
				ALCATEL-LUCENT NOTE:
				ACCESS:	READ-WRITE
				USAGE:	OPT
				PERSIST:	YES
				INSRVMOD:	NO 
				RANGE:	0|(60..86400)
				DEFVALUE:	3600
				UNITS:	Second
				SPARSE:	NO
                                "
                                ::= { sipVSPEntry 35 }


                         sipVSPSubscribeHeadStart OBJECT-TYPE
                                SYNTAX INTEGER
                                ACCESS read-write
                                STATUS mandatory
                                DESCRIPTION 
				"Object that allows to configure the number of seconds prior to expiration of a subscription at which the client 
                sends a SUBSCRIBE request to refresh the subscription.
                The value '0' means the sipVSPSubscribeHeadStart functionality does not take effect.
				ALCATEL-LUCENT NOTE:
				ACCESS:	READ-WRITE
				USAGE:	OPT
				PERSIST:	YES
				INSRVMOD:	NO 
				RANGE:	0|(32..86400)
				DEFVALUE:	600
				UNITS:	Second
				SPARSE:	NO
	               		"
                        ::= { sipVSPEntry 36 }


                         sipVSPT38withSameUDP OBJECT-TYPE
                                SYNTAX INTEGER
                                {
                                       disable (1),
                                       enable (2)
                                }
                                ACCESS read-write
                                STATUS mandatory
                                DESCRIPTION 
				"Objcetthat allows to configure whether the same UDP port  is to be used when Voice switching to T.38 or 
                T.38 switching to Voice. 
                Disable (1) : the UDP ports used by Voice and T38 are different. T38 choose the biggest free UDP port from
                              pool.
                Enable (2) : the UDP ports used by Voice and T38 are same.
				ALCATEL-LUCENT NOTE:
				ACCESS:	READ-WRITE
				USAGE:	OPT
				PERSIST:	YES
				INSRVMOD:	YES 
				RANGE:	1|2
				DEFVALUE:	disable (1)
				UNITS:	NA
				SPARSE:	NO
	                        "
            ::= { sipVSPEntry 37 }
 
            sipVSPSSPProfileName OBJECT-TYPE
                SYNTAX OCTET STRING (SIZE (0..64))
                ACCESS read-write 
                STATUS mandatory 
                DESCRIPTION
                    " The name of the SIP Service Profile assigned to a Service Gateway (sipVSPTable entry). 
                    The SSPs that can be associated with a sipVSPTable entry must be present in the activated CDE file. 
                    The Operator has the possibility to assign a different SSP for each sipVSPTable entry or can assign the same SSP to multiple sipVSPTable entries. 
                    The SSPs that are present in the activated CDE file can be displayed by means of the sipSSPProfileTable. (ref. the related show CLI command) 
                    Should the operator not configure a SSP for a particular sipVSPTable entry, the system will autonomously assign the SSP with the lowest profile id 
                    present in the activated CDE file at the moment the admin state of this sipVSPTable entry is changed from 'down' to 'up'.


                    ALCATEL-LUCENT NOTE: 
                    ACCESS: READ-WRITE 
                    USAGE:  OPT
                    PERSIST:  YES 
                    INSRVMOD: NO
                    RANGE: SIZE (0..64)  
                    DEFVALUE: NULL
                    UNITS:  NA  
                    SPARSE: NO  
           " 
           ::= { sipVSPEntry 38 }       

				sipVSPDtmfSipInfo OBJECT-TYPE
                        	SYNTAX INTEGER
                        	{
                                disable (1),
                                enable (2)
                         	}
                                ACCESS read-write
                                STATUS optional
                                DESCRIPTION 
                         	"Allows to enable/disable DTMF transmission via SIP INFO.
				ALCATEL-LUCENT NOTE:
				ACCESS:	READ-WRITE
				USAGE:	OPT
				PERSIST:	YES
				INSRVMOD:	NO 
				RANGE:	1|2
				DEFVALUE:	disable (1)
				UNITS:	NA
				SPARSE:	NO
                                "
                        ::= { sipVSPEntry 39 }

--=============================================================================
-- 	Sip Voice Service Provider Mapping Table
--=============================================================================
		sipVSPMappingTable OBJECT-TYPE
			SYNTAX SEQUENCE OF SipVSPMappingEntry
			ACCESS not-accessible
			STATUS mandatory
			DESCRIPTION
			"The operator friendly Service Gateway name to unique internal identifier mapping table.

            7302/7330 ISAM FTTN : Supported
            7363 MX : Supported
            7367 SX : Supported

			ALCATEL NOTE: 
			TABLESIZE:  17
			DESCR:      NA
			 "
		::= { sipMIB 17}

		
		sipVSPMappingEntry OBJECT-TYPE
			SYNTAX SipVSPMappingEntry
			ACCESS not-accessible
			STATUS mandatory
			DESCRIPTION
			"An entry in the sipVSPMappingTable.
            An entry is auto-created upon the creation of an entry in the sipVSPTable.
            An entry is auto-deleted upon the deletion of an entry in the sipVSPTable.
			"
			INDEX { sipVSPMappingName }
		::= { sipVSPMappingTable 1 }

		SipVSPMappingEntry ::=
			SEQUENCE { 
				sipVSPMappingName
					OCTET STRING,
				sipVSPMappingId
					INTEGER	
			 }	

		sipVSPMappingName OBJECT-TYPE
			SYNTAX OCTET STRING (SIZE (0..32))
			ACCESS not-accessible
			STATUS mandatory
			DESCRIPTION
                "The administrative domain name of a Service Gateway.
                This name must be unique across all configured entries of the sipVSPTable.
			ALCATEL-LUCENT NOTE:
			ACCESS:	NOT-ACCESSIBLE
			USAGE:	MANDATORY
			PERSIST:	NA
			INSRVMOD:	NA 
			RANGE:	SIZE (0..32)
			DEFVALUE:	NA
			UNITS:	NA
			SPARSE:	NO
			"
		::= { sipVSPMappingEntry 1 }


		sipVSPMappingId OBJECT-TYPE
			SYNTAX INTEGER 
			ACCESS read-only
			STATUS mandatory
			DESCRIPTION
				"The unique internal identifier of a Service Gateway.
			ALCATEL-LUCENT NOTE:
			ACCESS:	READ-ONLY
			USAGE:	NA
			PERSIST:	NA
			INSRVMOD:	NA 
			RANGE:	(1..17)
			DEFVALUE:	NA
			UNITS:	NA
			SPARSE:	NO
		"
		::= { sipVSPMappingEntry 2 }


--=================================================================================
-- 	Sip User Agent Access Point Table
--=================================================================================
		sipUserAgentAccessPointTable OBJECT-TYPE
			SYNTAX SEQUENCE OF SipUserAgentAccessPointEntry
			ACCESS not-accessible
			STATUS mandatory
			DESCRIPTION
			"The entry/entries in the SIP User Agent Access Point Table is/are auto-created by the system with default values upon the creation of an entry in the sipUserAgentTable.
            In case the SIP User Agent Table entry for the autonomously created entry in the sipVspTable is created with the IP config mode set to 'DHCP', then the SIP User Agent Access PointTable entries are created with admin state set to 'up' .
            In case the SIP User Agent Table entry for a manually created entry in the sipVspTable is created with the IP config mode set to 'DHCP', then the SIP User Agent Access PointTable entries are created with admin state set to 'down' .
            Such SIP User Agent Access Point entry is common to all voice LT boards in the node.
            The SIP User Agent Access Point Table contains an entry/entries for each Service Gateway created and administratively enabled in the access node.

            7302/7330 ISAM FTTN :
            1)     sipUAIpAddrPolicy configured as 'distributed' : a SIP User Agent Access Point Table entry is created for each of the planned voice LT boards. The sipUaApAssocSlotId contains the voice LT board's slot id.
            2)     sipUAIpAddrPolicy configured as 'centralised' : a single SIP User Agent Access Point Table entry is created. The sipUaApAssocSlotId contains the NT-A's slot id i.e. 0x1101.

            7363 MX :
            sipUAIpAddrPolicy configured as 'centralised' : a single SIP User Agent Access Point Table entry is created. The sipUaApAssocSlotId contains the slot id of the board (NTIO/NT) at which the signaling IP@ and voice IP@ are configured.

            7367 SX :
            sipUAIpAddrPolicy configured as 'centralised' : a single SIP User Agent Access Point Table entry is created. The sipUaApAssocSlotId contains the slot id of the board (NT) at which the signaling IP@ and voice IP@ are configured.

            Ref. Limitations in the description section of the SIP User Agent Table
            Limitations are checked upon changing the administrative state of a SIP User Agent Access Point entry in the sipUserAgentAccessPointTable from 'down' to 'up'. 
            The system will perform the following checks :
            In case 2 SIP User Agent entries are considered as having the same configuration settings, but for the related SIP User Agent Access Point entries, different signaling  and/or media IP@ are configured, the administrative 'UP' modification action for the SIP User Agent Access Point Table will be rejected.
            In case of the centralized IP@ architecture, the SIP User Agent Access Point entry checks are done at node level.
            In case of the distributed IP@ architecture, the SIP User Agent Access Point entry checks are done at voice LT board level.
            Upon the creation of a SIP User Agent  Access Point entry with admin state = down, the configuration  entry is stored within the NT DB.
            Upon the rejection of the admin state change the configured entry remains stored in the DB.


			ALCATEL NOTE:
 
			7302/7330 ISAM FTTN :
			TABLESIZE:	DEP [max LT slot number of the shelf * 16]
			DESCR:	NA

			7363 MX / 7367 SX:
			TABLESIZE:	1
			DESCR:	NA "
		::= { sipMIB 18}

		sipUserAgentAccessPointEntry OBJECT-TYPE
			SYNTAX SipUserAgentAccessPointEntry
			ACCESS not-accessible
			STATUS mandatory
			DESCRIPTION
				" Each entry contains the information of a Sip UserAgent Access Point.
				"
				INDEX { sipUserAgentId,sipUaApAssocSlotId }
			::= { sipUserAgentAccessPointTable 1 }

		SipUserAgentAccessPointEntry ::=
			SEQUENCE {
				sipUaApAssocSlotId			INTEGER,
				sipUaApRowStatus			RowStatus,					
				sipUaApAdminStatus			INTEGER,
				sipUaApOperStatus			INTEGER,
				sipUaApIpAddrType			InetAddressType,
				sipUaApSignalIpAddr			InetAddress,
				sipUaApSignalIpPrefixLength		InetAddressPrefixLength,
				sipUaApRtpIpAddr 			InetAddress,
				sipUaApRtpIpPrefixLength		InetAddressPrefixLength,                                          
				sipUaApDHCPFQDN				DisplayString,
				sipUaApDHCPCustomerID			DisplayString,
                sipUaApLSARtpIpAddr         InetAddress,
                sipUaApLSARtpIpPrefixLength InetAddressPrefixLength
			}
		
		sipUaApAssocSlotId OBJECT-TYPE
			SYNTAX INTEGER (1..65535)
			ACCESS read-only 
			STATUS mandatory
			DESCRIPTION
				" 
                7302/7330 ISAM FTTN :
                The slot position of the board at which the signaling IP@ and voice IP@ are configured. 

                1)  sipUAIpAddrPolicy configured as 'distributed' : a SIP User Agent Access Point Table entry is created for each of the planned voice LT boards. The sipUaApAssocSlotId contains the voice LT board's slot id.
                2)  sipUAIpAddrPolicy configured as 'centralised' : a single SIP User Agent Access Point Table entry is created. The sipUaApAssocSlotId contains the NT-A's slot id i.e. 0x1101.

                7363 MX :
                sipUAIpAddrPolicy configured as 'centralised' : a single SIP User Agent Access Point Table entry is created. The sipUaApAssocSlotId contains the slot id of the NTIO board

                7367 SX :
                sipUAIpAddrPolicy configured as 'centralised' : a single SIP User Agent Access Point Table entry is created. The sipUaApAssocSlotId contains the slot id of the NT board

			ALCATEL-LUCENT NOTE:
			ACCESS:	read-only
			USAGE:	MANDATORY
			PERSIST:  	YES
			INSRVMOD: NA
			RANGE:	NA
			DEFVALUE: 	NA
			UNITS:	NA	
			SPARSE:	NO							
			"
		::= { sipUserAgentAccessPointEntry 1 }

		sipUaApRowStatus OBJECT-TYPE
			SYNTAX RowStatus
			ACCESS read-write
			STATUS mandatory
			DESCRIPTION
				"The status of this conceptual row.
				The RowStatus TC requires that this DESCRIPTION clause
				states under which circumstances other objects in this row
				can be modified.  The value of this object has no effect on
				whether other objects in this conceptual row can be
				modified.
				A conceptual row can always be made active.
			ALCATEL-LUCENT NOTE:
			ACCESS:	READ-WRITE
			USAGE:	MAND
			PERSIST:  	NO
			INSRVMOD: YES
			RANGE:	1 	-- active (1)
			DEFVALUE: 	NA
			UNITS:	NA
			SPARSE:	NO
        		"
		::= { sipUserAgentAccessPointEntry 2 }

			
		sipUaApAdminStatus OBJECT-TYPE
			SYNTAX INTEGER
			{
				up(1),
				down(2)
			}
			ACCESS read-write
			STATUS mandatory
			DESCRIPTION
				"The administrative status of this sip user agent access-point.
				When the administrative status of a SIP User Agent Access Point is modified from 'up' to 'down', then following actions are taken by the system for the voice LT boards associated with this Sip user Agent Access Point :
 				Active calls are immediately aborted;
 				SIP terminations are de-registered;
 				The operational status of the SIP terminations is modified to 'down'.
 				The physcial-lines of the SIP terminations are powered down.

				UP (1) : the attributes of this entry that are indicated as INSRVMOD=YES can be modified.
				DOWN (2) : the attributes of this entry that are indicated as INSRVMOD=YES and the attributes that are
					indicated as INSRVMOD=NO can be modified.
					Note that the attributes of the same entry that are indicated INSRVMOD=NA cannot be modified after
					creation.
					In case sipUserAgentGwConfigMode in the SIP User Agent Table is configured as 'DHCP', this object is 
					read-write.
                             		In case sipUserAgentGwConfigMode in the SIP User Agent Table is configured as 'MANUAL', this object is
					read-write.
			ALCATEL-LUCENT NOTE:
			ACCESS:	READ-WRITE
			USAGE:	OPT
			PERSIST:  	YES
			INSRVMOD: YES
			RANGE:	1 | 2
			DEFVALUE: 	down(2)
			UNITS:	NA	
			SPARSE:	NO							
			 "
		::= { sipUserAgentAccessPointEntry 3 }


		sipUaApOperStatus OBJECT-TYPE
			SYNTAX INTEGER
			{
				up(1),
				down(2)
			}
			ACCESS read-only
			STATUS mandatory
			DESCRIPTION
				"The operational status of this sip user agent access-point. 
				Up(1)	: The sip user agent access-point is up and functional.
				Down(2) : The sip user agent access-point is out of service.
				ALCATEL-LUCENT NOTE:
				ACCESS:	READ-ONLY
				USAGE:	NA
				PERSIST:  	NO
				INSRVMOD: NA
				RANGE:	1 | 2
				DEFVALUE: 	NA
				UNITS:	NA	
				SPARSE:    NO							
			"
		::= { sipUserAgentAccessPointEntry 4 }

		sipUaApIpAddrType OBJECT-TYPE
			SYNTAX InetAddressType
			ACCESS read-only
			STATUS mandatory
			DESCRIPTION
				"The IP address type of sipUaApSignalIpAddr and SipUaApRtpIpAddr.
			ALCATEL-LUCENT NOTE:
			ACCESS:	READ-ONLY
			USAGE:	NA
			PERSIST:  	NO
			INSRVMOD: NO
			RANGE:	1	-- only ipv4(1)
			DEFVALUE: 	ipv4
			UNITS:	NA	
			SPARSE:	NO							
			"
		::= { sipUserAgentAccessPointEntry 5 }


		sipUaApSignalIpAddr OBJECT-TYPE
			SYNTAX InetAddress
			ACCESS read-write
			STATUS mandatory
			DESCRIPTION
				"IP address of this sip user agent access-point for signaling traffic.
				The IP context is defined by sipUaApIpAddrType.
				In case sipUserAgentGwConfigMode in the SIP User Agent Table is configured as 'DHCP', this object is 
				read-only.
                             	In case sipUserAgentGwConfigMode in the SIP User Agent Table is configured as 'MANUAL', this object is
				read-write.
				ALCATEL-LUCENT NOTE:
				ACCESS:	READ-WRITE
				USAGE:	NA
				PERSIST:  	YES
				INSRVMOD: NO
				RANGE:	NA
				DEFVALUE: 	NA
				UNITS:	NA	
          			SPARSE:	NO			
			"
		::= { sipUserAgentAccessPointEntry 6 }

		sipUaApSignalIpPrefixLength OBJECT-TYPE
			SYNTAX InetAddressPrefixLength
			ACCESS read-write
			STATUS mandatory
			DESCRIPTION
				"The subnet mask of sipUaApSignalingIpAddr.
				In case sipUserAgentGwConfigMode in the SIP User Agent Table is configured as 'DHCP', this object is 
				read-only.
                             	In case sipUserAgentGwConfigMode in the SIP User Agent Table is configured as 'MANUAL', this object is
				read-write.
			ALCATEL-LUCENT NOTE:
			ACCESS:	READ-WRITE
			USAGE:	NA
			PERSIST:  	YES
			INSRVMOD: NO
			RANGE:	NA
			DEFVALUE: 	NA
			UNITS:	NA
			SPARSE:	NO
			"
		::= { sipUserAgentAccessPointEntry 7 }

		sipUaApRtpIpAddr OBJECT-TYPE
			SYNTAX InetAddress
			ACCESS read-write
			STATUS mandatory
			DESCRIPTION
				"IP address of this sip user agent access-point for voice traffic.
				The IP context is defined by sipUaApIpAddrType.
				In case sipUserAgentGwConfigMode in the SIP User Agent Table is configured as 'DHCP', this object is 
				read-only.
                             	In case sipUserAgentGwConfigMode in the SIP User Agent Table is configured as 'MANUAL', this object is
				read-write.
				Should no value be configured for this sipUaApRtpIpAddr object, then the same IP@ as configured for the
				sipUaApSignalIpAddr object is used for the voice traffic.
			ALCATEL-LUCENT NOTE:
			ACCESS:	READ-WRITE
			USAGE:	OPT
			PERSIST:  	YES
			INSRVMOD:	NO
			RANGE:	NA
			DEFVALUE:  	sipUaApSignalIpAddr
			UNITS:	NA	
			SPARSE:	NO			
			"
		::= { sipUserAgentAccessPointEntry 8 }

		sipUaApRtpIpPrefixLength OBJECT-TYPE
			SYNTAX InetAddressPrefixLength
			ACCESS read-write
			STATUS mandatory
			DESCRIPTION
				"The subnet mask of sipUaApRtpIpAddr .
				In case sipUserAgentGwConfigMode in the SIP User Agent Table is configured as 'DHCP', this object is 
				read-only.
                             	In case sipUserAgentGwConfigMode in the SIP User Agent Table is configured as 'MANUAL', this object is
				read-write.
				Should no value be configured for this sipUaApRtpIpPrefixLength object, then the same prefix length as configured for the sipUaApSignalIpPrefixLength object is used.
				ALCATEL-LUCENT NOTE:
			ACCESS:	READ-WRITE
			USAGE:	OPT
			PERSIST:  	YES
			INSRVMOD: NO
			RANGE:	NA
			DEFVALUE:   sipUaApSignalIpPrefixLength
			UNITS:	NA
			SPARSE:	NO
			"
		::= { sipUserAgentAccessPointEntry 9 }

			
		sipUaApDHCPFQDN OBJECT-TYPE
	    		SYNTAX DisplayString (SIZE (0..255))
	    		ACCESS read-write
	    		STATUS mandatory
	    		DESCRIPTION
	      			"This object is for Clinet FQDN(Fully-Qualified Domain Name). FQDN is a domain name that specifies 
         			its exact location in the tree hierarchy of the Domain Name System(DNS). It specifies all domain levels, 
         			including the top-level domain and the root domain. A fully qualified domain name is distinguished by 
         			its unambiguity; it can only be interpreted one way. FQDN string must consist of digits, letters, and 
         			several special symbos like '.', '-'. If this object is configured, FQDN will be added in option 81 when UA 
         			sends out DHCP request. The object is valid only in the case of the forwarding policy is defined as 
         			distributed(1) and sip user agent gateway config mode is dhcp(1). 
      			ALCATEL-LUCENT NOTE: 
      			ACCESS: NA 
      			USAGE: NA 
      			PERSIST: YES 
      			INSRVMOD: YES 
      			RANGE: SIZE (0..255) 
      			DEFVALUE: null 
      			UNITS: NA 
      			SPARSE: NO 
     			 "
	    	::= { sipUserAgentAccessPointEntry 10 }

		sipUaApDHCPCustomerID OBJECT-TYPE
			SYNTAX DisplayString (SIZE (0..64))
			ACCESS read-write
			STATUS mandatory
			DESCRIPTION
				"This object allows to configure the DHCP option 82 Remote-ID sub-option.  
				Only Remote-ID is supported for DHCP option 82,
				Circuit-ID is not supported for Voice-LT DHCP option 82 .
				The default value is the Physical-ID string, which means that a string with the format 'rack/shelf/slot' will be 
				inserted to DHCP option 82 Remote-ID sub-option.. 

			ALCATEL-LUCENT NOTE:
			ACCESS:	READ-WRITE
			USAGE:	OPT
			PERSIST: 	YES
			INSRVMOD: YES
			RANGE: 	SIZE (0..64)
			DEFVALUE: 	Physical-ID
			UNITS: 	NA
			SPARSE: 	NO
			"
		::= { sipUserAgentAccessPointEntry 11 }
		
        sipUaApLSARtpIpAddr OBJECT-TYPE
        SYNTAX InetAddress
        ACCESS read-write
        STATUS mandatory
        DESCRIPTION
        "Media IP address for the LSA media VLAN.
        This object is associated with the sipUALSARTPVlanID
        Should the operator neither configure the sipUaApLSAARTPIpAddr nor the
        sipUALSARTPVlanId then upon switching to LSA server mode the SIP UA will use the
        media VLAN ID and media IP address as configured in the sipUserAgentRtpVlanId  and
        sipUaApRtpIpAddr objects.
        Should only the sipUApLSARTPIpAddr or only the sipUALSARTPVlanId object be configured 
        then upon switching to LSA server mode the SIP UA will use the media VLAN ID and media
        IP address as configured in the sipUserAgentRtpVlanId and sipUaApRtpIpAddr objects.

        ALCATEL-LUCENT NOTE:
        ACCESS:   READ-WRITE
        USAGE:    OPT
        PERSIST:  YES
        INSRVMOD: NO
        RANGE:    NA
        DEFVALUE: sipUaApRtpIpAddr
        UNITS:    NA 
        SPARSE:   NO
        "
        ::= { sipUserAgentAccessPointEntry 12 }


        sipUaApLSARtpIpPrefixLength OBJECT-TYPE
        SYNTAX InetAddressPrefixLength
        ACCESS read-write
        STATUS mandatory
        DESCRIPTION
        "The subnet mask of sipUaApLSARtpIpAddr.
        Should no value be configured for this sipUaApLSARtpIpPrefixLength object, then the same prefix length as configured for the sipUaApRtpIpPrefixLength object is used.

        ALCATEL-LUCENT NOTE:
        ACCESS: READ-WRITE
        USAGE:    OPT
        PERSIST:  YES
        INSRVMOD: NO
        RANGE:    NA
        DEFVALUE: NA
        UNITS:    NA
        SPARSE:	  NO
        "
        ::= { sipUserAgentAccessPointEntry 13 }

--=============================================================================
--	Sip LineId Syntax Profile Table
--=============================================================================
		sipLineIdSyntaxProfileTable OBJECT-TYPE
			SYNTAX SEQUENCE OF SipLineIdSyntaxProfileEntry
			ACCESS not-accessible
			STATUS mandatory
			DESCRIPTION
				"The sipLineIdSyntaxProfileTable allowing to configure the Line ID Syntax Profile.
                When modifying the Line Id Syntax, it will take effect from the moment the following event takes place :
		 		->A new SIP termination is configured.
		 		->The voice LT board gets reset.
		 		->The SIP termination attributes are updated
                A single MIB table entry is shared by all VAGs configured in the access node. A single entry is 
                auto-created by the system upon system start-up. It can afterwards be modified by the operator.
				
	            7302/7330 ISAM FTTN : Supported
                7363 MX : Supported
		7367 SX : Supported

				ALCATEL NOTE: 
				TABLESIZE:  1
				DESCR:      NA "
			::= { sipMIB 19 }

        
    sipLineIdSyntaxProfileEntry OBJECT-TYPE
			SYNTAX SipLineIdSyntaxProfileEntry
			ACCESS not-accessible
			STATUS mandatory
			DESCRIPTION
					"An entry in the sipLineIdSyntaxProfileTable."
			INDEX { sipLineIdSyntaxProfileId }
			::= { sipLineIdSyntaxProfileTable 1 }


		SipLineIdSyntaxProfileEntry ::=
			SEQUENCE { 
				sipLineIdSyntaxProfileId			INTEGER,
				sipLineIdSyntaxProfileName		OCTET STRING,
				sipLineIdSyntaxProfileRowStatus		RowStatus,
				sipLineIdSyntaxPattern			INTEGER,
				sipLineIdPotsSyntax				OCTET STRING,
				sipLineIdIsdnSyntax				OCTET STRING
				}

	
		sipLineIdSyntaxProfileId OBJECT-TYPE
			SYNTAX INTEGER 
			ACCESS not-accessible
			STATUS mandatory
			DESCRIPTION
					"The unique internal identifier of the Line Id Syntax Profile.
				ALCATEL-LUCENT NOTE:
				ACCESS:	NOT-ACCESSIBLE
				USAGE:	MANDATORY
				PERSIST:  	YES
				INSRVMOD: NA
				RANGE:	(1..1)
				DEFVALUE:	NA
				UNITS:	NA
				SPARSE:	NO
				"
			::= { sipLineIdSyntaxProfileEntry 1 }

		sipLineIdSyntaxProfileName OBJECT-TYPE
			SYNTAX OCTET STRING (SIZE (0..32))
			ACCESS read-only
			STATUS mandatory
			DESCRIPTION
					" The operator friendly name for the Line Id Syntax Profile.
				ALCATEL-LUCENT NOTE:
				ACCESS:	READ-ONLY
				USAGE:	NA
				PERSIST:  	YES
				INSRVMOD:	NA
				RANGE:	SIZE (0..32)
				DEFVALUE: 	profile1
				UNITS:	NA	
				SPARSE#:	NO			
					"
			::= { sipLineIdSyntaxProfileEntry 2 }

		sipLineIdSyntaxProfileRowStatus OBJECT-TYPE
			SYNTAX RowStatus
			ACCESS read-write
			STATUS mandatory
			DESCRIPTION
				"The status of this conceptual row.
				The RowStatus TC requires that this DESCRIPTION clause
				states under which circumstances other objects in this row
				can be modified.  The value of this object has no effect on
				whether other objects in this conceptual row can be
				modified.
				A conceptual row can always be made active.
                It is created when system is up. So only active is supported.
 
				ALCATEL-LUCENT NOTE:
					ACCESS:     NA
                    USAGE:       MAND
					PERSIST:  	NO
					INSRVMOD: YES
					RANGE:	1	-- active (1)
					DEFVALUE: 	NA
					UNITS:	NA
                                        SPARSE:    NO
         		"
			::= { sipLineIdSyntaxProfileEntry 3 }

		sipLineIdSyntaxPattern OBJECT-TYPE
			SYNTAX INTEGER
				{
				terminationUriOrDN(1),
				physicalLineID(2),
				randomPerRegister(3),
				randomPerRegisterAndDialog(4)
				}
			ACCESS read-write
			STATUS mandatory
			DESCRIPTION
					" The pattern to be applied for the Line Id.
				ALCATEL-LUCENT NOTE:
				ACCESS:	READ-WRITE
				USAGE:        OPT
				PERSIST:	YES
				INSRVMOD: NO
				RANGE:	1 | 2 | 3 | 4 
				DEFVALUE: 	terminationUriOrDN(1)
				UNITS:	NA		
				SPARSE:	NO		
					"
			::= { sipLineIdSyntaxProfileEntry 4 }

		sipLineIdPotsSyntax OBJECT-TYPE
			SYNTAX OCTET STRING (SIZE (0..128))
			ACCESS read-write
			STATUS mandatory
			DESCRIPTION
					" The Line Id Syntax for a POTS termination.
				ALCATEL-LUCENT NOTE:
				ACCESS:	READ-WRITE
				USAGE:        OPT
				PERSIST:	YES
				INSRVMOD: YES
				RANGE:	SIZE(0..128) 
				DEFVALUE: 	al/channel/Port/Slot/Frame/Rack/Access_Node_ID 
				UNITS:	NA		
				SPARSE:	NO		
					 "
			::= { sipLineIdSyntaxProfileEntry 5 }

		sipLineIdIsdnSyntax OBJECT-TYPE
			SYNTAX OCTET STRING (SIZE (0..128))
			ACCESS read-write
			STATUS mandatory
			DESCRIPTION
					"The Line Id Syntax for an ISDN termination. 
				ALCATEL-LUCENT NOTE:
				ACCESS:	READ-WRITE
				USAGE:        OPT
				PERSIST:	YES
				INSRVMOD: YES
				RANGE:	SIZE(0..128) 
				DEFVALUE: 	pra/Channel/Port/Slot/Frame/Rack/Access_Node_ID 
				UNITS:	NA		
				SPARSE:	NO		
					 "
			::= { sipLineIdSyntaxProfileEntry 6 }



--=============================================================================
--      Sip LineIdSyntaxProfile Mapping Table
--=============================================================================
		sipLineIdSyntaxProfileMappingTable OBJECT-TYPE
			SYNTAX SEQUENCE OF SipLineIdSyntaxProfileMappingEntry
			ACCESS not-accessible
			STATUS mandatory
			DESCRIPTION
					"The Sip LineId Syntax Profile name to index mapping table.
		
	                7302/7330 ISAM FTTN : Supported
                    7363 MX : Supported
		    7367 SX : Supported

				ALCATEL NOTE: 
				TABLESIZE:  1
				DESCR:      NA "
			::= { sipMIB 20 }

		sipLineIdSyntaxProfileMappingEntry OBJECT-TYPE
			SYNTAX SipLineIdSyntaxProfileMappingEntry
			ACCESS not-accessible
			STATUS mandatory
			DESCRIPTION
					"The Sip LineId Syntax Profile name to index mapping table.
					Row creation : auto-instantiated as a result of creation of an entry in the sipLineIdSyntaxProfileTable."
			INDEX { sipLineIdSyntaxProfileMappingName }
			::= { sipLineIdSyntaxProfileMappingTable 1 }

		SipLineIdSyntaxProfileMappingEntry ::=
			SEQUENCE { 
				sipLineIdSyntaxProfileMappingName		OCTET STRING,
				sipLineIdSyntaxProfileMappingId			INTEGER	
			}	

		sipLineIdSyntaxProfileMappingName OBJECT-TYPE
			SYNTAX OCTET STRING (SIZE (0..32))
			ACCESS not-accessible
			STATUS mandatory
			DESCRIPTION
					" The user friendly name for this sip LineIdSyntaxProfile
				ALCATEL-LUCENT NOTE:
				ACCESS:	NOT-ACCESSIBLE
				USAGE:	MANDATORY
				PERSIST:	NA
				INSRVMOD:	NA	
				RANGE:	SIZE (0..32)
				DEFVALUE: 	NA
				UNITS:	NA	
				SPARSE:	NO			
					"
			::= { sipLineIdSyntaxProfileMappingEntry 1 }

		sipLineIdSyntaxProfileMappingId OBJECT-TYPE
			SYNTAX INTEGER 
			ACCESS read-only
			STATUS mandatory
			DESCRIPTION
					"This index is the unique internal identifier of this sip LineId Syntax Profile.
				ALCATEL-LUCENT NOTE:
				ACCESS:	READ-ONLY
				USAGE:	NA
				PERSIST:  	NA	
				INSRVMOD: NA
				RANGE:	(1..1)
				DEFVALUE: 	NA
				UNITS:	NA
				SPARSE:	NO
					"
			::= { sipLineIdSyntaxProfileMappingEntry 2 }	

-- ==================================================================
-- SIP BASIC RATE ISDN MIB.
-- ==================================================================
			
-- =============================================================================
-- Sip ISDN Group Definition
-- =============================================================================
		sipIsdnGroup OBJECT IDENTIFIER ::= { sipMIB 21 }	

-- =============================================================================
-- SIP BASIC RATE ISDN INTERFACE EXTENDED TABLE
-- =============================================================================
		sipIsdnBasicRateExtTable OBJECT-TYPE
			SYNTAX SEQUENCE OF SipIsdnBasicRateExtEntry
			ACCESS not-accessible
			STATUS mandatory
			DESCRIPTION
				"This table contains additional objects for the isdnBasicRateTable
                7302/7330 ISAM-V : NOT supported
                7363 NGVR : NOT supported
                7367 SX : NOT Supported.

                                 ALCATEL NOTE: 
                                 SUPPORT: NO 
                                 PERSIST: NA 
                                 INSRVMOD: NA 
                                 RANGE: NA 
                                 DEFVALUE: NA 
                                 UNITS: NA."
			::= { sipIsdnGroup 1 }

		
		sipIsdnBasicRateExtEntry OBJECT-TYPE
			SYNTAX SipIsdnBasicRateExtEntry
			ACCESS not-accessible
			STATUS mandatory
			DESCRIPTION
				"Each entry contains additional information applicable to a particular ISDN Basic Rate Interface
                                 ALCATEL NOTE: 
                                 SUPPORT: NO 
                                 PERSIST: NA 
                                 INSRVMOD: NA 
                                 RANGE: NA 
                                 DEFVALUE: NA 
                                 UNITS: NA."
			INDEX { ifIndex }
			::= { sipIsdnBasicRateExtTable 1 }

		
		SipIsdnBasicRateExtEntry ::=
			SEQUENCE { 
				isdnBasicRateActivateType
					INTEGER,
				isdnBearer1OperStatus
					IsdnBearerOperStatus,
				isdnBearer2OperStatus
					IsdnBearerOperStatus,
				isdnLapdOperStatus
					IsdnLapdOperStatus
			 }

		
	   isdnBasicRateActivateType OBJECT-TYPE
		   	SYNTAX INTEGER
		   	{
		   		permanent(1),
		   		percall(2)
		   	}
		   	ACCESS read-write
		   	STATUS mandatory
		   	DESCRIPTION "the activate type to be used for this ISDN Basic Rate Interface. 
				ALCATEL NOTE:
					SUPPORT:  	NO
					PERSIST:  	YES
					INSRVMOD: 	NO
					RANGE:	permanent(1) | percall(2)
					DEFVALUE: 	percall(2)
					UNITS:	NA				
				"
		   ::= {sipIsdnBasicRateExtEntry 1}
		
		isdnBearer1OperStatus OBJECT-TYPE
			SYNTAX IsdnBearerOperStatus 
			ACCESS read-only
			STATUS mandatory
			DESCRIPTION
				"the bearer channel 1 operational Status for this ISDN Basic Rate Interface.

				ALCATEL NOTE:
					SUPPORT:  	NO
					PERSIST:  	NO
					INSRVMOD: 	NA
					RANGE:	idle(1) | connecting(2) | connected(3) | active(4) | down(5) |unknown(6)
					DEFVALUE: 	NA
					UNITS:	NA				
				"
			::= { sipIsdnBasicRateExtEntry 2 }

		isdnBearer2OperStatus OBJECT-TYPE
			SYNTAX IsdnBearerOperStatus 
			ACCESS read-only
			STATUS mandatory
			DESCRIPTION
				"the bearer channel 2 operational Status for this ISDN Basic Rate Interface.

				ALCATEL NOTE:
					SUPPORT:  	NO
					PERSIST:  	NO
					INSRVMOD: 	NA
					RANGE:	idle(1) | connecting(2) | connected(3) | active(4) | down(5) |unknown(6)
					DEFVALUE: 	NA
					UNITS:	NA				
				"
			::= { sipIsdnBasicRateExtEntry 3 }

		isdnLapdOperStatus OBJECT-TYPE
			SYNTAX IsdnLapdOperStatus 
			ACCESS read-only
			STATUS mandatory
			DESCRIPTION
				"the lapd channel operational Status for this ISDN Basic Rate Interface.

				ALCATEL NOTE:
					SUPPORT:  	NO
					PERSIST:  	NO
					INSRVMOD: 	NA
					RANGE:	inactive(1) | l1Active(2) | l2Active(3)
					DEFVALUE: 	NA
					UNITS:	NA				
				"
			::= { sipIsdnBasicRateExtEntry 4 }			

-- ==================================================================
-- END SIP BASIC RATE ISDN MIB.
-- ==================================================================

-- =============================================================================
-- Sip Statistics And Data Definition
-- =============================================================================
    sipStatisticsAndData OBJECT IDENTIFIER ::= { sipMIB 22 }	
	
-- =============================================================================
-- Sip Term Stats Tca Table
--=============================================================================
	sipTermStatsTcaTable OBJECT-TYPE
				SYNTAX SEQUENCE OF SipTermStatsTcaEntry
				ACCESS not-accessible
				STATUS mandatory
				DESCRIPTION
						"The sip termination statistics tca table.
						When an entry is created in the SIP termination table, a row for this termination is auto-created in this SIP 
						Termination Statistics TCA Table.
						When an entry is deleted in the SIP termination table, the corresponding entry in this table is auto-deleted.
						The operator cannot create nor delete an entry in this table, only update is supported.
						
						7302/7330 ISAM-V : Supported
						7363 NGVR : Supported
						7367 SX : Supported
			
				ALCATEL NOTE: 
			  SUPPORT:  YES
				TABLESIZE:  DEP [NumOfLT * NumOfLinesPerLT ]
			"
	::= { sipStatisticsAndData 1 }

		sipTermStatsTcaEntry OBJECT-TYPE
				SYNTAX SipTermStatsTcaEntry
				ACCESS not-accessible
				STATUS mandatory
				DESCRIPTION
						"An entry in the sipTermStatsTcaTable
				ALCATEL NOTE:
				SUPPORT:  YES
			"
				INDEX { ifIndex }
	::= { sipTermStatsTcaTable 1 }

		SipTermStatsTcaEntry ::=
				SEQUENCE { 
						sipTermStatsTcaEnable			INTEGER,
						sipTermStatsHighJBFLTcaThreshold	INTEGER,
						sipTermStatsLowJBFLTcaThreshold	INTEGER
						}

		sipTermStatsTcaEnable OBJECT-TYPE
				SYNTAX INTEGER
						{
						enabled(1),
						disabled(2)
						}
				ACCESS read-write
				STATUS mandatory
				DESCRIPTION
						" Allows to enable / disable the TCA feature / TCA alarm reporting for this termination.
						Actually, the TCA feature is only supported for the Jitter Buffer Fill Level.
						Jitter Buffer Fill Level is only supported for the current 15min interval . 
						It is not supported for the current 1day interval.
				ALCATEL-LUCENT NOTE:
				ACCESS:	READ-WRITE
				USAGE:	OPT
				PERSIST:	YES
				INSRVMOD:	YES
				RANGE:	1|2
				DEFVALUE: 	disabled (2)
				UNITS:	NA
		    SPARSE:	NO
			"
	::= { sipTermStatsTcaEntry 1 }

		sipTermStatsHighJBFLTcaThreshold OBJECT-TYPE
				SYNTAX INTEGER (0..100)
				ACCESS read-write
				STATUS mandatory
				DESCRIPTION
						" The high Jitter Buffer Fill Level Tca Threshold of the sip termination.
						A value '100' means that this high threshold need not to be considered.
						The high threshold value shall not be smaller than sipTermStatsLowJBFLTcaThreshold.
						When the result of the progressive average calculation exceeds the
						sipTermStatsHighJBFLTcaThreshold, an alarm is immediately raised.
				ALCATEL-LUCENT NOTE:
				ACCESS:	READ-WRITE
				USAGE:	OPT
				PERSIST:	YES
				INSRVMOD:	YES
				RANGE:	(0..100)
				DEFVALUE: 	90
				UNITS:	Percentage
		    SPARSE:	NO
			"
	::= { sipTermStatsTcaEntry 2 }

		sipTermStatsLowJBFLTcaThreshold OBJECT-TYPE
				SYNTAX INTEGER (0..100)
				ACCESS read-write
				STATUS mandatory
				DESCRIPTION
						" The low Jitter Buffer Fill Level Tca Threshold of the sip termination.
						A value '0' means that this low threshold need not be considered.
						The low threshold shall not be larger  than sipTermStatsHighJBFLTcaThreshold.
						If the result of the progressive average at the end of the current 15m period, falls below  
						the sipTermStatsLowJBFLTcaThreshold or if tehcall has ended, the alarm (if any) is cleared..
				ALCATEL-LUCENT NOTE:
				ACCESS:	READ-WRITE
				USAGE:	OPT
				PERSIST:	YES
				INSRVMOD:	YES
				RANGE:	(0..100)
				DEFVALUE: 	80
				UNITS:	Percentage
		    SPARSE:	NO
			"
	::= { sipTermStatsTcaEntry 3 }
-- =============================================================================
-- 
-- Sip System Monitor Group
--=============================================================================

		sipSystemMonitorGroup OBJECT IDENTIFIER ::= { sipStatisticsAndData  2 }
--		This group is system-level actual statistics of SIP application.

		sipNumConfigAndAvailTerm OBJECT-TYPE
			SYNTAX Gauge
			ACCESS read-only
			STATUS mandatory
			DESCRIPTION
				" The number of created SIP Terminations whose operational state is UP
		
			7302/7330 ISAM-V : Supported
			7363 NGVR : Supported
			7367 SX : Supported
		
			ALCATEL-LUCENT NOTE:
			ACCESS:	READ-ONLY
			USAGE:	NA
			PERSIST:	NO
			INSRVMOD:	NA
			RANGE:	NA
			DEFVALUE: 	NA
			UNITS:      number	
		        SPARSE:	NA
			"
		::= { sipSystemMonitorGroup 1 }

		sipNumConfigAndUnavailTerm OBJECT-TYPE
			SYNTAX Gauge
			ACCESS read-only
			STATUS mandatory
			DESCRIPTION
				"The number of created SIP Terminations whose operational state is DOWN.
			
			7302/7330 ISAM-V : Supported
			7363 NGVR : Supported
			7367 SX : Supported
		
			ALCATEL-LUCENT NOTE:
			ACCESS:	READ-ONLY
			USAGE:	NA
			PERSIST:	NO
			INSRVMOD:	NA
			RANGE:	NA
			DEFVALUE: 	NA
			UNITS:	    number
		        SPARSE:	NA
			"
		::= { sipSystemMonitorGroup 2 }

		sipNumUnconfigTerm OBJECT-TYPE
			SYNTAX Gauge
			ACCESS read-only
			STATUS mandatory
			DESCRIPTION
				"the number of not created SIP Termination table for planned voice LT boards.
		
			7302/7330 ISAM-V : Supported
			7363 NGVR : Supported
			7367 SX : Supported
		
			ALCATEL-LUCENT NOTE:
			ACCESS:	READ-ONLY
			USAGE:	NA
			PERSIST:	NO
			INSRVMOD:	NA
			RANGE:	NA
			DEFVALUE: 	NA
			UNITS:  number	
		        SPARSE:	NA
			"
		::= { sipSystemMonitorGroup 3 }



-- =============================================================================
-- 
-- Sip Term Stats P15m Table
--=============================================================================
    sipTermStatsP15mTable OBJECT-TYPE
				SYNTAX SEQUENCE OF SipTermStatsP15mEntry
				ACCESS not-accessible
				STATUS mandatory
				DESCRIPTION
						"This table contains the previous 15 minutes sip term statistics.
						The table is auto-created. A row is associated with a row in sipTerminationTable
						At the end of 15 minutes interval, the current 15 minutes interval contents are copied to the 
						recent previous interval. Up to 96 previous 15 minutes intervals are supported for each sip
						termination.
						The registers associated with a SIP termination connected to a particular voice LT board 
						shall be set to '0' when this voice LT board has restarted
						In addition 
						- The Invalid data flag shall be set to 'True' to indicate that the results shown 
						   for this interval are invalid. 
						- The measured time shall be set to '0'.
						Summarized : measuredTime: 0, invalidData: True, counter: 0.
			
						7302/7330 ISAM-V : Supported
						7363 NGVR : Supported
						7367 SX : Supported
			
			 	ALCATEL NOTE: 
				SUPPORT:  YES
			  TABLESIZE:  DEP [NumOfLT * NumOfLinesPerLT * 96]
			"
  ::= { sipStatisticsAndData 3 }

    sipTermStatsP15mEntry OBJECT-TYPE
				SYNTAX SipTermStatsP15mEntry
				ACCESS not-accessible
				STATUS mandatory
				DESCRIPTION
						"The entry in the sipTermStatsP15mTable.
				ALCATEL NOTE:
				SUPPORT:  YES
			"
	      INDEX { ifIndex, sipTermStatsP15mIntervalNumber }
  ::= { sipTermStatsP15mTable 1 }

    SipTermStatsP15mEntry ::=
				SEQUENCE { 
						sipTermStatsP15mIntervalNumber 			INTEGER,
						sipTermStatsP15mMeasuredTime			INTEGER,
						sipTermStatsP15mInvalidDataFlag			INTEGER,
						sipTermStatsP15mTotalSendPackets			Counter,
						sipTermStatsP15mTotalSendOctets			Counter,
						sipTermStatsP15mTotalReceivePackets			Counter,
						sipTermStatsP15mTotalReceiveOctets			Counter,
						sipTermStatsP15mTotalLostPackets			INTEGER,
						sipTermStatsP15mAvgJBFL				INTEGER,
						sipTermStatsP15mAvgInterArrivalJitter			Gauge,
						sipTermStatsP15mAvgRoundTripDelay			Gauge,
						sipTermStatsP15mPeakInterArrivalJitter			Gauge,
						sipTermStatsP15mPeakRoundTripDelay			Gauge,
						sipTermStatsP15mAvgJBFLG711A			INTEGER,
						sipTermStatsP15mAvgJBFLG711U			INTEGER,
						sipTermStatsP15mAvgJBFLG723				INTEGER,
						sipTermStatsP15mAvgJBFLG729				INTEGER,
						sipTermStatsP15mRegisterReqSuccessful		INTEGER,
						sipTermStatsP15mRegisterReqFailed			INTEGER,
						sipTermStatsP15mRegistrationsActive			INTEGER,
						sipTermStatsP15mOutgoingCallsAnswered		INTEGER,
						sipTermStatsP15mIncomingCallsAnswered		INTEGER,
						sipTermStatsP15mTimeStamp		        NetworkTimeInSeconds,
                        sipTermStatsP15mOutCallAtt              INTEGER,
                        sipTermStatsP15mOutCallSeizDur          INTEGER,
                        sipTermStatsP15mInCallAtt               INTEGER,
                        sipTermStatsP15mInCallSeizDur           INTEGER,
                        sipTermStatsP15mExpRtpPkts              Counter,
                        sipTermStatsP15mAccRtpPkts              Counter,
                        sipTermStatsP15mDiscRtpPkts             Counter,
                        sipTermStatsP15mELArrRtpPkts            Counter,
                        sipTermStatsP15mPortRegDur              INTEGER,
                        sipTermStatsP15mPortAvailDur            INTEGER,
                        sipTermStatsP15mOutFailLostSeiz         INTEGER,
                        sipTermStatsP15mInFailLostSeiz          INTEGER,
                        sipTermStatsP15mOutSuccInitInv          INTEGER
			      }

		sipTermStatsP15mIntervalNumber OBJECT-TYPE
				SYNTAX INTEGER(1..96)
				ACCESS not-accessible
				STATUS mandatory
				DESCRIPTION
						"A number between 1 and 96, which identifies the interval for which the set of statistics is available.
						The interval identified by I is the most recently completed 15 minutes interval, and the interval identified by N
						is the interval immediately preceding the one identified by N-1.
				ALCATEL-LUCENT NOTE:
				ACCESS:	NOT-ACCESSIBLE
				USAGE:	NA
				PERSIST:	NO
				INSRVMOD:	NA
				RANGE:	(1..96)
				DEFVALUE: 	NA
				UNITS:	NA
		    SPARSE:	NA
			"
	::= { sipTermStatsP15mEntry 1 }

		sipTermStatsP15mMeasuredTime OBJECT-TYPE
				SYNTAX INTEGER
				ACCESS read-only
				STATUS mandatory
				DESCRIPTION
						"The amount of time, measured in seconds, that statistics for this entry have been counted.
				ALCATEL-LUCENT NOTE:
				ACCESS:	READ-ONLY
				USAGE:	NA
				PERSIST:	NO
				INSRVMOD:	NA
				RANGE:	NA
				DEFVALUE: 	NA
				UNITS:	Second
		    SPARSE:	NA
			"
	::= { sipTermStatsP15mEntry 2 }

		sipTermStatsP15mInvalidDataFlag OBJECT-TYPE
				SYNTAX INTEGER(0..1)
				ACCESS read-only
				STATUS mandatory
				DESCRIPTION
						"This object indicates the validity of the corresponding PM data.
						It is set to 1 when the PM data is incomplete or invalid and set to 0 when the PM data is complete and valid.
				ALCATEL-LUCENT NOTE:
				ACCESS:	READ-ONLY
				USAGE:	NA
				PERSIST:	NO
				INSRVMOD:	NA
				RANGE:	(0..1)
				DEFVALUE: 	NA
				UNITS:	NA
		    SPARSE:	NA
			"
	::= { sipTermStatsP15mEntry 3 }

		sipTermStatsP15mTotalSendPackets OBJECT-TYPE
				SYNTAX Counter
				ACCESS read-only
				STATUS mandatory
				DESCRIPTION
			      "The total amount of RTP packets transmitted by this SIP termination in this interval.
				ALCATEL-LUCENT NOTE:
				ACCESS:	READ-ONLY
				USAGE:	NA
				PERSIST:	NO
				INSRVMOD:	NA
				RANGE:	NA
				DEFVALUE: 	NA
				UNITS:	Packets
		    SPARSE:	NA
			"
  ::= { sipTermStatsP15mEntry 4 }

		sipTermStatsP15mTotalSendOctets OBJECT-TYPE
				SYNTAX Counter
				ACCESS read-only
				STATUS mandatory
				DESCRIPTION
			      "The total amount of RTP octets transmitted by this SIP termination in this interval.
				ALCATEL-LUCENT NOTE:
				ACCESS:	READ-ONLY
				USAGE:	NA
				PERSIST:	NO
				INSRVMOD:	NA
				RANGE:	NA
				DEFVALUE: 	NA
				UNITS:	Octets
		    SPARSE:	NA
			"
	::= { sipTermStatsP15mEntry 5 }

		sipTermStatsP15mTotalReceivePackets OBJECT-TYPE
				SYNTAX Counter
				ACCESS read-only
				STATUS mandatory
				DESCRIPTION
						"The total amount of RTP packets received by this SIP termination in this interval.
				ALCATEL-LUCENT NOTE:
				ACCESS:	READ-ONLY
				USAGE:	NA
				PERSIST:	NO
				INSRVMOD:	NA
				RANGE:	NA
				DEFVALUE: 	NA
				UNITS:	Packets
		    SPARSE:	NA
			"
  ::= { sipTermStatsP15mEntry 6 }

		sipTermStatsP15mTotalReceiveOctets OBJECT-TYPE
				SYNTAX Counter
				ACCESS read-only
				STATUS mandatory
				DESCRIPTION
			      "The total amount of RTP octets received by this SIP termination in this interval.
				ALCATEL-LUCENT NOTE:
				ACCESS:	READ-ONLY
				USAGE:	NA
				PERSIST:	NO
				INSRVMOD:	NA
				RANGE:	NA
				DEFVALUE: 	NA
				UNITS:	Octets
		    SPARSE:	NA
			"
  ::= { sipTermStatsP15mEntry 7 }

		sipTermStatsP15mTotalLostPackets OBJECT-TYPE
				SYNTAX INTEGER
				ACCESS read-only
				STATUS mandatory
				DESCRIPTION
						"The total amount of lost RTP packets for this SIP termination in this interval.  The amount of packets lost is defined to be the amount of packets expected less the amount of packets actually received:
									lost = expected - s->received;
									Since this signed number is carried in 24 bits, it should be clamped at 0x7fffff for positive loss or 0x800000 for negative loss rather than wrapping around.
				ALCATEL-LUCENT NOTE:
				ACCESS:	READ-ONLY
				USAGE:	NA
				PERSIST:	NO
				INSRVMOD:	NA
				RANGE:	NA
				DEFVALUE: 	NA
				UNITS:	Packets
		    SPARSE:	NA
			"
  ::= { sipTermStatsP15mEntry 8 }

		sipTermStatsP15mAvgJBFL OBJECT-TYPE
				SYNTAX INTEGER(0..100)
				ACCESS read-only
				STATUS mandatory
				DESCRIPTION
						"Average Jitter Buffer Fill Level Percentage measured for both, originating and terminating calls at a 
						SIP termination (incoming direction of RTP packets only) in this interval.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
  ::= { sipTermStatsP15mEntry 9 }

		sipTermStatsP15mAvgInterArrivalJitter OBJECT-TYPE
				SYNTAX Gauge
				ACCESS read-only
				STATUS mandatory
				DESCRIPTION
			      "Average inter-arrival Jitter measured for this SIP termination in one interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
  ::= { sipTermStatsP15mEntry 10 }

		sipTermStatsP15mAvgRoundTripDelay OBJECT-TYPE
				SYNTAX Gauge
				ACCESS read-only
				STATUS mandatory
				DESCRIPTION
			      "Average round-trip delay measured for this SIP termination in one interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
  ::= { sipTermStatsP15mEntry 11 }

		sipTermStatsP15mPeakInterArrivalJitter OBJECT-TYPE
				SYNTAX Gauge
				ACCESS read-only
				STATUS mandatory
				DESCRIPTION
			      "Peak inter-arrival Jitter measured for this SIP termination in one interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
  ::= { sipTermStatsP15mEntry 12 }

		sipTermStatsP15mPeakRoundTripDelay OBJECT-TYPE
				SYNTAX Gauge
				ACCESS read-only
				STATUS mandatory
				DESCRIPTION
			      "Peak round-trip delay measured for this SIP termination in one interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
  ::= { sipTermStatsP15mEntry 13 }

		sipTermStatsP15mAvgJBFLG711A OBJECT-TYPE
				SYNTAX INTEGER(0..100)
				ACCESS read-only
				STATUS mandatory
				DESCRIPTION
						" Average Jitter Buffer Fill Level measured at this SIP termination during the receipt of an RTP 
						stream encoded with G711_a in the course of a single interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
  ::= { sipTermStatsP15mEntry 14 }

		sipTermStatsP15mAvgJBFLG711U OBJECT-TYPE
				SYNTAX INTEGER(0..100)
			  ACCESS read-only
				STATUS mandatory
				DESCRIPTION
						" Average Jitter Buffer Fill Level measured at this SIP termination during the receipt of an RTP 
						stream encoded with G711_u in the course of a single interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
  ::= { sipTermStatsP15mEntry 15 }

		sipTermStatsP15mAvgJBFLG723 OBJECT-TYPE
				SYNTAX INTEGER(0..100)
				ACCESS read-only
				STATUS mandatory
				DESCRIPTION
						" Average Jitter Buffer Fill Level measured at this SIP termination during the receipt of an RTP 
						stream encoded with G723 in the course of a single interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
	::= { sipTermStatsP15mEntry 16 }

		sipTermStatsP15mAvgJBFLG729 OBJECT-TYPE
				SYNTAX INTEGER(0..100)
				ACCESS read-only
				STATUS mandatory
				DESCRIPTION
						" Average Jitter Buffer Fill Level measured at this SIP termination during the receipt of an RTP 
						stream encoded with G729 in the course of a single interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
  ::= { sipTermStatsP15mEntry 17 }

		sipTermStatsP15mRegisterReqSuccessful OBJECT-TYPE
				SYNTAX INTEGER
				ACCESS read-only
				STATUS mandatory
				DESCRIPTION
			      " The amount of (re-)registration requests which are successfully replied in this recent 15min Interval. Successfully replied means that a response = 200 OK with expire header time = 0 or expire header <> 0 has been returned by the Registrar.
				ALCATEL-LUCENT NOTE:
				ACCESS:	READ-ONLY
				USAGE:	NA
				PERSIST:	NO
				INSRVMOD:	NA
				RANGE:	NA
				DEFVALUE: 	NA
				UNITS:	Number
		    SPARSE:	NA
			"
  ::= { sipTermStatsP15mEntry 18 }

		sipTermStatsP15mRegisterReqFailed OBJECT-TYPE
				SYNTAX INTEGER
				ACCESS read-only
				STATUS mandatory
				DESCRIPTION
						" The amount of (re-)registration requests which failed in this recent 15 min interval. 
						Failed means that a response <> 200 OK was retruned by the SIP First Hop server / Registrar or that SIP transaction time-out occured.
				ALCATEL-LUCENT NOTE:
				ACCESS:	READ-ONLY
				USAGE:	NA
				PERSIST:	NO
				INSRVMOD:	NA
				RANGE:	NA
				DEFVALUE: 	NA
				UNITS:	Number
		    SPARSE:	NA
			"
  ::= { sipTermStatsP15mEntry 19 }

		sipTermStatsP15mRegistrationsActive OBJECT-TYPE
				SYNTAX INTEGER
				ACCESS read-only
				STATUS mandatory
				DESCRIPTION
						" The amount of registrations being active at a subscriber port at the end of the recent 15 min
						interval. In the current implementation, only 1 registration can be active at a subscriber port at a
						time. An active registration is counted when a registration request has been successfully completed in the past
						(200 OK received to register request with 'expire header' time <> 0) and the register expiration interval
						hasn't expired.
				ALCATEL-LUCENT NOTE:
				ACCESS:	READ-ONLY
				USAGE:	NA
				PERSIST:	NO
				INSRVMOD:	NA
				RANGE:	NA
				DEFVALUE: 	NA
				UNITS:	Number
		    SPARSE:	NA
			"
  ::= { sipTermStatsP15mEntry 20 }

		sipTermStatsP15mOutgoingCallsAnswered OBJECT-TYPE
				SYNTAX INTEGER
				ACCESS read-only
				STATUS mandatory
				DESCRIPTION
						" The amount of outgoing call attempts in this recent 15 min interval for which an initial INVITE
						request is sent AND for which a response is received. The system allows to provision what kind of response
						must be received as to be counted as a successful outgoing call attempt. The system offers the following
						options : 
						o Any response be received (irrespective of whether this is a successful or unsuccessful response). 
						o A successful response be received (180 or 200 response only).
				ALCATEL-LUCENT NOTE:
				ACCESS:	READ-ONLY
				USAGE:	NA
				PERSIST:	NO
				INSRVMOD:	NA
				RANGE:	NA
				DEFVALUE: 	NA
				UNITS:	Number
		    SPARSE:	NA
			"
  ::= { sipTermStatsP15mEntry 21 }

		sipTermStatsP15mIncomingCallsAnswered OBJECT-TYPE
				SYNTAX INTEGER
				ACCESS read-only
				STATUS mandatory
				DESCRIPTION
						" The amount of incoming call attempts in this recent 15 min interval for which a SIP response
						is sent being the result of the off-hook event been detected. The system allows to provision the kind of
						response that will be considered as to be counted as a successful incoming call attempt. The system offers the
						following options : 
						o Any response be sent. 
						o 180 response be sent.
                                                o 200 response be sent.
				ALCATEL-LUCENT NOTE:
				ACCESS:	READ-ONLY
				USAGE:	NA
				PERSIST:	NO
				INSRVMOD:	NA
				RANGE:	NA
				DEFVALUE: 	NA
				UNITS:	Number
		    SPARSE:	NA
			"
  ::= { sipTermStatsP15mEntry 22 }

         sipTermStatsP15mTimeStamp OBJECT-TYPE
                       SYNTAX NetworkTimeInSeconds
                       ACCESS read-only
                       STATUS mandatory
                       DESCRIPTION
                        "The value of sipTermStatsP15mTimeStamp indicating the time stamp of start time for termination statistic of per 15 minutes.
                       ALCATEL-LUCENT NOTE:
                       ACCESS: READ-ONLY
                       USAGE: NA
                       PERSIST: NO
                       INSRVMOD: NA
                       RANGE: (0..4294967295)
                       DEFVALUE: 0
                       UNITS:  seconds
                       SPARSE: NA
                               "
   ::= { sipTermStatsP15mEntry 23 }

        sipTermStatsP15mOutCallAtt OBJECT-TYPE
                SYNTAX INTEGER
                ACCESS read-only
                STATUS mandatory
                DESCRIPTION
                    " The number of off-hooks being detected and considered as being the starting event to make an outgoing call attempt (The detection of an off-hook event as the result of  an incoming call attempt must not be considered).
                    This counter counts both, the off-hook events detected as being the starting event of a outgoing call attempt in the scope of a  basic call and the Hook-flashes as being the starting event of a new outgoing call attempt in the scope of a conference call.

                ALCATEL-LUCENT NOTE:
                ACCESS: READ-ONLY
                USAGE:  NA
                PERSIST:    NO
                INSRVMOD:   NA
                RANGE:  NA
                DEFVALUE:   NA
                UNITS:  Number
                SPARSE: NA
                "
    ::= { sipTermStatsP15mEntry 24 }

    sipTermStatsP15mOutCallSeizDur  OBJECT-TYPE
                SYNTAX INTEGER
                ACCESS read-only
                STATUS mandatory
                DESCRIPTION
                        " The port seizure time for outgoing call attempts. This counter is only applicable to the outgoing call attempts whereby  the subscriber dials a valid digit before the starting dial timer expiry. (With valid digit is to be understood a digit that at least partially matches one digit map pattern in the configured digit map.)
                        This counter is not applicable to outgoing call attempts that are abnormally ended due to a subscriber action (before the starting dial timer expiry)  or  whereby no dial tone could be put at the line or whereby the system interrupts the outgoing call attempt before the subscriber is even able to dial a first digit.

                        Basic call :
                        The port seizure time is measured from the receipt of the off-hook event till the receipt of the first valid dialed digit.

                        Conference call :  
                        The port seizure time is measured from the moment the MSAN requests the HW to put special dial tone at the line till the receipt of the first valid dialed digit.

                        Call Transfer : 
                        Two types of the Call Transfer Service are supported : the UNATTENDED call transfer service and the ATTENDED call transfer service. 

                        Unattended Call Transfer Service : 
                            Subscriber A establishes a basic call with subscriber B.
                            Subscriber A performs flash hook and dials  service SOC followed by DN of C. 
                            This causes subscriber A to enter the releasing state. Ringing tone is put on the line of subscriber C.
                            When C goes off-hook, a basic call is established between subscribers B and C. 
                            For subscriber A, transferring the call to subscriber C, outgoingCallSeizureDur is measured
                                   from the receipt of the flash hook till the receipt of the first valid dialed digit.

                        Attended Call Transfer Service :
                            Subscriber A establishes a basic call with subscriber B.
                            Subscriber A performs flash hook and dials subscriber C's DN.
                            Ringing tone is put on subscriber C's line.
                            Subscriber C goes off-hook and subscribers B and C are connected.
                            Subscriber A performs flash hook and dials SOC.
                            A basic call is established between subscribers B and C. Subscriber A is put in releasing state.
                            For subscriber A, transferring the call to subscriber C, outgoingCallSeizureDur is measured from the receipt of the flash hook till the receipt of the first valid dialed digit.

                        Call Forwarding :
                            Subscriber A did activate Call Forwarding to subscriber B.
                            Subscriber C goes off-hook and dials subscriber A's DN.
                            Ringing tone is put on subscriber B's line. 
                            Subscriber B goes off-hook; a basic call is established between subscribers C and B. 
                            For subscriber C outgoingCallSeizureDur is measured from the receipt of the off-hook event till the receipt of the first valid dialed digit. 

                ALCATEL-LUCENT NOTE:
                ACCESS: READ-ONLY
                USAGE:  NA
                PERSIST:    NO
                INSRVMOD:   NA
                RANGE:  NA
                DEFVALUE:   NA
                UNITS:  Seconds
                SPARSE: NA
                "
    ::= { sipTermStatsP15mEntry 25 }

    sipTermStatsP15mInCallAtt OBJECT-TYPE
                SYNTAX INTEGER
                ACCESS read-only
                STATUS mandatory
                DESCRIPTION
                        " The total number of incoming SIP INVITE requests, considered as being a SIP INVITE request for a new incoming call attempt, and this regardless of whether the incoming call attempt has successfully been processed / replied or not.
                        A SIP INVITE request being the retransmission of a SIP INVITE request already been handled (and counted) shall NOT be counted once again.
                        It shall be noted that the count of the incoming SIP INVITE request may not be fully correct :
                        - Incoming SIP INVITE messages dropped at a layer beneath the SIP stack layer cannot be counted. (e.g. high load situations)
                        - Incoming SIP INVITE messages without CSEQ are silently dropped by the SIP stack. Since the calling side does not receive a response to such SIP INVITE request, the calling side will retry the SIP INVITE. At the called site the SIP stack cannot know whether such SIP INVITE requests are retry messages or not. Thus the counter will be increased for the first SIP INVITE request been received as well as for the subsequent SIP INVITE retries been received.

                ALCATEL-LUCENT NOTE:
                ACCESS: READ-ONLY
                USAGE:  NA
                PERSIST:    NO
                INSRVMOD:   NA
                RANGE:  NA
                DEFVALUE:   NA
                UNITS:  Number
                SPARSE: NA
                "
    ::= { sipTermStatsP15mEntry 26 }

    sipTermStatsP15mInCallSeizDur OBJECT-TYPE
                SYNTAX INTEGER
                ACCESS read-only
                STATUS mandatory
                DESCRIPTION
                        " The  port seizure time for incoming call attempts. The port seizure duration is the time elapsed from the moment the called subscriber gets notified that an incoming call attempt has arrived (ringing / call-waiting tone put at the line  till one of the following events is detected :
                            - the receipt of the off-hook or 
                            - the receipt of the flash-hook event or
                            - the receipt of the SIP CANCEL request or
                            - the expiry of the ringing tone sequence or
                            - the expiry of the (call forwarding no reply) No Answer Timeout or
                            - the receipt of the call-waiting tone sequence. 
                             - the transmission of a 487 Request Terminated (without sending SIP CANCEL request) by the called side before the expiry of the ringing tone (the called side gets e.g. physical failure or the admin-status set to down).
                        SIP CANCEL Request : The ringing / call-waiting tone timer pre-provisioned in the MSAN's CDE file can be different from the Request response outage timer provisioned at the SIP  Server.
                        In case the ringing / call-waiting timer pre-provisioned in the MSAN's CDE file, the Request response outage timer provisioned at the SIP Server, the calling subscriber shall receive the 487 Request Terminated response while the called subscriber shall receive the CANCEL request from the SIP Server and this before the expiry of the ringing / call-waiting tone timer at the MSAN.
                        Upon the receipt of the CANCEL request, the ringing / call-waiting tone is stopped.
                        In this case the port seizure duration is the time elapsed from the moment the called subscriber gets notified that an incoming call attempt has arrived (ringing / call-waiting tone put at the line  till the receipt of the CANCEL request.
              
                        Idle line - Basic call :
                        The port seizure time is measured from the moment the ringing tone is put at the line till
                            - the receipt of the off-hook or
                            - the receipt of the SIP CANCEL request or
                            - the expiry of the ringing tone sequence
             
                        Ongoing call - Call waiting :
                        The port seizure time is measured from the moment the call-waiting tone is put at the line till
                            - the receipt of the flash hook (followed by the SOC that accepts the waiting call) or
                            - the expiry of the call-waiting tone sequence or
                            - the receipt of te SIP CANCEL request or
                            - the receipt of the off-hook event in the following scenario : Call-waiting tone put at the line of subscriber X; subscriber X goes on-hook; (call waiting tone timer still not expired); 
                                Ringing tone put a subscriber X's line; subscriber X goes off-hook.

                        Call Waiting : Case_1 :
                            Subscriber A goes off-hook and dials subscriber B's DN. 
                            Ringing tone is put at subscriber B's line at time t0.
                            Subscriber B goes off-hook at time t0+x sec; a basic call is established between subscribers A and B.
                            Subscriber C goes off-hook and dials subscriber A's  DN; subscriber A receives an initial  SIP INVITE request; Call waiting tone is put at subscriber A's line at time t1.
                            Subscriber A goes on-hook at time t1+y sec. (Call waiting tone timer still not expired) Subscriber B will be releasing. Ringing tone is put at subscriber A's line;  subscriber A goes off-hook at time t1+ z sec; a basic call is established between subscribers A & C.
                            For subscriber B incomingCallSeizureDur is measured from the moment the ringing tone is put at subscriber B line till the receipt of the off-hook event. (x sec)(subscriber A calls subscriber B).
                                For subscriber A, incomingCallSeizureDur is measured from the moment the call waiting tone is put at subscriber B's line till the receipt of the off-hook event. (z sec)

                        Call Waiting : Case_2 :
                            Subscriber A goes off-hook and dials subscriber B's DN. 
                            Ringing tone is put at subscriber B's line at time t0.
                            Subscriber B goes off-hook at time t0+x sec; A basic call is established between subscribers A and B.
                            Subscriber A pushes the flash-hook and dials subscriber C's DN.
                            Ringing tone is put at subscriber C's line at time t1.
                            Subscriber A goes on-hook. Subscriber C receives Cancel request at time t1+y sec;
                            Ringing tone is put at subscriber A's line. Subscriber A goes off-hook at time t1+ z sec;
                            The call between subscribers A and B is resumed.
                                 For subscriber B incomingCallSeizureDur is measured from the moment the ringing tone is
                                     put at subscriber B's line till the receipt of the off-hook event. (x sec)(subscriber A calls subscriber B).
                                 For subscriber C incomingCallSeizureDur is measured from the moment the ringing tone
                                     is put at subscriber C's line till the receipt of the SIP CANCEL request (y sec).
                                 For subscriber A (point 4) incomingCallSeizureDur measurement is not applicable as it
                                     concerns the resume of a previously established call and which was temporarily put on hold.
             
                        Call Transfer :
                        Two types of the Call Transfer Service are supported : the UNATTENDED call transfer service and the ATTENDED call transfer service.
             
                        Unattended Call Transfer Service :
                            Subscriber A establishes a basic call with subscriber B.
                            Subscriber A performs flash hook and dials service SOC followed by C's DN.
                            This causes subscriber A to enter the releasing state. Ringing tone is put on the line of subscriber C.
                            When C goes off-hook, a basic call is established between subscribers B and C.
                            For subscribe C, the called subscriber, it is considered a basic call process.
                                 For subscriber B incomingCallSeizureDur is measured from the moment the ringing tone is put at subscriber B's line till the receipt of the off-hook event. (subscriber A calls subscriber B).
                                 For subscriber C incomingCallSeizureDur is measured from the moment the ringing tone is put at subscriber C's line till the receipt of the off-hook event. (subscriber A transfers the call to subscriber C).
              
                        Attended Call Transfer Service :
                            Subscriber A establishes a basic call with subscriber B.
                            Subscriber A performs flash hook and dials subscriber C's DN.
                            Ringing tone is put on subscriber C's line.
                            Subscriber C goes off-hook and subscribers B and C are connected.
                            Subscriber A performs flash hook and dials SOC.
                            A basic call is established between subscribers B and C. Subscriber A is put in releasing state.
                                For subscriber B, incomingCallSeizureDur is measured from the moment the ringing tone is put at subscriber B's line till the receipt of the off-hook event. (subscriber A calls subscriber B).
                                For subscriber C,incomingCallSeizureDur is measured from the moment the ringing tone is put at subscriber C's line till the receipt of the off-hook event. (subscriber A calls subscriber C).
             
                        Call Forwarding :
                        The system supports 3 types of Call Forwarding :  Call Forwarding Unconditional, Call Forwarding No Reply and Call Forwarding Busy.
             
                        Call Forwarding Unconditional : (all incoming calls are unconditionally forwarded)
                            Subscriber A has enabled Call Forwarding Unconditional to subscriber B.
                            Subscriber C goes off-hook and dials subscriber A's DN; The line of subscriber B will be ringing.
                            Subscriber B goes off-hook; A basic call is  established between subscribers B and C. 
                                 For subscriber B, incomingCallSeizureDur is measured from the moment the ringing tone is put at subscriber B's line till the receipt of the off-hook event. (subscriber C calls subscriber B).
                                 For subscriber A, no port seizure time is measured.
             
                        Call  Forwarding No Reply : (an incoming call is forwarded on the condition that it gets not answered by the called subscriber)
                            Subscriber A has enabled Call Forwarding No Reply to subscriber Line B.
                            Subscriber C goes off-hook and dials subscriber A's DN; The line of subscriber A will be ringing.
                            Subscriber A does not go off-hook upon timer expiry; Call is forwarded to subscriber B; The line of subscriber B is ringing.
                            Subscriber B goes off-hook; a basic call is established between subscribers B and C.
                                For subscriber A, incomingCallSeizureDur is measured from the moment the ringing tone is
                                     put at subscriber A's line till the expiry of the (Call forwarding No Reply) No Answer Timeout. (Ringing tone is stopped at subscriber A's line)
                                 For subscriber B, incomingCallSeizureDur is measured from the moment the ringing tone is
                                     put at subscriber B's line till the receipt of the off-hook event. (subscriber C calls subscriber B).
                        
                        Call Forwarding Busy case :
                            Subscriber A has enabled Call Forwarding Busy to subscriber B.
                            Subscriber A goes off-hook and establishes a call to subscriber D.
                            Subscriber C goes off-hook and dials subscriber A's DN; The line of subscriber B will be ringing.
                            Subscriber B goes off-hook; a basic call is established between the subscribers B and C.
                                 For subscriber B, incomingCallSeizureDur is measured from the moment the ringing tone is put at subscriber B's line till the receipt of the off-hook event. (subscriber C calls subscriber B).
                                 For subscriber A, no port seizure time is measured.
             
                        When the call has been canceled before the ringing / call-waiting tone is put at the line, no port seizure time is measured.

                ALCATEL-LUCENT NOTE:
                ACCESS: READ-ONLY
                USAGE:  NA
                PERSIST:    NO
                INSRVMOD:   NA
                RANGE:  NA
                DEFVALUE:   NA
                UNITS:      Seconds 
                SPARSE: NA
                "
    ::= { sipTermStatsP15mEntry 27 }

    sipTermStatsP15mExpRtpPkts OBJECT-TYPE
                SYNTAX Counter
                ACCESS read-only
                STATUS mandatory
                DESCRIPTION
                        " The number of RTP packets EXPECTED is defined to be the extended last sequence number received, less the initial sequence number received.
                        The above definition is valid in case the entire RTP stream starts and ends within the same 15 min interval.
                        However for an RTP stream that starts in one 15 min interval and ends in another 15 min interval, the definition of the number of expected packets is a bit different .
                        - The RTP stream starts and ends in the same interval :
                            The number of RTP packets EXPECTED is defined to be the extended last sequence number received, less the initial sequence number received.
                        - The RTP stream starts and ends in a different Interval :
                            - For the interval in which the RTP stream starts :
                                The number of RTP packets expected is defined to be the extended last sequence number received at the end of the 15 min interval, less the initial sequence number received.
                            - For the interval in which the RTP stream  continues :
                                The number of RTP packets expected is defined to be the extended last sequence number received at the end of the 15 min interval, less the initial sequence number received at the beginning of the interval.
                            - For the interval in which the RTP stream ends :
                                The number of RTP packets expected is defined to be the extended last sequence number received, less the initial sequence number received at the beginning of the interval.

                ALCATEL-LUCENT NOTE:
                ACCESS: READ-ONLY
                USAGE:  NA
                PERSIST:    NO
                INSRVMOD:   NA
                RANGE:  NA
                DEFVALUE:   NA
                UNITS:  Packets
                SPARSE: NA
                "
    ::= { sipTermStatsP15mEntry 30 }

    sipTermStatsP15mAccRtpPkts OBJECT-TYPE
                SYNTAX Counter
                ACCESS read-only
                STATUS mandatory
                DESCRIPTION
                        " The number of ACCEPTED RTP packets = the number of expected RTP packets  -  the number of missed RTP packets  -  the number of defect RTP packets  -  the number of doubled RTP packets -  the number of later arrived RTP packets  -  the number of early received RTP packets.
                        Or in other words, the number of ACCEPTED RTP packets  = the number of RTP packets used for voice generation at the receiving side.
                        Since our PM statistics framework is based on a periodically reporting of PM statistics  i.e.  per 15 min interval, for RTP streams that cross the interval boundary, the number of accepted RTP packets must be calculated per 15 min interval.
             
                        The above definition is valid in case the entire RTP stream starts and ends within the same 15 min interval.
                        However for an RTP stream that starts in one 15 min interval and ends in another 15 min interval, the definition of the number of accepted packets is a bit different .
                        The RTP stream starts and ends in the same interval :
                            The number of RTP packets ACCEPTED is defined to be the number of expected RTP packets  -  the number of missed RTP packets  -  the number of defect RTP packets  -  the number of doubled RTP packets -  the number of later arrived RTP packets  -  the number of early received RTP packets.
                        The RTP stream starts and ends in a different Interval :
                            For the interval in which the RTP stream starts :
                                The number of RTP packets ACCEPTED is defined to be the number of expected RTP packets  - the number of missed RTP packets  -  the number of defect RTP packets  -  the number of doubled RTP packets -  the number of later arrived RTP packets  -  the number of early received RTP packets, measure till the end of the interval
                            For the interval in which the RTP stream  continues :
                                The number of RTP packets ACCEPTED is defined to be the number of expected RTP packets  - the number of missed RTP packets  -  the number of defect RTP packets  -  the number of doubled RTP packets -  the number of later arrived RTP packets  -  the number of early received RTP packets, measured from the beginning of the interval till the end of the interval.
                            For the interval in which the RTP stream ends :
                                The number of RTP packets ACCEPTED is defined to be the number of expected RTP packets  - the number of missed RTP packets  -  the number of defect RTP packets  -  the number of doubled RTP packets -  the number of later arrived RTP packets  -  the number of early received RTP packets, measured from the beginning of the interval till the end of the RTP stream.

                ALCATEL-LUCENT NOTE:
                ACCESS: READ-ONLY
                USAGE:  NA
                PERSIST:    NO
                INSRVMOD:   NA
                RANGE:  NA
                DEFVALUE:   NA
                UNITS:  Packets
                SPARSE: NA
                "
    ::= { sipTermStatsP15mEntry 31 }

    sipTermStatsP15mDiscRtpPkts OBJECT-TYPE
                SYNTAX Counter
                ACCESS read-only
                STATUS mandatory
                DESCRIPTION
                        " The number of DISCARDED RTP packets other than late or early arrived = the number of received but not used downstream RTP packets which can be assigned to the port and without early or late package loss = the number of defect RTP packets + the number of duplicated  RTP packets.  (The number of missed RTP packets shall not be considered as these RTP packets were not received.)
                        The above definition is valid in case the entire RTP stream starts and ends within the same 15 min interval.
                        However for an RTP stream that starts in one 15 min interval and ends in another 15 min interval, the definition of the number of expected packets is a bit different .
                        The RTP stream starts and ends in the same interval :
                            The number of RTP packets DISCARDED is defined to be the number of defect RTP packets + the number of duplicated RTP packets.
                        The RTP stream starts and ends in a different Interval :
                            For the interval in which the RTP stream starts :
                                The number of RTP packets discarded is defined to be the number of defect RTP packets  + the number of duplicated RTP packets measured from the beginning of the call till the expiry of the 15 min interval.
                            For the interval in which the RTP stream  continues :
                                The number of RTP packets discarded is defined to be the number of defect RTP packets  + the number of duplicated RTP packets measured from the beginning of the 15 min interval till the expiry of that same 15 min interval.
                            For the interval in which the RTP stream ends :
                                The number of RTP packets discarded is defined to be the number of defect RTP packets  + the number of duplicated RTP packets measured from the beginning of the 15 min interval till the end of the call.

                ALCATEL-LUCENT NOTE:
                ACCESS: READ-ONLY
                USAGE:  NA
                PERSIST:    NO
                INSRVMOD:   NA
                RANGE:  NA
                DEFVALUE:   NA
                UNITS:  Packets
                SPARSE: NA
                "
    ::= { sipTermStatsP15mEntry 32 }

    sipTermStatsP15mELArrRtpPkts OBJECT-TYPE
                SYNTAX Counter
                ACCESS read-only
                STATUS mandatory
                DESCRIPTION
                        " The number of DISCARDED RTP packets due to early or late arrival = the number of received RTP packets which can be assigned to the port but are received too early (Jitter buffer over-flow) or too late (Jitter buffer under-run) and consequently not used for the generation of the voice stream = the number of early received RTP packets + the number late received RTP packets.
                        The above definition is valid in case the entire RTP stream starts and ends within the same 15 min interval.
                        However for an RTP stream that starts in one 15 min interval and ends in another 15 min interval, the definition of the number of expected packets is a bit different .
                        The RTP stream starts and ends in the same interval :
                            The number of DISCARDED EARLY/LATE arrived RTP packets = the number of received RTP packets which can be assigned to the port but are received too early (Jitter buffer over-flow) or too late (Jitter buffer under-run) and consequently not used for the generation of the voice stream = the number of early received RTP packets + the number late received RTP packets.
                        The RTP stream starts and ends in a different Interval :
                            For the interval in which the RTP stream starts :
                                The number of DISCARDED EARLY/LATE arrived RTP packets = the number of received RTP packets which can be assigned to the port but are received too early (Jitter buffer over-flow) or too late (Jitter buffer under-run) and consequently not used for the generation of the voice stream = the number of early received RTP packets + the number late received RTP packets measured from the beginning of the call till the expiry of the 15 min interval.
                            For the interval in which the RTP stream  continues :
                                The number of DISCARDED EARLY/LATE arrived RTP packets = the number of received RTP packets which can be assigned to the port but are received too early (Jitter buffer over-flow) or too late (Jitter buffer under-run) and consequently not used for the generation of the voice stream = the number of early received RTP packets + the number late received RTP packets measured from the beginning of the 15 min interval till the expiry of that same 15 min interval.
                            For the interval in which the RTP stream ends :
                                The number of DISCARDED EARLY/LATE arrived RTP packets = the number of received RTP packets which can be assigned to the port but are received too early (Jitter buffer over-flow) or too late (Jitter buffer under-run) and consequently not used for the generation of the voice stream = the number of early received RTP packets + the number late received RTP packets measured from the beginning of the 15 min interval till the end of the call.

                ALCATEL-LUCENT NOTE:
                ACCESS: READ-ONLY
                USAGE:  NA
                PERSIST:    NO
                INSRVMOD:   NA
                RANGE:  NA
                DEFVALUE:   NA
                UNITS:  Packets
                SPARSE: NA
                "
    ::= { sipTermStatsP15mEntry 33 }

    sipTermStatsP15mPortRegDur OBJECT-TYPE
                SYNTAX INTEGER
                ACCESS read-only
                STATUS mandatory
                DESCRIPTION
                        " The total amount of time that from an MSAN point of view, a SIP termination is considered to be successfully registered at the IMS core.
                        Usually the MSAN registers or de-registers a SIP termination to the IMS core. However, it should be noted that a registration can also autonomously be deleted by the IMS core.  Such registration state change is not explicitly notified to the MSAN (unless the reg event package would be supported and subscribed by the MSAN, which is actually not the case).
                        The total amount of time that from an MSAN point of view, a SIP termination is considered to be successfully registered at the IMS core,  may be different from that same SIP termination to be successfully registered from an IMS core point of view.
                        When the MSAN considers a SIP termination to be successfully registered at the IMS core, its operational state is set to UP.
                        When the MSAN considers a SIP termination not to be registered at the IMS core, its operational state is set to down.
                        The port registration duration counter of a particular SIP termination shall start counting upon the receipt of the 200 OK to the initial registration request for that same SIP termination.
                        The registerDur counting for a particular SIP termination shall stop  :
                         upon the receipt of the 200 OK to the de-registration request for that same SIP termination.
                            (A de-registration request is sent as a consequence of the following actions : SIP Termination Admin state change from up to down, SIP User Agent Admin state change from up to down, SIP User Agent Access Point Admin state change from up to down, VSP Admin state change from up to down, Ground key / Port High temperature alarm raised at the port, ...etc.)
                         Upon Fail-back, requiring a de-register of the SIP terminations at the secondary SIP server.
                         Upon Deliberate Update, requiring a de-register of the SIP terminations at the current Primary SIP server.
                         Upon the receipt of an error response to a SIP RE-REGISTER request, with one of the following error codes: 408 (Request Timeout), 500 (Server Internal Error), 503 (Service Unavailable), 504 (Server Time-Out) or 600 (Busy Everywhere) response.
                         Upon the detection of a non-recoverable error requiring a fail-over and requiring a new initial registration to be done to the secondary SIP server.
                         Upon the receipt of an error response to a SIP INVITE request, with an error code for which the SSP has been provisioned with an error-code clause that, as recovery action,  requires a new initial register to be sent.
                        It shall be noted that in case the SIP termination is still registered at the IMS while its operational state at the MSAN side is set to disabled (meaning that the MSAN considers that same SIP termination as being NOT registered ) or no longer configured, that upon the receipt of an incoming SIP Invite request for that same SIP
                        termination the following error response is returned :
             
                        INVITE(User-x)  404 Not Found       user-x is not configured (user not linked to any SIP termination )
                        INVITE(User-x)  404 Not Found       user-x has been deleted (sip termination deleted)
                        INVITE          480 Temporarily     Unavailable user-x is configured though is not registered 
                                                            (operational status = down, reason= registering/registerfailure) though port is admin=up
                        INVITE          480 Temporarily     Unavailable user-x is configured though SIP termination is admin-down
                        INVITE          480 Temporarily     Unavailable user-x is configured though SIP termination is FAULTY (ground key alarm)


                ALCATEL-LUCENT NOTE:
                ACCESS: READ-ONLY
                USAGE:  NA
                PERSIST:    NO
                INSRVMOD:   NA
                RANGE:  NA
                DEFVALUE:   NA
                UNITS:  Seconds
                SPARSE: NA
            "
    ::= { sipTermStatsP15mEntry 34 }

    sipTermStatsP15mPortAvailDur OBJECT-TYPE
                SYNTAX INTEGER
                ACCESS read-only
                STATUS mandatory
                DESCRIPTION
                        " The total amount of time a port is considered to be administratively available.
                        This is the time that all, the port's administrative state as well as its higher layer object's administrative status (SIP User Agent admin state, SIP User Agent Access Point admin state, Voice Service Provider admin state) are all set to unlocked. 
                        Or in other words, from the moment that at least one of the above mentioned 4 administrative states is changed to locked, the system shall stop counting for the AvailableDur counter, as the port is considered to be not available from that moment onwards.

                ALCATEL-LUCENT NOTE:
                ACCESS: READ-ONLY
                USAGE:  NA
                PERSIST:    NO
                INSRVMOD:   NA
                RANGE:  NA
                DEFVALUE:   NA
                UNITS:  Seconds
                SPARSE: NA
                "
    ::= { sipTermStatsP15mEntry 35 }

    sipTermStatsP15mOutFailLostSeiz OBJECT-TYPE
                SYNTAX INTEGER
                ACCESS read-only
                STATUS mandatory
                DESCRIPTION
                "The number of outgoing call attempts been made that could not successfully be completed  because of  a
                    lost seizure with the control network.
                    Or in other words, the number of outgoing call attempts that fail because of an access failure to the voice
                    network :
                    - Failing/aborted  TCP connection
                    - Timer B expiry
                    An outgoing call attempt that could not successfully completed because of an erroneous or abnormal
                    subscriber behavior (no dialing incl, incomplete dialing, early on-hook) shall not be consider by this
                    counter.
                    This applies to both, outgoing calls made in the scope of the basic call and outgoing call attempts made in
                     the scope of the conference call
                    This counter will be implemented in R55.
                ALCATEL-LUCENT NOTE:
                ACCESS: READ-ONLY
                USAGE:  NA  
                PERSIST:    NO
                INSRVMOD:   NA
                RANGE:  NA
                DEFVALUE:   NA
                UNITS:  Number
                SPARSE: NA
                "
    ::= { sipTermStatsP15mEntry 39 }

    sipTermStatsP15mInFailLostSeiz OBJECT-TYPE
                SYNTAX INTEGER
                ACCESS read-only
                STATUS mandatory
                DESCRIPTION
                "The number of received incoming call attempts that could not successfully be completed  because of  a lost
                    seizure with the control network. 
                    Or in other words, the number of incoming call attempts that fail because of an access failure to the voice
                    network :
                    - Failing/aborted  TCP connection
                    - Timer B expiry
                    An incoming call attempt that could not successfully be completed because of an erroneous or abnormal
                    subscriber behavior (early on-hook) shall not be consider by this counter.
                    This counter will be implemented in R55.

                    ALCATEL-LUCENT NOTE:
                ACCESS: READ-ONLY
                USAGE:  NA
                PERSIST:    NO
                INSRVMOD:   NA
                RANGE:  NA
                DEFVALUE:   NA
                UNITS:  Number
                SPARSE: NA
                "
    ::= { sipTermStatsP15mEntry 46 }

    sipTermStatsP15mOutSuccInitInv OBJECT-TYPE
                SYNTAX INTEGER
                ACCESS read-only
                STATUS mandatory
                DESCRIPTION
                        " The number of initial SIP INVITE requests that are replied by the IMS core with a 100-Trying followed by A 180-Ringing Provisional Response or A 183-Session Progress Provisional Response, A 200 OK (18x Provisional Response in between the receipt of the 100-trying and the 200 OK). The system does not take into account what response is subsequently received after the 180-ringing / 183-Session Progress has been received.This applies to both, outgoing call attempts made in the scope of the basic call and outgoing call attempts made in the scope of a supplementary service.

                ALCATEL-LUCENT NOTE:
                ACCESS: READ-ONLY
                USAGE:  NA  
                PERSIST:    NO
                INSRVMOD:   NA
                RANGE:  NA
                DEFVALUE:   NA
                UNITS:  Number
                SPARSE: NA
                "
    ::= { sipTermStatsP15mEntry 51 }


-- =============================================================================
-- 
-- Sip Term Stats C15m Table
--=============================================================================

		sipTermStatsC15mTable OBJECT-TYPE
				SYNTAX SEQUENCE OF SipTermStatsC15mEntry
				ACCESS not-accessible
				STATUS mandatory
				DESCRIPTION
						"This table contains the current 15 minute sip term statistics.
						When an entry is created in the SIP termination table, a row for this termination is auto-created in this SIP 
						Termination Statistics Table.
						When an entry is deleted in the SIP termination table, the corresponding entry in this table is auto-deleted.
						At the end of 15 minutes interval, the current 15 minutes interval contents are copied to the recent previous interval.
						The registers associated with this SIP termination connected to a particular voice LT board shall be 
						set to '0' when this voice LT board has restarted
						In addition 
									- The Invalid data flag shall be set to 'False' 
									- The measured time shall be set to '0'.
						Summarized : measuredTime: 0, invalidData: False, counter: 0.
						
						7302/7330 ISAM-V : Supported
						7363 NGVR : Supported
						7367 SX : Supported
			
				ALCATEL NOTE: 
				SUPPORT:  YES
				TABLESIZE:  DEP [NumOfLT * NumOfLinesPerLT]
		  "
  ::= { sipStatisticsAndData 4 }

		sipTermStatsC15mEntry OBJECT-TYPE
				SYNTAX SipTermStatsC15mEntry
				ACCESS not-accessible
				STATUS mandatory
				DESCRIPTION
						"The entry in the sipTermStatsC15mTable.
				ALCATEL NOTE:
				SUPPORT:  YES
			"
				INDEX { ifIndex }
  ::= { sipTermStatsC15mTable 1 }

		SipTermStatsC15mEntry ::=
				SEQUENCE { 
						sipTermStatsC15mMeasuredTime			INTEGER,
						sipTermStatsC15mInvalidDataFlag			INTEGER,
						sipTermStatsC15mTotalSendPackets			Counter,
						sipTermStatsC15mTotalSendOctets			Counter,
						sipTermStatsC15mTotalReceivePackets			Counter,
						sipTermStatsC15mTotalReceiveOctets			Counter,
						sipTermStatsC15mTotalLostPackets			INTEGER,
						sipTermStatsC15mAvgJBFL				INTEGER,
						sipTermStatsC15mAvgInterArrivalJitter			Gauge,
						sipTermStatsC15mAvgRoundTripDelay			Gauge,
						sipTermStatsC15mPeakInterArrivalJitter		Gauge,
						sipTermStatsC15mPeakRoundTripDelay		Gauge,
						sipTermStatsC15mAvgJBFLG711A			INTEGER,
						sipTermStatsC15mAvgJBFLG711U			INTEGER,
						sipTermStatsC15mAvgJBFLG723			INTEGER,
						sipTermStatsC15mAvgJBFLG729			INTEGER,
						sipTermStatsC15mRegisterReqSuccessful		INTEGER,
						sipTermStatsC15mRegisterReqFailed			INTEGER,
						sipTermStatsC15mRegistrationsActive			INTEGER,
						sipTermStatsC15mOutgoingCallsAnswered		INTEGER,
						sipTermStatsC15mIncomingCallsAnswered  		INTEGER,
                        sipTermStatsC15mOutCallAtt              INTEGER,
                        sipTermStatsC15mOutCallSeizDur          INTEGER,
                        sipTermStatsC15mInCallAtt               INTEGER,
                        sipTermStatsC15mInCallSeizDur           INTEGER,
                        sipTermStatsC15mExpRtpPkts              Counter,
                        sipTermStatsC15mAccRtpPkts              Counter,
                        sipTermStatsC15mDiscRtpPkts             Counter,
                        sipTermStatsC15mELArrRtpPkts            Counter,
                        sipTermStatsC15mPortRegDur              INTEGER,
                        sipTermStatsC15mPortAvailDur            INTEGER, 
                        sipTermStatsC15mOutFailLostSeiz         INTEGER,
                        sipTermStatsC15mInFailLostSeiz          INTEGER,
                        sipTermStatsC15mOutSuccInitInv          INTEGER
						}

		sipTermStatsC15mMeasuredTime OBJECT-TYPE
				SYNTAX INTEGER
			  ACCESS read-only
				STATUS mandatory
				DESCRIPTION
						"The amount of time, measured in seconds, that statistics for this entry have been counted.
				ALCATEL-LUCENT NOTE:
				ACCESS:	READ-ONLY
				USAGE:	NA
				PERSIST:	NO
				INSRVMOD:	NA
				RANGE:	NA
				DEFVALUE: 	NA
				UNITS:	Second
		    SPARSE:	NA
			"
  ::= { sipTermStatsC15mEntry 1 }

		sipTermStatsC15mInvalidDataFlag OBJECT-TYPE
				SYNTAX INTEGER(0..1)
				ACCESS read-only
				STATUS mandatory
				DESCRIPTION
						"This object indicates the validity of the corresponding PM data. It is set to 1 when the PM data is incomplete
			      or invalid and set to 0 when the PM data is complete and valid.
				ALCATEL-LUCENT NOTE:
				ACCESS:	READ-ONLY
				USAGE:	NA
				PERSIST:	NO
				INSRVMOD:	NA
				RANGE:	(0..1)
				DEFVALUE: 	NA
				UNITS:	NA
		    SPARSE:	NA
			"
	::= { sipTermStatsC15mEntry 2 }

		sipTermStatsC15mTotalSendPackets OBJECT-TYPE
				SYNTAX Counter
				ACCESS read-only
				STATUS mandatory
				DESCRIPTION
			      "The total amount of RTP packets transmitted by this SIP termination in the current 15 min interval.
				ALCATEL-LUCENT NOTE:
				ACCESS:	READ-ONLY
				USAGE:	NA
				PERSIST:	NO
				INSRVMOD:	NA
				RANGE:	NA
				DEFVALUE: 	NA
				UNITS:	Packets
		    SPARSE:	NA
			"
  ::= { sipTermStatsC15mEntry 3 }

		sipTermStatsC15mTotalSendOctets OBJECT-TYPE
				SYNTAX Counter
				ACCESS read-only
				STATUS mandatory
				DESCRIPTION
			      "The total amount of RTP octets transmitted by this SIP termination in the current 15 min interval.
				ALCATEL-LUCENT NOTE:
				ACCESS:	READ-ONLY
				USAGE:	NA
				PERSIST:	NO
				INSRVMOD:	NA
				RANGE:	NA
				DEFVALUE: 	NA
				UNITS:	Octets
		    SPARSE:	NA
			"
  ::= { sipTermStatsC15mEntry 4 }

		sipTermStatsC15mTotalReceivePackets OBJECT-TYPE
				SYNTAX Counter
				ACCESS read-only
				STATUS mandatory
				DESCRIPTION
						"The total amount of RTP packets received by this SIP termination in the current 15 min interval.
				ALCATEL-LUCENT NOTE:
				ACCESS:	READ-ONLY
				USAGE:	NA
				PERSIST:	NO
				INSRVMOD:	NA
				RANGE:	NA
				DEFVALUE: 	NA
				UNITS:	Packets
		    SPARSE:	NA
			"
  ::= { sipTermStatsC15mEntry 5 }

		sipTermStatsC15mTotalReceiveOctets OBJECT-TYPE
				SYNTAX Counter
				ACCESS read-only
				STATUS mandatory
				DESCRIPTION
						"The total amount of RTP octets received by this SIP termination in the current 15 min interval..
				ALCATEL-LUCENT NOTE:
				ACCESS:	READ-ONLY
				USAGE:	NA
				PERSIST:	NO
				INSRVMOD:	NA
				RANGE:	NA
				DEFVALUE: 	NA
				UNITS:	Octets
		    SPARSE:	NA
			"
  ::= { sipTermStatsC15mEntry 6 }

		sipTermStatsC15mTotalLostPackets OBJECT-TYPE
				SYNTAX INTEGER
				ACCESS read-only
				STATUS mandatory
				DESCRIPTION
						"The total amount of lost RTP packets for this SIP termination in the current 15 min interval.
						The amount of packets lost is defined to be the amount of packets expected less the amount of packets actually received:
									lost = expected - s->received;
									Since this signed number is carried in 24 bits, it should be clamped at 0x7fffff for positive loss or 0x800000 for negative loss rather than wrapping around.
				ALCATEL-LUCENT NOTE:
				ACCESS:	READ-ONLY
				USAGE:	NA
				PERSIST:	NO
				INSRVMOD:	NA
				RANGE:	NA
				DEFVALUE: 	NA
				UNITS:	Packets
		    SPARSE:	NA
			"
  ::= { sipTermStatsC15mEntry 7 }

		sipTermStatsC15mAvgJBFL OBJECT-TYPE
				SYNTAX INTEGER(0..100)
				ACCESS read-only
				STATUS mandatory
				DESCRIPTION
			      "Average Jitter Buffer Fill Level Percentage measured for both, originating and terminating calls at this SIP termination line (incoming direction of RTP packets only) in this interval
				ALCATEL-LUCENT NOTE:
				ACCESS:	READ-ONLY
				USAGE:	NA
				PERSIST:	NO
				INSRVMOD:	NA
				RANGE:	(0..100)
				DEFVALUE: 	NA
				UNITS:	Percentage
		    SPARSE:	NA
			"
  ::= { sipTermStatsC15mEntry 8 }

		sipTermStatsC15mAvgInterArrivalJitter OBJECT-TYPE
				SYNTAX Gauge
				ACCESS read-only
				STATUS mandatory
				DESCRIPTION
						"Average inter-arrival Jitter measured for this SIP termination in the current 15 min interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
  ::= { sipTermStatsC15mEntry 9 }

		sipTermStatsC15mAvgRoundTripDelay OBJECT-TYPE
				SYNTAX Gauge
				ACCESS read-only
				STATUS mandatory
				DESCRIPTION
			      "Average round-trip delay measured for this SIP termination in the current 15 min interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
  ::= { sipTermStatsC15mEntry 10 }

		sipTermStatsC15mPeakInterArrivalJitter OBJECT-TYPE
				SYNTAX Gauge
				ACCESS read-only
				STATUS mandatory
				DESCRIPTION
			      "Peak inter-arrival Jitter measured for this SIP termination in the current 15 min interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
  ::= { sipTermStatsC15mEntry 11 }

		sipTermStatsC15mPeakRoundTripDelay OBJECT-TYPE
				SYNTAX Gauge
				ACCESS read-only
				STATUS mandatory
				DESCRIPTION
						"Peak round-trip delay measured for this SIP termination in the current 15 min interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
  ::= { sipTermStatsC15mEntry 12 }

		sipTermStatsC15mAvgJBFLG711A OBJECT-TYPE
				SYNTAX INTEGER(0..100)
				ACCESS read-only
				STATUS mandatory
				DESCRIPTION
						" Average Jitter Buffer Fill Level measured at this SIP termination during the receipt of an RTP 
						stream encoded with G711_a in the course of the current 15 min interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
  ::= { sipTermStatsC15mEntry 13 }

		sipTermStatsC15mAvgJBFLG711U OBJECT-TYPE
				SYNTAX INTEGER(0..100)
				ACCESS read-only
				STATUS mandatory
				DESCRIPTION
						" Average Jitter Buffer Fill Level measured at a subscriber line during the receipt of an RTP 
						stream encoded with G711_u in the course of the current 15 min interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
  ::= { sipTermStatsC15mEntry 14 }

		sipTermStatsC15mAvgJBFLG723 OBJECT-TYPE
				SYNTAX INTEGER(0..100)
				ACCESS read-only
				STATUS mandatory
				DESCRIPTION
						" Average Jitter Buffer Fill Level measured at a subscriber line during the receipt of an RTP 
						stream encoded with G723 in the course of the current 15 min interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
  ::= { sipTermStatsC15mEntry 15 }

		sipTermStatsC15mAvgJBFLG729 OBJECT-TYPE
				SYNTAX INTEGER(0..100)
				ACCESS read-only
				STATUS mandatory
				DESCRIPTION
						" Average Jitter Buffer Fill Level measured at a subscriber line during the receipt of an RTP 
						stream encoded with G729 in the current 15 min interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
  ::= { sipTermStatsC15mEntry 16 }

		sipTermStatsC15mRegisterReqSuccessful OBJECT-TYPE
				SYNTAX INTEGER
				ACCESS read-only
				STATUS mandatory
				DESCRIPTION
						" The amount of (re-)registration requests which are successfully replied in this current 15min interval. Successfully replied means that a response = 200 OK with expire header time = 0 or expire header <> 0 has been returned by the Registrar.
				ALCATEL-LUCENT NOTE:
				ACCESS:	READ-ONLY
				USAGE:	NA
				PERSIST:	NO
				INSRVMOD:	NA
				RANGE:	NA
				DEFVALUE: 	NA
				UNITS:	Number
		    SPARSE:	NA
			"
  ::= { sipTermStatsC15mEntry 17 }

		sipTermStatsC15mRegisterReqFailed OBJECT-TYPE
				SYNTAX INTEGER
				ACCESS read-only
				STATUS mandatory
				DESCRIPTION
						" The amount of (re-)registration requests which failed in this current 15 min interval. Failed means that a response <> 200 OK was retruned by the SIP First Hop server / Registrar or that SIP transaction time-out occured.
				ALCATEL-LUCENT NOTE:
				ACCESS:	READ-ONLY
				USAGE:	NA
				PERSIST:	NO
				INSRVMOD:	NA
				RANGE:	NA
				DEFVALUE: 	NA
				UNITS:	Number
		    SPARSE:	NA
			"
  ::= { sipTermStatsC15mEntry 18 }

		sipTermStatsC15mRegistrationsActive OBJECT-TYPE
				SYNTAX INTEGER
				ACCESS read-only
				STATUS mandatory
				DESCRIPTION
			  		" The amount of registrations being active at a subscriber port at the end of the current 15 min interval. In the current implementation, only 1 registration can be active at a subscriber port at a time. An active registration is counted when a registration request has been successfully completed in the past (200 OK received to register request with 'expire header' time <> 0) and the register expiration interval hasn't expired.
				ALCATEL-LUCENT NOTE:
				ACCESS:	READ-ONLY
				USAGE:	NA
				PERSIST:	NO
				INSRVMOD:	NA
				RANGE:	NA
				DEFVALUE: 	NA
				UNITS:	Number
		    SPARSE:	NA
			"
  ::= { sipTermStatsC15mEntry 19 }

		sipTermStatsC15mOutgoingCallsAnswered OBJECT-TYPE
				SYNTAX INTEGER
				ACCESS read-only
				STATUS mandatory
				DESCRIPTION
						" The amount of outgoing call attempts in this current 15 min interval for which an initial INVITE request is sent AND for which a response is received. The system allows to provision what kind of response must be received as to be counted as a successful outgoing call attempt. The system offers the following options : 
						o Any response be received (irrespective of whether this is a successful or unsuccessful response). 
						o A successful response be received (180 or 200 response only).
				ALCATEL-LUCENT NOTE:
				ACCESS:	READ-ONLY
				USAGE:	NA
				PERSIST:	NO
				INSRVMOD:	NA
				RANGE:	NA
				DEFVALUE: 	NA
				UNITS:	Number
		    SPARSE:	NA
			"
  ::= { sipTermStatsC15mEntry 20 }

		sipTermStatsC15mIncomingCallsAnswered OBJECT-TYPE
				SYNTAX INTEGER
				ACCESS read-only
				STATUS mandatory
				DESCRIPTION
						" The amount of incoming call attempts in this current 15 min interval for which a SIP response is sent being the result of the off-hook event been detected. The system allows to provision the kind of response that will be considered as to be counted as a successful incoming call attempt. The system offers the following options : 
						o Any response be sent. 
						o 180 response be sent.
                                                o 200 response be sent.

				ALCATEL-LUCENT NOTE:
				ACCESS:	READ-ONLY
				USAGE:	NA
				PERSIST:	NO
				INSRVMOD:	NA
				RANGE:	NA
				DEFVALUE: 	NA
				UNITS:	Number
		    SPARSE:	NA
			"
  ::= { sipTermStatsC15mEntry 21 }

        sipTermStatsC15mOutCallAtt OBJECT-TYPE
                SYNTAX INTEGER
                ACCESS read-only
                STATUS mandatory
                DESCRIPTION
                        "Ref. PM statistic definition in corresponding P15m MIB object definition.

                ALCATEL-LUCENT NOTE:
                ACCESS: READ-ONLY
                USAGE:  NA
                PERSIST:    NO
                INSRVMOD:   NA
                RANGE:  NA
                DEFVALUE:   NA
                UNITS:  Number
                SPARSE: NA
                "
    ::= { sipTermStatsC15mEntry 22 }

        sipTermStatsC15mOutCallSeizDur  OBJECT-TYPE
                SYNTAX INTEGER
                ACCESS read-only
                STATUS mandatory
                DESCRIPTION
                        "Ref. PM statistic definition in corresponding P15m MIB object definition.

                ALCATEL-LUCENT NOTE:
                ACCESS: READ-ONLY
                USAGE:  NA
                PERSIST:    NO
                INSRVMOD:   NA
                RANGE:  NA
                DEFVALUE:   NA
                UNITS:  Seconds
                SPARSE: NA
                "
    ::= { sipTermStatsC15mEntry 23 }

    sipTermStatsC15mInCallAtt OBJECT-TYPE
                SYNTAX INTEGER
                ACCESS read-only
                STATUS mandatory
                DESCRIPTION
                        "Ref. PM statistic definition in corresponding P15m MIB object definition.

                ALCATEL-LUCENT NOTE:
                ACCESS: READ-ONLY
                USAGE:  NA
                PERSIST:    NO
                INSRVMOD:   NA
                RANGE:  NA
                DEFVALUE:   NA
                UNITS:  Number
                SPARSE: NA
                "
    ::= { sipTermStatsC15mEntry 24 }

        sipTermStatsC15mInCallSeizDur OBJECT-TYPE
                SYNTAX INTEGER
                ACCESS read-only
                STATUS mandatory
                DESCRIPTION
                        "Ref. PM statistic definition in corresponding P15m MIB object definition.

                ALCATEL-LUCENT NOTE:
                ACCESS: READ-ONLY
                USAGE:  NA
                PERSIST:    NO
                INSRVMOD:   NA
                RANGE:  NA
                DEFVALUE:   NA
                UNITS:  Seconds
                SPARSE: NA
                "
    ::= { sipTermStatsC15mEntry 25 }

        sipTermStatsC15mExpRtpPkts OBJECT-TYPE
                SYNTAX Counter
                ACCESS read-only
                STATUS mandatory
                DESCRIPTION
                        " Ref. PM statistic definition in corresponding P15m MIB object definition.

                ALCATEL-LUCENT NOTE:
                ACCESS: READ-ONLY
                USAGE:  NA
                PERSIST:    NO
                INSRVMOD:   NA
                RANGE:  NA
                DEFVALUE:   NA
                UNITS:  Packets
                SPARSE: NA
                "
    ::= { sipTermStatsC15mEntry 28 }

        sipTermStatsC15mAccRtpPkts OBJECT-TYPE
                SYNTAX Counter
                ACCESS read-only
                STATUS mandatory
                DESCRIPTION
                        " Ref. PM statistic definition in corresponding P15m MIB object definition.

                ALCATEL-LUCENT NOTE:
                ACCESS: READ-ONLY
                USAGE:  NA
                PERSIST:    NO
                INSRVMOD:   NA
                RANGE:  NA
                DEFVALUE:   NA
                UNITS:  Packets
                SPARSE: NA
                "
    ::= { sipTermStatsC15mEntry 29 }

        sipTermStatsC15mDiscRtpPkts OBJECT-TYPE
                SYNTAX Counter
                ACCESS read-only
                STATUS mandatory
                DESCRIPTION
                        " Ref. PM statistic definition in corresponding P15m MIB object definition.

                ALCATEL-LUCENT NOTE:
                ACCESS: READ-ONLY
                USAGE:  NA
                PERSIST:    NO
                INSRVMOD:   NA
                RANGE:  NA
                DEFVALUE:   NA
                UNITS:  Packets
                SPARSE: NA
                "
    ::= { sipTermStatsC15mEntry 30 }

        sipTermStatsC15mELArrRtpPkts OBJECT-TYPE
                SYNTAX Counter
                ACCESS read-only
                STATUS mandatory
                DESCRIPTION
                        " Ref. PM statistic definition in corresponding P15m MIB object definition.

                ALCATEL-LUCENT NOTE:
                ACCESS: READ-ONLY
                USAGE:  NA
                PERSIST:    NO
                INSRVMOD:   NA
                RANGE:  NA
                DEFVALUE:   NA
                UNITS:  Packets
                SPARSE: NA
                "
    ::= { sipTermStatsC15mEntry 31 }

        sipTermStatsC15mPortRegDur OBJECT-TYPE
                SYNTAX INTEGER
                ACCESS read-only
                STATUS mandatory
                DESCRIPTION
                        " Ref. PM statistic definition in corresponding P15m MIB object definition.

                ALCATEL-LUCENT NOTE:
                ACCESS: READ-ONLY
                USAGE:  NA
                PERSIST:    NO
                INSRVMOD:   NA
                RANGE:  NA
                DEFVALUE:   NA
                UNITS:  Seconds
                SPARSE: NA
                "
    ::= { sipTermStatsC15mEntry 32 }

        sipTermStatsC15mPortAvailDur OBJECT-TYPE
                SYNTAX INTEGER
                ACCESS read-only
                STATUS mandatory
                DESCRIPTION
                        " Ref. PM statistic definition in corresponding P15m MIB object definition.

                ALCATEL-LUCENT NOTE:
                ACCESS: READ-ONLY
                USAGE:  NA
                PERSIST:    NO
                INSRVMOD:   NA
                RANGE:  NA
                DEFVALUE:   NA
                UNITS:  Seconds
                SPARSE: NA
                "
    ::= { sipTermStatsC15mEntry 33 }

sipTermStatsC15mOutFailLostSeiz OBJECT-TYPE
                SYNTAX INTEGER
                ACCESS read-only
                STATUS mandatory
                DESCRIPTION
                " Ref. PM statistic definition in corresponding P15m MIB object definition.
		This counter will be implemented in R55.                      
                    ALCATEL-LUCENT NOTE:
                ACCESS: READ-ONLY
                USAGE:  NA
                PERSIST:    NO
                INSRVMOD:   NA
                RANGE:  NA
                DEFVALUE:   NA
                UNITS:  number
                SPARSE: NA
                "
    ::= { sipTermStatsC15mEntry 37 }

    sipTermStatsC15mInFailLostSeiz OBJECT-TYPE
                SYNTAX INTEGER
                ACCESS read-only
                STATUS mandatory
                DESCRIPTION
                " Ref. PM statistic definition in corresponding P15m MIB object definition.
		This counter will be implemented in R55.                      

                ALCATEL-LUCENT NOTE:
                ACCESS: READ-ONLY
                USAGE:  NA
                PERSIST:    NO
                INSRVMOD:   NA
                RANGE:  NA
                DEFVALUE:   NA
                UNITS:  number
                SPARSE: NA
                "
    ::= { sipTermStatsC15mEntry 44 }

    sipTermStatsC15mOutSuccInitInv OBJECT-TYPE
                SYNTAX INTEGER
                ACCESS read-only
                STATUS mandatory
                DESCRIPTION
                "Ref. PM statistic definition in corresponding P15m MIB object definition.
		This counter will be implemented in R55.                      

                ALCATEL-LUCENT NOTE:
                ACCESS: READ-ONLY
                USAGE:  NA  
                PERSIST:    NO
                INSRVMOD:   NA
                RANGE:  NA
                DEFVALUE:   NA
                UNITS:  Number
                SPARSE: NA
                "
    ::= { sipTermStatsC15mEntry 49 }


-- =============================================================================
-- 
-- Sip Term Stats P1d Table
--=============================================================================

		sipTermStatsP1dTable OBJECT-TYPE
				SYNTAX SEQUENCE OF SipTermStatsP1dEntry
				ACCESS not-accessible
				STATUS mandatory
				DESCRIPTION
						"This table contains the previous 1 day sip term statistics.
						The table is auto-created. A row is associated with a row in sipTerminationTable
						At the end of 1 day interval, the current 1day interval contents are copied to the 
						recent previous interval. Up to 3 previous intervals are supported for each sip termination.
						The registers associated with this SIP termination connected to a particular voice LT board shall be set to '0' when this voice LT board has restarted
						In addition
						- The Invalid data flag shall be set to 'True' to indicate that the results shown for this 
						   interval are invalid. 
						- The measured time shall be set to '0'.
						Summarized : measuredTime: 0, invalidData: True, counter: 0.
						
						7302/7330 ISAM-V : Supported
						7363 NGVR : Supported
						7367 SX : Supported
						
				ALCATEL NOTE: 
				SUPPORT:  YES
			  TABLESIZE:  DEP [NumOfLT * NumOfLinesPerLT * 3]
			"
  ::= { sipStatisticsAndData 5 }

		sipTermStatsP1dEntry OBJECT-TYPE
				SYNTAX SipTermStatsP1dEntry
				ACCESS not-accessible
				STATUS mandatory
				DESCRIPTION
						"The entry in the sipTermStatsP1dTable.
				ALCATEL NOTE:
				SUPPORT:  YES
			"
				INDEX { ifIndex, sipTermStatsP1dIntervalNumber }
  ::= { sipTermStatsP1dTable 1 }

		SipTermStatsP1dEntry ::=
				SEQUENCE { 
						sipTermStatsP1dIntervalNumber 			INTEGER,
						sipTermStatsP1dMeasuredTime				INTEGER,
						sipTermStatsP1dInvalidDataFlag				INTEGER,
						sipTermStatsP1dTotalSendPackets			Counter,
						sipTermStatsP1dTotalSendOctets				Counter,
						sipTermStatsP1dTotalReceivePackets			Counter,
						sipTermStatsP1dTotalReceiveOctets			Counter,
						sipTermStatsP1dTotalLostPackets				INTEGER,
						sipTermStatsP1dAvgJBFL					INTEGER,
						sipTermStatsP1dAvgInterArrivalJitter			Gauge,
						sipTermStatsP1dAvgRoundTripDelay			Gauge,
						sipTermStatsP1dPeakInterArrivalJitter			Gauge,
						sipTermStatsP1dPeakRoundTripDelay			Gauge,
						sipTermStatsP1dAvgJBFLG711A				INTEGER,
						sipTermStatsP1dAvgJBFLG711U				INTEGER,
						sipTermStatsP1dAvgJBFLG723				INTEGER,
						sipTermStatsP1dAvgJBFLG729				INTEGER,
						sipTermStatsP1dRegisterReqSuccessful			INTEGER,
						sipTermStatsP1dRegisterReqFailed			INTEGER,
						sipTermStatsP1dRegistrationsActive			INTEGER,
						sipTermStatsP1dOutgoingCallsAnswered		INTEGER,
						sipTermStatsP1dIncomingCallsAnswered		INTEGER,
						sipTermStatsP1dTimeStamp  			NetworkTimeInSeconds
						}

		sipTermStatsP1dIntervalNumber OBJECT-TYPE
				SYNTAX INTEGER(1..3)
				ACCESS not-accessible
				STATUS mandatory
				DESCRIPTION
						"A number between 1 and 3, which identifies the interval for which the set of statistics is available. The interval identified by I is the most recently completed 1 day interval, and the interval identified by N is the interval immediately preceding the one identified by N-1 .
				ALCATEL-LUCENT NOTE:
				ACCESS:	NOT-ACCESSIBLE
				USAGE:	NA
				PERSIST:	NO
				INSRVMOD:	NA
				RANGE:	(1..3)
				DEFVALUE: 	NA
				UNITS:	NA
		    SPARSE:	NA
			"
  ::= { sipTermStatsP1dEntry 1 }

		sipTermStatsP1dMeasuredTime OBJECT-TYPE
				SYNTAX INTEGER
				ACCESS read-only
				STATUS mandatory
				DESCRIPTION
						"The amount of time, measured in seconds, that statistics for this entry have been counted.
				ALCATEL-LUCENT NOTE:
				ACCESS:	READ-ONLY
				USAGE:	NA
				PERSIST:	NO
				INSRVMOD:	NA
				RANGE:	NA
				DEFVALUE: 	NA
				UNITS:	Second
		    SPARSE:	NA
			"
  ::= { sipTermStatsP1dEntry 2 }

		sipTermStatsP1dInvalidDataFlag OBJECT-TYPE
	SYNTAX INTEGER(0..1)
	ACCESS read-only
	STATUS mandatory
	DESCRIPTION
			"This object indicates the validity of the corresponding PM data.
It is set to 1 when the PM data is incomplete or invalid and set to 0 when the PM data is complete and valid.
		ALCATEL-LUCENT NOTE:
		ACCESS:	READ-ONLY
		USAGE:	NA
		PERSIST:	NO
		INSRVMOD:	NA
		RANGE:	(0..1)
		DEFVALUE: 	NA
		UNITS:	NA
                   SPARSE:	NA
			"
	::= { sipTermStatsP1dEntry 3 }

		sipTermStatsP1dTotalSendPackets OBJECT-TYPE
				SYNTAX Counter
				ACCESS read-only
				STATUS mandatory
				DESCRIPTION
						"The total amount of RTP packets transmitted by this subscriber line in this interval.
				ALCATEL-LUCENT NOTE:
				ACCESS:	READ-ONLY
				USAGE:	NA
				PERSIST:	NO
				INSRVMOD:	NA
				RANGE:	NA
				DEFVALUE: 	NA
				UNITS:	Packets
		    SPARSE:	NA
			"
  ::= { sipTermStatsP1dEntry 4 }

		sipTermStatsP1dTotalSendOctets OBJECT-TYPE
				SYNTAX Counter
				ACCESS read-only
				STATUS mandatory
				DESCRIPTION
			  		"The total amount of RTP octets transmitted by this subscriber line in this interval.
				ALCATEL-LUCENT NOTE:
				ACCESS:	READ-ONLY
				USAGE:	NA
				PERSIST:	NO
				INSRVMOD:	NA
				RANGE:	NA
				DEFVALUE: 	NA
				UNITS:	Octets
		    SPARSE:	NA
			"
  ::= { sipTermStatsP1dEntry 5 }

		sipTermStatsP1dTotalReceivePackets OBJECT-TYPE
				SYNTAX Counter
				ACCESS read-only
				STATUS mandatory
				DESCRIPTION
						"The total amount of RTP packets received by this subscriber line in this interval.
				ALCATEL-LUCENT NOTE:
				ACCESS:	READ-ONLY
				USAGE:	NA
				PERSIST:	NO
				INSRVMOD:	NA
				RANGE:	NA
				DEFVALUE: 	NA
				UNITS:	Packets
		    SPARSE:	NA
			"
  ::= { sipTermStatsP1dEntry 6 }

		sipTermStatsP1dTotalReceiveOctets OBJECT-TYPE
				SYNTAX Counter
				ACCESS read-only
				STATUS mandatory
				DESCRIPTION
						"The total amount of RTP octets received by this subscriber line in this interval.
				ALCATEL-LUCENT NOTE:
				ACCESS:	READ-ONLY
				USAGE:	NA
				PERSIST:	NO
				INSRVMOD:	NA
				RANGE:	NA
				DEFVALUE: 	NA
				UNITS:	Octets
		    SPARSE:	NA
			"
  ::= { sipTermStatsP1dEntry 7 }

		sipTermStatsP1dTotalLostPackets OBJECT-TYPE
				SYNTAX INTEGER
				ACCESS read-only
				STATUS mandatory
				DESCRIPTION
						"The total amount of lost RTP packets for this subscriber line in this interval.
						The amount of packets lost is defined to be the amount of packets expected less the amount of packets
						actually received:
						lost = expected - s->received;
						Since this signed number is carried in 24 bits, it should be clamped at 0x7fffff for positive loss or 0x800000 for negative loss rather than wrapping around.
				ALCATEL-LUCENT NOTE:
				ACCESS:	READ-ONLY
				USAGE:	NA
				PERSIST:	NO
				INSRVMOD:	NA
				RANGE:	NA
				DEFVALUE: 	NA
				UNITS:	Packets
		    SPARSE:	NA
			"
  ::= { sipTermStatsP1dEntry 8 }

		sipTermStatsP1dAvgJBFL OBJECT-TYPE
				SYNTAX INTEGER(0..100)
				ACCESS read-only
				STATUS mandatory
				DESCRIPTION
						"Average Jitter Buffer Fill Level Percentage measured for both, originating and terminating calls at a
						subscriber line (incoming direction of RTP packets only) in this interval.
					ALCATEL-LUCENT NOTE:
					ACCESS:	READ-ONLY
					USAGE:	NA
					PERSIST:	NO
					INSRVMOD:	NA
					RANGE:	(0..100)
					DEFVALUE: 	NA
					UNITS:	Percentage
			    SPARSE:	NA
				"
  ::= { sipTermStatsP1dEntry 9 }

		sipTermStatsP1dAvgInterArrivalJitter OBJECT-TYPE
				SYNTAX Gauge
				ACCESS read-only
				STATUS mandatory
				DESCRIPTION
						"Average inter-arrival Jitter measured for this SIP termination in one interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
  ::= { sipTermStatsP1dEntry 10 }

		sipTermStatsP1dAvgRoundTripDelay OBJECT-TYPE
				SYNTAX Gauge
				ACCESS read-only
				STATUS mandatory
				DESCRIPTION
						"Average round-trip delay measured for this SIP termination in one interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
	::= { sipTermStatsP1dEntry 11 }

		sipTermStatsP1dPeakInterArrivalJitter OBJECT-TYPE
				SYNTAX Gauge
				ACCESS read-only
				STATUS mandatory
				DESCRIPTION
						"Peak inter-arrival Jitter measured for a subscriber line in one interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
  ::= { sipTermStatsP1dEntry 12 }

		sipTermStatsP1dPeakRoundTripDelay OBJECT-TYPE
				SYNTAX Gauge
				ACCESS read-only
				STATUS mandatory
				DESCRIPTION
						"Peak round-trip delay measured for a subscriber line in one interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
	::= { sipTermStatsP1dEntry 13 }

		sipTermStatsP1dAvgJBFLG711A OBJECT-TYPE
				SYNTAX INTEGER(0..100)
			  ACCESS read-only
				STATUS mandatory
				DESCRIPTION
						" Average Jitter Buffer Fill Level measured at a subscriber line during the receipt of an RTP 
						stream encoded with G711_a in the course of a single interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
  ::= { sipTermStatsP1dEntry 14 }

		sipTermStatsP1dAvgJBFLG711U OBJECT-TYPE
				SYNTAX INTEGER(0..100)
				ACCESS read-only
				STATUS mandatory
				DESCRIPTION
						" Average Jitter Buffer Fill Level measured at a subscriber line during the receipt of an RTP 
						stream encoded with G711_u in the course of a single interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
  ::= { sipTermStatsP1dEntry 15 }

		sipTermStatsP1dAvgJBFLG723 OBJECT-TYPE
				SYNTAX INTEGER(0..100)
				ACCESS read-only
				STATUS mandatory
				DESCRIPTION
						" Average Jitter Buffer Fill Level measured at a subscriber line during the receipt of an RTP 
						stream encoded with G723 in the course of a single interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
  ::= { sipTermStatsP1dEntry 16 }

		sipTermStatsP1dAvgJBFLG729 OBJECT-TYPE
				SYNTAX INTEGER(0..100)
				ACCESS read-only
				STATUS mandatory
				DESCRIPTION
						" Average Jitter Buffer Fill Level measured at a subscriber line during the receipt of an RTP 
						stream encoded with G729 in the course of a single interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
  ::= { sipTermStatsP1dEntry 17 }

		sipTermStatsP1dRegisterReqSuccessful OBJECT-TYPE
				SYNTAX INTEGER
				ACCESS read-only
				STATUS mandatory
				DESCRIPTION
						" The amount of (re-)registration requests which are successfully replied in this recent 1 day interval. Successfully replied means that a response = 200 OK with expire header time = 0 or expire header <> 0 has been returned by the Registrar.
				ALCATEL-LUCENT NOTE:
				ACCESS:	READ-ONLY
				USAGE:	NA
				PERSIST:	NO	
				INSRVMOD:	NA
				RANGE:	NA
				DEFVALUE: 	NA
				UNITS:	Number
		    SPARSE:	NA
			"
	::= { sipTermStatsP1dEntry 18 }

		sipTermStatsP1dRegisterReqFailed OBJECT-TYPE
				SYNTAX INTEGER
				ACCESS read-only
				STATUS mandatory
				DESCRIPTION
						" The amount of (re-)registration requests which failed in this recent 1 day interval. 
						Failed means that a response <> 200 OK was retruned by the SIP First Hop server / Registrar or that SIP transaction time-out occured.
				ALCATEL-LUCENT NOTE:
				ACCESS:	READ-ONLY
				USAGE:	NA
				PERSIST:	NO
				INSRVMOD:	NA
				RANGE:	NA
				DEFVALUE: 	NA
				UNITS:	Number
		    SPARSE:	NA
			"
	::= { sipTermStatsP1dEntry 19 }

		sipTermStatsP1dRegistrationsActive OBJECT-TYPE
				SYNTAX INTEGER
				ACCESS read-only
				STATUS mandatory
				DESCRIPTION
						" The amount of registrations being active at a subscriber port at the end of the recent 1 day interval. In the current implementation, only 1 registration can be active at a subscriber port at a time. An active registration is counted when a registration request has been successfully completed in the past (200 OK received to register request with 'expire header' time <> 0) and the register expiration interval hasn't expired.
				ALCATEL-LUCENT NOTE:
				ACCESS:	READ-ONLY
				USAGE:	NA
				PERSIST:	NO
				INSRVMOD:	NA
				RANGE:	NA
				DEFVALUE: 	NA
				UNITS:	Number
		    SPARSE:	NA
			"
	::= { sipTermStatsP1dEntry 20 }

		sipTermStatsP1dOutgoingCallsAnswered OBJECT-TYPE
				SYNTAX INTEGER
				ACCESS read-only
				STATUS mandatory
				DESCRIPTION
						" The amount of outgoing call attempts in this recent 1 day interval for which an initial INVITE request is sent AND for which a response is received. The system allows to provision what kind of response must be received as to be counted as a successful outgoing call attempt. The system offers the following options : 
						o Any response be received (irrespective of whether this is a successful or unsuccessful response). 
						o A successful response be received (180 or 200 response only).
				ALCATEL-LUCENT NOTE:
				ACCESS:	READ-ONLY
				USAGE:	NA
				PERSIST:	NO
				INSRVMOD:	NA
				RANGE:	NA
				DEFVALUE: 	NA
				UNITS:	Number
		    SPARSE:	NA
			"
  ::= { sipTermStatsP1dEntry 21 }

		sipTermStatsP1dIncomingCallsAnswered OBJECT-TYPE
				SYNTAX INTEGER
				ACCESS read-only
				STATUS mandatory
				DESCRIPTION
						" The amount of incoming call attempts in this recent 1 day interval for which a SIP response is sent being the result of the off-hook event been detected. The system allows to provision the kind of response that will be considered as to be counted as a successful incoming call attempt. The system offers the following options : 
						o Any response be sent. 
						o 180 response be sent.
				ALCATEL-LUCENT NOTE:
				ACCESS:	READ-ONLY
				USAGE:	NA
				PERSIST:	NO
				INSRVMOD:	NA
				RANGE:	NA
				DEFVALUE: 	NA
				UNITS:	Number
		    SPARSE:	NA
			"
  ::= { sipTermStatsP1dEntry 22 }

                 sipTermStatsP1dTimeStamp  OBJECT-TYPE
                                SYNTAX NetworkTimeInSeconds
                                ACCESS read-only
                                STATUS mandatory
                                DESCRIPTION
                        "The value of sipTermStatsP1dTimeStamp indicating the time stamp of start time for termination statistic of per one day.
                                ALCATEL-LUCENT NOTE:
                                ACCESS:READ-ONLY
                                USAGE: NA
                                PERSIST: NO
                                INSRVMOD: NA
                                RANGE: (0..4294967295)
                                DEFVALUE: 0
                                UNITS:  seconds
                                SPARSE: NA
                                    "
    ::= { sipTermStatsP1dEntry  23 }


-- =============================================================================
-- 
-- Sip Term Stats C1d Table
--=============================================================================

		sipTermStatsC1dTable OBJECT-TYPE
				SYNTAX SEQUENCE OF SipTermStatsC1dEntry
				ACCESS not-accessible
				STATUS mandatory
				DESCRIPTION
									"This table contains the current 1 day sip term statistics.
						When an entry is created in the SIP termination table, a row for this termination is auto-created in this SIP 
						Termination Statistics Table.
						When an entry is deleted in the SIP termination table, the corresponding entry in this table is auto-deleted.
						
						The registers associated with this SIP termination connected to a particular voice LT board shall be 
						set to '0' when this voice LT board has restarted
						In addition 
									- The Invalid data flag shall be set to 'False' 
									- The measured time shall be set to '0'.
						Summarized : measuredTime: 0, invalidData: False, counter: 0.
						
						7302/7330 ISAM-V : Supported
						7363 NGVR : Supported
						7367 SX : Supported
			
				ALCATEL NOTE: 
				SUPPORT:  YES
				TABLESIZE:  DEP [NumOfLT * NumOfLinesPerLT]
		  "
	::= { sipStatisticsAndData 6 }

		sipTermStatsC1dEntry OBJECT-TYPE
				SYNTAX SipTermStatsC1dEntry
				ACCESS not-accessible
				STATUS mandatory
				DESCRIPTION
						"The entry in the sipTermStatsC1dTable.
				ALCATEL NOTE:
				SUPPORT:  YES
			"
				INDEX { ifIndex }
  ::= { sipTermStatsC1dTable 1 }

		SipTermStatsC1dEntry ::=
				SEQUENCE { 
						sipTermStatsC1dMeasuredTime				INTEGER,
						sipTermStatsC1dInvalidDataFlag			INTEGER,
						sipTermStatsC1dTotalSendPackets			Counter,
						sipTermStatsC1dTotalSendOctets			Counter,
						sipTermStatsC1dTotalReceivePackets			Counter,
						sipTermStatsC1dTotalReceiveOctets			Counter,
						sipTermStatsC1dTotalLostPackets			INTEGER,
						sipTermStatsC1dAvgJBFL					INTEGER,
						sipTermStatsC1dAvgInterArrivalJitter			Gauge,
						sipTermStatsC1dAvgRoundTripDelay			Gauge,
						sipTermStatsC1dPeakInterArrivalJitter			Gauge,
						sipTermStatsC1dPeakRoundTripDelay			Gauge,
						sipTermStatsC1dAvgJBFLG711A				INTEGER,
						sipTermStatsC1dAvgJBFLG711U			INTEGER,
						sipTermStatsC1dAvgJBFLG723				INTEGER,
						sipTermStatsC1dAvgJBFLG729				INTEGER,
						sipTermStatsC1dRegisterReqSuccessful			INTEGER,
						sipTermStatsC1dRegisterReqFailed			INTEGER,
						sipTermStatsC1dRegistrationsActive			INTEGER,
						sipTermStatsC1dOutgoingCallsAnswered		INTEGER,
						sipTermStatsC1dIncomingCallsAnswered		INTEGER
						}

		sipTermStatsC1dMeasuredTime OBJECT-TYPE
				SYNTAX INTEGER
				ACCESS read-only
				STATUS mandatory
				DESCRIPTION
						"The amount of time, measured in seconds, that statistics for this entry have been counted.
				ALCATEL-LUCENT NOTE:
				ACCESS:	READ-ONLY
				USAGE:	NA
				PERSIST:	NO
				INSRVMOD:	NA
				RANGE:	NA
				DEFVALUE: 	NA
				UNITS:	Second
		    SPARSE:	NA
			"
  ::= { sipTermStatsC1dEntry 1 }

		sipTermStatsC1dInvalidDataFlag OBJECT-TYPE
				SYNTAX INTEGER(0..1)
				ACCESS read-only
				STATUS mandatory
				DESCRIPTION
						"This object indicates the validity of the corresponding PM data.
			      It is set to 1 when the PM data is incomplete or invalid and set to 0 when the PM data is complete and valid.
				ALCATEL-LUCENT NOTE:
				ACCESS:	READ-ONLY
				USAGE:	NA
				PERSIST:	NO
				INSRVMOD:	NA
				RANGE:	(0..1)
				DEFVALUE: 	NA
				UNITS:	NA
		    SPARSE:	NA
			"
	::= { sipTermStatsC1dEntry 2 }

		sipTermStatsC1dTotalSendPackets OBJECT-TYPE
				SYNTAX Counter
				ACCESS read-only
				STATUS mandatory
				DESCRIPTION
						"The total amount of RTP packets transmitted by this SIP termination in the current 1 day interval.
				ALCATEL-LUCENT NOTE:
				ACCESS:	READ-ONLY
				USAGE:	NA
				PERSIST:	NO
				INSRVMOD:	NA
				RANGE:	NA
				DEFVALUE: 	NA
				UNITS:	Packets
		    SPARSE:	NA
			"
  ::= { sipTermStatsC1dEntry 3 }

		sipTermStatsC1dTotalSendOctets OBJECT-TYPE
				SYNTAX Counter
				ACCESS read-only
				STATUS mandatory
				DESCRIPTION
						"The total amount of RTP octets transmitted by this SIP termination in the current 1 day interval.
				ALCATEL-LUCENT NOTE:
				ACCESS:	READ-ONLY
				USAGE:	NA
				PERSIST:	NO
				INSRVMOD:	NA
				RANGE:	NA
				DEFVALUE: 	NA
				UNITS:	Octets
		    SPARSE:	NA
			"
	::= { sipTermStatsC1dEntry 4 }

		sipTermStatsC1dTotalReceivePackets OBJECT-TYPE
				SYNTAX Counter
				ACCESS read-only
				STATUS mandatory
				DESCRIPTION
						"The total amount of RTP packets received by this SIP termination in the current 1 day interval.
				ALCATEL-LUCENT NOTE:
				ACCESS:	READ-ONLY
				USAGE:	NA
				PERSIST:	NO
				INSRVMOD:	NA
				RANGE:	NA
				DEFVALUE: 	NA
				UNITS:	Packets
		    SPARSE:	NA
			"
	::= { sipTermStatsC1dEntry 5 }

		sipTermStatsC1dTotalReceiveOctets OBJECT-TYPE
				SYNTAX Counter
				ACCESS read-only
				STATUS mandatory
				DESCRIPTION
						"The total amount of RTP octets received by this SIP termination in the current 1 day interval.
				ALCATEL-LUCENT NOTE:
				ACCESS:	READ-ONLY
				USAGE:	NA
				PERSIST:	NO
				INSRVMOD:	NA
				RANGE:	NA
				DEFVALUE: 	NA
				UNITS:	Octets
		    SPARSE:	NA
			"
	::= { sipTermStatsC1dEntry 6 }

		sipTermStatsC1dTotalLostPackets OBJECT-TYPE
				SYNTAX INTEGER
				ACCESS read-only
				STATUS mandatory
				DESCRIPTION
						"The total amount of lost RTP packets for this SIP termination in the current 1 day intervalt.
						The amount of packets lost is defined to be the amount of packets expected less the amount of packets
						actually received:
									lost = expected - s->received;
									Since this signed number is carried in 24 bits, it should be clamped at 0x7fffff for positive loss or 0x800000
						for negative loss rather than wrapping around.
				ALCATEL-LUCENT NOTE:
				ACCESS:	READ-ONLY
				USAGE:	NA
				PERSIST:	NO
				INSRVMOD:	NA
				RANGE:	NA
				DEFVALUE: 	NA
				UNITS:	Packets
		    SPARSE:	NA
			"
	::= { sipTermStatsC1dEntry 7 }

		sipTermStatsC1dAvgJBFL OBJECT-TYPE
				SYNTAX INTEGER(0..100)
				ACCESS read-only
				STATUS mandatory
				DESCRIPTION
						"Average Jitter Buffer Fill Level Percentage measured for both, originating and terminating calls at a subscriber line (incoming direction of RTP packets only) in this interval
				ALCATEL-LUCENT NOTE:
				ACCESS:	READ-ONLY
				USAGE:	NA
				PERSIST:	NO
				INSRVMOD:	NA
				RANGE:	(0..100)
				DEFVALUE: 	NA
				UNITS:	Percentage
		    SPARSE:	NA
			"
	::= { sipTermStatsC1dEntry 8 }

		sipTermStatsC1dAvgInterArrivalJitter OBJECT-TYPE
				SYNTAX Gauge
				ACCESS read-only
				STATUS mandatory
				DESCRIPTION
						"Average inter-arrival Jitter measured for this SIP termination in the current 1 day interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
	::= { sipTermStatsC1dEntry 9 }

		sipTermStatsC1dAvgRoundTripDelay OBJECT-TYPE
				SYNTAX Gauge
				ACCESS read-only
				STATUS mandatory
				DESCRIPTION
						"Average round-trip delay measured for this SIP termination in the current 1 day interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
	::= { sipTermStatsC1dEntry 10 }

		sipTermStatsC1dPeakInterArrivalJitter OBJECT-TYPE
				SYNTAX Gauge
				ACCESS read-only
				STATUS mandatory
				DESCRIPTION
						"Peak inter-arrival Jitter measured for this SIP termination in the current 1 day interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
	::= { sipTermStatsC1dEntry 11 }

		sipTermStatsC1dPeakRoundTripDelay OBJECT-TYPE
				SYNTAX Gauge
				ACCESS read-only
				STATUS mandatory
				DESCRIPTION
						"Peak round-trip delay measured for this subscriber in the current 1 day interval.
				ALCATEL-LUCENT NOTE:
				ACCESS:	READ-ONLY
				USAGE:	NA
				PERSIST:	NO
				INSRVMOD:	NA
				RANGE:	NA
				DEFVALUE: 	NA
				UNITS:	Milli-Second
		    SPARSE:	NA
			"
	::= { sipTermStatsC1dEntry 12 }
	
		sipTermStatsC1dAvgJBFLG711A OBJECT-TYPE
				SYNTAX INTEGER(0..100)
				ACCESS read-only
				STATUS mandatory
				DESCRIPTION
						" Average Jitter Buffer Fill Level measured at this SIP termination line during the receipt of an RTP 
						stream encoded with G711_a in the course of a single interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
	::= { sipTermStatsC1dEntry 13 }

		sipTermStatsC1dAvgJBFLG711U OBJECT-TYPE
				SYNTAX INTEGER(0..100)
				ACCESS read-only
				STATUS mandatory
				DESCRIPTION
						" Average Jitter Buffer Fill Level measured at this SIP termination line during the receipt of an RTP 
						stream encoded with G711_u in the course of a single interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
	::= { sipTermStatsC1dEntry 14 }

		sipTermStatsC1dAvgJBFLG723 OBJECT-TYPE
				SYNTAX INTEGER(0..100)
				ACCESS read-only
				STATUS mandatory
				DESCRIPTION
						" Average Jitter Buffer Fill Level measured at this SIP termination line during the receipt of an RTP 
						stream encoded with G723 in the course of a single interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
	::= { sipTermStatsC1dEntry 15 }

		sipTermStatsC1dAvgJBFLG729 OBJECT-TYPE
				SYNTAX INTEGER(0..100)
				ACCESS read-only
				STATUS mandatory
				DESCRIPTION
						" Average Jitter Buffer Fill Level measured at this SIP termination line during the receipt of an RTP 
						stream encoded with G729 in the course of a single interval. The measurement includes the 
						receipt of RTP packets for both, originating and terminating calls. The measured average JBFL 
						is expressed as a percentage.
				ALCATEL-LUCENT NOTE:
				ACCESS:	READ-ONLY
				USAGE:	NA
				PERSIST:	NO
				INSRVMOD:	NA
				RANGE:	(0..100)
				DEFVALUE: 	NA
				UNITS:	Percentage
		    SPARSE:	NA
			"
	::= { sipTermStatsC1dEntry 16 }

		sipTermStatsC1dRegisterReqSuccessful OBJECT-TYPE
				SYNTAX INTEGER
				ACCESS read-only
				STATUS mandatory
				DESCRIPTION
						" The amount of (re-)registration requests which are successfully replied in this current 1 day interval. Successfully replied means that a response = 200 OK with expire header time = 0 or expire header <> 0 has been returned by the Registrar.
				ALCATEL-LUCENT NOTE:
				ACCESS:	READ-ONLY
				USAGE:	NA
				PERSIST:	NO
				INSRVMOD:	NA
				RANGE:	NA
				DEFVALUE: 	NA
				UNITS:	Number
		    SPARSE:	NA
			"
	::= { sipTermStatsC1dEntry 17 }

		sipTermStatsC1dRegisterReqFailed OBJECT-TYPE
				SYNTAX INTEGER
				ACCESS read-only
				STATUS mandatory
				DESCRIPTION
						" The amount of (re-)registration requests which failed in this current 1 day interval. Failed means that a response <> 200 OK was retruned by the SIP First Hop server / Registrar or that SIP transaction time-out occured.
                ALCATEL-LUCENT NOTE:
                ACCESS:     READ-ONLY
                USAGE:      NA
                PERSIST:    NO
                INSRVMOD:   NA
                RANGE:      NA
                DEFVALUE:   NA
                UNITS:      Number
                SPARSE:     NA
			"
	::= { sipTermStatsC1dEntry 18 }

		sipTermStatsC1dRegistrationsActive OBJECT-TYPE
				SYNTAX INTEGER
				ACCESS read-only
				STATUS mandatory
				DESCRIPTION
						" The amount of registrations being active at a subscriber port at the end of the current 1 day interval. In the current implementation, only 1 registration can be active at a subscriber port at a time. An active registration is counted when a registration request has been successfully completed in the past (200 OK received to register request with 'expire header' time <> 0) and the register expiration interval hasn't expired.
				ALCATEL-LUCENT NOTE:
				ACCESS:	READ-ONLY
				USAGE:	NA
				PERSIST:	NO
				INSRVMOD:	NA
				RANGE:	NA
				DEFVALUE: 	NA
				UNITS:	Number
		    SPARSE:	NA
			"
	::= { sipTermStatsC1dEntry 19 }

		sipTermStatsC1dOutgoingCallsAnswered OBJECT-TYPE
				SYNTAX INTEGER
				ACCESS read-only
				STATUS mandatory
				DESCRIPTION
						" The amount of outgoing call attempts in this current 1 day interval for which an initial INVITE request is sent AND for which a response is received. The system allows to provision what kind of response must be received as to be counted as a successful outgoing call attempt. The system offers the following options : 
						o Any response be received (irrespective of whether this is a successful or unsuccessful response). 
						o A successful response be received (180 or 200 response only).
				ALCATEL-LUCENT NOTE:
				ACCESS:	READ-ONLY
				USAGE:	NA
				PERSIST:	NO
				INSRVMOD:	NA
				RANGE:	NA
				DEFVALUE: 	NA
				UNITS:	Number
		    SPARSE:	NA
			"
	::= { sipTermStatsC1dEntry 20 }

		sipTermStatsC1dIncomingCallsAnswered OBJECT-TYPE
				SYNTAX INTEGER
				ACCESS read-only
				STATUS mandatory
				DESCRIPTION
						" The amount of incoming call attempts in this current 1 day interval for which a SIP response is sent being the result of the off-hook event been detected. The system allows to provision the kind of response that will be considered as to be counted as a successful incoming call attempt. The system offers the following options : 
						o Any response be sent. 
						o 180 response be sent.
				ALCATEL-LUCENT NOTE:
				ACCESS:	READ-ONLY
				USAGE:	NA
				PERSIST:	NO
				INSRVMOD:	NA
				RANGE:	NA
				DEFVALUE: 	NA
				UNITS:	Number
		    SPARSE:	NA
			"
	::= { sipTermStatsC1dEntry 21 }


-- =============================================================================
-- 
-- Sip Term Stats Perf Info Table
--=============================================================================

		sipTermStatsPerfInfoTable OBJECT-TYPE
				SYNTAX SEQUENCE OF SipTermStatsPerfInfoEntry
				ACCESS not-accessible
				STATUS mandatory
				DESCRIPTION
						"Table of statistics performance information on a termination
						When an entry is created in the SIP termination table, a row for this termination is auto-created in this SIP 
						Termination Statistics Performance Info Table.
						When an entry is deleted in the SIP termination table, the corresponding entry in this table is auto-deleted.
			
						7302/7330 ISAM-V : Supported
						7363 NGVR : Supported
						7367 SX : Supported
						
				ALCATEL NOTE: 
				SUPPORT:  YES
			  TABLESIZE:  DEP [NumOfLT * NumOfLinesPerLT]
		  "
	::= { sipStatisticsAndData 7 }

		sipTermStatsPerfInfoEntry OBJECT-TYPE
				SYNTAX SipTermStatsPerfInfoEntry
				ACCESS not-accessible
				STATUS mandatory
				DESCRIPTION
						"The entry in the sipTermStatsPerfInfoTable.
				ALCATEL NOTE:
				SUPPORT:  YES
			"
				INDEX { ifIndex }
	::= { sipTermStatsPerfInfoTable 1 }

		SipTermStatsPerfInfoEntry ::=
				SEQUENCE { 
						sipTermStatsPerfC15mElapsedTime			INTEGER,
						sipTermStatsPerfC1dElapsedTime			INTEGER,
						sipTermStatsPerfIntervals					INTEGER,
						sipTermStatsPerf1days					INTEGER
						}

		sipTermStatsPerfC15mElapsedTime OBJECT-TYPE
				SYNTAX INTEGER
				ACCESS read-only
				STATUS mandatory
				DESCRIPTION
						"The amount of time, measured in seconds, that elapsed for the current 15 minutes interval.
				ALCATEL-LUCENT NOTE:
				ACCESS:	READ-ONLY
				USAGE:	NA
				PERSIST:	NO
				INSRVMOD:	NA
				RANGE:	NA
				DEFVALUE: 	NA
				UNITS:	Second
		    SPARSE:	NA
			"
	::= { sipTermStatsPerfInfoEntry 1 }

		sipTermStatsPerfC1dElapsedTime OBJECT-TYPE
				SYNTAX INTEGER
				ACCESS read-only
				STATUS mandatory
				DESCRIPTION
						"The amount of time, measured in seconds, that elapsed for the current 1 day interval.
				ALCATEL-LUCENT NOTE:
				ACCESS:	READ-ONLY
				USAGE:	NA
				PERSIST:	NO
				INSRVMOD:	NA
				RANGE:	NA
				DEFVALUE: 	NA
				UNITS:	Second
		    SPARSE:	NA
			"
	::= { sipTermStatsPerfInfoEntry 2 }

		sipTermStatsPerfIntervals OBJECT-TYPE
				SYNTAX INTEGER(0..96)
				ACCESS read-only
				STATUS mandatory
				DESCRIPTION
						"Amount of previous 15 minutes intervals.
				ALCATEL-LUCENT NOTE:
				ACCESS:	READ-ONLY
				USAGE:	NA
				PERSIST:	NO
				INSRVMOD:	NA
				RANGE:	(0..96)
				DEFVALUE: 	NA
				UNITS:	Number
		    SPARSE:	NA
			"
	::= { sipTermStatsPerfInfoEntry 3 }

		sipTermStatsPerf1days OBJECT-TYPE
				SYNTAX INTEGER(0..3)
				ACCESS read-only
				STATUS mandatory
				DESCRIPTION
						"Amount of previous 1 day intervals.
				ALCATEL-LUCENT NOTE:
				ACCESS:	READ-ONLY
				USAGE:	NA
				PERSIST:	NO
				INSRVMOD:	NA
				RANGE:	(0..3)
				DEFVALUE: 	NA
				UNITS:	Number
		    SPARSE:	NA
			"
	::= { sipTermStatsPerfInfoEntry 4 }			

-- =============================================================================
-- 
-- Sip Call Stats P15m Table
-- =============================================================================

		sipCallStatsP15mTable OBJECT-TYPE
			SYNTAX SEQUENCE OF SipCallStatsP15mEntry
			ACCESS not-accessible
			STATUS mandatory
			DESCRIPTION
			"This table contains the recent 15 minutes sip call statistics.
		 	At most, 15 min history data for a duration of 1 day is recorded
		
			7302/7330 ISAM-V : Supported
			7363 NGVR : NOT supported
			7367 SX : NOT Supported
		
			ALCATEL NOTE: 
			SUPPORT:  YES
			TABLESIZE:  DEP [NumOfLT *14516]
			"
		::= { sipStatisticsAndData 8 }

		sipCallStatsP15mEntry OBJECT-TYPE
			SYNTAX SipCallStatsP15mEntry
			ACCESS not-accessible
			STATUS mandatory
			DESCRIPTION
				"The entry in the sipCallStatsP15mTable.
				ALCATEL NOTE:
				SUPPORT:  YES
				"
			INDEX { ifIndex, sipCallStatsP15mIntervalNumber,sipCallStatsP15mStartTime, sipCallStatsP15mIcid }
		::= { sipCallStatsP15mTable 1 }

		SipCallStatsP15mEntry ::=
			SEQUENCE { 
			sipCallStatsP15mIntervalNumber			INTEGER,
			sipCallStatsP15mStartTime				NetworkTimeInSeconds,
			sipCallStatsP15mIcid					OCTET STRING,
			sipCallStatsP15mEndTime					NetworkTimeInSeconds,
			sipCallStatsP15mTotalSendPackets			Counter,
			sipCallStatsP15mTotalSendOctets			Counter,
			sipCallStatsP15mTotalReceivePackets			Counter,
			sipCallStatsP15mTotalReceiveOctets			Counter,
			sipCallStatsP15mTotalLostPackets			INTEGER,
			sipCallStatsP15mDiscPacketJBOverFlow		Counter,
			sipCallStatsP15mAvgInterArrivalJitter			Gauge,
			sipCallStatsP15mAvgRoundTripDelay			Gauge,
			sipCallStatsP15mPeakInterArrivalJitter			Gauge,
			sipCallStatsP15mPeakRoundTripDelay			Gauge,
			sipCallStatsP15mDialogStateFlag                         INTEGER
			}

		sipCallStatsP15mIntervalNumber OBJECT-TYPE
			SYNTAX INTEGER(1..96)
			ACCESS not-accessible
			STATUS mandatory
			DESCRIPTION
			"A number between 1 and 96, which identifies the interval for which the set of statistics is available. The interval identified by I is the most recently completed 15 minutes interval, and the interval identified by N is the interval immediately preceding the one identified by N-1 .
			ALCATEL-LUCENT NOTE:
			ACCESS:	NOT-ACCESSIBLE
			USAGE:	NA
			PERSIST:	NO
			INSRVMOD:	NA
			RANGE:	(1..96)
			DEFVALUE: 	NA
			UNITS:	NA
		        SPARSE:	NA
			"
		::= { sipCallStatsP15mEntry 1 }

		sipCallStatsP15mStartTime OBJECT-TYPE
			SYNTAX NetworkTimeInSeconds
			ACCESS not-accessible
			STATUS mandatory
			DESCRIPTION
				"Time value in seconds when the call portion was initialized.  0 means the call portion start at the start time of
		 		this interval.
			ALCATEL-LUCENT NOTE:
			ACCESS:	NOT-ACCESSIBLE
			USAGE:	NA
			PERSIST:	NO
			INSRVMOD:	NA
			RANGE:	NA
			DEFVALUE: 	NA
			UNITS:	Second
		        SPARSE:	NA
			"
		::= { sipCallStatsP15mEntry 2 }

		sipCallStatsP15mIcid OBJECT-TYPE
			SYNTAX OCTET STRING (SIZE (0..38))
			ACCESS not-accessible
			STATUS mandatory
			DESCRIPTION
			" In case the customer's IMS network supports the IMS Charging ID then the generated ICID 
			that applies to a dialog is filled in. In case the customer's IMS network doesn't support 
			the IMS Charging ID then the system will fill in an autonomous generated dialog identifier 
			which consist of the fixed string 'NoIcid' followed by an internally generated call 
			identity and termination identity i.e. Noicid[call-identity][termination-id].  
			ALCATEL-LUCENT NOTE:
			ACCESS:	NOT-ACCESSIBLE
			USAGE:	NA
			PERSIST:	NO
			INSRVMOD:	NA
			RANGE:	SIZE (0..38)
			DEFVALUE: 	NA
			UNITS:	NA
                   	SPARSE:	NA
		"
		::= { sipCallStatsP15mEntry 3 }

		sipCallStatsP15mEndTime OBJECT-TYPE
			SYNTAX NetworkTimeInSeconds
			ACCESS read-only
			STATUS mandatory
			DESCRIPTION
				"Time value in seconds when the call portion has ended.  A value 0 means that the end of this call portion coincides with the expiry of the interval.
			ALCATEL-LUCENT NOTE:
			ACCESS:	READ-ONLY
			USAGE:	NA
			PERSIST:	NO
			INSRVMOD:	NA
			RANGE:	NA
			DEFVALUE: 	NA
			UNITS:	Second
		        SPARSE:	NA
			"
		::= { sipCallStatsP15mEntry 4 }

		sipCallStatsP15mTotalSendPackets OBJECT-TYPE
			SYNTAX Counter
			ACCESS read-only
			STATUS mandatory
			DESCRIPTION
				"The total amount of RTP packets transmitted in this call portion.
			ALCATEL-LUCENT NOTE:
			ACCESS:	READ-ONLY
			USAGE:	NA
			PERSIST:	NO
			INSRVMOD:	NA
			RANGE:	NA
			DEFVALUE: 	NA
			UNITS:	Packets
		        SPARSE:	NA
			"
		::= { sipCallStatsP15mEntry 5 }

		sipCallStatsP15mTotalSendOctets OBJECT-TYPE
			SYNTAX Counter
			ACCESS read-only
			STATUS mandatory
			DESCRIPTION
				"The total amount of RTP octets transmitted in this call portion.
			ALCATEL-LUCENT NOTE:
			ACCESS:	READ-ONLY
			USAGE:	NA
			PERSIST:	NO
			INSRVMOD:	NA
			RANGE:	NA
			DEFVALUE: 	NA
			UNITS:	Octets
		        SPARSE:	NA
			"
		::= { sipCallStatsP15mEntry 6 }

		sipCallStatsP15mTotalReceivePackets OBJECT-TYPE
			SYNTAX Counter
			ACCESS read-only
			STATUS mandatory
			DESCRIPTION
				"The total amount of RTP packets received in this call portion.
			ALCATEL-LUCENT NOTE:
			ACCESS:	READ-ONLY
			USAGE:	NA
			PERSIST:	NO
			INSRVMOD:	NA
			RANGE:	NA
			DEFVALUE: 	NA
			UNITS:	Packets
		        SPARSE:	NA
			"
		::= { sipCallStatsP15mEntry 7 }

		sipCallStatsP15mTotalReceiveOctets OBJECT-TYPE
			SYNTAX Counter
			ACCESS read-only
			STATUS mandatory
			DESCRIPTION
				"The total amount of RTP octets received in this call portion.
			ALCATEL-LUCENT NOTE:
			ACCESS:	READ-ONLY
			USAGE:	NA
			PERSIST:	NO
			INSRVMOD:	NA
			RANGE:	NA
			DEFVALUE: 	NA
			UNITS:	Octets
		        SPARSE:	NA
			"
		::= { sipCallStatsP15mEntry 8 }

		sipCallStatsP15mTotalLostPackets OBJECT-TYPE
			SYNTAX INTEGER
			ACCESS read-only
			STATUS mandatory
			DESCRIPTION
				"The total amount of lost receiving RTP packets in this call portion.
				The amount of packets lost is defined to be the amount of packets expected less the amount of packets
				actually received:
				lost = expected - s->received;
				Since this signed number is carried in 24 bits, it should be clamped at 0x7fffff for positive loss or 0x800000
				for negative loss rather than wrapping around.
			ALCATEL-LUCENT NOTE:
			ACCESS:	READ-ONLY
			USAGE:	NA
			PERSIST:	NO
			INSRVMOD:	NA
			RANGE:	NA
			DEFVALUE: 	NA
			UNITS:	Packets
		        SPARSE:	NA
			"
		::= { sipCallStatsP15mEntry 9 }

		sipCallStatsP15mDiscPacketJBOverFlow OBJECT-TYPE
			SYNTAX Counter
			ACCESS read-only
			STATUS mandatory
			DESCRIPTION
				"The total amount of discarded RTP packets due to the Jitter Buffer over-flow in this call portion.
			ALCATEL-LUCENT NOTE:
			ACCESS:	READ-ONLY
			USAGE:	NA
			PERSIST:	NO
			INSRVMOD:	NA
			RANGE:	NA
			DEFVALUE: 	NA
			UNITS:	Packets
		        SPARSE:	NA
			"
		::= { sipCallStatsP15mEntry 10 }

		sipCallStatsP15mAvgInterArrivalJitter OBJECT-TYPE
			SYNTAX Gauge
			ACCESS read-only
			STATUS mandatory
			DESCRIPTION
				"The average inter-arrival Jitter measured in this call portion.
			ALCATEL-LUCENT NOTE:
			ACCESS:	READ-ONLY
			USAGE:	NA
			PERSIST:	NO
			INSRVMOD:	NA
			RANGE:	NA
			DEFVALUE: 	NA
			UNITS:	Milli-Second
		        SPARSE:	NA
			"
		::= { sipCallStatsP15mEntry 11 }

		sipCallStatsP15mAvgRoundTripDelay OBJECT-TYPE
			SYNTAX Gauge
			ACCESS read-only
			STATUS mandatory
			DESCRIPTION
				"The average round-trip delay measured in this call portion.
			ALCATEL-LUCENT NOTE:
			ACCESS:	READ-ONLY
			USAGE:	NA
			PERSIST:	NO
			INSRVMOD:	NA
			RANGE:	NA
			DEFVALUE: 	NA
			UNITS:	Milli-Second
		        SPARSE:	NA
			"
		::= { sipCallStatsP15mEntry 12 }

		sipCallStatsP15mPeakInterArrivalJitter OBJECT-TYPE
			SYNTAX Gauge
			ACCESS read-only
			STATUS mandatory
			DESCRIPTION
				"The peak inter-arrival Jitter measured in this call portion.
			ALCATEL-LUCENT NOTE:
			ACCESS:	READ-ONLY
			USAGE:	NA
			PERSIST:	NO
			INSRVMOD:	NA
			RANGE:	NA
			DEFVALUE: 	NA
			UNITS:	Milli-Second
		        SPARSE:	NA
			"
		::= { sipCallStatsP15mEntry 13 }

		sipCallStatsP15mPeakRoundTripDelay OBJECT-TYPE
			SYNTAX Gauge
			ACCESS read-only
			STATUS mandatory
			DESCRIPTION
					"The peak round-trip delay measured in this call portion.
				ALCATEL-LUCENT NOTE:
				ACCESS:	READ-ONLY
				USAGE:	NA
				PERSIST:	NO
				INSRVMOD:	NA
				RANGE:	NA
				DEFVALUE: 	NA
				UNITS:	Milli-Second
		                 SPARSE:	NA
				"
			::= { sipCallStatsP15mEntry 14 }


                 
                sipCallStatsP15mDialogStateFlag OBJECT-TYPE
                        SYNTAX INTEGER
                                {
                                start-dialog(1),
                                continue-dialog(2),
                                end-dialog(3),
                                single-interval-dialog(4)
                                }       
                        ACCESS read-only
                        STATUS mandatory
                        DESCRIPTION     
                                "Per call dialog state flag. For one dialog starts and ends in the same interval, the value is single-interval-dialog; For one dialog starts and ends in different intervals, there are 3 possible values : start-dialog, continue-dialog, end-dialog. example:
               interval 1 : A calls B : ICID = X ; start-dialog; 
               interval 2 : A remains in conversation with B : ICID = X, continue-dialog; 
               interval 3 : A puts B on hold : ICID = X, end-dialog; 
               interval 3 : A calls C : ICID = Y, start-dialog; 
               interval 4 : A remains in conversation with C : ICID = Y, continue-dialog; 
               interval 5 : A ends call with C : ICID = Y, end-dialog; 
               interval 5 : A resumes call with B : ICID = Z, start-dialog; 
               interval 6 : A remains in dialog with B : ICID = Z, continue-dialog; 
               interval 7 : A goes on-hook : ICID = Z, end-dialog

                                ALCATEL-LUCENT NOTE:
                                        SUPPORT:      YES
                                        PERSIST:      NO
                                        INSRVMOD:     NA
                                        RANGE:        1 | 2 | 3 | 4
                                        DEFVALUE:     NA
                                        UNITS:        NA
                                "
                        ::= { sipCallStatsP15mEntry 15 }
			
-- =============================================================================
-- NEXT FREE SIP APPLICATION SERVER ID 
-- =============================================================================
                 sipDNSServerIdNext OBJECT-TYPE
                 	SYNTAX INTEGER
                 	ACCESS read-only
                 	STATUS mandatory
                 	DESCRIPTION
                 		"The next free SIP DNS Server index.
						Should an a next free SIP DNSServer index be requested while no free sip DNSServer index is available anymore, the system will return a genErr response.
                 			ALCATEL-LUCENT NOTE:
                 			ACCESS:     READ-ONLY
                                        USAGE:      NA
                 			PERSIST:    NA 
                 			INSRVMOD: 	NA
                 			RANGE:	NA
                 			DEFVALUE:  NA
                 			UNITS:	NA
							SPARSE: NO
                 		"
                 	::= { sipMIB 23 }

-- =============================================================================
-- The Sip DNS Sever Table
-- =============================================================================                 	
		sipDNSServerTable OBJECT-TYPE   
			SYNTAX SEQUENCE OF SipDNSServerEntry
			ACCESS not-accessible
			STATUS mandatory
			DESCRIPTION
				"The sipDNSServerTable allowing to configure one or multiple DNS servers.

                Maximum 96 DNS servers can be created.

                7302/7330 ISAM FTTN : Supported
                7363 MX : Supported
                7367 SX : Supported for single Service Gateway topology only
		
		  		ALCATEL NOTE: 
				TABLESIZE: 96
				DESCR:NA."
		::= { sipMIB 24 }

                	
                sipDNSServerEntry OBJECT-TYPE
                	SYNTAX SipDNSServerEntry
                	ACCESS not-accessible
                	STATUS mandatory
                	DESCRIPTION
                		"An entry in the sipDNSServerTable."
                	INDEX { sipDNSServerId }
                	::= { sipDNSServerTable 1 }
                	
                SipDNSServerEntry ::=
                	SEQUENCE { 
                        sipDNSServerId INTEGER,
                        sipDNSServerName OCTET STRING,
                        sipDNSServerAdminStatus INTEGER,
--                      sipDNSServerOperStatus INTEGER,
                        sipDNSServerRowStatus RowStatus,
                        sipDNSServerAddrType InetAddressType,
                        sipDNSServerAddr InetAddress,
                        sipDNSServerPriority INTEGER,
                        sipDNSServerRedunSite INTEGER,
                        sipDNSServerAdminDomName OCTET STRING,
                        sipDNSServerPort InetPortNumber
                 		}
                 		
		sipDNSServerId OBJECT-TYPE
			SYNTAX INTEGER 
			ACCESS not-accessible
			STATUS mandatory
			DESCRIPTION 
			"The unique internal identifier of a DNS server.
					ALCATEL-LUCENT NOTE:
					ACCESS:	NOT-ACCESSIBLE
					USAGE:	MANDATORY
					PERSIST:	YES	
					INSRVMOD:	NO
					RANGE:	(1..96)
					DEFVALUE:	NA
					UNITS:	NA	
			SPARSE:	NO			
					"
		::= { sipDNSServerEntry 1}	

		sipDNSServerName OBJECT-TYPE
			SYNTAX OCTET STRING (SIZE (0..32))
			ACCESS read-write
			STATUS mandatory
			DESCRIPTION
			"The operator friendly name of a DNS server. 
            This name must be unique across all entries of the sipDNSServerTable.
			 		ALCATEL-LUCENT NOTE:
					ACCESS:	READ-WRITE
					USAGE:	NA
					PERSIST:	YES	
					INSRVMOD:	YES
					RANGE:	SIZE (0..32)
					DEFVALUE:	NA
					UNITS:	NA	
					SPARSE:	NO			
					"
		::= { sipDNSServerEntry 2 }

		sipDNSServerAdminStatus OBJECT-TYPE
			SYNTAX INTEGER
				{
				up(1),
				down(2)
				}
			ACCESS read-write
			STATUS mandatory
			DESCRIPTION
					" The administrative status of the DNS server.
				UP (1) : the attributes of this entry that are indicated as INSRVMOD=YES can be modified.
				DOWN (2) : the attributes of this entry that are indicated as INSRVMOD=YES and the attributes that are
				 indicated as INSRVMOD=NO can be modified.
				Note that the attributes of this entry that are indicated INSRVMOD=NA can not be modified
				 after creation.
				ALCATEL-LUCENT NOTE:
				ACCESS:	READ-WRITE
				USAGE:	OPT
				PERSIST:	YES	
				INSRVMOD:	YES
				RANGE:	1|2
				DEFVALUE:	down(2)
				UNITS:	NA	
				SPARSE:	NO			
			"
	::= { sipDNSServerEntry 3 }


--		sipDNSServerOperStatus OBJECT-TYPE
--			SYNTAX INTEGER
--				{
--				up(1),
--				down(2)
--				}
--			ACCESS read-only
--			STATUS mandatory
--			DESCRIPTION
--				"The operational status of the DNS server.
--              up(1)   - The DNS server is up and functional.
--              down(2) - The DNS server is out of service.
--				ALCATEL-LUCENT NOTE:
--					ACCESS:     NA
--                                        USAGE:       NA		
--					PERSIST:  	NO
--					INSRVMOD: 	NA
--					RANGE:	1 | 2
--					DEFVALUE: 	NA
--					UNITS:	NA	
--                                        SPARSE:    NO	
--				"
--			::= { sipDNSServerEntry 4 }
		
		sipDNSServerRowStatus OBJECT-TYPE
			SYNTAX RowStatus
			ACCESS read-write
			STATUS mandatory
			DESCRIPTION
					"The status of this conceptual row.
					The RowStatus TC requires that this DESCRIPTION clause
					states under which circumstances other objects in this row
					can be modified.  The value of this object has no effect on
					whether other objects in this conceptual row can be
					modified.
					A conceptual row can always be made active.
					ALCATEL-LUCENT NOTE:
					ACCESS:	NA
					USAGE:	MAND
					PERSIST:	NO
					INSRVMOD: YES
					RANGE:	1 | 4 | 6	-- active (1), createAndGo (4), destroy (6)
					DEFVALUE: 	NA
					UNITS:	NA
					SPARSE:    NO
		         			"
			::= { sipDNSServerEntry 5 }

		sipDNSServerAddrType OBJECT-TYPE
				SYNTAX InetAddressType
				ACCESS read-write
				STATUS mandatory
				DESCRIPTION
				"IP Address type of sipDNSServerAddr.
		                Ipv4(1) An Ipv4 address as defined by the InetAddressIPv4 textual convention
				ALCATEL-LUCENT NOTE:
				ACCESS:	READ-WRITE
				USAGE:       OPT
				PERSIST:  	YES
				INSRVMOD: NO
				RANGE:	1	-- ipv4(1)
				DEFVALUE: 	ipv4(1)
				UNITS:	NA
				SPARSE:	NO
		                "
		 	::= { sipDNSServerEntry 6 } 

		sipDNSServerAddr OBJECT-TYPE
				SYNTAX InetAddress
				ACCESS read-write
				STATUS mandatory
				DESCRIPTION
				"IP Address of the DNS server.
				ALCATEL-LUCENT NOTE:
				ACCESS:	READ-WRITE
				USAGE:	MAND		
				PERSIST:	YES
				INSRVMOD: NO
				RANGE:	NA
				DEFVALUE:	NA
				UNITS:	NA
				SPARSE:	NO		
		                 		"
		::= { sipDNSServerEntry 7 }                 	
   	
		sipDNSServerPriority OBJECT-TYPE
				SYNTAX INTEGER 
				ACCESS read-write
				STATUS mandatory
				DESCRIPTION
				"The priority of the DNS server. The lower the value the higher the priority. 
				Each DNS server must be assigned a different priority.
		 		ALCATEL-LUCENT NOTE:
		                 	ACCESS:	READ-WRITE
				USAGE:	OPT		
				PERSIST:  	YES
				INSRVMOD: YES
				RANGE:	0..65535
				DEFVALUE: 	100
				UNITS:	NA
				SPARSE:	NO
                 		"
		::= { sipDNSServerEntry 8 }

			sipDNSServerRedunSite OBJECT-TYPE
				SYNTAX INTEGER
				{
				primary-site (1),
				backup-site (2)
				}
				ACCESS read-write
				STATUS mandatory
				DESCRIPTION
					"The site the DNS server belongs to.
				ALCATEL-LUCENT NOTE:
				ACCESS:	READ-WRITE
				USAGE:	OPT
				PERSIST:  	YES
				INSRVMOD:	YES
				RANGE:	1 | 2 
				DEFVALUE: primary-site (1)
				UNITS:	NA	
				SPARSE:    NO	

                 		"
                 	::= { sipDNSServerEntry 9 }
                 	
		sipDNSServerAdminDomName OBJECT-TYPE
				SYNTAX OCTET STRING (SIZE (0..32))
				ACCESS read-write
				STATUS mandatory
				DESCRIPTION
				"The administrative domain name of the DNS server. The administrative domain is the Service Gateway domain.
                It is assumed that both the [farm of] DNS server(s) and the (farm of) SIP First Hop server(s) are located in the same Service Gateway domain. A split in the sense that the one farm is located in the one administrative domain while the other farm is  located in the other administrative domain is considered not being realistic.
				ALCATEL-LUCENT NOTE:
				ACCESS:	READ-WRITE
				USAGE:	OPT
				PERSIST:	YES
				INSRVMOD: NO
				RANGE:	SIZE (0..32))
				DEFVALUE: 	null
				UNITS:	NA	
				SPARSE:	NO
			"
		::= { sipDNSServerEntry 10}

		sipDNSServerPort OBJECT-TYPE
			SYNTAX InetPortNumber
			ACCESS read-write
			STATUS mandatory
			DESCRIPTION
				" transport protocol port of the DNS server. If configured with value '0', the default port is used.
				ALCATEL-LUCENT NOTE:
				ACCESS:	READ-WRITE
				USAGE:	OPT		
				PERSIST:  	YES
				INSRVMOD:	NO
				RANGE:	NA
				DEFVALUE: 	53
				UNITS:	NA
				SPARSE:	NO		
				"
			::= { sipDNSServerEntry 11 }

-- =============================================================================
-- The Sip DNS Sever Mapping Table
-- =============================================================================                 	                 	
		sipDNSServerMappingTable OBJECT-TYPE
			SYNTAX SEQUENCE OF SipDNSServerMappingEntry
			ACCESS not-accessible
			STATUS mandatory
			DESCRIPTION
			"The DNS Server operator friendly name to unique internal identifier mapping table.

            7302/7330 ISAM FTTN : Supported
            7363 MX : Supported
            7367 SX : Supported for single Service Gateway topology only
			
			 ALCATEL NOTE: 
			TABLESIZE: 96
			DESCR:NA.
			"
		::= { sipMIB 25 }

		sipDNSServerMappingEntry OBJECT-TYPE
				SYNTAX SipDNSServerMappingEntry
				ACCESS not-accessible
				STATUS mandatory
				DESCRIPTION
					"AN entry of the sipDNSServerTable."
				INDEX {sipDNSServerMappingName}
		 ::= { sipDNSServerMappingTable 1 }

		SipDNSServerMappingEntry ::=
			SEQUENCE { 
			sipDNSServerMappingName		OCTET STRING,
			sipDNSServerMappingId			INTEGER
                 		}

		sipDNSServerMappingName OBJECT-TYPE
			SYNTAX OCTET STRING (SIZE (0..32))
			ACCESS not-accessible
			STATUS mandatory
			DESCRIPTION
				"The operator friendly name of the  DNS server. The name must be unique across all entries of the sipDNSServerMappingTable.
			ALCATEL-LUCENT NOTE:
			ACCESS:	NOT-ACCESSIBLE
			USAGE:	MANDATORY
			PERSIST:  	NA
			INSRVMOD: NO
			RANGE:	SIZE (0..32)
			DEFVALUE: 	NA
			UNITS:	NA	
			SPARSE:	NO
                 	"
        	::= { sipDNSServerMappingEntry 1 }             
          			                  	
		sipDNSServerMappingId OBJECT-TYPE
			SYNTAX INTEGER 
			ACCESS read-only
			STATUS mandatory
			DESCRIPTION 
				"The unique internal identifier of a DNS server.
			ALCATEL-LUCENT NOTE:
			ACCESS:	READ-ONLY
			USAGE:	NA
			PERSIST:  	NA
			INSRVMOD: NO
			RANGE:	(1..96)
			DEFVALUE:  NA
			UNITS:	NA
			SPARSE:    NO
			" 
		::= { sipDNSServerMappingEntry 2}

                 
-- =============================================================================
-- The sip NAPTR Query Table
-- =============================================================================                 	                 	
		sipNAPTRTable OBJECT-TYPE
			SYNTAX SEQUENCE OF SipNAPTREntry
			ACCESS not-accessible
			STATUS mandatory
			DESCRIPTION
				"The NAPTR Resource Record Table.
				Actually, this table is is NOT supported; only defined in the MIB for future usage.
		
		        7302/7330 ISAM FTTN : NOT supported
                7363 MX : NOT supported
		7367 SX : NOT Supported

			ALCATEL NOTE: 
			TABLESIZE: DEP [(NumOfLT )*(numberOfResourcein LT)
			DESCR:NA."
		::= { sipMIB 26 }

		sipNAPTREntry OBJECT-TYPE
			SYNTAX SipNAPTREntry
			ACCESS not-accessible
			STATUS mandatory
			DESCRIPTION
					"Each entry contains the information of a cached NAPTR resource record."
			INDEX {sipNAPTRSlotId }
		::= { sipNAPTRTable 1 }


		SipNAPTREntry::=
			SEQUENCE { 
			sipNAPTRSlotId		INTEGER,
			sipNAPTRDomain		OCTET STRING,
			sipNAPTRTtl			INTEGER,
			sipNAPTRClass		INTEGER, 
			sipNAPTRTtl			INTEGER,
			sipNAPTROrder		INTEGER,
			sipNAPTRPreference	INTEGER,
			sipNAPTRFlags		OCTET STRING,
			sipNAPTRService		OCTET STRING,
			sipNAPTRRegexp		OCTET STRING,
			sipNAPTRReplacement	OCTET STRING
                	 	}

			sipNAPTRSlotId OBJECT-TYPE
				SYNTAX INTEGER 
				ACCESS not-accessible
				STATUS mandatory
				DESCRIPTION 
				"The slot ID of the voice LT board at which the NAPTR resource record is cached.
				ALCATEL-LUCENT NOTE:
				ACCESS:	NOT-ACCESSIBLE
				USAGE:	NA
				PERSIST:	NO
				INSRVMOD: NA
				RANGE:	NA
				DEFVALUE:  NA
				UNITS:	NA
				SPARSE:	NO
				" 
			::= { sipNAPTREntry 1}

		sipNAPTRDomain OBJECT-TYPE
			SYNTAX OCTET STRING (SIZE(0..63))
			ACCESS read-only
			STATUS mandatory
			DESCRIPTION
				"The domain field of the NAPTR resource record.
			ALCATEL-LUCENT NOTE:
			ACCESS:	READ-ONLY
			USAGE:	NA
			PERSIST:	NO
			INSRVMOD: NA
			RANGE:	SIZE(0..63)
			DEFVALUE:  NA
			UNITS:	NA
			SPARSE:	NO
			" 
		::= { sipNAPTREntry 2 }

		sipNAPTRTtl OBJECT-TYPE
			SYNTAX INTEGER
			ACCESS read-only
			STATUS mandatory
			DESCRIPTION
				"The TTL field of the NAPTR resource record.
			ALCATEL-LUCENT NOTE:
			ACCESS:	READ-ONLY
			USAGE:	NA
			PERSIST:	NO
			INSRVMOD: NA
			RANGE:	NA
			DEFVALUE:  NA
			UNITS:	Second
			SPARSE:	NO
			" 
		::= { sipNAPTREntry 3 }

		sipNAPTRClass OBJECT-TYPE
			SYNTAX INTEGER
			ACCESS read-only
			STATUS mandatory
			DESCRIPTION
			"The Clas field s of the NAPTR resource record.
			ALCATEL-LUCENT NOTE:
			ACCESS:	READ-ONLY
			USAGE:	NA
			PERSIST:	NO
			INSRVMOD: NA
			RANGE:	NA
			DEFVALUE:  NA
			UNITS:	NA
			SPARSE:	NO
			" 
		::= { sipNAPTREntry 4 }

		sipNAPTROrder OBJECT-TYPE
			SYNTAX INTEGER
			ACCESS read-only
			STATUS mandatory
			DESCRIPTION
				"The order field of the NAPTR resource record.
			ALCATEL-LUCENT NOTE:
			ACCESS:	READ-ONLY
			USAGE:	NA
			PERSIST:	NO
			INSRVMOD: NA
			RANGE:	NA
			DEFVALUE:  NA
			UNITS:	NA
			SPARSE:	NO
			" 
		::= { sipNAPTREntry 5 }

		sipNAPTRPreference OBJECT-TYPE
			SYNTAX INTEGER
			ACCESS read-only
			STATUS mandatory
			DESCRIPTION
			"The preference field of the NAPTR resource record.
			ALCATEL-LUCENT NOTE:
			ACCESS:	READ-ONLY
			USAGE:	NA
			PERSIST:	NO
			INSRVMOD: NA
			RANGE:	NA
			DEFVALUE:  NA
			UNITS:	NA
			SPARSE:	NO
			" 
		::= { sipNAPTREntry 6 }

		sipNAPTRFlags OBJECT-TYPE
			SYNTAX OCTET STRING (SIZE(0..32))
			ACCESS read-only
			STATUS mandatory
			DESCRIPTION
			"The flags field of the NAPTR resource record.
			ALCATEL-LUCENT NOTE:
			ACCESS:	READ-ONLY
			USAGE:	NA
			PERSIST:	NO
			INSRVMOD: NA
			RANGE:	SIZE(0..32)
			DEFVALUE:  NA
			UNITS:	NA
			SPARSE:	NO
			" 
		::= { sipNAPTREntry 7 }

		sipNAPTRService OBJECT-TYPE
			SYNTAX OCTET STRING (SIZE(0..63))
			ACCESS read-only
			STATUS mandatory
			DESCRIPTION
			"The service field of the NAPTR resource record.
			ALCATEL-LUCENT NOTE:
			ACCESS:	READ-ONLY
			USAGE:	NA
			PERSIST:	NO
			INSRVMOD: NA
			RANGE:	SIZE(0..63)
			DEFVALUE:  NA
			UNITS:	NA
			SPARSE:	NO
			" 
		::= { sipNAPTREntry 8 }

		sipNAPTRRegexp OBJECT-TYPE
			SYNTAX OCTET STRING (SIZE(0..63))
			ACCESS read-only
			STATUS mandatory
			DESCRIPTION
			"The regular expression field of the NAPTR resource record.
			ALCATEL-LUCENT NOTE:
			ACCESS:	READ-ONLY
			USAGE:	NA
			PERSIST:	NO
			INSRVMOD: NA
			RANGE:	SIZE(0..63)
			DEFVALUE:  NA
			UNITS:	NA
			SPARSE:	NO
			" 
		::= { sipNAPTREntry 9 }

		sipNAPTRReplacement OBJECT-TYPE
			SYNTAX OCTET STRING (SIZE(0..63))
			ACCESS read-only
			STATUS mandatory
			DESCRIPTION
				"The replacement field of the NAPTR resource record.
			ALCATEL-LUCENT NOTE:
			ACCESS:	READ-ONLY
			USAGE:	NA
			PERSIST:	NO
			INSRVMOD: NA
			RANGE:	SIZE(0..63)
			DEFVALUE:  NA
			UNITS:	NA
			SPARSE:	NO
			" 
		::= { sipNAPTREntry 10 }

                                                                                                                                                                                                                             		 
-- =============================================================================
-- The Sip SRV Query Table
-- =============================================================================                 	                 	
		sipSRVTable OBJECT-TYPE
			SYNTAX SEQUENCE OF SipSRVEntry
			ACCESS not-accessible
			STATUS mandatory
			DESCRIPTION
				"The SRV Resource Record Table.
				Actually, this table is is NOT supported; only defined in the MIB for future usage.
		
		        7302/7330 ISAM FTTN : NOT supported
                7363 MX : NOT supported
		7367 SX : NOT Supported

			ALCATEL NOTE: 
			TABLESIZE: DEP [(NumOfLT )*(numberOfResourcein LT)
			DESCR:NA."
		::= { sipMIB 27 }

		sipSRVEntry OBJECT-TYPE
			SYNTAX SipSRVEntry
			ACCESS not-accessible
			STATUS mandatory
			DESCRIPTION
				"Each entry contains the information of a cached SRV resource record."
			INDEX {sipSRVSlotId }
		::= { sipSRVTable 1 }

		SipSRVEntry::=
			SEQUENCE { 
				sipSRVSlotId		INTEGER,
				sipSRVServer		OCTET STRING,
				sipSRVProtocol	INTEGER,
				sipSRVName		OCTET STRING,
				sipSRVTtl		INTEGER,
				sipSRVPriority	INTEGER,
				sipSRVWeight	INTEGER,
				sipSRVPort		INTEGER,
				sipSRVTarget		OCTET STRING
				}

		sipSRVSlotId OBJECT-TYPE
			SYNTAX INTEGER 
			ACCESS not-accessible
			STATUS mandatory
			DESCRIPTION 
			"The slot id of the voice LT board at which the SRV resource record is cached.
			ALCATEL-LUCENT NOTE:
			ACCESS:	NOT-ACCESSIBLE
			USAGE:	NA
			PERSIST:	NO
			INSRVMOD: NA
			RANGE:	NA
			DEFVALUE:  NA
			UNITS:	NA
			SPARSE:	NO
			" 
		::= { sipSRVEntry 1}

		sipSRVServer OBJECT-TYPE
			SYNTAX OCTET STRING (SIZE(0..63))
			ACCESS read-only
			STATUS mandatory
			DESCRIPTION
			"The server name field of the SRV resource record.
			ALCATEL-LUCENT NOTE:
			ACCESS:	READ-ONLY
			USAGE:	NA
			PERSIST:	NO
			INSRVMOD: NA
			RANGE:	SIZE(0..63)
			DEFVALUE:  NA
			UNITS:	NA
			SPARSE:	NO
			" 
		::= { sipSRVEntry 2 }

		sipSRVProtocol OBJECT-TYPE
			SYNTAX INTEGER 
			ACCESS read-only
			STATUS mandatory
			DESCRIPTION 
			"The protocol field of the SRV resource record.
			ALCATEL-LUCENT NOTE:
			ACCESS:	READ-ONLY
			USAGE:	NA
			PERSIST:	NO
			INSRVMOD: NA
			RANGE:	NA
			DEFVALUE:  NA
			UNITS:	NA
			SPARSE:	NO
			" 
		::= { sipSRVEntry 3}

		sipSRVName OBJECT-TYPE
			SYNTAX OCTET STRING (SIZE(0..63))
			ACCESS read-only
			STATUS mandatory
			DESCRIPTION
			"The service name field of the SRV resource record.
			ALCATEL-LUCENT NOTE:
			ACCESS:	READ-ONLY
			USAGE:	NA
			PERSIST:	NO
			INSRVMOD: NA
			RANGE:	SIZE(0..63)
			DEFVALUE:  NA
			UNITS:	NA
			SPARSE:	NO
			" 
                 ::= { sipSRVEntry 4 }

		sipSRVTtl OBJECT-TYPE
			SYNTAX INTEGER
			ACCESS read-only
			STATUS mandatory
			DESCRIPTION
			"The TTL field of the SRV resource record.
			ALCATEL-LUCENT NOTE:
			ACCESS:	READ-ONLY
			USAGE:	NA
			PERSIST:	NO
			INSRVMOD: NA
			RANGE:	NA
			DEFVALUE:  NA
			UNITS:	Second
			SPARSE:	NO
			" 
		::= { sipSRVEntry 5 }

		sipSRVPriority OBJECT-TYPE
			SYNTAX INTEGER
			ACCESS read-only
			STATUS mandatory
			DESCRIPTION
			"The priority field of the SRV resource record.
			ALCATEL-LUCENT NOTE:
			ACCESS:	READ-ONLY
			USAGE:	NA
			PERSIST:	NO
			INSRVMOD: NA
			RANGE:	NA
			DEFVALUE:  NA
			UNITS:	NA
			SPARSE:	NO
			" 
		::= { sipSRVEntry 6 }      

		sipSRVWeight OBJECT-TYPE
			SYNTAX INTEGER
			ACCESS read-only
			STATUS mandatory
			DESCRIPTION
			"The weight field of the SRV resource record.
			ALCATEL-LUCENT NOTE:
			ACCESS:	READ-ONLY
			USAGE:	NA
			PERSIST:	NO
			INSRVMOD: NA
			RANGE:	NA
			DEFVALUE:  NA
			UNITS:	NA
			SPARSE:	NO
			" 
		::= { sipSRVEntry 7 }

		sipSRVPort OBJECT-TYPE
			SYNTAX INTEGER
			ACCESS read-only
			STATUS mandatory
			DESCRIPTION
			"The port field of the SRV resource record.
			ALCATEL-LUCENT NOTE:
			ACCESS:	READ-ONLY
			USAGE:	NA
			PERSIST:	NO
			INSRVMOD: NA
			RANGE:	NA
			DEFVALUE:  NA
			UNITS:	NA
			SPARSE:	NO
			" 
		::= { sipSRVEntry 8 }

		sipSRVTarget OBJECT-TYPE
			SYNTAX OCTET STRING (SIZE(0..63))
			ACCESS read-only
			STATUS mandatory
			DESCRIPTION
			"The target field of the SRV resource record.
			ALCATEL-LUCENT NOTE:
			ACCESS:	READ-ONLY
			USAGE:	NA
			PERSIST:	NO
			INSRVMOD: NA
			RANGE:	SIZE(0..63)
			DEFVALUE:  NA
			UNITS:	NA
			SPARSE:	NO
			" 
		::= { sipSRVEntry 9 }

                                                                                            
-- =============================================================================
-- The Sip A Query Table
-- =============================================================================                 	                 	                 
		sipATable OBJECT-TYPE
			SYNTAX SEQUENCE OF SipAEntry
			ACCESS not-accessible
			STATUS mandatory
			DESCRIPTION
				"The A Resource Record Table.
				Actually, this table is is NOT supported; only defined in the MIB for future usage.
		
            	7302/7330 ISAM FTTN : NOT supported
                7363 MX : NOT supported
		7367 SX : NOT Supported

				ALCATEL NOTE: 
				TABLESIZE: DEP [(NumOfLT )*(numberOfResourcein LT)
				DESCR:NA."
			::= { sipMIB 28 }

		sipAEntry OBJECT-TYPE
			SYNTAX SipAEntry
			ACCESS not-accessible
			STATUS mandatory
			DESCRIPTION
				" Each entry contains the information of a cached A resource record."
			INDEX {sipASlotId }
			::= { sipATable 1 }

		SipAEntry::=
			SEQUENCE { 
				sipASlotId		INTEGER,
				sipAName		OCTET STRING,
				sipATtl		INTEGER,
				sipARdlength		INTEGER,
				sipAIpAddr		InetAddress
			}

		sipASlotId OBJECT-TYPE
			SYNTAX INTEGER 
			ACCESS not-accessible
			STATUS mandatory
			DESCRIPTION 
			"The slot id of the voice LT board at which the A resource record is cached.
			ALCATEL-LUCENT NOTE:
			ACCESS:	NOT-ACCESSIBLE
			USAGE:	NA
			PERSIST:	NO
			INSRVMOD: NA
			RANGE:	NA
			DEFVALUE:  NA
			UNITS:	NA
			SPARSE:	NO
			" 
		::= { sipAEntry 1}

		sipAName OBJECT-TYPE
			SYNTAX OCTET STRING (SIZE(0..63))
			ACCESS read-only
			STATUS mandatory
			DESCRIPTION
			"The name filed of the A resource record.
			ALCATEL-LUCENT NOTE:
			ACCESS:	READ-ONLY
			USAGE:	NA
			PERSIST:	NO
			INSRVMOD: NA
			RANGE:	SIZE(0..63)
			DEFVALUE:  NA
			UNITS:	NA
			SPARSE:	NO
			" 
		::= { sipAEntry 2 }

		sipATtl OBJECT-TYPE
			SYNTAX INTEGER
			ACCESS read-only
			STATUS mandatory
			DESCRIPTION
			"The ttl field of the A resource record.
			ALCATEL-LUCENT NOTE:
			ACCESS:	READ-ONLY
			USAGE:	NA
			PERSIST:	NO
			INSRVMOD: NA
			RANGE:	NA
			DEFVALUE:  NA
			UNITS:	Second
			SPARSE:	NO
			" 
		::= { sipAEntry 3 }

		sipARdlength OBJECT-TYPE
			SYNTAX INTEGER
			ACCESS read-only
			STATUS mandatory
			DESCRIPTION
			"The rdlen filed of the A resource record.
			ALCATEL-LUCENT NOTE:
			ACCESS:	READ-ONLY
			USAGE:	NA
			PERSIST:	NO
			INSRVMOD: NA
			RANGE:	NA
			DEFVALUE:  NA
			UNITS:	NA
			SPARSE:	NO
			" 
		::= { sipAEntry 4 }                  
                                      		                  
		sipAIpAddr OBJECT-TYPE
			SYNTAX InetAddress 
			ACCESS read-only
			STATUS mandatory
			DESCRIPTION 
			"The ip address(ipv4) field of the A resource record.
			ALCATEL-LUCENT NOTE:
			ACCESS:	READ-ONLY
			USAGE:	NA
			PERSIST:	NO
			INSRVMOD: NA
			RANGE:	NA
			DEFVALUE:  NA
			UNITS:	NA
			SPARSE:	NO
			" 
		::= { sipAEntry 5}

-- =============================================================================
-- 
-- Sip Board Stats P15m Table
--=============================================================================
		sipBoardStatsP15mTable OBJECT-TYPE
			SYNTAX SEQUENCE OF SipBoardStatsP15mEntry
			ACCESS not-accessible
			STATUS mandatory
			DESCRIPTION
				"This table contains the recent 15 minutes sip board statistics.
				The table entry is auto-created upon board initialization.
				Upon the current 15 min interval expiry, the content of the current 15 minutes interval contents is copied to the recent 15 min interval. Up to 96 recent 15 minutes intervals are supported for each voice LT board.
				The registers associated with a particular voice LT board shall be set to '0' when this voice LT board has restarted.
				In addition 
				- The Invalid data flag shall be set to 'True' to indicate that the results shown for this interval are invalid. 
				- The measured time shall be set to '0'. 
				Summarized : measuredTime: 0, invalidData: True, counter: 0.
				For NT-A or NT-B board, the RTP/Signalling related counters will be displayed as 'NA' (Not Applicable)
		
				7302/7330 ISAM-V : Supported
				7363 NGVR : NOT supported
				7367 SX : NOT Supported
		
		 		ALCATEL NOTE: 
				SUPPORT:  YES
	          	TABLESIZE:  DEP [(NumOfLT + 2) *  96]. (+2 as the entries for NT-A and NT-B are to be included.)
                                "
		 ::= { sipStatisticsAndData 9 }

		sipBoardStatsP15mEntry OBJECT-TYPE
			SYNTAX SipBoardStatsP15mEntry
			ACCESS not-accessible
			STATUS mandatory
			DESCRIPTION
				"The entry in the sipBoardStatsP15mTable.
			ALCATEL NOTE:
		        SUPPORT:  YES "
			INDEX { eqptSlotId, sipBoardStatsP15mIntervalNumber }
		::= { sipBoardStatsP15mTable 1 }


		SipBoardStatsP15mEntry ::=
			SEQUENCE { 
				sipBoardStatsP15mIntervalNumber			INTEGER,
				sipBoardStatsP15mMeasuredTime			INTEGER,
				sipBoardStatsP15mInvalidDataFlag			INTEGER,
				sipBoardStatsP15mTotalSendPackets			Counter,
				sipBoardStatsP15mTotalSendOctets			Counter,
				sipBoardStatsP15mTotalReceivePackets			Counter,
				sipBoardStatsP15mTotalReceiveOctets			Counter,
				sipBoardStatsP15mTotalLostPackets			INTEGER,
				sipBoardStatsP15mAvgJBFL				INTEGER,
				sipBoardStatsP15mAvgInterArrivalJitter			Gauge,
				sipBoardStatsP15mAvgRoundTripDelay			Gauge,
				sipBoardStatsP15mPeakInterArrivalJitter		Gauge,
				sipBoardStatsP15mPeakRoundTripDelay		Gauge,
				sipBoardStatsP15mAvgJBFLG711A			INTEGER,
				sipBoardStatsP15mAvgJBFLG711U			INTEGER,
				sipBoardStatsP15mAvgJBFLG723			INTEGER,
				sipBoardStatsP15mAvgJBFLG729			INTEGER,
				sipBoardStatsP15mAvgCPULoad				Gauge,
				sipBoardStatsP15mAvgMemUtilization			Gauge,
				sipBoardStatsP15mAvgMemPoolFree			Gauge,
				sipBoardStatsP15mAvgMemPoolUsed			Gauge,
				sipBoardStatsP15mMemPoolTotal			Gauge,
				sipBoardStatsP15mNumSparePOTSPorts		Gauge,
				sipBoardStatsP15mNumActivePOTSPorts		Gauge,
				sipBoardStatsP15mNumInactivePOTSPorts		Gauge,
				sipBoardStatsP15mRegisterReqSuccessful		INTEGER,
				sipBoardStatsP15mRegisterReqFailed			INTEGER,
				sipBoardStatsP15mRegistrationsActive		INTEGER,
				sipBoardStatsP15mOutgoingCallsAnswered		INTEGER,
				sipBoardStatsP15mIncomingCallsAnswered		INTEGER,
				sipBoardStatsP15mTimeStamp                  NetworkTimeInSeconds,
                sipBoardStatsP15mPortAvailDur           INTEGER,
                sipBoardStatsP15mPortRegDur             INTEGER,
                sipBoardStatsP15mActiveConnections      INTEGER,
                sipBoardStatsP15mBrokenPorts            INTEGER
			}

		sipBoardStatsP15mIntervalNumber OBJECT-TYPE
			SYNTAX INTEGER(1..96)
			ACCESS not-accessible
			STATUS mandatory
			DESCRIPTION
				"A number between 1 and 96, which identifies the interval for which the set of statistics is available. The 
				interval identified by I is the most recently completed 15 minutes interval, and the interval identified by N is 
				the interval immediately preceding the one identified by N-1 .
				ALCATEL-LUCENT NOTE:
				ACCESS:	NOT-ACCESSIBLE
				USAGE:	NA
				PERSIST:	NO
				INSRVMOD:	NA
				RANGE:	(1..96)
				DEFVALUE: 	NA
				UNITS:	Number
		        SPARSE:	NA
				"
		::= { sipBoardStatsP15mEntry 1 }

		sipBoardStatsP15mMeasuredTime OBJECT-TYPE
			SYNTAX INTEGER
			ACCESS read-only
			STATUS mandatory
			DESCRIPTION
				"The amount of time, measured in seconds, that statistics for this entry have been counted.
				ALCATEL-LUCENT NOTE:
				ACCESS:	READ-ONLY
				USAGE:	NA
				PERSIST:	NO
				INSRVMOD:	NA
				RANGE:	NA
				DEFVALUE: 	NA
				UNITS:	Second
		        SPARSE:	NA
				"
			::= { sipBoardStatsP15mEntry 2 }

		sipBoardStatsP15mInvalidDataFlag OBJECT-TYPE
			SYNTAX INTEGER(0..1)
			ACCESS read-only
			STATUS mandatory
			DESCRIPTION
				"This object indicates the validity of the corresponding PM data.
				It is set to 1 when the PM data is incomplete or invalid and set to 0 when the PM data is complete and valid.
				ALCATEL-LUCENT NOTE:
				ACCESS:	READ-ONLY
				USAGE:	NA
				PERSIST:	NO
				INSRVMOD:	NA
				RANGE:	(0..1)
				DEFVALUE: 	NA
				UNITS:	NA
		        SPARSE:	NA
				"
		::= { sipBoardStatsP15mEntry 3 }

		sipBoardStatsP15mTotalSendPackets OBJECT-TYPE
			SYNTAX Counter
			ACCESS read-only
			STATUS mandatory
			DESCRIPTION
			"The total amount of RTP packets transmitted by all SIP terminations of this board during this 15 min interval.
			ALCATEL-LUCENT NOTE:
			ACCESS:	READ-ONLY
			USAGE:	NA
			PERSIST:	NO
			INSRVMOD:	NA
			RANGE:	NA
			DEFVALUE: 	NA
			UNITS:	Packets
		    SPARSE:	NA
			"
		::= { sipBoardStatsP15mEntry 4 }

		sipBoardStatsP15mTotalSendOctets OBJECT-TYPE
			SYNTAX Counter
			ACCESS read-only
			STATUS mandatory
			DESCRIPTION
				"The total amount of RTP octets transmitted by all SIP terminations of this board during this 15 min interval.
				ALCATEL-LUCENT NOTE:
				ACCESS:	READ-ONLY
				USAGE:	NA
				PERSIST:	NO
				INSRVMOD:	NA
				RANGE:	NA
				DEFVALUE: 	NA
				UNITS:	Octets
		        SPARSE:	NA
				"
		::= { sipBoardStatsP15mEntry 5 }

		sipBoardStatsP15mTotalReceivePackets OBJECT-TYPE
			SYNTAX Counter
			ACCESS read-only
			STATUS mandatory
			DESCRIPTION
				"The total amount of RTP packets received by all SIP terminations of this board during this 15 min interval.
				ALCATEL-LUCENT NOTE:
				ACCESS:	READ-ONLY
				USAGE:	NA
				PERSIST:	NO
				INSRVMOD:	NA
				RANGE:	NA
				DEFVALUE: 	NA
				UNITS:	Packets
		        SPARSE:	NA
			"
		::= { sipBoardStatsP15mEntry 6 }

		sipBoardStatsP15mTotalReceiveOctets OBJECT-TYPE
			SYNTAX Counter
			ACCESS read-only
			STATUS mandatory
			DESCRIPTION
			"The total amount of RTP octets received by all SIP terminations of this board during this 15 min interval.
			ALCATEL-LUCENT NOTE:
			ACCESS:	READ-ONLY
			USAGE:	NA
			PERSIST:	NO
			INSRVMOD:	NA
			RANGE:	NA
			DEFVALUE: 	NA
			UNITS:	Octets
		    SPARSE:	NA
			"
		::= { sipBoardStatsP15mEntry 7 }

		sipBoardStatsP15mTotalLostPackets OBJECT-TYPE
			SYNTAX INTEGER
			ACCESS read-only
			STATUS mandatory
			DESCRIPTION
			"The total amount of lost RTP packets for all SIP terminations of this board during this 15 min interval.
			The amount of packets lost is defined to be the amount of packets expected less the amount of packets actually received:
			lost = expected - s->received;
			Since this signed number is carried in 24 bits, it should be clamped at 0x7fffff for positive loss or 0x800000
			for negative loss rather than wrapping around.
			ALCATEL-LUCENT NOTE:
			ACCESS:	READ-ONLY
			USAGE:	NA
			PERSIST:	NO
			INSRVMOD:	NA
			RANGE:	NA
			DEFVALUE: 	NA
			UNITS:	Packets
		    SPARSE:	NA
			"
		::= { sipBoardStatsP15mEntry 8 }

		sipBoardStatsP15mAvgJBFL OBJECT-TYPE
			SYNTAX INTEGER(0..100)
			ACCESS read-only
			STATUS mandatory
			DESCRIPTION
			" Average Jitter Buffer Fill Level measured over all SIP terminations connected to a voice LT board 
			during the receipt of RTP streams in the course of this 15 min interval. The measurement includes the 
			receipt of RTP packets for both, originating and terminating calls. The measured average JBFL is expressed 
			as a percentage.
			ALCATEL-LUCENT NOTE:
			ACCESS:	READ-ONLY
			USAGE:	NA
			PERSIST:	NO
			INSRVMOD:	NA
			RANGE:	(0..100)
			DEFVALUE: 	NA
			UNITS:	Percentage
		    SPARSE:	NA
			"
		::= { sipBoardStatsP15mEntry 9 }

		sipBoardStatsP15mAvgInterArrivalJitter OBJECT-TYPE
			SYNTAX Gauge
			ACCESS read-only
			STATUS mandatory
			DESCRIPTION
			" Average inter-arrival Jitter measured over all SIP termination lines connected to a voice LT board 
			during the receipt of RTP streams in the course of this 15 min interval. The measurement includes the 
			receipt of RTP packets for both, originating and terminating calls. The measured average JBFL is expressed 
			in milli-seconds.
			ALCATEL-LUCENT NOTE:
			ACCESS:	READ-ONLY
			USAGE:	NA
			PERSIST:	NO
			INSRVMOD:	NA
			RANGE:	NA
			DEFVALUE: 	NA
			UNITS:	Milli-Second
		    SPARSE:	NA
			"
		::= { sipBoardStatsP15mEntry 10 }

		sipBoardStatsP15mAvgRoundTripDelay OBJECT-TYPE
			SYNTAX Gauge
			ACCESS read-only
			STATUS mandatory
			DESCRIPTION
			" Average Round Trip Delay measured over all SIP termination lines connected to a voice LT board 
            during the receipt of RTP streams in the course of this 15 min interval. The measurement includes the 
			receipt of RTP packets for both, originating and terminating calls. The measured average JBFL is expressed 
			in milli-seconds.
			ALCATEL-LUCENT NOTE:
			ACCESS:	READ-ONLY
			USAGE:	NA
			PERSIST:	NO
			INSRVMOD:	NA
			RANGE:	NA
			DEFVALUE: 	NA
			UNITS:	Milli-Second
		    SPARSE:	NA
			"
		::= { sipBoardStatsP15mEntry 11 }

		sipBoardStatsP15mPeakInterArrivalJitter OBJECT-TYPE
			SYNTAX Gauge
			ACCESS read-only
			STATUS mandatory
			DESCRIPTION
			" Peak inter-arrival Jitter measured over all the subscriber lines connected to a voice LT board 
			during the receipt of RTP streams in the course of this 15 min interval. The measurement includes the 
			receipt of RTP packets for both, originating and terminating calls. The measured average JBFL is expressed 
			in milli-seconds.
			ALCATEL-LUCENT NOTE:
			ACCESS:	READ-ONLY
			USAGE:	NA
			PERSIST:	NO
			INSRVMOD:	NA
			RANGE:	NA
			DEFVALUE: 	NA
			UNITS:	Milli-Second
		    SPARSE:	NA
			"
		::= { sipBoardStatsP15mEntry 12 }


		sipBoardStatsP15mPeakRoundTripDelay OBJECT-TYPE
			SYNTAX Gauge
			ACCESS read-only
			STATUS mandatory
			DESCRIPTION
			" Peak Round Trip Delay measured over all SIP termination lines connected to a voice LT board 
			during the receipt of RTP streams in the course of this 15 min interval. The measurement includes the 
			receipt of RTP packets for both, originating and terminating calls. The measured average JBFL is expressed 
			in milli-seconds.
			ALCATEL-LUCENT NOTE:
			ACCESS:	READ-ONLY
			USAGE:	NA
			PERSIST:	NO
			INSRVMOD:	NA
			RANGE:	NA
			DEFVALUE: 	NA
			UNITS:	Milli-Second
		    SPARSE:	NA
			"
		::= { sipBoardStatsP15mEntry 13 }

		sipBoardStatsP15mAvgJBFLG711A OBJECT-TYPE
			SYNTAX INTEGER(0..100)
			ACCESS read-only
			STATUS mandatory
			DESCRIPTION
			" Average Jitter Buffer Fill Level measured over all SIP termination lines connected to a voice LT board 
			during the receipt of RTP streams encoded with G711_a in the course of this 15 min interval. The 
			measurement includes the receipt of RTP packets for both, originating and terminating calls. The measured 
			average JBFL is expressed as a percentage.
			ALCATEL-LUCENT NOTE:
			ACCESS:	READ-ONLY
			USAGE:	NA
			PERSIST:	NO
			INSRVMOD:	NA
			RANGE:	(0..100)
			DEFVALUE: 	NA
			UNITS:	Percentage
		    SPARSE:	NA
			"
		::= { sipBoardStatsP15mEntry 14 }

		sipBoardStatsP15mAvgJBFLG711U OBJECT-TYPE
			SYNTAX INTEGER(0..100)
			ACCESS read-only
			STATUS mandatory
			DESCRIPTION
			" Average Jitter Buffer Fill Level measured over all subscriber lines connected to a voice LT board 
			during the receipt of RTP streams encoded with G711_u in the course of this 15 min interval. The 
			measurement includes the receipt of RTP packets for both, originating and terminating calls. The measured 
			average JBFL is expressed as a percentage.
			ALCATEL-LUCENT NOTE:
			ACCESS:	READ-ONLY
			USAGE:	NA
			PERSIST:	NO
			INSRVMOD:	NA
			RANGE:	(0..100)
			DEFVALUE: 	NA
			UNITS:	Percentage
		    SPARSE:	NA
			"
		::= { sipBoardStatsP15mEntry 15 }


		sipBoardStatsP15mAvgJBFLG723 OBJECT-TYPE
			SYNTAX INTEGER(0..100)
			ACCESS read-only
			STATUS mandatory
			DESCRIPTION
			" Average Jitter Buffer Fill Level measured over all subscriber lines connected to a voice LT board 
			during the receipt of RTP streams encoded with G723 in the course of this 15 min interval. The measurement 
			includes the receipt of RTP packets for both, originating and terminating calls. The measured average 
			JBFL is expressed as a percentage.
			ALCATEL-LUCENT NOTE:
			ACCESS:	READ-ONLY
			USAGE:	NA
			PERSIST:	NO
			INSRVMOD:	NA
			RANGE:	(0..100)
			DEFVALUE: 	NA
			UNITS:	Percentage
		    SPARSE:	NA
			"
		::= { sipBoardStatsP15mEntry 16 }

		sipBoardStatsP15mAvgJBFLG729 OBJECT-TYPE
			SYNTAX INTEGER(0..100)
			ACCESS read-only
			STATUS mandatory
			DESCRIPTION
			" Average Jitter Buffer Fill Level measured over all subscriber lines connected to a voice LT board 
			during the receipt of RTP streams encoded with G729 in the course of this 15 min interval. The measurement 
			includes the receipt of RTP packets for both, originating and terminating calls. The measured average 
			JBFL is expressed as a percentage.
			ALCATEL-LUCENT NOTE:
			ACCESS:	READ-ONLY
			USAGE:	NA
			PERSIST:	NO
			INSRVMOD:	NA
			RANGE:	(0..100)
			DEFVALUE: 	NA
			UNITS:	Percentage
		    SPARSE:	NA
			"
		::= { sipBoardStatsP15mEntry 17 }

		sipBoardStatsP15mAvgCPULoad OBJECT-TYPE
			SYNTAX Gauge
			ACCESS read-only
			STATUS mandatory
			DESCRIPTION
			" Average CPU load measured at a board (voice LT board / NT board) in the course of this 15 min interval. The measured average CPU load is expressed as a percentage. 
			ALCATEL-LUCENT NOTE:
			ACCESS:	READ-ONLY
			USAGE:	NA
			PERSIST:	NO
			INSRVMOD:	NA
			RANGE:	(0..100)
			DEFVALUE: 	NA
			UNITS:	Percentage
		    SPARSE:	NA
			"
		::= { sipBoardStatsP15mEntry 18 }

		sipBoardStatsP15mAvgMemUtilization OBJECT-TYPE
			SYNTAX Gauge
			ACCESS read-only
			STATUS mandatory
			DESCRIPTION
			" Average amount of semi and dynamic memory been used at a board (voice LT board / NT board) in the
			course of this 15 min interval. The measured value is expressed as a percentage.
			ALCATEL-LUCENT NOTE:
			ACCESS:	READ-ONLY
			USAGE:	NA
			PERSIST:	NO
			INSRVMOD:	NA
			RANGE:	(0..100)
			DEFVALUE: 	NA
			UNITS:	Percentage
		    SPARSE:	NA
			"
		::= { sipBoardStatsP15mEntry 19}

		sipBoardStatsP15mAvgMemPoolFree OBJECT-TYPE
			SYNTAX Gauge
			ACCESS read-only
			STATUS mandatory
			DESCRIPTION
			" Average amount of free semi and dynamic memory measured at a board (voice LT board / 
			NT board) in the course of a this 15 min interval. The measured value is expressed in Mbytes..
			ALCATEL-LUCENT NOTE:
			ACCESS:	READ-ONLY
			USAGE:	NA
			PERSIST:	NO
			INSRVMOD:	NA
			RANGE:	NA
			DEFVALUE: 	NA
			UNITS:	Mbyte
		    SPARSE:	NA
			"
		::= { sipBoardStatsP15mEntry 20}

		sipBoardStatsP15mAvgMemPoolUsed OBJECT-TYPE
			SYNTAX Gauge
			ACCESS read-only
			STATUS mandatory
			DESCRIPTION
			" Average amount of semi and dynamic memory been used at a board (voice LT board / 
			NT board) in the course of this 15 min interval. The measured value is expressed in Mbytes.
			ALCATEL-LUCENT NOTE:
			ACCESS:	READ-ONLY
			USAGE:	NA
			PERSIST:	NO
			INSRVMOD:	NA
			RANGE:	NA
			DEFVALUE: 	NA
			UNITS:	Mbyte
		    SPARSE:	NA
			"
		::= { sipBoardStatsP15mEntry 21}

		sipBoardStatsP15mMemPoolTotal OBJECT-TYPE
			SYNTAX Gauge
			ACCESS read-only
			STATUS mandatory
			DESCRIPTION
			" The total amount of semi and dynamic memory available at a board (voice LT board /
			NT board. It is expressed in Mbytes
			ALCATEL-LUCENT NOTE:
			ACCESS:	READ-ONLY
			USAGE:	NA
			PERSIST:	NO
			INSRVMOD:	NA
			RANGE:	NA
			DEFVALUE: 	NA
			UNITS:	Mbyte
		    SPARSE:	NA
			"
		::= { sipBoardStatsP15mEntry 22}

		sipBoardStatsP15mNumSparePOTSPorts  OBJECT-TYPE
			SYNTAX Gauge
			ACCESS read-only
			STATUS mandatory
			DESCRIPTION
            "The number of free voice ports in the line card that have not been created on voice line cards that have
            already been planned. The value is independent of the control network registration status and is recorded
            at the end of the 15 min integration period. 
			ALCATEL-LUCENT NOTE:
			ACCESS:	READ-ONLY
			USAGE:	NA
			PERSIST:	NO
			INSRVMOD:	NA
			RANGE:	NA
			DEFVALUE: 	NA
			UNITS:	Number
		    SPARSE:	NA
			"
		::= { sipBoardStatsP15mEntry 23 }

		sipBoardStatsP15mNumActivePOTSPorts OBJECT-TYPE
			SYNTAX Gauge
			ACCESS read-only
			STATUS mandatory
			DESCRIPTION
            "The number of created voice ports in the line card that are administratively enabled. The value is
            independent of the control network registration status and is recorded at the end of the 15 min
            integration period.
            A 'fully configured' port may use the pre-provisioned default configuration of the voice port, SIP User Agent
            parameters at startup of the line card or an operator-specific configuration that has replaced this default
            configuration.
			ALCATEL-LUCENT NOTE:
			ACCESS:	READ-ONLY
			USAGE:	NA
			PERSIST:	NO
			INSRVMOD:	NA
			RANGE:	NA
			DEFVALUE: 	NA
			UNITS:	Number
		    SPARSE:	NA
			"
		::= { sipBoardStatsP15mEntry 24 }

		sipBoardStatsP15mNumInactivePOTSPorts OBJECT-TYPE
			SYNTAX Gauge
			ACCESS read-only
			STATUS mandatory
			DESCRIPTION
            "The number of created voice ports in the line card that are administratively disabled.  The value is
            independent of the control network registration status and is recorded at the end of the 15 min
            integration period. 
            The port may have been created though pre-provisioning of the default configuration of the voice 
            port, SIP User Agent parameters at startup of the line card or through specific operator provisioning of these 
            parameters.
			ALCATEL-LUCENT NOTE:
            ACCESS:	READ-ONLY
            USAGE:	NA
            PERSIST:	NO
            INSRVMOD:	NA
            RANGE:	NA
            DEFVALUE: 	NA
            UNITS:	Number
            SPARSE:	NA
            "
		::= { sipBoardStatsP15mEntry 25 }

		sipBoardStatsP15mRegisterReqSuccessful OBJECT-TYPE
			SYNTAX INTEGER
			ACCESS read-only
			STATUS mandatory
			DESCRIPTION
				" The amount of (re-)registration requests which are successfully replied in this 15min interval. The amount of (re-)registration requests which are successfully replied in this current 15min interval.                   A (re-)registration request is considered successful when a response = 200 OK is returned by the registrar to the (re-)register request AND the contact address send by the MSAN in the (re-)REGISTER request is:
                  1. present in a contact header field of the 200 OK returned by the registrar AND this contact header field has an expires parameter with value set to value <> 0.
                  2. present in a contact header field of the 200 OK returned by the registrar which has no expires parameter AND the 200 OK has an expires header field present with value set to value <> 0.

				ALCATEL-LUCENT NOTE:
				ACCESS:	READ-ONLY
				USAGE:	NA
				PERSIST:	NO
				INSRVMOD:	NA
				RANGE:	NA
				DEFVALUE: 	NA
				UNITS:	Number
		                SPARSE:	NA
				"
		::= { sipBoardStatsP15mEntry 26 }


		sipBoardStatsP15mRegisterReqFailed OBJECT-TYPE
			SYNTAX INTEGER
			ACCESS read-only
			STATUS mandatory
			DESCRIPTION
				" The amount of (re-)registration requests which failed in this 15 min interval. 
                                Failed means that:
                                1. A response <> 200 OK was retruned by the SIP First Hop server.
                                2. Registrar or that SIP transaction time-out occured.
                                3. The contact address send by the MSAN in the (re-)REGISTER request
                                   is present in a contact header field of the 200 OK returned by the registrar
                                   AND this contact header field has an expires parameter with value set to value = 0.
                               4. The contact address send by the MSAN in the (re-)REGISTER request is present in
                                   a contact header field of the 200 OK returned by the registrar which has no expires
                                 parameter AND the 200 OK has an expires header field present with value set to value = 0

				ALCATEL-LUCENT NOTE:
				ACCESS:	READ-ONLY
				USAGE:	NA
				PERSIST:	NO
				INSRVMOD:	NA
				RANGE:	NA
				DEFVALUE: 	NA
				UNITS:	Number
		                SPARSE:	NA
				"
		::= { sipBoardStatsP15mEntry 27 }

		sipBoardStatsP15mRegistrationsActive OBJECT-TYPE
			SYNTAX INTEGER
			ACCESS read-only
			STATUS mandatory
			DESCRIPTION
				" The amount of registrations being active at a subscriber port at the end of this 15 min interval. 
                In the current implementation, only 1 registration can be active at a subscriber port at a time. 
                An active registration is counted when a registration request has been successfully completed in the past 
                (200 OK received to register request with 'expire header' time <> 0) and the register expiration interval 
                hasn't expired.
				ALCATEL-LUCENT NOTE:
				ACCESS:	READ-ONLY
				USAGE:	NA
				PERSIST:	NO
				INSRVMOD:	NA
				RANGE:	NA
				DEFVALUE: 	NA
				UNITS:	Number
		        SPARSE:	NA
				"
		::= { sipBoardStatsP15mEntry 28 }

		sipBoardStatsP15mOutgoingCallsAnswered OBJECT-TYPE
			SYNTAX INTEGER
			ACCESS read-only
			STATUS mandatory
			DESCRIPTION
			" The amount of outgoing call attempts in this 15 min interval for which an initial INVITE request 
            is sent AND for which a response is received. The system allows to provision what kind of response 
            must be received as to be counted as a successful outgoing call attempt. The system offers the following options : 
			o Any response be received (irrespective of whether this is a successful or unsuccessful response). 
			o A successful response be received (180 or 200 response only).
			ALCATEL-LUCENT NOTE:
			ACCESS:	READ-ONLY
			USAGE:	NA
			PERSIST:	NO
			INSRVMOD:	NA
			RANGE:	NA
			DEFVALUE: 	NA
			UNITS:	Number
		    SPARSE:	NA
			"
		::= { sipBoardStatsP15mEntry 29 }

		sipBoardStatsP15mIncomingCallsAnswered OBJECT-TYPE
			SYNTAX INTEGER
			ACCESS read-only
			STATUS mandatory
			DESCRIPTION
			" The amount of incoming call attempts in this 15 min interval for which a SIP response is sent being the result of the off-hook event been detected. The system allows to provision the kind of response that will be considered as to be counted as a successful incoming call attempt. The system offers the following options : 
			o Any response be sent. 
			o 180 response be sent.
			ALCATEL-LUCENT NOTE:
			ACCESS:	READ-ONLY
			USAGE:	NA
			PERSIST:	NO
			INSRVMOD:	NA
			RANGE:	NA
			DEFVALUE: 	NA
			UNITS:	Number
		    SPARSE:	NA
			"
		::= { sipBoardStatsP15mEntry 30 }

        sipBoardStatsP15mTimeStamp OBJECT-TYPE
            SYNTAX NetworkTimeInSeconds
            ACCESS read-only
            STATUS mandatory
            DESCRIPTION
            "The absolute start time of the 15 min interval.
            ALCATEL-LUCENT NOTE:
            ACCESS: READ-ONLY
            USAGE: NA
            PERSIST: NO
            INSRVMOD: NA
            RANGE: (0..4294967295)
            DEFVALUE: 0
            UNITS: seconds
            SPARSE: NA
            "
        ::= { sipBoardStatsP15mEntry  31 }

        sipBoardStatsP15mPortAvailDur OBJECT-TYPE
            SYNTAX INTEGER
            ACCESS read-only
            STATUS mandatory
            DESCRIPTION
            " The total amount of time that the SIP terminations configured at the voice LT board are considered to be
                administratively available.
                This is the elapse time that all, the port's administrative state as well as its higher layer object’ administrative
                status  (SIP User Agent admin state, SIP User Agent Access Point admin state, Voice Service Provider admin
                state) are all set to unlocked”
                Or in other words, from the moment that at least one of the above mentioned 4 administrative states is
                changed to locked, the system shall stop counting for the AvailableDur counter, as the port is considered
                to be not available from that moment onwards.
                There is no dependency on the operational state of the ports.

                    ALCATEL-LUCENT NOTE:
            ACCESS: READ-ONLY
            USAGE:  NA
            PERSIST:    NO
            INSRVMOD:   NA
            RANGE:  NA
            DEFVALUE:   NA
            UNITS:  Seconds
            SPARSE: NA
            "
        ::= { sipBoardStatsP15mEntry 32 }

        sipBoardStatsP15mPortRegDur OBJECT-TYPE
            SYNTAX INTEGER
            ACCESS read-only
            STATUS mandatory
            DESCRIPTION
            " The total amount of time that from an MSAN point of view, the SIP terminations configured at a voice LT
                board are considered to be successfully registered at the IMS core.
                Usually the MSAN registers or de-registers a SIP termination to the IMS core. However, it should be noted that
                a registration can also autonomously be deleted by the IMS core.  Such registration state change is not
                explicitly notified to the MSAN (unless the reg event package would be supported and subscribed by the
                MSAN, which is actually not the case).
                The total amount of time that from an MSAN point of view, a SIP termination is considered to be successfully
                registered at the IMS core,  may be different from that same SIP termination to be successfully registered from
                an IMS core point of view.
                When the MSAN considers a SIP termination to be successfully registered at the IMS core, its operational state
                is set to UP.
                When the MSAN considers a SIP termination not to be registered at the IMS core, its operational state is set to
                down.
                The port registration duration counter of a particular SIP termination shall start counting upon the receipt of
                the 200 OK to the initial registration request for that same SIP termination.
                The registerDur counting for a particular SIP termination shall stop  :
                 upon the receipt of the 200 OK to the de-registration request for that same SIP termination.
                (A de-registration request is sent as a consequence of the following actions : SIP Termination Admin
                state change from up to down, SIP User Agent Admin state change from up to down, SIP User Agent
                Access Point Admin state change from up to down, VSP Admin state change from up to down, Ground
                key / Port High temperature alarm raised at the port, ...etc.)
                 Upon Fail-back, requiring a de-register of the SIP terminations at the secondary SIP server.
                 Upon Deliberate Update, requiring a de-register of the SIP terminations at the current Primary SIP server.
                 Upon the receipt of an error response to a SIP RE-REGISTER request, with one of the following error codes:
                408 (Request Timeout), 500 (Server Internal Error), 503 (Service Unavailable), 504 (Server Time-Out)
                or 600 (Busy Everywhere) response.
                 Upon the detection of a non-recoverable error requiring a fail-over and requiring a new initial registration
                to be done to the secondary SIP server.
                 Upon the receipt of an error response to a SIP INVITE request, with an error code for which the SSP has
                been provisioned with an error-code clause that, as recovery action,  requires a new initial register to
                be sent.
                It shall be noted that in case the SIP termination is still registered at the IMS while its operational state at the
                MSAN side is set to disabled (meaning that the MSAN considers that same SIP termination as being NOT
                registered ) or no longer configured, that upon the receipt of an incoming SIP Invite request for that same SIP
                termination the following error response is returned :
         
                INVITE(User-x)  404 Not Found               user-x is not configured (user not linked to any SIP termination )
                INVITE(User-x)  404 Not Found               user-x has been deleted (sip termination deleted)
                INVITE          480 Temporarily Unavailable user-x is configured though is not registered 
                                                            (operational status = down, reason= registering/registerfailure) though port is admin=up
                INVITE          480 Temporarily Unavailable user-x is configured though SIP termination is admin-down
                INVITE          480 Temporarily Unavailable user-x is configured though SIP termination is FAULTY (ground key alarm)



            ALCATEL-LUCENT NOTE:
            ACCESS: READ-ONLY
            USAGE:  NA
            PERSIST:    NO
            INSRVMOD:   NA
            RANGE:  NA
            DEFVALUE:   NA
            UNITS:  Seconds
            SPARSE: NA
            "
        ::= { sipBoardStatsP15mEntry 33}

        sipBoardStatsP15mActiveConnections OBJECT-TYPE
            SYNTAX INTEGER
            ACCESS read-only
            STATUS mandatory
            DESCRIPTION
                    " The number of incoming or outgoing stable call connections that are active at the Line Card.
                    An active connection is considered a call in stable phase regardless of whether this call is on hold (3 pty call)
                    or not on hold (basic call & 3 pty call).
                    In the scope of this counter, a connection is considered to be active from the moment an outgoing or
                    incoming call attempt is replied with a 200 OK (200 OK sent to incoming call attempt or 200 OK received
                    on outgoing call attempt.
                    The previous interval contains a snapshot of the number of connections that were active at the Line Card at
                    the at the start of the current interval for which this previous interval has been created. 

            ALCATEL-LUCENT NOTE:
            ACCESS: READ-ONLY
            USAGE:  NA
            PERSIST:    NO
            INSRVMOD:   NA
            RANGE:  NA
            DEFVALUE:   NA
            UNITS:  Number
            SPARSE: NA
            "
        ::= { sipBoardStatsP15mEntry 34 }

        sipBoardStatsP15mBrokenPorts OBJECT-TYPE
            SYNTAX INTEGER
            ACCESS read-only
            STATUS mandatory
            DESCRIPTION
                        " The number of ports that, due to a HW failure, cannot be operational.
                    The counter is event driven, upon both, HW fault detection and HW fault resolved/disappearing.
                    The counter can be reset upon the beginning of a new current interval since the HW fault event for an
                    already existing HW fault is not going to be received once again at the start of a new interval.  (HW faults that
                    were detected in an earlier interval and that were still not resolved).
                    The following fault events can be detected by the SW at the NPOT-B/NPOT-C voice LT board 
                       VP_DEV_EVID_BAT_FLT     = 0x0001,   /** Device detected battery fault       */
                       VP_DEV_EVID_CLK_FLT     = 0x0002,   /** Device detected clock fault         */
                       VP_LINE_EVID_THERM_FLT  = 0x0004,       /** Thermal Overload condition      */
                       VP_LINE_EVID_DC_FLT     = 0x0008,   /** DC Fault detected on line       */
                       VP_LINE_EVID_AC_FLT     = 0x0010,   /** AC Fault detected on line       */
                       VP_LINE_EVID_SYNC_FLT   = 0x0020,       /** SLAC Synchronization fault      */
                       VP_LINE_EVID_RES_LEAK_FLT   = 0x0040,   /** Low loop resistance while on-hook   */
                       VP_LINE_EVID_SEAL_CUR_FLT   = 0x0080,   /** Sealing current error           */
                       VP_DEV_EVID_WDT_FLT = 0x2000,       /** Watchdog timer fault            */
                       VP_DEV_EVID_EVQ_OFL_FLT = 0x4000,   /** event queue overflow fault      */
                       VP_DEV_EVID_SYSTEM_FLT  = 0x8000,       /** VCP2 system fault           */

                    The previous interval reflects the number of broken ports at the Line Card at the start of the current interval for which this previous interval has been created. 

            ALCATEL-LUCENT NOTE:
            ACCESS: READ-ONLY
            USAGE:  NA
            PERSIST:    NO
            INSRVMOD:   NA
            RANGE:  NA
            DEFVALUE:   NA
            UNITS:  Number
            SPARSE: NA
            "
        ::= { sipBoardStatsP15mEntry 35 }


-- =============================================================================
-- 
-- Sip Board Stats C15m Table
--=============================================================================
		sipBoardStatsC15mTable OBJECT-TYPE
			SYNTAX SEQUENCE OF SipBoardStatsC15mEntry
			ACCESS not-accessible
			STATUS mandatory
			DESCRIPTION
				"This table contains the current 15 minute board statistics.
				The table entry is auto-created upon board initialization.
				The registers associated with a particular voice LT board shall be set to '0' when this voice LT board has restarted
				In addition 
				- The Invalid data flag shall be set to 'False'. 
				- The measured time shall be set to '0'.
				Summarized : measuredTime: 0, invalidData: False, counter: 0.
				For NT-A or NT-B board, the RTP/Signalling related counters will be displayed as 'NA' (Not Applicable) 
				
			7302/7330 ISAM-V : Supported
			7363 NGVR : NOT supported
			7367 SX : NOT Supported
				
			ALCATEL NOTE: 
			SUPPORT:  YES
			TABLESIZE:  DEP [NumOfLT + 2].  (+2 as the entries for NT-A and NT-B are to be included.)
                       "
		::= { sipStatisticsAndData 10 }

		sipBoardStatsC15mEntry OBJECT-TYPE
			SYNTAX SipBoardStatsC15mEntry
			ACCESS not-accessible
			STATUS mandatory
			DESCRIPTION
				"The entry in the sipBoardStatsC15mTable.
			ALCATEL NOTE:
			SUPPORT:  YES "
			INDEX { eqptSlotId }
		::= { sipBoardStatsC15mTable 1 }

		SipBoardStatsC15mEntry ::=
			SEQUENCE { 
			sipBoardStatsC15mMeasuredTime			    INTEGER,
			sipBoardStatsC15mInvalidDataFlag			INTEGER,
			sipBoardStatsC15mTotalSendPackets			Counter,
			sipBoardStatsC15mTotalSendOctets			Counter,
			sipBoardStatsC15mTotalReceivePackets		Counter,
			sipBoardStatsC15mTotalReceiveOctets			Counter,
			sipBoardStatsC15mTotalLostPackets			INTEGER,
			sipBoardStatsC15mAvgJBFL				    INTEGER,
			sipBoardStatsC15mAvgInterArrivalJitter		Gauge,
			sipBoardStatsC15mAvgRoundTripDelay	    	Gauge,
			sipBoardStatsC15mPeakInterArrivalJitter		Gauge,
			sipBoardStatsC15mPeakRoundTripDelay		    Gauge,
			sipBoardStatsC15mAvgJBFLG711A			    INTEGER,
			sipBoardStatsC15mAvgJBFLG711U			    INTEGER,
			sipBoardStatsC15mAvgJBFLG723			    INTEGER,
			sipBoardStatsC15mAvgJBFLG729			    INTEGER,
			sipBoardStatsC15mAvgCPULoad			        Gauge,
			sipBoardStatsC15mAvgMemUtilization		    Gauge,
			sipBoardStatsC15mAvgMemPoolFree			    Gauge,
			sipBoardStatsC15mAvgMemPoolUsed			    Gauge,
			sipBoardStatsC15mMemPoolTotal			    Gauge,
			sipBoardStatsC15mNumSparePOTSPorts		    Gauge,
			sipBoardStatsC15mNumActivePOTSPorts		    Gauge,
			sipBoardStatsC15mNumInactivePOTSPorts		Gauge,
			sipBoardStatsC15mRegisterReqSuccessful		INTEGER,
			sipBoardStatsC15mRegisterReqFailed			INTEGER,
			sipBoardStatsC15mRegistrationsActive		INTEGER,
			sipBoardStatsC15mOutgoingCallsAnswered	    INTEGER,
			sipBoardStatsC15mIncomingCallsAnswered	    INTEGER,
            sipBoardStatsC15mPortAvailDur               INTEGER,
            sipBoardStatsC15mPortRegDur                 INTEGER,
            sipBoardStatsC15mActiveConnections          INTEGER,
            sipBoardStatsC15mBrokenPorts                INTEGER
			}


		sipBoardStatsC15mMeasuredTime OBJECT-TYPE
			SYNTAX INTEGER
			ACCESS read-only
			STATUS mandatory
			DESCRIPTION
				"The amount of time, measured in seconds, that statistics for this entry have been counted.
				ALCATEL NOTE:
					SUPPORT:   YES
					PERSIST:   NO
					INSRVMOD:  NA
					RANGE:     NA	
					DEFVALUE:  NA
					UNITS:	   Seconds
				"
			::= { sipBoardStatsC15mEntry 1 }

		sipBoardStatsC15mInvalidDataFlag OBJECT-TYPE
			SYNTAX INTEGER(0..1)
			ACCESS read-only
			STATUS mandatory
			DESCRIPTION
					"This object indicates the validity of the corresponding PM data.
				It is set to 1 when the PM data is incomplete or invalid and set to 0 when the PM data is complete and valid.
				ALCATEL-LUCENT NOTE:
				ACCESS:	  READ-ONLY
				USAGE:	  NA
				PERSIST:  NO
				INSRVMOD: NA
				RANGE:    (0..1)
				DEFVALUE: NA
				UNITS:	  NA
		        SPARSE:   NA
				"
		::= { sipBoardStatsC15mEntry 2 }


		sipBoardStatsC15mTotalSendPackets OBJECT-TYPE
			SYNTAX Counter
			ACCESS read-only
			STATUS mandatory
			DESCRIPTION
			"The total amount of RTP packets transmitted by all SIP termination lines of this board in the current 15min
			 interval.
			ALCATEL-LUCENT NOTE:
			ACCESS:	   READ-ONLY
			USAGE:	   NA
			PERSIST:   NO
			INSRVMOD:  NA
			RANGE:	   NA
			DEFVALUE:  NA
			UNITS:	   Packets
		    SPARSE:	   NA
			"
		::= { sipBoardStatsC15mEntry 3 }

		sipBoardStatsC15mTotalSendOctets OBJECT-TYPE
			SYNTAX Counter
			ACCESS read-only
			STATUS mandatory
			DESCRIPTION
			"The total amount of RTP octets transmitted by all SIP terminations lines of this board in the current 15 min
			interval.
				ALCATEL-LUCENT NOTE:
				ACCESS:   READ-ONLY
				USAGE:    NA
				PERSIST:  NO
				INSRVMOD: NA
				RANGE:    NA
				DEFVALUE: NA
				UNITS:    Octets
		        SPARSE:   NA
				"
		::= { sipBoardStatsC15mEntry 4 }

		sipBoardStatsC15mTotalReceivePackets OBJECT-TYPE
			SYNTAX Counter
			ACCESS read-only
			STATUS mandatory
			DESCRIPTION
				"The total amount of RTP packets received by all SIP termination lines of this board in the current 15 min interval.
				ALCATEL-LUCENT NOTE:
				ACCESS:   READ-ONLY
				USAGE:	  NA
				PERSIST:  NO
				INSRVMOD: NA
				RANGE:    NA
				DEFVALUE: NA
				UNITS:	  Packets
		        SPARSE:   NA
			"
		::= { sipBoardStatsC15mEntry 5 }

		sipBoardStatsC15mTotalReceiveOctets OBJECT-TYPE
			SYNTAX Counter
			ACCESS read-only
			STATUS mandatory
			DESCRIPTION
			"The total amount of RTP octets received by all SIP termination lines of this board in the current 15 min 
			interval.
				ALCATEL-LUCENT NOTE:
				ACCESS:    READ-ONLY
				USAGE:     NA
				PERSIST:   NO
				INSRVMOD:  NA
				RANGE:     NA
				DEFVALUE:  NA
				UNITS:     Octets
		        SPARSE:    NA
				"
		::= { sipBoardStatsC15mEntry 6 }

		sipBoardStatsC15mTotalLostPackets OBJECT-TYPE
			SYNTAX INTEGER
			ACCESS read-only
			STATUS mandatory
			DESCRIPTION
					"The total amount of lost receiving RTP packets for all SIP termination lines of this board in the current 15 min 
					interval.
					The amount of packets lost is defined to be the amount of packets expected less the amount of packets
					actually received:
					lost = expected - s->received;
					Since this signed number is carried in 24 bits, it should be clamped at 0x7fffff for positive loss or 0x800000
					for negative loss rather than wrapping around.
				ALCATEL-LUCENT NOTE:
				ACCESS:     READ-ONLY
				USAGE:      NA
				PERSIST:    NO
				INSRVMOD:   NA
				RANGE:      NA
				DEFVALUE:   NA
				UNITS:      Packets
		        SPARSE:     NA
				"
		::= { sipBoardStatsC15mEntry 7 }

		sipBoardStatsC15mAvgJBFL OBJECT-TYPE
			SYNTAX INTEGER(0..100)
			ACCESS read-only
			STATUS mandatory
			DESCRIPTION
			" Average Jitter Buffer Fill Level measured over all SIP termination lines connected to a voice LT board 
			during the receipt of RTP streams in the course of this current 15 min interval. The measurement includes the 
			receipt of RTP packets for both, originating and terminating calls. The measured average JBFL is expressed 
			as a percentage.
				ALCATEL-LUCENT NOTE:
				ACCESS:    READ-ONLY
				USAGE:     NA
				PERSIST:   NO
				INSRVMOD:  NA
				RANGE:     (0..100)
				DEFVALUE:  NA
				UNITS:     Percentage
		        SPARSE:    NA
				"
		::= { sipBoardStatsC15mEntry 8 }


		sipBoardStatsC15mAvgInterArrivalJitter OBJECT-TYPE
			SYNTAX Gauge
			ACCESS read-only
			STATUS mandatory
			DESCRIPTION
			" Average inter-arrival Jitter measured over all SIP termination lines connected to a voice LT board 
			during the receipt of RTP streams in the course of this current 15 min interval. The measurement includes the 
			receipt of RTP packets for both, originating and terminating calls. The measured average JBFL is 
			expressed in milli-seconds.
				ALCATEL-LUCENT NOTE:
				ACCESS:   READ-ONLY
				USAGE:    NA
				PERSIST:  NO
				INSRVMOD: NA
				RANGE:    NA
				DEFVALUE: NA
				UNITS:    Milli-Second
		        SPARSE:   NA
				"
		::= { sipBoardStatsC15mEntry 9 }

		sipBoardStatsC15mAvgRoundTripDelay OBJECT-TYPE
			SYNTAX Gauge
			ACCESS read-only
			STATUS mandatory
			DESCRIPTION
			" Average Round Trip Delay measured over all SIP termination lines connected to a voice LT board 
			during the receipt of RTP streams in the course of this current 15 min interval. The measurement includes 
			the receipt of RTP packets for both, originating and terminating calls. The measured average JBFL 
			is expressed in milli-seconds.
				ALCATEL-LUCENT NOTE:
				ACCESS:     READ-ONLY
				USAGE:      NA
				PERSIST:    NO
				INSRVMOD:   NA
				RANGE:      NA
				DEFVALUE: 	NA
				UNITS:      Milli-Second
		        SPARSE:     NA
			"
		::= { sipBoardStatsC15mEntry 10 }

		sipBoardStatsC15mPeakInterArrivalJitter OBJECT-TYPE
			SYNTAX Gauge
			ACCESS read-only
			STATUS mandatory
			DESCRIPTION
			" Peak inter-arrival Jitter measured over all SIP termination lines connected to a voice LT board 
			during the receipt of RTP streams in the course of this current 15 min interval. The measurement includes 
			the receipt of RTP packets for both, originating and terminating calls. The measured average JBFL 
			is expressed in milli-seconds.
				ALCATEL-LUCENT NOTE:
				ACCESS:     READ-ONLY
				USAGE:      NA
				PERSIST:    NO
				INSRVMOD:   NA
				RANGE:      NA
				DEFVALUE:   NA
				UNITS:      Milli-Second
		        SPARSE:     NA
			"
		::= { sipBoardStatsC15mEntry 11 }

		sipBoardStatsC15mPeakRoundTripDelay OBJECT-TYPE
			SYNTAX Gauge
			ACCESS read-only
			STATUS mandatory
			DESCRIPTION
			" Peak Round Trip Delay measured over all SIP termination lines connected to a voice LT board 
			during the receipt of RTP streams in the course of this current 15 min interval. The measurement includes 
			the receipt of RTP packets for both, originating and terminating calls. The measured average JBFL 
			is expressed in milli-seconds.
				ALCATEL-LUCENT NOTE:
				ACCESS:    READ-ONLY
				USAGE:     NA
				PERSIST:   NO
				INSRVMOD:  NA
				RANGE:     NA
				DEFVALUE:  NA
				UNITS:     Milli-Second
		        SPARSE:    NA
			"
		::= { sipBoardStatsC15mEntry 12 }

		sipBoardStatsC15mAvgJBFLG711A OBJECT-TYPE
			SYNTAX INTEGER(0..100)
			ACCESS read-only
			STATUS mandatory
			DESCRIPTION
			" Average Jitter Buffer Fill Level measured over all SIP termination lines connected to a voice LT board 
			during the receipt of RTP streams encoded with G711_a in the course of this current 15 min interval. The measurement includes the receipt of RTP packets for both, originating and terminating calls. The measured average JBFL is expressed as a percentage.
				ALCATEL-LUCENT NOTE:
				ACCESS:    READ-ONLY
				USAGE:     NA
				PERSIST:   NO
				INSRVMOD:  NA
				RANGE:     (0..100)
				DEFVALUE:  NA
				UNITS:     Percentage
		        SPARSE:    NA
			"
		::= { sipBoardStatsC15mEntry 13 }

		sipBoardStatsC15mAvgJBFLG711U OBJECT-TYPE
			SYNTAX INTEGER(0..100)
			ACCESS read-only
			STATUS mandatory
			DESCRIPTION
			" Average Jitter Buffer Fill Level measured over all SIP termination lines connected to a voice LT board 
			during the receipt of RTP streams encoded with G711_u in the course of this current 15 min interval. The measurement includes the receipt of RTP packets for both, originating and terminating calls. The measured average JBFL is expressed as a percentage.
				ALCATEL-LUCENT NOTE:
				ACCESS:    READ-ONLY
				USAGE:     NA
				PERSIST:   NO
				INSRVMOD:  NA
				RANGE:     (0..100)
				DEFVALUE:  NA
				UNITS:     Percentage
		        SPARSE:    NA
				"
		::= { sipBoardStatsC15mEntry 14 }

		sipBoardStatsC15mAvgJBFLG723 OBJECT-TYPE
			SYNTAX INTEGER(0..100)
			ACCESS read-only
			STATUS mandatory
			DESCRIPTION
			" Average Jitter Buffer Fill Level measured over all SIP termination lines connected to a voice LT board 
			during the receipt of RTP streams encoded with G723 in the course of this current 15 min interval. The measurement includes the receipt of RTP packets for both, originating and terminating calls. The measured average JBFL is expressed as a percentage.
				ALCATEL-LUCENT NOTE:
				ACCESS:	READ-ONLY
				USAGE:	NA
				PERSIST:	NO
				INSRVMOD:	NA
				RANGE:	(0..100)
				DEFVALUE: 	NA
				UNITS:	Percentage
		                SPARSE:	NA
			"
		::= { sipBoardStatsC15mEntry 15 }

		sipBoardStatsC15mAvgJBFLG729 OBJECT-TYPE
			SYNTAX INTEGER(0..100)
			ACCESS read-only
			STATUS mandatory
			DESCRIPTION
			" Average Jitter Buffer Fill Level measured over all SIP termination lines connected to a voice LT board 
			during the receipt of RTP streams encoded with G729 in the course of this current 15 min interval. The measurement includes the receipt of RTP packets for both, originating and terminating calls. The measured average JBFL is expressed as a percentage.
				ALCATEL-LUCENT NOTE:
				ACCESS:	READ-ONLY
				USAGE:	NA
				PERSIST:	NO
				INSRVMOD:	NA
				RANGE:	(0..100)
				DEFVALUE: 	NA
				UNITS:	Percentage
		                SPARSE:	NA
				"
		::= { sipBoardStatsC15mEntry 16 }

		sipBoardStatsC15mAvgCPULoad OBJECT-TYPE
			SYNTAX Gauge
			ACCESS read-only
			STATUS mandatory
			DESCRIPTION
			" Average CPU load measured at a board (voice LT board / NT board) in the course of this current 15 min 
			interval. The measured average CPU load is expressed as a percentage.
				ALCATEL-LUCENT NOTE:
				ACCESS:	READ-ONLY
				USAGE:	NA
				PERSIST:	NO
				INSRVMOD:	NA
				RANGE:	(0..100)
				DEFVALUE: 	NA
				UNITS:	Percentage
		                SPARSE:	NA
				"
		::= { sipBoardStatsC15mEntry 17 }

		sipBoardStatsC15mAvgMemUtilization OBJECT-TYPE
			SYNTAX Gauge
			ACCESS read-only
			STATUS mandatory
			DESCRIPTION
			" Average amount of semi and dynamic memory been used at a board (voice LT board / 
			NT board) in the course of this current 15 min interval. The measured value is expressed as a percentage.
				ALCATEL-LUCENT NOTE:
				ACCESS:	READ-ONLY
				USAGE:	NA
				PERSIST:	NO
				INSRVMOD:	NA
				RANGE:	(0..100)
				DEFVALUE: 	NA
				UNITS:	Percentage
		                SPARSE:	NA
				"
		::= { sipBoardStatsC15mEntry 18}

		sipBoardStatsC15mAvgMemPoolFree OBJECT-TYPE
			SYNTAX Gauge
			ACCESS read-only
			STATUS mandatory
			DESCRIPTION
			" Average amount of free semi and dynamic memory measured at a board (voice LT board / 
			NT board) in the course of this current 15 min interval. The measured value is expressed in Mbytes.
				ALCATEL-LUCENT NOTE:
				ACCESS:	READ-ONLY
				USAGE:	NA
				PERSIST:	NO
				INSRVMOD:	NA
				RANGE:	NA
				DEFVALUE: 	NA
				UNITS:	Mbyte
		                SPARSE:	NA
			"
		::= { sipBoardStatsC15mEntry 19}

		sipBoardStatsC15mAvgMemPoolUsed OBJECT-TYPE
			SYNTAX Gauge
			ACCESS read-only
			STATUS mandatory
			DESCRIPTION
			" Average amount of semi and dynamic memory been used at a board (voice LT board / 
			NT board) in the course of this current 15 min interval. The measured value is expressed in Mbytes.
				ALCATEL-LUCENT NOTE:
				ACCESS:	READ-ONLY
				USAGE:	NA
				PERSIST:	NO
				INSRVMOD:	NA
				RANGE:	NA
				DEFVALUE: 	NA
				UNITS:	Mbyte
		                SPARSE:	NA
			"
		::= { sipBoardStatsC15mEntry 20}

		sipBoardStatsC15mMemPoolTotal OBJECT-TYPE
			SYNTAX Gauge
			ACCESS read-only
			STATUS mandatory
			DESCRIPTION
			" The total amount of semi and dynamic memory available at a board (voice LT board / 
			NT board. It is expressed in Mbytes
				ALCATEL-LUCENT NOTE:
				ACCESS:	READ-ONLY
				USAGE:	NA
				PERSIST:	NO
				INSRVMOD:	NA
				RANGE:	NA
				DEFVALUE: 	NA
				UNITS:	Mbyte
		                SPARSE:	NA
			"
		::= { sipBoardStatsC15mEntry 21}

		sipBoardStatsC15mNumSparePOTSPorts OBJECT-TYPE
			SYNTAX Gauge
			ACCESS read-only
			STATUS mandatory
			DESCRIPTION
            "The number of free voice ports in the line card that have not been created on voice line cards that have
            already been planned. The value is independent of the control network registration status and is recorded
            at the end of the 15 min integration period. 
				ALCATEL-LUCENT NOTE:
				ACCESS:	READ-ONLY
				USAGE:	NA
				PERSIST:	NO
				INSRVMOD:	NA
				RANGE:	NA
				DEFVALUE: 	NA
				UNITS:	Number
		                SPARSE:	NA
			"
		::= { sipBoardStatsC15mEntry 22 }


		sipBoardStatsC15mNumActivePOTSPorts OBJECT-TYPE
			SYNTAX Gauge
			ACCESS read-only
			STATUS mandatory
			DESCRIPTION
            "The number of created voice ports in the line card that are administratively enabled. The value is
            independent of the control network registration status and is recorded at the end of the 15 min
            integration period.
            A 'fully configured' port may use the pre-provisioned default configuration of the voice port, SIP User Agent
            parameters at startup of the line card or an operator-specific configuration that has replaced this default
				ALCATEL-LUCENT NOTE:
				ACCESS:	READ-ONLY
				USAGE:	NA
				PERSIST:	NO
				INSRVMOD:	NA
				RANGE:	NA
				DEFVALUE: 	NA
				UNITS:	Number
		                SPARSE:	NA
			"
		::= { sipBoardStatsC15mEntry 23 }

		sipBoardStatsC15mNumInactivePOTSPorts OBJECT-TYPE
			SYNTAX Gauge
			ACCESS read-only
			STATUS mandatory
			DESCRIPTION
            "The number of created voice ports in the line card that are administratively disabled.  The value is
            independent of the control network registration status and is recorded at the end of the 15 min
            integration period. 
            The port may have been created though pre-provisioning of the default configuration of the voice 
            port, SIP User Agent parameters at startup of the line card or through specific operator provisioning of these 
            parameters.
				ALCATEL-LUCENT NOTE:
				ACCESS:	READ-ONLY
				USAGE:	NA
				PERSIST:	NO
				INSRVMOD:	NA
				RANGE:	NA
				DEFVALUE: 	NA
				UNITS:	Number
		                   SPARSE:	NA
					"
		::= { sipBoardStatsC15mEntry 24 }

		sipBoardStatsC15mRegisterReqSuccessful OBJECT-TYPE
			SYNTAX INTEGER
			ACCESS read-only
			STATUS mandatory
			DESCRIPTION
			" The amount of (re-)registration requests which are successfully replied in this current 15min interval. A (re-)registration request is considered successful when a response = 200 OK is returned by the registrar to the (re-)register request AND the contact address send by the MSAN in the (re-)REGISTER request is:
                         1. present in a contact header field of the 200 OK returned by the registrar AND this contact header field has an expires parameter with value set to value <> 0
                         2. present in a contact header field of the 200 OK returned by the registrar which has no expires parameter AND the 200 OK has an expires header field present with value set to value <> 0

				ALCATEL-LUCENT NOTE:
				ACCESS:	READ-ONLY
				USAGE:	NA
				PERSIST:	NO
				INSRVMOD:	NA
				RANGE:	NA
				DEFVALUE: 	NA
				UNITS:	Number
		                   SPARSE:	NA
					"
			::= { sipBoardStatsC15mEntry 25 }

		sipBoardStatsC15mRegisterReqFailed OBJECT-TYPE
			SYNTAX INTEGER
			ACCESS read-only
			STATUS mandatory
			DESCRIPTION
			" The amount of (re-)registration requests which failed in this current 15 min interval.
                          Failed means that:
                          1. A response <> 200 OK was retruned by the SIP First Hop server.
                          2. Registrar or that SIP transaction time-out occured 
                          3. The contact address send by the MSAN in the (re-)REGISTER request
                             is present in a contact header field of the 200 OK returned by the registrar
                             AND this contact header field has an expires parameter with value set to value = 0.
                          4. The contact address send by the MSAN in the (re-)REGISTER request is present in 
                             a contact header field of the 200 OK returned by the registrar which has no expires
                             parameter AND the 200 OK has an expires header field present with value set to value = 0.

				ALCATEL-LUCENT NOTE:
				ACCESS:	READ-ONLY
				USAGE:	NA
				PERSIST:	NO
				INSRVMOD:	NA
				RANGE:	NA
				DEFVALUE: 	NA
				UNITS:	Number
		                   SPARSE:	NA
					"
		::= { sipBoardStatsC15mEntry 26 }

		sipBoardStatsC15mRegistrationsActive OBJECT-TYPE
			SYNTAX INTEGER
			ACCESS read-only
			STATUS mandatory
			DESCRIPTION
			" The amount of registrations being active at a subscriber port at the end of the current 15 min interval. In the current implementation, only 1 registration can be active at a subscriber port at a time. An active registration is counted when a registration request has been successfully completed in the past (200 OK received to register request with 'expire header' time <> 0) and the register expiration interval hasn't expired.
				ALCATEL-LUCENT NOTE:
				ACCESS:	READ-ONLY
				USAGE:	NA
				PERSIST:	NO
				INSRVMOD:	NA
				RANGE:	NA
				DEFVALUE: 	NA
				UNITS:	Number
		                SPARSE:	NA
			"
		::= { sipBoardStatsC15mEntry 27 }

		sipBoardStatsC15mOutgoingCallsAnswered OBJECT-TYPE
			SYNTAX INTEGER
			ACCESS read-only
			STATUS mandatory
			DESCRIPTION
			" The amountr of outgoing call attempts in this [current/recent 15 min/24 h] interval for which an initial INVITE request is sent AND for which a response is received. The system allows to provision what kind of response must be received as to be counted as a successful outgoing call attempt. The system offers the following options : 
			o Any response be received (irrespective of whether this is a successful or unsuccessful response). 
			o A successful response be received (180 or 200 response only).
				ALCATEL-LUCENT NOTE:
				ACCESS:	READ-ONLY
				USAGE:	NA
				PERSIST:	NO
				INSRVMOD:	NA
				RANGE:	NA
				DEFVALUE: 	NA
				UNITS:	Number
		                   SPARSE:	NA
					"
			::= { sipBoardStatsC15mEntry 28 }

		sipBoardStatsC15mIncomingCallsAnswered OBJECT-TYPE
			SYNTAX INTEGER
			ACCESS read-only
			STATUS mandatory
			DESCRIPTION
			" The amount of incoming call attempts in this [current/recent 15 min/24 h interval for which a SIP response is sent being the result of the off-hook event been detected. The system allows to provision the kind of response that will be considered as to be counted as a successful incoming call attempt. The system offers the following options : 
			o Any response be sent. 
			o 180 response be sent.
				ALCATEL-LUCENT NOTE:
				ACCESS:	READ-ONLY
				USAGE:	NA
				PERSIST:	NO
				INSRVMOD:	NA
				RANGE:	NA
				DEFVALUE: 	NA
				UNITS:	Number
		                SPARSE:	NA
			"
		::= { sipBoardStatsC15mEntry 29 }

        sipBoardStatsC15mPortAvailDur OBJECT-TYPE
            SYNTAX INTEGER
            ACCESS read-only
            STATUS mandatory
            DESCRIPTION
            " Ref. the sipBoardStatsP15mPortAvailDur object for the definition of the counter.

                    ALCATEL-LUCENT NOTE:
            ACCESS: READ-ONLY
            USAGE:  NA
            PERSIST:    NO
            INSRVMOD:   NA
            RANGE:  NA
            DEFVALUE:   NA
            UNITS:  Seconds
            SPARSE: NA
            "
        ::= { sipBoardStatsC15mEntry 30 }

        sipBoardStatsC15mPortRegDur OBJECT-TYPE
            SYNTAX INTEGER
            ACCESS read-only
            STATUS mandatory
            DESCRIPTION
             " Ref. the sipBoardStatsP15mPortRegDur object for the definition of the counter.

                    ALCATEL-LUCENT NOTE:
            ACCESS: READ-ONLY
            USAGE:  NA
            PERSIST:    NO
            INSRVMOD:   NA
            RANGE:  NA
            DEFVALUE:   NA
            UNITS:  Seconds
            SPARSE: NA
            "
        ::= { sipBoardStatsC15mEntry 31 }

        sipBoardStatsC15mActiveConnections OBJECT-TYPE
            SYNTAX INTEGER
            ACCESS read-only
            STATUS mandatory
            DESCRIPTION
                    " Ref. the sipBoardStatsP15mActiveConnections object for the definition of the counter.
                    The current interval reflects at all times the number of active connections in the course of the interval.

            ALCATEL-LUCENT NOTE:
            ACCESS: READ-ONLY
            USAGE:  NA
            PERSIST:    NO
            INSRVMOD:   NA
            RANGE:  NA
            DEFVALUE:   NA
            UNITS:  Number
            SPARSE: NA
            "
            ::= { sipBoardStatsC15mEntry 32 }

        sipBoardStatsC15mBrokenPorts OBJECT-TYPE
            SYNTAX INTEGER
            ACCESS read-only
            STATUS mandatory
            DESCRIPTION
                    "ref. the sipBoardStatsP15mBrokenPorts object for the definition of the counter.
                    This counter is NOT reset at the beginning of a new current interval i.e. the number of broken ports at the
                    beginning of the new current interval = the number of broken ports upon te expiry of the expired current
                    interval.
                    The current interval reflects at all times the number of broken ports in the course of the interval.

            ALCATEL-LUCENT NOTE:
            ACCESS: READ-ONLY
            USAGE:  NA
            PERSIST:    NO
            INSRVMOD:   NA
            RANGE:  NA
            DEFVALUE:   NA
            UNITS:  Number
            SPARSE: NA
            "
    ::= { sipBoardStatsC15mEntry 33 }


-- =============================================================================
-- 
-- Sip Board Stats P1d Table
--=============================================================================						
		sipBoardStatsP1dTable OBJECT-TYPE
			SYNTAX SEQUENCE OF SipBoardStatsP1dEntry
			ACCESS not-accessible
			STATUS mandatory
			DESCRIPTION
			"This table contains the previous 1 day sip board statistics. 
			The table entry is auto-created upon board initialization.
			Upon expiry of the current 1 day interval, the current 1day interval content is copied to the recent interval.
			Up to 3 previous intervals are supported for each voice LT board.
			The registers associated with a partciluar voice LT board shall be set to '0' when this voice LT board has
			restarted
			In addition 
			- The Invalid data flag shall be set to 'True' to indicate that the results shown for this interval are invalid. 
			- The measured time shall be set to '0'.
			Summarized : measuredTime: 0, invalidData: True, counter: 0.
			For NT-A or NT-B board, the RTP/Signalling related counters will be displayed as 'NA' (Not Applicable) 
		
			7302/7330 ISAM-V : Supported
			7363 NGVR : NOT supported
			7367 SX : NOT Supported
		
			ALCATEL NOTE: 
			SUPPORT:  YES
			TABLESIZE:  DEP [(NumOfLT + 2)*3].  (+2 as the entries for NT-A and NT-B are to be included.) 
                        "
		::= { sipStatisticsAndData 11 }


		sipBoardStatsP1dEntry OBJECT-TYPE
			SYNTAX SipBoardStatsP1dEntry
			ACCESS not-accessible
			STATUS mandatory
			DESCRIPTION
				"The entry in the sipBoardStatsP1dTable.
			ALCATEL NOTE:
			SUPPORT:  YES "
			INDEX { eqptSlotId, sipBoardStatsP1dIntervalNumber }
			::= { sipBoardStatsP1dTable 1 }


		SipBoardStatsP1dEntry ::=
			SEQUENCE { 
				sipBoardStatsP1dIntervalNumber 
					INTEGER,
				sipBoardStatsP1dMeasuredTime
					INTEGER,
				sipBoardStatsP1dInvalidDataFlag
					INTEGER,
				sipBoardStatsP1dTotalSendPackets
					Counter,
				sipBoardStatsP1dTotalSendOctets
					Counter,
				sipBoardStatsP1dTotalReceivePackets
					Counter,
				sipBoardStatsP1dTotalReceiveOctets
					Counter,
				sipBoardStatsP1dTotalLostPackets
					INTEGER,
				sipBoardStatsP1dAvgJBFL
					INTEGER,
				sipBoardStatsP1dAvgInterArrivalJitter
					Gauge,
				sipBoardStatsP1dAvgRoundTripDelay
					Gauge,
				sipBoardStatsP1dPeakInterArrivalJitter
					Gauge,
				sipBoardStatsP1dPeakRoundTripDelay
					Gauge,
				sipBoardStatsP1dAvgJBFLG711A
					INTEGER,
				sipBoardStatsP1dAvgJBFLG711U
					INTEGER,
				sipBoardStatsP1dAvgJBFLG723
					INTEGER,
				sipBoardStatsP1dAvgJBFLG729
					INTEGER,
				sipBoardStatsP1dAvgCPULoad
					Gauge,
				sipBoardStatsP1dAvgMemUtilization
					Gauge,
				sipBoardStatsP1dAvgMemPoolFree
					Gauge,
				sipBoardStatsP1dAvgMemPoolUsed
					Gauge,
				sipBoardStatsP1dMemPoolTotal
					Gauge,
				sipBoardStatsP1dNumSparePOTSPorts
					Gauge,
				sipBoardStatsP1dNumActivePOTSPorts
					Gauge,
				sipBoardStatsP1dNumInactivePOTSPorts
					Gauge,
				sipBoardStatsP1dRegisterReqSuccessful
					INTEGER,
				sipBoardStatsP1dRegisterReqFailed
					INTEGER,
				sipBoardStatsP1dRegistrationsActive
					INTEGER,
				sipBoardStatsP1dOutgoingCallsAnswered
					INTEGER,
				sipBoardStatsP1dIncomingCallsAnswered
					INTEGER,
				sipBoardStatsP1dTimeStamp
				        NetworkTimeInSeconds
				}

		sipBoardStatsP1dIntervalNumber OBJECT-TYPE
			SYNTAX INTEGER(1..3)
			ACCESS not-accessible
			STATUS mandatory
			DESCRIPTION
				"A number between 1 and 3, which identifies the interval for which the set of statistics is available. The interval identified by I is the most recently completed 1 day interval, and the interval identified by N is the interval immediately preceding the one identified by N-1 .
				ALCATEL-LUCENT NOTE:
				ACCESS:	NOT-ACCESSIBLE
				USAGE:	NA
				PERSIST:	NO
				INSRVMOD:	NA
				RANGE:	(1..3)
				DEFVALUE: 	NA
				UNITS:	NA
		                   SPARSE:	NA
					"
			::= { sipBoardStatsP1dEntry 1 }

		sipBoardStatsP1dMeasuredTime OBJECT-TYPE
			SYNTAX INTEGER
			ACCESS read-only
			STATUS mandatory
			DESCRIPTION
					"The amount of time, measured in seconds, that statistics for this entry have been counted.
				ALCATEL-LUCENT NOTE:		
				ACCESS:	READ-ONLY
				USAGE:	NA
				PERSIST:	NO
				INSRVMOD:	NA
				RANGE:	NA
				DEFVALUE: 	NA
				UNITS:	Second
		                   SPARSE:	NA
					"
			::= { sipBoardStatsP1dEntry 2 }

		sipBoardStatsP1dInvalidDataFlag OBJECT-TYPE
			SYNTAX INTEGER(0..1)
			ACCESS read-only
			STATUS mandatory
			DESCRIPTION
					"This object indicates the validity of the corresponding PM data.
				It is set to 1 when the PM data is incomplete or invalid and set to 0 when the PM data is complete and valid.
				ALCATEL-LUCENT NOTE:
				ACCESS:	READ-ONLY
				USAGE:	NA
				PERSIST:	NO
				INSRVMOD:	NA
				RANGE:	(0..1)
				DEFVALUE: 	NA
				UNITS:	NA
		                   SPARSE:	NA
					"
			::= { sipBoardStatsP1dEntry 3 }

		sipBoardStatsP1dTotalSendPackets OBJECT-TYPE
			SYNTAX Counter
			ACCESS read-only
			STATUS mandatory
			DESCRIPTION
			"The total amount of RTP packets transmitted by all SIP termination lines of this board in this interval.
				ALCATEL-LUCENT NOTE:
				ACCESS:	READ-ONLY
				USAGE:	NA
				PERSIST:	NO
				INSRVMOD:	NA
				RANGE:	NA
				DEFVALUE: 	NA
				UNITS:	Packets
		                   SPARSE:	NA
					"
			::= { sipBoardStatsP1dEntry 4 }

		sipBoardStatsP1dTotalSendOctets OBJECT-TYPE
			SYNTAX Counter
			ACCESS read-only
			STATUS mandatory
			DESCRIPTION
			"The total amount of RTP octets transmitted by all SIP termination lines of this board in this interval.
				ALCATEL-LUCENT NOTE:
				ACCESS:	READ-ONLY
				USAGE:	NA
				PERSIST:	NO
				INSRVMOD:	NA
				RANGE:	NA
				DEFVALUE: 	NA
				UNITS:	Octets
		                   SPARSE:	NA
					"
			::= { sipBoardStatsP1dEntry 5 }

		sipBoardStatsP1dTotalReceivePackets OBJECT-TYPE
			SYNTAX Counter
			ACCESS read-only
			STATUS mandatory
			DESCRIPTION
			"The total amount of RTP packets received by all SIP termination lines of this board in this interval.
				ALCATEL-LUCENT NOTE:
				ACCESS:	READ-ONLY
				USAGE:	NA
				PERSIST:	NO
				INSRVMOD:	NA
				RANGE:	NA
				DEFVALUE: 	NA
				UNITS:	Packets
		                   SPARSE:	NA
					"
			::= { sipBoardStatsP1dEntry 6 }

		sipBoardStatsP1dTotalReceiveOctets OBJECT-TYPE
			SYNTAX Counter
			ACCESS read-only
			STATUS mandatory
			DESCRIPTION
				"The total amount of RTP octets received by all SIP termination lines of this board in this interval.
				ALCATEL-LUCENT NOTE:
				ACCESS:	READ-ONLY
				USAGE:	NA
				PERSIST:	NO
				INSRVMOD:	NA
				RANGE:	NA
				DEFVALUE: 	NA
				UNITS:	Octets
		                   SPARSE:	NA
					"
			::= { sipBoardStatsP1dEntry 7 }

		sipBoardStatsP1dTotalLostPackets OBJECT-TYPE
			SYNTAX INTEGER
			ACCESS read-only
			STATUS mandatory
			DESCRIPTION
				"The total amount of lost RTP packets for all SIP termination lines of this board in this interval.
				The amount of packets lost is defined to be the amount of packets expected less the amount of packets actually received:
				lost = expected - s->received;
				Since this signed number is carried in 24 bits, it should be clamped at 0x7fffff for positive loss or 0x800000
				for negative loss rather than wrapping around.
				ALCATEL-LUCENT NOTE:
				ACCESS:	READ-ONLY
				USAGE:	NA
				PERSIST:	NO
				INSRVMOD:	NA
				RANGE:	NA
				DEFVALUE: 	NA
				UNITS:	Packets
		                   SPARSE:	NA
					"
			::= { sipBoardStatsP1dEntry 8 }

		sipBoardStatsP1dAvgJBFL OBJECT-TYPE
			SYNTAX INTEGER(0..100)
			ACCESS read-only
			STATUS mandatory
			DESCRIPTION
			" Average Jitter Buffer Fill Level measured over all SIP termination lines connected to a voice LT 
			board during the receipt of RTP streams in the course of this interval. The measurement includes 
			the receipt of RTP packets for both, originating and terminating calls. The measured average JBFL is 
			expressed as a percentage.
				ALCATEL-LUCENT NOTE:
				ACCESS:	READ-ONLY
				USAGE:	NA
				PERSIST:	NO
				INSRVMOD:	NA
				RANGE:	(0..100)
				DEFVALUE: 	NA
				UNITS:	Percentage
		                   SPARSE:	NA
					"
			::= { sipBoardStatsP1dEntry 9 }

		sipBoardStatsP1dAvgInterArrivalJitter OBJECT-TYPE
			SYNTAX Gauge
			ACCESS read-only
			STATUS mandatory
			DESCRIPTION
			" Average inter-arrival Jitter measured over all SIP termination lines connected to a voice LT 
			board during the receipt of RTP streams in the course of this interval. The measurement includes 
			the receipt of RTP packets for both, originating and terminating calls. The measured average JBFL is 
			expressed as milli-seconds.
				ALCATEL-LUCENT NOTE:
				ACCESS:	READ-ONLY
				USAGE:	NA
				PERSIST:	NO
				INSRVMOD:	NA
				RANGE:	NA
				DEFVALUE: 	NA
				UNITS:	Milli-Second
		                   SPARSE:	NA
					"
			::= { sipBoardStatsP1dEntry 10 }

		sipBoardStatsP1dAvgRoundTripDelay OBJECT-TYPE
			SYNTAX Gauge
			ACCESS read-only
			STATUS mandatory
			DESCRIPTION
			" Average Round Trip Delay measured over all SIP termination lines connected to a voice LT board during the receipt of RTP streams in the course of this interval. The measurement includes the receipt of RTP packets for both, originating and terminating calls. The measured average JBFL is expressed as milli-seconds.
				ALCATEL-LUCENT NOTE:
				ACCESS:	READ-ONLY
				USAGE:	NA
				PERSIST:	NO
				INSRVMOD:	NA
				RANGE:	NA
				DEFVALUE: 	NA
				UNITS:	Milli-Second
		                   SPARSE:	NA
					"
			::= { sipBoardStatsP1dEntry 11 }

		sipBoardStatsP1dPeakInterArrivalJitter OBJECT-TYPE
			SYNTAX Gauge
			ACCESS read-only
			STATUS mandatory
			DESCRIPTION
			" Peak inter-arrival Jitter measured over all SIP termination lines connected to a voice LT board during the receipt of RTP streams in the course of this interval. The measurement includes the receipt of RTP packets for both, originating and terminating calls. The measured average JBFL is expressed as milli-seconds.
				ALCATEL-LUCENT NOTE:
				ACCESS:	READ-ONLY
				USAGE:	NA
				PERSIST:	NO
				INSRVMOD:	NA
				RANGE:	NA
				DEFVALUE: 	NA
				UNITS:	Milli-Second
		                   SPARSE:	NA
					"
			::= { sipBoardStatsP1dEntry 12 }

		sipBoardStatsP1dPeakRoundTripDelay OBJECT-TYPE
			SYNTAX Gauge
			ACCESS read-only
			STATUS mandatory
			DESCRIPTION
				" Peak Round Trip Delay measured over all SIP termination lines connected to a voice LT board during 
				the receipt of RTP streams in the course of this interval. The measurement includes the receipt of 
				RTP packets for both, originating and terminating calls. The measured average JBFL is expressed as 
				milli-seconds.
				ALCATEL-LUCENT NOTE:
				ACCESS:	READ-ONLY
				USAGE:	NA
				PERSIST:	NO
				INSRVMOD:	NA
				RANGE:	NA
				DEFVALUE: 	NA
				UNITS:	Milli-Second
		                   SPARSE:	NA
					"
			::= { sipBoardStatsP1dEntry 13 }


		sipBoardStatsP1dAvgJBFLG711A OBJECT-TYPE
			SYNTAX INTEGER(0..100)
			ACCESS read-only
			STATUS mandatory
			DESCRIPTION
			" Average Jitter Buffer Fill Level measured over all SIP termination lines connected to a voice LT board 
			during the receipt of RTP streams encoded with G711_a in the course of this interval. The measurement 
			includes the receipt of RTP packets for both, originating and terminating calls. The measured average 
			JBFL is expressed as a percentage.
				ALCATEL-LUCENT NOTE:
				ACCESS:	READ-ONLY
				USAGE:	NA
				PERSIST:	NO
				INSRVMOD:	NA
				RANGE:	(0..100)
				DEFVALUE: 	NA
				UNITS:	Percentage
		                   SPARSE:	NA
					"
			::= { sipBoardStatsP1dEntry 14 }

		sipBoardStatsP1dAvgJBFLG711U OBJECT-TYPE
			SYNTAX INTEGER(0..100)
			ACCESS read-only
			STATUS mandatory
			DESCRIPTION
			" Average Jitter Buffer Fill Level measured over all SIP termination lines connected to a voice LT board 
			during the receipt of RTP streams encoded with G711_u in the course of this interval. The measurement 
			includes the receipt of RTP packets for both, originating and terminating calls. The measured average 
			JBFL is expressed as a percentage.
				ALCATEL-LUCENT NOTE:
				ACCESS:	READ-ONLY
				USAGE:	NA
				PERSIST:	NO
				INSRVMOD:	NA
				RANGE:	(0..100)
				DEFVALUE: 	NA
				UNITS:	Percentage
		                   SPARSE:	NA
					"
			::= { sipBoardStatsP1dEntry 15 }

		sipBoardStatsP1dAvgJBFLG723 OBJECT-TYPE
			SYNTAX INTEGER(0..100)
			ACCESS read-only
			STATUS mandatory
			DESCRIPTION
			" Average Jitter Buffer Fill Level measured over all SIP termination lines connected to a voice LT board 
			during the receipt of RTP streams encoded with G723 in the course of this interval. The measurement 
			includes the receipt of RTP packets for both, originating and terminating calls. The measured average 
			JBFL is expressed as a percentage.
				ALCATEL-LUCENT NOTE:
				ACCESS:	READ-ONLY
				USAGE:	NA
				PERSIST:	NO
				INSRVMOD:	NA
				RANGE:	(0..100)
				DEFVALUE: 	NA
				UNITS:	Percentage
		                   SPARSE:	NA
					"
			::= { sipBoardStatsP1dEntry 16 }


		sipBoardStatsP1dAvgJBFLG729 OBJECT-TYPE
			SYNTAX INTEGER(0..100)
			ACCESS read-only
			STATUS mandatory
			DESCRIPTION
			" Average Jitter Buffer Fill Level measured over all SIP termination lines connected to a voice LT board 
			during the receipt of RTP streams encoded with G729 in the course of this interval. The measurement 
			includes the receipt of RTP packets for both, originating and terminating calls. The measured average 
			JBFL is expressed as a percentage.
				ALCATEL-LUCENT NOTE:
				ACCESS:	READ-ONLY
				USAGE:	NA
				PERSIST:	NO
				INSRVMOD:	NA
				RANGE:	(0..100)
				DEFVALUE: 	NA
				UNITS:	Percentage
		                   SPARSE:	NA
					"
			::= { sipBoardStatsP1dEntry 17 }

		sipBoardStatsP1dAvgCPULoad OBJECT-TYPE
			SYNTAX Gauge
			ACCESS read-only
			STATUS mandatory
			DESCRIPTION
			" Average CPU load measured at a board (voice LT board / NT board) in the course of this interval. The
			measured average CPU load is expressed as a percentage.
				ALCATEL-LUCENT NOTE:
				ACCESS:	READ-ONLY
				USAGE:	NA
				PERSIST:	NO
				INSRVMOD:	NA
				RANGE:	(0..100)
				DEFVALUE: 	NA
				UNITS:	Percentage
		                   SPARSE:	NA
					"
		::= { sipBoardStatsP1dEntry 18 }

		sipBoardStatsP1dAvgMemUtilization OBJECT-TYPE
			SYNTAX Gauge
			ACCESS read-only
			STATUS mandatory
			DESCRIPTION
			" Average amount of semi and dynamic memory been used at a board (voice LT board / NT board) in the
			course of this interval. The measured value is expressed as a percentage.
				ALCATEL-LUCENT NOTE:
				ACCESS:	READ-ONLY
				USAGE:	NA
				PERSIST:	NO
				INSRVMOD:	NA
				RANGE:	(0..100)
				DEFVALUE: 	NA
				UNITS:	Percentage
		                   SPARSE:	NA
					"
		::= { sipBoardStatsP1dEntry 19}

		sipBoardStatsP1dAvgMemPoolFree OBJECT-TYPE
			SYNTAX Gauge
			ACCESS read-only
			STATUS mandatory
			DESCRIPTION
			" Average amount of free semi and dynamic memory measured at a board (voice LT board / NT board) in
			the course of this interval. The measured value is expressed in Mbytes.
				ALCATEL-LUCENT NOTE:
				ACCESS:	READ-ONLY
				USAGE:	NA
				PERSIST:	NO
				INSRVMOD:	NA
				RANGE:	NA
				DEFVALUE: 	NA
				UNITS:	Mbyte
		                   SPARSE:	NA
					"
		::= { sipBoardStatsP1dEntry 20}

		sipBoardStatsP1dAvgMemPoolUsed OBJECT-TYPE
			SYNTAX Gauge
			ACCESS read-only
			STATUS mandatory
			DESCRIPTION
			" Average amount of semi and dynamic memory been used at a board (voice LT board / NT board) in the
			course of this interval. The measured value is expressed in Mbytes..
				ALCATEL-LUCENT NOTE:
				ACCESS:	READ-ONLY
				USAGE:	NA
				PERSIST:	NO
				INSRVMOD:	NA
				RANGE:	NA
				DEFVALUE: 	NA
				UNITS:	Mbyte
		                   SPARSE:	NA
			"
		::= { sipBoardStatsP1dEntry 21}

		sipBoardStatsP1dMemPoolTotal OBJECT-TYPE
			SYNTAX Gauge
			ACCESS read-only
			STATUS mandatory
			DESCRIPTION
			 " The total amount of semi and dynamic memory available at a board (voice LT board / NT board. It is
			expressed in Mbytes
				ALCATEL-LUCENT NOTE:
				ACCESS:	READ-ONLY
				USAGE:	NA
				PERSIST:	NO
				INSRVMOD:	NA
				RANGE:	NA
				DEFVALUE: 	NA
				UNITS:	Mbyte
		                   SPARSE:	NA
				"
		::= { sipBoardStatsP1dEntry 22}

		sipBoardStatsP1dNumSparePOTSPorts OBJECT-TYPE
			SYNTAX Gauge
			ACCESS read-only
			STATUS mandatory
			DESCRIPTION
					" Amount of free ports i.e. the amount of POTS ports, which are not created, however exist on linecards which
				have been planned. The value is taken at the end of the interval
				ALCATEL-LUCENT NOTE:
				ACCESS:	READ-ONLY
				USAGE:	NA
				PERSIST:	NO
				INSRVMOD:	NA
				RANGE:	NA
				DEFVALUE: 	NA
				UNITS:	Number
		                   SPARSE:	NA
					"
			::= { sipBoardStatsP1dEntry 23 }

		sipBoardStatsP1dNumActivePOTSPorts OBJECT-TYPE
			SYNTAX Gauge
			ACCESS read-only
			STATUS mandatory
			DESCRIPTION
					" Amount of active POTS ports. Total amount of the available configured (configured and not blocked
				administratively) subscriber ports independ-ent of line status and registration). The value is taken at the end of the interval
				ALCATEL-LUCENT NOTE:
				ACCESS:	READ-ONLY
				USAGE:	NA
				PERSIST:	NO
				INSRVMOD:	NA
				RANGE:	NA
				DEFVALUE: 	NA
				UNITS:	Number
		                   SPARSE:	NA
					"
			::= { sipBoardStatsP1dEntry 24 }

		sipBoardStatsP1dNumInactivePOTSPorts OBJECT-TYPE
			SYNTAX Gauge
			ACCESS read-only
			STATUS mandatory
			DESCRIPTION
					" Amount of inactive POTS ports. Total amount of the available configured (blocked) subscriber ports
				independent of line status and registration). The value is taken at the end of the interval
				ALCATEL-LUCENT NOTE:
				ACCESS:	READ-ONLY
				USAGE:	NA
				PERSIST:	NO
				INSRVMOD:	NA
				RANGE:	NA
				DEFVALUE: 	NA
				UNITS:	Number
		                   SPARSE:	NA
				"
		::= { sipBoardStatsP1dEntry 25 }

		sipBoardStatsP1dRegisterReqSuccessful OBJECT-TYPE
			SYNTAX INTEGER
			ACCESS read-only
			STATUS mandatory
			DESCRIPTION
			" The amount of (re-)registration requests which are successfully replied in this recent 1 day interval.
			Successfully replied means that a response = 200 OK with expire header time = 0 or expire header <> 0
			has been returned by the Registrar.
				ALCATEL-LUCENT NOTE:
				ACCESS:	READ-ONLY
				USAGE:	NA
				PERSIST:	NO
				INSRVMOD:	NA
				RANGE:	NA
				DEFVALUE: 	NA
				UNITS:	Number
		                   SPARSE:	NA
					"
			::= { sipBoardStatsP1dEntry 26 }

		sipBoardStatsP1dRegisterReqFailed OBJECT-TYPE
			SYNTAX INTEGER
			ACCESS read-only
			STATUS mandatory
			DESCRIPTION
			" The amount of (re-)registration requests which failed in this recent 1 day interval. Failed means that a
			response <> 200 OK was retruned by the SIP First Hop server / Registrar or that SIP transaction time-out
			occured.
				ALCATEL-LUCENT NOTE:
				ACCESS:	READ-ONLY
				USAGE:	NA
				PERSIST:	NO
				INSRVMOD:	NA
				RANGE:	NA
				DEFVALUE: 	NA
				UNITS:	Number
		                   SPARSE:	NA
				"
			::= { sipBoardStatsP1dEntry 27 }


		sipBoardStatsP1dRegistrationsActive OBJECT-TYPE
			SYNTAX INTEGER
			ACCESS read-only
			STATUS mandatory
			DESCRIPTION
			" The amount of registrations being active at a subscriber port at the end of the recent 1 day interval. 
			In the current implementation, only 1 registration can be active at a subscriber port at a time. An active
			registration is counted when a registration request has been successfully completed in the past (200 OK
			received to register request with 'expire header' time <> 0) and the register expiration interval hasn't expired.
				ALCATEL-LUCENT NOTE:
				ACCESS:	READ-ONLY
				USAGE:	NA
				PERSIST:	NO
				INSRVMOD:	NA
				RANGE:	NA
				DEFVALUE: 	NA
				UNITS:	Number
		                   SPARSE:	NA
				"
			::= { sipBoardStatsP1dEntry 28 }

		sipBoardStatsP1dOutgoingCallsAnswered OBJECT-TYPE
			SYNTAX INTEGER
			ACCESS read-only
			STATUS mandatory
			DESCRIPTION
			" The amount of outgoing call attempts in this recent 1 day interval for which an initial INVITE request is sent AND for which a response is received. The system allows to provision what kind of response must be received as to be counted as a successful outgoing call attempt. The system offers the following options : 
			o Any response be received (irrespective of whether this is a successful or unsuccessful response). 
			o A successful response be received (180 or 200 response only).
				ALCATEL-LUCENT NOTE:
				ACCESS:	READ-ONLY
				USAGE:	NA
				PERSIST:	NO
				INSRVMOD:	NA
				RANGE:	NA
				DEFVALUE: 	NA
				UNITS:	Number
		                   SPARSE:	NA
					"
			::= { sipBoardStatsP1dEntry 29 }

		sipBoardStatsP1dIncomingCallsAnswered OBJECT-TYPE
			SYNTAX INTEGER
			ACCESS read-only
			STATUS mandatory
			DESCRIPTION
				" The amount of incoming call attempts in this recent 1 day interval for which a SIP response is sent being the
				result of the off-hook event been detected. The system allows to provision the kind of response that will be
				considered as to be counted as a successful incoming call attempt. The system offers the following options : 
				o Any response be sent. 
				o 180 response be sent.
				ALCATEL-LUCENT NOTE:
				ACCESS:	READ-ONLY
				USAGE:	NA
				PERSIST:	NO
				INSRVMOD:	NA
				RANGE:	NA
				DEFVALUE: 	NA
				UNITS:	Number
		                   SPARSE:	NA
					"
			::= { sipBoardStatsP1dEntry 30 }

              sipBoardStatsP1dTimeStamp  OBJECT-TYPE
                             SYNTAX NetworkTimeInSeconds
                             ACCESS read-only
                             STATUS mandatory
                             DESCRIPTION
              "The value of sipBoardStatsP1dTimeStamp indicating the time stamp of start time for board statistic of per one day.
                             ALCATEL-LUCENT NOTE:
                             ACCESS: READ-ONLY
                             USAGE: NA
                             PERSIST: NO
                             INSRVMOD: NA
                             RANGE: (0..4294967295)
                             DEFVALUE: 0
                             UNITS: seconds
                             SPARSE: NA
                                     "
 ::= { sipBoardStatsP1dEntry 31 }


-- =============================================================================
-- 
-- Sip Board Stats C1d Table
--=============================================================================						
		sipBoardStatsC1dTable OBJECT-TYPE
			SYNTAX SEQUENCE OF SipBoardStatsC1dEntry
			ACCESS not-accessible
			STATUS mandatory
			DESCRIPTION
			"This table contains the current 1 day board statistics.
			The table entry is auto-created upon board initialization.
			 	The registers associated with a partciluar voice LT board shall be set to '0' when this voice LT board has
			restarted
				In addition 
				- The Invalid data flag shall be set to 'False'. 
				- The measured time shall be set to '0'.
				Summarized : measuredTime: 0, invalidData: False, counter: 0.
			For NT-A or NT-B board, the RTP/Signalling related counters will be displayed as 'NA' (Not Applicable) 
		
			7302/7330 ISAM-V : Supported
			7363 NGVR : NOT supported
			7367 SX : NOT Supported
			
			ALCATEL NOTE: 
			SUPPORT:  YES
			TABLESIZE:  DEP [NumOfLT + 2].  (+2 as the entries for NT-A and NT-B are to be included.) 
                        "
			::= { sipStatisticsAndData 12 }

		sipBoardStatsC1dEntry OBJECT-TYPE
			SYNTAX SipBoardStatsC1dEntry
			ACCESS not-accessible
			STATUS mandatory
			DESCRIPTION
				"The entry in the sipBoardStatsC1dTable.
			ALCATEL NOTE:
			SUPPORT:  YES "
			INDEX { eqptSlotId }
			::= { sipBoardStatsC1dTable 1 }

		SipBoardStatsC1dEntry ::=
			SEQUENCE { 
			sipBoardStatsC1dMeasuredTime			INTEGER,
			sipBoardStatsC1dInvalidDataFlag		INTEGER,
			sipBoardStatsC1dTotalSendPackets		Counter,
			sipBoardStatsC1dTotalSendOctets		Counter,
			sipBoardStatsC1dTotalReceivePackets		Counter,
			sipBoardStatsC1dTotalReceiveOctets		Counter,
			sipBoardStatsC1dTotalLostPackets		INTEGER,
			sipBoardStatsC1dAvgJBFL				INTEGER,
			sipBoardStatsC1dAvgInterArrivalJitter		Gauge,
			sipBoardStatsC1dAvgRoundTripDelay		Gauge,
			sipBoardStatsC1dPeakInterArrivalJitter		Gauge,
			sipBoardStatsC1dPeakRoundTripDelay		Gauge,
			sipBoardStatsC1dAvgJBFLG711A		INTEGER,
			sipBoardStatsC1dAvgJBFLG711U		INTEGER,
			sipBoardStatsC1dAvgJBFLG723			INTEGER,
			sipBoardStatsC1dAvgJBFLG729			INTEGER,
			sipBoardStatsC1dAvgCPULoad			Gauge,
			sipBoardStatsC1dAvgMemUtilization		Gauge,
			sipBoardStatsC1dAvgMemPoolFree		Gauge,
			sipBoardStatsC1dAvgMemPoolUsed		Gauge,
			sipBoardStatsC1dMemPoolTotal			Gauge,
			sipBoardStatsC1dNumSparePOTSPorts		Gauge,
			sipBoardStatsC1dNumActivePOTSPorts		Gauge,
			sipBoardStatsC1dNumInactivePOTSPorts	Gauge,
			sipBoardStatsC1dRegisterReqSuccessful	INTEGER,
			sipBoardStatsC1dRegisterReqFailed		INTEGER,
			sipBoardStatsC1dRegistrationsActive		INTEGER,
			sipBoardStatsC1dOutgoingCallsAnswered	INTEGER,
			sipBoardStatsC1dIncomingCallsAnswered	INTEGER
			}

		sipBoardStatsC1dMeasuredTime OBJECT-TYPE
			SYNTAX INTEGER
			ACCESS read-only
			STATUS mandatory
			DESCRIPTION
				"The amount of time, measured in seconds, that statistics for this entry have been counted.
				ALCATEL-LUCENT NOTE:		
				ACCESS:	READ-ONLY
				USAGE:	NA
				PERSIST:	NO
				INSRVMOD:	NA
				RANGE:	NA
				DEFVALUE: 	NA
				UNITS:	Second
		                   SPARSE:	NA
				"
			::= { sipBoardStatsC1dEntry 1 }

		sipBoardStatsC1dInvalidDataFlag OBJECT-TYPE
			SYNTAX INTEGER(0..1)
			ACCESS read-only
			STATUS mandatory
			DESCRIPTION
				"This object indicates the validity of the corresponding PM data.
				It is set to 1 when the PM data is incomplete or invalid and set to 0 when the PM data is complete and valid.
				ALCATEL-LUCENT NOTE:
				ACCESS:	READ-ONLY
				USAGE:	NA
				PERSIST:	NO
				INSRVMOD:	NA
				RANGE:	(0..1)
				DEFVALUE: 	NA
				UNITS: NA
		                   SPARSE:	NA
				"
			::= { sipBoardStatsC1dEntry 2 }

		sipBoardStatsC1dTotalSendPackets OBJECT-TYPE
			SYNTAX Counter
			ACCESS read-only
			STATUS mandatory
			DESCRIPTION
			"The total amount of RTP packets transmitted by all SIP termination lines of this board in the current 1 day
			interval.
				ALCATEL-LUCENT NOTE:
				ACCESS:	READ-ONLY
				USAGE:	NA
				PERSIST:	NO
				INSRVMOD:	NA
				RANGE:	NA
				DEFVALUE: 	NA
				UNITS:	Packets
		                   SPARSE:	NA
				"
		::= { sipBoardStatsC1dEntry 3 }

		sipBoardStatsC1dTotalSendOctets OBJECT-TYPE
			SYNTAX Counter
			ACCESS read-only
			STATUS mandatory
			DESCRIPTION
			"The total amount of RTP octets transmitted by all SIP termination lines of this board in the current 1 day
			interval.
				ALCATEL-LUCENT NOTE:
				ACCESS:	READ-ONLY
				USAGE:	NA
				PERSIST:	NO
				INSRVMOD:	NA
				RANGE:	NA
				DEFVALUE: 	NA
				UNITS:	Octets
		                   SPARSE:	NA
				"
			::= { sipBoardStatsC1dEntry 4 }

		sipBoardStatsC1dTotalReceivePackets OBJECT-TYPE
			SYNTAX Counter
			ACCESS read-only
			STATUS mandatory
			DESCRIPTION
			"The total amount of RTP packets received by all SIP termination lines of this board in the current 1 day
			interval.
				ALCATEL-LUCENT NOTE:
				ACCESS:	READ-ONLY
				USAGE:	NA
				PERSIST:	NO
				INSRVMOD:	NA
				RANGE:	NA
				DEFVALUE: 	NA
				UNITS:	Packets
		                   SPARSE:	NA
				"
			::= { sipBoardStatsC1dEntry 5 }

		sipBoardStatsC1dTotalReceiveOctets OBJECT-TYPE
			SYNTAX Counter
			ACCESS read-only
			STATUS mandatory
			DESCRIPTION
			"The total amount of RTP octets received by all SIP termination lines of this board in the current 1 day interval.
				ALCATEL-LUCENT NOTE:
				ACCESS:	READ-ONLY
				USAGE:	NA
				PERSIST:	NO
				INSRVMOD:	NA
				RANGE:	NA
				DEFVALUE: 	NA
				UNITS:	Octets
		                   SPARSE:	NA
				"
			::= { sipBoardStatsC1dEntry 6 }

		sipBoardStatsC1dTotalLostPackets OBJECT-TYPE
			SYNTAX INTEGER
			ACCESS read-only
			STATUS mandatory
			DESCRIPTION
				"The total amount of lost RTP packets for all SIP termination lines of this board in the current 1 day interval.
				The amount of packets lost is defined to be the amount of packets expected less the amount of packets actually received:
					lost = expected - s->received;
					Since this signed number is carried in 24 bits, it should be clamped at 0x7fffff for positive loss or 0x800000
				for negative loss rather than wrapping around.
				ALCATEL-LUCENT NOTE:
				ACCESS:	READ-ONLY
				USAGE:	NA
				PERSIST:	NO
				INSRVMOD:	NA
				RANGE:	NA
				DEFVALUE: 	NA
				UNITS:	Packets
		                   SPARSE:	NA
					"
			::= { sipBoardStatsC1dEntry 7 }

		sipBoardStatsC1dAvgJBFL OBJECT-TYPE
			SYNTAX INTEGER(0..100)
			ACCESS read-only
			STATUS mandatory
			DESCRIPTION
			" Average Jitter Buffer Fill Level measured over all SIP termination lines connected to a voice LT board during
			the receipt of RTP streams in the course of the current 1 day interval. The measurement includes the receipt of
			RTP packets for both, originating and terminating calls. The measured average JBFL is expressed as a percentage.
				ALCATEL-LUCENT NOTE:
				ACCESS:	READ-ONLY
				USAGE:	NA
				PERSIST:	NO
				INSRVMOD:	NA
				RANGE:	(0..100)
				DEFVALUE: 	NA
				UNITS:	Percentage
		                   SPARSE:	NA
				"
			::= { sipBoardStatsC1dEntry 8 }

		sipBoardStatsC1dAvgInterArrivalJitter OBJECT-TYPE
			SYNTAX Gauge
			ACCESS read-only
			STATUS mandatory
			DESCRIPTION
			" Average inter-arrival Jitter measured over all SIP termination lines connected to a voice LT board during the
			receipt of RTP streams in the course of the current 1 day interval. The measurement includes the receipt of
			RTP packets for both, originating and terminating calls. The measured average JBFL is expressed as 
			milli-seconds.
				ALCATEL-LUCENT NOTE:
				ACCESS:	READ-ONLY
				USAGE:	NA
				PERSIST:	NO
				INSRVMOD:	NA
				RANGE:	NA
				DEFVALUE: 	NA
				UNITS:	Milli-Second
		                   SPARSE:	NA
			"
			::= { sipBoardStatsC1dEntry 9 }

		sipBoardStatsC1dAvgRoundTripDelay OBJECT-TYPE
			SYNTAX Gauge
			ACCESS read-only
			STATUS mandatory
			DESCRIPTION
			" Average Round Trip Delay measured over all SIP termination lines connected to a voice LT board during the
			receipt of RTP streams in the course of a single interval. The measurement includes the receipt of RTP packets
			for both, originating and terminating calls. The measured average JBFL is expressed as milli-seconds.
				ALCATEL-LUCENT NOTE:
				ACCESS:	READ-ONLY
				USAGE:	NA
				PERSIST:	NO
				INSRVMOD:	NA
				RANGE:	NA
				DEFVALUE: 	NA
				UNITS:	Milli-Second
		                   SPARSE:	NA
				"
			::= { sipBoardStatsC1dEntry 10 }

		sipBoardStatsC1dPeakInterArrivalJitter OBJECT-TYPE
			SYNTAX Gauge
			ACCESS read-only
			STATUS mandatory
			DESCRIPTION
			" Peak inter-arrival Jitter measured over all SIP termination lines connected to a voice LT board during the
			receipt of RTP streams in the course of a single interval. The measurement includes the receipt of RTP packets
			for both, originating and terminating calls. The measured average JBFL is expressed as milli-seconds.
				ALCATEL-LUCENT NOTE:
				ACCESS:	READ-ONLY
				USAGE:	NA
				PERSIST:	NO
				INSRVMOD:	NA
				RANGE:	NA
				DEFVALUE: 	NA
				UNITS:	Milli-Second
		                   SPARSE:	NA
					"
			::= { sipBoardStatsC1dEntry 11 }

		sipBoardStatsC1dPeakRoundTripDelay OBJECT-TYPE
			SYNTAX Gauge
			ACCESS read-only
			STATUS mandatory
			DESCRIPTION
			" Peak Round Trip Delay measured over all SIP termination lines connected to a voice LT board during the receipt of RTP streams in the course of the current 1 day interval. The measurement includes the receipt of RTP packets for both, originating and terminating calls. The measured average JBFL is expressed as milli-seconds.
				ALCATEL-LUCENT NOTE:
				ACCESS:	READ-ONLY
				USAGE:	NA
				PERSIST:	NO
				INSRVMOD:	NA
				RANGE:	NA
				DEFVALUE: 	NA
				UNITS:	Milli-Second
		                   SPARSE:	NA
				"
			::= { sipBoardStatsC1dEntry 12 }

		sipBoardStatsC1dAvgJBFLG711A OBJECT-TYPE
			SYNTAX INTEGER(0..100)
			ACCESS read-only
			STATUS mandatory
			DESCRIPTION
			" Average Jitter Buffer Fill Level measured over all SIP termination lines connected to a voice LT board during
			the receipt of RTP streams encoded with G711_a in the course of the current 1day interval. The measurement
			includes the receipt of RTP packets for both, originating and terminating calls. The measured average JBFL is
			expressed as a percentage.
				ALCATEL-LUCENT NOTE:
				ACCESS:	READ-ONLY
				USAGE:	NA
				PERSIST:	NO
				INSRVMOD:	NA
				RANGE:	(0..100)
				DEFVALUE: 	NA
				UNITS:	Percentage
		                   SPARSE:	NA
				"
			::= { sipBoardStatsC1dEntry 13 }

		sipBoardStatsC1dAvgJBFLG711U OBJECT-TYPE
			SYNTAX INTEGER(0..100)
			ACCESS read-only
			STATUS mandatory
			DESCRIPTION
			" Average Jitter Buffer Fill Level measured over all SIP termination lines connected to a voice LT board during
			the receipt of RTP streams encoded with G711_u in the course of the current 1 day interval. The measurement includes the receipt of RTP packets for both, originating and terminating calls. The
			measured average JBFL is expressed as a percentage.
				ALCATEL-LUCENT NOTE:
				ACCESS:	READ-ONLY
				USAGE:	NA
				PERSIST:	NO
				INSRVMOD:	NA
				RANGE:	(0..100)
				DEFVALUE: 	NA
				UNITS:	Percentage
		                   SPARSE:	NA
				"
			::= { sipBoardStatsC1dEntry 14 }

		sipBoardStatsC1dAvgJBFLG723 OBJECT-TYPE
			SYNTAX INTEGER(0..100)
			ACCESS read-only
			STATUS mandatory
			DESCRIPTION
			" Average Jitter Buffer Fill Level measured over all SIP termination lines connected to a voice LT board 
			during the receipt of RTP streams encoded with G723 in the course of the current 1 day interval. The
			measurement includes the receipt of RTP packets for both, originating and terminating calls. The measured
			average JBFL is expressed as a percentage.
				ALCATEL-LUCENT NOTE:
				ACCESS:	READ-ONLY
				USAGE:	NA
				PERSIST:	NO
				INSRVMOD:	NA
				RANGE:	(0..100)
				DEFVALUE: 	NA
				UNITS:	Percentage
		                   SPARSE:	NA
				"
			::= { sipBoardStatsC1dEntry 15 }

		sipBoardStatsC1dAvgJBFLG729 OBJECT-TYPE
			SYNTAX INTEGER(0..100)
			ACCESS read-only
			STATUS mandatory
			DESCRIPTION
			" Average Jitter Buffer Fill Level measured over all SIP termination lines connected to a voice LT board 
			during the receipt of RTP streams encoded with G729 in the course of the current 1 day interval. The measurement includes the receipt of RTP packets for both, originating and terminating calls. The measured average JBFL is expressed as a percentage.
				ALCATEL-LUCENT NOTE:
				ACCESS:	READ-ONLY
				USAGE:	NA
				PERSIST:	NO
				INSRVMOD:	NA
				RANGE:	(0..100)
				DEFVALUE: 	NA
				UNITS:	Percentage
		                   SPARSE:	NA
					"
			::= { sipBoardStatsC1dEntry 16 }

		sipBoardStatsC1dAvgCPULoad OBJECT-TYPE
			SYNTAX Gauge
			ACCESS read-only
			STATUS mandatory
			DESCRIPTION
			" Average CPU load measured at a board (voice LT board / NT board) in the course of the current 1 day interval. The measured average CPU load is expressed as a percentage. 
				ALCATEL-LUCENT NOTE:
				ACCESS:	READ-ONLY
				USAGE:	NA
				PERSIST:	NO
				INSRVMOD:	NA
				RANGE:	(0..100)
				DEFVALUE: 	NA
				UNITS:	Percentage
		                   SPARSE:	NA
				"
			::= { sipBoardStatsC1dEntry 17 }

		sipBoardStatsC1dAvgMemUtilization OBJECT-TYPE
			SYNTAX Gauge
			ACCESS read-only
			STATUS mandatory
			DESCRIPTION
			" Average amount of semi and dynamic memory been used at a board (voice LT board / NT board) in the course of the current 1 day interval. The measured value is expressed as a percentage.
				ALCATEL-LUCENT NOTE:
				ACCESS:	READ-ONLY
				USAGE:	NA
				PERSIST:	NO
				INSRVMOD:	NA
				RANGE:	(0..100)
				DEFVALUE: 	NA
				UNITS:	Percentage
		                   SPARSE:	NA
				"
		::= { sipBoardStatsC1dEntry 18}

		sipBoardStatsC1dAvgMemPoolFree OBJECT-TYPE
			SYNTAX Gauge
			ACCESS read-only
			STATUS mandatory
			DESCRIPTION
			" Average amount of free semi and dynamic memory measured at a board (voice LT board / NT board) in the course of the current 1 day interval. The measured value is expressed in Mbytes.
				ALCATEL-LUCENT NOTE:
				ACCESS:	READ-ONLY
				USAGE:	NA
				PERSIST:	NO
				INSRVMOD:	NA
				RANGE:	NA
				DEFVALUE: 	NA
				UNITS:	Mbyte
		                   SPARSE:	NA
				"
		::= { sipBoardStatsC1dEntry 19}

		sipBoardStatsC1dAvgMemPoolUsed OBJECT-TYPE
			SYNTAX Gauge
			ACCESS read-only
			STATUS mandatory
			DESCRIPTION
			" Average amount of semi and dynamic memory been used at a board (voice LT board / NT board) in the course of the current 1 day interval. The measured value is expressed in Mbytes.
				ALCATEL-LUCENT NOTE:
				ACCESS:	READ-ONLY
				USAGE:	NA
				PERSIST:	NO
				INSRVMOD:	NA
				RANGE:	NA
				DEFVALUE: 	NA
				UNITS:	Mbyte
		                   SPARSE:	NA
					"
		::= { sipBoardStatsC1dEntry 20}

		sipBoardStatsC1dMemPoolTotal OBJECT-TYPE
			SYNTAX Gauge
			ACCESS read-only
			STATUS mandatory
			DESCRIPTION
			" The total amount of semi and dynamic memory available at a board (voice LT board / NT board. It is 	expressed in Mbytes
				ALCATEL-LUCENT NOTE:
				ACCESS:	READ-ONLY
				USAGE:	NA
				PERSIST:	NO
				INSRVMOD:	NA
				RANGE:	NA
				DEFVALUE: 	NA
				UNITS:	Mbyte
		                   SPARSE:	NA
					"
		::= { sipBoardStatsC1dEntry 21}

		sipBoardStatsC1dNumSparePOTSPorts OBJECT-TYPE
			SYNTAX Gauge
			ACCESS read-only
			STATUS mandatory
			DESCRIPTION
					" Amount of free ports i.e. the amount of POTS ports, which are not created, however exist on linecards which
				have been planned. The value is taken at the end of the interval
				ALCATEL-LUCENT NOTE:
				ACCESS:	READ-ONLY
				USAGE:	NA
				PERSIST:	NO
				INSRVMOD:	NA
				RANGE:	NA
				DEFVALUE: 	NA
				UNITS:	Number
		                   SPARSE:	NA
				"
			::= { sipBoardStatsC1dEntry 22 }

		sipBoardStatsC1dNumActivePOTSPorts OBJECT-TYPE
			SYNTAX Gauge
			ACCESS read-only
			STATUS mandatory
			DESCRIPTION
				" Amount of active POTS ports. Total amount of the available configured (configured and not blocked administratively) subscriber ports independ-ent of line status and registration). The value is taken at the end of the interval
				ALCATEL-LUCENT NOTE:
				ACCESS:	READ-ONLY
				USAGE:	NA
				PERSIST:	NO
				INSRVMOD:	NA
				RANGE:	NA
				DEFVALUE: 	NA
				UNITS:	Number
		                   SPARSE:	NA
					"
			::= { sipBoardStatsC1dEntry 23 }

		sipBoardStatsC1dNumInactivePOTSPorts OBJECT-TYPE
			SYNTAX Gauge
			ACCESS read-only
			STATUS mandatory
			DESCRIPTION
				" Amount of inactive POTS ports. Total amount of the available configured (blocked) subscriber ports independent of line status and registration). The value is taken at the end of the interval
				ALCATEL-LUCENT NOTE:
				ACCESS:	READ-ONLY
				USAGE:	NA
				PERSIST:	NO
				INSRVMOD:	NA
				RANGE:	NA
				DEFVALUE: 	NA
				UNITS:	Number
		                   SPARSE:	NA
					"
			::= { sipBoardStatsC1dEntry 24 }

		sipBoardStatsC1dRegisterReqSuccessful OBJECT-TYPE
			SYNTAX INTEGER
			ACCESS read-only
			STATUS mandatory
			DESCRIPTION
				" The amount of (re-)registration requests which are successfully replied in this current 1 day interval. Successfully replied means that a response = 200 OK with expire header time = 0 or expire header <> 0 has been returned by the Registrar.
				ALCATEL-LUCENT NOTE:
				ACCESS:	READ-ONLY
				USAGE:	NA
				PERSIST:	NO
				INSRVMOD:	NA
				RANGE:	NA
				DEFVALUE: 	NA
				UNITS:	Number
		                   SPARSE:	NA
					"
			::= { sipBoardStatsC1dEntry 25 }

		sipBoardStatsC1dRegisterReqFailed OBJECT-TYPE
			SYNTAX INTEGER
			ACCESS read-only
			STATUS mandatory
			DESCRIPTION
			" The amount of (re-)registration requests which failed in this current 1day interval. Failed means that a response <> 200 OK was retruned by the SIP First Hop server / Registrar or that SIP transaction time-out occured.
				ALCATEL-LUCENT NOTE:
				ACCESS:	READ-ONLY
				USAGE:	NA
				PERSIST:	NO
				INSRVMOD:	NA
				RANGE:	NA
				DEFVALUE: 	NA
				UNITS:	Number
		                   SPARSE:	NA
					"
			::= { sipBoardStatsC1dEntry 26 }

		sipBoardStatsC1dRegistrationsActive OBJECT-TYPE
			SYNTAX INTEGER
			ACCESS read-only
			STATUS mandatory
			DESCRIPTION
			" The amount of registrations being active at SIP termination ports at the end of the current 1 day interval. In the current implementation, only 1 registration can be active at a subscriber port at a time. An active registration is counted when a registration request has been successfully completed in the past (200 OK received to register request with 'expire header' time <> 0) and the register expiration interval hasn't expired.
				ALCATEL-LUCENT NOTE:
				ACCESS:	READ-ONLY
				USAGE:	NA
				PERSIST:	NO
				INSRVMOD:	NA
				RANGE:	NA
				DEFVALUE: 	NA
				UNITS:	Number
		                   SPARSE:	NA
					"
			::= { sipBoardStatsC1dEntry 27 }

		sipBoardStatsC1dOutgoingCallsAnswered OBJECT-TYPE
			SYNTAX INTEGER
			ACCESS read-only
			STATUS mandatory
			DESCRIPTION
			" The amount of outgoing call attempts in this current 1 day interval for which an initial INVITE request is sent AND for which a response is received. The system allows to provision what kind of response must be received as to be counted as a successful outgoing call attempt. The system offers the following options : 
			o Any response be received (irrespective of whether this is a successful or unsuccessful response). 
			o A successful response be received (180 or 200 response only).
				ALCATEL-LUCENT NOTE:
				ACCESS:	READ-ONLY
				USAGE:	NA
				PERSIST:	NO
				INSRVMOD:	NA
				RANGE:	NA
				DEFVALUE: 	NA
				UNITS:	Number
		                   SPARSE:	NA
					"
			::= { sipBoardStatsC1dEntry 28 }

		sipBoardStatsC1dIncomingCallsAnswered OBJECT-TYPE
			SYNTAX INTEGER
			ACCESS read-only
			STATUS mandatory
			DESCRIPTION
			" The amount of incoming call attempts in this current 1 day interval for which a SIP response is sent being the result of the off-hook event been detected. The system allows to provision the kind of response that will be considered as to be counted as a successful incoming call attempt. The system offers the following options : 
			o Any response be sent. 
			o 180 response be sent.
				ALCATEL-LUCENT NOTE:
				ACCESS:	READ-ONLY
				USAGE:	NA
				PERSIST:	NO
				INSRVMOD:	NA
				RANGE:	NA
				DEFVALUE: 	NA
				UNITS:	Number
		                   SPARSE:	NA
					"
			::= { sipBoardStatsC1dEntry 29 }

-- =============================================================================
-- 
-- Sip Board Stats Perf Info Table
--=============================================================================
		sipBoardStatsPerfInfoTable OBJECT-TYPE
			SYNTAX SEQUENCE OF SipBoardStatsPerfInfoEntry
			ACCESS not-accessible
			STATUS mandatory
			DESCRIPTION
				"Statistics performance information for a voice LT board. An entry is create dupon voice LT board insertion. 
		
				7302/7330 ISAM-V : Supported.
				7363 NGVR : NOT supported.
				7367 SX : NOT Supported
		
			ALCATEL NOTE: 
			SUPPORT:  YES
			TABLESIZE:  DEP [NumOfLT] "
			::= { sipStatisticsAndData 13 }

		sipBoardStatsPerfInfoEntry OBJECT-TYPE
			SYNTAX SipBoardStatsPerfInfoEntry
			ACCESS not-accessible
			STATUS mandatory
			DESCRIPTION
				"The entry in the sipBoardStatsPerfInfoTable.
			ALCATEL NOTE:
			SUPPORT:  YES "
			INDEX { eqptSlotId }
			::= { sipBoardStatsPerfInfoTable 1 }


		SipBoardStatsPerfInfoEntry ::=
			SEQUENCE { 
			sipBoardStatsPerfC15mElapsedTime			INTEGER,
			sipBoardStatsPerfC1dElapsedTime			INTEGER,
			sipBoardStatsPerfIntervals					INTEGER,
			sipBoardStatsPerf1days					INTEGER
			}

		sipBoardStatsPerfC15mElapsedTime OBJECT-TYPE
			SYNTAX INTEGER
			ACCESS read-only
			STATUS mandatory
			DESCRIPTION
				"The amount of time, measured in seconds, that elapsed for the current 15 minutes interval.
				ALCATEL-LUCENT NOTE:
				ACCESS:	READ-ONLY
				USAGE:	NA
				PERSIST:	NO
				INSRVMOD:	NA
				RANGE:	NA
				DEFVALUE: 	NA
				UNITS:	Second
		                   SPARSE:	NA
					"
			::= { sipBoardStatsPerfInfoEntry 1 }

		sipBoardStatsPerfC1dElapsedTime OBJECT-TYPE
			SYNTAX INTEGER
			ACCESS read-only
			STATUS mandatory
			DESCRIPTION
					"The amount of time, measured in seconds, that elapsed for the current 1 day interval.
				ALCATEL-LUCENT NOTE:
				ACCESS:	READ-ONLY
				USAGE:	NA
				PERSIST:	NO
				INSRVMOD:	NA
				RANGE:	NA
				DEFVALUE: 	NA
				UNITS:	Second
		                   SPARSE:	NA
					"
			::= { sipBoardStatsPerfInfoEntry 2 }

		sipBoardStatsPerfIntervals OBJECT-TYPE
			SYNTAX INTEGER(0..96)
			ACCESS read-only
			STATUS mandatory
			DESCRIPTION
					"Number of previous 15 minutes intervals.
				ALCATEL-LUCENT NOTE:
				ACCESS:	READ-ONLY
				USAGE:	NA
				PERSIST:	NO
				INSRVMOD:	NA
				RANGE:	(0..96)
				DEFVALUE: 	NA
				UNITS:	NA
		                   SPARSE:	NA
					"
			::= { sipBoardStatsPerfInfoEntry 3 }


		sipBoardStatsPerf1days OBJECT-TYPE
			SYNTAX INTEGER(0..3)
			ACCESS read-only
			STATUS mandatory
			DESCRIPTION
					"Number of previous 1 day intervals.
				ALCATEL-LUCENT NOTE:
				ACCESS:	READ-ONLY
				USAGE:	NA
				PERSIST:	NO
				INSRVMOD:	NA
				RANGE:	(0..3)
				DEFVALUE: 	NA
				UNITS:	NA
		                   SPARSE:	NA
					"
			::= { sipBoardStatsPerfInfoEntry 4 }



-- =============================================================================
-- 
-- Sip Stats Config Table
--=============================================================================
		sipStatsConfigTable OBJECT-TYPE
			SYNTAX SEQUENCE OF SipStatsConfigEntry
			ACCESS not-accessible
			STATUS mandatory
			DESCRIPTION
			" Allows to configure the deployment properties of the Voice Performance Monitoring service. 
			Actually only 1 entry is supported as only 1 VSP is supported. This entry is auto-created upon system start-up. 
			
			7302/7330 ISAM-V : Supported.
			7363 NGVR : Supported.
			7367 SX : Supported
			
			ALCATEL NOTE: 
			SUPPORT:  YES
		        TABLESIZE:  1 "
		::= { sipStatisticsAndData 14 }

		sipStatsConfigEntry OBJECT-TYPE
			SYNTAX SipStatsConfigEntry
			ACCESS not-accessible
			STATUS mandatory
			DESCRIPTION
				"The entry in the sipStatsConfigTable.
			ALCATEL NOTE:
		        SUPPORT:  YES "
			INDEX { sipVSPId }
		::= { sipStatsConfigTable 1 }

		SipStatsConfigEntry ::=
			SEQUENCE { 
			sipStatsConfigAllowance				OCTET STRING,
			sipStatsConfigOutgCallAnsweredResp		OCTET STRING, 
			sipStatsConfigIncCallAnsweredResp		OCTET STRING
			}

		sipStatsConfigAllowance OBJECT-TYPE
			SYNTAX OCTET STRING (SIZE(1))
			ACCESS read-write
			STATUS mandatory
			DESCRIPTION
			" Bitmap that allows to enable/disable one, multiple or all Voice Performance Statistics Actually the system Following options ar esupported :
			option 1 : all Voice Performance Monitoring statistics categories enabled (15). 
			option 2 : all Voice Performance Monitoring statistics categories disabled (0). 
			Bitmap clarification :
			Bit 0 : per-line-statistics(1)
			Bit 1 : per-board-statistics(2) 
			Bit 2 : per-system-statistics(4) 
			Bit 3 :per-call-statistics(8)
			ALCATEL-LUCENT NOTE:
			ACCESS:	READ-WRITE
			USAGE:	OPT
			PERSIST:	YES
			INSRVMOD:	NO
			RANGE:	0|15
			DEFVALUE: 	15
			UNITS:	NA
		        SPARSE:	NA
			"
		::= { sipStatsConfigEntry 1 }

		sipStatsConfigOutgCallAnsweredResp OBJECT-TYPE
			SYNTAX OCTET STRING (SIZE(1)) 
			ACCESS read-write 
			STATUS mandatory 
			DESCRIPTION 
			"Bitmap that allows to configure the response code to be received as a reply to an outgoing call attempt in
			order to let the outgoing call atempt to be counted as successful. 
			Bitmap clarification :
			Bit 0 : any-response-recv(1), 
			Bit 1 : response-180-recv(2), 
			Bit 2 : response-200-recv(4),
			ALCATEL-LUCENT NOTE:
			ACCESS:	READ-WRITE
			USAGE:	OPT
			PERSIST:	YES
			INSRVMOD:	NO
			RANGE:	1|4|6
			DEFVALUE: 	1
			UNITS:	NA
			SPARSE:	NA
			"
		::= { sipStatsConfigEntry 2 } 

		sipStatsConfigIncCallAnsweredResp OBJECT-TYPE
			SYNTAX OCTET STRING (SIZE(1)) 
			ACCESS read-write 
			STATUS mandatory 
			DESCRIPTION 
			"Bitmap that allows to configure the response code to be sent as a reply to an incoming call attempt in order to let the incoming call atempt to be counted as successful. 
			Bitmap clarification :
			Bit 0 : any-response-sent(1), 
			Bit 1 : response-180-sent(2),
            BIT 2 : response-200-sent(4)
			ALCATEL-LUCENT NOTE:
			ACCESS:	READ-WRITE
			USAGE:	OPT
			PERSIST:	YES
			INSRVMOD:	NO
			RANGE:	1|2|4
			DEFVALUE: 	1
			UNITS:	NA
		    SPARSE:	NA
			"
		::= { sipStatsConfigEntry 3 }


--===================================================================
-- SIP Transport Table
--===================================================================
			sipTransportTable OBJECT-TYPE
				SYNTAX SEQUENCE OF SipTransporttEntry
				ACCESS not-accessible
				STATUS mandatory
				DESCRIPTION
					"Transport protocols supported by the access device.

                    The system allows to do the provisioning in the following way :
                    (1) Method 1 : a separate entry is created for each of the transport protocols to be supported 
                    by the system for the Service Gateway. 
                    (2) Method 2 : a single entry is created enabling all transport protocols to be supported by the 
                    system for the Service Gateway. This method can only be used if the system can listen to the 
                    same transport protocol port for all transport protocols enabled by this entry. 
                    (3) Method 3 : A mix of method 1 and method 2.
                                        
                    R4.3 and following releases  implementation restriction :
                    The Common SIP Voice Call Control Package does only support UDP and TCP as underlying transport protocol for SIP. 
                    Conclusion : only METHOD 2 is supported. 

                    The flexibility to have also method 1 and method 3 supported is intended for (a) future releases of the
                    Common SIP Voice Call Control Package.
                                                                        
                    The operator must create a transport protocol entry for each Service Gateway created and activated
                    in the access node (administrative state = unlocked).
                    Maximum 16 entries can be created in the sipTransportTable.

                    7302/7330 ISAM FTTN : Supported
                    7363 MX : Supported
                    7367 SX : Supported					
					 				   
					ALCATEL NOTE: 
					SUPPORT:  YES
					TABLESIZE:  16
			              "
			::= { sipMIB 29}

		sipTransportEntry OBJECT-TYPE
			SYNTAX SipTransporttEntry
			ACCESS not-accessible
			STATUS mandatory
			DESCRIPTION
				" An entry in the SIP Transport Table. "
			INDEX { sipTransportProtocol, sipTransportProviderName }
			::= { sipTransportTable 1 }

		SipTransporttEntry::=
			SEQUENCE { 
				sipTransportProtocol			INTEGER,
				sipTransportProviderName		OCTET STRING,
				sipTransportRowStatus			RowStatus,					
				sipTransportAdminStatus			INTEGER,
				sipTransportPortRcv				InetPortNumber,
				sipTransportTCPIdleTime			INTEGER,
				sipTransportMaxOutgUdpReqSize	INTEGER
			 	}

		sipTransportProtocol OBJECT-TYPE
			SYNTAX INTEGER
			ACCESS not-accessible
			STATUS mandatory
			DESCRIPTION
				" The SIP Transport protocol being supported as underlying transport protocol for SIP Signaling.
				Actually, the Common SIP Voice Call Control Package does only support UDP and TCP as underlying
				transport protocol for SIP.
				Supported values :
				bit 0 = reserved, 
				bit 1 = UDP,
				bit 2 = TCP, 
				bit 3 = SCTP, (for future extendibility)
				bit 4 = TLSoTCP, (for future extendibility)
				bit 5 = TLSoSCTP. (for future extendibility)
				In case METHOD 1 is applied, this object may be provisioned with either bit 1 set or bit 2 set.
				In case METHOD 2 is applied, this object may be provisioned with either bit 1 set or bit 2 set or both 
				bit1 and bit 2 set. 
				In case METHOD 3 is applied, this object may be set either as explained for method 1 or as explained for
				 method 2.
				ALCATEL-LUCENT NOTE:
				ACCESS:	NOT-ACCESSIBLE
				USAGE:	MANDATORY
				PERSIST:	YES
				INSRVMOD: NO
				RANGE:	2|4|6
				DEFVALUE:  2
				UNITS:	NA
				SPARSE:	NO
				" 
			::= { sipTransportEntry 1 }


		sipTransportProviderName OBJECT-TYPE
			SYNTAX OCTET STRING (SIZE (0..32))
			ACCESS read-write
			STATUS mandatory
			DESCRIPTION
                          "The name of the parent Service Gateway.
                          The transport protocol(s) to be supported by the system are to be defined in function of the transport 
                          protocol(s) supported by the SIP first hop. (The transport protocols supported behind the SIP first hop 
                          are out of the scope of the Common SIP Voice Call Control package).

			 ALCATEL NOTE:
			 ACCESS:read_write
			 USAGE:	NA		
			 PERSIST:	YES
			 INSRVMOD: NO
			 RANGE:	SIZE (0..32))
			 DEFVALUE: 	vsp1
			 UNITS:	NA	
			 SPARSE:	NO
			 "				
			::= { sipTransportEntry 2 }

		sipTransportRowStatus OBJECT-TYPE
			SYNTAX RowStatus
			ACCESS read-write
			STATUS mandatory
			DESCRIPTION
				"The row status state of this conceptual row.
				ALCATEL-LUCENT NOTE:
				ACCESS:	READ-WRITE
				USAGE:	MAND
				PERSIST:	NO
				INSRVMOD: YES
				RANGE:	1 | 4 | 6	-- active (1), createAndGo (4), destroy (6)
				DEFVALUE:  NA
				UNITS:	NA
				SPARSE:	NO
			" 
		::= { sipTransportEntry 3 }

		sipTransportAdminStatus OBJECT-TYPE
			SYNTAX INTEGER
				{
				up(1),
				down(2)
				}
			ACCESS read-write
			STATUS mandatory
			DESCRIPTION
				" The administrative state of this Sip Transport table entry.
				UP(1) : only the configurable attributes of this entry that have the INSRVMOD attribute in the ALCATEL NOTE set to YES can be modified.
				DOWN (2) : all configurable attributes of this entry can be modified, irrespective of whether the INSRVMOD
				attribute in the ALCATEL NOTE is set to YES or NO
				Note that the attributes for which the INSRVMOD attribute in the ALCATEL NOTE is set to NA cannot be modified.
				ALCATEL-LUCENT NOTE:
				ACCESS:	READ-WRITE
				USAGE:	OPT
				PERSIST:	YES
				INSRVMOD: YES
				RANGE:	up (1) | down (2)
				DEFVALUE:  down (2)
				UNITS:	NA
				SPARSE:	NO
			" 
		::= { sipTransportEntry 4 }

		sipTransportPortRcv OBJECT-TYPE
			SYNTAX InetPortNumber
			ACCESS read-write
			STATUS mandatory
			DESCRIPTION
			" The transport protocol port to which the SIP User Agent  will listen.
			Actually, the Common Voice Package does only support UDP and TCP as 
			underlying transport protocol for SIP.
			It does currently not offer the possibility to listen to a different port number for UDP and for TCP.
			
			7302/7330 ISAM FTTN : 
		    In case the forwarding policy is defined as centralized then
              -   The configuration of this object is irrelevant,
              -   The system shall autonomously define the receive port.
              -   Any value that would be configured for this object will be ignored by the system
              -   As the default value = 5060, in order to avoid any confusion, it is preferred to configure the value 0 for this object.
 

			7363 MX / 7367 SX:
            The 7363 MX and 7367 SX does only support the centralized IP Addressing mode.
            The operator can configure the transport protocol port to which the SIP User Agent will listen.
            Should no input be received from the operator, the system will allocate the default port number i.e.  
            5060 as transport protocol listen port.

			
			ALCATEL-LUCENT NOTE:
			ACCESS:	READ-WRITE
			USAGE:	OPT
			PERSIST:	YES
			INSRVMOD: NO
			RANGE:	(0..65534)
			DEFVALUE:  5060
			UNITS:	NA
			SPARSE:	NO
			" 
		::= { sipTransportEntry 5 }

		sipTransportTCPIdleTime OBJECT-TYPE
			SYNTAX INTEGER (32..3600)
			ACCESS read-write
			STATUS mandatory
			DESCRIPTION
			" The value used to calculate the time period after which a TCP connection, over which no activity 
			was detected, is closed. The configured value will be applied as a cyclic timer value. As a result, a 
			TCP connection over which no activity was detected for a period of minimum 
			SIPTransportTCPMaxIdleTime and a maximum of 2* SIPTransportTCPMaxIdleTime will be closed.
			The value configured for this object shall be aligned with the SIP transaction time-out (Timer B / Timer F).
			This object has only relevance in case TCP is supported as underlying transport protocol for SIP. 
			ALCATEL-LUCENT NOTE:
			ACCESS:	READ-WRITE
			USAGE:	OPT
			PERSIST:	YES
			INSRVMOD: NO
			RANGE:	(32..3600)
			DEFVALUE:  64
			UNITS:	Second
			SPARSE:	NO
			" 
		::= { sipTransportEntry 6 }

		sipTransportMaxOutgUdpReqSize OBJECT-TYPE
			SYNTAX INTEGER (576..65535)
			ACCESS read-write
			STATUS mandatory
			DESCRIPTION
			" The maximum SIP request size that may be sent over UDP.
			This object has only relevance in case both UDP and TCP are support as underlying transport 
			protocols for SIP.
			A value 65535 means that UDP to TCP fail-over is disabled.)
			ALCATEL-LUCENT NOTE:
			ACCESS:	READ-WRITE
			USAGE:	OPT
			PERSIST:	YES
			INSRVMOD: NO
			RANGE:	(576..65535)
			DEFVALUE:  65535
			UNITS:	Byte
			SPARSE:	NO
			" 
		::= { sipTransportEntry 7 }


--===================================================================
--SIP Register Table
--===================================================================
		sipRegisterTable OBJECT-TYPE
			SYNTAX SEQUENCE OF SipRegisterEntry
			ACCESS not-accessible
			STATUS mandatory
			DESCRIPTION
			"The SIP Register Table allowing to configure the SIP Register method specifc characteristics 

            An entry is auto-created upon the creation of an entry in the sipVSPTable.
            An entry is auto-deleted upon the deletion of an entry in the sipVSPTable.

            The sipRegisterTable may contain up to 17 entries.

            7302/7330 ISAM FTTN : Supported
            7363 MX : Supported
	    7367 SX : Supported
			
			ALCATEL NOTE: 
			SUPPORT:  YES
			TABLESIZE:  17
			"
		::= { sipMIB 30}

		sipRegisterEntry OBJECT-TYPE
			SYNTAX SipRegisterEntry
			ACCESS not-accessible
			STATUS mandatory
			DESCRIPTION
			" An entry in the SIP Register Table. "
			INDEX { sipRegisterProviderName }
		::= { sipRegisterTable 1 }

		SipRegisterEntry ::=
			SEQUENCE { 
			sipRegisterProviderName			OCTET STRING,
			sipRegisterRowStatus			RowStatus,					
			sipRegisterUri				OCTET STRING,
			sipRegisterIntv				INTEGER,
			sipRegisterRetryIntv				INTEGER,
			sipRegisterHeadStart			INTEGER,
			sipRegisterStartMin				INTEGER,
			sipRegisterPrevAvalancheIntv		INTEGER
	 		}

		sipRegisterProviderName OBJECT-TYPE
			SYNTAX OCTET STRING (SIZE (0..32))
			ACCESS read-only
			STATUS mandatory
			DESCRIPTION
				"The name of the parent Service Gateway. 
				ALCATEL-LUCENT NOTE:
				ACCESS:	READ-ONLY
				USAGE:	MANDATORY
				PERSIST:	YES
				INSRVMOD: NO
				RANGE:	SIZE(0..32)
				DEFVALUE:  NA
				UNITS:	NA
				SPARSE:	NO
				" 
			::= { sipRegisterEntry 1 }

		sipRegisterRowStatus OBJECT-TYPE
			SYNTAX RowStatus
			ACCESS read-write
			STATUS mandatory
			DESCRIPTION
			"The row status state of this conceptual row.
			ALCATEL-LUCENT NOTE:
			ACCESS:	READ-WRITE
			USAGE:	MAND
			PERSIST:	NO
			INSRVMOD: YES
			RANGE:	1	-- active (1)
			DEFVALUE:  NA
			UNITS:	NA
			SPARSE:	NO
			" 
		::= { sipRegisterEntry 2 }

		sipRegisterUri OBJECT-TYPE
			SYNTAX OCTET STRING
			ACCESS read-write
			STATUS mandatory
			DESCRIPTION
			"The registration URI to be used by all SIP terminations associated with a particular Service Gateway.
			ALCATEL-LUCENT NOTE:
			ACCESS:	READ-WRITE
			USAGE:	OPT
			PERSIST:	YES
			INSRVMOD: NO
			RANGE:	(0..80)
			DEFVALUE:  null
			UNITS:	NA
			SPARSE:	NO
			" 
		::= { sipRegisterEntry 3 }

		sipRegisterIntv OBJECT-TYPE
			SYNTAX INTEGER
			ACCESS read-write
			STATUS mandatory
			DESCRIPTION
				"The initial Re-register Interval.
				The Re-registering can be disabled by provisioning this object with a value = 0. 
				When the Re-registering is disabled it means that all SIP terminations shall not refresh a registration even if
				the server specifies an expiration interval 
				ALCATEL-LUCENT NOTE:
				ACCESS:	READ-WRITE
				USAGE:	OPT
				PERSIST:	YES
				INSRVMOD: NO
				RANGE:	0|(60..86400)
				DEFVALUE:  3600
				UNITS:	Second
				SPARSE:	NO
				" 
		::= { sipRegisterEntry 4 }

		sipRegisterRetryIntv OBJECT-TYPE
			SYNTAX INTEGER
			ACCESS read-write
			STATUS mandatory
			DESCRIPTION
			" This object allows to define the register retry interval in case ofregister failure. 
			The value of 0 shall disable registration retry. 
			ALCATEL-LUCENT NOTE:
			ACCESS:	READ-WRITE
			USAGE:	OPT
			PERSIST:	YES
			INSRVMOD: NO
			RANGE:	0|(30..86400)
			DEFVALUE:  60
			UNITS:	Second
			SPARSE:	NO
			" 
		::= { sipRegisterEntry 5 }

		sipRegisterHeadStart OBJECT-TYPE
			SYNTAX INTEGER
			ACCESS read-write
			STATUS mandatory
			DESCRIPTION
			" The number of seconds prior to expiration of a registration (Low Frequent registration interval) at
			which the client sends a REGISTER request to refresh the registration.
			 The time to send the re-registration message is defined as follows :
			If Low Frequent registration interval expirey > 2* register_head_start then register_head_start 
			seconds prior to expiration i.e. the actual interval for re-registration message is 
			[Low Frequent registration interval expiry - register_head_start].
			Otherwise:  the re-registration will be done at [Low Frequent registration interval expiry * 0.5]
			ALCATEL-LUCENT NOTE:
			ACCESS:	READ-WRITE
			USAGE:	OPT
			PERSIST:	YES
			INSRVMOD: NO
			RANGE:	0|(32..86400)
			DEFVALUE:  600
			UNITS:	Second
			SPARSE:	NO
			" 
		::= { sipRegisterEntry 6 }

		sipRegisterStartMin OBJECT-TYPE
			SYNTAX INTEGER (30..70)
			ACCESS read-write
			STATUS mandatory
			DESCRIPTION
			" The percentage  prior to expiration of a registration 
			ALCATEL-LUCENT NOTE:
			ACCESS:	READ-WRITE
			USAGE:	OPT
			PERSIST:	YES
			INSRVMOD: NO
			RANGE:	(30..70)
			DEFVALUE:  50
			UNITS:	Percentage
			SPARSE:	NO
			" 
		::= { sipRegisterEntry 7 }  

		sipRegisterPrevAvalancheIntv OBJECT-TYPE
			SYNTAX INTEGER (100..32000)
			ACCESS read-write
			STATUS mandatory
			DESCRIPTION
			"Allows to define the magnitude of time nterval that must be awaited before the system is allowed to initiate
			another register request. The effective time interval being applied may be slightly different from the configured time interval because of some implementation constraints.
			ALCATEL-LUCENT NOTE:
			ACCESS:	READ-WRITE
			USAGE:	OPT
			PERSIST:	YES
			INSRVMOD: NO
			RANGE:	(100..32000)
			DEFVALUE:  500
			UNITS:	Milli-Second
			SPARSE:	NO
			" 
		::= { sipRegisterEntry 8 }

               
--===================================================================
--sip DHCP Authentication Params Table 
--===================================================================
		sipDHCPAuthentParaTable OBJECT-TYPE
			SYNTAX SEQUENCE OF SipDHCPAuthentParaEntry
			ACCESS not-accessible
			STATUS mandatory
			DESCRIPTION
			"This table allows to configure the Secret ID, Key and action type required when DHCP authentication is to be 
			applied. 
			The table is on relevant in case of the IP address policy is defined as 'distributed' and the config mode 
			defined as 'dhcp'.
		
    		7302/7330 ISAM FTTN : Supported
                7363 MX : Supported
	        7367 SX : Supported

			ALCATEL NOTE:
			TABLESIZE:  DEP [16 * 4]
			DESCR:      NA "
		::= { sipMIB 31}         

		sipDHCPAuthentParaEntry OBJECT-TYPE
			SYNTAX SipDHCPAuthentParaEntry
			ACCESS not-accessible
			STATUS mandatory
			DESCRIPTION
			" Each entry allows to configure the secret id, secret key and its action type." 
			INDEX {sipUserAgentId,sipDHCPAuthentParaSecretId }
		::= { sipDHCPAuthentParaTable 1 }

		SipDHCPAuthentParaEntry ::=
			SEQUENCE { 
			sipDHCPAuthentParaSecretId		INTEGER,
			sipDHCPAuthentParaKey			DisplayString,                                     
			sipDHCPAuthentParaActionType		INTEGER,
			sipDHCPAuthentParaRowStatus		RowStatus
		}

		sipDHCPAuthentParaSecretId OBJECT-TYPE
			SYNTAX  INTEGER (1.. 4294967295)
			ACCESS not-accessible
			STATUS mandatory
			DESCRIPTION
			" A unique identifier of the DHCP authentication record.
			ALCATEL-LUCENT NOTE:
			ACCESS:	NOT-ACCESSIBLE
			USAGE:	MANDATORY
			PERSIST:	YES
			INSRVMOD:	YES
			RANGE:	(1.. 4294967295)
			DEFVALUE:	NA
			UNITS:	NA
			SPARSE:	NO
			"
		::= { sipDHCPAuthentParaEntry 1 }

		sipDHCPAuthentParaKey OBJECT-TYPE
			SYNTAX DisplayString (SIZE (0..32))
			ACCESS read-write
			STATUS mandatory
			DESCRIPTION
			"DHCP secret key used for DHCP message authentication. Every letter in key must be in '0'~'9', 'a'~'f', 'A'~'F'
			 and the string length must  be even. For example, '1f2a3d'.
			ALCATEL-LUCENT NOTE:
			ACCESS:	READ-WRITE
			USAGE:	OPT
			PERSIST:	YES
			INSRVMOD:	YES
			RANGE: 	SIZE (0..32)
			DEFVALUE:	null
			UNITS:	NA
			SPARSE:	NO
			"
		::= { sipDHCPAuthentParaEntry 2 }

		sipDHCPAuthentParaActionType OBJECT-TYPE
			SYNTAX INTEGER
			{
			normal-send-request(1),
			force-renew-send-discover(2),
			force-renew-send-renew(3),
			norm-send-req-and-force-renew-send-discov (4),
			norm-send-req-and-force-renew-send-renew(5)
			}
			ACCESS read-write
			STATUS mandatory
			DESCRIPTION
			"This parameter defines the action type for the configured DHCP secret keys. 
			This means that the DHCP client and server can use this secret key and secret id for the
			authentication of normal request message, discover message in force renew state, 
			renew message in force renew sate, or their combine situations: normal request and force renew.
			ALCATEL-LUCENT NOTE:
			ACCESS:	READ-WRITE
			USAGE:	OPT
			PERSIST:	YES
			INSRVMOD:	YES
			RANGE: 	1 | 2 | 3 | 4 | 5
			DEFVALUE:	1
			UNITS:	NA
			SPARSE:	NO
			"
		::= { sipDHCPAuthentParaEntry 3 } 

		sipDHCPAuthentParaRowStatus OBJECT-TYPE
			SYNTAX RowStatus
			ACCESS read-write
			STATUS mandatory
			DESCRIPTION
			"The status of this conceptual row.
			The RowStatus TC requires that this DESCRIPTION clause
			states under which circumstances other objects in this row
			can be modified.  The value of this object has no effect on
			whether other objects in this conceptual row can be
			modified.
			A conceptual row can always be made active.
			ALCATEL-LUCENT NOTE:
			ACCESS:	READ-WRITE
			USAGE:	MAND
			PERSIST:	NO
			INSRVMOD:	YES
			RANGE:  	1 | 4 | 6       -- active (1), createAndGo(4), destroy (6)
			DEFVALUE:	NA
			UNITS: 	NA
			SPARSE:	NO
			"
		::= { sipDHCPAuthentParaEntry 4 }


          	

--===================================================================
--SIP Redundancy Command Table	
--===================================================================
		sipRedunCommandTable OBJECT-TYPE
			SYNTAX SEQUENCE OF SipRedunCommandEntry
			ACCESS not-accessible
			STATUS mandatory
			DESCRIPTION
				"The SIP Redundancy Command allows the administrator to perform a manually triggered 
                Geo Fail-Over or Geo Fail-Back and to follow the progress of these actions.

                7302/7330 ISAM FTTN : Supported
                7363 MX : Supported
		7367 SX : Supported
				
				ALCATEL NOTE: 
				SUPPORT:  YES
				TABLESIZE:  1
				"
		::= { sipMIB 34}

		sipRedunCommandEntry OBJECT-TYPE
			SYNTAX SipRedunCommandEntry
			ACCESS not-accessible
			STATUS mandatory
			DESCRIPTION
			" An entry in the Sip redundancy CommandTable
			ALCATEL NOTE:
			SUPPORT:  YES" 
			INDEX {sipRedunCommandAdminDomName}
		::= { sipRedunCommandTable 1 }

		SipRedunCommandEntry ::=
		SEQUENCE { 
			sipRedunCommandAdminDomName		OCTET STRING,				
			sipRedunCommandRowStatus		        	RowStatus,	
			sipRedunCommandFailXStartTime		NetworkTimeInSeconds,
			sipRedunCommandFailXEndTime		NetworkTimeInSeconds,
			sipRedunCommandFailXType			INTEGER,
			sipRedunCommandFailXProgress		INTEGER,
			sipRedunCommandFailXFailureReason		OCTET STRING
			}

		sipRedunCommandAdminDomName OBJECT-TYPE
			SYNTAX OCTET STRING (SIZE (0..32))
				ACCESS read-only
				STATUS mandatory
				DESCRIPTION
				"The name of the parent Service Gateway. 
				ALCATEL-LUCENT NOTE:
				ACCESS:	READ-ONLY
				USAGE:	NA		
				PERSIST:	NO
				INSRVMOD: YES
				RANGE:	SIZE (0..32))
				DEFVALUE: 	NA
				UNITS:	NA	
				SPARSE:	NO
				"
		::= { sipRedunCommandEntry 1}

		sipRedunCommandRowStatus OBJECT-TYPE
			SYNTAX RowStatus
			ACCESS read-write
			STATUS mandatory
			DESCRIPTION
				"The row status state of this conceptual row.
			ALCATEL-LUCENT NOTE:
			ACCESS:	READ-WRITE
			USAGE:	MAND
			PERSIST:	NO
			INSRVMOD: YES
			RANGE:	1 	-- active (1)
			DEFVALUE: 	NA
			UNITS:	NA	
			SPARSE:	NO
			"
		::= { sipRedunCommandEntry 2 }

		sipRedunCommandFailXStartTime OBJECT-TYPE
			SYNTAX NetworkTimeInSeconds
			ACCESS read-write
			STATUS mandatory
			DESCRIPTION
			" The absolute time when the manually triggeredl GEO Fail-Over / Fail-Back needs to start.
			A value 0 means that the Fail-Over / Fail-Back must immediately be triggered.
			ALCATEL-LUCENT NOTE:
			ACCESS:	READ-WRITE
			USAGE:	OPT
			PERSIST:	NO
			INSRVMOD: YES
			RANGE:	NA
			DEFVALUE: 	0
			UNITS:	NA	
			SPARSE:	NO
			"				
		::= { sipRedunCommandEntry 3 }

		sipRedunCommandFailXEndTime OBJECT-TYPE
			SYNTAX NetworkTimeInSeconds
			ACCESS read-write
			STATUS mandatory
			DESCRIPTION
			" The absolute time when the manually triggered graceful Geo Fail-Over / Fail-Back needs to be completed.
			After this time period, forced Failx will be triggered.
			The time entered for this object must always be greater than the time entered for the object
			sipRedunCommandXStartTime                
			ALCATEL-LUCENT NOTE:
			ACCESS:	READ-WRITE
			USAGE:	OPT
			PERSIST:	NO
			INSRVMOD: YES
			RANGE:	NA
			DEFVALUE: 	0
			UNITS:	NA	
			SPARSE:	NO
			"				
		::= { sipRedunCommandEntry  4 }

		sipRedunCommandFailXType OBJECT-TYPE
			SYNTAX INTEGER
			{
				geo-fail-over (1),
				geo-fail-back (2)
				}
			ACCESS read-write
			STATUS mandatory
			DESCRIPTION
			" The kind of Fail-Over / Fail-Back action to be triggered.
			ALCATEL-LUCENT NOTE:
			ACCESS:	READ-WRITE
			USAGE:	OPT
			PERSIST:	NO
			INSRVMOD: YES
			RANGE:	1 | 2
			DEFVALUE: 	NA
			UNITS:	NA	
			SPARSE:	NO
			"				
		::= { sipRedunCommandEntry 5 }

		sipRedunCommandFailXProgress OBJECT-TYPE
			SYNTAX INTEGER
			{
				not-started (1),                                                  
				running (2),                                                       
				successful-completed (3),                                         
				failed (4)                                                         
				}                                                                          
			ACCESS read-only                                                                   
			STATUS mandatory                                                                   
			DESCRIPTION                                                                        
				" The progress of  the Fail-Over / Fail-Back action being triggered.  
				ALCATEL-LUCENT NOTE:                                                 
				ACCESS:	READ-ONLY                                                
				USAGE:	NA                                                 
				PERSIST:	NA                                                 
				INSRVMOD: NA                                                       
				RANGE:	1 | 2   | 3 | 4                                            
				DEFVALUE: 	NA                                                 
				UNITS:	NA	                                                   
		                SPARSE  :	NO                                         
			"				                                           
		::= { sipRedunCommandEntry 6 }             
                               
		sipRedunCommandFailXFailureReason OBJECT-TYPE                                                        
			SYNTAX OCTET STRING (SIZE (0..32))
			ACCESS read-only                                                                  
			STATUS mandatory                                                                   
			DESCRIPTION                                                                        
			" sipRedunCommandFailXFailureReason  shows the result of the command 
			If it was successfully completed, then sipRedunCommandFailXFailureReason has less meaning. (shall be null)
			But if it has failed, then sipRedunCommandFailXFailureReason shall indicate the reason why it has failed.
			The value can be as followings:
			-Redundancy not enabled 
			- No valid server in back-up site
			- No valid server in primary site
			- Already in primary site
			- Already in back up site
			ALCATEL-LUCENT NOT  E:                                                 
				ACCESS:	READ-O NLY                                                
				USAGE:	NA                                                 
				PERSIST:	NA                                                 
				INSRVMOD: NA                                                       
				RANGE:	SIZE (0..32) 
				DEFVALUE: 	NA                                                 
				UNITS:	NA	                                                   
				SPARSE  :	NO                                         
			"				                             
	        ::= { sipRedunCommandEntry 7 }

--===================================================================
--Sip Port State Table
--===================================================================

        sipPortStateTable OBJECT-TYPE
            SYNTAX SEQUENCE OF SipPortStateEntry
            ACCESS not-accessible
            STATUS mandatory
            DESCRIPTION
            "The port state table allows to display the port state of a SIP termination in compliancy with Technical Guideline 163TR26
            Upon the start-up of a voice LT board, an entry for each port of the voice LT board (NPOT-B =72 / NPOT-C = 48)
            gets auto-created by the system in the sipPortStateTable. The entry is auto-created with default port state = P0.

            7302/7330 ISAM FTTN : Supported
            7363 MX : NOT Supported
	    7367 SX : NOT Supported

            ALCATEL NOTE:
            TABLESIZE: DEP [max nbr voice LT boards planned in a shelf (1..18) * Max nbr of subscriber ports of a voice LT board (48 or 72)]
            DESCR:NA."

            ::= {sipMIB 35}

        sipPortStateEntry OBJECT-TYPE
            SYNTAX SipPortStateEntry 
            ACCESS not-accessible
            STATUS mandatory
            DESCRIPTION
            "An entry of the sipPortStatetable.
            The entry reflects the current port state of a provisioned / not provisioned SIP termination."
            INDEX { ifIndex }
            ::= {sipPortStateTable 1}

        SipPortStateEntry ::=
            SEQUENCE {
                sipPortStateConn1 OCTET STRING ,
                sipPortStateConn2 OCTET STRING ,
                sipPortQueryResult              DisplayString,   
                sipPortAdminStatus              INTEGER,         
                sipPortOperStatus               INTEGER,
                sipPortLineTermination          INTEGER,       
                sipPortUssStatus                INTEGER,     
                sipPortSupplyVoltageRT          INTEGER,        
                sipPortSupplyVoltageTR          INTEGER,       
                sipPortSupplyVoltageRG          INTEGER,      
                sipPortSupplyVoltageTG          INTEGER,     
                sipPortSupplyCurrent            INTEGER,    
                sipPortLongitudinalCurrent      INTEGER,   
                sipPortFeedingStatusValidity    INTEGER   
            }

        sipPortStateConn1 OBJECT-TYPE
            SYNTAX OCTET STRING (SIZE (0..32)) 
            ACCESS read-only
            STATUS mandatory
            DESCRIPTION
		       "
		        P0           --;Not created
		        P1           --;Idle state 
		        P2           --;Outgoing Seizure
		        P2.1         --;End-of-dialing
		        P3           --;Incoming seizure
		        P4           --;Stable call state
		        P4.1         --;Hold a connection
		        P4.2         --;Hold a connection and additional connection has been established.
		        P4.3         --;Service
		        P4.4         --;Conference
		        P5.1         --;Release request 1
		        P5.2         --;Release request 2
		        P5.3         --;Release request 3
		        P6           --;Port blocked
		        P7           --;Test

            Following overall rules apply:
            1.  Rule 1 : sipTermTestAccessState = 'ON(1)' <or>  sipTerminationTestStatus = 'INTGLINETESTING(3)' : 
              Port state = 'P7' state.
            2.  Rule 2 : sipTermTestAccessState = 'OFF(2)' <and>  sipTerminationTestStatus = 'NOTESTING(1)'  <and> sipTerminationOperStatus = 'DOWN(2)'  : 
              Port state = 'P6' state.
            3.  Rule 3 : sipTermTestAccessState = 'OFF(2)' <and>  sipTerminationTestStatus = 
             'NOTESTING(1)'  <and> sipTerminationOperStatus = 'UP(1)' : 
             Port state = Call state (P1 ... P5.3) ref. above table.
          
            Note : Operational State = 'Down (2)' may be caused by :
            Admin state of the SIP termination set to 'down' by the operator.
            Admin state of the SIP termination set to 'up' by the operator but the SIP termination is not (successfully) registered (yet).
            Admin state of the SIP termination set to 'up' by the operator but the SIP termination's line is in alarm state.

            Additional details can be found in document 'Technische Richtlinie 163TR26-Umsetzung der Zeichengabe an Analogen Telefonanschlussen ohne Durchwahl auf das 
            SIP-Protokoll im Netz der Deutschen Telekom' Ausgabe: V1.4.1, Januar 2014.
	
            ALCATEL-LUCENT NOTE:
	        ACCESS: READ-ONLY
	        USAGE: NA
	        PERSIST: NO
	        INSRVMOD: NA
	        RANGE: SIZE (0..32)
	        DEFVALUE: P0
	        UNITS: NA
	        SPARSE: NO
	             "
	       ::= {sipPortStateEntry 1}


       sipPortStateConn2 OBJECT-TYPE
           SYNTAX OCTET STRING (SIZE (0..32))
	       ACCESS read-only
           STATUS mandatory
           DESCRIPTION
           "Actually not supported; defined fro future usage. Value fixed to P0.

           ALCATEL-LUCENT NOTE:                 
           ACCESS: READ-ONLY                 
           USAGE: NA                 
           PERSIST: NO                 
           INSRVMOD: NA                 
           RANGE: SIZE (0..32)                 
           DEFVALUE: P0                 
           UNITS: NA                 
           SPARSE: NO
           "
	       ::= {sipPortStateEntry 2}

       sipPortQueryResult OBJECT-TYPE
            SYNTAX     DisplayString  (SIZE (0..63)) 
            ACCESS     read-only
            STATUS     mandatory
            DESCRIPTION "the textual result description . Filled by LT and interpret by network manager
            ALCATEL-LUCENT NOTE:
               ACCESS:     READ-ONLY
               USAGE:      NA
               PERSIST:    NO
               INSRVMOD:   NA
               RANGE:      NA
               DEFVALUE:   null 
               UNITS:      NA
               SPARSE:     NO"
            ::= { sipPortStateEntry 3}
       
       sipPortAdminStatus OBJECT-TYPE
           SYNTAX INTEGER
           {
              up(1),
              down(2)
           }
           ACCESS read-only
           STATUS mandatory
           DESCRIPTION    "The administrative status of this sip termination.
                           When the administrative status of a SIP termination is modified from 'up' to 'down', then the system will
                           de-register the SIP termination and power down the line. 
                           UP (1): the attributes of this entry that are indicated as INSRVMOD=YES can be modified.
                           DOWN (2): the attributes of this entry that are indicated as INSRVMOD=YES and the attributes that are 
                                      indicated as INSRVMOD=NO can be modified.
                           Note that the attributes of this entry that are indicated INSRVMOD=NA can not be modified after creation.
            ALCATEL-LUCENT NOTE: 
            ACCESS:        READ-ONLY
            USAGE:         NA
            PERSIST:       NO   
            INSRVMOD:      NO
            RANGE:         1 | 2 
            DEFVALUE:      down  
            UNITS:         NA      
            SPARSE:        NO  "     
           ::= { sipPortStateEntry 4}
       
       sipPortOperStatus OBJECT-TYPE
            SYNTAX INTEGER
           {
              up(1),
              down(2)
            }
            ACCESS read-only
            STATUS mandatory
            DESCRIPTION   " The operational status of this sip termination.
                           up(1) :  The SIP Termination is up and able to make calls.
                           down(2) : The SIP Termination is out of service.
            ALCATEL-LUCENT NOTE:
            ACCESS:        READ-ONLY
            USAGE:         NA
            PERSIST:       NO
            INSRVMOD:      NA
            RANGE:         1 | 2
            DEFVALUE:      down 
            UNITS:         NA
            SPARSE:        NO "
           ::= { sipPortStateEntry 5}
       
       sipPortLineTermination   OBJECT-TYPE
            SYNTAX INTEGER
           {
              high-resistance(1),
              low-resistance(2)
           }
           ACCESS read-only
           STATUS mandatory
           DESCRIPTION
                       "The status of call at this termination, The meaning of the status is list as following:
                       high-Resistance(1): hook on without any call
                       Low-Resistance(2): hook off but user no dialing
           ALCATEL-LUCENT NOTE:
           ACCESS:        READ-ONLY
           USAGE:         NA
           PERSIST:       NO
           INSRVMOD:      NA
           RANGE:         1 | 2
           DEFVALUE:      high-Resistance 
           UNITS:         NA  
           SPARSE:        NO"
       ::= { sipPortStateEntry 6 }
       
       sipPortUssStatus OBJECT-TYPE
            SYNTAX INTEGER
           {
              true(1),
              false(2)
            }
           ACCESS read-only
           STATUS mandatory
           DESCRIPTION " A loop closure will be unnecessary when the port is in sipPortStatus = P5.3 and 
           there is nothing to hear on the line. this state also is called as parking mode or IdleOffHook. 
           1-TR110 sections 6.2.3.4 (figure 6.2) calls it Pull down state.
           the loop closure is not unnecessary as long as you hear GBsTone. The subscriber 
           should has a chance to hang up the telephone and so to open the loop.
                        true(1),    port is in P5.3 and GBsTone is already switched off (Power Down)
                        false(2),   port is not in Power Down
       
           ALCATEL-LUCENT NOTE:
           ACCESS:        READ-ONLY
           USAGE:         NA
           PERSIST:       NO
           INSRVMOD:      NA
           RANGE:         1 | 2
           DEFVALUE:      false
           UNITS:         NA  
           SPARSE:        NO"
           ::= { sipPortStateEntry 7 }
       
       sipPortSupplyVoltageRT OBJECT-TYPE
            SYNTAX     INTEGER
            ACCESS     read-only
            STATUS     mandatory
            DESCRIPTION "value report from LT.
                         Feeded DC voltage of user line (Ring-Tip) 
            ALCATEL-LUCENT NOTE:
            ACCESS:    READ-ONLY
            USAGE:     NA
            PERSIST:   NO
            INSRVMOD:  NA
            RANGE:     NA
            DEFVALUE:  0
            UNITS:     uV 
            SPARSE:    NO"
            ::= { sipPortStateEntry 8}
       
       sipPortSupplyVoltageTR   OBJECT-TYPE
            SYNTAX     INTEGER
            ACCESS     read-only
            STATUS     mandatory
            DESCRIPTION "value report from LT.
                         Feeded DC voltage of user line (Tip-Ring) 
            ALCATEL-LUCENT NOTE:
            ACCESS:    READ-ONLY
            USAGE:     NA
            PERSIST:   NO
            INSRVMOD:  NA
            RANGE:     NA
            DEFVALUE:  0 
            UNITS:     uV 
            SPARSE:    NO"
            ::= { sipPortStateEntry 9}
       
       sipPortSupplyVoltageRG   OBJECT-TYPE
            SYNTAX     INTEGER
            ACCESS     read-only
            STATUS     mandatory
            DESCRIPTION "value report from LT.
                         Feeded DC voltage of user line (Ring-Groud) 
            ALCATEL-LUCENT NOTE:
            ACCESS:    READ-ONLY
            USAGE:     NA
            PERSIST:   NO
            INSRVMOD:  NA
            RANGE:     NA
            DEFVALUE:  0
            UNITS:     uV 
            SPARSE:    NO"
            ::= { sipPortStateEntry 10}
       
       sipPortSupplyVoltageTG   OBJECT-TYPE
            SYNTAX     INTEGER
            ACCESS     read-only
            STATUS     mandatory
            DESCRIPTION "value report from LT.
                         Feeded DC voltage of user line (Tip-Groud) 
            ALCATEL-LUCENT NOTE:
            ACCESS:    READ-ONLY
            USAGE:     NA
            PERSIST:   NO
            INSRVMOD:  NA
            RANGE:     NA
            DEFVALUE:  0
            UNITS:     uV 
            SPARSE:    NO"
            ::= { sipPortStateEntry 11}
       
       
       sipPortSupplyCurrent   OBJECT-TYPE
            SYNTAX     INTEGER
            ACCESS     read-only
            STATUS     mandatory
            DESCRIPTION "value report from LT.
                         Feeding current(Tip-Ring)
            ALCATEL-LUCENT NOTE:
            ACCESS:    READ-ONLY
            USAGE:     NA
            PERSIST:   NO
            INSRVMOD:  NA
            RANGE:     NA
            DEFVALUE:  0
            UNITS:     uA 
            SPARSE:    NO"
            ::= { sipPortStateEntry 12}
       
       sipPortLongitudinalCurrent    OBJECT-TYPE
            SYNTAX     INTEGER
            ACCESS     read-only
            STATUS     mandatory
            DESCRIPTION "value report from LT.
                         Measurement of the difference between the currents on the a-lead and the b-lead
            ALCATEL-LUCENT NOTE:
            ACCESS:    READ-ONLY
            USAGE:     NA
            PERSIST:   NO
            INSRVMOD:  NA
            RANGE:     NA
            DEFVALUE:  0
            UNITS:     uA 
            SPARSE:    NO"
            ::= { sipPortStateEntry 13}
            
       sipPortFeedingStatusValidity    OBJECT-TYPE
            SYNTAX     INTEGER
            ACCESS     read-only
            STATUS     mandatory
            DESCRIPTION "bitmap to show the validity for items from sipPortAdminStatus to sipPortLongitudinalCurrent
            ALCATEL-LUCENT NOTE:
            ACCESS:    READ-ONLY
            USAGE:     NA
            PERSIST:   NO
            INSRVMOD:  NA
            RANGE:     NA
            DEFVALUE:  0 
            UNITS:     NA
            SPARSE:    NO"
            ::= { sipPortStateEntry 14}

--===================================================================
--Network Redundancy State Table
--===================================================================
		netwRedunStateTable OBJECT-TYPE
			SYNTAX SEQUENCE OF NetwRedunStateEntry
			ACCESS not-accessible
			STATUS deprecated
			DESCRIPTION
			"The Network Redundancy State Table provides an overview of the redundancy state perceived by a 
			Sip User agent instance for a particular VSP.
			Actually the system supports only 1 VSP. 
			
                        7302/7330 ISAM FTTN : Deprecated
                        7363 MX : Deprecated
			7367 SX : Deprecated

			ALCATEL NOTE: 
			SUPPORT:  DEPRECATED
			TABLESIZE:  DEP [Max number of slot positions in the shelf]
			"
		::= { sipMIB 36}

		netwRedunStateEntry OBJECT-TYPE
			SYNTAX NetwRedunStateEntry
			ACCESS not-accessible
			STATUS deprecated
			DESCRIPTION
			" An entry in the Network Redundancy State Table." 
				INDEX {netwRedunStateSlotId, netwRedunStateAdminDomName }
		::= { netwRedunStateTable 1 }

                
		NetwRedunStateEntry ::=
			SEQUENCE { 
			netwRedunStateSlotId				INTEGER,	
			netwRedunStateAdminDomName		OCTET STRING,		
			netwRedunState					INTEGER
			                		}

		netwRedunStateSlotId OBJECT-TYPE
			SYNTAX	INTEGER (1..65535)
			ACCESS  read-only
			STATUS deprecated
			DESCRIPTION
			" The slot ID of the voice LT board for which the network redundancy state is shown.
			ALCATEL-LUCENT NOTE:
			ACCESS:	 READ-ONLY
			USAGE:	NA
			PERSIST:	NO
			INSRVMOD: NA
			RANGE: 	(1..65535)
			DEFVALUE: 	NA
			UNITS:	NA
			SPARSE:	NO
			"					
		::= { netwRedunStateEntry 1 }

		netwRedunStateAdminDomName OBJECT-TYPE
			SYNTAX OCTET STRING (SIZE (0..32))
			ACCESS read-only
			STATUS deprecated
			DESCRIPTION
			" The name of the administrative domain that hosts the redundancy group. 
			The administrative domain is VSP's domain actually.
			ALCATEL-LUCENT NOTE:
			ACCESS:	READ-ONLY
			USAGE:	NA		
			PERSIST:	YES
			INSRVMOD: NO
			RANGE:	SIZE (0..32))
			DEFVALUE: 	null
			UNITS:	NA	
			SPARSE:	NO
			"				
		::= { netwRedunStateEntry 2 }

		netwRedunState OBJECT-TYPE
			SYNTAX INTEGER
			{	
			connected-to-primary (1),
			connected-to-geo-back-up (2),
			connected-to-sos-back-up (3),
			sip-server-fail-over-ongoing (4),
			sip-server-fail-back-ongoing (5),
			geo-fail-over-ongoing (6),
			geo-fail-back-ongoing (7),
			sos-fail-over-ongoing (8),
			sos-fail-back-ongoing (9),
			deliberate-update-ongoing (10)
			}
			ACCESS read-only
			STATUS deprecated
			DESCRIPTION
			"The Redundancy state as perceived by the SIP User Agent Instance for a particular VSP or VAG
			ALCATEL-LUCENT NOTE:
			ACCESS:	READ-ONLY
			USAGE:	NA		
			PERSIST:	YES
			INSRVMOD: NO
			RANGE:	SIZE (1..10)
			DEFVALUE: 	NA
			UNITS:	NA	
			SPARSE:	NO
			"			                				
		::= { netwRedunStateEntry 3 }

                
--===================================================================
--Network Redundancy Table
--===================================================================                
		netwRedunTable OBJECT-TYPE
			SYNTAX SEQUENCE OF NetwRedunEntry
			ACCESS not-accessible
			STATUS mandatory
			DESCRIPTION
			"The netwRedunTable allowing to configure the network redundancy characteristics for a Service Gateway.  
            The MIB definition is based on the firm believe that both, the DNS server and the SIP first hop 
            are located in the same administrative domain i.e. either both the DNS server and the SIP first hop
            are located in the Service Gateway domain.

            An entry is auto-created upon the creation of an entry in the sipVSPTable.
            An entry is auto-deleted upon the deletion of an entry in the sipVSPTable.
                            
            The netwRedunTable may contain up to 17 entries.

            7302/7330 ISAM FTTN : Supported
            7363 MX : Supported
	    7367 SX : Supported
			
			ALCATEL NOTE: 
			SUPPORT:  YES
			TABLESIZE:  17
			"
		::= { sipMIB 37}

		netwRedunEntry OBJECT-TYPE
			SYNTAX NetwRedunEntry
			ACCESS not-accessible
			STATUS mandatory
			DESCRIPTION
			" An entry in the Network redundancy Table. "
			INDEX { netwRedunAdminDomName }
		::= { netwRedunTable 1 }

		NetwRedunEntry ::=
			SEQUENCE { 
			netwRedunAdminDomName		OCTET STRING,
			netwRedunRowStatus			RowStatus,			
			netwRedundancy				INTEGER,					
			netwRedunDNSPurge			INTEGER,
			netwRedunDNSInitRetransIntv		INTEGER,
			netwRedunDNSMaxNbrRetrans		INTEGER,
			netwRedunFGMonitorMethod		INTEGER,
			netwRedunFGMonitorIntv			INTEGER,
			netwRedunBGMonitorMethod		INTEGER,
			netwRedunBGMonitorIntv			INTEGER,
			netwRedunStableObsPeriod		INTEGER,
			netwRedunFOHysteresis			INTEGER,
			netwRedunDelUpdThreshold		INTEGER,
			netwRedunAutoSipServerFO		INTEGER,
			netwRedunAutoSipServerFB		INTEGER,
			netwRedunAutoSosFO			INTEGER,
			netwRedunAutoSosFB			INTEGER,
			netwRedunRetryAfterThreshold		INTEGER,
			netwRedunOPTIONSMaxForward	INTEGER,
			netwDNSRedunMode			INTEGER
			}

		netwRedunAdminDomName OBJECT-TYPE
			SYNTAX OCTET STRING (SIZE (0..32))
			ACCESS read-only
			STATUS mandatory	
			DESCRIPTION
			"The name of the parent Service Gateway. 
			ALCATEL-LUCENT NOTE:
			ACCESS:	READ-ONLY
			USAGE:	MANDATORY		
			PERSIST:	YES
			INSRVMOD: NO
			RANGE:	SIZE (0..32)
			DEFVALUE: 	NA
			UNITS:	NA	
			SPARSE:	NO
			"				
		::= { netwRedunEntry 1 }

		netwRedunRowStatus OBJECT-TYPE
			SYNTAX RowStatus
			ACCESS read-write
			STATUS mandatory
			DESCRIPTION
			"The row status state of this conceptual row.
			ALCATEL-LUCENT NOTE:
			ACCESS:	READ-WRITE
			USAGE:	MAND		
			PERSIST:	NO
			INSRVMOD: YES
			RANGE:	1	-- active (1)
			DEFVALUE: 	NA
			UNITS:	NA	
			SPARSE:	NO
			"
		::= { netwRedunEntry 2 }

		netwRedundancy OBJECT-TYPE
			SYNTAX INTEGER
			{
			enable (1),
			disable (2)
			}
			ACCESS read-write
			STATUS mandatory
			DESCRIPTION
			"This object allows the administrator to define whether the Service Gateway supports redundancy or not
			ALCATEL-LUCENT NOTE:
			ACCESS:	READ-WRITE
			USAGE:	OPT		
			PERSIST:	YES
			INSRVMOD: NO
			RANGE:	1 | 2 
			DEFVALUE: 	2
			UNITS:	NA	
			SPARSE:	NO
			"
		::= { netwRedunEntry 3 }

		netwRedunDNSPurge OBJECT-TYPE
			SYNTAX INTEGER (0..86400)
			ACCESS read-write
			STATUS mandatory
			DESCRIPTION
			"The DNS purge timer.
				When netwRedunDNSPurge is set to value <> 0 :
			RR caching time = MIN [ DNS purge timer; MINTTL ]
			MINTTL = MIN {[TTL NAPTR]*; [TTL SRV]*; [TTL A]*}
			When netwRedunDNSPurge is set to value = 0 :
			RR caching time =  MINTTL
			MINTTL = MIN {[TTL NAPTR]*; [TTL SRV]*; [TTL A]*}
			
			ALCATEL-LUCENT NOTE:
			ACCESS:	READ-WRITE
			USAGE:	OPT		
			PERSIST:	YES
			INSRVMOD: YES
			RANGE:	(0..86400) 
			DEFVALUE: 	86400
			UNITS:	Second	
			SPARSE:	NO
			"
		::= { netwRedunEntry 4 }

		netwRedunDNSInitRetransIntv OBJECT-TYPE
			SYNTAX INTEGER (200..1000)
			ACCESS read-write
			STATUS mandatory
			DESCRIPTION
			"The initial DNS query retransmission interval.
			By initial DNS query retransmission interval is meant, the initial retransmission time for a DNS Query, while the maximum time specifies the total time period during which a DNS query should be re-attempted before finally the decision is taken that the DNS server cannot be reached.  The system doubles the retransmission timer value for each subsequent retransmission. If the total elapse time between the time the initial query was sent to this DNS server and the time the next retry is going to be sent to the same DNS Server, is less than the configured maximum retransmission period, then the system will still retransmits the DNS query to the DNS server. Otherwise the the DNS query shall be repeated at the next DNS server in the DNS server pool.
			ALCATEL-LUCENT NOTE:
			ACCESS:	READ-WRITE
			USAGE:	OPT		
			PERSIST:	YES
			INSRVMOD: YES
			RANGE:	(200..1000) 
			DEFVALUE: 	500
			UNITS:	Milli-Second	
			SPARSE:	NO
			"
		::= { netwRedunEntry 5 }

		netwRedunDNSMaxNbrRetrans OBJECT-TYPE
			SYNTAX INTEGER (0..4)
			ACCESS read-write
			STATUS mandatory
			DESCRIPTION
			"The maximum number of DNS query retransmissions to the same DNS server in case of no response 
			The retransmission algorithm is based on an initial transmission of the query and a number of 
			retransmissions. 
			This parameter defines the number of retransmissions
			ALCATEL-LUCENT NOTE:
			ACCESS:	READ-WRITE
			USAGE:	OPT		
			PERSIST:	YES
			INSRVMOD: YES
			RANGE:	(0..4) 
			DEFVALUE: 	2
			UNITS:	NA	
			SPARSE:	NO
			"
		::= { netwRedunEntry 6 }

		netwRedunFGMonitorMethod OBJECT-TYPE
			SYNTAX INTEGER
			{
			register-method (1),
			options-method (2),
			passive-heartbeat (3)
					}
			ACCESS read-write
			STATUS mandatory
			DESCRIPTION
			"The Foreground healthy monitoring method.
			The Foreground healthy monitoring is used to check the connection with the server which has some termination registered.
			If passive-heartbeat is configured, system will monitor SIP First Hop Server without sending OPTIONS/RE-REGISTER request periodically. If there's no request/response received from SIP First Hop Server during a period time, it will notify the system the SIP First Hop Server is not available, and then perform initial register or fail over based on restoration setting.
			ALCATEL-LUCENT NOTE:
			ACCESS:	READ-WRITE
			USAGE:	OPT		
			PERSIST:	YES
			INSRVMOD: NO
			RANGE:	1|2|3
			DEFVALUE: 	1
			UNITS:	NA	
			SPARSE:	NO
			"
		::= { netwRedunEntry 7 }

		netwRedunFGMonitorIntv OBJECT-TYPE
			SYNTAX INTEGER
			ACCESS read-write
			STATUS mandatory
			DESCRIPTION
			"The Foreground healthy monitoring interval.
			When the netwRedunFGMonitorIntv is set to the value 0, it means that the foreground healthy 
			monitoring is disabled.
			ALCATEL-LUCENT NOTE:
			ACCESS:	READ-WRITE
			USAGE:	OPT		
			PERSIST:	YES
			INSRVMOD: YES
			RANGE:	(0,32..3600)
			DEFVALUE: 	90
			UNITS:	Second	
			SPARSE:	NO
			"
		::= { netwRedunEntry 8 }

		netwRedunBGMonitorMethod OBJECT-TYPE
			SYNTAX INTEGER
			{
			options-method (1)
			}
			ACCESS read-write
			STATUS mandatory
			DESCRIPTION
			"The Background healthy monitoring method. Actually, only the OPTIONS method is supported.
			The Background healthy monitoring is used to check the connection with the server which 
			has no termination registered.                
			ALCATEL-LUCENT NOTE:
			ACCESS:	READ-WRITE
			USAGE:	OPT		
			PERSIST:	YES
			INSRVMOD: NO
			RANGE:	1
			DEFVALUE: 	1
			UNITS:	NA	
			SPARSE:	NO
			"
		::= { netwRedunEntry 9 }

		netwRedunBGMonitorIntv OBJECT-TYPE
			SYNTAX INTEGER 
			ACCESS read-write
			STATUS mandatory
			DESCRIPTION
			"The Background healthy monitoring interval.
			When the netwRedunBGMonitorIntv is set to the value 0, it means that the background healthy 
			monitoring is disabled.
			ALCATEL-LUCENT NOTE:
			ACCESS:	READ-WRITE
			USAGE:	OPT		
			PERSIST:	YES
			INSRVMOD: YES
			RANGE:	(0,60..86400)
			DEFVALUE: 	3600
			UNITS:	Second	
			SPARSE:	NO
			"
		::= { netwRedunEntry 10 }

		netwRedunStableObsPeriod OBJECT-TYPE
			SYNTAX INTEGER (0..86400)
				ACCESS read-write
				STATUS mandatory
				DESCRIPTION
			"The SIP server stable observation period. It intends to observe the stability of the SIP first hop once 
			this SIP first hop is back in service after having failed.
			The value 0 means the observed next hop will be back in service immediately                 
			ALCATEL-LUCENT NOTE:
			ACCESS:	READ-WRITE
			USAGE:	OPT		
			PERSIST:	YES
			INSRVMOD: YES
			RANGE:	(0..86400)
			DEFVALUE: 	21600
			UNITS:	Second	
			SPARSE:	NO
			"
		::= { netwRedunEntry 11 }

		netwRedunFOHysteresis OBJECT-TYPE
			SYNTAX INTEGER (0..5)
			ACCESS read-write
			STATUS mandatory
			DESCRIPTION
			"The Fail-Over hysteresis.
			As to avoid unnecessary SIP Server Fail-over actions and as such avoiding any connection toggling
			between SIP first hops, the system shall introduce a configurable Foreground Non-recoverable 
			Hysteresis Threshold. Such concept shall allow the system to distinguish accidental from persistent 
			foreground non-recoverable error conditions. 
			Accidental error conditions are considered to appear seldom and often it is even impossible to find 
			a clear explanation for them. Consequently, such occurrences are considered stand-alone events 
			detected at a single moment in time but disappearing quite fast. It is obvious that such occurrences 
			shall not give rise to a Fail-over action.
			When the netwRedunFOHysteresis is set to the value 0, it means that the Fail-Over hysteresis is 
			disabled.
			ALCATEL-LUCENT NOTE:
			ACCESS:	READ-WRITE
			USAGE:	OPT		
			PERSIST:	YES
			INSRVMOD: YES
			RANGE:	(0..5)
			DEFVALUE: 	0
			UNITS:	Occurrences of error condition 	
			SPARSE:	NO
			"
		::= { netwRedunEntry 12 }

		netwRedunDelUpdThreshold OBJECT-TYPE
			SYNTAX INTEGER (0..86400)
			ACCESS read-write
			STATUS mandatory
			DESCRIPTION
			"The Deliberate Update Threshold. This is the time period by which the graceful deliberate updated must be 
			completed,  knowing that the deliberate update shall be immediately started from the moment the 
			change in the farm of SIP first hops configuration has been notified to the system.
			After this time period, forced deliberate update will be triggered.
			When the netwRedunDelUpdThreshold is set to the value 0, it means that the deliberate update shall be triggered upon the next DNS cache refresh. It shall be completed before the first subsequent DNS cache refresh is to happen.                 
			ALCATEL-LUCENT NOTE:
			ACCESS:	READ-WRITE
			USAGE:	OPT		
			PERSIST:	YES
			INSRVMOD: YES
			RANGE:	(0..86400)
			DEFVALUE: 	0
			UNITS:	Second 	
			SPARSE:	NO
			"
		::= { netwRedunEntry 13 }

		netwRedunAutoSipServerFO OBJECT-TYPE
			SYNTAX INTEGER 
			{
			enable (1),
			disable (2)
			}
			ACCESS read-write
			STATUS mandatory
			DESCRIPTION
			"This object allows to enable/disable autonomous SIP Server Fail-Over. 
			This object takes effect only when netwRedundancy = enabled                 
			 ALCATEL-LUCENT NOTE:
			ACCESS:	READ-WRITE
			USAGE:	OPT		
			PERSIST:	YES
			INSRVMOD: YES
			RANGE:	1|2
			DEFVALUE: 	2
			UNITS:	NA 	
			SPARSE:	NO
			"
		::= { netwRedunEntry 14 }

		netwRedunAutoSipServerFB OBJECT-TYPE
			SYNTAX INTEGER (0..86400)
			ACCESS read-write
			STATUS mandatory
			DESCRIPTION
			"This object allows to enable/disable autonomous SIP Server Fail-Back. 
			When netwREdunAutoSipServerFB is set to the value0, it means that SIP server Fail-Back is disabled.
			When netwREdunAutoSipServerFB is set to a value <> 0, it means that SIP server Fail-Back is enabled. 
			The value indicates the time period by which the SIP server Fail-Back must be completed. 
			   			This period is measured from the moment the SIP server Fail-Back is triggered by the system.
			ALCATEL-LUCENT NOTE:
			ACCESS:	READ-WRITE
			USAGE:	OPT		
			PERSIST:	YES
			INSRVMOD: YES
			RANGE:	(0..86400)
			DEFVALUE: 	0
			UNITS:	Second 	
			SPARSE:	NO
			"
		::= { netwRedunEntry 15 }

		netwRedunAutoSosFO OBJECT-TYPE
			SYNTAX INTEGER 
			{
			enable (1),
			disable (2)
			}
			ACCESS read-write
			STATUS mandatory
			DESCRIPTION
			"This object allows to enable/disable autonomous SOS Fail-Over. 
			This object takes effect only when netwRedundancy = enabled                 
			 ALCATEL-LUCENT NOTE:
			ACCESS:	READ-WRITE
			USAGE:	OPT		
			PERSIST:	YES
			INSRVMOD: YES
			RANGE:	1|2
			DEFVALUE: 	2
			UNITS:	NA 	
			SPARSE:	NO
			"
		::= { netwRedunEntry 16 }

		netwRedunAutoSosFB OBJECT-TYPE
			SYNTAX INTEGER (0..86400)
			ACCESS read-write
			STATUS mandatory
			DESCRIPTION
			"This object allows to enable/disable autonomous SOS Fail-Back. 
			When netwREdunAutoSOSFB is set to the value0, it means that SOS Fail-Back is disabled.
			When netwREdunAutoSOSFB is set to a value <> 0, it means that SOS Fail-Back is enabled. 
			The value indicates the time period by which the SOS Fail-Back must be completed. 
			                  		This period is measured from the moment the SOS Fail-Back is triggered by the system.
			ALCATEL-LUCENT NOTE:
			ACCESS:	READ-WRITE
			USAGE:	OPT		
			PERSIST:	YES
			INSRVMOD: YES
			RANGE:	(0..86400)
			DEFVALUE: 	0
			UNITS:	Second 	
			SPARSE:	NO
			"
		::= { netwRedunEntry 17 }

		netwRedunRetryAfterThreshold OBJECT-TYPE
			SYNTAX INTEGER (0..30000)
			ACCESS read-write
			STATUS mandatory
			DESCRIPTION
			"retry-after threshold, 
			e.g. with Retry-After header : Restoration action : Attempt a new initial registration for this SIP termination to the same SIP server upon the expiry of the retry-after timer, 
			Should the retry-after timer value exceed retry-after  threshold, then a SIP server Fail-over must triggered for this SIP termination.
			ALCATEL-LUCENT NOTE:
			ACCESS:	READ-WRITE
			USAGE:	OPT		
			PERSIST:	YES
			INSRVMOD: YES
			RANGE:	(0..30000)
			DEFVALUE: 	0
			UNITS:	Milli-Second 	
			SPARSE:	NO
			"
		::= { netwRedunEntry 18 }    

		netwRedunOPTIONSMaxForward OBJECT-TYPE
			SYNTAX INTEGER (0..1)
			ACCESS read-write
			STATUS mandatory
			DESCRIPTION 
			" Max-forwarding is used to configure max-forward attribute for the forwarding property of the SIP OPTIONS message.
			Value - 0: Must not forward this OPTIONS 
			Value - 1: Allow to forward once
			ALCATEL-LUCENT NOTE:
			ACCESS:	READ-WRITE
			USAGE:	OPT		
			PERSIST:	YES
			INSRVMOD: YES
			RANGE:	0|1
			DEFVALUE: 	0
			UNITS:	NA 	
			SPARSE:	NO
			"
		::= { netwRedunEntry 19 }

		netwDNSRedunMode OBJECT-TYPE
			SYNTAX INTEGER
			{
			dns-redun-primary (1),
			dns-redun-at-successful (2)
			}
			ACCESS read-write
			STATUS mandatory
			DESCRIPTION 
			" The object specifies the used DNS selection algorithm. 
			Following two algorithms are supported: 
			dns-redun-primary (1) : always start at the Primary. Send DNS requests always first to the Primary 
			DNS server even if it did not successfully respond to the previous request. 
			dns-redun-at-successful (2)  : stay at the successful. Send DNS requests to the DNS server where the 
			previous requests were successfully answered. It will only failover/failback if the successful DNS server fails.
			ALCATEL-LUCENT NOTE:
			ACCESS:	READ-WRITE
			USAGE:	OPT		
			PERSIST:	YES
			INSRVMOD: NO
			RANGE:	1|2
			DEFVALUE: 	dns-redun-primary(1)
			UNITS:	NA 	
			SPARSE:	NO
			"
		::= { netwRedunEntry 20 }


--===================================================================
--Network RedundancyState New Table
--===================================================================
			netwRedunStateNewTable OBJECT-TYPE
			SYNTAX SEQUENCE OF NetwRedunStateNewEntry
			ACCESS not-accessible
			STATUS mandatory
			DESCRIPTION
			"The Network Redundancy State New Table provides an overview of the redundancy state perceived  by a 
            Sip User agent instance for a particular Service Gateway.

            7302/7330 ISAM FTTN : Supported
            7363 MX : Supported
	    7367 SX : Supported
			
			ALCATEL NOTE:
			SUPPORT:  YES
			TABLESIZE: DEP [LT boards * 72/2(2 sip termination group) * 2 (concurrency old and new = 1296]"
		::= { sipMIB 38}

		netwRedunStateNewEntry OBJECT-TYPE
			SYNTAX NetwRedunStateNewEntry
			ACCESS not-accessible
			STATUS mandatory
			DESCRIPTION
			" An entry in the Network Redundancy State New Table."
			INDEX { netwRedunNewStateSlotId, netwRedunNewStateAdminDomName, netwRedunNewStateSipTg}
		::= { netwRedunStateNewTable 1 }

		NetwRedunStateNewEntry ::=
			SEQUENCE {
			netwRedunNewStateSlotId				INTEGER,
			netwRedunNewStateAdminDomName		OCTET STRING,
			netwRedunNewStateSipTg				INTEGER,
			netwRedunNewState				INTEGER,
			netwRedunNewStateSipFirstHop			InetAddress
		}

		netwRedunNewStateSlotId OBJECT-TYPE
			SYNTAX  INTEGER (1..65535)
			ACCESS read-only 
			STATUS mandatory
			DESCRIPTION
			" The unique identifier of the slot position of the voice LT board.
			ALCATEL-LUCENT NOTE:
			ACCESS: READ-ONLY	
			USAGE:	NA
			PERSIST:	NO
			INSRVMOD:	NA
			RANGE:	(1..65535)
			DEFVALUE:	NA
			UNITS:	NA
			SPARSE:	NO
			"
		::= { netwRedunStateNewEntry 1 }

		netwRedunNewStateAdminDomName OBJECT-TYPE
			SYNTAX OCTET STRING (SIZE (0..32))
			ACCESS read-only 
			STATUS mandatory
			DESCRIPTION
			"The name of the parent Service Gateway. 
			ALCATEL-LUCENT NOTE:
			ACCESS: READ-ONLY	
			USAGE:	NA
			PERSIST:	NO
			INSRVMOD: NO
			RANGE: 	SIZE (0..32)
			DEFVALUE: 	NA
			UNITS:	NA
			SPARSE: 	NO
			"
		::= { netwRedunStateNewEntry 2 }

		netwRedunNewStateSipTg OBJECT-TYPE
			SYNTAX INTEGER
			ACCESS read-only 
			STATUS mandatory
			DESCRIPTION 
			"The SIP Termination Group this SIP termination actually belongs to.
			ALCATEL-LUCENT NOTE:
			ACCESS: READ-ONLY	
			USAGE:	NA
			PERSIST:	NO
			INSRVMOD:	NA
			RANGE:	0...72
			DEFVALUE:	NA
			UNITS:	NA
			SPARSE:	NO
			"
		::= { netwRedunStateNewEntry 3 }

		netwRedunNewState OBJECT-TYPE
			SYNTAX INTEGER
			{
			connected-to-primary (1),
			connected-to-geo-back-up (2),
			connected-to-sos-back-up (3),
			sip-server-fail-over-ongoing (4),
			sip-server-fail-back-ongoing (5),
			geo-fail-over-ongoing (6),
			geo-fail-back-ongoing (7),
			sos-fail-over-ongoing (8),
			sos-fail-back-ongoing (9),
			deliberate-update-ongoing (10),
			deliberate-update-ongoing-Bu (11),
			sip-server-fail-over-ongoing-Bu (12),
			sip-server-fail-back-ongoing-Bu (13)
			}
			ACCESS read-only
			STATUS mandatory
			DESCRIPTION
			"The Redundancy state as perceived by the SIP User Agent Instance for a particular Service Gateway.
			ALCATEL-LUCENT NOTE:
			ACCESS:	READ-ONLY
			USAGE:	NA
			PERSIST:	NO
			INSRVMOD:	NA
			RANGE:	(1...13)
			DEFVALUE:	NA
			UNITS:	NA
			SPARSE:	NO
			"
		::= { netwRedunStateNewEntry 4 }

		netwRedunNewStateSipFirstHop OBJECT-TYPE
			SYNTAX InetAddress
			ACCESS read-only
			STATUS mandatory
			DESCRIPTION 
			"This object returns either the IP@ or the FQDN of the First Hop SIP server currently in use by the SIP Termination Group. 
            Whether an IP@ or FQDN is going to be displayed depends on the mode been applied to configure the SIP Server Table and the DNS 
            zone file tree structure uploaded to the DNS server. 
            In case the IP@ mode is applied then an IP@ is going to be displayed. 
            In case the configuration mode is FQDN with 1:1 mapping between FQDN and A record, the system shows the FQDN. 
            In case the configuration mode is FQDN with 1:N mapping between FQDN and A record, the system shows the currently used IP@.

            An FQDN being displayed has only relevance and can only uniquely define a SIP First Hop server on the condition that the Domain Name 
            service being deployed in the customer's network offers a 1:1 mapping between FQDN and A Resource Record. 
            Ahould the DN / FQDN mode been applied to configure the SIP Server Table and should the Domain Name Service being deployed in 
            the customer's network offer a 1:N mapping between FQDN and A Resource Record, then this object will return an IP@. 
            Due to the 1:N mapping between FQDN and A resource Record, an FQDN value will not uniquely identify the SIP First Hop server actually 
            being in use by a SIP termination Group.

			Following content is seen possible :
			When object netwRedunNewState set to connected-to-primary(1): the first hop SIP server actually in use by the SIP TG at the GEO primary site.
			When object netwRedunNewState set to connected-to-geo-back-up(2):the first hop SIP server actually in use 
			by the SIP TG at the GEO back-up site.
			When object netwRedunNewState set to connected-to-sos-back-up(3) : the SOS first hop SIP server actually in use by the SIP TG at the SOS back-up site.
			When object netwRedunNewState set to sip-server-fail-over-ongoing(4) : the first hop SIP server actually in use by the SIP TG at the GEO primary site.
			When object netwRedunNewState set to sip-server-fail-back-ongoing(5) : the first hop SIP server actually in use by the SIP TG at the GEO primary site.
			When object netwRedunNewState set to geo-fail-over-ongoing(6): the first hop SIP server actually in use by the SIP TG at the GEO primary site.
			When object netwRedunNewState set to geo-fail-back-ongoing(7) ; the first hop SIP server actually in use by the SIP TG at the GEO back-up site.
			When object netwRedunNewState set to sos-fail-over-ongoing(8) : the first hop SIP server actually in use by the SIP TG at the GEO primary site.
			When object netwRedunNewState set to sos-fail-back-ongoing(9) : the SOS first hop SIP server actually in use by the SIP TG at the SOS Back-up site
			When object netwRedunNewState set to deliberate-update-ongoing(10) : the first hop SIP server actually in use by the SIP TG at the GEO primary site.
			When object netwRedunNewState set to deliberate-update-ongoing-Bu(11) : the first hop SIP server actually in use by the SIP TG at the GEO back-up site.
			When object netwRedunNewState set to sip-server-fail-over-ongoing-Bu(12) : the first hop SIP server actually in use by the SIP TG at the GEO back-up site.
			When object netwRedunNewState set to sip-server-fail-back-ongoing-Bu(13) : the first hop SIP server actually in use by the SIP TG at the GEO back-up site.
			e.g.
			SIP server fail-over ongoing at GEO primary site; sip server 1 -> sip server 2; SIP TG X (ss 1) ; SIP TG Y (ss 2)
			Show :
			SIP Tg X; netwRedunNewState = sip-server-fail-over-ongoing (4); netwRedunSipFirstHop = SS1
			SIP Tg Y; netwRedunNewState = connected-to-primary (1); netwRedunSipFirstHop = SS2
			
			SIP server fail-over ongoing at GEO back-up site; sip server 3 -> sip server 4; SIP TG X (ss 3) ; SIP TG Y (ss 4)
			Show :
			SIP Tg X; netwRedunNewState = sip-server-fail-over-ongoing-Bu (12); netwRedunSipFirstHop = SS3
			SIP Tg Y; netwRedunNewState = connected-to-geo-back-up (2); netwRedunSipFirstHop = SS4
			
			Geo Fail-over ongoing; Geo primary site / sip server 1 / SIP TG X (ss1); Geo back-up site / sip server 3 / SIP TG Y (ss3)
			Show :
			SIP Tg X; netwRedunNewState = geo-fail-over-ongoing (6); netwRedunSipFirstHop = SS1
			SIP Tg Y; netwRedunNewState = connected-to-geo-back-up (2); netwRedunSipFirstHop = SS3
			
			SOS fail-back ongoing: SOS back-up site / sip server 6 / SIP TG A (ss6); Geo primary site / sip server 1 / SIP TG X (ss1)
			Show :
			SIP Tg A; netwRedunNewState = sos-fail-back-ongoing (9); netwRedunSipFirstHop = SS6
			SIP Tg X; netwRedunNewState = connected-to-primary (1); netwRedunSipFirstHop = SS1
			
			ALCATEL-LUCENT NOTE:
			ACCESS:          READ-ONLY
			USAGE:            NA
			PERSIST:         NA
			INSRVMOD:      NA
			RANGE:            NA
			DEFVALUE:      NA
			UNITS:  NA
			SPARSE:          NO
			"
		::= { netwRedunStateNewEntry 5 }

-- =============================================================================
-- NEXT FREE SIP VSP ID 
-- =============================================================================
        sipVSPIdNext OBJECT-TYPE
            SYNTAX INTEGER
            ACCESS read-only
            STATUS mandatory
            DESCRIPTION
                "The next free VSP identifier
                Should a next free VSP identifier be requested while no free VSP identifier is found, the system will return a 
                genErr response.
 
             ALCATEL-LUCENT NOTE:
             ACCESS:     NA
             USAGE:     NA
             PERSIST:        NO
             INSRVMOD:       NA
             RANGE:  (1..17)
             DEFVALUE:  NA
             UNITS:  NA
             SPARSE:    NO
             "
          ::= { sipMIB 39 }

-- ==================================================================
-- SIP PRIMARY RATE ISDN MIB.
-- ==================================================================

-- ==================================================================   
-- SIP PRIMARY RATE ISDN TERMINATION TABLE.
-- ==================================================================
    sipIsdnCasTerminationTable OBJECT-TYPE
        SYNTAX SEQUENCE OF SipIsdnCasTerminationEntry
        ACCESS not-accessible
        STATUS mandatory
        DESCRIPTION
            "The sipIsdnCasTerminationTable allows to create PRA ISDN or R2 CAS SIP Terminations. A PRA ISDN or R2 CAS SIP termination must be associated a sipVSPTable entry. This shall be done through the configuration of the sipIsdnCasTerminationProviderName attribute. (the same name shall be configured as configured in the sipVSPName attribute of the parent sipVSPTable entry).
            7302/7330 ISAM FTTN :   Supported
            7363 MX :               Not supported 
            7367 SX :               Not supported

            ALCATEL NOTE: 
            TABLESIZE: DEP [max slot of one shelf multiply max termination of one board]
            DESCR:NA."
        ::= { sipMIB 40 }

        sipIsdnCasTerminationEntry OBJECT-TYPE
            SYNTAX SipIsdnCasTerminationEntry
            ACCESS not-accessible
            STATUS mandatory
            DESCRIPTION
                "An entry in the sipIsdnCasTerminationTable."
            INDEX { ifIndex }
        ::= { sipIsdnCasTerminationTable  1 }

        SipIsdnCasTerminationEntry ::=
        SEQUENCE {
            sipIsdnCasTerminationGroupDirectoryNumber  OCTET STRING,
            sipIsdnCasTerminationUserName              OCTET STRING,
            sipIsdnCasTerminationUri                   OCTET STRING,
            sipIsdnCasTerminationMD5Realm              OCTET STRING,
            sipIsdnCasTerminationMD5Password           OCTET STRING,
            sipIsdnCasTerminationAdminStatus           INTEGER,
            sipIsdnCasTerminationOperStatus            INTEGER,
            sipIsdnCasTerminationRowStatus             RowStatus,
            sipIsdnCasTermContactUserInfo              OCTET STRING,
            sipIsdnCasTerminationDisplayName           OCTET STRING,
            sipIsdnCasTerminationOpStatDownReason      INTEGER,
            sipIsdnCasTerminationGroup                 INTEGER, 
            sipIsdnCasTerminationSIPServerAddr         InetAddress,
            sipIsdnCasTerminationPaniHeaderLineId      OCTET STRING,
            sipIsdnCasTerminationProviderName          OCTET STRING, 
            sipIsdnCasTerminationNbrBChannelIdle       INTEGER,    
            sipIsdnCasTerminationNbrBChannelUsed       INTEGER,
            sipIsdnCasTerminationPUIDlist              OCTET STRING,
            sipIsdnCasTerminationTestState             INTEGER,
            sipIsdnCasTerminationTestAccessState       INTEGER,
            sipIsdnCasTerminationTestAccessTimeout      INTEGER,
            sipIsdnCasTerminationBusyOverWrite         TruthValue,
            sipIsdnCasTerminationSpecRuleSet           OCTET STRING
        }
            
        sipIsdnCasTerminationGroupDirectoryNumber        OBJECT-TYPE
                SYNTAX OCTET STRING (SIZE (0..32))
                ACCESS read-write
                STATUS mandatory
                DESCRIPTION
                    " The Directory number of this PRA ISDN or R2 CAS SIP termination. 
                    Both, the sipIsdnCasTerminationGroupDirectoryNumber object and the sipIsdnCasTerminationUri object cannot at the same time contain the null string
                    - In case the sipIsdnCasterminationGroupDirectoryNumber is configured with a value <> null string while the sipIsdnCasTerminationUri contains the null string : the register URI is composed by concatenating the configured value of the sipIsdnCasTerminationGroupDirectoryNumber and the register URI 
configured in the sipRegisterTable. 
                    - In case the sipIsdnCasterminationGroupDirectoryNumber contains the null string while the sipIsdnCasTerminationUri is configured with a value <> null string : the register URI equals the configured sipIsdnCasTerminationUri value.
                    ALCATEL-LUCENT NOTE:
                    ACCESS:     READ-WRITE
                    USAGE:      OPT 
                    PERSIST:    YES
                    INSRVMOD:   NO
                    RANGE:      SIZE (0..32)
                    DEFVALUE:   null
                    UNITS:      NA  
                    SPARSE:     NO          
                    "
        ::= { sipIsdnCasTerminationEntry 1 }

        sipIsdnCasTerminationUserName OBJECT-TYPE
            SYNTAX OCTET STRING (SIZE (0..64))
            ACCESS read-write
            STATUS mandatory
            DESCRIPTION
                " The User name of this PRA ISDN or R2 CAS SIP termination. 
                The configured User name must be unique across all entries of the sipIsdnCasTerminationTable. 

                ALCATEL-LUCENT NOTE:
                ACCESS:     READ-WRITE
                USAGE:      OPT
                PERSIST:    YES
                INSRVMOD:   NO
                RANGE:      SIZE (0..64)
                DEFVALUE:   null
                UNITS:      NA  
                SPARSE:     NO          
                "
        ::= { sipIsdnCasTerminationEntry 2 }

        sipIsdnCasTerminationUri OBJECT-TYPE
            SYNTAX OCTET STRING (SIZE (0..80))
            ACCESS read-write
            STATUS mandatory
            DESCRIPTION
                " The SIP URI by which the user agent identifies this PRA ISDN or R2 CAS SIP termination. 
                The configured SIP URI must be unique across all entries of the sipIsdnCasTerminationTable 
                Both, the sipIsdnCasTerminationGroupDirectoryNumber object and the sipIsdnCasTerminationUri object cannot at the same time contain the null string. 
                - In case the sipIsdnCasterminationGroupDirectoryNumber is configured with a value <> null string while the sipIsdnCasTerminationUri contains the null string : the register URI is composed by concatenating the configured value of the sipIsdnCasTerminationGroupDirectoryNumber and the register URI 
configured in the sipRegisterTable. 
                - In case the sipIsdnCasterminationGroupDirectoryNumber contains the null string while the sipIsdnCasTerminationUri is configured with a value <> null string : the register URI equals the configured sipIsdnCasTerminationUri value. 

                ALCATEL-LUCENT NOTE:
                ACCESS:     READ-WRITE
                USAGE:      OPT
                PERSIST:    YES
                INSRVMOD:   NO
                RANGE:      SIZE (0..80)
                DEFVALUE:   null
                UNITS:      NA  
                SPARSE:     NO          
                "
        ::= { sipIsdnCasTerminationEntry 3 }
        
        sipIsdnCasTerminationMD5Realm OBJECT-TYPE
            SYNTAX OCTET STRING (SIZE (0..64))
            ACCESS read-write
            STATUS mandatory
            DESCRIPTION
                "The realm identifier that corresponds to the VSP or VAG domain. 
                
                ALCATEL-LUCENT NOTE:
                ACCESS:     READ-WRITE
                USAGE:      OPT
                PERSIST:    YES
                INSRVMOD:   NO
                RANGE:      SIZE (0..64)
                DEFVALUE:   null
                UNITS:      NA      
                SPARSE:     NO      
                "
        ::= { sipIsdnCasTerminationEntry 4 }
                
        sipIsdnCasTerminationMD5Password OBJECT-TYPE
            SYNTAX OCTET STRING (SIZE (0..64))
            ACCESS read-write
            STATUS mandatory
            DESCRIPTION
                "The MD5 password assigned to the PRA ISDN or R2 CAS SIP termination. 
                As the MD5 password is encrypted by the system, it is displayed as the '******' string by the CLI/SNMP management interface.
                The encryption is based on DES-CBC algorithm. 

                ALCATEL-LUCENT NOTE:
                ACCESS:     READ-WRITE
                USAGE:      OPT
                PERSIST:    YES
                INSRVMOD:   NO
                RANGE:      SIZE (0..64)
                DEFVALUE:   null
                UNITS:      NA
                SPARSE:     NO              
                "
        ::= { sipIsdnCasTerminationEntry 5 }

        sipIsdnCasTerminationAdminStatus OBJECT-TYPE
            SYNTAX INTEGER
            {
                up(1),
                down(2)
            }
            ACCESS read-write
            STATUS mandatory
            DESCRIPTION
                " The administrative status of this PRA ISDN or R2 CAS SIP termination. 
                When the administrative status of the PRA ISDN or R2 CAS SIP termination is modified from 'up' to 'down', the system will de-register the PRA ISDN or R2 CAS SIP termination and power down the line. 
                Also when the administartive status is 
                UP (1) : the attributes of this entry that are indicated as INSRVMOD=YES can be modified. 
                DOWN (2) : the attributes of this entry that are indicated as INSRVMOD=YES and the attributes that are indicated as INSRVMOD=NO can be modified. Note that the attributes of this entry that are indicated INSRVMOD=NA cannot be modified after creation. 

                ALCATEL-LUCENT NOTE: 
                ACCESS:     READ-WRITE
                USAGE:      OPT
                PERSIST:    YES   
                INSRVMOD:   YES
                RANGE:      1 | 2 
                DEFVALUE:   down  
                UNITS:      NA      
                SPARSE:     NO      
                "     
        ::= { sipIsdnCasTerminationEntry 6 }

        sipIsdnCasTerminationOperStatus OBJECT-TYPE
            SYNTAX INTEGER
            {
                up(1),
                down(2)
            }
            ACCESS read-only
            STATUS mandatory
            DESCRIPTION
                " The operational status of this PRA ISDN or R2 CAS SIP termination. 
                For PRA ISDN SIP Termination:
                up(1) : The PRA ISDN SIP Termination is registered to the IMS core and both, the ISDN layer 1 and the ISDN layer 2 are up. 
                down(2) : The PRA ISDN SIP termination's operational status can be down because of one of the following reasons : 
                - The PRA ISDN SIP Termination's registration to the IMS core is in progress. 
                - The PRA ISDN SIP Termination's registration to the IMS core has failed. 
                - The PRA ISDN SIP Termination is registered to the IMS core but the ISDN Layer1 is down. 
                - The PRA ISDN SIP Termination is registered to the IMS core and the ISDN Layer1 is up, but ISDN Layer2 is down. 
                For R2 CAS SIP Termination:
                up(1) : The R2 CAS SIP Termination is registered to the IMS core and the CAS layer 1 is up. 
                down(2) : The R2 CAS SIP termination's operational status can be down because of one of the following reasons : 
                - The R2 CAS SIP Termination's registration to the IMS core is in progress. 
                - The R2 CAS SIP Termination's registration to the IMS core has failed. 
                - The R2 CAS SIP Termination is registered to the IMS core but the CAS Layer1 is down. 
                The operational status down reason is displayed via the sipIsdnCasTerminationOpStatDownReason object. 

                ALCATEL-LUCENT NOTE:
                ACCESS:     READ-ONLY
                USAGE:      NA
                PERSIST:    NO
                INSRVMOD:   NA
                RANGE:      1 | 2
                DEFVALUE:   NA
                UNITS:      NA
                SPARSE:     NO
                "
        ::= { sipIsdnCasTerminationEntry 7 }

        sipIsdnCasTerminationRowStatus OBJECT-TYPE
            SYNTAX RowStatus
            ACCESS read-write
            STATUS mandatory
            DESCRIPTION
                "The status of this conceptual row.
                The RowStatus TC requires that this DESCRIPTION clause states under which circumstances other objects in this row can be modified. 
                The value of this object has no effect on whether other objects in this conceptual row can be modified.
                A conceptual row can always be made active.

                ALCATEL-LUCENT NOTE:
                ACCESS:     READ-WRITE
                USAGE:      MAND
                PERSIST:    NO
                INSRVMOD:   YES
                RANGE:      1 | 4 | 6   -- active (1), createAndGo (4), destroy (6)
                DEFVALUE:   NA
                UNITS:      NA
                SPARSE:     NO
                "
        ::= { sipIsdnCasTerminationEntry 8 }

        sipIsdnCasTermContactUserInfo OBJECT-TYPE
            SYNTAX OCTET STRING (SIZE (1..128))
            ACCESS read-only
            STATUS mandatory
            DESCRIPTION
                "The user-info of contact field in SIP message associated with the user
                When the sipLineIdSyntaxPattern is configured as 'terminationUriOrDN (1)' and sipIsdnCasTerminationUri is NOT empty, then
                this object contains the user part of sipIsdnCasTerminationUri as the user info; if sipIsdnCasTerminationUri
                doesn't contain a '@', then this object contains the user part of sipIsdnCasTerminationDN as the user info.
                When the sipLineIdSyntaxPattern is configured as 'terminationUriOrDN (1)' and sipIsdnCasTerminationUri is EMPTY, then this
                object contains the user part of sipIsdnCasTerminationDN as the user info.
                When the sipLineIdSyntaxPattern is configured as 'PhysicalLineId (2)', then this object contains the physical lineId as the user info.
                When the LT Board is not present Physically, then this object is empty.

                ALCATEL-LUCENT NOTE:
                ACCESS:     READ-ONLY
                USAGE:      NA
                PERSIST:    NO
                INSRVMOD:   NA
                RANGE:      SIZE (1..128)
                DEFVALUE:   NA
                UNITS:      NA
                SPARSE:     NO
                "
        ::= { sipIsdnCasTerminationEntry 9 }

        sipIsdnCasTerminationDisplayName OBJECT-TYPE
            SYNTAX OCTET STRING (SIZE (0..64))
            ACCESS read-write
            STATUS mandatory
            DESCRIPTION
                "The Display name of this PRA ISDN or R2 CAS SIP termination

                ALCATEL-LUCENT NOTE:
                ACCESS:     READ-WRITE
                USAGE:      OPT
                PERSIST:    YES
                INSRVMOD:   NO
                RANGE:      SIZE (0..64)
                DEFVALUE:   null
                UNITS:      NA
                SPARSE:     NO
                "
        ::= { sipIsdnCasTerminationEntry 10 }

        sipIsdnCasTerminationOpStatDownReason OBJECT-TYPE
            SYNTAX INTEGER
            {
                none(0),
                registering(1),
                registrationFailure(2),
                l1Inactive(3),
                l2Inactive(4)
            }
            ACCESS read-only
            STATUS mandatory
            DESCRIPTION
                " The Operational status Down Reason of this PRA ISDN or R2 CAS SIP termination. 
                For PRA ISDN SIP termination:
                - none(0) : The operational status of the PRA ISDN SIP termination is UP 
                - registering(1) : The PRA ISDN SIP Termination's registration to the IMS core is in progress. 
                - registrationFailure(2) : The PRA ISDN SIP Termination's registration to the IMS core has failed. 
                - L1Inactive(3) : The PRA ISDN SIP Termination is registered to the IMS core but the ISDN Layer1 is down. 
                - L2Inactive(4) : The PRA ISDN SIP Termination is registered to the IMS core and the ISDN Layer1 is up, but ISDN Layer2 is down. 
                For R2 CAS SIP termination:
                - none(0) : The operational status of the R2 CAS SIP termination is UP 
                - registering(1) : The R2 CAS SIP Termination's registration to the IMS core is in progress. 
                - registrationFailure(2) : The CAS SIP Termination's registration to the IMS core has failed. 
                - L1Inactive(3) : The CAS SIP Termination is registered to the IMS core but the CAS Layer1 is down. 
                - L2Inactive(4) : NOT AVAILABLE. This down reason is only available for PRA ISDN SIP termination. 

                ALCATEL-LUCENT NOTE:
                ACCESS:     READ-WRITE
                USAGE:      NA
                PERSIST:    NO
                INSRVMOD:   NA
                RANGE:      0 |1 | 2 | 3 | 4
                DEFVALUE:   NA
                UNITS:      NA
                SPARSE:     NO
                "
        ::= { sipIsdnCasTerminationEntry 11 }

        sipIsdnCasTerminationGroup OBJECT-TYPE
            SYNTAX INTEGER
            ACCESS read-only
            STATUS mandatory
            DESCRIPTION  
                "The SIP Termination Group to which this PRA ISDN or R2 CAS SIP termination belongs to. 
                - Should the SIP Restoration feature be enabled then this object may be set to a value in the range 0..8 whereby a value 0 means that the PRA ISDN or R2 CAS SIP termination has not been assigned yet to a SIP Termination Group. (not successfully registered yet) 
                - Should the SIP Restoration feature be disabled then this object shall be set to the value 0 whereby a value 0 means that the SIP Termination Group approach doesn't apply. 

                ALCATEL-LUCENT NOTE:
                ACCESS:     READ-WRITE
                USAGE:      NA  
                PERSIST:    NO
                INSRVMOD:   NA
                RANGE:      0..8
                DEFVALUE:   NA
                UNITS:      NA
                SPARSE:     NO
                "
        ::= { sipIsdnCasTerminationEntry  12 }

        sipIsdnCasTerminationSIPServerAddr OBJECT-TYPE
            SYNTAX InetAddress
            ACCESS read-only
            STATUS mandatory
            DESCRIPTION  
                "This object returns either the IP@ or the FQDN of the First Hop SIP server currently in use by the PRA ISDN or R2 CAS SIP Termination.
                Whether an IP@ or FQDN is going to be displayed depends on the mode been applied to configure the SIP Server Table.
                In case the IP@ mode is applied then an IP@ is going to be displayed. Otherwise, in case the DN / FQDN mode is applied then an FQDN is going to be displayed.
                An FQDN being displayed has only relevance and can only uniquely define a SIP First Hop server on the condition that the Domain Name Service being deployed in the customer's network offers a 1:1 mapping between FQDN and A Resource Record : should the DN / FQDN mode been applied to configure the SIP Server Table and should the Domain Name Service being deployed in the customer's network offer a 1:N mapping between FQDN and A Resource Record, then this object will return an FQDN value. However, due to the 1:N mapping between FQDN and A resource Record, this FQDN value will not uniquely identify the SIP First Hop server actually being in use by a PRA ISDN or R2 CAS SIP termination.
                1) SIP restoration disabled
                ==> this object shall contain the SIP first hop address / FQDN to which all originating SIP requests are addressed.
                ==> this SIP first hop address / FQDN is filled in from the moment the PRA ISDN or R2 CAS SIP termination is successfully registered, otherwise no  value is shown
                2) SIP restoration enabled
                ==> this object shall contain the SIP first hop address / FQDN to which all originating SIP requests are addressed.
                ==> this SIP first hop address / FQDN is filled in from the moment the PRA ISDN or R2 CAS SIP termination is successfully registered i.e. belongs to a PRA ISDN or R2 CAS SIP termination group, otherwise no value is shown.

                ALCATEL-LUCENT NOTE:
                ACCESS:     READ-ONLY
                USAGE:      NA
                PERSIST:    NO
                INSRVMOD:   NA
                RANGE:      NA
                DEFVALUE:   NA
                UNITS:      NA
                SPARSE:     NO
                "
        ::= { sipIsdnCasTerminationEntry 13 }

        sipIsdnCasTerminationPaniHeaderLineId OBJECT-TYPE 
            SYNTAX OCTET STRING (SIZE (0..63))
            ACCESS read-write
            STATUS mandatory
            DESCRIPTION
                " The Line ID of this PRA ISDN or R2 CAS SIP termination. It is contained in the Pani header. 
                The line id configuration is not bounded to any format. It is the responsibility of the customer to define the desired line ID format. 
                There is no restriction on the character set being used to configure the line ID / line ID format. 

                ALCATEL-LUCENT NOTE:
                ACCESS:     READ-WRITE
                USAGE:      OPT
                PERSIST:    YES
                INSRVMOD:   NO
                RANGE:      SIZE (0..63)
                DEFVALUE:   null
                UNITS:      NA
                SPARSE:     NO
                "
        ::= { sipIsdnCasTerminationEntry 14 }


        sipIsdnCasTerminationProviderName OBJECT-TYPE
            SYNTAX OCTET STRING (SIZE (0..32))
            ACCESS read-write
            STATUS mandatory
            DESCRIPTION
                "The name of the parent Service Gateway.

                ALCATEL NOTE:
                ACCESS:     READ-WRITE
                USAGE:      OPT
                PERSIST:    YES
                INSRVMOD:   NO
                RANGE:      SIZE (0..32)
                DEFVALUE:   vsp1
                UNITS:      NA
                SPARSE:     NO
                "
        ::= { sipIsdnCasTerminationEntry 15 }

        sipIsdnCasTerminationNbrBChannelIdle OBJECT-TYPE
            SYNTAX INTEGER(-1..30)
            ACCESS read-only
            STATUS mandatory
            DESCRIPTION
                "The number of idle B-channel for this PRA ISDN or CAS R2 Interface. 
                -1 means that the number of idle B-channel is not applicable. This value is returned when the operational status of this PRA ISDN or R2 CAS SIP termination is down.
                
                ALCATEL NOTE:
                ACCESS:     READ-ONLY
                USAGE:      NA
                PERSIST:    NO
                INSRVMOD:   NA
                RANGE:      (-1..30)
                DEFVALUE:   NA
                UNITS:      NA
                SPARSE:     NO
                "
        ::= { sipIsdnCasTerminationEntry  16 }

        sipIsdnCasTerminationNbrBChannelUsed OBJECT-TYPE
            SYNTAX INTEGER(-1..30)
            ACCESS read-only
            STATUS mandatory
            DESCRIPTION
                "The number of B-channels actually in use for this PRA ISDN or CAS R2 interface. 
                -1 means that the number of used B-channel is not applicable. This value is returned when the operational status of this PRA ISDN or R2 CAS SIP termination is down. 
                With 'in use' state of the B-channel is meant that : 
                - Or a connection attempt (outgoing call) is being made on this B-Channel, 
                - Or an incoming call is in the progress of validation for this B-Channel, 
                - Or a call is active on this B-Channel.

                ALCATEL NOTE:
                ACCESS:     READ-ONLY
                USAGE:      NA
                PERSIST:    NO
                INSRVMOD:   NA
                RANGE:      (-1..30)
                DEFVALUE:   NA
                UNITS:      NA
                SPARSE:     NO
                "
        ::= { sipIsdnCasTerminationEntry  17 }

        sipIsdnCasTerminationPUIDlist OBJECT-TYPE
            SYNTAX OCTET STRING (SIZE (0..2560)) 
            ACCESS read-only
            STATUS mandatory
            DESCRIPTION
                "The implicitly registered AORs for this PRA ISDN or R2 CAS SIP termination. 
                For both, the 3GPP and the ETSI standardized approaches applies i.e. the 200 OK response to the REGISTER request (after a successful authentication challenge), contains a P-Associated-URI (PAU) [RFC3455] header with the list of the SIP URIs or TEL URIs (i.e., phone numbers) that are implicitly registered AORs. 
                In case the size of the list of SIP URIs or TEL URIs in P-Associated-URI exceeds the size of this object, the list copied to this object will be truncated such that it fits the object definition.

                ALCATEL NOTE:
                ACCESS:     READ-ONLY
                USAGE:      NA
                PERSIST:    NO
                INSRVMOD:   NA
                RANGE:      SIZE (0..2560)
                DEFVALUE:   NA
                UNITS:      NA
                SPARSE:     NO
                "
        ::= { sipIsdnCasTerminationEntry  18 }
                
        sipIsdnCasTerminationTestState OBJECT-TYPE
            SYNTAX INTEGER
            {     
                noTesting(1),
                intgLineTesting(2),
                loopBackTesting(3),
                loopBackEnvSet(4)
            }     
            ACCESS read-only
            STATUS mandatory
            DESCRIPTION
                " The test status of this PRA ISDN or R2 CAS SIP termination. 
                For PRA ISDN SIP termination:
                - noTesting(1) - The PRA ISDN SIP termination is not under testing. 
                - intgLineTesting(2) - The PRA ISDN SIP termination is under integrated line testing. 
                - loopBackTesting(3) - The PRA ISDN SIP termination is under local, single or cable loopback testing is running 
                - loopBackEnvSet(4) - The PRA ISDN SIP termination is under remote or payload loop back environment has been configured 
                For R2 CAS SIP termination:
                - noTesting(1) - The R2 CAS SIP termination is not under testing. 
                - intgLineTesting(2) - Not supported actually. 
                - loopBackTesting(3) - Not supported actually 
                - loopBackEnvSet(4) - Not supported actually. 

                ALCATEL-LUCENT NOTE:
                ACCESS:     READ-ONLY
                USAGE:      NA
                PERSIST:    NO
                INSRVMOD:   NA
                RANGE:      1 | 2
                DEFVALUE:   NA
                UNITS:      NA  
                SPARSE:     NO                  
                "
        ::= { sipIsdnCasTerminationEntry 19 }
            
        sipIsdnCasTerminationTestAccessState   OBJECT-TYPE
            SYNTAX    INTEGER
            {
                on (1),
                off (2)
            }
            ACCESS     read-write
            STATUS     mandatory
            DESCRIPTION
                "The configured TestAccessState of a PRA ISDN or R2 CAS SIP termination.
                ON (1) : The line of the PRA ISDN or R2 CAS SIP termination is exclusively reserved to run NBLT. Incoming and outgoing call attempts are blocked for this PRA ISDN or R2 CAS SIP termination for as long as the TestAccessState remains set to 'ON'.
                OFF (2) : The line of the PRA ISDN or R2 CAS SIP termination can handle incoming and outgoing call attempts (On the condition that there is no other reason to block the PRA ISDN or R2 CAS SIP termination e.g. an ongoing NBLT) and can also handle NBLT requests.

                The  actual administrative / operational / test status of the PRA ISDN or R2 CAS SIP termination does not have any influence on the    setting of the TestAccessState, i.e. this object can be changed at any time from the moment the PRA ISDN or R2 CAS SIP termination has been created.

                The receipt of a configuration command to switch the sipIsdnCasTerminationTestAccessState to 'ON(1)':
                1. Only the MIB objects sipIsdnCasTerminationBusyOverWrite and sipIsdnCasTerminationTestAcessTimeout can be included in the configuration command that intends to modify the sipIsdnCasTerminationTestAccessState to the value 'ON (1)'.
                2. Should upon the receipt of the configuration command the sipIsdnCasTerminationTestAccessState value equals 'OFF (2)', then  the sipIsdnCasTerminationTestAccessState is changed to 'ON (1)' and a timer with the default/configured value of sipIsdnCasTerminationTestAcessTimeout is started.
                3. Should upon the receipt of the configuration command the sipIsdnCasTerminationTestAccessState value equals 'ON (1)', then the currently running sipIsdnCasTerminationTestAcessTimeout timer gets aborted and a new timer will be started with the default/newly configured  sipIsdnCasTerminationTestAcessTimeout timer.
                4. Upon the expiry of the sipIsdnCasTerminationTestAcessTimeout timer, the sipIsdnCasTerminationTestAccessState value changes to 'OFF(2)'.
                5. Should upon the expiry of the sipIsdnCasTerminationTestAcessTimeout timer, a NBLT test still be running, the sipIsdnCasTerminationTestAcessTimeout timer is re-started and the ISDN NBLT test continues till completion. The sipIsdnCasTerminationTestAccessState remains set to 'ON' till the restarted timer expiry.

                The receipt of a configuration command to switch the sipIsdnCasTerminationTestAccessState to 'OFF(2)':
                1. No other MIB objects can be included in the configuration command that intends to modify the sipIsdnCasTerminationTestAccessState   to the value 'OFF(2)'.
                2. Should upon the receipt of the configuration command the sipIsdnCasTerminationTestAccessState value equals 'ON (1)' and no NBLT test being running then the sipIsdnCasTerminationTestAccessState is changed to 'OFF (2)' and the running timer gets aborted.
                3. Should upon the receipt of the configuration command the sipIsdnCasTerminationTestAccessState value equals 'ON (1)' and a   NBLT test still being running then the sipIsdnCasTerminationTestAccessState is changed to 'OFF (2)' and the running timer gets aborted. However, incoming and outgoing calls remain blocked till the running NBLT session has completed.
                4. Should upon the receipt of the configuration command the sipIsdnCasTerminationTestAccessState value equals 'OFF (2)', then  the configuration command is ignored.

                The sipIsdnCasTerminationTestAccessState object is not persistent, which means that its value will be reset to the default value upon a board reset.

                ALCATEL-LUCENT NOTE:
                ACCESS:     READ-WRITE
                USAGE:      OPT
                PERSIST:    NO
                INSRVMOD:   YES
                RANGE:      1 | 2
                DEFVALUE:   off (2)
                UNITS:      NA
                SPARSE:     NO
                "
        ::= {sipIsdnCasTerminationEntry 20}

        sipIsdnCasTerminationTestAccessTimeout   OBJECT-TYPE
            SYNTAX    INTEGER
            ACCESS     read-write
            STATUS     mandatory
            DESCRIPTION
                "This sipIsdnCasTerminationTestAccessTimeout object allows to configure the maximum elapse time that the sipIsdnCasTerminationTestAccessState object shall remain set to 'ON (1)'. 

                Upon the expiry of the sipIsdnCasTerminationTestAccessTimeout timer, the system autonomously changes the sipIsdnCasTerminationTestAccessState value to 'OFF (2)'. 

                1) Should upon the sipIsdnCasTerminationTestAccessTimeout timer expiry, still a NBLT session be running, then the sipIsdnCasTerminationTestAcessTimeout timer gets autonomously RESTARTED with the default/latest configured timer value. 
                The sipIsdnCasTerminationTestAccessState remains set to 'ON(1)' till the restarted timer expiry. 

                2) Should a NBLT session be completed prior to the sipIsdnCasTerminationTestAccessTimeout timer expiry, then the 
                sipIsdnCasTerminationTestAccessTimeout timer gets autonomously RESTARTED with the default/latest configured timer value. 
                The sipIsdnCasTerminationTestAccessState remains set to 'ON(1)' till the restarted timer expiry.
                The sipIsdnCasTerminationTestAccessTimeout object can only be configured in the configuration command that intends to modify 
                the sipIsdnCasTerminationTestAccessState to the value 'ON (1)'. 
                The sipIsdnCasTerminationTestAccessTimeout object can be configured in the range [1.. 900] seconds. 
                Should no configuration input be received for the sipIsdnCasTerminationTestAccessTimeout object, the default value (900 sec) 
                gets assumed.
                Upon the recipt of a configuration command to modify the sipIsdnCasTerminationTestAccessState to the value 'ON (1)' while the 
                actual value of the sipIsdnCasTerminationTestAccessState equals 'ON (1)', then the current running sipIsdnCasTerminationTestAccessTimeout 
                timer is aborted, and a new timer with the default /newly configured value for sipIsdnCasTerminationTestAccessTimeout is started.
                This object is not persistent, which means that its value will be reset to the value '0' upon a board reset.
                When the sipIsdnCasTerminationTestAccessState equals 'ON (1)', a read operation for the sipIsdnCasTerminationTestAccessTimeout object will 
                return the time left before the sipIsdnCasTerminationTestAccessTimeout timer expires. 
                When the sipIsdnCasTerminationTestAccessState equals 'OFF(2)', a read operation for the sipIsdnCasTerminationTestAccessTimeout object will 
                return the value '0'.

                ALCATEL-LUCENT NOTE:
                ACCESS:     READ-WRITE
                USAGE:      OPT
                PERSIST:    NO
                INSRVMOD:   YES
                RANGE:      0..900
                DEFVALUE:   900
                UNITS:      Second
                SPARSE:     NO
                "
        ::= {sipIsdnCasTerminationEntry 21}
            
        sipIsdnCasTerminationBusyOverWrite   OBJECT-TYPE
            SYNTAX    TruthValue
            ACCESS     read-write
            STATUS     mandatory
            DESCRIPTION
                "This sipIsdnCasTerminationBusyOverWrite object allows to forcibly turn on the sipIsdnCasTerminationTestAccessState of a PRA ISDN or R2 CAS SIP termination  by dropping all active calls that are ongoing for that PRA ISDN or R2 CAS SIP termination at the moment the configuration command gets received.
                1) Upon the receipt of a configuration command requesting the sipIsdnCasTerminationTestAccessState to be switched to 'ON (1)' and 
                sipIsdnCasTerminationBusyOverWrite set to 'TRUE (1)' : Should there still an active call be ongoing for this PRA ISDN or R2 CAS SIP termination, 
                then this call is forcibly dropped and subsequently, the sipIsdnCasTerminationTestAccessState is switched to 'ON (1)'.

                2) Upon the receipt of a configuration command requesting the sipIsdnCasTerminationTestAccessState to be switched to 'ON (1)' and 
                sipIsdnCasTerminationBusyOverWrite set to 'FALSE (2)' : Should there still an active call be ongoing for this PRA ISDN or R2 CAS SIP termination, 
                then the request to switch on the sipIsdnCasTerminationTestAccessState gets rejected.

                The sipIsdnCasTerminationBusyOverWrite object can only be configured in the configuration command that intends to modify the 
                sipIsdnCasTerminationTestAccessState to the value 'ON (1)'.

                If not specified during the modification of the sipIsdnCasTerminationTestAccessState from 'OFF (2)' to 'ON(1)', the system assumes that 
                the sipIsdnCasTerminationBusyOverWrite object is set to the value 'False (2)' (which is the default value).

                This object is not persistent, which means that its value will be reset to the default value upon a board reset. 

                When the sipIsdnCasTerminationTestAccessState value equals 'ON (1)', a read operation for the sipIsdnCasTerminationBusyOverWrite object will 
                result in the sipIsdnCasTerminationBusyOverWrite value being returned that has been configured/adopted by the system during the 
                last sipIsdnCasTerminationTestAccessState = 'ON(1)' modification request. 

                Otherwise, should the sipIsdnCasTerminationTestAccessState value equals 'OFF (2)' a read operation for the sipIsdnCasTerminationBusyOverWrite 
                object will return the value 'FALSE(2)'.

                ALCATEL-LUCENT NOTE:
                ACCESS:     READ-WRITE
                USAGE:      OPT
                PERSIST:    NO
                INSRVMOD:   YES
                RANGE:      TRUE (1) | FALSE (2)
                DEFVALUE:   FALSE (2)
                UNITS:      NA
                SPARSE:     NO
                "
        ::= {sipIsdnCasTerminationEntry 22}

        sipIsdnCasTerminationSpecRuleSet  OBJECT-TYPE 
              SYNTAX OCTET STRING (SIZE (0..32))
              ACCESS read-write
              STATUS mandatory
              DESCRIPTION
				" Assign  rule(s) for an IsdnCasTtermination. 
				NOKIA NOTE:
				ACCESS: 		READ-WRITE
				USAGE:		    OPT
				PERSIST:		YES
				INSRVMOD:		NO
				RANGE:	    	SIZE (0..32)
				DEFVALUE:		NULL
				UNITS:	    	NA
				SPARSE: 		NO
				"
	::= { sipIsdnCasTerminationEntry 23 }

-- =============================================================================
-- SIP PRIMARY RATE ISDN BEARER CHANNEL TABLE
-- =============================================================================

    sipBChannelTable OBJECT-TYPE
        SYNTAX SEQUENCE OF SipBChannelEntry
        ACCESS not-accessible
        STATUS mandatory
        DESCRIPTION
            "This table defines port specific operational, statistics and active call data for ISDN B channels. Each entry in this table describes one B (bearer) channel.
            7302/7330 ISAM FTTN : Not Supported Actually
            7363 MX : Not Supported Actually
            7367 SX : Not Supported Actually

            ALCATEL NOTE: 
            TABLESIZE: DEP [max slot of one shelf multiply max termination of one board multiply 30B-channel]
            DESCR:NA."
    ::= { sipMIB 41}

        sipBChannelEntry OBJECT-TYPE
            SYNTAX SipBChannelEntry
            ACCESS not-accessible
            STATUS mandatory
            DESCRIPTION
                "An entry in the sipBChannelTable."
            INDEX { ifIndex }
        ::= { sipBChannelTable 1 }

        SipBChannelEntry ::=
            SEQUENCE {
                bearerChannelType  INTEGER,
                bearerChannelOperStatus  INTEGER,
                bearerChannelNumber  INTEGER  
            }

            bearerChannelType OBJECT-TYPE
                SYNTAX INTEGER {
                    dialup(1),
                    leased(2)
                }
                ACCESS  read-write
                STATUS  mandatory
                DESCRIPTION
                    "The B channel type. If the B channel is connected to a dialup line, this object shall be set to the value 'dialup(1)'.
                     In this case, it is controlled by an associated signaling channel.
                     If the B channel is connected to a leased line, this object shall be set to the value 'leased(2)'. 
                     For leased line B channels, there is no signaling channel control available.
                    ALCATEL-LUCENT NOTE:
                        ACCESS:       READ-WRITE
                        USAGE:        OPT
                        PERSIST:      Yes
                        INSRVMOD:     NO
                        RANGE:        1|2
                        DEFVALUE:     1
                        UNITS:        NA
                        SPARSE:       NO
                    "
            ::= { sipBChannelEntry 1 }

            bearerChannelOperStatus OBJECT-TYPE
                SYNTAX INTEGER {
                    idle(1),
                    connecting(2),
                    connected(3),
                    active(4)
                }
                ACCESS  read-only
                STATUS      mandatory
                DESCRIPTION
                "The current call control state for this port.
                    idle(1):        The B channel is idle.No call or call attempt is going on.
                    connecting(2):  A connection attempt (outgoing call)is being made on this interface.
                    connected(3):   An incoming call is in the process of validation.
                    active(4):      A call is active on this interface.
                ALCATEL-LUCENT NOTE: 
                    ACCESS:     READ-ONLY
                    USAGE:      NA
                    PERSIST:    NO
                    INSRVMOD:   NA
                    RANGE:  1 | 2 | 3 | 4
                    DEFVALUE:   NA
                    UNITS:      NA
                    SPARSE:     NOT
                "
            ::= { sipBChannelEntry 2 }

            bearerChannelNumber         OBJECT-TYPE
                SYNTAX INTEGER (1..30)
                ACCESS  read-only
                STATUS      mandatory
                DESCRIPTION
                "The identifier being used by a signaling protocol
                to identify this B channel, also referred to as
                B channel number. 
                ALCATEL-LUCENT NOTE: 
                    ACCESS:     READ-ONLY
                    USAGE:      NA
                    PERSIST:    NO
                    INSRVMOD:   NA
                    RANGE:     1..30
                    DEFVALUE:   NA
                    UNITS:      NA
                    SPARSE:     NO 
                "
            ::= { sipBChannelEntry 3 }

-- ==================================================================
-- END SIP PRIMARY RATE ISDN MIB.
-- ==================================================================

-- =============================================================================
-- SIP MULTIPLE SERVICE PROFILE TABLE
-- =============================================================================

       sipSSPProfileTable OBJECT-TYPE
           SYNTAX SEQUENCE OF SipSSPProfileEntry
           ACCESS not-accessible 
           STATUS mandatory
           DESCRIPTION
               "This table allows to display the list of SIP Service profiles included in the activated CDE file version. 
               The output report contains the SIP Service Profile ID, the SIP Service Profile Name and a short description of the intended use.               
               7302/7330 ISAM FTTN : Supported
               7363 MX :  Supported
               7367 SX : Not Supported (Multiple SSP per access node not supported)
           
               ALCATEL NOTE: 
               TABLESIZE: 5
               DESCR:NA
               "
       ::= { sipMIB 42 }

                                                                                                                                                                                                                                          
       sipSSPProfileEntry OBJECT-TYPE
           SYNTAX SipSSPProfileEntry
           ACCESS not-accessible
           STATUS mandatory
           DESCRIPTION
               "An entry in the sipSSPProfileTable."
	   INDEX { sipSSPProfileId }
       ::= { sipSSPProfileTable 1 }

       SipSSPProfileEntry ::=
           SEQUENCE {
           sipSSPProfileId          INTEGER,
           sipSSPProfileName       OCTET STRING,
           sipSSPProfileDescription        OCTET STRING
       }

	
       sipSSPProfileId OBJECT-TYPE
           SYNTAX  INTEGER
           ACCESS  read-only
           STATUS  mandatory
           DESCRIPTION "ID of the SSP profile as present in the activated CDE file.
               ALCATEL-LUCENT NOTE:
               ACCESS:    READ-ONLY
               USAGE:     NA
               PERSIST:   NO
               INSRVMOD:  NA
               RANGE:     (1..16)
               DEFVALUE:  NA
               UNITS:     NA
               SPARSE:    NO
               "
       ::= { sipSSPProfileEntry 1}


       sipSSPProfileName OBJECT-TYPE
           SYNTAX OCTET STRING  (SIZE (0..64))
           ACCESS  read-only
           STATUS  mandatory
           DESCRIPTION "Name of the SSP profile as present in the activated CDE file.
               ALCATEL-LUCENT NOTE:
               ACCESS:    READ-ONLY
               USAGE:     NA
               PERSIST:   NO
               INSRVMOD:  NA
               RANGE:SIZE (0..64)
               DEFVALUE:  NA
               UNITS:     NA
               SPARSE:    NO
               "
       ::= { sipSSPProfileEntry 2}


       sipSSPProfileDescription OBJECT-TYPE
           SYNTAX OCTET STRING  (SIZE (0..64))
           ACCESS  read-only
           STATUS  mandatory
           DESCRIPTION "Description of the SSP profile as present in the activated CDE file.
               ALCATEL-LUCENT NOTE:
               ACCESS:    READ-ONLY
               USAGE:     NA
               PERSIST:   NO
               INSRVMOD:  NA
               RANGE:SIZE (0..64)
               DEFVALUE:  NA
               UNITS:     NA
               SPARSE:    NO
               "
       ::= { sipSSPProfileEntry 3}

-- =============================================================================
-- SIP DHCP SIP SERVER TABLE
-- =============================================================================
		sipDhcpSipServerTable OBJECT-TYPE
            SYNTAX SEQUENCE OF SipDhcpSipServerEntry
			ACCESS not-accessible
			STATUS mandatory
			DESCRIPTION
				"The sipDhcpSipServerTable allowing to show the sip servers returned by means of dhcp option 120.
                This table is supported for the single Service Gateway topology (legacy top[ology) as well as for the multiple Service Gateway topology.
                Maximum 4 sip servers can be displayed per Service Gateway.
                use VSP/VAG Name as mapping index 

                7302/7330 ISAM FTTN : Supported
                7363 MX : Supported
                7367 SX : Not supported
		
			ALCATEL NOTE: 
			TABLESIZE: 16 
			DESCR:NA."
			::= { sipMIB 43 }

		sipDhcpSipServerEntry OBJECT-TYPE
			SYNTAX SipDhcpSipServerEntry
			ACCESS not-accessible
			STATUS mandatory
			DESCRIPTION
				"An entry in the sipDhcpSipServerTable."
			INDEX { sipVSPId }
			::= { sipDhcpSipServerTable 1 }

		
		SipDhcpSipServerEntry ::=
			SEQUENCE { 
				sipDhcpSipServer1AddrType	InetAddressType,
				sipDhcpSipServer1Addr	InetAddress,
				sipDhcpSipServer1OperStatus 	INTEGER,
				sipDhcpSipServer1Priority		INTEGER,
				sipDhcpSipServer2AddrType	InetAddressType,
				sipDhcpSipServer2Addr	InetAddress,
				sipDhcpSipServer2OperStatus 	INTEGER,
				sipDhcpSipServer2Priority		INTEGER,
				sipDhcpSipServer3AddrType	InetAddressType,
				sipDhcpSipServer3Addr	InetAddress,
				sipDhcpSipServer3OperStatus 	INTEGER,
				sipDhcpSipServer3Priority		INTEGER,
				sipDhcpSipServer4AddrType	InetAddressType,
				sipDhcpSipServer4Addr	InetAddress,
				sipDhcpSipServer4OperStatus 	INTEGER,
				sipDhcpSipServer4Priority		INTEGER
			 }


		sipDhcpSipServer1AddrType OBJECT-TYPE
			SYNTAX InetAddressType
			ACCESS read-only
			STATUS mandatory
			DESCRIPTION
			    " The IP Address type of the dhcp sip server 1.
				Ipv4(1) : An Ipv4 address as defined by the InetAddressIPv4 textual convention
				Dns(16) : A DNS name as defined by the InetAddressDNS textual convention.
		
			ALCATEL-LUCENT NOTE:
			ACCESS:	    READ-ONLY
			USAGE:      NA				
			PERSIST: 	NO
			INSRVMOD:	NO
			RANGE:	1 | 16 -- ipv4(1) or dns(16)
			DEFVALUE:	ipv4(1)
			UNITS:	NA
			SPARSE:	NO
					 "
			::= { sipDhcpSipServerEntry 1 }

		sipDhcpSipServer1Addr OBJECT-TYPE
			SYNTAX InetAddress
			ACCESS read-only
			STATUS mandatory
			DESCRIPTION
			    " IP Address or DNS name of the dhcp sip server 1. 
                The Address type is defined by SipDhcpSipServer1AddrType. 
				The  maximum length of this field = 64 Octets
		
			ALCATEL-LUCENT NOTE:
			ACCESS:	    READ-ONLY
			USAGE:      NA		
			PERSIST:	NO
			INSRVMOD:   NO
			RANGE:      NA
			DEFVALUE:   NA
			UNITS:      NA
			SPARSE:     NO		
			"
			::= { sipDhcpSipServerEntry 2 }

		sipDhcpSipServer1OperStatus OBJECT-TYPE
			SYNTAX INTEGER
				{
				up(1),
				down(2)
				}
			ACCESS read-only
			STATUS mandatory
			DESCRIPTION
			    "The operational status of the dhcp sip server 1.
				UP ( 1) : The server is in service.
				DOWN (2) : The server is out of service.
			ALCATEL-LUCENT NOTE:
			ACCESS:	    READ-ONLY
		    USAGE:      NA		
			PERSIST:	NO
			INSRVMOD:	NA
			RANGE:      1 | 2
			DEFVALUE:   NA
			UNITS:      NA	
		    SPARSE:     NO	
					"
			::= { sipDhcpSipServerEntry 3 }

		sipDhcpSipServer1Priority OBJECT-TYPE
			SYNTAX INTEGER 
			ACCESS read-only
			STATUS mandatory
			DESCRIPTION
			    "The priority of the dhcp sip server 1. The lower the value the higher the priority of the sip server.
                 Different sip servers have a different priority.

			ALCATEL-LUCENT NOTE:
			ACCESS:	    READ-ONLY
			USAGE:      NA		
			PERSIST:    NO
			INSRVMOD:   NO
			RANGE:      (0...4)	
			DEFVALUE:   NA
			UNITS:      NA
		 	SPARSE:     NO
			"
			::= { sipDhcpSipServerEntry 4 }

		sipDhcpSipServer2AddrType OBJECT-TYPE
			SYNTAX InetAddressType
			ACCESS read-only
			STATUS mandatory
			DESCRIPTION
			    " The IP Address type of the dhcp sip server 2.
				Ipv4(1) : An Ipv4 address as defined by the InetAddressIPv4 textual convention
				Dns(16) : A DNS name as defined by the InetAddressDNS textual convention.
		
			ALCATEL-LUCENT NOTE:
			ACCESS:	   READ-ONLY
			USAGE:     NA				
			PERSIST:   NO
			INSRVMOD:  NO
			RANGE:     1 | 16 -- ipv4(1) or dns(16)
			DEFVALUE:  ipv4(1)
			UNITS:     NA
			SPARSE:    NO
			"
			::= { sipDhcpSipServerEntry 5 }

		sipDhcpSipServer2Addr OBJECT-TYPE
			SYNTAX InetAddress
			ACCESS read-only
			STATUS mandatory
			DESCRIPTION
			    " IP Address or DNS name of the dhcp sip server 2. 
                The Address type is defined by SipDhcpSipServer2AddrType. 
				The  maximum length of this field = 64 Octets
		
			ALCATEL-LUCENT NOTE:
			ACCESS:	    READ-ONLY
			USAGE:      NA
			PERSIST:    NO
			INSRVMOD:   NO
			RANGE:      NA
			DEFVALUE:   NA
			UNITS:      NA
			SPARSE:     NO		
			"
			::= { sipDhcpSipServerEntry 6 }

		sipDhcpSipServer2OperStatus OBJECT-TYPE
			SYNTAX INTEGER
				{
				up(1),
				down(2)
				}
			ACCESS read-only
			STATUS mandatory
			DESCRIPTION
			    "The operational status of the dhcp sip server 2.
				UP ( 1) : The server is in service.
				DOWN (2) : The server is out of service.
			ALCATEL-LUCENT NOTE:
			ACCESS:	    READ-ONLY
		    USAGE:      NA
			PERSIST:    NO
			INSRVMOD:   NA
			RANGE:      1 | 2
			DEFVALUE:   NA
			UNITS:      NA	
		    SPARSE:     NO	
			"
			::= { sipDhcpSipServerEntry 7 }

		sipDhcpSipServer2Priority OBJECT-TYPE
			SYNTAX INTEGER 
			ACCESS read-only
			STATUS mandatory
			DESCRIPTION
			    "The priority of the dhcp sip server 2. The lower the value the higher the priority of the sip server.
                 Different sip servers have a different priority.

			ALCATEL-LUCENT NOTE:
			ACCESS:	    READ-ONLY
			USAGE:      NA
			PERSIST:    NO
			INSRVMOD:   NO
			RANGE:      (0...4)	
			DEFVALUE:   0
			UNITS:      NA
		 	SPARSE:     NO
			"
			::= { sipDhcpSipServerEntry 8 }

		sipDhcpSipServer3AddrType OBJECT-TYPE
			SYNTAX InetAddressType
			ACCESS read-only
			STATUS mandatory
			DESCRIPTION
				" The IP Address type of the dhcp sip server 3.
				Ipv4(1) : An Ipv4 address as defined by the InetAddressIPv4 textual convention
				Dns(16) : A DNS name as defined by the InetAddressDNS textual convention.
		
			ALCATEL-LUCENT NOTE:
			ACCESS:     READ-ONLY
			USAGE:      NA
			PERSIST:    NO
			INSRVMOD:   NO
			RANGE:      1 | 16 -- ipv4(1) or dns(16)
			DEFVALUE:   ipv4(1)
			UNITS:      NA
			SPARSE:     NO
		    "
			::= { sipDhcpSipServerEntry 9 }

		sipDhcpSipServer3Addr OBJECT-TYPE
			SYNTAX InetAddress
			ACCESS read-only
			STATUS mandatory
			DESCRIPTION
				" IP Address or DNS name of the dhcp sip server 3. 
                The Address type is defined by SipDhcpSipServer3AddrType. 
				The  maximum length of this field = 64 Octets
		
			ALCATEL-LUCENT NOTE:
			ACCESS:	    READ-ONLY
			USAGE:      NA
			PERSIST:    NO
			INSRVMOD:   NO
			RANGE:      NA
			DEFVALUE:   NA
			UNITS:      NA
			SPARSE:     NO		
			"
			::= { sipDhcpSipServerEntry 10 }

		sipDhcpSipServer3OperStatus OBJECT-TYPE
			SYNTAX INTEGER
				{
				up(1),
				down(2)
				}
			ACCESS read-only
			STATUS mandatory
			DESCRIPTION
				"The operational status of the dhcp sip server 3.
				UP ( 1) : The server is in service.
				DOWN (2) : The server is out of service.
			ALCATEL-LUCENT NOTE:
			ACCESS:     READ-ONLY	
		    USAGE:      NA
			PERSIST:    NO
			INSRVMOD:   NA
			RANGE:      1 | 2
			DEFVALUE:   NA
			UNITS:      NA	
		    SPARSE:     NO	
			"
			::= { sipDhcpSipServerEntry 11 }

		sipDhcpSipServer3Priority OBJECT-TYPE
			SYNTAX INTEGER 
			ACCESS read-only
			STATUS mandatory
			DESCRIPTION
				"The priority of the dhcp sip server 3. The lower the value the higher the priority of the sip server.
                 Different sip servers have a  different priority.

			ALCATEL-LUCENT NOTE:
			ACCESS:	   READ-ONLY
			USAGE:     NA
			PERSIST:   NO
			INSRVMOD:  NO
			RANGE:     (0...4)	
			DEFVALUE:  0
			UNITS:     NA
		 	SPARSE:    NO
			"
			::= { sipDhcpSipServerEntry 12 }

		sipDhcpSipServer4AddrType OBJECT-TYPE
			SYNTAX InetAddressType
			ACCESS read-only
			STATUS mandatory
			DESCRIPTION
				" The IP Address type of the dhcp sip server 4.
				Ipv4(1) : An Ipv4 address as defined by the InetAddressIPv4 textual convention
				Dns(16) : A DNS name as defined by the InetAddressDNS textual convention.
		
			ALCATEL-LUCENT NOTE:
			ACCESS:	    READ-ONLY
			USAGE:      NA
			PERSIST:    NO
			INSRVMOD:   NO
			RANGE:      1 | 16 -- ipv4(1) or dns(16)
			DEFVALUE:   ipv4(1)
			UNITS:      NA
			SPARSE:     NO
			"
			::= { sipDhcpSipServerEntry 13 }

		sipDhcpSipServer4Addr OBJECT-TYPE
			SYNTAX InetAddress
			ACCESS read-only
			STATUS mandatory
			DESCRIPTION
				" IP Address or DNS name of the dhcp sip server 4. 
                The Address type is defined by SipDhcpSipServer4AddrType. 
				The  maximum length of this field = 64 Octets
		
			ALCATEL-LUCENT NOTE:
			ACCESS:	    READ-ONLY
			USAGE:      NA
			PERSIST:    NA
			INSRVMOD:   NA
			RANGE:      NA
			DEFVALUE:   NA
			UNITS:      NA
			SPARSE:     NO
			"
			::= { sipDhcpSipServerEntry 14 }

		sipDhcpSipServer4OperStatus OBJECT-TYPE
			SYNTAX INTEGER
				{
				up(1),
				down(2)
				}
			ACCESS read-only
			STATUS mandatory
			DESCRIPTION
				"The operational status of the dhcp sip server 4.
				UP ( 1) : The server is in service.
				DOWN (2) : The server is out of service.
			ALCATEL-LUCENT NOTE:
			ACCESS:	    READ-ONLY
		    USAGE:      NO
			PERSIST:    NO
			INSRVMOD:   NA
			RANGE:      1 | 2
			DEFVALUE:   NA
			UNITS:      NA	
		    SPARSE:     NO	
			"
			::= { sipDhcpSipServerEntry 15 }

		sipDhcpSipServer4Priority OBJECT-TYPE
			SYNTAX INTEGER 
			ACCESS read-only
			STATUS mandatory
			DESCRIPTION
				"The priority of the dhcp sip server 4. The lower the value the higher the priority of the sip server.
                 Different sip servers have a different priority.

			ALCATEL-LUCENT NOTE:
			ACCESS:     READ-only
			USAGE:      NA
			PERSIST:    NO
			INSRVMOD:   NO
			RANGE:      (0...4)	
			DEFVALUE:   0
			UNITS:      NA
		 	SPARSE:     NO
			"
			::= { sipDhcpSipServerEntry 16 }


-- ==================================================================
-- SIP MULTIPLE SERVICE PROFILE MAPPING TABLE
-- ===========================================================================

                sipSSPProfileMappingTable OBJECT-TYPE
                        SYNTAX          SEQUENCE OF SipSSPProfileMappingEntry
                        ACCESS          not-accessible 
                        STATUS          mandatory 
                        DESCRIPTION 
                                "The operator friendly SIP Service Profile name to unique internal identifier mapping table. 

                        7302/7330 ISAM FTTN : Supported
                        7363 MX :  Supported
                        7367 SX : Not Supported (Multiple SSP per access node not supported)

                        ALCATEL NOTE: 
                        TABLESIZE: 5 
                        DESCR: NA 
                        " 
                ::= { sipMIB 44} 

                sipSSPProfileMappingEntry OBJECT-TYPE
                        SYNTAX          SipSSPProfileMappingEntry 
                        ACCESS          not-accessible 
                        STATUS          mandatory 
                        DESCRIPTION 
                                "An entry in the sipSSPProfileMappingTable.
                                The entries are dynamically created by the voice LT board upon the receipt of a request to map a 
                                SSP Profile name to a SSP Profile ID. 
                                The entries cannot autonomously be created upon the activation of the CDE file as the NT board
                                cannot parse the content of the CDE file. Only the voice LT board can parse the CDE file.
                                " 
                        INDEX { sipSSPProfileMappingName } 
                        ::= { sipSSPProfileMappingTable 1 } 

                        SipSSPProfileMappingEntry ::= 
                        SEQUENCE {
                        sipSSPProfileMappingName        OCTET STRING, 
                        sipSSPProfileMappingId          INTEGER 
                        } 

                sipSSPProfileMappingName OBJECT-TYPE
                        SYNTAX          OCTET STRING (SIZE (0..64)) 
                        ACCESS          not-accessible 
                        STATUS          mandatory 
                        DESCRIPTION 
                                "The operator friendly name of the SIP Service Profile.

                        ALCATEL-LUCENT NOTE: 
                        ACCESS:       NOT-ACCESSIBLE 
                        USAGE:        MANDATORY 
                        PERSIST:      YES 
                        INSRVMOD:     NA 
                        RANGE:        SIZE (0..64) 
                        DEFVALUE:     NA 
                        UNITS:        NA 
                        SPARSE:       NO 
                        " 
                ::= { sipSSPProfileMappingEntry 1 } 

                sipSSPProfileMappingId OBJECT-TYPE
                        SYNTAX          INTEGER 
                        ACCESS          read-only 
                        STATUS          mandatory 
                        DESCRIPTION 
                                "The unique internal identifier of a SIP Service Profile.
                        
                        ALCATEL-LUCENT NOTE: 
                        ACCESS:       READ-ONLY 
                        USAGE:        NA 
                        PERSIST:      YES 
                        INSRVMOD:     NA 
                        RANGE:        (1..5) 
                        DEFVALUE:     NA 
                        UNITS:        NA 
                        SPARSE:       NO 
                        " 
                ::= { sipSSPProfileMappingEntry 2 } 

-- =============================================================================
-- Sip Shared Line Termination Table.
-- =============================================================================
                sipSharedLineTermTable OBJECT-TYPE
                        SYNTAX SEQUENCE OF SipSharedLineTermEntry
                        ACCESS not-accessible
                        STATUS mandatory
                        DESCRIPTION
                                "The sipTerminationTable together with the sipSharedLineTerminationTable allows to
                                 configure the prime and the secondary SIP termination that are connected to a POTS
                                 port. The prime SIP termination is configured in the sipTerminationTable while the
                                 secondary SIP termination is configured in the sipSharedLineTerminationTable. The
                                 prime and the secondary SIP termination share the same Ifindex, however own a different
                                 DN / URI. Supplementary services are separately configurable for prime and secondary
                                 SIP termination. The configurable line characteristics and line test properties are
                                 configurable in the sipTerminationTable only. If a POTS LT board configured with POTS
                                 ports connected to a single SIP termination, the maximum number of SIP terminations
                                 supported by the NPOT-B board = 72 and by the NPOT-C = 48, while if a POTS ports connected
                                 to a prime and secondary SIP termination or even a mixture of both configuration options,
                                 the maximum number of SIP terminations supported by the NPOT-B board = 82 and by the NPOT-C = 82.
                                 The following configuration policy applies :
                                 - The secondary SIP termination can be created in the sipSharedLineTerminationTable on
                                   the condition that the prime SIP termination has been created in the sipTerminationTable.
                                 - The secondary SIP termination can at any time be deleted.
                                 - The prime SIP termination can be deleted on the condition that the secondary SIP
                                   termination has been deleted before in the sipSharedLineTerminationTable.
                                7302/7330 ISAM FTTN : Supported
                                7363 MX : NOT Supported
                                7367 SX : NOT Supported

                        ALCATEL NOTE: 
                        TABLESIZE: DEP [max slot of one shelf multiply max termination of one board]/2
                        DESCR:NA."
                ::= { sipMIB 45 }

                sipSharedLineTermEntry OBJECT-TYPE
                        SYNTAX SipSharedLineTermEntry
                        ACCESS not-accessible
                        STATUS mandatory
                        DESCRIPTION
                                "An entry in the sipSharedLineTermTable. 
                                For a paired phone set, the SIP termination configured in the sipSharedLineTermTable 
                                shares the same IFINDEX as the SIP termination configured in the sipTerminationTable" 
                        INDEX { ifIndex }
                ::= { sipSharedLineTermTable 1 }

                SipSharedLineTermEntry ::=
                        SEQUENCE { 
                        sipSharedLineTermDn                         OCTET STRING,
                        sipSharedLineTermUserName                   OCTET STRING,
                        sipSharedLineTermUri                        OCTET STRING,
                        sipSharedLineTermCallStatus                 INTEGER,
                        sipSharedLineTermAdminStatus                INTEGER,
                        sipSharedLineTermOperStatus                 INTEGER,
                        sipSharedLineTermRowStatus                  RowStatus,
                        sipSharedLineTermContactUserInfo            OCTET STRING,
                        sipSharedLineTermDisplayName                OCTET STRING,
                        sipSharedLineTermETSIClipDataMode           INTEGER,
                        sipSharedLineTermEnableCallWaiting          INTEGER,
                        sipSharedLineTermEnableCallHold             INTEGER,
                        sipSharedLineTermEnableCallConference       INTEGER,
                        sipSharedLineTermEnableCallTransfer         INTEGER
                        }


                sipSharedLineTermDn OBJECT-TYPE
                        SYNTAX OCTET STRING (SIZE (0..32))
                        ACCESS read-write
                        STATUS mandatory
                        DESCRIPTION
                                "Directory number of the secondary SIP termination.
                                Both, the sipSharedLineTermDn and sipSharedLineTermUri can not be configured with the null string.
                                Should DN being configured and URI left empty then the register URI is composed by concatenating the
                                configured DN together with the register URI configured in the sipRegisterTable.
                                Should this object not been configured then the sipSharedLineTermUri must be configured.
                        ALCATEL-LUCENT NOTE:
                        ACCESS: NA
                        USAGE:  OPT 
                        PERSIST:        YES
                        INSRVMOD: NO
                        RANGE:  SIZE (0..32)
                        DEFVALUE:       null
                        UNITS:  NA      
                        SPARSE: NO                      
                        "
                ::= { sipSharedLineTermEntry 1 }

                sipSharedLineTermUserName OBJECT-TYPE
                        SYNTAX OCTET STRING (SIZE (0..64))
                        ACCESS read-write
                        STATUS mandatory
                        DESCRIPTION
                                "User name of the secondary SIP termination.
                                Must be unique across all entries of this table and sipTerminationTable.
                        ALCATEL-LUCENT NOTE:
                        ACCESS: NA
                        USAGE:  OPT
                        PERSIST:        YES
                        INSRVMOD: NO
                        RANGE:  SIZE (0..64)
                        DEFVALUE:       null
                        UNITS:  NA      
                        SPARSE: NO                      
                        "
                ::= { sipSharedLineTermEntry 2 }

                sipSharedLineTermUri OBJECT-TYPE
                        SYNTAX OCTET STRING (SIZE (0..80))
                        ACCESS read-write
                        STATUS mandatory
                        DESCRIPTION
                                "SIP URI by which the user agent identifies the secondary SIP termination.
                                Must be unique across all entries of this table and sipTerminationTable.
                                sipSharedLineTermDn and sipSharedLineTermUri can not be configured to the null string at the same time.
                                The register URI in the sipRegisterTable must not be configured in case this object is configured as the 
                                URI configured in this object also includes the register domain.
                        ALCATEL-LUCENT NOTE:
                        ACCESS: NA
                        USAGE:  OPT
                        PERSIST:        YES
                        INSRVMOD: NO
                        RANGE:  SIZE (0..80)
                        DEFVALUE:       null
                        UNITS:  NA      
                        SPARSE: NO                      
                        "
                ::= { sipSharedLineTermEntry 3 }

                sipSharedLineTermCallStatus OBJECT-TYPE
                        SYNTAX INTEGER 
                        {
                                onhook(1),
                                offhook(2),
                                dialing(3),
                                calling(4),
                                connected(5),
                                idleOffhook(6),
                                busyTone(7),
                                howlerTone(8),
                                ringing(9),
                                releasing(10),
                                ringback(11),
                                sharedCutoff(12)
                        }
                        ACCESS read-only
                        STATUS mandatory
                        DESCRIPTION
                                "The call/line status of the secondary SIP termination, The meaning of the status is list as following:
                                onhook(1): hook on without any call
                                offhook(2): hook off but user no dialing
                                dialing(3): dial digit
                                calling(4): send INVITE and wait response
                                connected(5): call connect
                                idleOffhook(6): parking
                                busyTone(7): this status no used after R41
                                howlerTone(8): this status no used after R41
                                ringing(9): ring
                                releasing(10): call have been terminated, but subscriber does not hook on, some tone maybe play in this
                                                state, the line is in releasing state
                                ringback(11): ringback tone to caller.
                                sharedCutoff(12): term should be in cutoff status with following condition
                                    Paired term is providing service (offhook, dialling, ringing, releasing, ringback), the other termination
                                    will go to cutoff status and hear silence if hooks off it, and incoming call request for it will
                                    be rejected
                        ALCATEL-LUCENT NOTE:
                        ACCESS: NA
                        USAGE:  NA
                        PERSIST:        NO
                        INSRVMOD: NA
                        RANGE:  1..11
                        DEFVALUE:       NA
                        UNITS:  NA
                        SPARSE: NO
                        "
                ::= { sipSharedLineTermEntry 4 }

                sipSharedLineTermAdminStatus OBJECT-TYPE
                        SYNTAX INTEGER
                        {
                                up(1),
                                down(2)
                        }
                        ACCESS read-write
                        STATUS mandatory
                        DESCRIPTION
                                "The administrative status of the secondary SIP termination.
                                 When the administrative status of a SIP termination is modified from 'up' to 'down',
                                 then the system will de-register the SIP termination. The physical line shall be
                                 powered off on the condition that the administrative state of both SIP terminations,
                                 the prime and the secondary, is disabled.
                                 UP (1) : the attributes of this entry that are indicated as INSRVMOD=YES can be modified.
                                 DOWN (2) : the attributes of this entry that are indicated as INSRVMOD=YES and the attributes that are
                                        indicated as INSRVMOD=NO can be modified.
                                 Note that the attributes of this entry that are indicated INSRVMOD=NA can not be modified after creation.

                        ALCATEL-LUCENT NOTE:
                        ACCESS: NA
                        USAGE:  OPT
                        PERSIST:        YES
                        INSRVMOD: YES
                        RANGE:  1 | 2
                        DEFVALUE:       down
                        UNITS:  NA              
                        SPARSE: NO              
                        "
                ::= { sipSharedLineTermEntry 5 }

                sipSharedLineTermOperStatus OBJECT-TYPE
                        SYNTAX INTEGER
                        {
                                up(1),
                                down(2)
                        }
                        ACCESS read-only
                        STATUS mandatory
                        DESCRIPTION
                                " The operational status of the secondary sip termination.
                                up(1) :  The SIP Termination is up and able to make calls.
                                down(2) : The SIP Termination is out of service.
                        ALCATEL-LUCENT NOTE:
                        ACCESS: NA
                        USAGE:  NA
                        PERSIST:        NO
                        INSRVMOD: NA
                        RANGE:  1 | 2
                        DEFVALUE:       NA
                        UNITS:  NA      
                        SPARSE: NO                                      
                        "
                ::= { sipSharedLineTermEntry 6 }

                sipSharedLineTermRowStatus OBJECT-TYPE
                        SYNTAX RowStatus
                        ACCESS read-write
                        STATUS mandatory
                        DESCRIPTION
                                "The status of this conceptual row.
                                The RowStatus TC requires that this DESCRIPTION clause
                                states under which circumstances other objects in this row
                                can be modified.  The value of this object has no effect on
                                whether other objects in this conceptual row can be
                                modified.
                                A conceptual row can always be made active.
                        ALCATEL-LUCENT NOTE:
                        ACCESS: NA
                        USAGE:  MAND
                        PERSIST:        NO
                        INSRVMOD: YES
                        RANGE:  1 | 4 | 6       -- active (1), createAndGo (4), destroy (6)
                        DEFVALUE:       NA
                        UNITS:  NA
                        SPARSE: NO
                        "
                ::= { sipSharedLineTermEntry 7 }

                sipSharedLineTermContactUserInfo OBJECT-TYPE
                        SYNTAX OCTET STRING (SIZE (1..128))
                        ACCESS read-only
                        STATUS mandatory
                        DESCRIPTION
                                "The user-info of contact field in SIP message associated with the user 
                                 When the sipLineIdSyntaxPattern is configured as 'terminationUriOrDN (1)'
                                 and sipSharedLineTermUri is NOT empty, then this object contains the
                                 user part of sipSharedLineTermUri as the user info.
                                 When the sipLineIdSyntaxPattern is configured as 'terminationUriOrDN (1)'
                                 and sipSharedLineTermUri is EMPTY, then this object contains the user part
                                 of sipSharedLineTermDN as the user info.
                                 When the sipLineIdSyntaxPattern is configured as 'PhysicalLineId (2)',
                                 then this object contains the physcial lineId as the user info.

                        ALCATEL-LUCENT NOTE:
                        ACCESS: NA
                        USAGE:  NA
                        PERSIST:        NO
                        INSRVMOD: NA
                        RANGE:  SIZE (1..128)
                        DEFVALUE:       NA
                        UNITS:  NA      
                        SPARSE: NO                      
                        "
                ::= { sipSharedLineTermEntry 8 }

                sipSharedLineTermDisplayName OBJECT-TYPE
                        SYNTAX OCTET STRING (SIZE (0..64))
                        ACCESS read-write
                        STATUS mandatory
                        DESCRIPTION
                                " Display name of the secondary sip termination.
                        ALCATEL-LUCENT NOTE:
                        ACCESS: NA
                        USAGE:  OPT
                        PERSIST:        YES
                        INSRVMOD: NO
                        RANGE:  SIZE (0..64)
                        DEFVALUE:       null
                        UNITS:  NA      
                        SPARSE: NO                      
                        "
                ::= { sipSharedLineTermEntry 9 }

                sipSharedLineTermETSIClipDataMode OBJECT-TYPE
                    SYNTAX INTEGER
                    {
                        cdevalue(1),
                        fsk(2),
                        dtmf(3)
                    }
                    ACCESS read-write
                    STATUS mandatory
                    DESCRIPTION
                        " The ETSI clip data transmission protocol of the secondary sip termination.
                        cdevalue(1) - CDE configuration will be applied for ETSI CLIP.
                        fsk(2)  - fsk will be applied for ETSI CLIP.
                        dtmf(3) - dtmf will be applied for ETSI CLIP.
                    ALCATEL-LUCENT NOTE:
                    ACCESS: NA
                    USAGE:  OPT
                    PERSIST:    Yes
                    INSRVMOD: NO
                    RANGE:  1 | 2 | 3
                    DEFVALUE:   1
                    UNITS:  NA
                    SPARSE: NO
                    "
                    DEFVAL {cdevalue}
                ::= { sipSharedLineTermEntry 10 }

                sipSharedLineTermEnableCallWaiting OBJECT-TYPE
                    SYNTAX INTEGER
                    {
                        disable (1),
                        enable (2),
                        subscribe (3)
                    }
                    ACCESS read-write
                    STATUS mandatory
                    DESCRIPTION
                        "This object allows to configure the Call Waiting properties for the secondary SIP termination.
                        Disable(1) - call waiting service is controlled by SIP Service Profile. The SSP will tell whether this service is
                        controlled by UA-Profile or the MIB disable value is applied (e.g. when the IMS core does not support the
                        UA-profile approach).
                        Enable(2) - call waiting service is enabled.
                        Subscribe(3) - call waiting service is subscribed and can be enabled/disabled by subscriber.
                    ALCATEL-LUCENT NOTE:
                    ACCESS: READ-WRITE
                    USAGE:  OPT
                    PERSIST:    YES
                    INSRVMOD:   NO
                    RANGE:  1|2|3
                    DEFVALUE:   disable (1)
                    UNITS:  NA
                    SPARSE: NO
                    "
                ::= { sipSharedLineTermEntry 11 }

                sipSharedLineTermEnableCallHold OBJECT-TYPE
                    SYNTAX INTEGER
                    {
                        disable (1),
                        enable (2),
                        subscribe (3)
                    }
                    ACCESS read-write
                    STATUS mandatory
                    DESCRIPTION
                        "This object allows to configure Call Hold properties for the secondary SIP termination.
                        Disable(1) - call hold service is controlled by SIP Service Profile. The SSP will tell whether this service is
                        controlled by UA-Profile or the MIB disable value is applied (e.g. when the IMS core does not support the
                        UA-profile approach).
                        Enable(2) - call hold service is enabled.
                        Subscribe(3) - call hold service is subscribed and can be enabled/disabled by subscriber. (This option is actually NOT supported)
                    ALCATEL-LUCENT NOTE:
                    ACCESS: READ-WRITE
                    USAGE:  OPT
                    PERSIST:    YES
                    INSRVMOD:   NO
                    RANGE:  1|2
                    DEFVALUE:   disable (1)
                    UNITS:  NA
                    SPARSE: NO
                    "
                ::= { sipSharedLineTermEntry 12 }

                sipSharedLineTermEnableCallConference OBJECT-TYPE
                    SYNTAX INTEGER
                    {
                        disable (1),
                        enable (2),
                        subscribe (3)
                    }
                    ACCESS read-write
                    STATUS mandatory
                    DESCRIPTION
                        "This object allows to configure Call Conference properties for the secondary SIP termination.
                        Disable(1) - call conference service is controlled by SIP Service Profile. The SSP will tell whether this service is
                        controlled by UA-Profile or the MIB disable value is applied (e.g. when the IMS core does not support the
                        UA-profile approach).
                        Enable(2) - call conference service is enabled.
                        Subscribe(3) - call conference service is subscribed and can be enabled/disabled by subscriber. (This option is actually NOT supported)
                    ALCATEL-LUCENT NOTE:
                    ACCESS: READ-WRITE
                    USAGE:  OPT
                    PERSIST:    YES
                    INSRVMOD:   NO
                    RANGE:  1|2
                    DEFVALUE:   disable (1)
                    UNITS:  NA
                    SPARSE: NO
                "
                ::= { sipSharedLineTermEntry 13 }

                sipSharedLineTermEnableCallTransfer OBJECT-TYPE
                    SYNTAX INTEGER
                    {
                        disable (1),
                        enable (2),
                        subscribe (3)
                    }
                    ACCESS read-write
                    STATUS mandatory
                    DESCRIPTION
                        "This object allows to configure Call Transfer properties for the secondary SIP termination.
                        Disable(1) - call transfer service is controlled by SIP Service Profile. The SSP will tell whether this service is
                        controlled by UA-Profile or the MIB disable value is applied (e.g. when the IMS core does not support the
                        UA-profile approach).
                        Enable(2) - call transfer service is enabled.
                        Subscribe(3) - call transfer service is subscribed and can be enabled/disabled by subscriber. (This option is actually NOT supported)
                    ALCATEL-LUCENT NOTE:
                    ACCESS: READ-WRITE
                    USAGE:  OPT
                    PERSIST:    YES
                    INSRVMOD:   NO
                    RANGE:  1|2
                    DEFVALUE:   disable (1)
                    UNITS:  NA
                    SPARSE: NO
                "
                ::= { sipSharedLineTermEntry 14 }

-- =============================================================================
-- Sip Rule Table.
-- =============================================================================
              sipRuleTable OBJECT-TYPE
	               SYNTAX 	SEQUENCE OF SipRuleEntry
	               ACCESS 	not-accessible
	               STATUS 	mandatory
	               DESCRIPTION
                      "The sipRuleTable allows to create the manipulation rule(s),
                      A rule is identified by its rule ID..
                      Nokia NOTE: 
                      TABLESIZE: 256 
                      DESCR:NA."
	              ::= { sipMIB 46 }

              sipRuleEntry OBJECT-TYPE
                 SYNTAX	SipRuleEntry
                 ACCESS 	not-accessible
                 STATUS 	mandatory
                 DESCRIPTION
			        "An entry in the sipRuleTable."
                 INDEX { sipRuleId }
                 ::= { sipRuleTable 1 }
              
              SipRuleEntry ::=
                    SEQUENCE { 
                             sipRuleId	        INTEGER,
                             sipRuleName        OCTET STRING,
                             sipRule            OCTET STRING,
                             sipRuleAdminState  INTEGER,
                             sipRuleRowStatus   RowStatus
                             }

              sipRuleId OBJECT-TYPE
                        SYNTAX INTEGER (1..256)
                        ACCESS read-write
                        STATUS mandatory
                        DESCRIPTION
                        "A rule is identified by its rule ID
                        NOKIA NOTE:
                        ACCESS:   READ-WRITE
                        USAGE:    MANDATORY
                        PERSIST:  YES
                        INSRVMOD: NA
                        RANGE:    1..256
                        DEFVALUE: NA
                        UNITS:  NA
                        SPARSE: NO
                        "
                ::= { sipRuleEntry 1 }

		      sipRuleName OBJECT-TYPE
                          SYNTAX OCTET STRING (SIZE (0..32))
                          ACCESS read-write
                          STATUS mandatory
                          DESCRIPTION
                          "The operator friendly name of the rule
                           NOKIA NOTE:
                           ACCESS:     READ-WRITE
                           USAGE:      OPT
                           PERSIST:    YES
                           INSRVMOD:   YES
                           RANGE:      SIZE (0..32)
                           DEFVALUE:   null
                           UNITS:      NA
                           SPARSE:     NO
                          "
              ::= { sipRuleEntry 2 }

              sipRule OBJECT-TYPE
                      SYNTAX OCTET STRING (SIZE (1..64))
                      ACCESS read-write
                      STATUS mandatory
                      DESCRIPTION
                      " A rule is built up of key words and configurable values which must be 
                      configured according to a predetermined order. The position of the key words and 
                      configurable values may be different depending on the manipulation rule type.
                      A template shall be defined for each manipulation rule type. Key words and 
                      allowed configurable values shall be defined per template.
                      The following rule types are supported whereby only 1 rule type can be configured for a rule :
                      1)  [outg-use-default-pbx-number:numericvalue]
                         The manipulation rule consists of a fixed character string 'outg-use-default-pbx-number:' including
                         the hyphens and the colon. It is immediately followed by a numeric value with a  range [0,1]. 
                           '0': Don't replace the calling number by the 'pilot number' when it is invalid. 
                           '1': Replace the calling number by the 'pilot number' even when it is invalid.
                         It is not allowed to insert a space between the fixed character string and the numeric value.
                         e.g.  configure voice sip manipulate-rule 1 rule outg-use-default-pbx-number:0 admin-status enabled 
                      2)  [inc-add-phone-context-to-number]
                         The manipulation rule consists of a fixed character string 'inc-add-phone-context-to-number'
                         including the hyphens. This rule type does not require the country code to be configured as part of the manipulation rule.
                         .e.g. configure voice sip manipulate-rule 1 rule inc-add-phone-context-to-number admin-status enabled 
                      3)  [outg-add-country-area-code-in-phone-context:countrycode-areacode]
                         The manipulation rule consists of a fixed character string 'outg-add-country-area-code-in-phone-context:'
                         including the hyphens and the colon. It is immediately followed by 2 numeric values combined with
                         a hyphen. It is not allowed to insert a space between the fixed character string and the numeric
                         value nor between the numeric value and the combining hyphen.The country code can be 1..3 digits
                         long while the area code can be 1..2 digits long. 
                         e.g. configure voice sip manipulate-rule 1 rule outg-add-country-area-code-in-phone-context:20-24 admin-status enabled 
                      4)  [inc-short-number-len:shortnumberlength] The manipulation rule consists of a fixed character string 
                         'inc-short-number-len:' including the hyphens and the colon. It is immediately followed by a numeric
                          value with a  range [1,9]. It is not allowed to insert a space between the fixed character 
                          string and the numeric value. 
                          e.g. configure voice sip manipulate-rule 1 rule inc-short-number-len:4 admin-status enabled
                      5)  [outg-add-domain-name-in-phone-context]
                         The manipulation rule consists of a fixed character string 'outg-add-domain-name-in-phone-context'
                         including the hyphens. This rule type does not require the domain name to be configured as part of the manipulation rule.
                         .e.g. configure voice sip manipulate-rule 1 rule outg-add-domain-name-in-phone-context admin-status enabled
                      NOKIA NOTE:
                      ACCESS:     READ-WRITE
                      USAGE:      MANDATORY
                      PERSIST:    YES
                      INSRVMOD:   NO
                      RANGE:      SIZE (1..64)
                      DEFVALUE:   none
                      UNITS:      NA
                      SPARSE:     NO
                      "
              ::= { sipRuleEntry 3 }
              
              sipRuleAdminState OBJECT-TYPE
                   SYNTAX INTEGER 
                          {
                          enabled(1),
                          disabled(2)
                          }
                   ACCESS read-write
                   STATUS mandatory
                   DESCRIPTION
                   "The administrative state of the rule.
                    Enabled(1) : the rule can be executed. The attributes of this entry that 
                                 are indicated as INSRVMOD=YES can be modified.
                    Disabled(2): the rule cannot be executed. The attributes of this entry that 
                                 are indicated as INSRVMOD=YES and the attributes that are indicated as INSRVMOD=NO can 
                                 be modified.

                    NOKIA NOTE:
                    ACCESS:     READ-WRITE
                    USAGE:      OPT
                    PERSIST:    YES
                    INSRVMOD:   YES
                    RANGE:      1 | 2
                    DEFVALUE:   disabled(2)
                    UNITS:      NA
                    SPARSE:     NO
                    "
              ::= { sipRuleEntry 4 }
  
              sipRuleRowStatus OBJECT-TYPE
		            SYNTAX RowStatus
		            ACCESS read-write
		            STATUS mandatory
		            DESCRIPTION
				       "The status of this conceptual row.
				       NOKIA NOTE:
				       ACCESS: 		READ-WRITE
				       USAGE:		MAND
				       PERSIST:		NO
				       INSRVMOD:		YES
				       RANGE:		1 | 4 | 6	-- active (1), createAndGo (4), destroy (6)
				       DEFVALUE:		NA
				       UNITS:		NA
				       SPARSE: 		NO
				       "
	          ::= { sipRuleEntry 5 }

END
