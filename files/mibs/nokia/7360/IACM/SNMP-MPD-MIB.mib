-- ALCATEL rfc3412 MIB
-- ===========================================================================
-- The following MIB module definition was extracted from rfc3412
-- and modified to reflect Alcatel's implementation.
--
         -- Postal: Alcatel Bell Telephone
         -- Francis Wellesplein 1
         -- 2018 Antwerpen
         -- BELGIUM

-- ===========================================================================
--  HISTORY:
--
--  date: 25/04/2005
--  editor: Vishnu Shetty
--  Major changes with respect to standard version:
--      * Conversion of SNMPv2-TC MIB from SNMPv2 to SNMPv1 syntax.
--
--  date: 24/01/2006
--  editor: Bart Bogaert
--  Version: 3FE21961EAAA_2.4.0.6
--  Changes:
--      * Implemented BDFhw70643: strict syntax checks (smilint)
-- ===========================================================================

SNMP-MPD-MIB DEFINITIONS ::= BEGIN

IMPORTS
    OBJECT-TYPE                          FROM RFC-1212
--  snmpModules FROM SNMPv2-SMI;
    Counter, snmpModules                FROM RFC1155-SMI;

snmpMPDMIB OBJECT IDENTIFIER ::= { snmpModules 11 }

-- Administrative assignments ***************************************

snmpMPDAdmin           OBJECT IDENTIFIER ::= { snmpMPDMIB 1 }
snmpMPDMIBObjects      OBJECT IDENTIFIER ::= { snmpMPDMIB 2 }

-- Statistics for SNMP Messages *************************************

snmpMPDStats           OBJECT IDENTIFIER ::= { snmpMPDMIBObjects 1 }

snmpUnknownSecurityModels OBJECT-TYPE
       SYNTAX       Counter
       ACCESS       read-only
       STATUS       mandatory
       DESCRIPTION "The total number of packets received by the SNMP
                    engine which were dropped because they referenced a
                    securityModel that was not known to or supported by
                    the SNMP engine.
                   "
       ::= { snmpMPDStats 1 }

snmpInvalidMsgs OBJECT-TYPE
       SYNTAX       Counter
       ACCESS       read-only
       STATUS       mandatory
       DESCRIPTION "The total number of packets received by the SNMP
                    engine which were dropped because there were invalid
                    or inconsistent components in the SNMP message.
                   "
       ::= { snmpMPDStats 2 }

snmpUnknownPDUHandlers OBJECT-TYPE
       SYNTAX       Counter
       ACCESS       read-only
       STATUS       mandatory
       DESCRIPTION "The total number of packets received by the SNMP
                    engine which were dropped because the PDU contained
                    in the packet could not be passed to an application
                    responsible for handling the pduType, e.g. no SNMP
                    application had registered for the proper
                    combination of the contextEngineID and the pduType.
                   "
       ::= { snmpMPDStats 3 }

-- Conformance information ******************************************

--   snmpMPDMIBCompliances OBJECT IDENTIFIER ::= {snmpMPDMIBConformance 1}
--   snmpMPDMIBGroups      OBJECT IDENTIFIER ::= {snmpMPDMIBConformance 2}

   -- Compliance statements

--   snmpMPDCompliance MODULE-COMPLIANCE
--       STATUS       mandatory
--       DESCRIPTION "The compliance statement for SNMP entities which
--                    implement the SNMP-MPD-MIB.
--                   "
--       MODULE    -**- this module
--           MANDATORY-GROUPS { snmpMPDGroup }
--       ::= { snmpMPDMIBCompliances 1 }
--
--   snmpMPDGroup OBJECT-GROUP
--       OBJECTS {
--                 snmpUnknownSecurityModels,
--                 snmpInvalidMsgs,
--                 snmpUnknownPDUHandlers
--               }
--       STATUS       mandatory
--       DESCRIPTION "A collection of objects providing for remote
--                    monitoring of the SNMP Message Processing and
--                    Dispatching process.
--                   "
--       ::= { snmpMPDMIBGroups 1 }
END
