ETH-RING-MIB DEFINITIONS ::= BEGIN

-- This SMIv1 module has been generated by smidump 0.4.3.
-- ========================================================================
-- This program contains proprietary information which is a trade secret
-- of Nokia and also is protected as an unpublished work under applicable
-- Copyright laws. Recipient is to retain this program in confidence and
-- is not permitted to use or make copies thereof other than as permitted
-- in a written agreement with Nokia.
-- ========================================================================
--     REVISION    "20160715"
--     DESCRIPTION
--           Version: 3FE69079AAAA_V5.5.01
--           Editor: Murugan Balraj 
--           Changes: 
--             * Update Instance,Path table paramter types and ranges. 
--               EthRingStateType, EthRingDefectStatusType,EthRingRApsLevelType,
--               Dot1agCfmMepIdOrZero,Dot1agCfmMdIndexOrZeroType,Dot1agCfmMaIndexOrZeroType.
--
--     REVISION    "20160330"
--     DESCRIPTION
--           Version: 3FE69079AAAA_V5.5
--           Editor: Soundarya Myneni
--           Changes: 
--             * Introduction of ERPS.
--
-- ==================================================================


IMPORTS
    InterfaceIndex, InterfaceIndexOrZero
        FROM ITF-MIB
    VlanId, VlanIndex
        FROM Q-BRIDGE-MIB
    OBJECT-TYPE
        FROM RFC-1212
    Counter, Gauge
        FROM RFC1155-SMI
    MacAddress, RowStatus, TAddress, TDomain, TimeInterval, TimeStamp, 
    TruthValue
        FROM SNMPv2-TC
    Dot1agCfmMepIdOrZero,Dot1agCfmMdIndexOrZeroType,Dot1agCfmMaIndexOrZeroType 
        FROM IEEE8021-CFM-MIB
    asam                           
        FROM SYSTEM-MIB; 

-- ************************************************************************
-- GENERAL NOTES:

-- ************************************************************************
-- .iso.org.dod.internet.private.enterprises.alcatel.asd.asam.ethRingMIB
-- (.1.3.6.1.4.1.637.61.1.109)

ethRingMIB OBJECT IDENTIFIER ::= { asam 109 }

-- ******************************************************************
-- Textual conventions
-- ******************************************************************

--
--  Few textual conversions
--

Boolean ::= INTEGER (0..1)

EthRingInstanceIdType ::= INTEGER (1..255)

-- EthRingInstanceIdType ::= TEXTUAL-CONVENTION
--     STATUS      mandatory
--     DESCRIPTION 
--         "The value  specifies the instance Id of an Ethernet ring".
--     SYNTAX      INTEGER (1..255) 

 
EthRingIdType ::= INTEGER (1..239)

-- EthRingIdType ::= TEXTUAL-CONVENTION
--     DISPLAY-HINT "d"
--     STATUS      mandatory
--     DESCRIPTION 
--         "The value specifies the index of an Ethernet ring."
--     REFERENCE
--         Draft ITU-T Recommendation G.8032/Y.1344 Version 2
--           Section 3.14, 3.15
--     SYNTAX      INTEGER (1..239) 

EthRingDescriptionType ::= OCTET STRING (SIZE(0..80))

-- EthRingDescriptionType ::= TEXTUAL-CONVENTION
--     DISPLAY-HINT "d"
--     STATUS      mandatory
--     DESCRIPTION 
--          "The value specifies the detailed description of the Ethernet Ring"
--     REFERENCE
--           Draft ITU-T Recommendation G.8032/Y.1344 Version 2
--           Section 3.14, 3.15
--     SYNTAX      OCTET STRING (SIZE(0..80)) 


EthRingAdminStateType ::=
   INTEGER { admin-down(1), admin-up(2) }

-- EthRingAdminStateType ::= TEXTUAL-CONVENTION
--     DISPLAY-HINT "d"
--     STATUS      mandatory
--     DESCRIPTION 
--          "The value specifies the Administrative State of the Ethernet Ring"
--     SYNTAX      INTEGER { admin-down(1), admin-up(2) }

EthRingStateType ::=
   INTEGER { not-started(0),idle(1), protection(2), manual-switch(3), forced-switch(4), pending(5) }

-- EthRingStateType ::= TEXTUAL-CONVENTION
--     DISPLAY-HINT "d"
--     STATUS      mandatory
--     DESCRIPTION
--          "The value specifies the State of the Ethernet Ring Instance"
--     REFERENCE "Draft ITU-T Recommendation G.8032/Y.1344 Version 2
--               Section 3.14, 3.15
--     Special value not-started(0) is a non-standard value which means State 
--     Machine is not started and not in any state."
--           
--     SYNTAX  INTEGER { not-started(0),idle(1), protection(2), manual-switch(3), forced-switch(4), pending(5) }   


EthRingRplNodeType ::=
   INTEGER { rplNone(0),rplOwner(1),rplNeighbor(2),rplNextNeighbour(3) }

-- EthRingRplNodeType ::= TEXTUAL-CONVENTION
--     DISPLAY-HINT "d"
--     STATUS      mandatory
--     DESCRIPTION
--         "The EthRingRplNodeType specifies the Ring Protection Link (RPL)
--          Node type. An object of this type may be assigned to a value of:
--             - rplNone (0)          The Ethernet Ring Node is not designated
--                                    as either an Owner or Neighbor Node.
--             - rplOwner(1)          The Ethernet Ring Node is adjacent to
--                                    the RPL that is responsible for blocking
--                                    its end of the RPL under normal
--                                    conditions. It is the responsibility of
--                                    the rplOwner for activating reversion
--                                    behaviour from protected or MS/FS
--                                    conditions.
--             - rplNeighbor(2)       The Ethernet Ring Node is adjacent to
--                                    the RPL that is responsible for blocking
--                                    its end of the RPL under normal
--                                    conditions in addition to the block by
--                                    the RPL Owner Node. The node is, however,
--                                    not responsibel for activating the
--                                    reversion behavior.
--             - rplNextNeighbour(3)  Ethernet ring nodes connected to the RPL owner
--                                    node or RPL neighbour node, termed as the RPL 
--                                    next-neighbour node. "
--    REFERENCE "Draft ITU-T Recommendation G.8032/Y.1344 Version 2
--               Section 3.14, 3.15"
--    SYNTAX      INTEGER {rplNone(0),rplOwner(1),rplNeighbor(2)
--                rplNextNeighbour(3)}

EthRingDefectStatusType ::= INTEGER (0..3)
     -- Bit-0 dfOP-PM(1)   Defect due to Provisioning Mistmatch
     -- Bit-1 dFOP-TO(2)   Defect due to Failure of Protocol-Timeout

-- EthRingDefectStatusType ::= TEXTUAL-CONVENTION
--     DISPLAY-HINT "d"
--     STATUS      mandatory
--     DESCRIPTION
--         "This Object indicates what are the defects present in Ethernet Ring
--               - dfOP-PM(1)   Defect due to Provisioning Mistmatch
--               - dFOP-TO(2)   Defect due to Failure of Protocol-Timeout"
--     REFERENCE "Draft ITU-T Recommendation G.8032/Y.1344 Version 2
--                Section 3.14, 3.15"
--     SYNTAX BITS {
--                 dfOP-PM(0),
--                 dFOP-TO(1)
--                 }

   
EthRingPathIndexType ::=
   INTEGER { path-A(0), path-B(1) }

-- EthRingPathIndexType ::= TEXTUAL-CONVENTION
--     DISPLAY-HINT "d"
--     STATUS      mandatory
--     DESCRIPTION 
--         "This object specifies unique Ethernet ring path identifier."
--     REFERENCE   
--     SYNTAX    INTEGER { path-A(0), path-B(1) } 

EthRingPathType ::=
   INTEGER { normal(0), rpl-End(1) }

-- EthRingPathType ::= TEXTUAL-CONVENTION
--     DISPLAY-HINT "d"
--     STATUS      mandatory
--     DESCRIPTION
--      "The value of EthRingPathType specifies the Ethernet Ring Node Path
--        acts as an rplEnd or in a normal state 
--     SYNTAX    { normal(0),rpl-End(1) } 


EthRingPathFwdStateType ::=
   INTEGER { blocked(0),unBlocked(1) }

--  EthRingPathFwdStateType ::= TEXTUAL-CONVENTION
--     DISPLAY-HINT "d"
--     STATUS      mandatory
--     DESCRIPTION
--        "The value of EthRingPathFwdStateType indicates whether the Ethernet
--         Ring Node Path blocks the transmission and reception of traffic on the
--         ring port
--     SYNTAX    { blocked(0),unBlocked(1) } 

EthRingApsPduType ::=
   OCTET STRING (SIZE (0|8..32))

--EthRingApsPduType           ::= TEXTUAL-CONVENTION
--   DISPLAY-HINT "1x-1x [1x:1x:1x:1x:1x:1x] 24x-"
--    STATUS      current
--    DESCRIPTION
--        "The EthRingApsPduType specifies the Ring APS specific PDU message
--         information. If the value of this object is an empty string, then
--         no R-APS PDU information is available.
--         The APS pdu uses the following format:
--
--           +=======+=======+===============+===============+===============+
--           |8 7 6 5|4 3 2 1|8 7 6 5 4 3 2 1|8 7 6 ... 3 2 1|8 7 6 ... 3 2 1|
--           |=======+=======+===============+===============+===============+
--           | Rqst/ | sub-  |    Status     | Node ID       | Reserved      |
--           | State | code  +=+=+=+=========+  (6 octets)   |  (24 octets)  |
--           |       |       |R|D|B| status  |               |               |
--           |       |       |B|N|P|   Rsvd  |               |               |
--           |       |       | |F|R|         |               |               |
--           +=======+=======+=+=+=+=========+===============+===============+"
--     REFERENCE "Draft ITU-T Recommendation G.8032/Y.1344 Version 2
--                Section 10.26"
--     SYNTAX    OCTET STRING (SIZE (0|8..32))

EthRingPathControlSwitchType ::=
   INTEGER { none(0),forced-switch(1),manual-switch(2) }

--  EthRingPathControlSwitchType ::= TEXTUAL-CONVENTION
--     DISPLAY-HINT "d"
--     STATUS      mandatory
--     DESCRIPTION
--         "This object is used for operator initiated protection switching.
--               none(0)            The condition when no local protection 
--                                  switching requests are active
--               forced-switch (1)  Forces a block on the ring port where the 
--                                  command is issued.
--               manual-switch (2)  In the absence of a failure or FS,
--                                  this forces a block on the ring port where
--                                  the command is issued."
--     REFERENCE "Draft ITU-T Recommendation G.8032/Y.1344 Version 2
--                Section 3.14, 3.15"
--     SYNTAX  INTEGER { none(0),forced-switch(1),manual-switch(2) }

EthRingPathSFStatusType ::= 
    INTEGER {none(0),ccm-only(1),los-only(2),ccmAndLos(3)}

-- EthRingPathSFStatusType ::= TEXTUAL-CONVENTION
--     DISPLAY-HINT "d"
--     STATUS      mandatory
--     DESCRIPTION
--        "The object indicates the defects which are present in a
--        Particular Path of an Ethernet Ring Instance."
--     SYNTAX   INTEGER {none(0),ccm-only(1),los-only(2),ccmAndLos(3)}  

EthRingRApsLevelType ::= INTEGER (0..7)

-- EthRingRApsLevelType::= TEXTUAL-CONVENTION
--     STATUS      mandatory
--     DESCRIPTION
--         "The value specifies the Level in which the R-APS to be transmitted in a path 
--          by an Ethernet Ring".
--     SYNTAX      INTEGER (0..7)


-- ******************************************************************
-- The Ethernet Ring Instance Table
-- ******************************************************************

-- ******************************************************************
-- The Ethernet Ring Instance Object. This group contains all the
-- MIB objects used to read, create, modify, and delete Ethernet Ring
-- configuration in the MIB.
-- ******************************************************************

ethRingInstanceTable OBJECT-TYPE
    SYNTAX      SEQUENCE OF EthRingInstanceEntry
    ACCESS      not-accessible
    STATUS      mandatory
    DESCRIPTION 
        "The Ethernet Ring Instance Table.     
             ALCATEL NOTE:
             TABLESIZE: DEP (Depends on the Platform) 
             DESCR: "

    ::= { ethRingMIB 1 }

ethRingInstanceEntry OBJECT-TYPE
    SYNTAX      EthRingInstanceEntry
    ACCESS      not-accessible
    STATUS      mandatory
    DESCRIPTION 
        "The Ethernet Ring Instance table entry. This entry will be persist
         after reboot.
         ALCATEL NOTE:
            Row creation : Instantiated as a result of an EthRing creation.
            Row deletion : Deleted as a result of an EthRing deletion. 
            Index usage  : See INDEX below."
    INDEX       { ethRingInstanceId }
    ::= { ethRingInstanceTable 1 }

EthRingInstanceEntry ::= SEQUENCE {
    ethRingInstanceId                EthRingInstanceIdType,
    ethRingId                        EthRingIdType, 
    ethRingDescription               EthRingDescriptionType,
    ethRingRplNodeType               EthRingRplNodeType,
    ethRingAdminStatus               EthRingAdminStateType,
    ethRingState                     EthRingStateType,
    ethRingGuardTime                 INTEGER,
    ethRingRevertTime                INTEGER,
    ethRingHoldOffTimer              INTEGER,
    ethRingNodeId                    MacAddress,
    ethRingTxApsPdu                  EthRingApsPduType,
    ethRingDefectStatus              EthRingDefectStatusType,
    ethRingClear                     Boolean,
    ethRingRowStatus                 RowStatus
}

ethRingInstanceId OBJECT-TYPE
    SYNTAX      EthRingInstanceIdType
    ACCESS      not-accessible
    STATUS      mandatory
    DESCRIPTION
        "The value of this object identifies the instance of an Ethernet ring.
         ALCATEL NOTE:
                ACCESS:     NA       USAGE:      NA
                PERSIST:    YES      INSRVMOD:   NO
                RANGE:      YES      DEFVALUE:   NA
                UNITS:      NA       SPARSE:     NA
                DESCR:      NA"
    ::= { ethRingInstanceEntry 1 }


ethRingId OBJECT-TYPE
    SYNTAX      EthRingIdType
    ACCESS      read-write
    STATUS      mandatory
    DESCRIPTION 
        "The value of this object identifies the Ring ID of an Ethernet ring.
         ALCATEL NOTE:
                ACCESS:     NA       USAGE:      NA
                PERSIST:    YES      INSRVMOD:   NO
                RANGE:      YES      DEFVALUE:   NA
                UNITS:      NA       SPARSE:     NA
                DESCR:      NA"
    ::= { ethRingInstanceEntry 2 }

ethRingDescription OBJECT-TYPE
    SYNTAX      EthRingDescriptionType 
    ACCESS      read-write
    STATUS      mandatory
    DESCRIPTION 
        "The value of this object specifies the description of the Ethernet Ring.
         ALCATEL NOTE:
                ACCESS:     NA       USAGE:      OPT 
                PERSIST:    YES      INSRVMOD:   NO
                RANGE:      NA       DEFVALUE:   NA
                UNITS:      NA       SPARSE:     NO
                DESCR:      NA"
    ::= { ethRingInstanceEntry 3 }

ethRingRplNodeType OBJECT-TYPE
    SYNTAX      EthRingRplNodeType
    ACCESS      read-write
    STATUS      mandatory
    DESCRIPTION 
        "The value of ethRingRplNode object specifies whether this node acts as an RPL Owner,
         Neighbour or none for this Ring Instance.
         ALCATEL NOTE:
                ACCESS:     NA       USAGE:      MAND 
                PERSIST:    YES      INSRVMOD:   NA 
                RANGE:      NA       DEFVALUE:   rplNone
                UNITS:      NA       SPARSE:     NA
                DESCR:      NA"
 DEFVAL     { rplNone }
    ::= { ethRingInstanceEntry 4 }


ethRingAdminStatus OBJECT-TYPE
    SYNTAX      EthRingAdminStateType
    ACCESS      read-write
    STATUS      mandatory
    DESCRIPTION 
        "The value of this object specifies the Administrative state of the Ethernet Ring.
         ALCATEL NOTE:
                ACCESS:     NA       USAGE:      MAND 
                PERSIST:    YES      INSRVMOD:   NO
                RANGE:      NA       DEFVALUE:   admin-down
                UNITS:      NA       SPARSE:     NA
                DESCR:      NA"
    DEFVAL      { admin-down }
    ::= { ethRingInstanceEntry 5 }

ethRingState OBJECT-TYPE
    SYNTAX      EthRingStateType
    ACCESS      read-only
    STATUS      mandatory
    DESCRIPTION 
        "The value of this object specifies the State of the Ethernet Ring.
         The Ring State is not-started when it is admin-down. 
         ALCATEL NOTE:
                ACCESS:     NA       USAGE:      MAND 
                PERSIST:    NO       INSRVMOD:   NO
                RANGE:      NA       DEFVALUE:   not-started 
                UNITS:      NA       SPARSE:     NA
                DESCR:      NA"
    DEFVAL      { not-started }
    ::= { ethRingInstanceEntry 6 }

ethRingGuardTime OBJECT-TYPE
    SYNTAX      INTEGER (10..2000) 
    ACCESS      read-write
    STATUS      mandatory
    DESCRIPTION 
        "The value of GuardTime specifies the guard timer, in milliseconds,
         of a Ring node.The guard timer is used to prevent the
         Ethernet Ring node from acting upon outdated R-APS messages and 
         prevent the possibility of forming a closed loop.
         While the guard timer is running, any received R-APS Request/State 
         and Status information is blocked and not forwarded to the Priority
         Logic.When the guard timer is not running, the R-APS Request/State 
         and Status information is forwarded unchanged.
         Multiples of 10ms values are accepted.
         ALCATEL NOTE:
            ACCESS:      NA            USAGE:       NA
            PERSIST:     YES           INSRVMOD:    NA
            RANGE:       NA            DEFVALUE:    500
            UNITS:       ms            SPARSE:      NA
            DESCR:       NA"
    DEFVAL      { 500 }
    ::= { ethRingInstanceEntry 7 }

ethRingRevertTime OBJECT-TYPE
    SYNTAX      INTEGER (0 |60..720)
    ACCESS      read-write
    STATUS      mandatory
    DESCRIPTION 
        "The value of EthRingRevertTime specifies the Wait-To-Restore (WTR) timer,
         in seconds, of a Ring node.The WTR timer is used to prevent 
         frequent operation of the protection switching due to intermittent signal
         failure defects.Setting EthRingRevertTime to the value zero (0) puts the 
         Ethernet Ring into a non-revertive mode.
         Multiples of 60 Sec's values are accepted.
         ALCATEL NOTE:
            ACCESS:      NA            USAGE:       NA
            PERSIST:     YES           INSRVMOD:    NA
            RANGE:       NA            DEFVALUE:    300
            UNITS:       sec           SPARSE:      NA
            DESCR:       NA"
    DEFVAL     { 300 }
    ::= { ethRingInstanceEntry 8 }

ethRingHoldOffTimer OBJECT-TYPE
    SYNTAX      INTEGER (0..10000)
    ACCESS      read-write
    STATUS      mandatory
    DESCRIPTION
        "Hold Off Timer is required in order to coordinate the timing of protection
         switches at multiple layers.When a new defect or more severe defect occurs
         (new SF), this event is not to be reported immediately to protection switching
         if the provisioned hold-off timer value is non-zero. Instead, the hold-off
         timer is started. When the hold-off timer expires, the trail that started the
         timer is checked as to whether a defect still exists. If one does exist, that
         defect is reported to protection switching.
         The reported defect need not be the same one that started the timer.
         Multiples of 100ms values are accepted.

         ALCATEL NOTE:
                ACCESS:     NA       USAGE:      MAND
                PERSIST:    YES      INSRVMOD:   NA
                RANGE:      NA       DEFVALUE:   0
                UNITS:      ms       SPARSE:     NA
                DESCR:      NA"
    DEFVAL     { 0 }
    ::= { ethRingInstanceEntry 9 }

ethRingNodeId OBJECT-TYPE
    SYNTAX      MacAddress
    ACCESS      read-write
    STATUS      mandatory
    DESCRIPTION 
        "The value of ethRingNodeId specifies the Ethernet Ring Node ID. 
         Setting a value of 00:00:00:00:00:00 resets this object value ,
         to the Node Mac Address.
         ALCATEL NOTE:
                ACCESS:     NA       USAGE:      MAND 
                PERSIST:    YES      INSRVMOD:   NA 
                RANGE:      NA       DEFVALUE:   NA 
                UNITS:      NA       SPARSE:     NA
                DESCR:      NA"
    ::= { ethRingInstanceEntry 10 }

ethRingTxApsPdu OBJECT-TYPE
    SYNTAX      EthRingApsPduType
    ACCESS      read-only
    STATUS      mandatory
    DESCRIPTION 
        "The value of this object indicates the contents of the last R-APS PDU transmitted on
         the Ethernet Ring.If the value of an object of  this type is the empty  string, then
         no Ring APS specific PDU message is available.
         ALCATEL NOTE:
                ACCESS:     NA       USAGE:      MAND 
                PERSIST:    NO       INSRVMOD:   NA 
                RANGE:      NA       DEFVALUE:   NA
                UNITS:      NA       SPARSE:     NA
                DESCR:      NA"

     ::= { ethRingInstanceEntry 11 }

ethRingDefectStatus OBJECT-TYPE
    SYNTAX      EthRingDefectStatusType
    ACCESS      read-only
    STATUS      mandatory
    DESCRIPTION 
        "This object indicates the defects present in this Ethernet Ring Instance.
         BIT(0) : when this bit is set to (value 1), it indicates dfOP-PM.
         BIT(1) : when this bit is set to (value 2), it indicates dfOP-TO.
         ALCATEL NOTE:
                ACCESS:     NA       USAGE:      MAND 
                PERSIST:    NO       INSRVMOD:   NA 
                RANGE:      NA       DEFVALUE:   NA
                UNITS:      NA       SPARSE:     NA
                DESCR:      NA
        "
     ::= { ethRingInstanceEntry 12 }

ethRingClear OBJECT-TYPE
    SYNTAX      Boolean
    ACCESS      write-only
    STATUS      mandatory
    DESCRIPTION
        "This object can be used to execute an administrative clear command on the Ring 
         Instance. It is used for the following operations
	 a. Clearing an active local administrative command (e.g., FS or MS). 
         b. Triggering reversion before the wait to restore (WTR) or wait to block
            (WTB) timer expires in the case of revertive operation.
	 c. Triggering reversion in the case of non-revertive operation
 
         ALCATEL NOTE:
                ACCESS:     NA       USAGE:      MAND 
                PERSIST:    NO       INSRVMOD:   NA 
                RANGE:      NA       DEFVALUE:   NA
                UNITS:      NA       SPARSE:     NA
                DESCR:      NA"

     ::= { ethRingInstanceEntry 13 }

ethRingRowStatus OBJECT-TYPE
    SYNTAX      RowStatus
    ACCESS      read-write
    STATUS      mandatory
    DESCRIPTION 
         "The Status of the Row.
         ALCATEL NOTE:
                ACCESS:     NA       USAGE:      MAND 
                PERSIST:    NO       INSRVMOD:   NA 
                RANGE:      NA       DEFVALUE:   NA
                UNITS:      NA       SPARSE:     NA
                DESCR:      NA"

     ::= { ethRingInstanceEntry 14 }


-- ******************************************************************
-- The Ethernet Ring Path Object. This group contains all the
-- MIB objects used to read, create, modify, and delete Ethernet Ring
-- Path in the MIB.
-- ******************************************************************

-- ******************************************************************
-- The Ethernet Ring Path Table
-- ******************************************************************

ethRingPathTable OBJECT-TYPE
    SYNTAX      SEQUENCE OF EthRingPathEntry
    ACCESS      not-accessible
    STATUS      mandatory
    DESCRIPTION 
        "The Ethernet Ring Path Table.  Each row in the table
         represents a Path.
         ALCATEL NOTE:
         TABLESIZE: DEP (Depends on the Platform)
         DESCR:"
    ::= { ethRingMIB 2 }

ethRingPathEntry OBJECT-TYPE
    SYNTAX      EthRingPathEntry
    ACCESS      not-accessible
    STATUS      mandatory
    DESCRIPTION 
        "The ethRingPathEntry table entry.
         ALCATEL NOTE:
            Row creation : Instantiated as a result of an Path Creation.
            Row deletion : Deleted as a result of an Path deletion. 
            Index usage  : See INDEX below."

    INDEX       { ethRingInstanceId, ethRingPathIndex }
    ::= { ethRingPathTable 1 }

EthRingPathEntry ::= SEQUENCE {
    ethRingPathIndex                           EthRingPathIndexType,
    ethRingPathIfIndex                         InterfaceIndexOrZero,
    ethRingPathDescription                     EthRingDescriptionType,
    ethRingPathType                            EthRingPathType,
    ethRingPathRapsTag                         VlanIndex,
    ethRingPathRapsLevel                       EthRingRApsLevelType,
    ethRingPathCcMdIndex                       Dot1agCfmMdIndexOrZeroType,
    ethRingPathCcMaIndex                       Dot1agCfmMaIndexOrZeroType,
    ethRingPathCcMepId                         Dot1agCfmMepIdOrZero, 
    ethRingPathControlSwitch                   EthRingPathControlSwitchType,
    ethRingPathFwdState                        EthRingPathFwdStateType,
    ethRingPathFwdStateChgTime                 TimeStamp,
    ethRingPathRxApsPdu                        EthRingApsPduType,
    ethRingPathSFStatus                        EthRingPathSFStatusType,
    ethRingPathRowStatus                       RowStatus
}

ethRingPathIndex OBJECT-TYPE
    SYNTAX      EthRingPathIndexType
    ACCESS      not-accessible
    STATUS      mandatory
    DESCRIPTION 
        "This object specifies unique Ethernet Ring path identifier.
	 Along with ethRingInstanceId refers to a unique path on the
         Ring Node.
         ALCATEL NOTE:
                ACCESS:     NA       USAGE:      NA
                PERSIST:    YES      INSRVMOD:   NO
                RANGE:      YES      DEFVALUE:   NA
                UNITS:      NA       SPARSE:     NA
                DESCR:      NA"
    ::= { ethRingPathEntry 1 }

ethRingPathIfIndex OBJECT-TYPE
    SYNTAX      InterfaceIndexOrZero
    ACCESS      read-write
    STATUS      mandatory
    DESCRIPTION 
        "This object specifies the IfIndex of the bridge port on which 
         the path is configured.
         ALCATEL NOTE:
                ACCESS:     NA       USAGE:      NA
                PERSIST:    YES      INSRVMOD:   NO
                RANGE:      YES      DEFVALUE:   NA
                UNITS:      NA       SPARSE:     NA
                DESCR:      NA"
    ::= { ethRingPathEntry 2 }

ethRingPathDescription OBJECT-TYPE
    SYNTAX      EthRingDescriptionType 
    ACCESS      read-write
    STATUS      mandatory
    DESCRIPTION 
        "This object specifies the description of the 
         Ethernet Ring Path.
         ALCATEL NOTE:
                ACCESS:     NA       USAGE:      OPT 
                PERSIST:    YES      INSRVMOD:   NO
                RANGE:      NA       DEFVALUE:   NA
                UNITS:      NA       SPARSE:     NO
                DESCR:      NA"
    ::= { ethRingPathEntry 3 }

ethRingPathType OBJECT-TYPE
    SYNTAX      EthRingPathType
    ACCESS      read-write
    STATUS      mandatory
    DESCRIPTION 
        "This object indicates whether the Ring Path is part of an RPL link.
         ALCATEL NOTE:
            ACCESS:      NA            USAGE:       NA
            PERSIST:     YES           INSRVMOD:    NA
            RANGE:       NA            DEFVALUE:    normal
            UNITS:       NA            SPARSE:      NA
            DESCR:       NA"
    DEFVAL      { normal } 
    ::= { ethRingPathEntry 4 }


ethRingPathRapsTag OBJECT-TYPE
    SYNTAX      VlanIndex
    ACCESS      read-write
    STATUS      mandatory
    DESCRIPTION 
        "This object indicates the Vlanindex used for encapsulation of R-APS messages.
         ALCATEL NOTE:
                ACCESS:     NA       USAGE:      NA
                PERSIST:    YES      INSRVMOD:   NO
                RANGE:      YES      DEFVALUE:   NA
                UNITS:      NA       SPARSE:     NA
                DESCR:      NA"
    ::= { ethRingPathEntry 5 }

ethRingPathRapsLevel OBJECT-TYPE
    SYNTAX      EthRingRApsLevelType
    ACCESS      read-write
    STATUS      mandatory
    DESCRIPTION 
        "This object indicates the MD Level at which R-APS messages are Transmitted or Processed.
         ALCATEL NOTE:
                ACCESS:     NA       USAGE:      NA
                PERSIST:    YES      INSRVMOD:   NO
                RANGE:      YES      DEFVALUE:   NA
                UNITS:      NA       SPARSE:     NA
                DESCR:      NA"
    ::= { ethRingPathEntry 6 }

ethRingPathCcMdIndex OBJECT-TYPE
   SYNTAX       Dot1agCfmMdIndexOrZeroType
    ACCESS      read-write
    STATUS      mandatory
    DESCRIPTION
       "This object specifies the CFM Maintenance Domain Index 
        corresponding to the MEP used for CCM monitoring to detect
        Local SF.
        ALCATEL NOTE:
                ACCESS:     NA       USAGE:      NA
                PERSIST:    YES      INSRVMOD:   NO
                RANGE:      YES      DEFVALUE:   0 
                UNITS:      NA       SPARSE:     NA
                DESCR:      NA"
    DEFVAL     { 0 }
    ::= { ethRingPathEntry 7 }

ethRingPathCcMaIndex OBJECT-TYPE
   SYNTAX       Dot1agCfmMaIndexOrZeroType
    ACCESS      read-write
    STATUS      mandatory
    DESCRIPTION
       "This object specifies the CFM Maintenance Association Index 
        corresponding to the MEP used for CCM monitoring to detect
        Local SF.
        ALCATEL NOTE:
                ACCESS:     NA       USAGE:      NA
                PERSIST:    YES      INSRVMOD:   NO
                RANGE:      YES      DEFVALUE:   0 
                UNITS:      NA       SPARSE:     NA
                DESCR:      NA"
    DEFVAL     { 0 }
    ::= { ethRingPathEntry 8 }

ethRingPathCcMepId OBJECT-TYPE
   SYNTAX       Dot1agCfmMepIdOrZero 
    ACCESS      read-write
    STATUS      mandatory
    DESCRIPTION
       "This object specifies the CFM Maintenance End Point Index 
        corresponding to the MEP used for CCM monitoring to detect 
        Local SF.
        ALCATEL NOTE:
                ACCESS:     NA       USAGE:      NA
                PERSIST:    YES      INSRVMOD:   NO
                RANGE:      YES      DEFVALUE:   0 
                UNITS:      NA       SPARSE:     NA
                DESCR:      NA"
    DEFVAL     { 0 }
    ::= { ethRingPathEntry 9 }
  
ethRingPathControlSwitch OBJECT-TYPE
   SYNTAX        EthRingPathControlSwitchType
   ACCESS        write-only
   STATUS        mandatory
   DESCRIPTION
      "This object is used for operator initiated protection switching.
       a. Forced switch (FS) -  Forces a block on the ring port where the
          command is issued.
       b. Manual switch (MS) - In the absence of a failure or FS, forces a
          block on the ring port where the command is issued.
       ALCATEL NOTE:
                ACCESS:     NA       USAGE:      MAND 
                PERSIST:    NO       INSRVMOD:   NA 
                RANGE:      NA       DEFVALUE:   none 
                UNITS:      NA       SPARSE:     NA
                DESCR:      NA"
     DEFVAL     { none }
     ::= { ethRingPathEntry 10 }

ethRingPathFwdState OBJECT-TYPE
    SYNTAX      EthRingPathFwdStateType
    ACCESS      read-only
    STATUS      mandatory
    DESCRIPTION 
        "This object  indicates whether the Ethernet Ring  Path blocks the 
         transmission and reception of traffic.
         ALCATEL NOTE:
            ACCESS:      NA            USAGE:       NA
            PERSIST:     NO            INSRVMOD:    NA
            RANGE:       NA            DEFVALUE:    unBlocked 
            UNITS:       NA            SPARSE:      NA
            DESCR:       NA" 
     DEFVAL     { unBlocked }
    ::= { ethRingPathEntry 11 }

ethRingPathFwdStateChgTime OBJECT-TYPE
    SYNTAX      TimeStamp
    ACCESS      read-only
    STATUS      mandatory
    DESCRIPTION 
        "This object indicates the time since startup,this Ethernet Ring
         path experienced a change in the forwarding state.
         ALCATEL NOTE:
            ACCESS:      NA            USAGE:       NA
            PERSIST:     NO            INSRVMOD:    NA
            RANGE:       NA            DEFVALUE:    NA
            UNITS:       NA            SPARSE:      NA
            DESCR:       NA"
    ::= { ethRingPathEntry 12 }

ethRingPathRxApsPdu OBJECT-TYPE
    SYNTAX      EthRingApsPduType
    ACCESS      read-only
    STATUS      mandatory
    DESCRIPTION 
        "The value of this object indicates the contents of the last received 
         R-APS PDU on this Ring Path. If the value of this object is an empty
         string, then no R-APS PDU information is available.
        ALCATEL NOTE:
                ACCESS:     NA       USAGE:      MAND 
                PERSIST:    NO       INSRVMOD:   NA 
                RANGE:      NA       DEFVALUE:   NA
                UNITS:      NA       SPARSE:     NA
                DESCR:      NA"

     ::= { ethRingPathEntry 13 }

ethRingPathSFStatus OBJECT-TYPE
   SYNTAX        EthRingPathSFStatusType
   ACCESS        read-only
   STATUS        mandatory
   DESCRIPTION
   "The object indicates the defects which are present on this Ring Path 
    contributing to a Signal Failure.
    ALCATEL NOTE:
                ACCESS:     NA       USAGE:      MAND
                PERSIST:    NO       INSRVMOD:   NA
                RANGE:      NA       DEFVALUE:   none 
                UNITS:      NA       SPARSE:     NA
                DESCR:      NA"

     DEFVAL     { none }
     ::= { ethRingPathEntry 14 }

ethRingPathRowStatus OBJECT-TYPE
    SYNTAX      RowStatus
    ACCESS      read-write
    STATUS      mandatory
    DESCRIPTION 
        "The Status of the Row.
         ALCATEL NOTE:
                ACCESS:     NA       USAGE:      MAND 
                PERSIST:    NO       INSRVMOD:   NA 
                RANGE:      NA       DEFVALUE:   NA
                UNITS:      NA       SPARSE:     NA
                DESCR:      NA"

     ::= { ethRingPathEntry 15 }

-- ******************************************************************
-- The Ethernet Ring Data Vlan Object. This group contains all the
-- MIB objects used to read, create and delete Ethernet Ring
-- Vlan in the MIB.
-- ******************************************************************

-- ******************************************************************
-- The Ethernet Ring Data Vlan Table
-- ******************************************************************

ethRingDataVlanTable OBJECT-TYPE
    SYNTAX      SEQUENCE OF EthRingDataVlanEntry
    ACCESS      not-accessible
    STATUS      mandatory
    DESCRIPTION 
       "The EthRingDataVlan Table.Table consists of Start and End Vlan Ids 
        where Multiple VLAN ranges can be attached to a Ring instance
        ALCATEL NOTE:
        TABLESIZE: DEP (Depends on the Platform)
        DESCR:"
    ::= { ethRingMIB 3 }

ethRingDataVlanEntry OBJECT-TYPE
    SYNTAX      EthRingDataVlanEntry
    ACCESS      not-accessible
    STATUS      mandatory
    DESCRIPTION 
       "The EthRingDataVlan Table Entry 
        ALCATEL NOTE:
        Row creation : Instantiated as a result of a Vlan Range attached to a Ring Instance.
        Row deletion : Deleted as a result of a Vlan Range detached from a Ring Instance. 
        Index usage  : See INDEX below."
    INDEX {ethRingInstanceId, ethRingDataVlanStartId , ethRingDataVlanEndId}
    ::= { ethRingDataVlanTable 1 }

EthRingDataVlanEntry ::= SEQUENCE {
    ethRingDataVlanStartId                         VlanId,
    ethRingDataVlanEndId                           VlanId,
    ethRingDataVlanRowStatus                       RowStatus
}

ethRingDataVlanStartId OBJECT-TYPE
    SYNTAX      VlanId
    ACCESS      not-accessible
    STATUS      mandatory
    DESCRIPTION 
       " This object defines the start id of a list of traffic VLANs 
         attached  to a Ring instance.Protection supported only at the Outer Vlan Level.
         S:0,C are outer VLAN's and it is treated same.
         Eg : (100:0) , 100 are treated as Outer VLAN 100. 
         ALCATEL NOTE:
         ACCESS:     NA       USAGE:      NA
         PERSIST:    YES      INSRVMOD:   NO
         RANGE:      NA       DEFVALUE:   NA
         UNITS:      NA       SPARSE:     NA
         DESCR:      NA"

    ::= { ethRingDataVlanEntry 1 }

ethRingDataVlanEndId OBJECT-TYPE
    SYNTAX      VlanId
    ACCESS      not-accessible
    STATUS      mandatory
    DESCRIPTION 
       " This object defines the End id of a list of traffic VLANs
         attached  to a Ring instance.
         Protection supported only at the Outer Vlan Level.
         S:0,C are outer VLAN's and it is treated same.
         Eg : (100:0),100 are treated as Outer VLAN 100.

         ALCATEL NOTE:
         ACCESS:     NA       USAGE:      NA
         PERSIST:    YES      INSRVMOD:   NO
         RANGE:      NA       DEFVALUE:   NA
         UNITS:      NA       SPARSE:     NA
         DESCR:      NA"
    
    ::= { ethRingDataVlanEntry 2 }

ethRingDataVlanRowStatus OBJECT-TYPE
    SYNTAX      RowStatus
    ACCESS      read-write
    STATUS      mandatory
    DESCRIPTION 
        "The Status of the Row.
         ALCATEL NOTE:
         ACCESS:     NA       USAGE:      MAND 
         PERSIST:    NO       INSRVMOD:   NA 
         RANGE:      NA       DEFVALUE:   NA
         UNITS:      NA       SPARSE:     NA                                                                                         DESCR:      NA"
 
    ::= { ethRingDataVlanEntry 3 }

END -- end of module ETH-RING-MIB.
