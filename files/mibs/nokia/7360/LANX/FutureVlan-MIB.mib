--
-- This SMIv1 module has been generated by smidump 0.4.8. Do not edit.
--

FutureVlan-MIB DEFINITIONS ::= BEGIN

IMPORTS
    PortList
        FROM Q-BRIDGE-MIB
    OBJECT-TYPE
        FROM RFC-1212
    Gauge, IpAddress, enterprises
        FROM RFC1155-SMI
    SnmpAdminString
        FROM SNMP-FRAMEWORK-MIB
    DisplayString, MacAddress, RowStatus, TruthValue
        FROM SNMPv2-TC;

futureVlanMIB OBJECT IDENTIFIER
    ::= { enterprises futuresoftware(2076) 65 }

-- futureVlanMIB MODULE-IDENTITY
--     LAST-UPDATED "200203060000Z"
--     ORGANIZATION 
--         "FUTURE SOFTWARE LIMITED"
--     CONTACT-INFO 
--         "FUTURE SOFTWARE LIMITED 
--          481 Mount Road 
--          Madras - 600 035 
--          Phone : +91-44-433 0550"
--     DESCRIPTION 
--         "||||||"
--     REVISION    "200203060000Z"
--     DESCRIPTION 
--         "The initial revision of this MIB module was published as
--          RFC 1450."
--     ::= { enterprises futuresoftware(2076) 65 }


VlanId ::=
    INTEGER (1..4094)

-- VlanId ::= TEXTUAL-CONVENTION
--     STATUS      mandatory
--     DESCRIPTION 
--         "A 12-bit VLAN ID used in the VLAN Tag header."
--     SYNTAX      INTEGER (1..4094)

VlanList ::=
    OCTET STRING

-- VlanList ::= TEXTUAL-CONVENTION
--     STATUS      mandatory
--     DESCRIPTION 
--         "Each octet within this value specifies a set of eight
--          vlans, with the first octet specifying vlans 1 through
--          8, the second octet specifying vlans 9 through 16, etc.
--          Within each octet, the most significant bit represents
--          the lowest numbered vlan, and the least significant bit
--          represents the highest numbered vlan.  Thus, each vlan
--          of the bridge is represented by a single bit within the
--          value of this object.  If that bit has a value of '1'
--          then that vlan is included in the set of vlans; the vlan
--          is not included if its bit has a value of '0'."
--     SYNTAX      OCTET STRING

EnabledStatus ::=
    INTEGER { enabled(1), disabled(2) }

-- EnabledStatus ::= TEXTUAL-CONVENTION
--     STATUS      mandatory
--     DESCRIPTION 
--         "A simple status value for the object."
--     SYNTAX      INTEGER
--                   { enabled(1), disabled(2) }

dot1qFutureVlan OBJECT IDENTIFIER
    ::= { futureVlanMIB 1 }

fsDot1qFutureVlanStatus OBJECT-TYPE
    SYNTAX      EnabledStatus
    ACCESS      read-write
    STATUS      mandatory
    DESCRIPTION 
        "The administrative status requested by management for the Vlan 
         feature. The value enabled(1) indicates that Vlan should be enabled  
         in the device on all ports. The value disabled(2) indicates that 
         Vlan should be disabled in the device on all ports. The object can 
         be set to disabled if and only if, dot1qGvrpStatus and dot1dGmrpStatus  
         are disabled. The object should NOT be enabled before setting  
         'dot1qFutureVlanType' and 'dot1qFutureVlanLearningType'.
         	ALCATEL NOTE:
         	      	ACCESS:      NA           USAGE:       NA
               	PERSIST:     YES          INSRVMOD:    YES
               	RANGE:       1,2          DEFVALUE:    2
               	UNITS:       NA           SPARSE:      NA
               	DESCR:       NA"
    ::= { dot1qFutureVlan 1 }

fsDot1qFutureVlanMacBasedOnAllPorts OBJECT-TYPE
    SYNTAX      EnabledStatus
    ACCESS      read-write
    STATUS      mandatory
    DESCRIPTION 
        "This object is only used to enable/disable the mac based type on all ports
         of dot1qFutureVlanPortMacBasedClassification
         	ALCATEL NOTE:
         	      	ACCESS:      NA           USAGE:       NA
              	PERSIST:     YES          INSRVMOD:    YES
              	RANGE:       1,2          DEFVALUE:    2
              	UNITS:       NA           SPARSE:      NA
              	DESCR:       This object is not used by Alcatel"
    ::= { dot1qFutureVlan 2 }

fsDot1qFutureVlanPortProtoBasedOnAllPorts OBJECT-TYPE
    SYNTAX      EnabledStatus
    ACCESS      read-write
    STATUS      mandatory
    DESCRIPTION 
        "This object is only used to enable/disable the mac based type on all ports
         of dot1qFutureVlanPortPortProtoBasedClassification
         	ALCATEL NOTE:
         	      	ACCESS:      NA           USAGE:       NA
              	PERSIST:     YES          INSRVMOD:    YES
              	RANGE:       1,2          DEFVALUE:    2
              	UNITS:       NA           SPARSE:      NA
              	DESCR:       This object is not used by Alcatel"
    ::= { dot1qFutureVlan 3 }

fsDot1qFutureVlanLearningType OBJECT-TYPE
    SYNTAX      INTEGER { ivl(1), svl(2), hybrid(3) }
    ACCESS      read-write
    STATUS      mandatory
    DESCRIPTION 
        "The type of the Vlan learning mode. This object must be set before 
         setting dot1qFutureVlanStatus. Setting of this object when  
         dot1qFutureVlanStatus is 'enabled' is disallowed. If Vlan Learning 
         Type is to be changed, then dot1qFutureVlanStatus must be first disabled 
         and then enabled.
         	ALCATEL NOTE:
         	      	ACCESS:      NA           USAGE:       NA
               	PERSIST:     YES          INSRVMOD:    YES
               	RANGE:       NA           DEFVALUE:    1
               	UNITS:       NA           SPARSE:      NA
               	DESCR:       This object is not used by Alcatel"
    ::= { dot1qFutureVlan 4 }

fsDot1qFutureVlanShutdownStatus OBJECT-TYPE
    SYNTAX      TruthValue
    ACCESS      read-write
    STATUS      mandatory
    DESCRIPTION 
        "The administrative shutdown status requested by management for Vlan  
         The value true(1) indicates that Vlan should be shutdown  
         in the device on all ports. All memory will be released. 
         The value false(2) indicates that Vlan should be active in the device  
         on all ports.
         	ALCATEL NOTE:
         	      	ACCESS:      RO           USAGE:       NA
               	PERSIST:     NO           INSRVMOD:    NO
               	RANGE:       1,2          DEFVALUE:    NA
               	UNITS:       NA           SPARSE:      NA
               	DESCR:       NA"
    DEFVAL      { false }
    ::= { dot1qFutureVlan 5 }

fsDot1qFutureGarpShutdownStatus OBJECT-TYPE
    SYNTAX      TruthValue
    ACCESS      read-write
    STATUS      mandatory
    DESCRIPTION 
        "The administrative status requested by management for GARP  
         The value true(1) indicates that GARP should be shutdown  
         in the device on all ports. All memory will be released. 
         The value false(2) indicates that GARP should be active in  
         the device on all ports. This object can be set to true only  
         when none of the Garp applications (GVRP, GMRP) are enabled. 
         Whenever Garp is enabled after shutdown, Gvrp and Gmrp must 
         be enabled explicitly.
         	ALCATEL NOTE:
         	      	ACCESS:      NA           USAGE:       NA
               	PERSIST:     YES          INSRVMOD:    YES
               	RANGE:       1,2          DEFVALUE:    2
               	UNITS:       NA           SPARSE:      NA
               	DESCR:       NA"
    DEFVAL      { false }
    ::= { dot1qFutureVlan 6 }

fsDot1qFutureVlanDebug OBJECT-TYPE
    SYNTAX      INTEGER
    ACCESS      read-write
    STATUS      mandatory
    DESCRIPTION 
        "Enables the tracing in the selected submodule in VLAN. A 32 bit integer
         is used to store the Tracing level in the specified module.
          Different Tracing Levels -
            BIT 0 - Initialisation and Shutdown Trace.
            BIT 1 - Management trace.
            BIT 2 - Data path trace.
            BIT 3 - Control Plane trace.
            BIT 4 - Packet Dump.
            BIT 5 - OS Resource trace.
            BIT 6 - All Failure trace (All failures including Packet Validation)
            BIT 7 - Buffer Trace.
         
          Different submodule Tracing -
            BIT 16 - Tracing in VLAN module.
            BIT 17 - Tracing in VLAN Priority module.
            BIT 18 - Tracing in GARP module.   
            BIT 19 - Tracing in GMRP module.  
            BIT 20 - Tracing in GVRP module.   
         
          The remaining bits are reserved. The combination of levels and submodules 
          are allowed i.e. Tracing can be allowed at all failure and data path 
          level in All submodules by setting the BIT appropriately.
          For Example, setting the debug value to the following bit stream, 
             00000000000000010000000000000100 will enable data path trace 
          prints in VLAN module. Multiple submodules and multiple levels can
          be combined by setting the corresponding bits.
          For Example, setting the debug value to the following bit stream,
             00000000000001010000000000001100 will enable data path and 
          control plane trace prints in VLAN and GARP modules.
          
          Note : BIT0 is the least significant bit and BIT31 is the most
          significant bit.
         	ALCATEL NOTE:
         	      	ACCESS:      NA           USAGE:       NA
               	PERSIST:     YES          INSRVMOD:    YES
               	RANGE:       NA           DEFVALUE:    0
               	UNITS:       NA           SPARSE:      NA
               	DESCR:       This object is not used by Alcatel"
    ::= { dot1qFutureVlan 7 }

fsDot1qFutureVlanPortTable OBJECT-TYPE
    SYNTAX      SEQUENCE OF FsDot1qFutureVlanPortEntry
    ACCESS      not-accessible
    STATUS      mandatory
    DESCRIPTION 
        "Table containing the port type information.
         ALCATEL NOTE:
             	TABLESIZE: DEP 
            	DESCR:	DEP(TABLESIZE) The size of the table is the maximum number of ports available
         			in the system. This value can be obtained from the object 
         			issSystemNumberOfPorts in fsiss.mib."
    ::= { dot1qFutureVlan 8 }

fsDot1qFutureVlanPortEntry OBJECT-TYPE
    SYNTAX      FsDot1qFutureVlanPortEntry
    ACCESS      not-accessible
    STATUS      mandatory
    DESCRIPTION 
        "Entry indicating the type of the port.
         Row creation : Entries are created during system start-up.
         Row deletion : Entries cannot be deleted
         Index usage : the index is the vlan port.
         Note that entries will be presented to the SNMP manager in full
         lexicographical order :  sorted on vlan port."
    INDEX       { fsDot1qFutureVlanPort }
    ::= { fsDot1qFutureVlanPortTable 1 }

FsDot1qFutureVlanPortEntry ::= SEQUENCE {
    fsDot1qFutureVlanPort                               INTEGER,
    fsDot1qFutureVlanPortType                           INTEGER,
    fsDot1qFutureVlanPortMacBasedClassification         EnabledStatus,
    fsDot1qFutureVlanPortPortProtoBasedClassification   EnabledStatus,
    fsDot1qFutureVlanPortDTModeIgnoreTag                INTEGER,
    fsDot1qFutureVlanPortDTModeTPID                     INTEGER,
    fsDot1qFutureVlanPortDTModePBitCopy                 INTEGER
}

fsDot1qFutureVlanPort OBJECT-TYPE
    SYNTAX      INTEGER (1..24)
    ACCESS      not-accessible
    STATUS      mandatory
    DESCRIPTION 
        "The port number of the port for which this entry applies.
         ALCATEL NOTE:
               	ACCESS:      NA           USAGE:       NA
            	PERSIST:     YES          INSRVMOD:    NA
            	RANGE:       NA           DEFVALUE:    NA
            	UNITS:       NA           SPARSE:      NO
            	DESCR:       NA"
    ::= { fsDot1qFutureVlanPortEntry 1 }

fsDot1qFutureVlanPortType OBJECT-TYPE
    SYNTAX      INTEGER { accessPort(1), trunkPort(2), hybridPort(3) }
    ACCESS      read-write
    STATUS      mandatory
    DESCRIPTION 
        "The type of the port is by default
         hybrid port. An access port can  
         accept and send only untagged frames.
         When configured as a trunk port, port is added as 
         member of all the existing Vlans and also for any new vlan
         created. A hybrid port can send or accept
         both tagged and untagged frames
         	ALCATEL NOTE:
         	      	ACCESS:      NA           USAGE:       NA
              	PERSIST:     YES          INSRVMOD:    YES
              	RANGE:       NA           DEFVALUE:    NA
              	UNITS:       NA           SPARSE:      NO
              	DESCR:       NA"
    DEFVAL      { hybridPort }
    ::= { fsDot1qFutureVlanPortEntry 2 }

fsDot1qFutureVlanPortMacBasedClassification OBJECT-TYPE
    SYNTAX      EnabledStatus
    ACCESS      read-write
    STATUS      mandatory
    DESCRIPTION 
        "Object to expilicitly enable/disable the Mac based Classification 
         on port. This can be independently set without 
         any dependency in available configuration of
          dot1qFutureVlanMacBasedOnAllPorts 
         	ALCATEL NOTE:
         	      	ACCESS:      NA           USAGE:       NA
               	PERSIST:     YES          INSRVMOD:    YES
               	RANGE:       1,2          DEFVALUE:    2
               	UNITS:       NA           SPARSE:      NO
               	DESCR:       This object is not used by Alcatel"
    ::= { fsDot1qFutureVlanPortEntry 3 }

fsDot1qFutureVlanPortPortProtoBasedClassification OBJECT-TYPE
    SYNTAX      EnabledStatus
    ACCESS      read-write
    STATUS      mandatory
    DESCRIPTION 
        "Object to expilicitly enable/disable the port and protocol
         Classification on port. This can be independently set without 
         any dependency in available configuration of
          dot1qFutureVlanPortProtoBasedOnAllPorts 
         	ALCATEL NOTE:
         	      	ACCESS:      NA           USAGE:       NA
               	PERSIST:     YES          INSRVMOD:    YES
               	RANGE:       1,2          DEFVALUE:    2
               	UNITS:       NA           SPARSE:      NO
               	DESCR:       This object is not used by Alcatel"
    ::= { fsDot1qFutureVlanPortEntry 4 }

fsDot1qFutureVlanPortDTModeIgnoreTag OBJECT-TYPE
    SYNTAX      INTEGER { enabled(1), disabled(2) }
    ACCESS      read-write
    STATUS      mandatory
    DESCRIPTION 
        "This bit should be set for 802.1q in 802.1q double
         tagging mode of operation. If set to enabled(1), then
         LANX will always treat incoming packets as untagged
         frames and inserts a SPVID tag into the incoming packet.
         If set to disabled (2), then LANX matches for TPID, if not
         found then frame is treated as untagged frame. 
         
         	ALCATEL NOTE:
         	      	ACCESS:      NA           USAGE:       NA
              	PERSIST:     YES          INSRVMOD:    YES
              	RANGE:       NA           DEFVALUE:    NA
              	UNITS:       NA           SPARSE:      NO
              	DESCR:       NA"
    DEFVAL      { disabled }
    ::= { fsDot1qFutureVlanPortEntry 5 }

fsDot1qFutureVlanPortDTModeTPID OBJECT-TYPE
    SYNTAX      INTEGER
    ACCESS      read-only
    STATUS      mandatory
    DESCRIPTION 
        "TPID is the EtherType for SPVLAN in 802.1q in 802.1q 
         double tagging mode. The default value for TPID is
         0x8100
         	ALCATEL NOTE:
         	      	ACCESS:      NA           USAGE:       NA
             	PERSIST:     NO           INSRVMOD:    NA
             	RANGE:       NA           DEFVALUE:    NA
             	UNITS:       NA           SPARSE:      NO
             	DESCR:       NA"
    ::= { fsDot1qFutureVlanPortEntry 6 }

fsDot1qFutureVlanPortDTModePBitCopy OBJECT-TYPE
    SYNTAX      INTEGER { enabled(1), disabled(2) }
    ACCESS      read-write
    STATUS      mandatory
    DESCRIPTION 
        "If configured enabled(1), LANX  copies .p bits from C-VLAN 
         to the S-VLAN if the S-VLAN is added at packet reception 
         on user port copying. If configured disabled(2),the default
         .p-bits shall be applied to the added S-VLAN tag
         	ALCATEL NOTE:
         	      	ACCESS:      NA           USAGE:       NA
              	PERSIST:     YES          INSRVMOD:    YES
              	RANGE:       NA           DEFVALUE:    NA
              	UNITS:       NA           SPARSE:      NO
              	DESCR:       NA"
    DEFVAL      { disabled }
    ::= { fsDot1qFutureVlanPortEntry 7 }

fsDot1qFutureVlanMacMapTable OBJECT-TYPE
    SYNTAX      SEQUENCE OF FsDot1qFutureVlanMacMapEntry
    ACCESS      not-accessible
    STATUS      mandatory
    DESCRIPTION 
        "A table that contains information on Vlan-MAC address 
         mapping. This table is valid only when dot1qFutureVlanType is 
         set to macBased
         	ALCATEL NOTE:
         	    	TABLESIZE: NA 
               	DESCR:	This object is not used by Alcatel"
    ::= { dot1qFutureVlan 9 }

fsDot1qFutureVlanMacMapEntry OBJECT-TYPE
    SYNTAX      FsDot1qFutureVlanMacMapEntry
    ACCESS      not-accessible
    STATUS      mandatory
    DESCRIPTION 
        "Entry that contains Vlan-MAC address mapping.
         Row creation : NA
         Row deletion : NA
         Index usage : NA
         lexicographical order :  NA
         This object is not used by Alcatel"
    INDEX       { fsDot1qFutureVlanMacMapAddr }
    ::= { fsDot1qFutureVlanMacMapTable 1 }

FsDot1qFutureVlanMacMapEntry ::= SEQUENCE {
    fsDot1qFutureVlanMacMapAddr         MacAddress,
    fsDot1qFutureVlanMacMapVid          VlanId,
    fsDot1qFutureVlanMacMapName         DisplayString,
    fsDot1qFutureVlanMacMapIsLearnt     TruthValue,
    fsDot1qFutureVlanMacMapRowStatus    RowStatus
}

fsDot1qFutureVlanMacMapAddr OBJECT-TYPE
    SYNTAX      MacAddress
    ACCESS      not-accessible
    STATUS      mandatory
    DESCRIPTION 
        "The Mac address for which the Vlan mapping is present in the entry.
         ALCATEL NOTE:
            ACCESS:      NA           USAGE:       NA
            PERSIST:     NA           INSRVMOD:    NA
            RANGE:       NA           DEFVALUE:    NA
            UNITS:       NA           SPARSE:      NA
            DESCR:       This object is not used by Alcatel"
    ::= { fsDot1qFutureVlanMacMapEntry 1 }

fsDot1qFutureVlanMacMapVid OBJECT-TYPE
    SYNTAX      VlanId
    ACCESS      read-write
    STATUS      mandatory
    DESCRIPTION 
        "The Vlan to which the mac address of this entry is mapped to.
         ALCATEL NOTE:
            ACCESS:      NA           USAGE:       NA
            PERSIST:     NA           INSRVMOD:    NA
            RANGE:       NA           DEFVALUE:    NA
            UNITS:       NA           SPARSE:      NA
            DESCR:       This object is not used by Alcatel"
    ::= { fsDot1qFutureVlanMacMapEntry 2 }

fsDot1qFutureVlanMacMapName OBJECT-TYPE
    SYNTAX      DisplayString (SIZE(0..254))
    ACCESS      read-write
    STATUS      mandatory
    DESCRIPTION 
        "The name of the Vlan to which the mac address of this entry is  
         mapped to. This field is valid if and only if  
         dot1qFutureVlanMacMapIsLearnt is false (2).
         	ALCATEL NOTE:
               ACCESS:      NA           USAGE:       NA
               PERSIST:     NA           INSRVMOD:    NA
               RANGE:       NA           DEFVALUE:    NA
               UNITS:       NA           SPARSE:      NA
               DESCR:       This object is not used by Alcatel"
    ::= { fsDot1qFutureVlanMacMapEntry 3 }

fsDot1qFutureVlanMacMapIsLearnt OBJECT-TYPE
    SYNTAX      TruthValue
    ACCESS      read-only
    STATUS      mandatory
    DESCRIPTION 
        "Indicates whether the entry is learnt dynamically or not. If true (1)  
         entry is learnt dynamically else entry has been created by management.
         	ALCATEL NOTE:
               ACCESS:      NA           USAGE:       NA
               PERSIST:     NA           INSRVMOD:    NA
               RANGE:       NA           DEFVALUE:    NA
               UNITS:       NA           SPARSE:      NA
               DESCR:       This object is not used by Alcatel"
    ::= { fsDot1qFutureVlanMacMapEntry 4 }

fsDot1qFutureVlanMacMapRowStatus OBJECT-TYPE
    SYNTAX      RowStatus
    ACCESS      read-write
    STATUS      mandatory
    DESCRIPTION 
        "The row status of the entry.
         ALCATEL NOTE:
            ACCESS:      NA           USAGE:       NA
            PERSIST:     NA           INSRVMOD:    NA
            RANGE:       NA           DEFVALUE:    NA
            UNITS:       NA           SPARSE:      NA
            DESCR:       This object is not used by Alcatel"
    ::= { fsDot1qFutureVlanMacMapEntry 5 }

fsDot1qFutureVlanIpAddrMapTable OBJECT-TYPE
    SYNTAX      SEQUENCE OF FsDot1qFutureVlanIpAddrMapEntry
    ACCESS      not-accessible
    STATUS      mandatory
    DESCRIPTION 
        "A table that contains information on Vlan-MAC address 
         mapping. This table is valid only when dot1qFutureVlanType is 
         set to macBased
         	ALCATEL NOTE:
         	    	TABLESIZE: DEP 
               	DESCR:       DEP(TABLESIZE):The range of the index is total number of IP interfaces 
         				in the system . 
         				This is obtained from the object fsVrfMaxIpInterfaces in fsvrf.mib"
    ::= { dot1qFutureVlan 10 }

fsDot1qFutureVlanIpAddrMapEntry OBJECT-TYPE
    SYNTAX      FsDot1qFutureVlanIpAddrMapEntry
    ACCESS      not-accessible
    STATUS      mandatory
    DESCRIPTION 
        "Entry that contains Vlan-MAC address mapping.
         Row creation : Entries are created when an IP address is configured for VLAN interface by setting
         		ifMultiNetIpRowStatus (ifMultiNetIpTable) to createAndGo(4).
         Row deletion : Entries shall be deleted by setting the ifMultiNetIpRowStatus (ifMultiNetIpTable) 
         		of the specific entry to destroy(6)
         Index usage : the index is the Vlan Id.
         Note that entries will be presented to the SNMP manager in full
         lexicographical order :  sorted on Vlan Id."
    INDEX       { fsDot1qFutureVlanRowIndexVid }
    ::= { fsDot1qFutureVlanIpAddrMapTable 1 }

FsDot1qFutureVlanIpAddrMapEntry ::= SEQUENCE {
    fsDot1qFutureVlanRowIndexVid    VlanId,
    fsDot1qFutureVlanIpAddr         IpAddress,
    fsDot1qFutureVlanIfIndex        INTEGER
}

fsDot1qFutureVlanRowIndexVid OBJECT-TYPE
    SYNTAX      VlanId
    ACCESS      not-accessible
    STATUS      mandatory
    DESCRIPTION 
        "The Vlan to which the Ip address of this entry is mapped to.
         ALCATEL NOTE:
               	ACCESS:      NA           USAGE:       NA
            	PERSIST:     NO           INSRVMOD:    NA
            	RANGE:       1..4094      DEFVALUE:    NA
            	UNITS:       NA           SPARSE:      NO
            	DESCR:       NA"
    ::= { fsDot1qFutureVlanIpAddrMapEntry 1 }

fsDot1qFutureVlanIpAddr OBJECT-TYPE
    SYNTAX      IpAddress
    ACCESS      read-only
    STATUS      mandatory
    DESCRIPTION 
        "The Ip address of this VLAN Entry
         ALCATEL NOTE:
               	ACCESS:      NA           USAGE:       NA
            	PERSIST:     NO           INSRVMOD:    NA
            	RANGE:       NA           DEFVALUE:    NA
            	UNITS:       NA           SPARSE:      NO
            	DESCR:       NA"
    ::= { fsDot1qFutureVlanIpAddrMapEntry 2 }

fsDot1qFutureVlanIfIndex OBJECT-TYPE
    SYNTAX      INTEGER
    ACCESS      read-only
    STATUS      mandatory
    DESCRIPTION 
        "The IVR IfIndex, of this VLAN Entry.this is basically an CFA IfIndex
         reffered to as IVR (Inter VLAN routing number)
         	ALCATEL NOTE:
         	      	ACCESS:      NA           USAGE:       NA
              	PERSIST:     NO           INSRVMOD:    NA
              	RANGE:       DEP      DEFVALUE:    NA
              	UNITS:       NA           SPARSE:      NO
            DESCR:       DEP(RANGE): The range is from 65536 to 65535 plus
                              total number of IP interfaces in the system.
                              But the indices 81920 & 81921 are reserved for
                              vlan 4094 & 4093 respectively. The total number of
                              IP interfaces in the system is obtained from the
                              object fsVrfMaxIpInterfaces in fsvrf.mib"
    ::= { fsDot1qFutureVlanIpAddrMapEntry 3 }

fsDot1qFutureVlanConfMACMovementTable OBJECT-TYPE
    SYNTAX      SEQUENCE OF FsDot1qFutureVlanConfMACMovementEntry
    ACCESS      not-accessible
    STATUS      mandatory
    DESCRIPTION 
        "The Table used to Enable/Disable MAC movement per VLAN.
         ALCATEL NOTE:
             	TABLESIZE: 4094
            	DESCR:	NA"
    ::= { dot1qFutureVlan 11 }

fsDot1qFutureVlanConfMACMovementEntry OBJECT-TYPE
    SYNTAX      FsDot1qFutureVlanConfMACMovementEntry
    ACCESS      not-accessible
    STATUS      mandatory
    DESCRIPTION 
        "Entry indicating the type of the port.
         Row creation : Entries shall be created when a Vlan is created by setting
          		dot1qVlanStaticRowStatus (dot1qVlanStaticTable) to createAndGo(4).
         Row deletion : Entries shall be deleted by setting the dot1qVlanStaticRowStatus (dot1qVlanStaticTable) 
         		of the specific entry to destroy(6)
         Index usage : the index is the Vlan Id.
         Note that entries will be presented to the SNMP manager in full
         lexicographical order :  sorted on Vlan Id."
    INDEX       { fsDot1qFutureVlanId }
    ::= { fsDot1qFutureVlanConfMACMovementTable 1 }

FsDot1qFutureVlanConfMACMovementEntry ::= SEQUENCE {
    fsDot1qFutureVlanId             Gauge,
    fsDot1qFutureVlanConfStatus     INTEGER
}

fsDot1qFutureVlanId OBJECT-TYPE
    SYNTAX      Gauge (1..4094)
    ACCESS      not-accessible
    STATUS      mandatory
    DESCRIPTION 
        "The Vlan Id of the VLAN for which this entry applies.
         ALCATEL NOTE:
               	ACCESS:      NA           USAGE:       NA
            	PERSIST:     YES          INSRVMOD:    NA
            	RANGE:       NA           DEFVALUE:    NA
            	UNITS:       NA           SPARSE:      NO
            	DESCR:       NA"
    ::= { fsDot1qFutureVlanConfMACMovementEntry 1 }

fsDot1qFutureVlanConfStatus OBJECT-TYPE
    SYNTAX      INTEGER { enable(1), disable(2) }
    ACCESS      read-write
    STATUS      mandatory
    DESCRIPTION 
        "This object is used to enable/disable
         MAC movement in the VLAN denoted by the VLAN ID
         which is the index of this table.
         	ALCATEL NOTE:
         	      	ACCESS:      NA           USAGE:       NA
              	PERSIST:     YES          INSRVMOD:    YES
              	RANGE:       NA           DEFVALUE:    NA
              	UNITS:       NA           SPARSE:      NO
              	DESCR:       NA"
    DEFVAL      { disable }
    ::= { fsDot1qFutureVlanConfMACMovementEntry 2 }

fsDot1qFutureVlanCurrentVlanList OBJECT-TYPE
    SYNTAX      VlanList
    ACCESS      read-only
    STATUS      mandatory
    DESCRIPTION 
        "This is to get VLANs for which an entry is avalable/notavailable in the dot1qVlanStaticTable.
         A 1 indicates an entry for this VLAN exits in the dot1qVlanStaticTable. A 0 indicates
         no corresponding entry exists.
         	ALCATEL NOTE:
         	      	ACCESS:      NA           USAGE:       NA
               	PERSIST:     NO           INSRVMOD:    NA
               	RANGE:       NA           DEFVALUE:    NA
               	UNITS:       NA           SPARSE:      NO
               	DESCR:       NA"
    ::= { dot1qFutureVlan 12 }

fsDot1qFutureVlanPortMaskTable OBJECT-TYPE
    SYNTAX      SEQUENCE OF FsDot1qFutureVlanPortMaskEntry
    ACCESS      not-accessible
    STATUS      mandatory
    DESCRIPTION 
        "The Table sets/clears associated ports for a particular VLAN.
         ALCATEL NOTE:
             	TABLESIZE: 4094
            	DESCR:	NA"
    ::= { dot1qFutureVlan 13 }

fsDot1qFutureVlanPortMaskEntry OBJECT-TYPE
    SYNTAX      FsDot1qFutureVlanPortMaskEntry
    ACCESS      not-accessible
    STATUS      mandatory
    DESCRIPTION 
        "Entry to set/clear portlist for a VLAN .
         Row creation : Entries shall be created when a Vlan is created by setting
          		dot1qVlanStaticRowStatus (dot1qVlanStaticTable) to createAndGo(4).
         Row deletion : Entries shall be deleted by setting the dot1qVlanStaticRowStatus (dot1qVlanStaticTable) 
         		of the specific entry to destroy(6)
         Index usage : the index is the Vlan Id.
         Note that entries will be presented to the SNMP manager in full
         lexicographical order :  sorted on Vlan Id."
    INDEX       { fsDot1qFutureVlanIndex }
    ::= { fsDot1qFutureVlanPortMaskTable 1 }

FsDot1qFutureVlanPortMaskEntry ::= SEQUENCE {
    fsDot1qFutureVlanIndex              INTEGER,
    fsDot1qFutureVlanSetMaskPortList    PortList,
    fsDot1qFutureVlanClearMaskPortList  PortList
}

fsDot1qFutureVlanIndex OBJECT-TYPE
    SYNTAX      INTEGER (1..4094)
    ACCESS      not-accessible
    STATUS      mandatory
    DESCRIPTION 
        "Index number of the Vlan for which the configuration
         in this entry applies.
         	ALCATEL NOTE:
         	      	ACCESS:      NA           USAGE:       NA
               	PERSIST:     NO           INSRVMOD:    NA
               	RANGE:       NA           DEFVALUE:    NA
               	UNITS:       NA           SPARSE:      NO
               	DESCR:       NA"
    ::= { fsDot1qFutureVlanPortMaskEntry 1 }

fsDot1qFutureVlanSetMaskPortList OBJECT-TYPE
    SYNTAX      PortList
    ACCESS      read-write
    STATUS      mandatory
    DESCRIPTION 
        "The portmask to set for a VLAN. The bit 1 indicates it shall be added to the VLAN 0
         means no action.
         	ALCATEL NOTE:
         	      	ACCESS:      NA           USAGE:       NA
               	PERSIST:     NO           INSRVMOD:    YES
               	RANGE:       NA           DEFVALUE:    NA
               	UNITS:       NA           SPARSE:      NO
               	DESCR:       NA"
    ::= { fsDot1qFutureVlanPortMaskEntry 2 }

fsDot1qFutureVlanClearMaskPortList OBJECT-TYPE
    SYNTAX      PortList
    ACCESS      read-write
    STATUS      mandatory
    DESCRIPTION 
        "The portmask to clear ports for a VLAN.The bit 1 indicates to clear  a port from a
         VLAN and 0 means no action.
         	ALCATEL NOTE:
         	      	ACCESS:      NA           USAGE:       NA
              	PERSIST:     NO           INSRVMOD:    YES
              	RANGE:       NA           DEFVALUE:    NA
              	UNITS:       NA           SPARSE:      NO
              	DESCR:       NA"
    ::= { fsDot1qFutureVlanPortMaskEntry 3 }

fsDot1qFutureVlanPortVlanListTable OBJECT-TYPE
    SYNTAX      SEQUENCE OF FsDot1qFutureVlanPortVlanListEntry
    ACCESS      not-accessible
    STATUS      mandatory
    DESCRIPTION 
        "The Table displays associated VLAN's to ports.
         ALCATEL NOTE:
             	TABLESIZE:  DEP
            	DESCR:	DEP(TABLESIZE) The size of the table is the maximum number of ports available
         			in the system. This value can be obtained from the object 
         			issSystemNumberOfPorts in fsiss.mib."
    ::= { dot1qFutureVlan 14 }

fsDot1qFutureVlanPortVlanListEntry OBJECT-TYPE
    SYNTAX      FsDot1qFutureVlanPortVlanListEntry
    ACCESS      not-accessible
    STATUS      mandatory
    DESCRIPTION 
        "Entry indicating to retrive the VlanList for a port.
         Row creation : All entries are created during system start-up.
         Row deletion : Entries cannot be deleted
         Index usage : the index is the port number.
         Note that entries will be presented to the SNMP manager in full
         lexicographical order :  sorted on port number."
    INDEX       { fsDot1qFutureBasePort }
    ::= { fsDot1qFutureVlanPortVlanListTable 1 }

FsDot1qFutureVlanPortVlanListEntry ::= SEQUENCE {
    fsDot1qFutureBasePort           INTEGER,
    fsDot1qFutureVlanPortVlanList   VlanList
}

fsDot1qFutureBasePort OBJECT-TYPE
    SYNTAX      INTEGER (1..24)
    ACCESS      not-accessible
    STATUS      mandatory
    DESCRIPTION 
        "Index number of the portumber for which the configuration
         in this entry applies.
         	ALCATEL NOTE:
         	      	ACCESS:      NA           USAGE:       NA
               	PERSIST:     NO           INSRVMOD:    NA
               	RANGE:       NA           DEFVALUE:    NA
               	UNITS:       NA           SPARSE:      NO
               	DESCR:       NA"
    ::= { fsDot1qFutureVlanPortVlanListEntry 1 }

fsDot1qFutureVlanPortVlanList OBJECT-TYPE
    SYNTAX      VlanList
    ACCESS      read-only
    STATUS      mandatory
    DESCRIPTION 
        "The VLAN's set for a port configured is displayed.The bit with value 1 indicates
         that VLAN is supported by this port and 0 indicates that VLAN is not supported by
         this port.
         	ALCATEL NOTE:
         	      	ACCESS:      NA           USAGE:       NA
              	PERSIST:     NO           INSRVMOD:    NA
              	RANGE:       NA           DEFVALUE:    NA
              	UNITS:       NA           SPARSE:      NO
              	DESCR:       NA"
    ::= { fsDot1qFutureVlanPortVlanListEntry 2 }

fsDot1qFutureVlanNameTable OBJECT-TYPE
    SYNTAX      SEQUENCE OF FsDot1qFutureVlanNameEntry
    ACCESS      not-accessible
    STATUS      mandatory
    DESCRIPTION 
        "The Table displays associated VLAN id for a VLAN name.
         ALCATEL NOTE:
             	TABLESIZE: 4094
            	DESCR:	NA"
    ::= { dot1qFutureVlan 15 }

fsDot1qFutureVlanNameEntry OBJECT-TYPE
    SYNTAX      FsDot1qFutureVlanNameEntry
    ACCESS      not-accessible
    STATUS      mandatory
    DESCRIPTION 
        "Entry indicating vlan name.
         Row creation : Entries shall be created when a Vlan is created by setting
          		dot1qVlanStaticRowStatus (dot1qVlanStaticTable) to createAndGo(4).
         Row deletion : Entries shall be deleted by setting the dot1qVlanStaticRowStatus (dot1qVlanStaticTable) 
         		of the specific entry to destroy(6).
         Index usage : the index is Vlan name and Vlan Id.
         Note that entries will be presented to the SNMP manager in full
         lexicographical order :  sorted on Vlan name, then on Vlan Id."
    INDEX       { fsDot1dFutureVlanName, fsDot1qFutureVlanNameIndex }
    ::= { fsDot1qFutureVlanNameTable 1 }

FsDot1qFutureVlanNameEntry ::= SEQUENCE {
    fsDot1dFutureVlanName       SnmpAdminString,
    fsDot1qFutureVlanNameIndex  INTEGER
}

fsDot1dFutureVlanName OBJECT-TYPE
    SYNTAX      SnmpAdminString
    ACCESS      read-only
    STATUS      mandatory
    DESCRIPTION 
        "Index name of the vlan for which the configuration
         in this entry applies.
         	ALCATEL NOTE:
         	      	ACCESS:      NA           USAGE:       NA
               	PERSIST:     NO           INSRVMOD:    NA
               	RANGE:       NA           DEFVALUE:    NA
               	UNITS:       NA           SPARSE:      NO
               	DESCR:       NA"
    ::= { fsDot1qFutureVlanNameEntry 1 }

fsDot1qFutureVlanNameIndex OBJECT-TYPE
    SYNTAX      INTEGER (1..2147483647)
    ACCESS      read-only
    STATUS      mandatory
    DESCRIPTION 
        "Index name of the vlan for which the configuration
         in this entry applies.
         	ALCATEL NOTE:
         	      	ACCESS:      NA           USAGE:       NA
               	PERSIST:     NO           INSRVMOD:    NA
               	RANGE:       1..4094      DEFVALUE:    NA
               	UNITS:       NA           SPARSE:      NO
               	DESCR:       NA"
    ::= { fsDot1qFutureVlanNameEntry 2 }

fsDot1qFutureVlanVersionNumberTable OBJECT-TYPE
    SYNTAX      SEQUENCE OF FsDot1qFutureVlanVersionNumberEntry
    ACCESS      not-accessible
    STATUS      mandatory
    DESCRIPTION 
        "The Table sets/gets associated version number for a particular static Vlan.
         ALCATEL NOTE:
             	TABLESIZE: 4094
            	DESCR:	NA"
    ::= { dot1qFutureVlan 16 }

fsDot1qFutureVlanVersionNumberEntry OBJECT-TYPE
    SYNTAX      FsDot1qFutureVlanVersionNumberEntry
    ACCESS      not-accessible
    STATUS      mandatory
    DESCRIPTION 
        "Entry to set/get vlan number for a VLAN .
         Row creation : Entries shall be created when a Vlan is created by setting
          		dot1qVlanStaticRowStatus (dot1qVlanStaticTable) to createAndGo(4).
         Row deletion : Entries shall be deleted by setting the dot1qVlanStaticRowStatus (dot1qVlanStaticTable) 
         		of the specific entry to destroy(6).
         Index usage : the index is the Vlan Id.
         Note that entries will be presented to the SNMP manager in full
         lexicographical order :  sorted on Vlan Id."
    INDEX       { fsDot1qFutureVlanIndex }
    ::= { fsDot1qFutureVlanVersionNumberTable 1 }

FsDot1qFutureVlanVersionNumberEntry ::= SEQUENCE {
    fsDot1qFutureVlanVersionNumber  INTEGER
}

fsDot1qFutureVlanVersionNumber OBJECT-TYPE
    SYNTAX      INTEGER
    ACCESS      read-write
    STATUS      mandatory
    DESCRIPTION 
        "The version number is configured for a vlan data.It is set to 1 when vlan is created
         can be incremented when vlan data is modified
         	ALCATEL NOTE:
         	      	ACCESS:      NA           USAGE:       NA
              	PERSIST:     YES          INSRVMOD:    YES
              	RANGE:       NA           DEFVALUE:    1
              	UNITS:       NA           SPARSE:      NO
              	DESCR:       NA"
    ::= { fsDot1qFutureVlanVersionNumberEntry 1 }

fsDot1qFutureVlanDuplicateMacTable OBJECT-TYPE
    SYNTAX      SEQUENCE OF FsDot1qFutureVlanDuplicateMacEntry
    ACCESS      not-accessible
    STATUS      mandatory
    DESCRIPTION 
        "The Table displays duplicates mac addresses learnt on a port.
         ALCATEL NOTE:
             	TABLESIZE: 2048
            	DESCR:	NA"
    ::= { dot1qFutureVlan 17 }

fsDot1qFutureVlanDuplicateMacEntry OBJECT-TYPE
    SYNTAX      FsDot1qFutureVlanDuplicateMacEntry
    ACCESS      not-accessible
    STATUS      mandatory
    DESCRIPTION 
        "Entry to display duplicate mac addressses for a VLAN .
         Row creation : Entries are created automatically when duplicate mac addresses are learnt.
         Row deletion : Entries are deleted automatically when entries are aged out.
         Index usage : the index is the Vlan Id, Port number and Mac address.
         Note that entries will be presented to the SNMP manager in full
         lexicographical order :  sorted on Vlan Id, then on port number and then on mac address."
    INDEX       { fsDot1qFutureVlanIndex, 
                  fsDot1qFutureVlanDupMacPortNumber, 
                  fsDot1qFutureVlanDupMacAddress }
    ::= { fsDot1qFutureVlanDuplicateMacTable 1 }

FsDot1qFutureVlanDuplicateMacEntry ::= SEQUENCE {
    fsDot1qFutureVlanDupMacPortNumber   INTEGER,
    fsDot1qFutureVlanDupMacAddress      MacAddress
}

fsDot1qFutureVlanDupMacPortNumber OBJECT-TYPE
    SYNTAX      INTEGER (1..2147483647)
    ACCESS      read-only
    STATUS      mandatory
    DESCRIPTION 
        "Index number of the portumber on which duplicate mac is learnt.
         ALCATEL NOTE:
               	ACCESS:      NA           USAGE:       NA
            	PERSIST:     NO           INSRVMOD:    NA
            	RANGE:       DEP          DEFVALUE:    NA
            	UNITS:       NA           SPARSE:      NO
            	DESCR:       DEP(RANGE):The range of the index is maximum number of physical interfaces
         			available in the system. This is obtained from the object issSystemNumberOfPorts in fsiss.mib"
    ::= { fsDot1qFutureVlanDuplicateMacEntry 1 }

fsDot1qFutureVlanDupMacAddress OBJECT-TYPE
    SYNTAX      MacAddress
    ACCESS      read-only
    STATUS      mandatory
    DESCRIPTION 
        "The Dup Mac address received on a port.
         ALCATEL NOTE:
               	ACCESS:      NA           USAGE:       NA
            	PERSIST:     NO           INSRVMOD:    NA
            	RANGE:       NA           DEFVALUE:    NA
            	UNITS:       NA           SPARSE:      NO
            	DESCR:       NA"
    ::= { fsDot1qFutureVlanDuplicateMacEntry 2 }

fsDot1qFutureLanxVlanConfigTable OBJECT-TYPE
    SYNTAX      SEQUENCE OF FsDot1qFutureLanxVlanConfigEntry
    ACCESS      not-accessible
    STATUS      mandatory
    DESCRIPTION 
        "The Table displays mode of operation of a vlan.
         ALCATEL NOTE:
             	TABLESIZE: 4094
            	DESCR:	NA"
    ::= { dot1qFutureVlan 18 }

fsDot1qFutureLanxVlanConfigEntry OBJECT-TYPE
    SYNTAX      FsDot1qFutureLanxVlanConfigEntry
    ACCESS      not-accessible
    STATUS      mandatory
    DESCRIPTION 
        "Entry to display mode of operation of a  VLAN .
         Row creation : Entries shall be created when a Vlan is created by setting
          		dot1qVlanStaticRowStatus (dot1qVlanStaticTable) to createAndGo(4).
         Row deletion : Entries shall be deleted by setting the dot1qVlanStaticRowStatus (dot1qVlanStaticTable) 
         		of the specific entry to destroy(6).
         Index usage : the index is the Vlan Id.
         Note that entries will be presented to the SNMP manager in full
         lexicographical order :  sorted on Vlan Id."
    INDEX       { fsDot1qFutureVlanIndex }
    ::= { fsDot1qFutureLanxVlanConfigTable 1 }

FsDot1qFutureLanxVlanConfigEntry ::= SEQUENCE {
    fsDot1qFutureVlanModeType               INTEGER,
    fsDot1qFutureVlanGratArpBCast           INTEGER,
    fsDot1qFutureUserToUserCommStatus       INTEGER,
    fsDot1qFutureVlanMACAddressLearning     INTEGER
}

fsDot1qFutureVlanModeType OBJECT-TYPE
    SYNTAX      INTEGER { residentialbridging(1), crossconnect(2), 
                    l2terminated(3), l2terminatedonnetworkports(4), 
                    vvlan(5), reserved(6), voicevlan(8), eponvlan(9) }
    ACCESS      read-write
    STATUS      mandatory
    DESCRIPTION 
        "This defines the type of the Vlan mode. By Default the vlan will be in 
         notclassified mode. All VLAN types excpet the corssconnect behave like 
         the residentialbridging VLAN. Following briefs on the various VLAN modes:
            L2 terminated on network ports - Used for VLANs for IP 
                                    forwarding (e.g. for RADIUS packet relay)
            V-VLAN -  This is used for communication between the LT and LANX and 
                      ideally has all the ASAM ports as member ports 
            reserved - This has the internal and external communicatieon VLAN
            notclassified - Default VLAN mode ( OBSOLETED)
            voicevlan - Enables Voice traffic through LANX in ISAM-V
         User has to change the VLAN mode from notclassified to any other valid 
         mode. Changing VLAN mode apart from notclassified is not allowed. 
            EPON VLAN -This is used for L2 communication between ASAM Ports and Subtending ports only.
         
         	ALCATEL NOTE:
         	      	ACCESS:      NA           USAGE:       MAND
              	PERSIST:     YES          INSRVMOD:    NO
              	RANGE:       NA           DEFVALUE:    NA
              	UNITS:       NA           SPARSE:      NO
              	DESCR:       NA"
    ::= { fsDot1qFutureLanxVlanConfigEntry 1 }

fsDot1qFutureVlanGratArpBCast OBJECT-TYPE
    SYNTAX      INTEGER { enable(1), disabled(2) }
    ACCESS      read-write
    STATUS      mandatory
    DESCRIPTION 
        "This defines wheather gratutious ARP broadcast is enabled or disabled  
         in a VLAN or not. 
         	ALCATEL NOTE:
         	      	ACCESS:      NA           USAGE:       NA
              	PERSIST:     YES          INSRVMOD:    YES
              	RANGE:       NA           DEFVALUE:    NA
              	UNITS:       NA           SPARSE:      NO
              	DESCR:       NA"
    DEFVAL      { disabled }
    ::= { fsDot1qFutureLanxVlanConfigEntry 2 }

fsDot1qFutureUserToUserCommStatus OBJECT-TYPE
    SYNTAX      INTEGER { enable(1), disable(2) }
    ACCESS      read-write
    STATUS      mandatory
    DESCRIPTION 
        "This object defines the the user-2-user communication status on a particular Vlan.
         This object is enabled by default for a voice vlan. The object status cannot be disabled 
         for a voice vlan. For all other kinds of vlan, this object is disabled by default. 
         At most there can be ten vlans including voice vlans with user-2-user communication 
         enabled.
         ALCATEL NOTE:
         	      	ACCESS:      NA           USAGE:       NA
               	PERSIST:     YES          INSRVMOD:    YES
               	RANGE:       NA           DEFVALUE:    NA
               	UNITS:       NA           SPARSE:      NO
               	DESCR:       NA"
    ::= { fsDot1qFutureLanxVlanConfigEntry 3 }

fsDot1qFutureVlanMACAddressLearning OBJECT-TYPE
    SYNTAX      INTEGER { enable(1), disable(2) }
    ACCESS      read-write
    STATUS      mandatory
    DESCRIPTION 
        "This MIB object determines the status of the MAC address learning feature per VLAN.
         If it is disable, then MAC learning will be disabled otherwise will be enabled. 	
         ALCATEL NOTE:
         ACCESS:      NA           USAGE:       NA
         PERSIST:     YES          INSRVMOD:    YES
         RANGE:       NA           DEFVALUE:    NA
         UNITS:       NA           SPARSE:      NA
         DESCR:       NA"
    DEFVAL      { enable }
    ::= { fsDot1qFutureLanxVlanConfigEntry 4 }

fsDot1qFutureVlanNumFdbEntriesLearnt OBJECT-TYPE
    SYNTAX      INTEGER
    ACCESS      read-only
    STATUS      mandatory
    DESCRIPTION 
        "This object is statistics variable, gives the number of FDB entries learnt.
         ALCATEL NOTE:
               	ACCESS:      NA           USAGE:       NA
            	PERSIST:     NO           INSRVMOD:    NA
            	RANGE:       NA           DEFVALUE:    0
            	UNITS:       NA           SPARSE:      NA
            	DESCR:       NA"
    ::= { dot1qFutureVlan 19 }

fsDot1qFutureVlanDualTaggingMode OBJECT-TYPE
    SYNTAX      INTEGER { enable(1), disabled(2) }
    ACCESS      read-write
    STATUS      mandatory
    DESCRIPTION 
        "Object for system level tagging mode. If set to 
         disabled (2), then LANX will be operating as
         an C-VLAN bridge in single tagged Mode. If set to
         enabled (1), then LANX will be operating as an
         S-VLAN bridge in dual tagged mode.
         	ALCATEL NOTE:
         	      	ACCESS:      NA           USAGE:       NA
              	PERSIST:     YES          INSRVMOD:    YES
              	RANGE:       NA           DEFVALUE:    NA
              	UNITS:       NA           SPARSE:      NA
              	DESCR:       NA"
    DEFVAL      { disabled }
    ::= { dot1qFutureVlan 20 }

fsDot1qFutureCpeConfigTable OBJECT-TYPE
    SYNTAX      SEQUENCE OF FsDot1qFutureCpeConfigEntry
    ACCESS      not-accessible
    STATUS      mandatory
    DESCRIPTION 
        "The Table has the list of vlans on which the ISAM control point (NT SWC) can be reached.
         ALCATEL NOTE:
             	TABLESIZE: 4
            	DESCR:	NA"
    ::= { dot1qFutureVlan 21 }

fsDot1qFutureCpeConfigEntry OBJECT-TYPE
    SYNTAX      FsDot1qFutureCpeConfigEntry
    ACCESS      not-accessible
    STATUS      mandatory
    DESCRIPTION 
        "Entry which holds the vlanid and its RowStatus.
         Row creation : Entries shall be created when a Vlan is created by setting
          		fsDot1qFutureCpeRowStatus to createAndGo(4).
         Row deletion : Entries shall be deleted by setting the fsDot1qFutureCpeRowStatus 
         		of the specific entry to destroy(6).
         Index usage : the index is the Vlan Id.
         Note that entries will be presented to the SNMP manager in full
         lexicographical order :  sorted on Vlan Id."
    INDEX       { fsDot1qFutureCpeVlanIndex }
    ::= { fsDot1qFutureCpeConfigTable 1 }

FsDot1qFutureCpeConfigEntry ::= SEQUENCE {
    fsDot1qFutureCpeVlanIndex   VlanId,
    fsDot1qFutureCpeRowStatus   RowStatus
}

fsDot1qFutureCpeVlanIndex OBJECT-TYPE
    SYNTAX      VlanId
    ACCESS      not-accessible
    STATUS      mandatory
    DESCRIPTION 
        "Vlan Id  through which the ISAM (NT SWC) component can be reached
         ALCATEL NOTE:
               	ACCESS:      NA           USAGE:       NA
            	PERSIST:     YES          INSRVMOD:    NA
            	RANGE:       1..4094      DEFVALUE:    NA
            	UNITS:       NA           SPARSE:      NA
            	DESCR:       NA"
    ::= { fsDot1qFutureCpeConfigEntry 1 }

fsDot1qFutureCpeRowStatus OBJECT-TYPE
    SYNTAX      RowStatus
    ACCESS      read-write
    STATUS      mandatory
    DESCRIPTION 
        "The CPE Management table entries can be created or deleted by using this variable.
         Only  'CreateAndGo', 'destroy' are supported. 
         By default External Vlan will have RowStatus as ACTIVE. 
         The status for Internal & External Vlan cannot be updated. 
         Maximum 3 Vlans  are allowed other than Internal & external Vlans.
         ALCATEL NOTE:
              	ACCESS:      NA           USAGE:       MAND
           	PERSIST:     YES          INSRVMOD:    DEP
           	RANGE:       4,6          DEFVALUE:    NA
           	UNITS:       NA           SPARSE:      NA
           	DESCR:       Cannot be set for internal and external vlan"
    ::= { fsDot1qFutureCpeConfigEntry 2 }

fsDot1qFutureU2UHairPinningGlobalStatus OBJECT-TYPE
    SYNTAX      INTEGER { enabled(1), disabled(2) }
    ACCESS      read-write
    STATUS      mandatory
    DESCRIPTION 
        "The administrative status requested by management for U2U  
         Hair-pinning feature. The value enabled(1) indicates that Hair-pinning  
         is enabled on all user-to-user communication enabled VLANs.
         The value disabled(2) indicates that Hair-pinning  
         is disabled on all user-to-user communication enabled VLANs.
         	ALCATEL NOTE:
         	      	ACCESS:      NA           USAGE:       NA
               	PERSIST:     YES          INSRVMOD:    YES
               	RANGE:       1,2          DEFVALUE:    disabled
               	UNITS:       NA           SPARSE:      NO
               	DESCR:       NA"
    DEFVAL      { disabled }
    ::= { dot1qFutureVlan 22 }

END -- end of module FutureVlan-MIB.
