--
-- This SMIv1 module has been generated by smidump 0.4.8. Do not edit.
--

LA-MIB DEFINITIONS ::= BEGIN

IMPORTS
    IANAifType
        FROM IANAifType-MIB
    InterfaceIndex
        FROM IF-MIB
    OBJECT-TYPE
        FROM RFC-1212
    TRAP-TYPE
        FROM RFC-1215
    Counter, Gauge, TimeTicks, enterprises
        FROM RFC1155-SMI
    DisplayString, PhysAddress, TruthValue
        FROM SNMPv2-TC;

fsla OBJECT IDENTIFIER
    ::= { enterprises futuresoftware(2076) 63 }

-- fsla MODULE-IDENTITY
--     LAST-UPDATED "200203060000Z"
--     ORGANIZATION 
--         "Future Software Private Limited"
--     CONTACT-INFO 
--         " 
--          
--          Postal:     Future Software Pvt. Ltd.,
--          
--                      480-481, Anna Salai,
--          
--                      Nandanam,
--          
--                      Chennai,
--          
--                      India  600 035
--          
--          Telephone: +91-44-4330550
--          
--          E-Mail:     support@future.futsoft.com "
--     DESCRIPTION 
--         " The proprietary MIB module for FutureLA. "
--     REVISION    "200203060000Z"
--     DESCRIPTION 
--         "The initial revision of this MIB module was published as
--          
--          RFC 1450."
--     ::= { enterprises futuresoftware(2076) 63 }


LacpState ::=
    OCTET STRING
--                   { lacpActivity(0), lacpTimeout(1), aggregation(2), 
--                     synchronization(3), collecting(4), 
--                     distributing(5), defaulted(6), expired(7) }

-- LacpState ::= TEXTUAL-CONVENTION
--     STATUS      mandatory
--     DESCRIPTION 
--         "The Actor and Partner State values from the LACPDU."
--     SYNTAX      OCTET STRING
--                   { lacpActivity(0), lacpTimeout(1), aggregation(2), 
--                     synchronization(3), collecting(4), 
--                     distributing(5), defaulted(6), expired(7) }

fsLaAggTraps OBJECT IDENTIFIER
    ::= { fsla 0 }

fsLaSystem OBJECT IDENTIFIER
    ::= { fsla 1 }

fsLaSystemControl OBJECT-TYPE
    SYNTAX      INTEGER { start(1), shutdown(2) }
    ACCESS      read-write
    STATUS      mandatory
    DESCRIPTION 
        "Starts or shutdowns Link Aggregation Module in the system
         
         
         
         When set as 'start',resources required by Link aggregation 
         
         module are allocated & Link aggregation module starts running.
         
         
         
         When shutdown, all resources used by Link aggregation module 
         
         will be released to the system 
         
         ALCATEL NOTE:
         
         ACCESS:      NA           USAGE:       NA
         
         PERSIST:     YES          INSRVMOD:    DEP
         
         RANGE:       NA           DEFVALUE:    start
         
         UNITS:       NA           SPARSE:      NA
         
         DESCR:       Can be set only if IssMacLearningStatus is enabled"
    ::= { fsLaSystem 1 }

fsLaStatus OBJECT-TYPE
    SYNTAX      INTEGER { enabled(1), disabled(2) }
    ACCESS      read-write
    STATUS      mandatory
    DESCRIPTION 
        "Enables or Disables Link Aggregation Module in the system.
         
         
         
         When set as 'enabled', Link Aggregation module starts protocol 
         
         operations.
         
         
         
         When set as 'disabled', Link Aggregation module releases all 
         
         the dynamically allocated resources to the free pools and 
         
         stops protocol operations
         
         ALCATEL NOTE:
         
         ACCESS:      NA           USAGE:       NA
         
         PERSIST:     YES          INSRVMOD:    DEP
         
         RANGE:       NA           DEFVALUE:    disabled
         
         UNITS:       NA           SPARSE:      NA
         
         DESCR:       Can be set only if IssMacLearningStatus is enabled and fsLaSystemControl is start"
    ::= { fsLaSystem 2 }

fsLaTraceOption OBJECT-TYPE
    SYNTAX      INTEGER
    ACCESS      read-write
    STATUS      mandatory
    DESCRIPTION 
        "This object is used to enable Trace Statements in 
         
         Link Aggregation Module.
         
         
         
         A FOUR BYTE integer is used for enabling the level of tracing. 
         
         Each BIT in the four byte integer, represents a particular 
         
         level of Trace. 
         
         
         
         The maping between the bit positions & the level of trace is 
         
         as follows: 
         
                 0 - Init and Shutdown Traces
         
                 1 - Management Traces
         
                 2 - Data Path Traces
         
                 3 - Control Plane Traces
         
                 4 - Packet Dump Traces
         
                 5 - Traces related to All Resources except Buffers
         
                 6 - All Failure Traces
         
                 7 - Buffer Traces
         
         
         
         The remaining bits are unused. Combination of levels are 
         
         also allowed.
         
         
         
         For example if the bits 0 and 1 are set, then the Trace
         
         statements related to Init-Shutdown and management 
         
         will be printed.
         
         
         
         The user has to enter the corresponding INTEGER VALUE for the
         
         bits set. For example if bits 0 and 1 are set then user has to 
         
         give the value 3.
         
         ALCATEL NOTE:
         
         ACCESS:      NA           USAGE:       NA
         
         PERSIST:     YES          INSRVMOD:    YES
         
         RANGE:       0..255       DEFVALUE:    NA
         
         UNITS:       NA           SPARSE:      NA
         
         DESCR:       NA"
    DEFVAL      { 0 }
    ::= { fsLaSystem 3 }

fsLaAggIf OBJECT IDENTIFIER
    ::= { fsla 3 }

fsAggIfTable OBJECT-TYPE
    SYNTAX      SEQUENCE OF FsAggIfEntry
    ACCESS      not-accessible
    STATUS      mandatory
    DESCRIPTION 
        "A list of Aggregator interface entries.
         
         ALCATEL NOTE:
         
         	TABLESIZE: DEP
         
            	DESCR:	 DEP(TABLESIZE)The range of this table is derived from the number of
         
         		       physical interfaces in the system. This value can be 
         
         		       got from the object issSystemNumberOfPorts in fsiss.mib. "
    ::= { fsLaAggIf 1 }

fsAggIfEntry OBJECT-TYPE
    SYNTAX      FsAggIfEntry
    ACCESS      not-accessible
    STATUS      mandatory
    DESCRIPTION 
        "An entry containing management information applicable
         
         to a particular Aggregator interface.
         
         
         
         This table is indexed by the ifIndex of the aggregator
         
         This statistics is applicable only for the aggregator index,
         
         i.e., the primary port of the LA, and not on a per port basis.
         
         If the index number is a secondary port, then the statistics 
         
         will display 0.
         
         Row creation : All entries will be created during system start-up if fsLaSystemControl
         
         is set to 'start' or whenever fsLaSystemControl is set to 'start'.
         
         Row deletion : All entries will be deleted when fsLaSystemControl is set to 'shutdown'.
         
         Index usage : the index is the Agg Interface index.
         
         Note that entries will be presented to the SNMP manager in full
         
         lexicographical order :  sorted on Agg Interface index."
    INDEX       { fsAggIfIndex }
    ::= { fsAggIfTable 1 }

FsAggIfEntry ::= SEQUENCE {
    fsAggIfIndex            InterfaceIndex,
    fsAggIfDescription      DisplayString,
    fsAggIfType             IANAifType,
    fsAggIfMtu              INTEGER,
    fsAggIfSpeed            Gauge,
    fsAggIfPhysAddress      PhysAddress,
    fsAggIfAdminStatus      INTEGER,
    fsAggIfOperStatus       INTEGER,
    fsAggIfLastChange       TimeTicks,
    fsAggIfInOctets         Counter,
    fsAggIfInUcastPkts      Counter,
    fsAggIfInDiscards       Counter,
    fsAggIfInErrors         Counter,
    fsAggIfInUnknownProtos  Counter,
    fsAggIfOutOctets        Counter,
    fsAggIfOutUcastPkts     Counter,
    fsAggIfOutDiscards      Counter,
    fsAggIfOutErrors        Counter,
    fsTrapAggIndex          InterfaceIndex
}

fsAggIfIndex OBJECT-TYPE
    SYNTAX      InterfaceIndex
    ACCESS      not-accessible
    STATUS      mandatory
    DESCRIPTION 
        "A unique value, greater than zero, for each
         
         aggregator. 
         
         ALCATEL NOTE:
         
         ACCESS:      NA           USAGE:       NA
         
         PERSIST:     YES          INSRVMOD:    NA
         
         RANGE:       DEP        DEFVALUE:    NA
         
         UNITS:       NA           SPARSE:      NO
         
         DESCR:       DEP(RANGE): The Value is the maximum number of physical interfaces available in the system.
         
         		This is obtained from the object issSystemNumberOfPorts in fsiss.mib"
    ::= { fsAggIfEntry 1 }

fsAggIfDescription OBJECT-TYPE
    SYNTAX      DisplayString (SIZE(0..255))
    ACCESS      read-only
    STATUS      mandatory
    DESCRIPTION 
        "A human-readable text string containing information 
         
         about the Aggregator.  This string is read-only.
         
         The contents are vendor specific.
         
         ALCATEL NOTE:
         
         ACCESS:      NA           USAGE:       NA
         
         PERSIST:     NO           INSRVMOD:    NA
         
         RANGE:       NA           DEFVALUE:    'The number of ports attached to this Aggregator is : 0'
         
         UNITS:       NA           SPARSE:      NO
         
         DESCR:       NA"
    ::= { fsAggIfEntry 2 }

fsAggIfType OBJECT-TYPE
    SYNTAX      IANAifType
    ACCESS      read-only
    STATUS      mandatory
    DESCRIPTION 
        "The type of interface.  Additional values for ifType
         
         are assigned by the Internet Assigned Numbers
         
         Authority (IANA), through updating the syntax of the
         
         IANAifType textual convention.
         
         
         
         The ifType for an aggregator is 'ieee8023adLag(161)'.
         
         ALCATEL NOTE:
         
         ACCESS:      NA           USAGE:       NA
         
         PERSIST:     NO           INSRVMOD:    NA
         
         RANGE:       161          DEFVALUE:    161
         
         UNITS:       NA           SPARSE:      NO
         
         DESCR:       NA"
    ::= { fsAggIfEntry 3 }

fsAggIfMtu OBJECT-TYPE
    SYNTAX      INTEGER
    ACCESS      read-only
    STATUS      mandatory
    DESCRIPTION 
        "The largest MAC Client SDU that can be carried by this
         
         Aggregator  (1500) 
         
         ALCATEL NOTE:
         
         ACCESS:      NA           USAGE:       NA
         
         PERSIST:     NO           INSRVMOD:    NA
         
         RANGE:       1500         DEFVALUE:    1500
         
         UNITS:       bytes        SPARSE:      NO
         
         DESCR:       NA"
    ::= { fsAggIfEntry 4 }

fsAggIfSpeed OBJECT-TYPE
    SYNTAX      Gauge
    ACCESS      read-only
    STATUS      mandatory
    DESCRIPTION 
        "The current data rate,in Mbits per second,of the 
         
         aggregate link.The value is calculated as N
         
         times the data rate of a single link in the aggregation,
         
         where N is the number of active links.
         
         This attribute is read-only.
         
         ALCATEL NOTE:
         
         ACCESS:      NA           USAGE:       NA
         
         PERSIST:     NO           INSRVMOD:    NA
         
         RANGE:       NA           DEFVALUE:    0
         
         UNITS:       Mbits per second      SPARSE:      NO
         
         DESCR:       NA"
    ::= { fsAggIfEntry 5 }

fsAggIfPhysAddress OBJECT-TYPE
    SYNTAX      PhysAddress
    ACCESS      read-only
    STATUS      mandatory
    DESCRIPTION 
        "A 6-octet read-only value carrying the  MAC 
         
         address assigned to the Aggregator.
         
         ALCATEL NOTE:
         
         ACCESS:      NA           USAGE:       NA
         
         PERSIST:     NO           INSRVMOD:    NA
         
         RANGE:       NA           DEFVALUE:    NA
         
         UNITS:       NA           SPARSE:      NO
         
         DESCR:       NA"
    ::= { fsAggIfEntry 6 }

fsAggIfAdminStatus OBJECT-TYPE
    SYNTAX      INTEGER { up(1), down(2) }
    ACCESS      read-write
    STATUS      mandatory
    DESCRIPTION 
        "This read-write value defines the administrative 
         
         state of the Aggregator.A value of 'up' indicates 
         
         that the operational state of the Aggregator
         
         (fsAggIfOperStatus)is permitted to be either up
         
         or down.A value of 'down' forces the operational 
         
         state of the Aggregator to be down.
         
         
         
         Changes to the administrative state affect the 
         
         operational state of the Aggregator only,not the
         
         operational state of the Aggregation Ports that are 
         
         attached to the Aggregator.A GET operation returns the
         
         current administrative state.A SET operation
         
         changes the administrative state to a new value
         
         ALCATEL NOTE:
         
         ACCESS:      NA           USAGE:       NA
         
         PERSIST:     YES          INSRVMOD:    YES
         
         RANGE:       NA           DEFVALUE:    up
         
         UNITS:       NA           SPARSE:      NO
         
         DESCR:       NA"
    ::= { fsAggIfEntry 7 }

fsAggIfOperStatus OBJECT-TYPE
    SYNTAX      INTEGER { up(1), down(2), testing(3), unknown(4), 
                    dormant(5), notPresent(6), lowerLayerDown(7) }
    ACCESS      read-only
    STATUS      mandatory
    DESCRIPTION 
        "This read-only value defines the operational state of 
         
         the Aggregator. 
         
         The operational state is 'up' if one or more of the 
         
         Aggregation Ports that are attached to the Aggregator 
         
         are collecting,or both collecting and distributing,and
         
         if the value of 'AdminState' for the Aggregator is also
         
         up.
         
         If none of the Aggregation Ports that are attached to the 
         
         Aggregator are collecting and/or distributing,or if there 
         
         are no Aggregation Ports attached to this Aggregator,
         
         then the operational state is down. 
         
         An operational state of up indicates that the Aggregator
         
         is a ailable for use by the MAC Client;a value of
         
         down indicates that the Aggregator is not available for use 
         
         by the MAC Client.
         
         ALCATEL NOTE:
         
         ACCESS:      NA           USAGE:       NA
         
         PERSIST:     NO           INSRVMOD:    NA
         
         RANGE:       NA           DEFVALUE:    down
         
         UNITS:       NA           SPARSE:      NO
         
         DESCR:       NA"
    ::= { fsAggIfEntry 8 }

fsAggIfLastChange OBJECT-TYPE
    SYNTAX      TimeTicks
    ACCESS      read-only
    STATUS      mandatory
    DESCRIPTION 
        "The value of aTimeSinceSystemReset at the time the
         
         interface entered its current operational state.
         
         If the current state was entered prior to the last 
         
         re-initialization of the local network management 
         
         subsystem,then this object contains a value of zero.
         
         This value is read-only.
         
         ALCATEL NOTE:
         
         ACCESS:      NA           USAGE:       NA
         
         PERSIST:     NO           INSRVMOD:    NA
         
         RANGE:       NA           DEFVALUE:    0
         
         UNITS:       TimeTicks    SPARSE:      NO
         
         DESCR:       NA"
    ::= { fsAggIfEntry 9 }

fsAggIfInOctets OBJECT-TYPE
    SYNTAX      Counter
    ACCESS      read-only
    STATUS      mandatory
    DESCRIPTION 
        "The total count of octets including padding octets
         
         received by this Aggregator,from the Aggregation 
         
         Ports that are (or have been)members of the aggregation.
         
         The count does not include octets received in frames 
         
         that carry LACP or Marker PDUs ,or frames discarded 
         
         by the Collection function of the Aggregator
         
         This value is read-only.
         
         ALCATEL NOTE:
         
         ACCESS:      NA           USAGE:       NA
         
         PERSIST:     NO           INSRVMOD:    NA
         
         RANGE:       NA           DEFVALUE:    0
         
         UNITS:       octets       SPARSE:      NO
         
         DESCR:       NA"
    ::= { fsAggIfEntry 10 }

fsAggIfInUcastPkts OBJECT-TYPE
    SYNTAX      Counter
    ACCESS      read-only
    STATUS      mandatory
    DESCRIPTION 
        "The total number of unicast user data frames received by the
         
         aggregation. This value is calculated as the value of 
         
         'fsAggIfInPkts', les the values of 'fsAggIfInMulticastPkts'
         
         and 'fsAggIfInBroadcastPkts.'
         
         ALCATEL NOTE:
         
         ACCESS:      NA           USAGE:       NA
         
         PERSIST:     NO           INSRVMOD:    NA
         
         RANGE:       NA           DEFVALUE:    0
         
         UNITS:       frames       SPARSE:      NO
         
         DESCR:       NA"
    ::= { fsAggIfEntry 11 }

fsAggIfInDiscards OBJECT-TYPE
    SYNTAX      Counter
    ACCESS      read-only
    STATUS      mandatory
    DESCRIPTION 
        "The total count of frames,received on all ports that are 
         
         (or have been)members of the aggregation,that were 
         
         discarded by the Collection function of the Aggregator as they
         
         were received on ports whose Collection function was disabled.
         
         This value is read-only.
         
         ALCATEL NOTE:
         
         ACCESS:      NA           USAGE:       NA
         
         PERSIST:     NO           INSRVMOD:    NA
         
         RANGE:       NA           DEFVALUE:    0
         
         UNITS:       frames       SPARSE:      NO
         
         DESCR:       NA"
    ::= { fsAggIfEntry 12 }

fsAggIfInErrors OBJECT-TYPE
    SYNTAX      Counter
    ACCESS      read-only
    STATUS      mandatory
    DESCRIPTION 
        "The total count of frames discarded on reception by all 
         
         ports that are (or have been)members of the aggregation,or 
         
         that were discarded by the Collection function of the 
         
         Aggregator,or that were discarded by the Aggregator 
         
         due to the detection of an illegal Slow Protocols PDU .
         
         This value is read-only.
         
         ALCATEL NOTE:
         
         ACCESS:      NA           USAGE:       NA
         
         PERSIST:     NO           INSRVMOD:    NA
         
         RANGE:       NA           DEFVALUE:    0
         
         UNITS:       frames       SPARSE:      NO
         
         DESCR:       NA"
    ::= { fsAggIfEntry 13 }

fsAggIfInUnknownProtos OBJECT-TYPE
    SYNTAX      Counter
    ACCESS      read-only
    STATUS      mandatory
    DESCRIPTION 
        "The total count of frames discarded on reception by all ports 
         
         that are (or have been)members of the aggregation,due to the 
         
         detection of an unknown Slow Protocols PDU .
         
         This value is read-only.
         
         ALCATEL NOTE:
         
         ACCESS:      NA           USAGE:       NA
         
         PERSIST:     NO           INSRVMOD:    NA
         
         RANGE:       NA           DEFVALUE:    0
         
         UNITS:       frames       SPARSE:      NO
         
         DESCR:       NA"
    ::= { fsAggIfEntry 14 }

fsAggIfOutOctets OBJECT-TYPE
    SYNTAX      Counter
    ACCESS      read-only
    STATUS      mandatory
    DESCRIPTION 
        "The total count of octets including padding octets 
         
         transmitted by this Aggregator on all Aggregation Ports
         
         that are (or have been) members of the aggregation.The 
         
         count does not include octets transmitted by the Aggregator
         
         in frames that carry LACPDUs or Marker PDUs .However,
         
         it includes frames discarded by the Distribution function
         
         of the Aggregator . This value is read-only.;.
         
         ALCATEL NOTE:
         
         ACCESS:      NA           USAGE:       NA
         
         PERSIST:     NO           INSRVMOD:    NA
         
         RANGE:       NA           DEFVALUE:    0
         
         UNITS:       octets       SPARSE:      NO
         
         DESCR:       NA"
    ::= { fsAggIfEntry 15 }

fsAggIfOutUcastPkts OBJECT-TYPE
    SYNTAX      Counter
    ACCESS      read-only
    STATUS      mandatory
    DESCRIPTION 
        "The total number of unicast user data frames transmitted by 
         
         aggregation. This value is calculated as the value of
         
         'fsAggIfOutPkts' , less the value of 'fsAggIfOutMulticastPkts'
         
         and 'fsAggIfOutBroadcastPkts'
         
         ALCATEL NOTE:
         
         ACCESS:      NA           USAGE:       NA
         
         PERSIST:     NO           INSRVMOD:    NA
         
         RANGE:       NA           DEFVALUE:    0
         
         UNITS:       frames       SPARSE:      NO
         
         DESCR:       NA"
    ::= { fsAggIfEntry 16 }

fsAggIfOutDiscards OBJECT-TYPE
    SYNTAX      Counter
    ACCESS      read-only
    STATUS      mandatory
    DESCRIPTION 
        "The total count of frames requested to be transmitted by this
         
         Aggregator that were discarded by the Distribution function of 
         
         the Aggregator when conversations are re-allocated to different
         
         ports,due to the requirement to ensure that the conversations
         
         are flushed on the old ports in order to maintain proper frame 
         
         ordering ,or discarded as a result of excessive collisions by 
         
         ports that are (or ha e been)members of the aggregation.
         
         This value is read-only.
         
         ALCATEL NOTE:
         
         ACCESS:      NA           USAGE:       NA
         
         PERSIST:     NO           INSRVMOD:    NA
         
         RANGE:       NA           DEFVALUE:    0
         
         UNITS:       frames       SPARSE:      NO
         
         DESCR:       NA"
    ::= { fsAggIfEntry 17 }

fsAggIfOutErrors OBJECT-TYPE
    SYNTAX      Counter
    ACCESS      read-only
    STATUS      mandatory
    DESCRIPTION 
        "The total count of frames requested to be transmitted by this
         
         Aggregator that experienced transmission errors on ports that
         
         are (or have been)members of the aggregation.This count does
         
         not include frames discarded due to excess collisions.
         
         
         
         This value is read-only.
         
         ALCATEL NOTE:
         
         ACCESS:      NA           USAGE:       NA
         
         PERSIST:     NO           INSRVMOD:    NA
         
         RANGE:       NA           DEFVALUE:    0
         
         UNITS:       frames       SPARSE:      NO
         
         DESCR:       NA"
    ::= { fsAggIfEntry 18 }

fsTrapAggIndex OBJECT-TYPE
    SYNTAX      InterfaceIndex
    ACCESS      read-only
    STATUS      mandatory
    DESCRIPTION 
        "This Index used to generate TRAP for the particular aggregator
         
         ALCATEL NOTE:
         
            ACCESS:      NA           USAGE:       NA
         
            PERSIST:     NO           INSRVMOD:    NA
         
            RANGE:       DEP        DEFVALUE:    NA
         
            UNITS:       NA           SPARSE:      NO
         
            DESCR:       DEP(RANGE): The Value is the maximum number of physical interfaces available in the system.
         
         			This is obtained from the object issSystemNumberOfPorts in fsiss.mib"
    ::= { fsAggIfEntry 19 }

fsAggIfXTable OBJECT-TYPE
    SYNTAX      SEQUENCE OF FsAggIfXEntry
    ACCESS      not-accessible
    STATUS      mandatory
    DESCRIPTION 
        "A list of interface entries.  The number of entries
         
         is given by the value of ifNumber.  This table
         
         contains additional objects for the interface table.
         
         ALCATEL NOTE:
         
         TABLESIZE: DEP
         
         DESCR:	 DEP(TABLESIZE)The range of this table is derived from the number of
         
         	       physical interfaces in the system. This value can be 
         
         	       got from the object issSystemNumberOfPorts in fsiss.mib. "
    ::= { fsLaAggIf 2 }

fsAggIfXEntry OBJECT-TYPE
    SYNTAX      FsAggIfXEntry
    ACCESS      not-accessible
    STATUS      mandatory
    DESCRIPTION 
        "An entry containing additional management information
         
         applicable to a particular interface.
         
         Row creation : All entries will be created during system start-up if fsLaSystemControl
         
         is set to 'start' or whenever fsLaSystemControl is set to 'start'.
         
         Row deletion : All entries will be deleted when fsLaSystemControl is set to 'shutdown'.
         
         Index usage : the index is the Agg Interface index.
         
         Note that entries will be presented to the SNMP manager in full
         
         lexicographical order :  sorted on Agg Interface index."
    INDEX       { fsAggIfIndex }
    ::= { fsAggIfXTable 1 }

FsAggIfXEntry ::= SEQUENCE {
    fsAggIfName                     DisplayString,
    fsAggIfLinkUpDownTrapEnable     INTEGER,
    fsAggIfConnectorPresent         TruthValue,
    fsAggIfHighSpeed                Gauge,
    fsAggIfInMulticastPkts          Counter,
    fsAggIfInBroadcastPkts          Counter,
    fsAggIfInPkts                   Counter,
    fsAggIfOutMulticastPkts         Counter,
    fsAggIfOutBroadcastPkts         Counter,
    fsAggIfOutPkts                  Counter
}

fsAggIfName OBJECT-TYPE
    SYNTAX      DisplayString (SIZE(0..20))
    ACCESS      read-write
    STATUS      mandatory
    DESCRIPTION 
        "Human-readable text string containing a locally significant name 
         
         for the Aggregator.This string is read-write.
         
         ALCATEL NOTE:
         
         ACCESS:      NA           USAGE:       NA
         
         PERSIST:     YES          INSRVMOD:    YES
         
         RANGE:       NA           DEFVALUE:    NA
         
         UNITS:       NA           SPARSE:      NO
         
         DESCR:       NA"
    ::= { fsAggIfXEntry 1 }

fsAggIfLinkUpDownTrapEnable OBJECT-TYPE
    SYNTAX      INTEGER { enabled(1), disabled(2) }
    ACCESS      read-write
    STATUS      mandatory
    DESCRIPTION 
        "When set to 'enabled',Link Up and Link Down notifications are
         
         enabled for this Aggregator.  When set to 'disabled' Link Up 
         
         and Link Down notifications are disabled for this 
         
         Aggregator.This value is read-write.
         
         ALCATEL NOTE:
         
         ACCESS:      NA           USAGE:       NA
         
         PERSIST:     YES          INSRVMOD:    YES
         
         RANGE:       NA           DEFVALUE:    disabled
         
         UNITS:       NA           SPARSE:      NO
         
         DESCR:       NA"
    ::= { fsAggIfXEntry 2 }

fsAggIfConnectorPresent OBJECT-TYPE
    SYNTAX      TruthValue
    ACCESS      read-only
    STATUS      mandatory
    DESCRIPTION 
        "This object has the value 'true(1)' if the interface
         
         sublayer has a physical connector and the value
         
         'false(2)' otherwise.
         
           
         
         For an aggregator interface this value will be 'false'
         
         ALCATEL NOTE:
         
         ACCESS:      NA           USAGE:       NA
         
         PERSIST:     NO           INSRVMOD:    NA
         
         RANGE:       2            DEFVALUE:    false
         
         UNITS:       NA           SPARSE:      NO
         
         DESCR:       NA"
    ::= { fsAggIfXEntry 3 }

fsAggIfHighSpeed OBJECT-TYPE
    SYNTAX      Gauge
    ACCESS      read-only
    STATUS      mandatory
    DESCRIPTION 
        " For Aggregator interface this value is 0 
         
         ALCATEL NOTE:
         
            ACCESS:      NA           USAGE:       NA
         
            PERSIST:     NO           INSRVMOD:    NA
         
            RANGE:       0            DEFVALUE:    0
         
            UNITS:       NA           SPARSE:      NO
         
            DESCR:       NA"
    ::= { fsAggIfXEntry 4 }

fsAggIfInMulticastPkts OBJECT-TYPE
    SYNTAX      Counter
    ACCESS      read-only
    STATUS      mandatory
    DESCRIPTION 
        "The total count of multicast frames received by this Aggregator,
         
         from the Aggregation Ports that are (or have been)members of 
         
         the aggregation,that were addressed to an active group address
         
         other than the broadcast address.The count does not include
         
         frames that carry LACP or Marker PDUs ,or frames discarded by
         
         the Collection function of the Aggregator .
         
         
         
         This value is read-only.
         
         ALCATEL NOTE:
         
         ACCESS:      NA           USAGE:       NA
         
         PERSIST:     NO           INSRVMOD:    NA
         
         RANGE:       NA           DEFVALUE:    0
         
         UNITS:       frames       SPARSE:      NO
         
         DESCR:       NA"
    ::= { fsAggIfXEntry 5 }

fsAggIfInBroadcastPkts OBJECT-TYPE
    SYNTAX      Counter
    ACCESS      read-only
    STATUS      mandatory
    DESCRIPTION 
        "The total count of the broadcast data frames received by this 
         
         Aggregator, from the Aggregation Ports that are (or have been)
         
         members of the aggregation.The count does not include frames 
         
         that carry LACP or Marker PDUs ,illegal or unknown protocol
         
         frames,or frames discarded by the Collection function of the
         
         Aggregator .
         
         
         
         This value is read-only.
         
         ALCATEL NOTE:
         
         ACCESS:      NA           USAGE:       NA
         
         PERSIST:     NO           INSRVMOD:    NA
         
         RANGE:       NA           DEFVALUE:    0
         
         UNITS:       frames       SPARSE:      NO
         
         DESCR:       NA"
    ::= { fsAggIfXEntry 6 }

fsAggIfInPkts OBJECT-TYPE
    SYNTAX      Counter
    ACCESS      read-only
    STATUS      mandatory
    DESCRIPTION 
        "The total count of frames received by this Aggregator,
         
         from the Aggregation Ports that are (or have been)members 
         
         of the aggregation.The count does not include frames that
         
         carry LACP or Marker PDUs.
         
         This value is read-only.
         
         ALCATEL NOTE:
         
         ACCESS:      NA           USAGE:       NA
         
         PERSIST:     NO           INSRVMOD:    NA
         
         RANGE:       NA           DEFVALUE:    0
         
         UNITS:       frames       SPARSE:      NO
         
         DESCR:       NA"
    ::= { fsAggIfXEntry 7 }

fsAggIfOutMulticastPkts OBJECT-TYPE
    SYNTAX      Counter
    ACCESS      read-only
    STATUS      mandatory
    DESCRIPTION 
        "The total count of multicast frames transmitted by this Aggregator on all
         
         Aggregation Ports that are (or have been)members of the 
         
         aggregation,to a group destination address other than the
         
         broadcast address.The count does not include frames transmitted 
         
         by the Aggregator that carry LACP or Marker PDUs .
         
         
         
         However,it includes frames discarded by the Distribution
         
         function of the Aggregator.
         
         
         
         This value is read-only.
         
         ALCATEL NOTE:
         
         ACCESS:      NA           USAGE:       NA
         
         PERSIST:     NO           INSRVMOD:    NA
         
         RANGE:       NA           DEFVALUE:    0
         
         UNITS:       frames       SPARSE:      NO
         
         DESCR:       NA"
    ::= { fsAggIfXEntry 8 }

fsAggIfOutBroadcastPkts OBJECT-TYPE
    SYNTAX      Counter
    ACCESS      read-only
    STATUS      mandatory
    DESCRIPTION 
        "the total count of the broadcast data frames transmitted by this 
         
         Aggregator on all Aggregation Ports that are (or have been)
         
         members of the aggregation.The count does not include frames 
         
         transmitted by the Aggregator that carry LACP or Marker PDUs
         
         However,it includes frames discarded by the Distribution 
         
         function of the Aggregator .This value is read-only.
         
         ALCATEL NOTE:
         
         ACCESS:      NA           USAGE:       NA
         
         PERSIST:     NO           INSRVMOD:    NA
         
         RANGE:       NA           DEFVALUE:    0
         
         UNITS:       frames       SPARSE:      NO
         
         DESCR:       NA"
    ::= { fsAggIfXEntry 9 }

fsAggIfOutPkts OBJECT-TYPE
    SYNTAX      Counter
    ACCESS      read-only
    STATUS      mandatory
    DESCRIPTION 
        "The total count of frames transmitted by this Aggregator on
         
         all Aggregation Ports that are (or have been)members of the
         
         aggregation.The count does not include frames transmitted by
         
         the Aggregator that carry LACP or Marker PDUs .
         
         This value is read-only.
         
         ALCATEL NOTE:
         
         ACCESS:      NA           USAGE:       NA
         
         PERSIST:     NO           INSRVMOD:    NA
         
         RANGE:       NA           DEFVALUE:    0
         
         UNITS:       frames       SPARSE:      NO
         
         DESCR:       NA"
    ::= { fsAggIfXEntry 10 }

fsAggConfigTable OBJECT-TYPE
    SYNTAX      SEQUENCE OF FsAggConfigEntry
    ACCESS      not-accessible
    STATUS      mandatory
    DESCRIPTION 
        "A list of Aggregator interface entries.
         
         ALCATEL NOTE:
         
         	TABLESIZE: DEP
         
            	DESCR:	 DEP(TABLESIZE)The range of this table is derived from the number of
         
         		       physical interfaces in the system. This value can be 
         
         		       got from the object issSystemNumberOfPorts in fsiss.mib. "
    ::= { fsLaAggIf 3 }

fsAggConfigEntry OBJECT-TYPE
    SYNTAX      FsAggConfigEntry
    ACCESS      not-accessible
    STATUS      mandatory
    DESCRIPTION 
        "An entry contains configurable information applicable
         
         to a particular Aggregator interface.
         
         
         
         This table is indexed by the ifIndex of the aggregator
         
         Row creation : All entries will be created during system start-up if fsLaSystemControl
         
         is set to 'start' or whenever fsLaSystemControl is set to 'start'.
         
         Row deletion : All entries will be deleted when fsLaSystemControl is set to 'shutdown'.
         
         Index usage : the index is the Agg Interface index.
         
         Note that entries will be presented to the SNMP manager in full
         
         lexicographical order :  sorted on Agg Interface index."
    INDEX       { fsAggIfIndex }
    ::= { fsAggConfigTable 1 }

FsAggConfigEntry ::= SEQUENCE {
    fsAggSelectionPolicy    INTEGER
}

fsAggSelectionPolicy OBJECT-TYPE
    SYNTAX      INTEGER { macSrc(1), macDst(2), macSrcDst(3), ipSrc(4), 
                    ipDst(5), ipSrcDst(6) }
    ACCESS      read-write
    STATUS      mandatory
    DESCRIPTION 
        "Link selection policy to be used by the aggregator. The 
         
         selection policies based on the IP address can be set if
         
         and only if hardware is present and supported.
         
         ALCATEL NOTE:
         
         ACCESS:      NA           USAGE:       NA
         
         PERSIST:     YES          INSRVMOD:    YES
         
         RANGE:       NA           DEFVALUE:    NA
         
         UNITS:       NA           SPARSE:      NO
         
         DESCR:       NA"
    DEFVAL      { macSrcDst }
    ::= { fsAggConfigEntry 1 }

fsLaAggPort OBJECT IDENTIFIER
    ::= { fsla 4 }

fsAggPortTable OBJECT-TYPE
    SYNTAX      SEQUENCE OF FsAggPortEntry
    ACCESS      not-accessible
    STATUS      mandatory
    DESCRIPTION 
        "A table that contains objects to reset specific fields of
         
         the dot3adAggPortActorAdminState and dot3adAggPortPartnerAdminState 
         
         of dot3adAggPortTable.
         
         ALCATEL NOTE:
         
         TABLESIZE: DEP
         
         DESCR:	 DEP(TABLESIZE):The range of this table is derived from the number of
         
         	       physical interfaces in the system. This value can be 
         
         	       got from the object issSystemNumberOfPorts in fsiss.mib. "
    ::= { fsLaAggPort 1 }

fsAggPortEntry OBJECT-TYPE
    SYNTAX      FsAggPortEntry
    ACCESS      not-accessible
    STATUS      mandatory
    DESCRIPTION 
        "Each entry in this table is for each physical port that participates 
         
         in Link Aggregation which can be either aggregatable or individual.
         
         This table is indexed by the InterfaceIndex.
         
         Row creation : All entries will be created during system start-up if fsLaSystemControl
         
         	is set to 'start' or whenever fsLaSystemControl is set to 'start'.
         
         Row deletion : All entries will be deleted when fsLaSystemControl is set to 'shutdown'.
         
         Index usage : the index is the Agg Port index.
         
         Note that entries will be presented to the SNMP manager in full
         
         lexicographical order :  sorted on Agg Port index."
    INDEX       { fsAggPortIndex }
    ::= { fsAggPortTable 1 }

FsAggPortEntry ::= SEQUENCE {
    fsAggPortIndex                      InterfaceIndex,
    fsAggPortResetActorAdminState       LacpState,
    fsAggPortResetPartnerAdminState     LacpState,
    fsAggPortLacpMode                   INTEGER,
    fsAggPortStandByOrActive            INTEGER
}

fsAggPortIndex OBJECT-TYPE
    SYNTAX      InterfaceIndex
    ACCESS      not-accessible
    STATUS      mandatory
    DESCRIPTION 
        "The ifIndex of the port
         
         ALCATEL NOTE:
         
            ACCESS:      NA           USAGE:       NA
         
            PERSIST:     YES          INSRVMOD:    NA
         
            RANGE:       DEP        DEFVALUE:    NA
         
            UNITS:       NA           SPARSE:      NO
         
            DESCR:       DEP(RANGE): The Value is the maximum number of physical interfaces available in the system.
         
         			This is obtained from the object issSystemNumberOfPorts in fsiss.mib"
    ::= { fsAggPortEntry 1 }

fsAggPortResetActorAdminState OBJECT-TYPE
    SYNTAX      LacpState
    ACCESS      read-write
    STATUS      mandatory
    DESCRIPTION 
        "A string of 8 bits,corresponding to the administrative values
         
         of Actor_State as transmitted by the Actor in LACPDUs.
         
         
         
         The first bit corresponds to bit 0 of Actor_State (LACP_Activity),
         
         the second bit corresponds to bit 1 (LACP_Timeout),the third bit
         
         corresponds to bit 2 (Aggregation),the fourth bit corresponds to
         
         bit 3 (Synchronization),the fifth bit corresponds to bit 4
         
         (Collecting),the sixth bit corresponds to bit 5 (Distributing),
         
         the seventh bit corresponds to bit 6 (Defaulted),and the eighth
         
         bit corresponds to bit 7 (Expired).
         
         
         
         This object allows the RESET of the values of Actor LACP_Activity, 
         
         LACP_Timeout and Aggregation.
         
         
         
         Get operation on this object returns the current Port State of 
         
         the Actor
         
         ALCATEL NOTE:
         
            ACCESS:      NA           USAGE:       NA
         
            PERSIST:     YES          INSRVMOD:    YES
         
            RANGE:       NA           DEFVALUE:    'B'
         
            UNITS:       NA           SPARSE:      NO
         
            DESCR:       Bits 0-4 should be 0 while setting"
    ::= { fsAggPortEntry 2 }

fsAggPortResetPartnerAdminState OBJECT-TYPE
    SYNTAX      LacpState
    ACCESS      read-write
    STATUS      mandatory
    DESCRIPTION 
        "A string of 8 bits,corresponding to the administrative values
         
         of Partner_State as transmitted by the partner in LACPDUs.
         
         
         
         The first bit corresponds to bit 0 of Actor_State (LACP_Activity),
         
         the second bit corresponds to bit 1 (LACP_Timeout),the third bit
         
         corresponds to bit 2 (Aggregation),the fourth bit corresponds to
         
         bit 3 (Synchronization),the fifth bit corresponds to bit 4
         
         (Collecting),the sixth bit corresponds to bit 5 (Distributing),
         
         the seventh bit corresponds to bit 6 (Defaulted),and the eighth
         
         bit corresponds to bit 7 (Expired).
         
         
         
         This object allows the RESET of the values of Partner LACP_Activity, 
         
         LACP_Timeout and Aggregation.
         
         
         
         Get operation on this object returns the current Port State of 
         
         the Partner
         
         ALCATEL NOTE:
         
            ACCESS:      NA           USAGE:       NA
         
            PERSIST:     YES          INSRVMOD:    YES
         
            RANGE:       NA           DEFVALUE:    'C'
         
            UNITS:       NA           SPARSE:      NO
         
            DESCR:       Bits 0-4 should be 0 while setting"
    ::= { fsAggPortEntry 3 }

fsAggPortLacpMode OBJECT-TYPE
    SYNTAX      INTEGER { lacpEnable(1), lacpDisable(2), manualConfig(3) }
    ACCESS      read-write
    STATUS      mandatory
    DESCRIPTION 
        "This object is used to enable LACP , disable LACP or manually aggregate a port
         
         ALCATEL NOTE:
         
            ACCESS:      NA           USAGE:       NA
         
            PERSIST:     YES          INSRVMOD:    DEP
         
            RANGE:       NA           DEFVALUE:    lacpDisable
         
            UNITS:       NA           SPARSE:      NO
         
            DESCR:       Can be set only if IssMacLearningStatus is enabled"
    ::= { fsAggPortEntry 4 }

fsAggPortStandByOrActive OBJECT-TYPE
    SYNTAX      INTEGER { active(0), standby(1) }
    ACCESS      read-only
    STATUS      mandatory
    DESCRIPTION 
        "This read-only object is used to find if a particular is in Active or 
         
         StandBy
         
         	ALCATEL NOTE:
         
               ACCESS:      NA           USAGE:       NA
         
               PERSIST:     NO           INSRVMOD:    NA
         
               RANGE:       NA           DEFVALUE:    active
         
               UNITS:       NA           SPARSE:      NO
         
               DESCR:       NA"
    ::= { fsAggPortEntry 5 }

fsAgglinkDownNotification TRAP-TYPE
    ENTERPRISE  fsla
    VARIABLES   { fsTrapAggIndex, fsAggIfOperStatus }
--     STATUS      mandatory
    DESCRIPTION 
        " When AggIfLinkUpDownNotificationEnable is set to enabled,
         
         a Link Down notification is generated when the Operational 
         
         State of the aggregator changes from up to down. When 
         
         fsAggIfLinkUpDownTrapEnable is set to disabled,no Link 
         
         DOWN notifications are generated.
         
         
         
         The notification carries the identifier of the Aggregator 
         
         whose state has changed."
    ::= 1

fsAgglinkUpNotification TRAP-TYPE
    ENTERPRISE  fsla
    VARIABLES   { fsTrapAggIndex, fsAggIfOperStatus }
--     STATUS      mandatory
    DESCRIPTION 
        " When AggIfLinkUpDownNotificationEnable is set to enabled,
         
         a Link Up notification is generated when the Operational
         
         State of the aggregator changes from down to up. When 
         
         fsAggIfLinkUpDownTrapEnable is set to disabled,no Link 
         
         Up notifications are generated. 
         
         
         
         The notification carries the identifier of the Aggregator
         
         whose state has changed."
    ::= 2

END -- end of module LA-MIB.
