--
-- This SMIv1 module has been generated by smidump 0.4.8. Do not edit.
--

FutureSnmp-MIB DEFINITIONS ::= BEGIN

IMPORTS
    OBJECT-TYPE
        FROM RFC-1212
    Gauge, IpAddress, enterprises
        FROM RFC1155-SMI
    DisplayString
        FROM SNMPv2-TC;

futuresnmp OBJECT IDENTIFIER
    ::= { enterprises futuresoftware(2076) 50 }

-- futuresnmp MODULE-IDENTITY
--     LAST-UPDATED "200205051937Z"
--     ORGANIZATION 
--         "Future Software Ltd.,"
--     CONTACT-INFO 
--         "  V.VIVEKANANDAN
--          Postal :  Future Software Pvt. Ltd.,
--                    480-481, Anna Salai,
--                    Nandanam,
--                    Chennai,
--                    India  600 035
--           Tel   :  +91-44-433 055 0
--           E-Mail:  vivekav@future.futsoft.com "
--     DESCRIPTION 
--         "The MIB module is for managing FutureSNMP."
--     REVISION    "200205051937Z"
--     DESCRIPTION 
--         "The initial revision of this MIB module was published as
--          RFC 1450."
--     ::= { enterprises futuresoftware(2076) 50 }


EntryStatus ::=
    INTEGER { valid(1), createRequest(2), underCreation(3), invalid(4) }

-- EntryStatus ::= TEXTUAL-CONVENTION
--     STATUS      mandatory
--     DESCRIPTION 
--         "Enumerated integer data type"
--     SYNTAX      INTEGER
--                   { valid(1), createRequest(2), underCreation(3), 
--                     invalid(4) }

fsSnmpListenPort OBJECT-TYPE
    SYNTAX      INTEGER (0..65535)
    ACCESS      read-only
    STATUS      mandatory
    DESCRIPTION 
        "Contains Port Number on which snmp
         Agent listens.
         ALCATEL NOTE:
         ACCESS:     NA	USAGE   :    NA
         PERSIST:    NO    	INSRVMOD:    NA
         RANGE:      NA	DEFVALUE:    NA
         UNITS:      NA	SPARSE:      NA
         DESCR:    NA"
    DEFVAL      { 161 }
    ::= { futuresnmp 1 }

fsSnmpListenTrapPort OBJECT-TYPE
    SYNTAX      INTEGER (0..65535)
    ACCESS      read-only
    STATUS      mandatory
    DESCRIPTION 
        "Contains Port Number on which snmp trap
         message are sent to manager.
         ALCATEL NOTE:
         ACCESS:     NA	USAGE   :    NA
         PERSIST:    NO      INSRVMOD:    NA
         RANGE:      NA	DEFVALUE:    NA
         UNITS:      NA	SPARSE:      NA
         DESCR:   NA"
    DEFVAL      { 162 }
    ::= { futuresnmp 2 }

fsSnmpCommunityTable OBJECT-TYPE
    SYNTAX      SEQUENCE OF FsSnmpCommunityEntry
    ACCESS      not-accessible
    STATUS      mandatory
    DESCRIPTION 
        "The SNMP Community Table is used to store the 
         machine and it's priviliges.
         ALCATEL NOTE :
         TABLESIZE    :10    
         DESCR        :NA"
    ::= { futuresnmp 3 }

fsSnmpCommunityEntry OBJECT-TYPE
    SYNTAX      FsSnmpCommunityEntry
    ACCESS      not-accessible
    STATUS      mandatory
    DESCRIPTION 
        "Each entry contains one community entry information.
         Row creation : A SnmpCommunity entry shall be created in one step by a
          set-request with all necessary parameter values and fsSnmpCommunityIndex set to Create-request(2).
         Row deletion : A SnmpCommunity entry shall be deleted by setting
          the fsSnmpCommunityIndex of the specific entry to invalid(4)
         Index usage : the index is fsSnmpCommunityIndex.
         Note that entries will be presented to the SNMP manager in full
         lexicographical order :  sorted on fsSnmpCommunityIndex"
    INDEX       { fsSnmpCommunityIndex }
    ::= { fsSnmpCommunityTable 1 }

FsSnmpCommunityEntry ::= SEQUENCE {
    fsSnmpCommunityIndex        INTEGER,
    fsSnmpCommunityName         DisplayString,
    fsSnmpCommunityPrivilege    INTEGER,
    fsSnmpCommunityIpAddr       IpAddress,
    fsSnmpStatus                EntryStatus
}

fsSnmpCommunityIndex OBJECT-TYPE
    SYNTAX      INTEGER (1..10)
    ACCESS      not-accessible
    STATUS      mandatory
    DESCRIPTION 
        "Index to the community table.
         ALCATEL NOTE:
           ACCESS:      NA           	 USAGE		: NA
           PERSIST:     YES          	 INSRVMOD	: NA 
           RANGE:       NA             	 DEFVALUE	: NA  
           UNITS:       NA              	 SPARSE		: NO
           DESCR:       NA"
    ::= { fsSnmpCommunityEntry 1 }

fsSnmpCommunityName OBJECT-TYPE
    SYNTAX      DisplayString (SIZE(0..255))
    ACCESS      read-write
    STATUS      mandatory
    DESCRIPTION 
        "The Community name.
         ALCATEL NOTE:
              ACCESS:      NA           	USAGE:       MAND
              PERSIST:     YES          	INSRVMOD:    YES
              RANGE:       NA           	DEFVALUE:    NA
              UNITS:       NA               	SPARSE:      NO
              DESCR:       NA"
    ::= { fsSnmpCommunityEntry 2 }

fsSnmpCommunityPrivilege OBJECT-TYPE
    SYNTAX      INTEGER { readonly(1), readwrite(2) }
    ACCESS      read-write
    STATUS      mandatory
    DESCRIPTION 
        "The previlige type.
         ALCATEL NOTE:
         ACCESS:      NA           	USAGE:       NA
         PERSIST:     YES          	INSRVMOD:    YES
         RANGE:       NA             	DEFVALUE:    NA
         UNITS:       NA               	SPARSE:      NO
         DESCR:       NA"
    DEFVAL      { readonly }
    ::= { fsSnmpCommunityEntry 3 }

fsSnmpCommunityIpAddr OBJECT-TYPE
    SYNTAX      IpAddress
    ACCESS      read-write
    STATUS      mandatory
    DESCRIPTION 
        "The IpAddress corresponding to the Community name.
         ALCATEL NOTE:
         ACCESS:      NA             	USAGE:       NA
         PERSIST:     YES           	INSRVMOD:    YES
         RANGE:       NA              	DEFVALUE:    NA
         UNITS:       NA                	SPARSE:      NO
         DESCR:       NA"
    DEFVAL      { '00000000'H }
    ::= { fsSnmpCommunityEntry 4 }

fsSnmpStatus OBJECT-TYPE
    SYNTAX      EntryStatus
    ACCESS      read-write
    STATUS      mandatory
    DESCRIPTION 
        " The Status of this snmpStatus entry
         ALCATEL NOTE:
              ACCESS:      NA            	USAGE:       MAND
              PERSIST:     YES           	INSRVMOD:    YES
              RANGE:       1..4              	DEFVALUE:    NA
              UNITS:       NA                	SPARSE:      NO
              DESCR:       NA"
    ::= { fsSnmpCommunityEntry 5 }

fsSnmpTrapTable OBJECT-TYPE
    SYNTAX      SEQUENCE OF FsSnmpTrapEntry
    ACCESS      not-accessible
    STATUS      mandatory
    DESCRIPTION 
        "The SNMP Trap Table is used to store the 
         IP addr the managers willing to receive the traps from 
         the device.
         
         This table is not supported anymore due to dual IP removal.
         Lanx will be using this table internally to send the trap to NT.
         ALCATEL NOTE :
         TABLESIZE    :10
         DESCR        :NA"
    ::= { futuresnmp 4 }

fsSnmpTrapEntry OBJECT-TYPE
    SYNTAX      FsSnmpTrapEntry
    ACCESS      not-accessible
    STATUS      mandatory
    DESCRIPTION 
        "Each entry contains one Manager entry information.
         Row creation : A SnmpTrap entry shall be created in one step by a
          set-request with all necessary parameter values and fsSnmpTrapIpAddr,fsSnmpTrapPort set to Create-request(2).
         Row deletion : A SnmpTrap entry shall be deleted by setting
          the fsSnmpTrapIpAddr,fsSnmpTrapPort of the specific entry to invalid(4)
         Index usage : the index is fsSnmpCommunityIndex.
         Note that entries will be presented to the SNMP manager in full
         lexicographical order :  sorted on fsSnmpTrapIpAddr,fsSnmpTrapPort index
         
         This is not used by Alcatel"
    INDEX       { fsSnmpTrapIpAddr, fsSnmpTrapPort }
    ::= { fsSnmpTrapTable 1 }

FsSnmpTrapEntry ::= SEQUENCE {
    fsSnmpTrapIpAddr            IpAddress,
    fsSnmpTrapPort              INTEGER,
    fsSnmpAlarmSeverity         INTEGER,
    fsSnmpTrapMask              INTEGER,
    fsSnmpTrapCommunityName     DisplayString,
    fsSnmpTrapMgrType           INTEGER,
    fsSnmpTrapStatus            EntryStatus
}

fsSnmpTrapIpAddr OBJECT-TYPE
    SYNTAX      IpAddress
    ACCESS      not-accessible
    STATUS      mandatory
    DESCRIPTION 
        "The IpAddress corresponding to the Trap Community name.
         ALCATEL NOTE:
               ACCESS:      NA           	USAGE:       NA
               PERSIST:     YES          	INSRVMOD:    NA
               RANGE:       NA             	DEFVALUE:    NA      
               UNITS:       NA               	SPARSE:      NO
               DESCR:       NA"
    ::= { fsSnmpTrapEntry 1 }

fsSnmpTrapPort OBJECT-TYPE
    SYNTAX      INTEGER (1..2147483647)
    ACCESS      not-accessible
    STATUS      mandatory
    DESCRIPTION 
        "The port number corresponding to the Trap Community.
         ALCATEL NOTE:
               ACCESS:      NA            	USAGE:       NA
               PERSIST:     YES           	INSRVMOD:    NA
               RANGE:       0..0xffff     	DEFVALUE:    NA      
               UNITS:       NA            	SPARSE:      NO
               DESCR:       NA"
    ::= { fsSnmpTrapEntry 2 }

fsSnmpAlarmSeverity OBJECT-TYPE
    SYNTAX      INTEGER { indeterminate(1), warning(2), minor(3), 
                    major(4), critical(5) }
    ACCESS      read-write
    STATUS      mandatory
    DESCRIPTION 
        "Minumum severity level of alarms for which
         changeOccurred traps to be generated to the SNMP trap manager.
         Indeterminate represents the minimum alarm severe. 
         By default, severity level is set to indeterminate
         ALCATEL NOTE:
         ACCESS:      NA             	USAGE:       NA
         PERSIST:     YES           	INSRVMOD:    YES
         RANGE:       NA              	DEFVALUE:    NA      
         UNITS:       NA                	SPARSE:      NO
         DESCR:       NA"
    DEFVAL      { indeterminate }
    ::= { fsSnmpTrapEntry 3 }

fsSnmpTrapMask OBJECT-TYPE
    SYNTAX      INTEGER
    ACCESS      read-write
    STATUS      mandatory
    DESCRIPTION 
        "Bitmap of traps mask for each manager to enable
         or disable to send traps to the SNMP trap manager. 
         Trap mask is a 32-bit bitmap data.  
         				This bitmap is used to enable (bit=1) or disable (bit=0) 
         				the sending of traps to a specific manager. 
         				Bit 0 in the LSB is the rightmost bit in the bitmask. 
         				Bit numbers are the same as the trap Id.
         
         				Bit number	Trap
         				0	      ColdStart
         				4	      authenticationFailure      
         				7	      changeOccurred
         
         				Examples:
         				
         				1. (0x00000091)  - all traps enabled
         				2. (0x00000081)  - changeOccurred and coldStart traps enabled
         				
         				By default, all the three traps are enabled.
         ALCATEL NOTE:
         ACCESS:      NA            	USAGE:       NA
         PERSIST:     YES           	INSRVMOD:    YES
         RANGE:       NA              	DEFVALUE:    NA      
         UNITS:       NA                	SPARSE:      NO
         DESCR:       NA"
    DEFVAL      { 145 }
    ::= { fsSnmpTrapEntry 4 }

fsSnmpTrapCommunityName OBJECT-TYPE
    SYNTAX      DisplayString (SIZE(0..255))
    ACCESS      read-write
    STATUS      mandatory
    DESCRIPTION 
        "The Trap Community name.
         ALCATEL NOTE:
              ACCESS:      NA	       		USAGE:       NA
              PERSIST:     YES                INSRVMOD:    YES
              RANGE:       NA                 DEFVALUE:    NA  
              UNITS:       NA                 SPARSE:      NO
              DESCR:       NA"
    DEFVAL      { "PUBLIC" }
    ::= { fsSnmpTrapEntry 5 }

fsSnmpTrapMgrType OBJECT-TYPE
    SYNTAX      INTEGER { v1(1), v2(2) }
    ACCESS      read-write
    STATUS      mandatory
    DESCRIPTION 
        "The Manager type.
         ALCATEL NOTE:
               ACCESS:      NA             	USAGE:       NA
               PERSIST:     YES           	INSRVMOD:    YES
               RANGE:       NA              	DEFVALUE:    NA       
               UNITS:       NA                	SPARSE:      NO
               DESCR:       NA"
    DEFVAL      { v2 }
    ::= { fsSnmpTrapEntry 6 }

fsSnmpTrapStatus OBJECT-TYPE
    SYNTAX      EntryStatus
    ACCESS      read-write
    STATUS      mandatory
    DESCRIPTION 
        " The Status of this snmpTrapStatus entry
         ALCATEL NOTE:
         ACCESS:      NA           	USAGE:       MAND
         PERSIST:     YES          	INSRVMOD:    YES
         RANGE:       1..4             	DEFVALUE:    NA  
         UNITS:       NA               	SPARSE:      NO
         DESCR:       NA"
    ::= { fsSnmpTrapEntry 7 }

fsSnmpCommunityTableAccess OBJECT-TYPE
    SYNTAX      IpAddress
    ACCESS      read-write
    STATUS      mandatory
    DESCRIPTION 
        "Determine who all has the Access to Community Table.
         ALCATEL NOTE:
         ACCESS:     NA	                           USAGE   :    NA
         PERSIST:    YES                            INSRVMOD:    YES
         RANGE:      0x00000000,0xffffffff          DEFVALUE:    NA
         UNITS:      NA		                   SPARSE:      NA
         DESCR:   NA"
    DEFVAL      { 'ffffffff'H }
    ::= { futuresnmp 5 }

END -- end of module FutureSnmp-MIB.
