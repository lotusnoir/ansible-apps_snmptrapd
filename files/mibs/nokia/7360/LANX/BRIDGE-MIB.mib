--
-- This SMIv1 module has been generated by smidump 0.4.8. Do not edit.
--

BRIDGE-MIB DEFINITIONS ::= BEGIN

IMPORTS
    OBJECT-TYPE
        FROM RFC-1212
    Counter, Gauge, TimeTicks
        FROM RFC1155-SMI
    mib-2
        FROM RFC1213-MIB
    MacAddress
        FROM SNMPv2-TC;

dot1dBridge OBJECT IDENTIFIER
    ::= { mib-2 17 }

-- dot1dBridge MODULE-IDENTITY
--     LAST-UPDATED "200112190130Z"
--     ORGANIZATION 
--         "FUTURE SOFTWARE LIMITED"
--     CONTACT-INFO 
--         " FUTURE SOFTWARE LIMITED
--          481 Mount Road
--          Madras - 600 035
--          Phone : +91-44-433 055 0
--          support@futsoft.com   "
--     DESCRIPTION 
--         "This mib module is for standard Bridge mib"
--     REVISION    "200112190130Z"
--     DESCRIPTION 
--         "The initial revision of this MIB module was published as
--          RFC 1450."
--     ::= { mib-2 17 }


BridgeId ::=
    OCTET STRING (SIZE(8))

-- BridgeId ::= TEXTUAL-CONVENTION
--     STATUS      mandatory
--     DESCRIPTION 
--         " Identifier of Bridge in 8 byte format"
--     SYNTAX      OCTET STRING (SIZE(8))

Timeout ::=
    INTEGER

-- Timeout ::= TEXTUAL-CONVENTION
--     DISPLAY-HINT "d4"
--     STATUS      mandatory
--     DESCRIPTION 
--         " Time out value in 4 byte"
--     SYNTAX      INTEGER

dot1dBase OBJECT IDENTIFIER
    ::= { dot1dBridge 1 }

dot1dBaseBridgeAddress OBJECT-TYPE
    SYNTAX      MacAddress
    ACCESS      read-only
    STATUS      mandatory
    DESCRIPTION 
        "The MAC address used by this bridge when it must
         be referred to in a unique fashion.   It is
         recommended that this be the numerically smallest
         MAC address of all ports that belong to this
         bridge.  However it is only required to be unique.
         When concatenated with dot1dStpPriority a unique
         BridgeIdentifier is formed which is used in the
         Spanning Tree Protocol.
         ALCATEL NOTE:
         ACCESS:      NA            USAGE:       NA
         PERSIST:     NO            INSRVMOD:    NA
         RANGE:       NA            DEFVALUE:    NA
         UNITS:       NA            SPARSE:      NA
         DESCR:       NA"
--     REFERENCE   
--         "P802.1d/D9, July 14, 1989: Sections 6.4.1.1.3 and 3.12.5"
    ::= { dot1dBase 1 }

dot1dBaseNumPorts OBJECT-TYPE
    SYNTAX      INTEGER
    ACCESS      read-only
    STATUS      mandatory
    DESCRIPTION 
        "The number of ports ( 255 ) controlled by this bridging
         entity.
         ALCATEL NOTE:
         ACCESS:      NA             USAGE:       NA
         PERSIST:     NO             INSRVMOD:    NA
         RANGE:       DEP            DEFVALUE:   DEP 
         UNITS:       NA             SPARSE:      NA
         DESCR:       DEP(RANGE DEFVALUE) :The range of the index is maximum number of physical interfaces available in the system.
         			This is obtained from the object issSystemNumberOfPorts in fsiss.mib."
--     REFERENCE   
--         "P802.1d/D9, July 14, 1989: Section 6.4.1.1.3"
    ::= { dot1dBase 2 }

dot1dBaseType OBJECT-TYPE
    SYNTAX      INTEGER { unknown(1), transparentonly(2), 
                    sourcerouteonly(3), srt(4) }
    ACCESS      read-only
    STATUS      mandatory
    DESCRIPTION 
        "Indicates what type of bridging this bridge can
         perform.  If a bridge is actually performing a
         certain type of bridging this will be indicated by
         entries in the port table for the given type.
         ALCATEL NOTE:
         ACCESS:      NA           USAGE:       NA
         PERSIST:     NO           INSRVMOD:    NA
         RANGE:       2            DEFVALUE:    2
         UNITS:       NA           SPARSE:      NA
         DESCR:       NA"
    ::= { dot1dBase 3 }

dot1dBasePortTable OBJECT-TYPE
    SYNTAX      SEQUENCE OF Dot1dBasePortEntry
    ACCESS      not-accessible
    STATUS      mandatory
    DESCRIPTION 
        "A table that contains generic information about
         every port that is associated with this bridge.
         Transparent, source-route, and srt ports are
         included.
         ALCATEL NOTE:
         TABLESIZE: DEP
         DESCR: DEP(TABLESIZE) The table size is the maximum number of ports in the system.
         		    This value can be got from the object issSystemNumberOfPorts
         		    in fsiss.mib. "
    ::= { dot1dBase 4 }

dot1dBasePortEntry OBJECT-TYPE
    SYNTAX      Dot1dBasePortEntry
    ACCESS      not-accessible
    STATUS      mandatory
    DESCRIPTION 
        "A list of information for each port of the
         bridge.
         Row creation : All the Entries are created by the system at the startup.
         Row deletion : All the Entries are deleted by the system when it shutdowns.
         Index usage : the index is the dot1dBasePort.
         Note that entries will be presented to the SNMP manager in full
         lexicographical order :  sorted on dot1dBasePort."
--     REFERENCE   
--         "P802.1d/D9, July 14, 1989: Section 6.4.2, 6.6.1"
    INDEX       { dot1dBasePort }
    ::= { dot1dBasePortTable 1 }

Dot1dBasePortEntry ::= SEQUENCE {
    dot1dBasePort                       INTEGER,
    dot1dBasePortIfIndex                INTEGER,
    dot1dBasePortCircuit                INTEGER,
    dot1dBasePortDelayExceededDiscards  Counter,
    dot1dBasePortMtuExceededDiscards    Counter
}

dot1dBasePort OBJECT-TYPE
    SYNTAX      INTEGER (1..65535)
    ACCESS      not-accessible
    STATUS      mandatory
    DESCRIPTION 
        "The port number of the port for which this entry contains				
         bridge management information.
         ALCATEL NOTE:
         ACCESS:      NA           USAGE:       NA
         PERSIST:     NO           INSRVMOD:    NA
         RANGE:       DEP          DEFVALUE:    NA
         UNITS:       NA           SPARSE:      NO
         DESCR:	 DEP(RANGE):The range of the index isfrom 1 to the maximum number of physical interfaces available in the system.
         		This is obtained from the object issSystemNumberOfPorts in fsiss.mib"
    ::= { dot1dBasePortEntry 1 }

dot1dBasePortIfIndex OBJECT-TYPE
    SYNTAX      INTEGER
    ACCESS      read-only
    STATUS      mandatory
    DESCRIPTION 
        "An index value that uniquely identifies an interface. 
         The Interface identified by a particular value of this
         index  is the same interface as identified by the same 
         value of ifIndex.
         ALCATEL NOTE:
              ACCESS:      NA           USAGE:       NA
              PERSIST:     NO           INSRVMOD:    NA
              RANGE:       DEP          DEFVALUE:    NA                        
              UNITS:       NA           SPARSE:      NO
         	    DESCR: 	 DEP(RANGE):The range of the index isfrom 1 to the maximum number of physical interfaces available in the system.
         				This is obtained from the object issSystemNumberOfPorts in fsiss.mib"
    ::= { dot1dBasePortEntry 2 }

dot1dBasePortCircuit OBJECT-TYPE
    SYNTAX      INTEGER
    ACCESS      read-only
    STATUS      mandatory
    DESCRIPTION 
        "An index value that uniquely identifies a logical
         interface along with the dot1dBasePortIfIndex.
         This object can have value of 0xffff to indicate
         all circuits corresponding to dot1dBasePortIfIndex
         on X.25/Frame Relay interfaces. For PPP/Ethernet
         interfaces it should be zero.
         ALCATEL NOTE:
              ACCESS:      NA           USAGE:       NA
              PERSIST:     NO           INSRVMOD:    NA
              RANGE:       0            DEFVALUE:    0                   
              UNITS:       NA           SPARSE:      NO
              DESCR:       NA"
    ::= { dot1dBasePortEntry 3 }

dot1dBasePortDelayExceededDiscards OBJECT-TYPE
    SYNTAX      Counter
    ACCESS      read-only
    STATUS      mandatory
    DESCRIPTION 
        "The number of frames discarded by this port due
         to excessive transit delay through the bridge.  It
         is incremented by both transparent and source
         route bridges.
         ALCATEL NOTE:
         ACCESS:      NA           USAGE:       NA
         PERSIST:     NO           INSRVMOD:    NA
         RANGE:       NA           DEFVALUE:    0
         UNITS:       frames       SPARSE:      NO
         DESCR:       NA"
--     REFERENCE   
--         "P802.1d/D9, July 14, 1989: Section 6.6.1.1.3"
    ::= { dot1dBasePortEntry 4 }

dot1dBasePortMtuExceededDiscards OBJECT-TYPE
    SYNTAX      Counter
    ACCESS      read-only
    STATUS      mandatory
    DESCRIPTION 
        "The number of frames discarded by this port due
         to an excessive size.  It is incremented by both
         transparent and source route bridges.
         ALCATEL NOTE:
         ACCESS:      NA           USAGE:       NA
         PERSIST:     NO           INSRVMOD:    NA
         RANGE:       NA           DEFVALUE:    0
         UNITS:       frames       SPARSE:      NO
         DESCR:       NA"
--     REFERENCE   
--         "P802.1d/D9, July 14, 1989: Section 6.6.1.1.3"
    ::= { dot1dBasePortEntry 5 }

dot1dStp OBJECT IDENTIFIER
    ::= { dot1dBridge 2 }

dot1dSr OBJECT IDENTIFIER
    ::= { dot1dBridge 3 }

dot1dTp OBJECT IDENTIFIER
    ::= { dot1dBridge 4 }

dot1dTpLearnedEntryDiscards OBJECT-TYPE
    SYNTAX      Counter
    ACCESS      read-only
    STATUS      mandatory
    DESCRIPTION 
        "The total number of Forwarding Database entries,
         which have been or would have been learnt, but
         have been discarded due to a lack of space to
         store them in the Forwarding Database.  If this
         Counter32 is increasing, it indicates that the
         Forwarding Database is regularly becoming full (a
         condition which has unpleasant performance effects
         on the subnetwork).  If this Counter32 has a
         significant value but is not presently increasing,
         it indicates that the problem has been occurring
         but is not persistent.
         ALCATEL NOTE:
         ACCESS:      NA           USAGE:       NA
         PERSIST:     NO           INSRVMOD:    NA
         RANGE:       NA           DEFVALUE:    0
         UNITS:       FDB Entries  SPARSE:      NA
         DESCR:       NA"
--     REFERENCE   
--         "P802.1d/D9, July 14, 1989: Section 6.7.1.1.3"
    ::= { dot1dTp 1 }

dot1dTpAgingTime OBJECT-TYPE
    SYNTAX      INTEGER (10..1000000)
    ACCESS      read-write
    STATUS      mandatory
    DESCRIPTION 
        "The timeout period in seconds for aging out
         dynamically learned forwarding information.
         ALCATEL NOTE:
         ACCESS:      NA            USAGE:       NA
         PERSIST:     YES           INSRVMOD:    YES
         RANGE:       NA            DEFVALUE:    NA
         UNITS:       seconds       SPARSE:      NA                 
         DESCR:       NA"
--     REFERENCE   
--         "P802.1d/D9, July 14, 1989: Section 6.7.1.1.3"
    DEFVAL      { 300 }
    ::= { dot1dTp 2 }

dot1dTpFdbTable OBJECT-TYPE
    SYNTAX      SEQUENCE OF Dot1dTpFdbEntry
    ACCESS      not-accessible
    STATUS      mandatory
    DESCRIPTION 
        "A table that contains information about unicast
         entries for which the bridge has forwarding and/or
         filtering information.  This information is used
         by the transparent bridging function in
         determining how to propagate a received frame.
         ALCATEL NOTE:
         TABLESIZE: NA
         DESCR: This object is not used by Alcatel"
    ::= { dot1dTp 3 }

dot1dTpFdbEntry OBJECT-TYPE
    SYNTAX      Dot1dTpFdbEntry
    ACCESS      not-accessible
    STATUS      mandatory
    DESCRIPTION 
        "Information about a specific unicast MAC address
         for which the bridge has some forwarding and/or
         filtering information.
         Row creation : NA
         Row deletion : NA
         Index usage : NA
         lexicographical order :NA
         This object is not used by Alcatel"
    INDEX       { dot1dTpFdbAddress }
    ::= { dot1dTpFdbTable 1 }

Dot1dTpFdbEntry ::= SEQUENCE {
    dot1dTpFdbAddress   MacAddress,
    dot1dTpFdbPort      INTEGER,
    dot1dTpFdbStatus    INTEGER
}

dot1dTpFdbAddress OBJECT-TYPE
    SYNTAX      MacAddress
    ACCESS      not-accessible
    STATUS      mandatory
    DESCRIPTION 
        "A unicast MAC address for which the bridge has
         forwarding and/or filtering information.
         ALCATEL NOTE:
         ACCESS:      NA           USAGE:       NA
         PERSIST:     NA           INSRVMOD:    NA
         RANGE:       NA           DEFVALUE:    NA
         UNITS:       NA           SPARSE:      NA
         DESCR:       This object is not used by Alcatel"
--     REFERENCE   
--         "P802.1d/D9, July 14, 1989: Section 3.9.1, 3.9.2"
    ::= { dot1dTpFdbEntry 1 }

dot1dTpFdbPort OBJECT-TYPE
    SYNTAX      INTEGER
    ACCESS      read-only
    STATUS      mandatory
    DESCRIPTION 
        "Either the value '0', or the port number of the port on which 			
         a frame having a source address equal to the value of the			
         corresponding instance of dot1dTpFdbAddress has been seen. A 
         value of '0' indicates that the port number has not been			
         learned but that the bridge does have some	forwarding/filtering 
         information about this address (e.g. in the dot1dStaticTable). 
         Implementors are encouraged to assign the port value to this 
         object whenever it is learned even for addresses for which the 
         corresponding value of dot1dTpFdbStatus is not learned(3).
         ALCATEL NOTE:
           ACCESS:      NA           USAGE:       NA
           PERSIST:     NA           INSRVMOD:    NA
           RANGE:       NA           DEFVALUE:    NA
           UNITS:       NA           SPARSE:      NA	
           DESCR:       This object is not used by Alcatel"
    ::= { dot1dTpFdbEntry 2 }

dot1dTpFdbStatus OBJECT-TYPE
    SYNTAX      INTEGER { other(1), invalid(2), learned(3), self(4), 
                    mgmt(5) }
    ACCESS      read-only
    STATUS      mandatory
    DESCRIPTION 
        "The status of this entry.  The meanings of the
         values are:
         
           other(1)   : none of the following.  
         
           invalid(2) : this entry is no longer valid.
         
           learned(3) : the value of the corresponding
                        instance of dot1dTpFdbPortIndex and
                        dot1dTpFdbPortCircuit  was
                        learned, and is being used.
         
           self(4)    : the value of the corresponding
                        instance of dot1dTpFdbAddress
                        represents one of the bridge's
                        addresses.  The corresponding
                        instance of dot1dTpFdbPortIndex
                        indicates which of the bridge's
                        ports has this address.
         
           mgmt(5)    : the value of the corresponding
                        instance of dot1dTpFdbAddress
                        represents a static address.
                        The corresponding instance of
                        dot1dTpFdbPortIndex and dot1dTpFdbCircuit
                        indicates which of the bridge's ports 
                        has this static address.
         ALCATEL NOTE:
         ACCESS:      NA           USAGE:       NA
         PERSIST:     NA           INSRVMOD:    NA
         RANGE:       NA           DEFVALUE:    NA
         UNITS:       NA           SPARSE:      NA
         DESCR:       This object is not used by Alcatel"
    DEFVAL      { mgmt }
    ::= { dot1dTpFdbEntry 3 }

dot1dTpPortTable OBJECT-TYPE
    SYNTAX      SEQUENCE OF Dot1dTpPortEntry
    ACCESS      not-accessible
    STATUS      mandatory
    DESCRIPTION 
        "A table that contains information about every
         port that is associated with this transparent
         bridge.
         ALCATEL NOTE:
         TABLESIZE: DEP
         DESCR: DEP(TABLESIZE) The table size is the maximum number of ports in the system.
         		    This value can be got from the object issSystemNumberOfPorts
         		    in fsiss.mib. "
    ::= { dot1dTp 4 }

dot1dTpPortEntry OBJECT-TYPE
    SYNTAX      Dot1dTpPortEntry
    ACCESS      not-accessible
    STATUS      mandatory
    DESCRIPTION 
        "A list of information for each port of a
         transparent bridge.
         Row creation : All the Entries are created by the system at the startup.
         Row deletion : All the Entries are deleted by the system when it shutdowns.
         Index usage : the index is the dot1dTpPort.
         Note that entries will be presented to the SNMP manager in full
         lexicographical order :  sorted on dot1dTpPort."
    INDEX       { dot1dTpPort }
    ::= { dot1dTpPortTable 1 }

Dot1dTpPortEntry ::= SEQUENCE {
    dot1dTpPort             INTEGER,
    dot1dTpPortMaxInfo      INTEGER,
    dot1dTpPortInFrames     Counter,
    dot1dTpPortOutFrames    Counter,
    dot1dTpPortInDiscards   Counter
}

dot1dTpPort OBJECT-TYPE
    SYNTAX      INTEGER (1..65535)
    ACCESS      not-accessible
    STATUS      mandatory
    DESCRIPTION 
        "The port number of the port for which this entry contains 				
         Transparent bridging management information.
         ALCATEL NOTE:
               ACCESS:      NA           USAGE:       NA
               PERSIST:     NO           INSRVMOD:    NA
               RANGE:       DEP          DEFVALUE:    NA
               UNITS:       NA           SPARSE:      NO
         	    DESCR:	 DEP(RANGE):The range of the index isfrom 1 to the maximum number of physical interfaces available in the system.
         				This is obtained from the object issSystemNumberOfPorts in fsiss.mib"
    ::= { dot1dTpPortEntry 1 }

dot1dTpPortMaxInfo OBJECT-TYPE
    SYNTAX      INTEGER
    ACCESS      read-only
    STATUS      mandatory
    DESCRIPTION 
        "The maximum size of the INFO (non-MAC) field that
         this port will receive or transmit.
         ALCATEL NOTE:
         ACCESS:      NA            USAGE:       NA
         PERSIST:     NO            INSRVMOD:    NA
         RANGE:       0             DEFVALUE:    0
         UNITS:       NA            SPARSE:      NO
         DESCR:       NA"
    ::= { dot1dTpPortEntry 2 }

dot1dTpPortInFrames OBJECT-TYPE
    SYNTAX      Counter
    ACCESS      read-only
    STATUS      mandatory
    DESCRIPTION 
        "The number of frames that have been received by
         this port from its segment. Note that a frame
         received on the interface corresponding to this
         port is only counted by this object if and only if
         it is for a protocol being processed by the local
         bridging function.
         ALCATEL NOTE:
         ACCESS:      NA                   USAGE:       NA
         PERSIST:     NO                   INSRVMOD:    NA
         RANGE:       NA                   DEFVALUE:    0
         UNITS:       frames               SPARSE:      NO                   
         DESCR:       NA"
--     REFERENCE   
--         "P802.1d/D9, July 14, 1989: Section 6.6.1.1.3"
    ::= { dot1dTpPortEntry 3 }

dot1dTpPortOutFrames OBJECT-TYPE
    SYNTAX      Counter
    ACCESS      read-only
    STATUS      mandatory
    DESCRIPTION 
        "The number of frames that have been transmitted
         by this port to its segment.  Note that a frame
         transmitted on the interface corresponding to this
         port is only counted by this object if and only if
         it is for a protocol being processed by the local
         bridging function.
         ALCATEL NOTE:
         ACCESS:      NA            USAGE:       NA
         PERSIST:     NO            INSRVMOD:    NA
         RANGE:       NA            DEFVALUE:    0
         UNITS:       frames        SPARSE:      NO                  
         DESCR:       NA"
--     REFERENCE   
--         "P802.1d/D9, July 14, 1989: Section 6.6.1.1.3"
    ::= { dot1dTpPortEntry 4 }

dot1dTpPortInDiscards OBJECT-TYPE
    SYNTAX      Counter
    ACCESS      read-only
    STATUS      mandatory
    DESCRIPTION 
        "Count of valid frames received which were 
         discarded (i.e., filtered) by the Forwarding 
         Process.
         ALCATEL NOTE:
         ACCESS:      NA           USAGE:       NA
         PERSIST:     NO           INSRVMOD:    NA
         RANGE:       NA           DEFVALUE:    0
         UNITS:       NA           SPARSE:      NO
         DESCR:       NA"
--     REFERENCE   
--         "IEEE 802.1D-1990: Section 6.6.1.1.3"
    ::= { dot1dTpPortEntry 5 }

dot1dStatic OBJECT IDENTIFIER
    ::= { dot1dBridge 5 }

dot1dStaticTable OBJECT-TYPE
    SYNTAX      SEQUENCE OF Dot1dStaticEntry
    ACCESS      not-accessible
    STATUS      mandatory
    DESCRIPTION 
        "A table containing filtering information 
         configured into the bridge by (local or network) 
         management specifying the set of ports to which 
         frames received from specific ports and containing 
         specific destination addresses are allowed to be 
         forwarded.  The value of zero in this table as the 
         port number from which frames with a specific 
         destination address are received, is used to 
         specify all ports for which there is no specific 
         entry in this table for that particular 
         destination address.  Entries are valid for 
         unicast and for group/broadcast addresses.
         ALCATEL NOTE:
         TABLESIZE:  NA
         DESCR: This object is not used by Alcatel"
--     REFERENCE   
--         "IEEE 802.1D-1990: Section 6.7.2"
    ::= { dot1dStatic 1 }

dot1dStaticEntry OBJECT-TYPE
    SYNTAX      Dot1dStaticEntry
    ACCESS      not-accessible
    STATUS      mandatory
    DESCRIPTION 
        "Filtering information configured into the bridge 
         by (local or network) management specifying the 
         set of ports to which frames received from a 
         specific port and containing a specific 
         destination address are allowed to be forwarded.
         Row creation : NA
         Row deletion : NA
         Index usage : NA
         lexicographical order :NA
         This object is not used by Alcatel"
--     REFERENCE   
--         "IEEE 802.1D-1990: Section 6.7.2"
    INDEX       { dot1dStaticAddress, dot1dStaticReceivePort }
    ::= { dot1dStaticTable 1 }

Dot1dStaticEntry ::= SEQUENCE {
    dot1dStaticAddress          MacAddress,
    dot1dStaticReceivePort      INTEGER,
    dot1dStaticAllowedToGoTo    OCTET STRING,
    dot1dStaticStatus           INTEGER
}

dot1dStaticAddress OBJECT-TYPE
    SYNTAX      MacAddress
    ACCESS      not-accessible
    STATUS      mandatory
    DESCRIPTION 
        "The destination MAC address in a frame to which 
         this entry's filtering information applies.  This 
         object can take the value of a unicast address, a 
         group address or the broadcast address.
         ALCATEL NOTE:
         ACCESS:      NA           USAGE:       NA
         PERSIST:     NA           INSRVMOD:    NA                  
         RANGE:       NA           DEFVALUE:    NA
         UNITS:       NA           SPARSE:      NA
         DESCR:       This object is not used by Alcatel"
--     REFERENCE   
--         "IEEE 802.1D-1990: Section 3.9.1, 3.9.2"
    ::= { dot1dStaticEntry 1 }

dot1dStaticReceivePort OBJECT-TYPE
    SYNTAX      INTEGER (1..65535)
    ACCESS      not-accessible
    STATUS      mandatory
    DESCRIPTION 
        "Either the value '0', or the port number of the 
         port from which a frame must be received in order 
         for this entry's filtering information to apply. 
         A value of zero indicates that this entry applies 
         on all ports of the bridge for which there is no 
         other applicable entry.
         ALCATEL NOTE:
         ACCESS:      NA           USAGE:       NA
         PERSIST:     NA           INSRVMOD:    NA                
         RANGE:       NA           DEFVALUE:    NA
         UNITS:       NA           SPARSE:      NA
         DESCR:       This object is not used by Alcatel"
    ::= { dot1dStaticEntry 2 }

dot1dStaticAllowedToGoTo OBJECT-TYPE
    SYNTAX      OCTET STRING
    ACCESS      read-write
    STATUS      mandatory
    DESCRIPTION 
        "The set of ports to which frames received from a 
         specific port and destined for a specific MAC 
         address, are allowed to be forwarded.  Each octet 
         within the value of this object specifies a set of 
         eight ports, with the first octet specifying ports 
         1 through 8, the second octet specifying ports 9 
         through 16, etc.  Within each octet, the most 
         significant bit represents the lowest numbered 
         port, and the least significant bit represents the 
         highest numbered port.  Thus, each port of the 
         bridge is represented by a single bit within the 
         value of this object.  If that bit has a value of 
         '1' then that port is included in the set of 
         ports; the port is not included if its bit has a 
         value of '0'.  (Note that the setting of the bit 
         corresponding to the port from which a frame is 
         received is irrelevant.)  The default value of 
         this object is a string of ones of appropriate 
         length.
         ALCATEL NOTE:
         ACCESS:      NA           USAGE:       NA
         PERSIST:     NA           INSRVMOD:    NA              
         RANGE:       NA           DEFVALUE:    NA               
         UNITS:       NA           SPARSE:      NA
         DESCR:       This object is not used by Alcatel"
    ::= { dot1dStaticEntry 3 }

dot1dStaticStatus OBJECT-TYPE
    SYNTAX      INTEGER { other(1), invalid(2), permanent(3), 
                    deleteOnReset(4), deleteOnTimeout(5) }
    ACCESS      read-write
    STATUS      mandatory
    DESCRIPTION 
        "This object indicates the status of this entry. 
         The default value is permanent(3). 
         
              other(1) - this entry is currently in use but 
                   the conditions under which it will 
                   remain so are different from each of the 
                   following values. 
              invalid(2) - writing this value to the object 
                   removes the corresponding entry. 
              permanent(3) - this entry is currently in use 
                   and will remain so after the next reset 
                   of the bridge. 
              deleteOnReset(4) - this entry is currently in 
                   use and will remain so until the next 
                   reset of the bridge. 
              deleteOnTimeout(5) - this entry is currently 
                   in use and will remain so until it is 
                   aged out.
                   ALCATEL NOTE:
         ACCESS:      NA           USAGE:       NA
         PERSIST:     NA           INSRVMOD:    NA                        
         RANGE:       NA           DEFVALUE:    NA                         
         UNITS:       NA           SPARSE:      NA
         DESCR:       This object is not used by Alcatel"
    ::= { dot1dStaticEntry 4 }

END -- end of module BRIDGE-MIB.
