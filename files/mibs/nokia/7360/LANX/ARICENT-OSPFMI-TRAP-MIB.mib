--
-- This SMIv1 module has been generated by smidump 0.4.8. Do not edit.
--

ARICENT-OSPFMI-TRAP-MIB DEFINITIONS ::= BEGIN

IMPORTS
    fsMIStdOspfEntry, fsMIStdOspfExtLsdbLimit, fsMIStdOspfIfState, 
    fsMIStdOspfNbrRtrId, fsMIStdOspfNbrState, fsMIStdOspfRouterId, 
    fsMIStdOspfVirtIfState, fsMIStdOspfVirtNbrState
        FROM ARICENT-MISTDOSPF-MIB
    OBJECT-TYPE
        FROM RFC-1212
    TRAP-TYPE
        FROM RFC-1215
    IpAddress, enterprises
        FROM RFC1155-SMI;

fsMIStdOspfTrap OBJECT IDENTIFIER
    ::= { enterprises futuresoftware(2076) 148 }

-- fsMIStdOspfTrap MODULE-IDENTITY
--     LAST-UPDATED "200702230000Z"
--     ORGANIZATION 
--         "ARICENT COMMUNICATIONS SOFTWARE"
--     CONTACT-INFO 
--         "ARICENT COMMUNICATIONS SOFTWARE
--          3460 Hillview Avenue,
--          Palo Alto, CA 94304-1388, USA,
--          Phone : +1-650-391-1088
--          E-mail:support@aricent.com"
--     DESCRIPTION 
--         "The enterprise ID 2076 was originally assigned to Future Software Pvt Limited.
--          Future Software is a part of Aricent."
--     REVISION    "200702230000Z"
--     DESCRIPTION 
--         "The Aricent Proprietary OSPFMI TRAP MIB modified from standard ospf trap MIB"
--     ::= { enterprises futuresoftware(2076) 148 }


fsMIStdOspfTraps OBJECT IDENTIFIER
    ::= { fsMIStdOspfTrap 0 }

fsMIStdOspfTrapControl OBJECT IDENTIFIER
    ::= { fsMIStdOspfTrap 1 }

fsMIStdOspfTrapTable OBJECT-TYPE
    SYNTAX      SEQUENCE OF FsMIStdOspfTrapEntry
    ACCESS      not-accessible
    STATUS      mandatory
    DESCRIPTION 
        "Ospf Trap Table for multiple context
         ALCATEL NOTE:
         		TABLE SIZE:   64
         		DESCR     :   NA"
    ::= { fsMIStdOspfTrapControl 1 }

fsMIStdOspfTrapEntry OBJECT-TYPE
    SYNTAX      FsMIStdOspfTrapEntry
    ACCESS      not-accessible
    STATUS      mandatory
    DESCRIPTION 
        "Trap information for one of the instance
         Row creation : An entry will be created when an OSPF instance is created. 
          Row deletion : An entry will be deleted when the OSPF instance is removed.
          Index usage : the index is fsMIStdOspfEntry.
            Note that entries will be presented to the SNMP manager in full
            lexicographical order :  sorted on fsMIStdOspfEntry."
    INDEX       { fsMIStdOspfContextId }
--     AUGMENTS    { fsMIStdOspfEntry }
    ::= { fsMIStdOspfTrapTable 1 }

FsMIStdOspfTrapEntry ::= SEQUENCE {
    fsMIStdOspfSetTrap          OCTET STRING,
    fsMIStdOspfConfigErrorType  INTEGER,
    fsMIStdOspfPacketType       INTEGER,
    fsMIStdOspfPacketSrc        IpAddress
}

fsMIStdOspfSetTrap OBJECT-TYPE
    SYNTAX      OCTET STRING (SIZE(4))
    ACCESS      read-write
    STATUS      mandatory
    DESCRIPTION 
        "A four-octet string serving as a bit  map  for
         the trap events defined by the OSPF traps. This
         object is used to enable and  disable  specific
         OSPF   traps   where  a  1  in  the  bit  field
         represents enabled.  The right-most bit  (least
         significant) represents trap 0. If MAX OSPF 
         CONTEXT ID is passed as fsMIStdOspfContextId
         then set the same trap for all the valid 
         ospf context
         ALCATEL NOTE:
          ACCESS:   NA             USAGE:     NA       
          PERSIST:  NO             INSRVMOD:  YES  
          RANGE:    4              DEFVALUE:  '\0'   
          UNITS:    NA             SPARSE:    NA      
          DESCR:    NA"
    ::= { fsMIStdOspfTrapEntry 1 }

fsMIStdOspfConfigErrorType OBJECT-TYPE
    SYNTAX      INTEGER { badVersion(1), areaMismatch(2), 
                    unknownNbmaNbr(3), unknownVirtualNbr(4), 
                    authTypeMismatch(5), authFailure(6), 
                    netMaskMismatch(7), helloIntervalMismatch(8), 
                    deadIntervalMismatch(9), optionMismatch(10) }
    ACCESS      read-only
    STATUS      mandatory
    DESCRIPTION 
        "Potential types  of  configuration  conflicts.
         Used  by the ospfConfigError and ospfConfigVir-
         tError traps.
         ALCATEL NOTE:
          ACCESS:     NA         USAGE:      NA      
          PERSIST:    NO         INSRVMOD:   NA 
          RANGE:      NA         DEFVALUE:   0 
          UNITS:      NA         SPARSE:     NA 
          DESCR:      NA"
    ::= { fsMIStdOspfTrapEntry 2 }

fsMIStdOspfPacketType OBJECT-TYPE
    SYNTAX      INTEGER { hello(1), dbDescript(2), lsReq(3), lsUpdate(4), 
                    lsAck(5) }
    ACCESS      read-only
    STATUS      mandatory
    DESCRIPTION 
        "OSPF packet types.
         ALCATEL NOTE:
            ACCESS:      NA        USAGE:      NA 
            PERSIST:     NO        INSRVMOD:   NA 
            RANGE:       NA        DEFVALUE:   0 
            UNITS:       NA        SPARSE:     NA 
            DESCR:       NA"
    ::= { fsMIStdOspfTrapEntry 3 }

fsMIStdOspfPacketSrc OBJECT-TYPE
    SYNTAX      IpAddress
    ACCESS      read-only
    STATUS      mandatory
    DESCRIPTION 
        "The IP address of an inbound packet that  can-
         not be identified by a neighbor instance.
         ALCATEL NOTE:
          ACCESS:      NA        USAGE:        NA    
          PERSIST:     NO        INSRVMOD:     NA
          RANGE:       NA        DEFVALUE:     '0.0.0.0'
          UNITS:       NA        SPARSE:       NA
          DESCR:       NA"
    ::= { fsMIStdOspfTrapEntry 4 }

ospfVirtIfStateChange TRAP-TYPE
    ENTERPRISE  fsMIStdOspfTrap
    VARIABLES   { fsMIStdOspfRouterId, fsMIStdOspfVirtIfState }
--     STATUS      mandatory
    DESCRIPTION 
        "An ospfIfStateChange trap signifies that there
         has  been a change in the state of an OSPF vir-
         tual interface.
         This trap should be generated when  the  inter-
         face  state  regresses  (e.g., goes from Point-
         to-Point to Down) or progresses to  a  terminal
         state (i.e., Point-to-Point)."
    ::= 1

ospfNbrStateChange TRAP-TYPE
    ENTERPRISE  fsMIStdOspfTrap
    VARIABLES   { fsMIStdOspfRouterId, fsMIStdOspfNbrRtrId, 
                  fsMIStdOspfNbrState }
--     STATUS      mandatory
    DESCRIPTION 
        "An  ospfNbrStateChange  trap  signifies   that
         there  has been a change in the state of a non-
         virtual OSPF neighbor.   This  trap  should  be
         generated  when  the  neighbor  state regresses
         (e.g., goes from Attempt or Full  to  1-Way  or
         Down)  or progresses to a terminal state (e.g.,
         2-Way or Full).  When an  neighbor  transitions
         from  or  to Full on non-broadcast multi-access
         and broadcast networks, the trap should be gen-
         erated  by the designated router.  A designated
         router transitioning to Down will be  noted  by
         ospfIfStateChange."
    ::= 2

ospfVirtNbrStateChange TRAP-TYPE
    ENTERPRISE  fsMIStdOspfTrap
    VARIABLES   { fsMIStdOspfRouterId, fsMIStdOspfVirtNbrState }
--     STATUS      mandatory
    DESCRIPTION 
        "An ospfIfStateChange trap signifies that there
         has  been a change in the state of an OSPF vir-
         tual neighbor.  This trap should  be  generated
         when  the  neighbor state regresses (e.g., goes
         from Attempt or  Full  to  1-Way  or  Down)  or
         progresses to a terminal state (e.g., Full)."
    ::= 3

ospfIfConfigError TRAP-TYPE
    ENTERPRISE  fsMIStdOspfTrap
    VARIABLES   { fsMIStdOspfRouterId, fsMIStdOspfPacketSrc, 
                  fsMIStdOspfConfigErrorType, fsMIStdOspfPacketType }
--     STATUS      mandatory
    DESCRIPTION 
        "An ospfIfConfigError  trap  signifies  that  a
         packet  has  been received on a non-virtual in-
         terface  from  a  router  whose   configuration
         parameters  conflict  with this router's confi-
         guration parameters.  Note that the  event  op-
         tionMismatch  should  cause  a  trap only if it
         prevents an adjacency from forming."
    ::= 4

ospfVirtIfConfigError TRAP-TYPE
    ENTERPRISE  fsMIStdOspfTrap
    VARIABLES   { fsMIStdOspfRouterId, fsMIStdOspfConfigErrorType, 
                  fsMIStdOspfPacketType }
--     STATUS      mandatory
    DESCRIPTION 
        "An ospfConfigError trap signifies that a pack-
         et  has  been  received  on a virtual interface
         from a router  whose  configuration  parameters
         conflict   with   this  router's  configuration
         parameters.  Note that the event optionMismatch
         should  cause a trap only if it prevents an ad-
         jacency from forming."
    ::= 5

ospfIfAuthFailure TRAP-TYPE
    ENTERPRISE  fsMIStdOspfTrap
    VARIABLES   { fsMIStdOspfRouterId, fsMIStdOspfPacketSrc, 
                  fsMIStdOspfConfigErrorType, fsMIStdOspfPacketType }
--     STATUS      mandatory
    DESCRIPTION 
        "An ospfIfAuthFailure  trap  signifies  that  a
         packet  has  been received on a non-virtual in-
         terface from a router whose authentication  key
         or  authentication  type  conflicts  with  this
         router's authentication key  or  authentication
         type."
    ::= 6

ospfVirtIfAuthFailure TRAP-TYPE
    ENTERPRISE  fsMIStdOspfTrap
    VARIABLES   { fsMIStdOspfRouterId, fsMIStdOspfConfigErrorType, 
                  fsMIStdOspfPacketType }
--     STATUS      mandatory
    DESCRIPTION 
        "An ospfVirtIfAuthFailure trap signifies that a
         packet has been received on a virtual interface
         from a router whose authentication key  or  au-
         thentication  type conflicts with this router's
         authentication key or authentication type."
    ::= 7

ospfIfRxBadPacket TRAP-TYPE
    ENTERPRISE  fsMIStdOspfTrap
    VARIABLES   { fsMIStdOspfRouterId, fsMIStdOspfPacketSrc, 
                  fsMIStdOspfPacketType }
--     STATUS      mandatory
    DESCRIPTION 
        "An ospfIfRxBadPacket trap  signifies  that  an
         OSPF  packet has been received on a non-virtual
         interface that cannot be parsed."
    ::= 8

ospfVirtIfRxBadPacket TRAP-TYPE
    ENTERPRISE  fsMIStdOspfTrap
    VARIABLES   { fsMIStdOspfRouterId, fsMIStdOspfPacketType }
--     STATUS      mandatory
    DESCRIPTION 
        "An ospfRxBadPacket trap signifies that an OSPF
         packet has been received on a virtual interface
         that cannot be parsed."
    ::= 9

ospfTxRetransmit TRAP-TYPE
    ENTERPRISE  fsMIStdOspfTrap
    VARIABLES   { fsMIStdOspfRouterId, fsMIStdOspfNbrRtrId, 
                  fsMIStdOspfPacketType }
--     STATUS      mandatory
    DESCRIPTION 
        "An ospfTxRetransmit  trap  signifies  than  an
         OSPF  packet  has  been retransmitted on a non-
         virtual interface.  All packets that may be re-
         transmitted  are associated with an LSDB entry.
         The LS type, LS ID, and Router ID are  used  to
         identify the LSDB entry."
    ::= 10

ospfVirtIfTxRetransmit TRAP-TYPE
    ENTERPRISE  fsMIStdOspfTrap
    VARIABLES   { fsMIStdOspfRouterId, fsMIStdOspfPacketType }
--     STATUS      mandatory
    DESCRIPTION 
        "An ospfTxRetransmit  trap  signifies  than  an
         OSPF packet has been retransmitted on a virtual
         interface.  All packets that may be retransmit-
         ted  are  associated with an LSDB entry. The LS
         type, LS ID, and Router ID are used to identify
         the LSDB entry."
    ::= 11

ospfOriginateLsa TRAP-TYPE
    ENTERPRISE  fsMIStdOspfTrap
    VARIABLES   { fsMIStdOspfRouterId }
--     STATUS      mandatory
    DESCRIPTION 
        "An ospfOriginateLsa trap signifies that a  new
         LSA  has  been originated by this router.  This
         trap should not be invoked for simple refreshes
         of  LSAs  (which happesn every 30 minutes), but
         instead will only be invoked  when  an  LSA  is
         (re)originated due to a topology change.  Addi-
         tionally, this trap does not include LSAs  that
         are  being  flushed  because  they have reached
         MaxAge."
    ::= 12

ospfMaxAgeLsa TRAP-TYPE
    ENTERPRISE  fsMIStdOspfTrap
    VARIABLES   { fsMIStdOspfRouterId }
--     STATUS      mandatory
    DESCRIPTION 
        "An ospfMaxAgeLsa trap signifies  that  one  of
         the LSA in the router's link-state database has
         aged to MaxAge."
    ::= 13

ospfLsdbOverflow TRAP-TYPE
    ENTERPRISE  fsMIStdOspfTrap
    VARIABLES   { fsMIStdOspfRouterId, fsMIStdOspfExtLsdbLimit }
--     STATUS      mandatory
    DESCRIPTION 
        "An ospfLsdbOverflow trap  signifies  that  the
         number of LSAs in the router's link-state data-
         base has exceeded fsMIStdOspfExtLsdbLimit."
    ::= 14

ospfLsdbApproachingOverflow TRAP-TYPE
    ENTERPRISE  fsMIStdOspfTrap
    VARIABLES   { fsMIStdOspfRouterId, fsMIStdOspfExtLsdbLimit }
--     STATUS      mandatory
    DESCRIPTION 
        "An ospfLsdbApproachingOverflow trap  signifies
         that  the  number of LSAs in the router's link-
         state database has exceeded ninety  percent  of
         fsMIStdOspfExtLsdbLimit."
    ::= 15

ospfIfStateChange TRAP-TYPE
    ENTERPRISE  fsMIStdOspfTrap
    VARIABLES   { fsMIStdOspfRouterId, fsMIStdOspfIfState }
--     STATUS      mandatory
    DESCRIPTION 
        "An ospfIfStateChange trap signifies that there
         has been a change in the state of a non-virtual
         OSPF interface. This trap should  be  generated
         when  the interface state regresses (e.g., goes
         from Dr to Down) or progresses  to  a  terminal
         state  (i.e.,  Point-to-Point, DR Other, Dr, or
         Backup)."
    ::= 16

END -- end of module ARICENT-OSPFMI-TRAP-MIB.
