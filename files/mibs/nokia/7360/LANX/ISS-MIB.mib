--
-- This SMIv1 module has been generated by smidump 0.4.8. Do not edit.
--

--
-- WARNING: this output may be incorrect due to significant parse errors
--

ISS-MIB DEFINITIONS ::= BEGIN

IMPORTS
    OBJECT-TYPE
        FROM RFC-1212
    TRAP-TYPE
        FROM RFC-1215
    Counter, Gauge, IpAddress, TimeTicks, enterprises
        FROM RFC1155-SMI
    DisplayString, MacAddress, RowStatus, TruthValue
        FROM SNMPv2-TC;

iss OBJECT IDENTIFIER
    ::= { enterprises futuresoftware(2076) 81 }

-- iss MODULE-IDENTITY
--     LAST-UPDATED "200207150000Z"
--     ORGANIZATION 
--         "Future Software Limited"
--     CONTACT-INFO 
--         "  
--          Postal:     Future Software Ltd., 
--                      480-481, Anna Salai, 
--                      Nandanam, 
--                      Chennai, 
--                      India  600 035. 
--          Telephone: +91-44-4330550 
--          E-Mail:     support@future.futsoft.com "
--     DESCRIPTION 
--         "The MIB for FutureISS."
--     REVISION    "200207150000Z"
--     DESCRIPTION 
--         "The initial revision of this MIB module was published as
--          RFC 1450."
--     ::= { enterprises futuresoftware(2076) 81 }


PortList ::=
    OCTET STRING

-- PortList ::= TEXTUAL-CONVENTION
--     STATUS      mandatory
--     DESCRIPTION 
--         "Each octet within this value specifies a set of eight
--          ports, with the first octet specifying ports 1 through
--          8, the second octet specifying ports 9 through 16, etc.
--          Within each octet, the most significant bit represents
--          the lowest numbered port, and the least significant bit
--          represents the highest numbered port.  Thus, each port
--          of the bridge is represented by a single bit within the
--          value of this object.  If that bit has a value of '1'
--          then that port is included in the set of ports; the port
--          is not included if its bit has a value of '0'."
--     SYNTAX      OCTET STRING

VlanIdOrZero ::=
    INTEGER (0..4094)

-- VlanIdOrZero ::= TEXTUAL-CONVENTION
--     STATUS      mandatory
--     DESCRIPTION 
--         "A 12-bit VLAN ID used in the VLAN Tag header.
--          0 means any vlan"
--     SYNTAX      INTEGER (0..4094)

issSystem OBJECT IDENTIFIER
    ::= { iss 1 }

issSwitchName OBJECT-TYPE
    SYNTAX      DisplayString (SIZE(1..15))
    ACCESS      read-write
    STATUS      mandatory
    DESCRIPTION 
        "System name used for identification of the device.
         ALCATEL NOTE:
         ACCESS	:   NA           	USAGE		:    NA
         PERSIST:   YES          	INSRVMOD	:    YES  
         RANGE	:   NA           	DEFVALUE	:     0          
         UNITS	:   NA           	SPARSE		:    NA
         DESCR	:   NA"
    ::= { issSystem 1 }

issHardwareVersion OBJECT-TYPE
    SYNTAX      DisplayString (SIZE(1..15))
    ACCESS      read-only
    STATUS      mandatory
    DESCRIPTION 
        "Version number of the Hardware.
         ALCATEL NOTE:
         ACCESS	:   NA           	USAGE		:    NA
         PERSIST:   NO          	INSRVMOD	:    NA 
         RANGE	:   NA           	DEFVALUE	:    'H/WVersion1'
         UNITS	:   NA           	SPARSE		:    NA
         DESCR	:   NA"
    ::= { issSystem 2 }

issFirmwareVersion OBJECT-TYPE
    SYNTAX      DisplayString (SIZE(1..15))
    ACCESS      read-only
    STATUS      mandatory
    DESCRIPTION 
        "Version number of the Firmware.
         ALCATEL NOTE:
         ACCESS	:   NA           	USAGE		:    NA
         PERSIST:   NO          	INSRVMOD	:    NA 
         RANGE	:   NA           	DEFVALUE	:    '3.1.1.1'
         UNITS	:   NA           	SPARSE		:    NA
         DESCR	:   NA"
    ::= { issSystem 3 }

issDefaultIpAddrCfgMode OBJECT-TYPE
    SYNTAX      INTEGER { manual(1), dynamic(2) }
    ACCESS      read-write
    STATUS      mandatory
    DESCRIPTION 
        "Specifies the means by which the default interface in the device 
         gets the IP address.
         
         If 'manual' mode is selected, the default interface takes the 
         'issDefaultIpAddr' configured in the system.
         
         If 'dynamic' mode is selected, the default interface gets the IP address
         through dynamic IP address configuration protocols such as RARP client, 
         BootP client, DHCP Client, etc. in that sequence.
         
         If the system fails to get the IP address dynamically through all the
         above protocols, the default interface uses the 'issDefaultIpAddr' 
         configured in the system.
         
         This object is not supported anymore due to dual IP removal.
         Shub does not have managment IP address anymore. 
         
            ALCATEL NOTE:
            ACCESS	:   NA           	USAGE		:    NA
            PERSIST:   YES          	INSRVMOD	:    YES 
            RANGE	:   NA           	DEFVALUE	:    NA
            UNITS	:   NA           	SPARSE		:    NA
            DESCR	:   This is not used by Alcatel"
    DEFVAL      { manual }
    ::= { issSystem 4 }

issDefaultIpAddr OBJECT-TYPE
    SYNTAX      IpAddress
    ACCESS      read-write
    STATUS      mandatory
    DESCRIPTION 
        "Default IP Address of the system.
         
         This IP address, if modified, will take effect only when the 
         configuration is stored & restored.
           ALCATEL NOTE:
           ACCESS	:   NA           	USAGE		:    NA
           PERSIST:   YES          	INSRVMOD	:    YES 
           RANGE	:   NA           	DEFVALUE	:    0x0a000001          
           UNITS	:   NA           	SPARSE		:    NA
           DESCR	:   NA"
    ::= { issSystem 5 }

issDefaultIpSubnetMask OBJECT-TYPE
    SYNTAX      IpAddress
    ACCESS      read-write
    STATUS      mandatory
    DESCRIPTION 
        "IP subnet mask for the default IP address.
         
         This subnet mask, if modified, will take effect only when the
         configuration is stored & restored.
           ALCATEL NOTE:
           ACCESS	:   NA           	USAGE		:    NA
           PERSIST:   YES          	INSRVMOD	:    YES 
           RANGE	:   NA           	DEFVALUE	:    0xff000000
           UNITS	:   NA           	SPARSE		:    NA
           DESCR	:   NA"
    ::= { issSystem 6 }

issEffectiveIpAddr OBJECT-TYPE
    SYNTAX      IpAddress
    ACCESS      read-only
    STATUS      deprecated
    DESCRIPTION 
        "Effective IP address of the switch to be used for contacting
         through SNMP interface or web interface.
         
         This IP address will be same as the default IP address if the
         device fails to get the IP address dynamically or the
         'DefaultIpAddrCfgMode' is 'manual'.
         
         This IP address will be different from the default IP address 
         if the device manages to get the IP address dynamically.
         
         In either condition, this is the effective IP address to be 
         used for contacting the switch.
           ALCATEL NOTE:
           ACCESS	:   NA           	USAGE		:    NA
           PERSIST:   NO          	INSRVMOD	:    NA 
           RANGE	:   NA           	DEFVALUE	:    10.0.0.1
           UNITS	:   NA           	SPARSE		:    NA
           DESCR	:   NA"
    ::= { issSystem 7 }

issDefaultInterface OBJECT-TYPE
    SYNTAX      DisplayString (SIZE(1..16))
    ACCESS      read-write
    STATUS      mandatory
    DESCRIPTION 
        "Name of the default interface that can be used for 
         communicating with the system for configuration through SNMP
         or WebInterface.
         
         The default interface, if modified, will take effect only when
         the configuration is stored & restored.
           ALCATEL NOTE:
           ACCESS	:   NA           	USAGE		:    NA
           PERSIST:   NO          	INSRVMOD	:    YES
           RANGE	:   NA           	DEFVALUE	:    'eth1535'
           UNITS	:   NA           	SPARSE		:    NA
           DESCR	:   NA"
    ::= { issSystem 8 }

issRestart OBJECT-TYPE
    SYNTAX      INTEGER { none(0), systemreset(1), applicationreset(2) }
    ACCESS      read-write
    STATUS      mandatory
    DESCRIPTION 
        "In dual processor architecture (ex. ECNT-A) this object allows the
         user to restart the Switch or force a warm application reset and in
         either case the entire switch will operationally go down (i.e) BCM
         hardware will also be reset.
         In single processor architecture (ex. ECNT-C) this object allows the
         user to only force a warm application reset in which the entire
         switch will operationally go down (i.e) BCM hardware will also be
         reset.             
         Once the switch/application is restarted, the value of this 
         object reverts to 'none'.
         ALCATEL NOTE:
         ACCESS	:   NA           	USAGE		:    NA
         PERSIST:   NO          	INSRVMOD	:    YES
         RANGE	:   NA           	DEFVALUE	:    NA
         UNITS	:   NA           	SPARSE		:    NA
         DESCR	:   NA"
    DEFVAL      { none }
    ::= { issSystem 9 }

issInitiateConfigSave OBJECT-TYPE
    SYNTAX      TruthValue
    ACCESS      read-write
    STATUS      mandatory
    DESCRIPTION 
        "When set as 'true' switch configurations save operation is
         initiated. 
         As soon as the configuration save operation is completed, the value 
         of this object reverts back to 'false'.
         
         All the configurations made via the three interfaces
         viz. 
             -> commandline interface
             -> Web Interface
             -> SNMP interface
         are saved either in flash or in the chosen remote system 
         depending upon 'ConfigSaveOption'.
           ALCATEL NOTE:
           ACCESS	:   NA           	USAGE		:    NA
           PERSIST:   NO          	INSRVMOD	:    YES
           RANGE	:   1,2           	DEFVALUE	:    NA
           UNITS	:   NA           	SPARSE		:    NA
           DESCR	:   NA"
    DEFVAL      { false }
    ::= { issSystem 13 }

issConfigSaveStatus OBJECT-TYPE
    SYNTAX      INTEGER { saveInProgress(1), saveSuccessful(2), 
                    saveFailed(3), notInitiated(4) }
    ACCESS      read-only
    STATUS      mandatory
    DESCRIPTION 
        "Status of configuration save operation.
         ALCATEL NOTE:
         ACCESS	:   NA           	USAGE		:    NA
         PERSIST:   NO          	INSRVMOD	:    NA
         RANGE	:   NA           	DEFVALUE	:    NA
         UNITS	:   NA           	SPARSE		:    NA
         DESCR	:   NA"
    ::= { issSystem 14 }

issConfigRestoreStatus OBJECT-TYPE
    SYNTAX      INTEGER { none(0), restoreInprogress(1), 
                    restoreSuccessful(2), restoreFailed(3) }
    ACCESS      read-only
    STATUS      mandatory
    DESCRIPTION 
        "The status of the switch configuration restore operation.
         ALCATEL NOTE:
         ACCESS	:   NA           	USAGE		:    NA
         PERSIST:   NO          	INSRVMOD	:    NA
         RANGE	:   NA           	DEFVALUE	:    NA
         UNITS	:   NA           	SPARSE		:    NA
         DESCR	:   NA"
    ::= { issSystem 18 }

issDlImageFromIp OBJECT-TYPE
    SYNTAX      IpAddress
    ACCESS      read-write
    STATUS      mandatory
    DESCRIPTION 
        "The Ip Address of machine from where the image has to be downloaded.
         ALCATEL NOTE:
         ACCESS	:   NA           	USAGE		:    NA
         PERSIST:   NO          	INSRVMOD	:    YES
         RANGE	:   NA           	DEFVALUE	:    NA
         UNITS	:   NA           	SPARSE		:    NA
         DESCR	:   NA"
    ::= { issSystem 19 }

issDlImageName OBJECT-TYPE
    SYNTAX      DisplayString (SIZE(1..256))
    ACCESS      read-write
    STATUS      mandatory
    DESCRIPTION 
        "The image name which is to be downloaded to the switch.
         ALCATEL NOTE:
         ACCESS	:   NA           	USAGE		:    NA
         PERSIST:   NO          	INSRVMOD	:    YES
         RANGE	:   1..150           	DEFVALUE	:    NA
         UNITS	:   NA           	SPARSE		:    NA
         DESCR	:   NA"
    ::= { issSystem 20 }

issInitiateDlImage OBJECT-TYPE
    SYNTAX      TruthValue
    ACCESS      read-write
    STATUS      mandatory
    DESCRIPTION 
        "Initiates the Image Download operation.
         ALCATEL NOTE:
         ACCESS	:   NA           	USAGE		:    NA
         PERSIST:   NO          	INSRVMOD	:    YES
         RANGE	:   1,2           	DEFVALUE	:    NA
         UNITS	:   NA           	SPARSE		:    NA
         DESCR	:   NA"
    ::= { issSystem 21 }

issLoggingOption OBJECT-TYPE
    SYNTAX      INTEGER { console(1), file(2) }
    ACCESS      read-write
    STATUS      mandatory
    DESCRIPTION 
        "The Logging option specifying whether the logging is to be 
         done at console or to a file(system buffer) in the system.
           ALCATEL NOTE:
           ACCESS	:   NA           	USAGE		:    NA
           PERSIST:   YES          	INSRVMOD	:    YES
           RANGE	:   NA           	DEFVALUE	:    NA
           UNITS	:   NA           	SPARSE		:    NA
           DESCR	:   NA"
    ::= { issSystem 22 }

issUploadLogFileToIp OBJECT-TYPE
    SYNTAX      IpAddress
    ACCESS      read-write
    STATUS      mandatory
    DESCRIPTION 
        "The Ip Address of machine to which the log file is to be uploaded.
         ALCATEL NOTE:
         ACCESS	:   NA           	USAGE		:    NA
         PERSIST:   YES          	INSRVMOD	:    YES
         RANGE	:   NA           	DEFVALUE	:    NA
         UNITS	:   NA           	SPARSE		:    NA
         DESCR	:   NA"
    ::= { issSystem 23 }

issLogFileName OBJECT-TYPE
    SYNTAX      DisplayString (SIZE(1..256))
    ACCESS      read-write
    STATUS      mandatory
    DESCRIPTION 
        "The file name to be used for uploading the logs from 'file' to the 
         remote system.
         
         This object is useful only when the 'LogOption' is chosen as 'file'.
            ALCATEL NOTE:
            ACCESS	:   NA           	USAGE		:    NA
            PERSIST:   YES          	INSRVMOD	:    YES
            RANGE	:   1..150           	DEFVALUE	:    NA
            UNITS	:   NA           	SPARSE		:    NA
            DESCR	:   NA"
    ::= { issSystem 24 }

issInitiateUlLogFile OBJECT-TYPE
    SYNTAX      TruthValue
    ACCESS      read-write
    STATUS      mandatory
    DESCRIPTION 
        "Initiates uploading of Log File to the specified IP address in 
         'issUploadLogFileToIp'.
         
         The logs will be uploaded in the specified 'issLogFileName'.
            ALCATEL NOTE:
            ACCESS	:   NA           	USAGE		:    NA
            PERSIST:   NO          	INSRVMOD	:    YES
            RANGE	:   1,2           	DEFVALUE	:    NA
            UNITS	:   NA           	SPARSE		:    NA
            DESCR	:   NA"
    ::= { issSystem 25 }

issDownloadStatus OBJECT-TYPE
    SYNTAX      INTEGER { inprogress(1), successful(2), failed(3) }
    ACCESS      read-only
    STATUS      mandatory
    DESCRIPTION 
        "The status of the Image download operation to the switch.
         ALCATEL NOTE:
         ACCESS	:   NA           	USAGE		:    NA
         PERSIST:   NO          	INSRVMOD	:    NA
         RANGE	:   NA           	DEFVALUE	:    2
         UNITS	:   NA           	SPARSE		:    NA
         DESCR	:   NA"
    ::= { issSystem 27 }

issSysContact OBJECT-TYPE
    SYNTAX      DisplayString
    ACCESS      read-write
    STATUS      mandatory
    DESCRIPTION 
        "The textual identification of the contact person for this
         managed node, together with information on how to contact
         this person.  If no contact information is known, the value
         is the zero-length string.
         ALCATEL NOTE:
         ACCESS	:   NA           	USAGE		:    NA
         PERSIST:   YES          	INSRVMOD	:    YES
         RANGE	:   0..50           	DEFVALUE	:    NA
         UNITS	:   NA           	SPARSE		:    NA
         DESCR	:   NA"
    ::= { issSystem 28 }

issSysLocation OBJECT-TYPE
    SYNTAX      DisplayString
    ACCESS      read-write
    STATUS      mandatory
    DESCRIPTION 
        "The physical location of this node (e.g., `telephone
         closet, 3rd floor').  If the location is unknown, the value
         is the zero-length string.
         ALCATEL NOTE:
         ACCESS	:   NA           	USAGE		:    NA
         PERSIST:   YES          	INSRVMOD	:    YES
         RANGE	:   0..50           	DEFVALUE	:    NA
         UNITS	:   NA           	SPARSE		:    NA
         DESCR	:   NA"
    ::= { issSystem 29 }

issLoginAuthentication OBJECT-TYPE
    SYNTAX      INTEGER { local(1), remote(2) }
    ACCESS      read-write
    STATUS      mandatory
    DESCRIPTION 
        "The mechanism by which the user login to access the GUI for 
         configuration has to be authenticated. Authentication is done 
         either locally or in the remote side through a RADIUS Server.
           ALCATEL NOTE:
           ACCESS	:   NA           	USAGE		:    NA
           PERSIST:   YES          	INSRVMOD	:    YES
           RANGE	:   NA           	DEFVALUE	:    1
           UNITS	:   NA           	SPARSE		:    NA
           DESCR	:   NA"
    ::= { issSystem 30 }

issLanXSoftwareVersionName OBJECT-TYPE
    SYNTAX      DisplayString (SIZE(1..256))
    ACCESS      read-write
    STATUS      mandatory
    DESCRIPTION 
        " Identifies the Name of the lanx Software release.
         The default name is LANX
         ALCATEL NOTE:
         ACCESS	:   NA           	USAGE		:    NA
         PERSIST:   NO          	INSRVMOD	:    YES
         RANGE	:   NA           	DEFVALUE	:    NA
         UNITS	:   NA           	SPARSE		:    NA
         DESCR	:   NA"
    DEFVAL      { "LANX" }
    ::= { issSystem 31 }

issLanXSoftwareReleaseNumber OBJECT-TYPE
    SYNTAX      DisplayString (SIZE(1..7))
    ACCESS      read-write
    STATUS      mandatory
    DESCRIPTION 
        "Identifies the software version number d.d.d.d
         The first 2 digits d.d identify the major 
         release number, EG 1.0, 1.1 The third digit 
         identifies a minor release number, Any minor releases 
         introducing MIB or agent behaviour change MUST change the
         third digit. The changing of the third digit does not  
         apply to intermediate (incremental) builds implementing 
         only partial features as it can quickly run out of numbers. 
         The last digit is the maintainance number
         ALCATEL NOTE:
         ACCESS	:   RO           	USAGE		:    NA
         PERSIST:   NO          	INSRVMOD	:    NA
         RANGE	:   NA           	DEFVALUE	:    NA
         UNITS	:   NA           	SPARSE		:    NA
         DESCR	:   NA"
    ::= { issSystem 32 }

issExternalVlanId OBJECT-TYPE
    SYNTAX      Gauge
    ACCESS      read-write
    STATUS      mandatory
    DESCRIPTION 
        "This InternalVlanId, if modified, will take effect only when the 
         when restarted.
         ALCATEL NOTE:
         ACCESS	:   NA           	USAGE		:    NA
         PERSIST:   YES          	INSRVMOD	:    YES
         RANGE	:   2..4093           	DEFVALUE	:    4093
         UNITS	:   NA           	SPARSE		:    NA
         DESCR	:   NA"
    ::= { issSystem 34 }

issSwitchRedundancyStatus OBJECT-TYPE
    SYNTAX      INTEGER { active(1), standby(2) }
    ACCESS      read-write
    STATUS      mandatory
    DESCRIPTION 
        "Specifies the switch redundancy status.
         When the switch is configured as standby except control port all 
         other ports will goes down. The switch in standby state, will not
         communicate with peer systems. When the switch is configured as  
         active, the switch will be operationally up and it will communicate 
         with peer systems.
         ALCATEL NOTE:
         ACCESS	:   NA           	USAGE		:    NA
         PERSIST:   NO          	INSRVMOD	:    YES
         RANGE	:   NA           	DEFVALUE	:    NA
         UNITS	:   NA           	SPARSE		:    NA
         DESCR	:   NA"
    DEFVAL      { standby }
    ::= { issSystem 35 }

issLastConfigChangeStatus OBJECT-TYPE
    SYNTAX      DisplayString
    ACCESS      read-only
    STATUS      mandatory
    DESCRIPTION 
        "Specifies whether Last Configuration change has been saved in NT after 
         restart and Current status of Restore.
         ALCATEL NOTE:
         ACCESS	:   NA           	USAGE		:    NA
         PERSIST:   NO          	INSRVMOD	:    NA
         RANGE	:   NA           	DEFVALUE	:    NA
         UNITS	:   NA           	SPARSE		:    NA
         DESCR	:   NA"
    ::= { issSystem 36 }

issHttpStatus OBJECT-TYPE
    SYNTAX      INTEGER { enable(1), disable(2) }
    ACCESS      read-write
    STATUS      mandatory
    DESCRIPTION 
        "Enables or disables Http Access for the Users.
         ALCATEL NOTE:
         ACCESS	:   NA           	USAGE		:    NA
         PERSIST:   YES          	INSRVMOD	:    YES
         RANGE	:   NA           	DEFVALUE	:    NA
         UNITS	:   NA           	SPARSE		:    NA
         DESCR	:   NA"
    ::= { issSystem 37 }

issBaseBridgeAddress OBJECT-TYPE
    SYNTAX      MacAddress
    ACCESS      read-only
    STATUS      mandatory
    DESCRIPTION 
        "The MAC address used by this bridge when it must
         be referred to in a unique fashion.   It is
         recommended that this be the numerically smallest
         MAC address of all ports that belong to this
         bridge.  However it is only required to be unique.
         When concatenated with dot1dStpPriority a unique
         BridgeIdentifier is formed which is used in the
         Spanning Tree Protocol.
         ALCATEL NOTE:
         ACCESS	:   NA           	USAGE		:    NA
         PERSIST:   NO          	INSRVMOD	:    NA
         RANGE	:   NA    		DEFVALUE	:    NA
         UNITS	:   NA           	SPARSE		:    NA
         DESCR	:   The Invalid MAC address are complete zero address 
         		  00:00:00:00:00:00 or Multicast or Broadcast Address"
    ::= { issSystem 38 }

issDefaultGateway OBJECT-TYPE
    SYNTAX      IpAddress
    ACCESS      read-write
    STATUS      mandatory
    DESCRIPTION 
        "Default IP Address of the system.
         
         This IP address, if modified, will take effect only when the 
         configuration is stored & restored.
           ALCATEL NOTE:
           ACCESS	:   NA           	USAGE		:    NA
           PERSIST:   YES          	INSRVMOD	:    YES
           RANGE	:   NA    	        DEFVALUE	:    NA
           UNITS	:   NA           	SPARSE		:    NA
           DESCR	:   NA"
    ::= { issSystem 39 }

issSystemMacAddress OBJECT-TYPE
    SYNTAX      MacAddress
    ACCESS      read-only
    STATUS      mandatory
    DESCRIPTION 
        "The System MAC address used by this bridge when it must
         be referred to in a unique fashion.
         ALCATEL NOTE:
         ACCESS	:   NA           	USAGE		:    NA
         PERSIST:   NO          	INSRVMOD	:    NA
         RANGE	:   NA    	        DEFVALUE	:    NA
         UNITS	:   NA           	SPARSE		:    NA
         DESCR	:   NA"
    ::= { issSystem 45 }

issOperatorReqOSPDevice OBJECT-TYPE
    SYNTAX      INTEGER { config1(1), config2(2), tffp(3) }
    ACCESS      read-write
    STATUS      mandatory
    DESCRIPTION 
        "Sets the requested version in the BSP
         ALCATEL NOTE:
         ACCESS	:   NA           	USAGE		:    NA
         PERSIST:   NO          	INSRVMOD	:    YES
         RANGE	:   NA    	        DEFVALUE	:    NA
         UNITS	:   NA           	SPARSE		:    NA
         DESCR	:   NA"
    ::= { issSystem 46 }

issCurrentOSPVersion OBJECT-TYPE
    SYNTAX      INTEGER { config1(1), config2(2), tffp(3) }
    ACCESS      read-only
    STATUS      mandatory
    DESCRIPTION 
        "Displays the current version from where it is loaded
         ALCATEL NOTE:
         ACCESS	:   NA           	USAGE		:    NA
         PERSIST:   NO          	INSRVMOD	:    NA
         RANGE	:   NA 	                DEFVALUE	:    NA
         UNITS	:   NA           	SPARSE		:    NA
         DESCR	:   NA"
    ::= { issSystem 47 }

issUBootromFromIp OBJECT-TYPE
    SYNTAX      IpAddress
    ACCESS      read-write
    STATUS      mandatory
    DESCRIPTION 
        "The Ip Address of machine from where the Bootrom has to be Updated.
         ALCATEL NOTE:
         ACCESS	:   NA           	USAGE		:    NA
         PERSIST:   NO          	INSRVMOD	:    YES
         RANGE	:   NA    	        DEFVALUE	:    NA
         UNITS	:   NA           	SPARSE		:    NA
         DESCR	:   NA"
    ::= { issSystem 49 }

issUBootromName OBJECT-TYPE
    SYNTAX      DisplayString (SIZE(1..256))
    ACCESS      read-write
    STATUS      mandatory
    DESCRIPTION 
        "The Bootrom name which is to be updated.
         ALCATEL NOTE:
         ACCESS	:   NA           	USAGE		:    NA
         PERSIST:   NO          	INSRVMOD	:    YES
         RANGE	:   1..150  	        DEFVALUE	:    NA
         UNITS	:   NA           	SPARSE		:    NA
         DESCR	:   NA"
    ::= { issSystem 50 }

issInitiateUBootrom OBJECT-TYPE
    SYNTAX      TruthValue
    ACCESS      read-write
    STATUS      mandatory
    DESCRIPTION 
        "Initiates the Update Bootrom operation. This will take only True value.
         and if set to false this will give error. When this object is set to 
         True, bootrom will be updated using the tftp and staus of the updation can
         be found using the issUBootromStaus.
            ALCATEL NOTE:
            ACCESS	:   NA           	USAGE		:    NA
            PERSIST:   NO          	INSRVMOD	:    YES
            RANGE	:   1  	                DEFVALUE	:    NA
            UNITS	:   NA           	SPARSE		:    NA
            DESCR	:   NA"
    ::= { issSystem 51 }

issUBootromStatus OBJECT-TYPE
    SYNTAX      INTEGER { inprogress(1), successful(2), failed(3) }
    ACCESS      read-only
    STATUS      mandatory
    DESCRIPTION 
        "The status of the Bootrom Image Update operation.
         ALCATEL NOTE:
         ACCESS	:   NA         		USAGE		:    NA
         PERSIST:   NO          	INSRVMOD	:    NA
         RANGE	:   NA  	        DEFVALUE	:    NA
         UNITS	:   NA           	SPARSE		:    NA
         DESCR	:   NA"
    ::= { issSystem 52 }

issSingleIPaddressStatus OBJECT-TYPE
    SYNTAX      INTEGER { enable(1), disable(2) }
    ACCESS      read-only
    STATUS      obsolete
    DESCRIPTION 
        "This object is readonly.The default value is single ip enabled.
         ALCATEL NOTE:
         ACCESS	:   NA         		USAGE		:    NA
         PERSIST:   NO          	INSRVMOD	:    NA
         RANGE	:   NA  	        DEFVALUE	:    NA
         UNITS	:   NA           	SPARSE		:    NA
         DESCR	:   NA"
    DEFVAL      { enable }
    ::= { issSystem 53 }

issEnCryptionFlagStatus OBJECT-TYPE
    SYNTAX      INTEGER { encrypted(1), notencrypted(2) }
    ACCESS      read-only
    STATUS      mandatory
    DESCRIPTION 
        "Status of Encryption flag of the iss configuration file.
         ALCATEL NOTE:
         ACCESS	:   NA         		USAGE		:    NA
         PERSIST:   NO          	INSRVMOD	:    NA
         RANGE	:   NA 	                DEFVALUE	:    NA
         UNITS	:   NA           	SPARSE		:    NA
         DESCR	:   NA"
    ::= { issSystem 54 }

issMacLearningStatus OBJECT-TYPE
    SYNTAX      INTEGER { enable(1), disable(2) }
    ACCESS      read-write
    STATUS      mandatory
    DESCRIPTION 
        "Enables or disables the Mac Learning option on network ports. when set disable Mac learning will 
         will be disabled on all the network ports.When set enable Mac learning will be
         enabled on network ports 
         ALCATEL NOTE:
         ACCESS	:   NA         		USAGE		:    NA
         PERSIST:   YES          	INSRVMOD	:    YES
         RANGE	:   NA  	        DEFVALUE	:    NA
         UNITS	:   NA           	SPARSE		:    NA
         DESCR	:   NA"
    DEFVAL      { enable }
    ::= { issSystem 55 }

issSwitchMacMode OBJECT-TYPE
    SYNTAX      INTEGER { native(1), legacy(2) }
    ACCESS      read-write
    STATUS      mandatory
    DESCRIPTION 
        "This object is used to specify the MAC address mode. If it is set to 'NATIVE' then next time 
         the system comes up system MAC address will be set to port no 1 MAC address. If it is set to
         'LEGACY' mode then the system MAC address will be set to port no 17 MAC address. This will take
         effect only from the next time the system boots up. This object does not have any relevance for
         ECNT-A releases. It is a dummy object for ECNT-A. So changing this object and restarting in ECNT-A
         will not result in a change in the system MAC address. 
         ALCATEL NOTE:
         ACCESS	:   NA         		USAGE		:    NA
         PERSIST:   YES          	INSRVMOD	:    YES
         RANGE	:   NA  	        DEFVALUE	:    DEP
         UNITS	:   NA           	SPARSE		:    NA
         DESCR	:   The Default value of this object for ECNT-A is 'legacy' and for ECNT-C is 'native'."
    ::= { issSystem 56 }

issConfigureNTIO OBJECT-TYPE
    SYNTAX      TruthValue
    ACCESS      read-write
    STATUS      mandatory
    DESCRIPTION 
        "When set as 'true' configuring the NTIO is initiated.
         As soon as the NTIO is configured, the value 
         of this object reverts back to 'false'.   
          
           ALCATEL NOTE:
           ACCESS	:   NA           	USAGE		:    NA
           PERSIST:   NO          	INSRVMOD	:    YES
           RANGE	:   1,2           	DEFVALUE	:    NA
           UNITS	:   NA           	SPARSE		:    NA
           DESCR	:   This object is applicable for ECNT-A/C/E and NANT-A.
         For ECNT-A/C/E  - The purpose of the object is to inform 
         LANX about the GENC NTIO card initialization status.
         For NANT-A - The purpose of the object is to inform LANX 
         about the NTIO board type and SFP presence status."
    DEFVAL      { false }
    ::= { issSystem 57 }

issSystemNumberOfPorts OBJECT-TYPE
    SYNTAX      INTEGER
    ACCESS      read-only
    STATUS      mandatory
    DESCRIPTION 
        "This object gives the number of ports available in the system. All the tables which have
         port number as index and whose table size is derived from the number of ports will have
         the size as the value of this object."
    ::= { issSystem 58 }

issPeerLanxCommStatus OBJECT-TYPE
    SYNTAX      INTEGER { down(1), up(2) }
    ACCESS      read-write
    STATUS      mandatory
    DESCRIPTION 
        "This MIB object  shows the status of the peer LANX
         communication. If the status of this object is UP 
         means, the peer LANX is up and able to communicate 
         with the peer LANX otherwise the peer LANX is down 
         and communication with the peer LANX is not possible.
         ALCATEL NOTE:
         ACCESS	:   NA           	USAGE		:    NA
         PERSIST:   NO          	INSRVMOD	:    NA
         RANGE	:   1 - 2           	DEFVALUE	:    down
         UNITS	:   NA           	SPARSE		:    NA
         DESCR	:   NA"
    DEFVAL      { down }
    ::= { issSystem 59 }

issLanxRedundancyOperStatus OBJECT-TYPE
    SYNTAX      INTEGER { active(1), coldstandby(2), hotstandby(3), 
                    inactive(4) }
    ACCESS      read-only
    STATUS      mandatory
    DESCRIPTION 
        "issLanxRedundancyOperStatus specifies Operational status
         Inactive: When in Inactive state, LANX shall make all the ports
         operationally down and wait for instructions from NT OBC to move
         to other operational states. If the LANX is in this mode there 
         wont be any hardware and software entries.
         
         Active: One of the operational modes of LANX in which the LANX 
         performs transmits and receives of all Control PDUs.
         
         Cold Standby: This is a state of the LANX in which the dynamic 
         data is not inline with the data held in the Active.The Static
         data in the Standby LANX is in sync with Standby NT (iss.conf).
         
         Hot Standby: In this state, the standby LANX is inline with the
         Active in terms of static and dynamic data and is ready to
         take-over traffic in case of switchover.
         
         Note: GET for this object, for boards which doesn't support Hitless 
              Redundancy feature(ERAM-A, ECNTC-CRMode), LANX Admin state 
              (issSwitchRedundancyStatus) is returned.
         ALCATEL NOTE:
         ACCESS	:   NA           	USAGE		:    NA
         PERSIST:   NO          	INSRVMOD	:    NA
         RANGE	:   1 - 4           DEFVALUE	:    inactive
         UNITS	:   NA           	SPARSE		:    NA
         DESCR	:   NA"
    ::= { issSystem 60 }

issSyncFailureCause OBJECT-TYPE
    SYNTAX      INTEGER { noSync(0), applyFail(1), seqNoMismatch(2), 
                    partialBulkSync(3), seqCounterOverflow(4), 
                    applyCounterOverflow(5) }
    ACCESS      read-only
    STATUS      mandatory
    DESCRIPTION 
        "This MIB object explains the cause of static or dynamic sync failure. 
         This mib ojects is always used with dynamicDataSyncFailure and 
         staticDataSyncFailure traps. 'noSync' is a dummy value and will not be used
         with static or dynamic sync failure traps. 
         ALCATEL NOTE:
         ACCESS	:   NA           	USAGE		:    NA
         PERSIST:   NO          	INSRVMOD	:    NA
         RANGE	:   0 - 5           	DEFVALUE	:    noSync
         UNITS	:   NA           	SPARSE		:    NA
         DESCR	:   NA"
    DEFVAL      { noSync }
    ::= { issSystem 61 }

issInitiateIntermediateConfigSave OBJECT-TYPE
    SYNTAX      TruthValue
    ACCESS      read-write
    STATUS      mandatory
    DESCRIPTION 
        "This object is triggered every 10mins from NT.When set as 'true' switch 
         intermediate configurations save operation is initiated. This object will 
         be acked only if the time gap between the previous SNMPSET and the currently 
         initiated SNMPSET 'IntermediateConfigSave' equals or exceeds the SNMP guard 
         time configured in the lanx.cfg file (<SNMP_GUARD_TIME>).The default value is 
         60 seconds. If the above condition is not met,the object 'intermediateConfigSave' 
         will be nacked with error-code 'Snmp inter SET pdu timer not expired'.
         
         While 'IntermediateConfigSave' is in progress,
         ->if any further SNMPSET is requested then the ongoing intermediateConfigSave
         process will be aborted(during preparing or writing the configuration file to 
         flash)with 'intermediateConfigSaveAbort' trap. The new SNMPSET will be processed. 
         This is the applicable for 'ForcedConfigSave' also.
         
         ->if no further SNMPSET is requested,the intermediate save process will continue to 
         complete and the value of this object reverts back to 'false'.
         
         All the configurations made via the three interfaces viz.
         -> commandline interface
         -> Web Interface
         -> SNMP interface
         are saved either in flash or in the chosen remote system
         depending upon 'ConfigSaveOption'.  
         
         ALCATEL NOTE:
         ACCESS  :   NA              USAGE       :    NA
         PERSIST :   NO              INSRVMOD    :    YES
         RANGE   :   1,2             DEFVALUE    :    NA
         UNITS   :   NA              SPARSE      :    NA
         DESCR   :   NA"
    DEFVAL      { false }
    ::= { issSystem 62 }

issIntermediateConfigSaveNeeded OBJECT-TYPE
    SYNTAX      TruthValue
    ACCESS      read-only
    STATUS      mandatory
    DESCRIPTION 
        "Specifies whether there was a change in system configuration
         since last configuration save.
         True(1)  -> Configuration changed since the last 
         Configuration save, so 'issInitiateIntermediateConfigSave'
         can be triggered.
         False(2) -> Configuration not changed since the last 
         Configuration save, so 'issInitiateIntermediateConfigSave' may 
         not be triggered.
         ALCATEL NOTE:
         ACCESS	:   NA           	USAGE		:    NA
         PERSIST:   NO          	INSRVMOD	:    NA
         RANGE	:   1,2         	DEFVALUE	:    FALSE 
         UNITS	:   NA           	SPARSE		:    NA
         DESCR	:   NA"
    DEFVAL      { false }
    ::= { issSystem 63 }

issSystemActivatedCde OBJECT-TYPE
    SYNTAX      Gauge (0..4294967295)
    ACCESS      read-only
    STATUS      mandatory
    DESCRIPTION 
        "The Activated CDE is a bitmap listing the CDE features that are 
         active in SHUB. CDE features are activated during system startup only, 
         and is based on the configured OperatorID.
         ALCATEL NOTE:
         ACCESS : NA		USAGE   : NA
         PERSIST: NA		INSRVMOD: NA
         RANGE  : NA		DEFVALUE: NA
         UNITS  : NA		SPARSE  : NA
         DESCR  : This object will not be used by LANX."
    DEFVAL      { 0 }
    ::= { issSystem 64 }

issConfigControl OBJECT IDENTIFIER
    ::= { iss 2 }

issConfigCtrlTable OBJECT-TYPE
    SYNTAX      SEQUENCE OF IssConfigCtrlEntry
    ACCESS      not-accessible
    STATUS      mandatory
    DESCRIPTION 
        "A table to control device features like egress traffic control,
         stats collection, etc. either for the entire switch or for each
         interface in the switch.
         ALCATEL NOTE :
         	TABLESIZE    : DEP
         DESCR        : DEP(TABLESIZE)The range of this table is the number of physical interfaces
         			   in the system + 1. The maximum ports in the system can be 
         			   got from the object issSystemNumberOfPorts from fsiss.mib."
    ::= { issConfigControl 1 }

issConfigCtrlEntry OBJECT-TYPE
    SYNTAX      IssConfigCtrlEntry
    ACCESS      not-accessible
    STATUS      mandatory
    DESCRIPTION 
        "An entry appears in this table for each interface in the system.
         
         In addition to that an entry with index '0' is created in this
         table by default.
         
         If 'issConfigCtrlStatus' of the entry '0' is made 'valid', then
         global control is chosen and the values against entry '0' is 
         applicable for all the interfaces of the switch.
         
         If 'issConfigCtrlStatus' of the entry '0' is made 'invalid', 
         then interface-wise control is chosen & the values against each 
         interface index is applicable for that interface.
         
         At a particular point of time, either global control will be
         applicable or interface-wise control is applicable. 
         Both will not be considered together.
         
         Index to the table is the interface index of the port.
         Row creation : A CONFIG-CTRL-ENTRY shall be created when the system is initialized.    
         Row deletion : NA.
         	Index usage : The indexe is issConfigCtrlIndex.
          	   Note that entries will be presented to the SNMP manager in full
          	   lexicographical order :  sorted on issConfigCtrlIndex"
    INDEX       { issConfigCtrlIndex }
    ::= { issConfigCtrlTable 1 }

IssConfigCtrlEntry ::= SEQUENCE {
    issConfigCtrlIndex              INTEGER,
    issConfigCtrlEgressStatus       INTEGER,
    issConfigCtrlStatsCollection    INTEGER,
    issConfigCtrlStatus             INTEGER
}

issConfigCtrlIndex OBJECT-TYPE
    SYNTAX      INTEGER (0..65535)
    ACCESS      not-accessible
    STATUS      mandatory
    DESCRIPTION 
        "Interface index of the port for which the configuration
         in this entry applies.
         
         If any configuration is made in this table for the index '0',
         that configuration will be considered as global configuration 
         and is applicable for all the interfaces of the switch.
            ALCATEL NOTE:
            ACCESS	:   NA         		USAGE		:    NA
            PERSIST:   YES          	INSRVMOD	:    NA
            RANGE	:   DEP  	        DEFVALUE	:    NA
            UNITS	:   NA           	SPARSE		:    NO
            DESCR	:   DEP(RANGE) The index value is derived from the object issSystemNumberOfPorts"
    ::= { issConfigCtrlEntry 1 }

issConfigCtrlEgressStatus OBJECT-TYPE
    SYNTAX      INTEGER { enabled(1), disabled(2) }
    ACCESS      read-write
    STATUS      mandatory
    DESCRIPTION 
        "Controls the transmission of egress traffic over this interface.
         
         This value for entry '0' controls the egress traffic over all 
         interfaces.
           ALCATEL NOTE:
           ACCESS	:   NA         		USAGE		:    NA
           PERSIST:   YES		        INSRVMOD	:    YES
           RANGE	:   NA  	        DEFVALUE	:    NA
           UNITS	:   NA           	SPARSE		:    NO
           DESCR	:   NA"
    DEFVAL      { enabled }
    ::= { issConfigCtrlEntry 2 }

issConfigCtrlStatsCollection OBJECT-TYPE
    SYNTAX      INTEGER { enabled(1), disabled(2) }
    ACCESS      read-write
    STATUS      mandatory
    DESCRIPTION 
        "Enables or disables statistics collection for this interface.
         
         This value for entry '0' controls the stats collection for all
         interfaces.
           ALCATEL NOTE:
           ACCESS	:   NA 	        	USAGE		:    NA
           PERSIST:   YES          	INSRVMOD	:    YES
           RANGE	:   NA  	        DEFVALUE	:    NA
           UNITS	:   NA           	SPARSE		:    NO
           DESCR	:   NA"
    DEFVAL      { enabled }
    ::= { issConfigCtrlEntry 3 }

issConfigCtrlStatus OBJECT-TYPE
    SYNTAX      INTEGER { valid(1), invalid(2) }
    ACCESS      read-write
    STATUS      mandatory
    DESCRIPTION 
        "Speficies the validity of the entry.
         
         If the 'Config Control Status' for entry '0' is made 'valid',
         then global control is chosen in the system.
         It signifies that the values against entry '0' is applicable 
         for all the interfaces of the switch.
         
         If the 'Config Control Status' for entry '0' is made 'invalid',
         then interface-wise control is chosen.
         Then the values against each interface index is applicable 
         for that interface.
         
         By default, 'issConfigCtrlStatus' will be 'invalid' for 
         entry '0' and 'valid' for all other entries. 
         (ie) by default, interface-wise configuration is enabled
         in the system.
         
         The status of entries other than the zeroth(0th) entry can not be
         made 'invalid'.
           ALCATEL NOTE:
           ACCESS	:   NA  	       	USAGE		:    NA
           PERSIST:   YES	         	INSRVMOD	:    YES
           RANGE	:   NA  	        DEFVALUE	:    1
           UNITS	:   NA           	SPARSE		:    NO
           DESCR	:   NA"
    ::= { issConfigCtrlEntry 4 }

issPortCtrlTable OBJECT-TYPE
    SYNTAX      SEQUENCE OF IssPortCtrlEntry
    ACCESS      not-accessible
    STATUS      mandatory
    DESCRIPTION 
        "A table to control the port specific parameters of the device like speed,
         duplex mode, etc.
         ALCATEL NOTE :
         	TABLESIZE    : DEP
         DESCR        : DEP(TABLESIZE)The range of the table is the maximum physical interfaces
         			   in the system which can be got from the object issSystemNumberOfPorts
         			   in fsiss.mib. "
    ::= { issConfigControl 2 }

issPortCtrlEntry OBJECT-TYPE
    SYNTAX      IssPortCtrlEntry
    ACCESS      not-accessible
    STATUS      mandatory
    DESCRIPTION 
        "An entry appears in this table for each Electrical interface in the system.
         
         Index to the table is the interface index of the port.
         Row creation : A PORT-CTRL-TABLE entry shall be created when the system is initialized.    
         Row deletion : NA.
         	Index usage : The indexe is issPortCtrlIndex.
          	   Note that entries will be presented to the SNMP manager in full
          	   lexicographical order :  sorted on issPortCtrlIndex"
    INDEX       { issPortCtrlIndex }
    ::= { issPortCtrlTable 1 }

IssPortCtrlEntry ::= SEQUENCE {
    issPortCtrlIndex                    INTEGER,
    issPortCtrlMode                     INTEGER,
    issPortCtrlDuplex                   INTEGER,
    issPortCtrlSpeed                    INTEGER,
    issPortCtrlFlowControl              INTEGER,
    issPortCtrlRenegotiate              TruthValue,
    issPortCtrlMaxMacAddr               INTEGER,
    issPortCtrlMaxMacAction             INTEGER,
    issPortCtrlType                     INTEGER,
    issPortCtrlMulticastFloodingMode    INTEGER,
    issPortCtrlSfpBankA0                OCTET STRING,
    issPortCtrlSfpBankA2                OCTET STRING,
    issPortCtrlSfpPresence              INTEGER,
    issPortCtrlRxLosSignalStatus        INTEGER,
    issPortCtrlTxFaultStatus            INTEGER,
    issPortCtrlClearCounters            TruthValue
}

issPortCtrlIndex OBJECT-TYPE
    SYNTAX      INTEGER (0..65535)
    ACCESS      not-accessible
    STATUS      mandatory
    DESCRIPTION 
        "Interface index of the port for which the configuration
         in this entry applies.
            ALCATEL NOTE:
            ACCESS	:   NA         		USAGE		:    NA
            PERSIST:   YES          	INSRVMOD	:    NA
            RANGE	:   DEP  	        DEFVALUE	:    NA
            UNITS	:   NA           	SPARSE		:    NO
            DESCR	:   DEP(RANGE)The range is the maximum number of physical ports available in 
         		     the system. The value can be got from the object issSystemNumberOfPorts
         		     in fsiss.mib."
    ::= { issPortCtrlEntry 1 }

issPortCtrlMode OBJECT-TYPE
    SYNTAX      INTEGER { auto(1), oneGB(2), hundredMBPS(3), tenMBPS(4), 
                    tenGbps(5), twoDotFiveGbps(6) }
    ACCESS      read-write
    STATUS      mandatory
    DESCRIPTION 
        "Speficies the mode in which the speed of the interface is
         determined. If set as 'auto', the hardware senses speed and 
         negotiates with the port on the other end of the link for 
         data transfer operation as 'full-duplex' or 'half-duplex' 
         and about flow contol. 
         	If set as oneGB, hundredMBPS, tenMBPS, tenGbps, twoDotFiveGbps
         the interface 	will be in 'nonegotiation' mode , and the
         configured values for interface link like duplex mode and
         flow control will be effective.
         --Added as part of FGNR4.1 BLSAP START
         If issPortCtrlType is configured as 'asam' and the port is 
         connected via back plane, then this object can be set only as 'auto'
         for ECNT-E and NRNT-A boards.
         --Added as part of FGNR4.1 BLSAP END
         ALCATEL NOTE:
         ACCESS	:   NA         		USAGE		:    NA
         PERSIST:   YES            	INSRVMOD	:    YES
         RANGE	:   NA  	        DEFVALUE	:    NA
         UNITS	:   NA           	SPARSE		:    NO
         DESCR	:   NA"
    DEFVAL      { auto }
    ::= { issPortCtrlEntry 2 }

issPortCtrlDuplex OBJECT-TYPE
    SYNTAX      INTEGER { full(1), half(2) }
    ACCESS      read-write
    STATUS      mandatory
    DESCRIPTION 
        "Configures interface data transfer mode as full-duplex or half-duplex.
         
         This object can be configured only if the 'PortCtrlMode' is 'nonegotiation'. 
         If the 'PortCtrlMode' is 'auto', it contains the default value and 
         if the mode changed from 'nonegotiation' to 'auto'  then   it 
          retains the configured value.
         
            ALCATEL NOTE:
            ACCESS	:   NA         		USAGE		:    NA
            PERSIST:   YES          	INSRVMOD	:    NO
            RANGE	:   NA  	        DEFVALUE	:    1
            UNITS	:   NA           	SPARSE		:    NO
            DESCR	:   This object can be configured only 
         	                    if the 'PortCtrlMode' is 'nonegotiation' so the INSRVMOD is NO"
    ::= { issPortCtrlEntry 3 }

issPortCtrlSpeed OBJECT-TYPE
    SYNTAX      INTEGER { oneGB(1), hundredMBPS(2), tenMBPS(3), 
                    tenGbps(4), twoDotFiveGbps(5) }
    ACCESS      read-only
    STATUS      mandatory
    DESCRIPTION 
        "Operational interface speed. This object obtains the value from
         Hardware to provide the current operational speed.
           ALCATEL NOTE:
         ACCESS	:   NA         		USAGE		:    NA
         PERSIST:   NO          	INSRVMOD	:    NA
         RANGE	:   NA  	        DEFVALUE	:    1
         UNITS	:   NA           	SPARSE		:    NO
         DESCR	:   NA"
    ::= { issPortCtrlEntry 4 }

issPortCtrlFlowControl OBJECT-TYPE
    SYNTAX      INTEGER { enable(1), disable(2) }
    ACCESS      read-write
    STATUS      mandatory
    DESCRIPTION 
        "Enables / disables flow control for the interface.
         
         This object be configured only if the 'PortCtrlMode' is 'nonegotiation'.
         If the 'PortCtrlMode' is 'auto', it obtains the value from Hardware 
         after negotiating  with its peer
            ALCATEL NOTE:
            ACCESS	:   NA         		USAGE		:    NA
            PERSIST:   YES          	INSRVMOD	:    NO
            RANGE	:   NA  	        DEFVALUE	:    2
            UNITS	:   NA           	SPARSE		:    NO
            DESCR	:   This object be configured only if the 
         		    'PortCtrlMode' is 'nonegotiation' so INSRVMOD is NO"
    ::= { issPortCtrlEntry 5 }

issPortCtrlRenegotiate OBJECT-TYPE
    SYNTAX      TruthValue
    ACCESS      read-write
    STATUS      mandatory
    DESCRIPTION 
        "When configured as 'true', restarts autonegotiation on the interface.
         
         Once autonegotiation is restarted, the value of this object reverts
         to 'false'.
           ALCATEL NOTE:
           ACCESS	:   NA         		USAGE		:    NA
           PERSIST:   NA          	INSRVMOD	:    NA
           RANGE	:   NA  	        DEFVALUE	:    NA
           UNITS	:   NA           	SPARSE		:    NA
           DESCR	:   This is not used by Alcatel"
    DEFVAL      { false }
    ::= { issPortCtrlEntry 6 }

issPortCtrlMaxMacAddr OBJECT-TYPE
    SYNTAX      INTEGER
    ACCESS      read-only
    STATUS      mandatory
    DESCRIPTION 
        "Specifies the maximum number of new MAC addresses that can be 
         learnt over the interface.
            ALCATEL NOTE:
            ACCESS	:   NA         		USAGE		:    NA
            PERSIST:   NA          	INSRVMOD	:    NA
            RANGE	:   NA  	        DEFVALUE	:    NA
            UNITS	:   NA           	SPARSE		:    NA
            DESCR	:   This is not used by Alcatel"
    ::= { issPortCtrlEntry 7 }

issPortCtrlMaxMacAction OBJECT-TYPE
    SYNTAX      INTEGER { drop(1), purgeLRU(2) }
    ACCESS      read-write
    STATUS      mandatory
    DESCRIPTION 
        "Specifies the action to be taken when the maximum number of new MAC 
         addresses that can be learnt over the interface is exceeded.
         
         If the action is 'drop', the packet with new mac address will be
         dropped once the maximum number of new MAC addresses that can be
         learnt over the interface is exceeded.
         
         If the action is 'purgeLRU', the 'Least Recently Used' mac address
         will be deleted from the MAC table and the new mac address will be
         added.
            ALCATEL NOTE:
            ACCESS	:   NA         		USAGE		:    NA
            PERSIST:   NA          	INSRVMOD	:    NA
            RANGE	:   NA  	        DEFVALUE	:    NA
            UNITS	:   NA           	SPARSE		:    NA
            DESCR	:   This is not used by Alcatel"
    ::= { issPortCtrlEntry 8 }

issPortCtrlType OBJECT-TYPE
    SYNTAX      INTEGER { user(1), subtending(2), network(3), asam(4), 
                    control(5), unused(6), outband(7) }
    ACCESS      read-write
    STATUS      mandatory
    DESCRIPTION 
        "Specifies the type of port to be configured on a given port index
         
         USER type is configured for all the users who are connected directly
         connected to LanX.
         
         Subteding type is configured for all the links used to connect HUB-ESAM.
         
         Network type is configured for the ports connected to ISP(s).
         
         The ASAM/CONTROL port types cannot be configured by user, they are fixed in the system.
         Unused Port means the port is not in use and its Configuration values are all default values.
         Outband Mangament port means are typically configured at ESAM installation time for dedicated manageability purpose
           ALCATEL NOTE:
           ACCESS	:   NA         		USAGE		:    NA
           PERSIST:   YES          	INSRVMOD	:    YES
           RANGE	:   NA 	                DEFVALUE	:    NA
           UNITS	:   NA           	SPARSE		:    NO
           DESCR	:   NA"
    ::= { issPortCtrlEntry 9 }

issPortCtrlMulticastFloodingMode OBJECT-TYPE
    SYNTAX      INTEGER { enable(1), disable(2) }
    ACCESS      read-write
    STATUS      mandatory
    DESCRIPTION 
        "Specifies the multicast flooding mode of the port.      
         If set as 'enable' then flood the multicast packet to all the member ports of the VLAN not in the multicast table.
         If set as 'disable', then drop multicast packet not in the multicast table.
         ALCATEL NOTE:
         ACCESS	:   NA         		USAGE		:    NA
         PERSIST:   NO          	INSRVMOD	:    YES
         RANGE	:   NA  	        DEFVALUE	:    NA
         UNITS	:   NA           	SPARSE		:    NO
         DESCR	:   NA"
    ::= { issPortCtrlEntry 10 }

issPortCtrlSfpBankA0 OBJECT-TYPE
    SYNTAX      OCTET STRING (SIZE(0..256))
    ACCESS      read-only
    STATUS      mandatory
    DESCRIPTION 
        "An string to store the bank A0 data from a SFP device. A SNMP timeout may happen if an attempt is made to 
         read more than 256 bytes using multivarbind.This mib object is intended to access by IACM only. In ECNT-C/NANT-x boards, 
         accessing this object or accessing by external managers will update OCTET STRING with 'Mib entry not supported'.
         ALCATEL NOTE:
         ACCESS	:   NA         		USAGE		:    NA
         PERSIST:   NO          	INSRVMOD	:    NA 
         RANGE	:   NA  	          DEFVALUE	:    NA
         UNITS	:   NA           	SPARSE		:    NO
         DESCR	:   NA"
    ::= { issPortCtrlEntry 11 }

issPortCtrlSfpBankA2 OBJECT-TYPE
    SYNTAX      OCTET STRING (SIZE(0..256))
    ACCESS      read-only
    STATUS      mandatory
    DESCRIPTION 
        "An string to store the bank A2 read data from a SFP device. A SNMP timeout may happen if an attempt is made to 
         read more than 256 bytes using multivarbind.This mib object is intended to access by IACM only. In ECNT-C/NANT-x boards, 
         accessing this object or accessing by external managers will  update OCTET STRING with 'Mib entry not supported'.
         ALCATEL NOTE:
             ACCESS:      NA           USAGE:       NA
             PERSIST:     NO           INSRVMOD:    NA 
             RANGE:       NA           DEFVALUE:    NA
             UNITS:         NA           SPARSE:      NO
             DESCR:       NA"
    ::= { issPortCtrlEntry 12 }

issPortCtrlSfpPresence OBJECT-TYPE
    SYNTAX      INTEGER { sfpNotPresent(0), sfpPresent(1), 
                    notAvailable(2) }
    ACCESS      read-only
    STATUS      mandatory
    DESCRIPTION 
        "This object checks for SFP presence for the particular port.If SFP is present, then this object returns value '1' and '0' if not present.This mib object is intended to access by IACM only. In ECNT-C /NANT-x boards accessing this object or 
         accessing by external managers will return 'NotAvailable'.
         ALCATEL NOTE:
         ACCESS	:   NA         		USAGE		:    NA
         PERSIST:   NA          	INSRVMOD	:    NA
         RANGE	:   NA  	        DEFVALUE	:    NA
         UNITS	:   NA           	SPARSE		:    NA
         DESCR	:   NAThis is not used by Alcatel"
    ::= { issPortCtrlEntry 13 }

issPortCtrlRxLosSignalStatus OBJECT-TYPE
    SYNTAX      INTEGER { norxLosSignal(0), rxLosSignal(1), 
                    notAvailable(2) }
    ACCESS      read-only
    STATUS      mandatory
    DESCRIPTION 
        "This object checks for RxL0S signal status for the particular SFP port. Retrieves '0' for no RX LOS signal or '1' for RxLOS status, or'2' if SFP is absent .If Rx LOS signal is OK then this object  returns '1' and '0' if NOK. This mib object is intended to access by IACM only.In ECNT-C /NANT-x boards accessing this object or or 
         accessing by external managers will also return 'NotAvailable'.
         ALCATEL NOTE:
         ACCESS	:   NA         		USAGE		:    NA
         PERSIST:   NA          	INSRVMOD	:    NA
         RANGE	:   NA  	        DEFVALUE	:    NA
         UNITS	:   NA           	SPARSE		:    NA
         DESCR	:   NAThis is not used by Alcatel"
    ::= { issPortCtrlEntry 14 }

issPortCtrlTxFaultStatus OBJECT-TYPE
    SYNTAX      INTEGER { notxfaultSignal(0), txfaultsignal(1), 
                    notAvailable(2) }
    ACCESS      read-only
    STATUS      mandatory
    DESCRIPTION 
        "This object checks for TX fault signal status for the particular SFP port. Retrieves '0' for no Tx Fault signal or '1' for Tx Fault signal status, or'2' if SFP is absent If Tx fault signal is OK then this object  returns '1' and '0' if NOK.This mib object is intended to access by IACM only. In ECNT-C/NANT-x boards accessing this object or accessing by external managers will also return 'NotAvailable'.
         
         ALCATEL NOTE:
         ACCESS	:   NA         		USAGE		:    NA
         PERSIST:   NA          	INSRVMOD	:    NA
         RANGE	:   NA  	        DEFVALUE	:    NA
         UNITS	:   NA           	SPARSE		:    NA
         DESCR	:   NAThis is not used by Alcatel"
    ::= { issPortCtrlEntry 15 }

issPortCtrlClearCounters OBJECT-TYPE
    SYNTAX      TruthValue
    ACCESS      read-write
    STATUS      mandatory
    DESCRIPTION 
        "When configured as 'true', clears the counters on the interface.
         Once the counters are cleared, the value of this object reverts
         to 'false'.The counters are represented by the following MIB objects:
            o ifHCInOctets
            o ifHCOutOctets 
            o dot1dTpHCPortInFrames 
            o dot1dTpHCPortOutFrames
            o ifHCInBroadcastPkts 
            o ifHCOutBroadcastPkts
            o ifHCInMulticastPkts
            o ifHCOutMulticastPkts
            o ifHCInUcastPkts
            o ifHCOutUcastPkts
            o ifInDiscards
            o ifOutDiscards
            o dot3StatsFCSErrors
            o etherStatsOversizePkts
            o etherStatsUndersizePkts
            o dot3StatsAlignmentErrors
            o dot3StatsSymbolErrors
         	  o dot1dTpPortInFrames  
         	  o dot1dTpPortOutFrames
         	  o dot1dBasePortBcastOutFrames 
         	  o dot1dBasePortMcastOutFrames 
         
         ALCATEL NOTE:
           ACCESS :   NA           USAGE   :    OPT
           PERSIST:   NO           INSRVMOD:    NA
           RANGE  :   NA           DEFVALUE:    false
           UNITS  :   NA           SPARSE  :    NA
           DESCR  :   NA"
    DEFVAL      { false }
    ::= { issPortCtrlEntry 16 }

issOpticalPortCtrlTable OBJECT-TYPE
    SYNTAX      SEQUENCE OF IssOpticalPortCtrlEntry
    ACCESS      not-accessible
    STATUS      mandatory
    DESCRIPTION 
        "A table to control the port specific parameters of the device .
         ALCATEL NOTE : This MIB Table is obsolete. It is retained for backward compatiblity.
         TABLESIZE     : 25 
         DESCR         : NA"
    ::= { issConfigControl 3 }

issOpticalPortCtrlEntry OBJECT-TYPE
    SYNTAX      IssOpticalPortCtrlEntry
    ACCESS      not-accessible
    STATUS      mandatory
    DESCRIPTION 
        "An entry appears in this table for each Optical interface in the system.
         
         Index to the table is the interface index of the port.
         Row creation : A OPTICAL-PORT-CTRL entry shall be created when the system is initialized.    
         Row deletion : NA.
         	Index usage : The indexe is issOpticalPortCtrlIndex.
          	   Note that entries will be presented to the SNMP manager in full
          	   lexicographical order :  sorted on issPortCtrlIndex"
    INDEX       { issOpticalPortCtrlIndex }
    ::= { issOpticalPortCtrlTable 1 }

IssOpticalPortCtrlEntry ::= SEQUENCE {
    issOpticalPortCtrlIndex                     INTEGER,
    issOpticalPortCtrlMode1GAutoNegotiation     INTEGER,
    issOpticalPortCtrlSpeed                     INTEGER
}

issOpticalPortCtrlIndex OBJECT-TYPE
    SYNTAX      INTEGER (0..65535)
    ACCESS      not-accessible
    STATUS      mandatory
    DESCRIPTION 
        "Physical Interface index of the port for which the configuration
         in this entry applies.
            ALCATEL NOTE: This MIB object is obsolete. It is retained for backward compatiblity. 
            ACCESS	:   NA         		USAGE		:    NA
            PERSIST:   YES          	INSRVMOD	:    NA
            RANGE	:   DEP  	        DEFVALUE	:    NA
            UNITS	:   NA           	SPARSE		:    NO
            DESCR	:  DEP(RANGE) The range is the maximum number of physical ports available in 
         		     the system. The value can be got from the object issSystemNumberOfPorts
         		     in fsiss.mib."
    ::= { issOpticalPortCtrlEntry 1 }

issOpticalPortCtrlMode1GAutoNegotiation OBJECT-TYPE
    SYNTAX      INTEGER { on(1), off(2) }
    ACCESS      read-write
    STATUS      mandatory
    DESCRIPTION 
        "Speficies the mode in which the speed of the interface is
         determined. If set as 'ON', the hardware senses speed and 
         negotiates with the port on the other end of the link.
         	If set as 'OFF', the interface 
         will be in 'nonegotiation' mode , and the Speed is the
         operational speed of the PHY.
         ALCATEL NOTE: This MIB object is obsolete. It is retained for backward compatiblity. 
         ACCESS	:   NA         		USAGE		:    NA
         PERSIST:   YES          	INSRVMOD	:    YES
         RANGE	:   NA  	        DEFVALUE	:    NA
         UNITS	:   NA           	SPARSE		:    NO
         DESCR	:   NA"
    DEFVAL      { off }
    ::= { issOpticalPortCtrlEntry 2 }

issOpticalPortCtrlSpeed OBJECT-TYPE
    SYNTAX      INTEGER { oneGB(1), hundredMBPS(2), tenGbps(3) }
    ACCESS      read-only
    STATUS      mandatory
    DESCRIPTION 
        "Operational Optical interface speed. This object obtains the value from
         Hardware to provide the current operational speed.
         ALCATEL NOTE: This MIB object is obsolete. It is retained for backward compatiblity. 
         ACCESS	:   NA         		USAGE		:    NA
         PERSIST:   NO          	INSRVMOD	:    NA
         RANGE	:   NA  	        DEFVALUE	:    NA
         UNITS	:   NA           	SPARSE		:    NO
         DESCR	:   NA"
    DEFVAL      { oneGB }
    ::= { issOpticalPortCtrlEntry 3 }

issInterfaceTypeTable OBJECT-TYPE
    SYNTAX      SEQUENCE OF IssInterfaceTypeEntry
    ACCESS      not-accessible
    STATUS      mandatory
    DESCRIPTION 
        "A table that gives interface type of the ports.
         ALCATEL NOTE :
         TABLESIZE    : DEP 
         DESCR        : DEP(TABLESIZE)The range of the table is the maximum physical interfaces+1
         			   in the system which can be got from the object issSystemNumberOfPorts
         			   in fsiss.mib. "
    ::= { issConfigControl 4 }

issInterfaceTypeEntry OBJECT-TYPE
    SYNTAX      IssInterfaceTypeEntry
    ACCESS      not-accessible
    STATUS      mandatory
    DESCRIPTION 
        "An entry appears in this table for each interface in the system,   
         Index to the table is the interface index of the port.
         Row creation : A INTERFACE-TYPE entry shall be created when the system is initialized.     
         Row deletion : NA.
         	Index usage : The indexe is issInterfaceTypeIndex .
          	   Note that entries will be presented to the SNMP manager in full
          	   lexicographical order :  sorted on issInterfaceTypeIndex "
    INDEX       { issInterfaceTypeIndex }
    ::= { issInterfaceTypeTable 1 }

IssInterfaceTypeEntry ::= SEQUENCE {
    issInterfaceTypeIndex   INTEGER,
    issInterfaceType        INTEGER
}

issInterfaceTypeIndex OBJECT-TYPE
    SYNTAX      INTEGER (0..65535)
    ACCESS      not-accessible
    STATUS      mandatory
    DESCRIPTION 
        "Interface index of the port for which the configuration
         in this entry applies.
            ALCATEL NOTE:
            ACCESS	:   NA         		USAGE		:    NA
            PERSIST:   NO          	INSRVMOD	:    NA
            RANGE	:   DEP  	        DEFVALUE	:    NA
            UNITS	:   NA           	SPARSE		:    NO
            DESCR	:   DEP(RANGE)The range is the maximum number of physical ports available in 
         		     the system. The value can be got from the object issSystemNumberOfPorts
         		     in fsiss.mib."
    ::= { issInterfaceTypeEntry 1 }

issInterfaceType OBJECT-TYPE
    SYNTAX      INTEGER { none(1), electrical(2), opticalAlcatelSFP(3), 
                    opticalNonAlcatelSFP(4), unknown(5) }
    ACCESS      read-only
    STATUS      mandatory
    DESCRIPTION 
        "Speficies the interface type through the packets 
         are transfered.This mib object is obsolete.For Backward compatability
         this mib object is retained.
         ALCATEL NOTE:
         ACCESS	:   NA         		USAGE		:    NA
         PERSIST:   NO          	INSRVMOD	:    NA
         RANGE	:   1,2,3,4 	        DEFVALUE	:    NA
         UNITS	:   NA           	SPARSE		:    NO
         DESCR	:   NA"
    ::= { issInterfaceTypeEntry 2 }

issMirror OBJECT IDENTIFIER
    ::= { iss 3 }

issMirrorStatus OBJECT-TYPE
    SYNTAX      INTEGER { disabled(1), enabled(2) }
    ACCESS      read-write
    STATUS      mandatory
    DESCRIPTION 
        "Provides control over the mirroring feature in the switch.
         ALCATEL NOTE:
         ACCESS	:   NA         		USAGE		:    NA
         PERSIST:   YES          	INSRVMOD	:    YES
         RANGE	:   NA 	                DEFVALUE	:    NA
         UNITS	:   NA           	SPARSE		:    NA
         DESCR	:   NA"
    DEFVAL      { disabled }
    ::= { issMirror 1 }

issMirrorToPort OBJECT-TYPE
    SYNTAX      INTEGER
    ACCESS      read-write
    STATUS      mandatory
    DESCRIPTION 
        "Specifies the port to which the mirrored traffic in the system 
         is to be copied.
          ALCATEL NOTE:
          ACCESS	:   NA         		USAGE		:    NA
          PERSIST:   YES          	INSRVMOD	:    YES
          RANGE	:   DEP	                DEFVALUE	:    0
          UNITS	:   NA           	SPARSE		:    NA
          DESCR	:   DEP(RANGE) The range is the maximum number of physical ports available in 
         		     the system. The value can be got from the object issSystemNumberOfPorts
         		     in fsiss.mib."
    ::= { issMirror 2 }

issMirrorCtrlTable OBJECT-TYPE
    SYNTAX      SEQUENCE OF IssMirrorCtrlEntry
    ACCESS      not-accessible
    STATUS      mandatory
    DESCRIPTION 
        "A table to control mirroring features for each interface in the switch.   
         ALCATEL NOTE:
         TABLESIZE    : DEP
         DESCR        : DEP(TABLESIZE)The range of the table is the maximum physical interfaces
         			   in the system which can be got from the object issSystemNumberOfPorts
         			   in fsiss.mib. "
    ::= { issMirror 3 }

issMirrorCtrlEntry OBJECT-TYPE
    SYNTAX      IssMirrorCtrlEntry
    ACCESS      not-accessible
    STATUS      mandatory
    DESCRIPTION 
        "An entry appears in this table for each interface 
         in the system.
         
         Both Hardware and Software Mirroring information is stored in each entry.
         
         Parameters in this table can be configured even if the 'issMirrorStatus'
         is disabled.When the 'issMirrorStatus' is enabled the parameters in 
         this table take effect.
                
         Row creation : A MIRROR-CONTROL entry shall be created when the system is initialized.     
         Row deletion : NA.
         	Index usage : The index is issMirrorCtrlIndex.
         lexicographical order :  sorted on issMirrorCtrlIndex"
    INDEX       { issMirrorCtrlIndex }
    ::= { issMirrorCtrlTable 1 }

IssMirrorCtrlEntry ::= SEQUENCE {
    issMirrorCtrlIndex                  INTEGER,
    issMirrorCtrlIngressMirroring       INTEGER,
    issMirrorCtrlEgressMirroring        INTEGER,
    issMirrorCtrlSwIngressMirroring     INTEGER,
    issMirrorCtrlSwEgressMirroring      INTEGER
}

issMirrorCtrlIndex OBJECT-TYPE
    SYNTAX      INTEGER (1..65535)
    ACCESS      not-accessible
    STATUS      mandatory
    DESCRIPTION 
        "The interface index of the port for which the configuration
         in this entry applies.
           
            ALCATEL NOTE:
            ACCESS	:   NA         		USAGE		:    NA
            PERSIST:   YES          	INSRVMOD	:    NA
            RANGE	:   DEP  	        DEFVALUE	:    NA
            UNITS	:   NA           	SPARSE		:    NO
            DESCR	:   DEP(RANGE) The range is the maximum number of physical ports available in 
         		     the system. The value can be got from the object issSystemNumberOfPorts
         		     in fsiss.mib."
    ::= { issMirrorCtrlEntry 1 }

issMirrorCtrlIngressMirroring OBJECT-TYPE
    SYNTAX      INTEGER { enabled(1), disabled(2) }
    ACCESS      read-write
    STATUS      mandatory
    DESCRIPTION 
        "Provides control to enable or disable mirroring of ingress 
         traffic over this interface to the mirrored-to port.
         
          ALCATEL NOTE:
          ACCESS	:   NA         		USAGE		:    NA
          PERSIST:   YES          	INSRVMOD	:    YES
          RANGE	:   NA  	        DEFVALUE	:    NA
          UNITS	:   NA           	SPARSE		:    NO
          DESCR	:   NA"
    DEFVAL      { disabled }
    ::= { issMirrorCtrlEntry 2 }

issMirrorCtrlEgressMirroring OBJECT-TYPE
    SYNTAX      INTEGER { enabled(1), disabled(2) }
    ACCESS      read-write
    STATUS      mandatory
    DESCRIPTION 
        "Provides control to enable or disable mirroring of egress 
         traffic over this interface to the mirrored-to port.
         
          ALCATEL NOTE:
          ACCESS	:   NA         		USAGE		:    NA
          PERSIST:   YES          	INSRVMOD	:    YES
          RANGE	:   NA  	        DEFVALUE	:    NA
          UNITS	:   NA           	SPARSE		:    NO
          DESCR	:   NA"
    DEFVAL      { disabled }
    ::= { issMirrorCtrlEntry 3 }

issMirrorCtrlSwIngressMirroring OBJECT-TYPE
    SYNTAX      INTEGER { enabled(1), disabled(2) }
    ACCESS      read-write
    STATUS      mandatory
    DESCRIPTION 
        " Provides control to enable or disable mirroring of ingress 
         traffic received on these ports to the CPU.
          ALCATEL NOTE:
          ACCESS	:   NA         		USAGE		:    NA
          PERSIST:   YES          	INSRVMOD	:    YES
          RANGE	:   NA 	             	DEFVALUE	:    NA
          UNITS	:   NA           	SPARSE		:    NA
         	 DESCR 	:   NA "
    DEFVAL      { disabled }
    ::= { issMirrorCtrlEntry 5 }

issMirrorCtrlSwEgressMirroring OBJECT-TYPE
    SYNTAX      INTEGER { enabled(1), disabled(2) }
    ACCESS      read-write
    STATUS      mandatory
    DESCRIPTION 
        " Provides control to enable or disable mirroring of egress 
         traffic transmitted by the CPU on these ports.
          ALCATEL NOTE:
          ACCESS	:   NA         		USAGE		:    NA
          PERSIST:   YES          	INSRVMOD	:    YES
          RANGE	:   NA 	        	DEFVALUE	:    NA
          UNITS	:   NA        		SPARSE	:    NA
          DESCR 	:   NA "
    DEFVAL      { disabled }
    ::= { issMirrorCtrlEntry 6 }

issRateControl OBJECT IDENTIFIER
    ::= { iss 4 }

issRateCtrlTable OBJECT-TYPE
    SYNTAX      SEQUENCE OF IssRateCtrlEntry
    ACCESS      not-accessible
    STATUS      mandatory
    DESCRIPTION 
        "A table to control the rate limiting parameters 
         either for the entire switch or for each interface in the switch.
          ALCATEL NOTE :
          TABLESIZE    : 25 
          DESCR        : NA"
    ::= { issRateControl 1 }

issRateCtrlEntry OBJECT-TYPE
    SYNTAX      IssRateCtrlEntry
    ACCESS      not-accessible
    STATUS      mandatory
    DESCRIPTION 
        "An entry appears in this table for each interface in the switch.
         
         In addition to that an entry with index '0' is created in this 
         table by default.
         
         If 'issRateCtrlStatus' of the entry '0' is made 'valid', 
         then global control is chosen and the values against entry '0'
         is applicable for all the interfaces of the switch.
         
         If 'issRateCtrlStatus' of the entry '0' is made 'invalid', then 
         interface-wise  control is chosen & the values against each 
         interface index is applicable for that interface.
         
         At a particular point of time, either global control will be 
         applicable or interface-wise control is applicable. Both will 
         not be considered together.
          Row creation : A RATE-CONTROL entry shall be created when the system is initialized.     
          Row deletion : NA.
         	Index usage : The indexe is issRateCtrlIndex.
           	   Note that entries will be presented to the SNMP manager in full
           	   lexicographical order :  sorted on issRateCtrlIndex"
    INDEX       { issRateCtrlIndex }
    ::= { issRateCtrlTable 1 }

IssRateCtrlEntry ::= SEQUENCE {
    issRateCtrlIndex                INTEGER,
    issRateCtrlDLFLimitStatus       INTEGER,
    issRateCtrlBCASTLimitStatus     INTEGER,
    issRateCtrlMCASTLimitStatus     INTEGER,
    issRateCtrlLimitValue           INTEGER,
    issRateCtrlStatus               INTEGER
}

issRateCtrlIndex OBJECT-TYPE
    SYNTAX      INTEGER (0..65535)
    ACCESS      not-accessible
    STATUS      mandatory
    DESCRIPTION 
        "The interface index for which the configuration in this 
         entry applies.
         
         If any configuration is made in this table for the index '0',
         that configuration will be considered as global configuration 
         and is applicable for all the interfaces of the switch.
           ALCATEL NOTE:
           ACCESS	:   NA         		USAGE		:    NA
           PERSIST:   YES          	INSRVMOD	:    NA
           RANGE	:   DEP  	        DEFVALUE	:    NA
           UNITS	:   NA           	SPARSE		:    NO
           DESCR	:   DEP(RANGE)The range is the maximum number of physical ports available in 
         		     the system. The value can be got from the object issSystemNumberOfPorts
         		     in fsiss.mib."
    ::= { issRateCtrlEntry 1 }

issRateCtrlDLFLimitStatus OBJECT-TYPE
    SYNTAX      INTEGER { enabled(1), disabled(2) }
    ACCESS      read-write
    STATUS      mandatory
    DESCRIPTION 
        "Provides control to enable or disable Destination Lookup Failure
         packet transmission control over the interface.
         
         This value for entry '0' controls DLF Limit Status for all the 
         interfaces in the switch.
           ALCATEL NOTE:
           ACCESS	:   NA         		USAGE		:    NA
           PERSIST:   YES          	INSRVMOD	:    YES
           RANGE	:   NA  	        DEFVALUE	:    NA
           UNITS	:   NA           	SPARSE		:    NO
           DESCR	:   NA"
    DEFVAL      { disabled }
    ::= { issRateCtrlEntry 2 }

issRateCtrlBCASTLimitStatus OBJECT-TYPE
    SYNTAX      INTEGER { enabled(1), disabled(2) }
    ACCESS      read-write
    STATUS      mandatory
    DESCRIPTION 
        "Provides control to enable or disable broadcast
         packet transmission control over the interface.
         
         This value for entry '0' controls broadcast Limit Status
         for all the interfaces in the switch.
          ALCATEL NOTE:
          ACCESS	:   NA         		USAGE		:    NA
          PERSIST:   YES          	INSRVMOD	:    YES
          RANGE	:   NA  	        DEFVALUE	:    NA
          UNITS	:   NA           	SPARSE		:    NO
          DESCR	:   NA"
    DEFVAL      { disabled }
    ::= { issRateCtrlEntry 3 }

issRateCtrlMCASTLimitStatus OBJECT-TYPE
    SYNTAX      INTEGER { enabled(1), disabled(2) }
    ACCESS      read-write
    STATUS      mandatory
    DESCRIPTION 
        "Provides control to enable or disable multicast 
         packet transmission control over theinterface.
         
         This value for entry '0' controls multicast traffic Limit Status
         for all the interfaces in the switch.
           ALCATEL NOTE:
           ACCESS	:   NA         		USAGE		:    NA
           PERSIST:   YES          	INSRVMOD	:    YES
           RANGE	:   NA  	        DEFVALUE	:    NA
           UNITS	:   NA           	SPARSE		:    NO
           DESCR	:   NA"
    DEFVAL      { disabled }
    ::= { issRateCtrlEntry 4 }

issRateCtrlLimitValue OBJECT-TYPE
    SYNTAX      INTEGER (0..2147483647)
    ACCESS      read-write
    STATUS      mandatory
    DESCRIPTION 
        "Allows to configure the limiting value for the maximum number
         of packets that can be transmitted over this interface.
         
         The LimitValue for entry '0' is applicable for 
         for all the interfaces in the switch.
           ALCATEL NOTE:
           ACCESS	:   NA         		USAGE		:    NA
           PERSIST:   YES          	INSRVMOD	:    YES
           RANGE  : 0..0x1ffffff        DEFVALUE	:    0
           UNITS	:   NA           	SPARSE		:    NO
           DESCR	:   NA"
    ::= { issRateCtrlEntry 5 }

issRateCtrlStatus OBJECT-TYPE
    SYNTAX      INTEGER { valid(1), invalid(2) }
    ACCESS      read-write
    STATUS      mandatory
    DESCRIPTION 
        "Speficies the validity of the entry.
         
         If the 'Rate Control Status' for entry '0' is made 'valid',
         then global control is chosen in the system.
         It signifies that the values against entry '0' is applicable
         for all the interfaces of the switch.
         
         If the 'Rate Control Status' for entry '0' is made 'invalid',
         then interface-wise control is chosen.
         Then the values against each interface index is applicable for
         that interface.
         
         By default, 'issRateCtrlStatus' will be 'invalid' for entry '0' 
         and 'valid' for all other entries. (ie) by default, 
         interface-wise configuration is enabled in the system.
         
         The status of entries other than the zeroth(0th) entry can not be
         made 'invalid'.
            ALCATEL NOTE:
            ACCESS	:   NA         		USAGE		:    NA
            PERSIST:   YES          	INSRVMOD	:    YES
            RANGE	:   NA 	  		DEFVALUE	:    NA
            UNITS	:   NA           	SPARSE		:    NO
            DESCR	:   NA"
    ::= { issRateCtrlEntry 6 }

issL2Filter OBJECT IDENTIFIER
    ::= { iss 5 }

issL2FilterTable OBJECT-TYPE
    SYNTAX      SEQUENCE OF IssL2FilterEntry
    ACCESS      not-accessible
    STATUS      mandatory
    DESCRIPTION 
        "A table to configure L2 filter rules in the system.
         ALCATEL NOTE :
         TABLESIZE    : 65535
         DESCR        : NA"
    ::= { issL2Filter 1 }

issL2FilterEntry OBJECT-TYPE
    SYNTAX      IssL2FilterEntry
    ACCESS      not-accessible
    STATUS      mandatory
    DESCRIPTION 
        "Each entry in this table is a L2 filter rule.
         
         Index to the table is the L2 filter number.
         Row creation :A L2-FILTER-ENTRY shall be created in one step by a set-request with all 
         		       necessary parameter values and issL2FilterStatus set to createAndGo(4).
         Row deletion : A L2-FILTER-ENTRY shall be deleted by setting the issL2FilterStatus 
         			of the specific entry to destroy(6).
         	Index usage : The indexe is issL2FilterNo.
          	   Note that entries will be presented to the SNMP manager in full
          	   lexicographical order :  sorted on issL2FilterNo"
    INDEX       { issL2FilterNo }
    ::= { issL2FilterTable 1 }

IssL2FilterEntry ::= SEQUENCE {
    issL2FilterNo               INTEGER,
    issL2FilterProtocolType     INTEGER,
    issL2FilterDstMacAddr       MacAddress,
    issL2FilterSrcMacAddr       MacAddress,
    issL2FilterVlanId           VlanIdOrZero,
    issL2FilterInPortList       PortList,
    issL2FilterAction           INTEGER,
    issL2FilterMatchCount       Counter,
    issL2FilterStatus           RowStatus
}

issL2FilterNo OBJECT-TYPE
    SYNTAX      INTEGER (1..65535)
    ACCESS      not-accessible
    STATUS      mandatory
    DESCRIPTION 
        "L2 Filter rule number.
         ALCATEL NOTE:
         ACCESS	:   NA         		USAGE		:    NA
         PERSIST:   YES          	INSRVMOD	:    NA
         RANGE	:   NA  	        DEFVALUE	:    NA
         UNITS	:   NA           	SPARSE		:    NO
         DESCR	:   NA"
    ::= { issL2FilterEntry 1 }

issL2FilterProtocolType OBJECT-TYPE
    SYNTAX      INTEGER (0..65535)
    ACCESS      read-write
    STATUS      mandatory
    DESCRIPTION 
        "Specifies the non IP protocol type to be filtered.
         aarp | amber | dec-spanning | decnet-iv | 
         diagnostic | dsm |etype-6000 | etype-8042 | 
         lat | lavc-sca | mop-console | mop-dump | 
         msdos | mumps | netbios | vines-echo |
         vines-ip | xns-idp: A non-IP protocol.
         
         A value of '0' means, the filter is applicable for all protocols.
           ALCATEL NOTE:
           ACCESS	:   NA         		USAGE		:    OPT
           PERSIST:   YES        		INSRVMOD	:    DEP
           RANGE	:   1536..65535         DEFVALUE	:    NA
           UNITS	:   NA           	SPARSE		:    NO
           DESCR	:   If the L2 filter status is ACTIVE the L2FilterProtocolType can't be set"
    DEFVAL      { 0 }
    ::= { issL2FilterEntry 4 }

issL2FilterDstMacAddr OBJECT-TYPE
    SYNTAX      MacAddress
    ACCESS      read-write
    STATUS      mandatory
    DESCRIPTION 
        "Destination MAC address to be matched with the packet.
         ALCATEL NOTE:
         ACCESS	:   NA         		USAGE		:    NA
         PERSIST:   YES          	INSRVMOD	:    DEP
         RANGE	:   NA  	        DEFVALUE	:    NA
         UNITS	:   NA           	SPARSE		:    NO
         DESCR	:   If the L2 filter status is ACTIVE the issL2FilterDstMacAddr can't be set"
    ::= { issL2FilterEntry 5 }

issL2FilterSrcMacAddr OBJECT-TYPE
    SYNTAX      MacAddress
    ACCESS      read-write
    STATUS      mandatory
    DESCRIPTION 
        "Source MAC address to be matched with the packet.
         ALCATEL NOTE:
         ACCESS	:   NA         		USAGE		:    NA
         PERSIST:   YES          	INSRVMOD	:    DEP
         RANGE	:   NA  	        DEFVALUE	:    NA
         UNITS	:   NA           	SPARSE		:    NO
         DESCR	:   If the L2 filter status is ACTIVE the issL2FilterSrcMacAddr can't be set"
    ::= { issL2FilterEntry 6 }

issL2FilterVlanId OBJECT-TYPE
    SYNTAX      VlanIdOrZero
    ACCESS      read-write
    STATUS      mandatory
    DESCRIPTION 
        "Vlan Id to be filtered.
         ALCATEL NOTE:
         ACCESS	:   NA         		USAGE		:    OPT
         PERSIST:   YES          	INSRVMOD	:    DEP
         RANGE	:   0..4094 	        DEFVALUE	:    0
         UNITS	:   NA           	SPARSE		:    NO
         DESCR	:   If the L2 filter status is ACTIVE the issL2FilterVlanId can't be set"
    ::= { issL2FilterEntry 7 }

issL2FilterInPortList OBJECT-TYPE
    SYNTAX      PortList
    ACCESS      read-write
    STATUS      mandatory
    DESCRIPTION 
        "Specifies the complete set of ports over which if the packet arrives
         the filter rule will be applicable.
         
         If the incoming port list is '0', the filter rule is applicable for all the 
         incoming ports.
         
         By default inport list is maintained as '0'.
            ALCATEL NOTE:
            ACCESS	:   NA         		USAGE		:    OPT
            PERSIST:   YES          	INSRVMOD	:    DEP
            RANGE	:   DEP 	        DEFVALUE	:    NA
            UNITS	:   NA           	SPARSE		:    NO
         	 DESCR 	:DEP(RANGE)This portlist is derived from the maximum number of ports in the system.
         	       	    The maximum number of ports can be got from issSystemNumberOfPorts in fsiss.mib.
            	 If the L2 filter status is ACTIVE the issL2FilterInPortList can't be set"
    ::= { issL2FilterEntry 8 }

issL2FilterAction OBJECT-TYPE
    SYNTAX      INTEGER { allow(1), drop(2) }
    ACCESS      read-write
    STATUS      mandatory
    DESCRIPTION 
        "Specifies the action to be taken on the packet if the filter
         rule matches.
         
         If the action is 'allow', the packet will be forwarded according
         to the forwarding rules.
         
         If the action is 'drop', the packet will be discarded.
            ALCATEL NOTE:
            ACCESS	:   NA         		USAGE		:    MAND
            PERSIST:   YES          	INSRVMOD	:    DEP
            RANGE	:   NA 	                DEFVALUE	:    NA
            UNITS	:   NA           	SPARSE		:    NO
            DESCR	:   If the L2 filter status is ACTIVE the issL2FilterAction can't be set"
    DEFVAL      { allow }
    ::= { issL2FilterEntry 9 }

issL2FilterMatchCount OBJECT-TYPE
    SYNTAX      Counter
    ACCESS      read-only
    STATUS      mandatory
    DESCRIPTION 
        "Number of times this filter is matched.
         ALCATEL NOTE:
         ACCESS	:   NA         		USAGE		:    NA
         PERSIST:   NO          	INSRVMOD	:    NA
         RANGE	:   NA 	                DEFVALUE	:    0
         UNITS	:   NA           	SPARSE		:    NO
         DESCR	:   For unsupported boards,it will always return the value as 0xffffffff"
    ::= { issL2FilterEntry 10 }

issL2FilterStatus OBJECT-TYPE
    SYNTAX      RowStatus
    ACCESS      read-write
    STATUS      mandatory
    DESCRIPTION 
        "This object indicates the status of this entry.
         
         The entry status will be made 'active' only if 
         
            --> Either of ProtocolType/src mac address /dst mac address is 
                configured in case of l2Filter.
            ALCATEL NOTE:
            ACCESS	:   NA         		USAGE		:    MAND
            PERSIST:   YES          	INSRVMOD	:    YES
            RANGE	:   NA 	                DEFVALUE	:    NA
            UNITS	:   NA           	SPARSE		:    NO
            DESCR	:   NA"
    ::= { issL2FilterEntry 11 }

issL3Filter OBJECT IDENTIFIER
    ::= { iss 6 }

issL3FilterTable OBJECT-TYPE
    SYNTAX      SEQUENCE OF IssL3FilterEntry
    ACCESS      not-accessible
    STATUS      mandatory
    DESCRIPTION 
        " A table to configure L3 filter rules in the system.
         ALCATEL NOTE :
         TABLESIZE    : 65535   
         DESCR        : NA  "
    ::= { issL3Filter 1 }

issL3FilterEntry OBJECT-TYPE
    SYNTAX      IssL3FilterEntry
    ACCESS      not-accessible
    STATUS      mandatory
    DESCRIPTION 
        " Each entry in this table is a L3 filter rule.
         Index to the table is L3 filter number. 
          Row creation :A L3-FILTER shall be created in one step by a set-request with all 
         	       necessary parameter values and issL3FilterStatus set to createAndGo(4).
         Row deletion : A L3-FILTER shall be deleted by setting	the issL3FilterStatus 
         		of the specific entry to destroy(6).
           Index usage : The index is issL3FilterNo.
            Note that entries will be presented to the SNMP manager in full
            lexicographical order :  sorted on issL3FilterNo"
    INDEX       { issL3FilterNo }
    ::= { issL3FilterTable 1 }

IssL3FilterEntry ::= SEQUENCE {
    issL3FilterNo               INTEGER,
    issL3FilterPriority         INTEGER,
    issL3FilterProtocol         INTEGER,
    issL3FilterMessageType      INTEGER,
    issL3FilterMessageCode      INTEGER,
    issL3FilterDstIpAddr        IpAddress,
    issL3FilterSrcIpAddr        IpAddress,
    issL3FilterDstIpAddrMask    IpAddress,
    issL3FilterSrcIpAddrMask    IpAddress,
    issL3FilterMinDstProtPort   INTEGER,
    issL3FilterMaxDstProtPort   INTEGER,
    issL3FilterMinSrcProtPort   INTEGER,
    issL3FilterMaxSrcProtPort   INTEGER,
    issL3FilterInPortList       PortList,
    issL3FilterOutPortList      PortList,
    issL3FilterAckBit           INTEGER,
    issL3FilterRstBit           INTEGER,
    issL3FilterTos              INTEGER,
    issL3FilterDirection        INTEGER,
    issL3FilterAction           INTEGER,
    issL3FilterMatchCount       Counter,
    issL3FilterStatus           RowStatus,
    issL3FilterVlanId           VlanIdOrZero
}

issL3FilterNo OBJECT-TYPE
    SYNTAX      INTEGER (1..65535)
    ACCESS      not-accessible
    STATUS      mandatory
    DESCRIPTION 
        "L3 Filter rule number.
         ALCATEL NOTE:
         ACCESS	:   NA         		USAGE		:    NA
         PERSIST:   YES          	INSRVMOD	:    NA 
         RANGE	:   NA  	        DEFVALUE	:    NA
         UNITS	:   NA           	SPARSE		:    NO
         DESCR	:   NA"
    ::= { issL3FilterEntry 1 }

issL3FilterPriority OBJECT-TYPE
    SYNTAX      INTEGER (1..65535)
    ACCESS      read-write
    STATUS      mandatory
    DESCRIPTION 
        "The priority of the filter can be used to decide which filter rule
         is applicable when 
            --> the packet matches with more than one filter rules
            --> All the filter rules result in 'allow'ing the packet
         
         Higher value of 'L3 filter priority' implies a higher priority.
         
         Usage of 'L3FilterPriority' is implementation dependant.
           ALCATEL NOTE:
           ACCESS	:   NA         		USAGE		:    NA 
           PERSIST:   NA			INSRVMOD	:    NA
           RANGE	:   NA         		DEFVALUE	:    NA
           UNITS	:   NA           	SPARSE		:    NA
           DESCR	:   This is not used by ALCATEL"
    DEFVAL      { 1 }
    ::= { issL3FilterEntry 2 }

issL3FilterProtocol OBJECT-TYPE
    SYNTAX      INTEGER (0..255)
    ACCESS      read-write
    STATUS      mandatory
    DESCRIPTION 
        " The type of protocol to be checked against the packet. The
         default value is 255. If the value is 255, it means that the
         protocol type can be anything and it will not be checked to 
         decide the action. 
            ALCATEL NOTE:
            ACCESS	:   NA         		USAGE		:    MAND
            PERSIST:   YES 		INSRVMOD	:    DEP
            RANGE	:   NA         		DEFVALUE	:    NA
            UNITS	:   NA           	SPARSE		:    NO
            DESCR	:   NA"
    DEFVAL      { 255 }
    ::= { issL3FilterEntry 3 }

issL3FilterMessageType OBJECT-TYPE
    SYNTAX      INTEGER (0..65535)
    ACCESS      read-write
    STATUS      mandatory
    DESCRIPTION 
        " The message type to be checked against the packet. If the
         message type matches with the packet, then the packet will be
         dropped / allowed based on the action set in issL3FilterAction.
         The default value is 255. It means that message type is not
         configured and need not be checked.
         Generally the value zero is given as default. But here
         zero can be an ICMP Type value. Hence 255 is given as the
         default value. 
         Some ICMP message types are: 
              echoReply(0),
              destinationUnreachable(3),
              sourceQuench(4),
              redirect(5),
              echoRequest(8),
              timeExceeded(11),
              parameterProblem(12),
              timestampRequest(13),
              timestampReply(14),
              informationRequest(15),
              informationReply(16),
              addressMaskRequest(17),
              addressMaskReply (18),
              noICMPType(255)
            ALCATEL NOTE:
            ACCESS	:   NA         		USAGE		:    OPT 
            PERSIST:   YES 		INSRVMOD	:    DEP
            RANGE	:   0..255		DEFVALUE	:    NA
            UNITS	:   NA           	SPARSE		:    NO
            DESCR	:   NA"
    DEFVAL      { 255 }
    ::= { issL3FilterEntry 4 }

issL3FilterMessageCode OBJECT-TYPE
    SYNTAX      INTEGER (0..65535)
    ACCESS      read-write
    STATUS      mandatory
    DESCRIPTION 
        " The message code to be checked against the packet. If the
         packet matches with the message code, then the packet will
         be dropped / allowed based on the action set in issL3FilterAction.
         The default value is 255. It means that message code is not 
         configured and need not be checked. Generally the value zero 
         will be given as default. But here, zero can be an ICMP Code 
         value. Hence 255 is given as the default value.
         Some ICMP message codes are :
              networkUnreachable(0),
              hostUnreachable(1),
              protocolUnreachable(2),
              portUnreachable(3),
              fragmentNeed(4),
              sourceRouteFail(5),
              destNetworkUnknown(6),
              destHostUnknown(7),
              srcHostIsolated(8),
              destNetworkAdminProhibited(9),
              destHostAdminProhibited(10),
              networkUnreachableTOS(11),
              hostUnreachableTOS(12),
              noICMPCode(255) 
            ALCATEL NOTE:
            ACCESS	:   NA         		USAGE		:    OPT 
            PERSIST:   YES 		INSRVMOD	:    DEP
            RANGE	:   0..255		DEFVALUE	:    NA
            UNITS	:   NA           	SPARSE		:    NO
            DESCR	:   NA"
    DEFVAL      { 255 }
    ::= { issL3FilterEntry 5 }

issL3FilterDstIpAddr OBJECT-TYPE
    SYNTAX      IpAddress
    ACCESS      read-write
    STATUS      mandatory
    DESCRIPTION 
        "Destination IP address to be matched with the packet.
         
         This object is valid only if the 'issFilterType' is 'l3filter'.
            ALCATEL NOTE:
            ACCESS	:   NA         		USAGE		:    NA
            PERSIST:   YES 		INSRVMOD	:    DEP
            RANGE	:   NA			DEFVALUE	:    0
            UNITS	:   NA           	SPARSE		:    NO
            DESCR	:   NA"
    ::= { issL3FilterEntry 6 }

issL3FilterSrcIpAddr OBJECT-TYPE
    SYNTAX      IpAddress
    ACCESS      read-write
    STATUS      mandatory
    DESCRIPTION 
        "Source IP address to be matched with the packet.
         
         This object is valid only if the 'issFilterType' is 'l3filter'.
          ALCATEL NOTE:
            ACCESS	:   NA         		USAGE		:    NA 
            PERSIST:   YES 		INSRVMOD	:    DEP
            RANGE	:   NA			DEFVALUE	:    0
            UNITS	:   NA           	SPARSE		:    NO
            DESCR	:   NA"
    ::= { issL3FilterEntry 7 }

issL3FilterDstIpAddrMask OBJECT-TYPE
    SYNTAX      IpAddress
    ACCESS      read-write
    STATUS      mandatory
    DESCRIPTION 
        "The IP subnet mask for Destination IP address.
         
         This object is valid only if the 'issFilterType' is 'l3filter'.
         ALCATEL NOTE:
            ACCESS	:   NA         		USAGE		:    NA 
            PERSIST:   YES 		INSRVMOD	:    DEP
            RANGE	:   NA			DEFVALUE	:    0
            UNITS	:   NA           	SPARSE		:    NO
            DESCR	:   NA"
    DEFVAL      { 'ffffffff'H }
    ::= { issL3FilterEntry 8 }

issL3FilterSrcIpAddrMask OBJECT-TYPE
    SYNTAX      IpAddress
    ACCESS      read-write
    STATUS      mandatory
    DESCRIPTION 
        "The IP subnet mask for Source IP address.
         
         This object is valid only if the 'issFilterType' is 'l3filter'.
          ALCATEL NOTE:
            ACCESS	:   NA         		USAGE		:    NA 
            PERSIST:   YES 		INSRVMOD	:    DEP
            RANGE	:   NA			DEFVALUE	:    0
            UNITS	:   NA           	SPARSE		:    NO
            DESCR	:   NA"
    DEFVAL      { 'ffffffff'H }
    ::= { issL3FilterEntry 9 }

issL3FilterMinDstProtPort OBJECT-TYPE
    SYNTAX      INTEGER (0..65535)
    ACCESS      read-write
    STATUS      mandatory
    DESCRIPTION 
        "The minimum port in the destination port range. Please note 
         these ports are the TCP / UDP ports.
         ALCATEL NOTE:
           ACCESS	:   NA         		USAGE		:    OPT
           PERSIST:   YES 		INSRVMOD	:    DEP
           RANGE	:   NA			DEFVALUE	:    NA
           UNITS	:   NA           	SPARSE		:    NO
           DESCR	:   NA"
    DEFVAL      { 0 }
    ::= { issL3FilterEntry 10 }

issL3FilterMaxDstProtPort OBJECT-TYPE
    SYNTAX      INTEGER (0..65535)
    ACCESS      read-write
    STATUS      mandatory
    DESCRIPTION 
        "The maximum port in the destination port range. Please note 
         these ports are the TCP / UDP ports.
         ALCATEL NOTE:
           ACCESS	:   NA         		USAGE		:    OPT 
           PERSIST:   YES 		INSRVMOD	:    DEP
           RANGE	:   NA			DEFVALUE	:    NA
           UNITS	:   NA           	SPARSE		:    NO
           DESCR	:   NA"
    DEFVAL      { 65535 }
    ::= { issL3FilterEntry 11 }

issL3FilterMinSrcProtPort OBJECT-TYPE
    SYNTAX      INTEGER (0..65535)
    ACCESS      read-write
    STATUS      mandatory
    DESCRIPTION 
        "The minimum port in the source port range. Please note 
         these ports are the TCP / UDP ports.
          ALCATEL NOTE:
           ACCESS	:   NA         		USAGE		:    OPT 
           PERSIST:   YES 		INSRVMOD	:    DEP
           RANGE	:   NA			DEFVALUE	:    NA
           UNITS	:   NA           	SPARSE		:    NO
           DESCR	:   NA"
    DEFVAL      { 0 }
    ::= { issL3FilterEntry 12 }

issL3FilterMaxSrcProtPort OBJECT-TYPE
    SYNTAX      INTEGER (0..65535)
    ACCESS      read-write
    STATUS      mandatory
    DESCRIPTION 
        "The maximum port in the source port range. Please note 
         these ports are the TCP / UDP ports.
         ALCATEL NOTE:
           ACCESS	:   NA         		USAGE		:    OPT 
           PERSIST:   YES 		INSRVMOD	:    DEP
           RANGE	:   NA			DEFVALUE	:    NA
           UNITS	:   NA           	SPARSE		:    NO
           DESCR	:   NA"
    DEFVAL      { 65535 }
    ::= { issL3FilterEntry 13 }

issL3FilterInPortList OBJECT-TYPE
    SYNTAX      PortList
    ACCESS      read-write
    STATUS      mandatory
    DESCRIPTION 
        "Specifies the complete set of ports over which if the packet arrives
         the filter rule will be applicable.
         
         If the incoming port list is '0', the filter rule is applicable for all the 
         incoming ports.
         
         By default inport list is maintained as '0'.
         ALCATEL NOTE:
            ACCESS	:   NA         		USAGE		:    OPT 
            PERSIST:   YES 		INSRVMOD	:    DEP
          	 RANGE	:   DEP			DEFVALUE	:    NA	
            UNITS	:   NA           	SPARSE		:    NO
         	 DESCR  : DEP(RANGE):This portlist is derived from the maximum number of ports in the system.
         	       	    The maximum number of ports can be got from issSystemNumberOfPorts in fsiss.mib."
    ::= { issL3FilterEntry 14 }

issL3FilterOutPortList OBJECT-TYPE
    SYNTAX      PortList
    ACCESS      read-write
    STATUS      mandatory
    DESCRIPTION 
        "This object is applicable only if the 'FilterAction' is 'allow'.
         
         If the out going port list is non-zero, the packet will be sent over
         the specifed ports only.
         
         If the out going port list is '0', the port over which the packet is
         to be switched will be based on further processing on the packet.
         By default inport list is maintained as '0'.
         ALCATEL NOTE:
            ACCESS	:   NA         		USAGE		:    OPT 
            PERSIST:   YES 		INSRVMOD	:    DEP
            RANGE	:   DEP			DEFVALUE	:    NA
            UNITS	:   NA           	SPARSE		:    NO
         	 DESCR	:DEP(RANGE)This portlist is derived from the maximum number of ports in the system.
         	       	       The maximum number of ports can be got from issSystemNumberOfPorts in fsiss.mib."
    ::= { issL3FilterEntry 15 }

issL3FilterAckBit OBJECT-TYPE
    SYNTAX      INTEGER { establish(1), notEstablish(2), any(3) }
    ACCESS      read-write
    STATUS      mandatory
    DESCRIPTION 
        " The TCP ACK bit to be checked against the packet. The default 
         value is 'any'(3). It means that ACK bit will not be checked 
         to decide the action. 
         ALCATEL NOTE:
         ACCESS	:   NA         		USAGE		:    OPT 
         PERSIST:   YES 		INSRVMOD	:    DEP
         RANGE	:   NA			DEFVALUE	:    NA
         UNITS	:   NA           	SPARSE		:    NO
         DESCR	:   NA"
    DEFVAL      { any }
    ::= { issL3FilterEntry 16 }

issL3FilterRstBit OBJECT-TYPE
    SYNTAX      INTEGER { set(1), notSet(2), any(3) }
    ACCESS      read-write
    STATUS      mandatory
    DESCRIPTION 
        " The TCP RST bit to be checked against the packet. The default 
         value is 'any'(3). It means that RST bit will not be checked to 
         decide the action. 
         ALCATEL NOTE:
         ACCESS	:   NA         		USAGE		:    OPT 
         PERSIST:   YES 		INSRVMOD	:    DEP
         RANGE	:   NA			DEFVALUE	:    NA
         UNITS	:   NA           	SPARSE		:    NO
         DESCR	:   NA"
    DEFVAL      { any }
    ::= { issL3FilterEntry 17 }

issL3FilterTos OBJECT-TYPE
    SYNTAX      INTEGER (0..8)
    ACCESS      read-write
    STATUS      mandatory
    DESCRIPTION 
        " The IP TOS bit to be checked against the packet. This is a 
         single byte integer of which the last three bits (least 
         significant bits) indicate Delay, Throughput and Reliability 
         i.e 'uuuuudtr', u-unused, d-delay, t-throughput, r-reliability.
         For example '6' indicates low delay and high throughput. 
         ALCATEL NOTE:
         ACCESS	:   NA         		USAGE		:    OPT 
         PERSIST:   YES 		INSRVMOD	:    DEP
         RANGE	:   NA			DEFVALUE	:    8
         UNITS	:   NA           	SPARSE		:    NO
         DESCR	:   NA"
    DEFVAL      { 0 }
    ::= { issL3FilterEntry 18 }

issL3FilterDirection OBJECT-TYPE
    SYNTAX      INTEGER { in(1), out(2) }
    ACCESS      read-write
    STATUS      mandatory
    DESCRIPTION 
        " This specifies in which direction the Filters are to be
         applied on the packets, either to incoming or outgoing
         packets. 
           ALCATEL NOTE:
            ACCESS	:   NA         		USAGE		:    MAND
            PERSIST:   YES 		INSRVMOD	:    DEP
            RANGE	:   NA			DEFVALUE	:    NA
            UNITS	:   NA           	SPARSE		:    NO
            DESCR	:   NA"
    DEFVAL      { in }
    ::= { issL3FilterEntry 19 }

issL3FilterAction OBJECT-TYPE
    SYNTAX      INTEGER { allow(1), drop(2) }
    ACCESS      read-write
    STATUS      mandatory
    DESCRIPTION 
        "Specifies the action to be taken on the packet if the filter
         rule matches.
         
         If the action is 'allow', the packet will be sent to the
         ports in 'out port list'. If the out port list is '0', 
         the port over which the packet is to be switched will be decided
         based on further processing on the packet.
         
         If the action is 'drop', the packet will be discarded.
          ALCATEL NOTE:
            ACCESS	:   NA         		USAGE		:    MAND
            PERSIST:   YES 		INSRVMOD	:    DEP
            RANGE	:   NA			DEFVALUE	:    NA
            UNITS	:   NA           	SPARSE		:    NO
            DESCR	:   NA"
    DEFVAL      { allow }
    ::= { issL3FilterEntry 20 }

issL3FilterMatchCount OBJECT-TYPE
    SYNTAX      Counter
    ACCESS      read-only
    STATUS      mandatory
    DESCRIPTION 
        "Number of times this filter is matched.
         ALCATEL NOTE:
         ACCESS	:   NA         		USAGE		:    NA 
         PERSIST:   NO			INSRVMOD	:    NA
         RANGE	:   NA			DEFVALUE	:    0
         UNITS	:   NA           	SPARSE		:    NO
         DESCR	:   NA"
    ::= { issL3FilterEntry 21 }

issL3FilterStatus OBJECT-TYPE
    SYNTAX      RowStatus
    ACCESS      read-write
    STATUS      mandatory
    DESCRIPTION 
        "This object indicates the status of this entry.
         
         The entry status will be made 'active' only if 
         
            --> Either of ProtocolType/src ip address/dst ip address is
                configured in case of l3Filter.
         ALCATEL NOTE:
            ACCESS	:   NA         		USAGE		:    MAND
            PERSIST:   YES 		INSRVMOD	:    YES
            RANGE	:   NA			DEFVALUE	:    NA
            UNITS	:   NA           	SPARSE		:    NO
            DESCR	:   NA"
    ::= { issL3FilterEntry 22 }

issL3FilterVlanId OBJECT-TYPE
    SYNTAX      VlanIdOrZero
    ACCESS      read-write
    STATUS      mandatory
    DESCRIPTION 
        "Vlan Id to be filtered.The value zero means wildcard for vlan.
         ALCATEL NOTE:
            ACCESS	:   NA         		USAGE		:    NA 
            PERSIST:   YES 		INSRVMOD	:    DEP
            RANGE	:   0..4094		DEFVALUE	:    0
            UNITS	:   NA           	SPARSE		:    NO
            DESCR	:   NA"
    ::= { issL3FilterEntry 23 }

issL3MgmtVlanFilter OBJECT IDENTIFIER
    ::= { iss 7 }

issIpMgmtVlanSrcIpTable OBJECT-TYPE
    SYNTAX      SEQUENCE OF IssIpMgmtVlanSrcIpEntry
    ACCESS      not-accessible
    STATUS      mandatory
    DESCRIPTION 
        "A table to control traffic for Mgmt vlan or External Vlan to allow only configured SrcIp addresses
         
         This table is not supported anymore due to dual IP removal
         Shub does not have managment IP address anymore.
         
         ALCATEL NOTE :
         TABLESIZE    : 100
         DESCR        : This is not used by Alcatel"
    ::= { issL3MgmtVlanFilter 1 }

issIpMgmtVlanSrcIpEntry OBJECT-TYPE
    SYNTAX      IssIpMgmtVlanSrcIpEntry
    ACCESS      not-accessible
    STATUS      mandatory
    DESCRIPTION 
        "An entry appears in this table SrcIp address allowed for a Mgmt vlan.
         Index to the table is one to three assigned to SrcIp address. 
         	Row creation :A IP-MGMT-VLAN-SRCIP-ENTRY shall be created in one step by a set-request with all 
         		       necessary parameter values and issIpMgmtVlanSrcIpAddrStatus set to createAndGo(4).
         Row deletion : A IP-MGMT-VLAN-SRCIP-ENTRY shall be deleted by setting the issIpMgmtVlanSrcIpAddrStatus 
         			of the specific entry to destroy(6).
         	Index usage : The indexe is issIpMgmtVlanSrcIpIndex.
         	   Note that entries will be presented to the SNMP manager in full
         	   lexicographical order :  sorted on issIpMgmtVlanSrcIpIndex"
    INDEX       { issIpMgmtVlanSrcIpIndex }
    ::= { issIpMgmtVlanSrcIpTable 1 }

IssIpMgmtVlanSrcIpEntry ::= SEQUENCE {
    issIpMgmtVlanSrcIpIndex         INTEGER,
    issIpMgmtVlanSrcIpAddr          IpAddress,
    issIpMgmtVlanSrcIpAddrStatus    RowStatus
}

issIpMgmtVlanSrcIpIndex OBJECT-TYPE
    SYNTAX      INTEGER (1..100)
    ACCESS      not-accessible
    STATUS      mandatory
    DESCRIPTION 
        "Index number of the SrcIp for which the configuration
         in this entry applies.
         	ALCATEL NOTE:
            ACCESS	:   NA         		USAGE		:    NA
            PERSIST:   YES 		INSRVMOD	:    NO
            RANGE	:   NA			DEFVALUE	:    NA
            UNITS	:   NA           	SPARSE		:    NO
            DESCR	:   NA"
    ::= { issIpMgmtVlanSrcIpEntry 1 }

issIpMgmtVlanSrcIpAddr OBJECT-TYPE
    SYNTAX      IpAddress
    ACCESS      read-write
    STATUS      mandatory
    DESCRIPTION 
        "MgmtVlan filter IP address to be matched with the packet.
         ALCATEL NOTE:
         ACCESS	:   NA         		USAGE		:    NA 
         PERSIST:   YES 		INSRVMOD	:    YES
         RANGE	:   NA			DEFVALUE	:    NA
         UNITS	:   NA           	SPARSE		:    NO
         DESCR	:   NA"
    ::= { issIpMgmtVlanSrcIpEntry 2 }

issIpMgmtVlanSrcIpAddrStatus OBJECT-TYPE
    SYNTAX      RowStatus
    ACCESS      read-write
    STATUS      mandatory
    DESCRIPTION 
        "This object indicates the status of this entry.
         
         The entry status will be have 'active' and Delete option only
         	ALCATEL NOTE:
            ACCESS	:   NA         		USAGE		:    MAND 
            PERSIST:   YES 		INSRVMOD	:    YES
            RANGE	:   1..6		DEFVALUE	:    NA
            UNITS	:   NA           	SPARSE		:    NO
            DESCR	:   NA"
    ::= { issIpMgmtVlanSrcIpEntry 3 }

issPortController OBJECT IDENTIFIER
    ::= { iss 8 }

issPortCopyTable OBJECT-TYPE
    SYNTAX      SEQUENCE OF IssPortCopyEntry
    ACCESS      not-accessible
    STATUS      mandatory
    DESCRIPTION 
        "A table Used to copy the Source port configuration informaion to the destination port.
         ALCATEL NOTE :
         TABLESIZE    : DEP  
         DESCR        : DEP(TABLESIZE) The range is the maximum number of physical ports available in 
         	     the system. The value can be got from the object issSystemNumberOfPorts
         	     in fsiss.mib."
    ::= { issPortController 1 }

issPortCopyEntry OBJECT-TYPE
    SYNTAX      IssPortCopyEntry
    ACCESS      not-accessible
    STATUS      mandatory
    DESCRIPTION 
        "Row creation : A  PORT-COPY entry shall be created when the system is initialized.     
         Row deletion : NA.
         	Index usage : The indexe is issSrcPortIndex.
         	   Note that entries will be presented to the SNMP manager in full
         	   lexicographical order :  sorted on issSrcPortIndex"
    INDEX       { issSrcPortIndex }
    ::= { issPortCopyTable 1 }

IssPortCopyEntry ::= SEQUENCE {
    issSrcPortIndex     INTEGER,
    issDestPortIndex    INTEGER
}

issSrcPortIndex OBJECT-TYPE
    SYNTAX      INTEGER (1..2147483647)
    ACCESS      not-accessible
    STATUS      mandatory
    DESCRIPTION 
        "Index number of the Source port from which we will get the configuration information of the source port
         and thatconfiguration information will be set for the destination Port.
         ALCATEL NOTE:
         ACCESS	:   NA         		USAGE		:    OPT 
         PERSIST:   NO	 		INSRVMOD	:    NO
         RANGE	:   DEP			DEFVALUE	:    NA
         UNITS	:   NA           	SPARSE		:    NO
         DESCR	:   DEP(RANGE) The range is the maximum number of physical ports available in 
         	     the system. The value can be got from the object issSystemNumberOfPorts
         	     in fsiss.mib."
    ::= { issPortCopyEntry 1 }

issDestPortIndex OBJECT-TYPE
    SYNTAX      INTEGER
    ACCESS      read-write
    STATUS      mandatory
    DESCRIPTION 
        "Destination port index, whose configuration values is set, 
         with the values of the source port. For SET the valid range
         is 1 to maximum number of physical ports available in 
          the system. But while GET, it always returns 0
         ALCATEL NOTE:
         ACCESS	:   NA         		USAGE		:    OPT 
         PERSIST:   NO	 		INSRVMOD	:    NO
         RANGE	:   DEP		DEFVALUE	:    NA
         UNITS	:   NA           	SPARSE		:    NO
         DESCR	:   DEP(RANGE) The range is the maximum number of physical ports available in 
         	     the system. The value can be got from the object issSystemNumberOfPorts
         	     in fsiss.mib."
    ::= { issPortCopyEntry 2 }

issFileOp OBJECT IDENTIFIER
    ::= { iss 9 }

issTraps OBJECT IDENTIFIER
    ::= { iss 10 }

issPCCPGroup OBJECT IDENTIFIER
    ::= { iss 11 }

issPCCPModuleStatus OBJECT-TYPE
    SYNTAX      INTEGER { enable(1), disable(2) }
    ACCESS      read-write
    STATUS      mandatory
    DESCRIPTION 
        "This object is used to enable/disable the Path Connectivity Check & Protection feature in the system.
         ALCATEL NOTE:
         ACCESS : NA		USAGE   : NA
         PERSIST: YES		INSRVMOD: YES
         RANGE  : NA		DEFVALUE: NA
         UNITS  : NA		SPARSE  : NA
         DESCR  : NA"
    DEFVAL      { disable }
    ::= { issPCCPGroup 1 }

issPCCPGroupTable OBJECT-TYPE
    SYNTAX      SEQUENCE OF IssPCCPGroupEntry
    ACCESS      not-accessible
    STATUS      mandatory
    DESCRIPTION 
        "Table representing the Path Connectivity Check & Protection Group.
         ALCATEL NOTE:
         TABLESIZE    : 4
         DESCR        : NA"
    ::= { issPCCPGroup 2 }

issPCCPGroupEntry OBJECT-TYPE
    SYNTAX      IssPCCPGroupEntry
    ACCESS      not-accessible
    STATUS      mandatory
    DESCRIPTION 
        "Path Connectivity Check & Protection Group Entry.
         Row creation 	: A PCCP Group Entry shall be created by setting the issPCCPRowStatus
         	      	  to createAndGo(4) or createAndWait(5).
         Row deletion 	: A PCCP Group Entry shall be deleted by setting the issPCCPRowStatus
         	      	  of the specific entry to destroy(6).
         Index usage  	: The index is issPCCPGroupID.
         Note that entries will be presented to the SNMP manager in full
         lexicographical order : sorted on issPCCPGroupID"
    INDEX       { issPCCPGroupID }
    ::= { issPCCPGroupTable 1 }

IssPCCPGroupEntry ::= SEQUENCE {
    issPCCPGroupID                  INTEGER,
    issPCCPGroupAdminState          INTEGER,
    issPCCPGroupOperState           INTEGER,
    issPCCPGroupPortslist           PortList,
    issPCCPPingCheckInterval        INTEGER,
    issPCCPPingCheckDestIPAdress    IpAddress,
    issPCCPManualSwitchOver         INTEGER,
    issPCCPTimeSinceLastSwitchover  TimeTicks,
    issPCCPRowStatus                RowStatus
}

issPCCPGroupID OBJECT-TYPE
    SYNTAX      INTEGER (1..4)
    ACCESS      read-only
    STATUS      mandatory
    DESCRIPTION 
        "The Path Connectivity Check & Protection Group identifier.
         ALCATEL NOTE:
         ACCESS : NA		USAGE   : NA
         PERSIST: YES		INSRVMOD: NA
         RANGE  : NA		DEFVALUE: NA
         UNITS  : NA		SPARSE  : NO
         DESCR  : NA"
    ::= { issPCCPGroupEntry 1 }

issPCCPGroupAdminState OBJECT-TYPE
    SYNTAX      INTEGER { enable(1), disable(2) }
    ACCESS      read-write
    STATUS      mandatory
    DESCRIPTION 
        "To enable/disable the Path Connectivity Check & Protection at Group level.
         ALCATEL NOTE:
         ACCESS : NA		USAGE   : OPT
         PERSIST: YES		INSRVMOD: YES
         RANGE  : NA		DEFVALUE: NA
         UNITS  : NA		SPARSE  : NO
         DESCR  : NA"
    DEFVAL      { disable }
    ::= { issPCCPGroupEntry 2 }

issPCCPGroupOperState OBJECT-TYPE
    SYNTAX      INTEGER { up(1), down(2) }
    ACCESS      read-only
    STATUS      mandatory
    DESCRIPTION 
        "The operational state of the Path Connectivity Check & Protection Group.
         ALCATEL NOTE:
         ACCESS : NA		USAGE   : NA
         PERSIST: NA		INSRVMOD: NA
         RANGE  : NA		DEFVALUE: NA
         UNITS  : NA		SPARSE  : NO
         DESCR  : NA"
    DEFVAL      { down }
    ::= { issPCCPGroupEntry 3 }

issPCCPGroupPortslist OBJECT-TYPE
    SYNTAX      PortList
    ACCESS      read-write
    STATUS      mandatory
    DESCRIPTION 
        "The list of Ports that are associated with this Path Connectivity Check & Protection Group. 
         Only Network/Outband ports can be associated with an PCCP Group.
         	ALCATEL NOTE:
         	ACCESS : NA		USAGE   : OPT
         	PERSIST: YES		INSRVMOD: YES
         	RANGE  : NA		DEFVALUE: NA
         	UNITS  : NA		SPARSE  : NO
         	DESCR  : NA"
    DEFVAL      { '00'H }
    ::= { issPCCPGroupEntry 4 }

issPCCPPingCheckInterval OBJECT-TYPE
    SYNTAX      INTEGER (0..60)
--     UNITS       "Seconds"
    ACCESS      read-write
    STATUS      mandatory
    DESCRIPTION 
        "Time interval between 2 PINGs and the ping will be initiated by IACM periodically 
         after Path Connectivity Check & Protection group is up.
         ALCATEL NOTE:
         ACCESS : NA		USAGE   : OPT
         PERSIST: YES		INSRVMOD: YES
         RANGE  : NA		DEFVALUE: NA
         UNITS  : NA		SPARSE  : NO
         DESCR  : NA"
    DEFVAL      { 5 }
    ::= { issPCCPGroupEntry 5 }

issPCCPPingCheckDestIPAdress OBJECT-TYPE
    SYNTAX      IpAddress
    ACCESS      read-write
    STATUS      mandatory
    DESCRIPTION 
        "The destination IP address of the Ping check.
         ALCATEL NOTE:
         ACCESS : NA		USAGE   : OPT
         PERSIST: YES		INSRVMOD: YES
         RANGE  : NA		DEFVALUE: NA
         UNITS  : NA		SPARSE  : NO
         DESCR  : NA"
    DEFVAL      { '00000000'H }
    ::= { issPCCPGroupEntry 6 }

issPCCPManualSwitchOver OBJECT-TYPE
    SYNTAX      INTEGER { on(1), off(2) }
    ACCESS      read-write
    STATUS      mandatory
    DESCRIPTION 
        "Allows to trigger manually a switch-over of the Path Connectivity Check & Protection.
         Congfiguring ON(1) to this object shall force to select a new MasterLink within 
         a PCCP Group. Any other operation on this object has no effect and
         it always returns OFF(2) when read
         ALCATEL NOTE:
         ACCESS : NA		USAGE   : OPT
         PERSIST: NO		INSRVMOD: YES
         RANGE  : NA		DEFVALUE: NA
         UNITS  : NA		SPARSE  : NO
         DESCR  : NA"
    DEFVAL      { off }
    ::= { issPCCPGroupEntry 7 }

issPCCPTimeSinceLastSwitchover OBJECT-TYPE
    SYNTAX      TimeTicks
--     UNITS       "Seconds"
    ACCESS      read-only
    STATUS      mandatory
    DESCRIPTION 
        "The time since last PCCP Switchover occurred.
         ALCATEL NOTE:
         ACCESS : NA		USAGE   : NA
         PERSIST: NA		INSRVMOD: NA
         RANGE  : NA		DEFVALUE: NA
         UNITS  : NA		SPARSE  : NO
         DESCR  : NA"
    DEFVAL      { 0 }
    ::= { issPCCPGroupEntry 8 }

issPCCPRowStatus OBJECT-TYPE
    SYNTAX      RowStatus
    ACCESS      read-write
    STATUS      mandatory
    DESCRIPTION 
        "Specifies the Row Status of the PCCP Group Entry. 
         To create a new entry into this table, this has to be configured with 
         the CreateAndWait or with CreateAndGo. To delete the entry from this
         table, the row status should be set to Destroy.
         	ALCATEL NOTE:
         	ACCESS : NA		USAGE   : MAND
         	PERSIST: YES		INSRVMOD: YES
         	RANGE  : 1,3,4,5,6	DEFVALUE: NA
         	UNITS  : NA		SPARSE  : NO
         	DESCR  : NA"
    ::= { issPCCPGroupEntry 9 }

issPCCPGroupPortTable OBJECT-TYPE
    SYNTAX      SEQUENCE OF IssPCCPGroupPortEntry
    ACCESS      not-accessible
    STATUS      mandatory
    DESCRIPTION 
        "Table representing the Ports that are part of Path Connectivity Check & Protection group.
         ALCATEL NOTE :
         	TABLESIZE    : DEP
         DESCR        : DEP(TABLESIZE)The range of the table is the maximum physical interfaces
         	  	       in the system which can be got from the object issSystemNumberOfPorts
         		       in fsiss.mib."
    ::= { issPCCPGroup 3 }

issPCCPGroupPortEntry OBJECT-TYPE
    SYNTAX      IssPCCPGroupPortEntry
    ACCESS      not-accessible
    STATUS      mandatory
    DESCRIPTION 
        "Path Connectivity Check & Protection Port Group Entry
         Index to the table is the interface index of the port.
         Row creation 	: When a Port is added to the PortList of an PCCP group,
         	      	  an entry will be created automatically into the table.
         Row deletion 	: When a Port is removed from the PortList of an PCCP group,
         	      	  an entry will be deleted automatically from the table.
         Index usage 	: The index is issPortCtrlIndex.
         Note that entries will be presented to the SNMP manager in full
         lexicographical order : sorted on issPortCtrlIndex"
    INDEX       { issPortCtrlIndex }
    ::= { issPCCPGroupPortTable 1 }

IssPCCPGroupPortEntry ::= SEQUENCE {
    issPCCPPortGroupID          INTEGER,
    issPCCPGroupPortForwState   INTEGER
}

issPCCPPortGroupID OBJECT-TYPE
    SYNTAX      INTEGER (1..4)
    ACCESS      read-only
    STATUS      mandatory
    DESCRIPTION 
        "The Path Connectivity Check & Protection Group Identifier.
         ALCATEL NOTE:
         ACCESS : NA		USAGE   : NA
         PERSIST: NA		INSRVMOD: NA
         RANGE  : NA		DEFVALUE: NA
         UNITS  : NA		SPARSE  : NO
         DESCR  : NA"
    ::= { issPCCPGroupPortEntry 1 }

issPCCPGroupPortForwState OBJECT-TYPE
    SYNTAX      INTEGER { discarding(1), forwarding(2) }
    ACCESS      read-only
    STATUS      mandatory
    DESCRIPTION 
        "The actual state of the port being involved in the Path Connectivity Check & Protection Group. 
         If the PCCP group admin state or PCCP feature is disabled then the state will be set to forwarding.
         ALCATEL NOTE:
         ACCESS : NA		USAGE   : NA
         PERSIST: NA		INSRVMOD: NA
         RANGE  : NA		DEFVALUE: NA
         UNITS  : NA		SPARSE  : NO
         DESCR  : NA"
    DEFVAL      { forwarding }
    ::= { issPCCPGroupPortEntry 2 }

issPCCPTraps OBJECT IDENTIFIER
    ::= { iss 12 }

issISAMvMirror OBJECT IDENTIFIER
    ::= { iss 13 }

issISAMvMirrorStatus OBJECT-TYPE
    SYNTAX      INTEGER { disabled(1), enabled(2) }
    ACCESS      read-write
    STATUS      mandatory
    DESCRIPTION 
        "Provides control over the ISAMv Packet mirroring feature in the switch.
         When this feature is enabled, then the legacy mirroring feature 
         - issMirrorStatus cannot be enabled. 
         Similarily when legacy mirroring feature is enabled, the
         issISAMvMirrorStatus cannot be enabled.
         ALCATEL NOTE:
         ACCESS	:   NA          	USAGE		:    NA
         PERSIST:   YES          	INSRVMOD	:    YES
         RANGE	:   NA           	DEFVALUE	:    disabled
         UNITS	:   NA           	SPARSE		:    NA
         DESCR	:   NA"
    DEFVAL      { disabled }
    ::= { issISAMvMirror 1 }

issISAMvLoopbackPort OBJECT-TYPE
    SYNTAX      INTEGER
    ACCESS      read-write
    STATUS      mandatory
    DESCRIPTION 
        "Specifies the port to which the ISAMv feature related mirrored traffic
         in the system is to be copied.Once set, this port can be only used for
         ISAMv mirroring feature. If it is being used for another purpose it
         shall be made unused and re-used internally for mirroring purpose.It 
         shall remain as unused so as to avoid any other configuration on it 
         including port type configuration.This can be configured even if 
         issISAMvMirrorStatus is disabled.When issISAMvMirrorStatus is enabled
         this port is configured as a loopback port and associated to the s-vlan
         and assigned as pvid.If this is set as '0' the port can then also be 
         used for any purpose other than Voice Traffic mirroring.
         As a pre-condition a s-vlan need to be present in the system. A s-vlan
         is identified as that vlan which is created with dot1qVlanStaticName
         as VoiceTrafficMirror.
         Any port other than ASAM ports can be configured as a loopback port.
          ALCATEL NOTE:
          ACCESS	:   NA           USAGE		:    NA
          PERSIST:   YES          INSRVMOD	:    YES
          RANGE	:   DEP	         DEFVALUE	:    0
          UNITS	:   NA           SPARSE		:    NA
          DESCR	:   DEP(RANGE)The range is the maximum number of physical ports 
                     available in the system.The value can be got from the 
                     object issSystemNumberOfPorts in fsiss.mib."
    DEFVAL      { 0 }
    ::= { issISAMvMirror 2 }

issISAMvMirrorIngressPortList OBJECT-TYPE
    SYNTAX      PortList
    ACCESS      read-write
    STATUS      mandatory
    DESCRIPTION 
        "Specifies the set of ports that need to be mirrored for traffic 
         received on it in the upstream direction. Only ASAM ports can be 
         members of the portlist.If the port list is '0',there are no 
         ports specified.
         
         By default portlist is maintained as '0'.
           ALCATEL NOTE:
           ACCESS	:   NA         		USAGE		:    NA
           PERSIST:   YES          	INSRVMOD	:    YES
           RANGE	:   DEP 	        DEFVALUE	:    0
           UNITS	:   NA           	SPARSE		:    NO
         	 DESCR 	:   DEP(RANGE)The range is the maximum number of physical ports 
                      available in the system.The value can be got from the 
                      object issSystemNumberOfPorts in fsiss.mib."
    ::= { issISAMvMirror 3 }

issISAMvMirrorEgressPortList OBJECT-TYPE
    SYNTAX      PortList
    ACCESS      read-write
    STATUS      mandatory
    DESCRIPTION 
        "Specifies the set of ports that need to be mirrored for traffic 
         transmitted on it in the downsteam direction. Both software 
         generated and hardware forwarded packets will be mirrored.Only 
         ASAM ports can be members of the portlist.If the  portlist 
         is '0',there are no ports specified.
         
         By default portlist is maintained as '0'.
           ALCATEL NOTE:
           ACCESS	:   NA         		USAGE		:    NA
           PERSIST:   YES          	INSRVMOD	:    YES
           RANGE	:   DEP 	        DEFVALUE	:    0
           UNITS	:   NA           	SPARSE		:    NO
         	 DESCR 	:   DEP(RANGE)The range is the maximum number of physical ports 
                      available in the system.The value can be got from the 
                      object issSystemNumberOfPorts in fsiss.mib."
    ::= { issISAMvMirror 4 }

issHistEthFrameCounters OBJECT IDENTIFIER
    ::= { iss 14 }

issHistCurrent15MinIntervalTable OBJECT-TYPE
    SYNTAX      SEQUENCE OF IssHistCurrent15MinIntervalEntry
    ACCESS      not-accessible
    STATUS      mandatory
    DESCRIPTION 
        "A table containing port statistics, on a per port basis. 
         This statistics is supported for all the ports in the system. 
         This table is indexed on the port index. 
         For the Current Bin, the counter value is fetched directly from BCM/SDK and the 
         difference from a reference count value is calculated and returned, when a Get
         for any counter is done. 
         
         LANX will collect the statistics for all the ports for every
         15 Minutes (Compile time constant - not a configurable value).
         
         The counter values at a particular time slot is not cumulative in
         nature. It contains statistics for the last 15 Minutes (or lesser) only.
         
         The counter values will be taken only for individual ports regardless 
         of whether the port is in trunk or not.
         
          
         If the port goes oper down, or the port is made admin down or the port type is
         changed to UNUSED, the counter statistics will freeze although the timers
         will continue to run.
         
         If the statistics collection status is DISABLED, the counter values will be
         cleared for both the Current and the History bins of 15 min counter."
    ::= { issHistEthFrameCounters 1 }

issHistCurrent15MinIntervalEntry OBJECT-TYPE
    SYNTAX      IssHistCurrent15MinIntervalEntry
    ACCESS      not-accessible
    STATUS      mandatory
    DESCRIPTION 
        "Entry table for Current 15 Min Ethernet Frame Counter"
    INDEX       { issHistCurrent15MinPortIndex }
    ::= { issHistCurrent15MinIntervalTable 1 }

IssHistCurrent15MinIntervalEntry ::= SEQUENCE {
    issHistCurrent15MinPortIndex        INTEGER,
    issHistCurrent15MinTimeElapsed      INTEGER,
    issHistCurrent15MinTimeMeasured     INTEGER,
    issHistCurrent15MinInvldDataFlg     TruthValue,
    issHistCurrent15MinValidIntervals   INTEGER,
    issHistCurrent15MinInErrors         OCTET STRING,
    issHistCurrent15MinOutErrors        OCTET STRING,
    issHistCurrent15MinInFrames         OCTET STRING,
    issHistCurrent15MinOutFrames        OCTET STRING,
    issHistCurrent15MinInOctets         OCTET STRING,
    issHistCurrent15MinOutOctets        OCTET STRING,
    issHistCurrent15MinInDiscards       OCTET STRING,
    issHistCurrent15MinOutDiscards      OCTET STRING,
    issHistCurrent15MinInDrops          OCTET STRING,
    issHistCurrent15MinOutDrops         OCTET STRING
}

issHistCurrent15MinPortIndex OBJECT-TYPE
    SYNTAX      INTEGER (1..65535)
    ACCESS      not-accessible
    STATUS      mandatory
    DESCRIPTION 
        "Interface index of the port for which the information
         in this entry applies.
         
         ALCATEL NOTE:
         
         ACCESS	:   NA         		USAGE		:    NA
         PERSIST :   YES          	INSRVMOD	:    NA
         RANGE	:   DEP  	        DEFVALUE	:    NA
         UNITS	:   NA           	SPARSE		:    NO
         DESCR	:   DEP(RANGE) The range is the maximum number of physical ports available in 
         	    the system. The value can be got from the object issSystemNumberOfPorts
         	    in this mib file - fsiss.mib."
    ::= { issHistCurrent15MinIntervalEntry 1 }

issHistCurrent15MinTimeElapsed OBJECT-TYPE
    SYNTAX      INTEGER (0..900)
    ACCESS      read-only
    STATUS      mandatory
    DESCRIPTION 
        "The Elapsed Time may be defined as the amount of time from the start of the interval
         to the instant when a Get for this Object is received (from the SNMP Manager).
         
         	ALCATEL NOTE:
         
         ACCESS :   NA           USAGE   :    NA
         PERSIST:   NO           INSRVMOD:    NA
         RANGE  :   (0..900)     DEFVALUE:    NA
         UNITS  :   seconds      SPARSE  :    NA
         DESCR  :   NA"
    ::= { issHistCurrent15MinIntervalEntry 2 }

issHistCurrent15MinTimeMeasured OBJECT-TYPE
    SYNTAX      INTEGER (0..900)
    ACCESS      read-only
    STATUS      mandatory
    DESCRIPTION 
        "The actual time (in seconds) for which the statistics collection was done successfully
         for the given port and for the given bin. This value will be ZERO if the statistics collection
         status is disabled from the start of the Current interval to the instant when the Get of this 
         Object is done.
         
         ALCATEL NOTE:
         
         ACCESS :   NA           USAGE   :    NA
         PERSIST:   NO           INSRVMOD:    NA
         RANGE  :   (0..900)    	DEFVALUE:    NA
         UNITS  :   Seconds      SPARSE  :    NA
         DESCR  :   NA"
    ::= { issHistCurrent15MinIntervalEntry 3 }

issHistCurrent15MinInvldDataFlg OBJECT-TYPE
    SYNTAX      TruthValue
    ACCESS      read-only
    STATUS      mandatory
    DESCRIPTION 
        "This flag indicates that the counter values may be
         inaccurate due to any event which might disrupt the 
         normal statistics collection. 
         
         The flag is expected to be set in the following cases:
         
         o	For the Current bin, after the system has come up
         o	For the Current bin, after the system has come up after a Hot Application Reset	
         o	For the Current bin after the system come up after a switchover
         o	For the Current bin after a SNTP time modification
         o	For the bin in which the statistics collection is enabled /disabled once or multiple
         times within the bin’s interval of 15 minutes
         o	For the interval in which the port type has been changed to UNUSED once or multiple times.
         o	For the bin in which the port admin status has been changed/toggled (up and down), 
         once or multiple times.
         o	For the bin in which the port status goes oper down for any reason.
         o	For the bin is which the Counters were cleared via SNMP Manager or the LANX CLI.
         
         ALCATEL NOTE:
         
         ACCESS :   NA           USAGE   :    NA
         PERSIST:   NO           INSRVMOD:    NA
         RANGE  :   1,2       	DEFVALUE:    true
         UNITS  :   NA           SPARSE  :    NA
         DESCR  :   NA"
    DEFVAL      { true }
    ::= { issHistCurrent15MinIntervalEntry 4 }

issHistCurrent15MinValidIntervals OBJECT-TYPE
    SYNTAX      INTEGER (0..96)
    ACCESS      read-only
    STATUS      mandatory
    DESCRIPTION 
        "This object is the count of Previous 15 Min Intervals (or History Bins) for 
         which the statistics collection was done, for some time say ‘x‘ seconds in the
         interval (where 0 < x < 900 seconds), irrespective of whether the counter values
         for that interval is valid or not.
         
         	ALCATEL NOTE:
         
         ACCESS :   NA           USAGE   :    NA
         PERSIST:   NO           INSRVMOD:    NA
         RANGE  :   0..96       	DEFVALUE:    NA
         UNITS  :   NA           SPARSE  :    NA
         DESCR  :   NA"
    ::= { issHistCurrent15MinIntervalEntry 5 }

issHistCurrent15MinInErrors OBJECT-TYPE
    SYNTAX      OCTET STRING (SIZE(8))
    ACCESS      read-only
    STATUS      mandatory
    DESCRIPTION 
        "The total number of error frames received on the 
         given ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent15MinIntervalEntry 6 }

issHistCurrent15MinOutErrors OBJECT-TYPE
    SYNTAX      OCTET STRING (SIZE(8))
    ACCESS      read-only
    STATUS      mandatory
    DESCRIPTION 
        "The number of error frames transmitted on the given 
         ethernet interface(port) for the given interval.
         
         	ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent15MinIntervalEntry 7 }

issHistCurrent15MinInFrames OBJECT-TYPE
    SYNTAX      OCTET STRING (SIZE(8))
    ACCESS      read-only
    STATUS      mandatory
    DESCRIPTION 
        "The total number of frames (includes good and bad frames)
         received on the given ethernet interface(port) for the 
         given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent15MinIntervalEntry 8 }

issHistCurrent15MinOutFrames OBJECT-TYPE
    SYNTAX      OCTET STRING (SIZE(8))
    ACCESS      read-only
    STATUS      mandatory
    DESCRIPTION 
        "The total number of frames (includes good and bad frames)
         transmitted on the given ethernet interface(port) for the 
         given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent15MinIntervalEntry 9 }

issHistCurrent15MinInOctets OBJECT-TYPE
    SYNTAX      OCTET STRING (SIZE(8))
    ACCESS      read-only
    STATUS      mandatory
    DESCRIPTION 
        "The number of octets(bytes) received on the given 
         ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent15MinIntervalEntry 10 }

issHistCurrent15MinOutOctets OBJECT-TYPE
    SYNTAX      OCTET STRING (SIZE(8))
    ACCESS      read-only
    STATUS      mandatory
    DESCRIPTION 
        "The number of octets(bytes) transmitted on the given 
         ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent15MinIntervalEntry 11 }

issHistCurrent15MinInDiscards OBJECT-TYPE
    SYNTAX      OCTET STRING (SIZE(8))
    ACCESS      read-only
    STATUS      mandatory
    DESCRIPTION 
        "The number of received frames that are discarded 
         on the given ethernet interface(port) for the 
         given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent15MinIntervalEntry 12 }

issHistCurrent15MinOutDiscards OBJECT-TYPE
    SYNTAX      OCTET STRING (SIZE(8))
    ACCESS      read-only
    STATUS      mandatory
    DESCRIPTION 
        "The number of frames discarded when transmitting 
         on the given ethernet interface(port) for the 
         given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent15MinIntervalEntry 13 }

issHistCurrent15MinInDrops OBJECT-TYPE
    SYNTAX      OCTET STRING (SIZE(8))
    ACCESS      read-only
    STATUS      mandatory
    DESCRIPTION 
        "The number of received frames that are dropped on the given  
         ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent15MinIntervalEntry 14 }

issHistCurrent15MinOutDrops OBJECT-TYPE
    SYNTAX      OCTET STRING (SIZE(8))
    ACCESS      read-only
    STATUS      mandatory
    DESCRIPTION 
        "The number of frames dropped when transmitting on the given  
         ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent15MinIntervalEntry 15 }

issHistCurrent1DayIntervalTable OBJECT-TYPE
    SYNTAX      SEQUENCE OF IssHistCurrent1DayIntervalEntry
    ACCESS      not-accessible
    STATUS      mandatory
    DESCRIPTION 
        "A table containing port statistics, on a per port basis. 
         This statistics is supported for all the ports in the system. 
         This table is indexed on the port index and the interval number. 
         
         LANX will collect the Counters for all the ports for every
         24 Hrs (Compile time constant - not a configurable value).
         
         The counter values at a particular time slot is not cumulative in
         nature. It contains statistics for the last 24 Hours only.
         
         The counter values will be taken ONLY for individual ports regardless 
         of whether the port is in trunk or not.
         
         If the port goes oper down, or the port is made admin down or the port type is
         changed to UNUSED, the counter statistics will freeze although the timers
         will continue to run.
         
         If the statistics collection status is DISABLED, the counter values will be
         cleared for both the Current and the History bins of  24 hour counter."
    ::= { issHistEthFrameCounters 2 }

issHistCurrent1DayIntervalEntry OBJECT-TYPE
    SYNTAX      IssHistCurrent1DayIntervalEntry
    ACCESS      not-accessible
    STATUS      mandatory
    DESCRIPTION 
        "Entry table for Current 24 Hour Ethernet Frame Counter"
    INDEX       { issHistCurrent1DayPortIndex }
    ::= { issHistCurrent1DayIntervalTable 1 }

IssHistCurrent1DayIntervalEntry ::= SEQUENCE {
    issHistCurrent1DayPortIndex         INTEGER,
    issHistCurrent1DayTimeElapsed       INTEGER,
    issHistCurrent1DayTimeMeasured      INTEGER,
    issHistCurrent1DayInvldDataFlg      TruthValue,
    issHistCurrent1DayValidIntervals    INTEGER,
    issHistCurrent1DayInErrors          OCTET STRING,
    issHistCurrent1DayOutErrors         OCTET STRING,
    issHistCurrent1DayInFrames          OCTET STRING,
    issHistCurrent1DayOutFrames         OCTET STRING,
    issHistCurrent1DayInOctets          OCTET STRING,
    issHistCurrent1DayOutOctets         OCTET STRING,
    issHistCurrent1DayInDiscards        OCTET STRING,
    issHistCurrent1DayOutDiscards       OCTET STRING,
    issHistCurrent1DayInDrops           OCTET STRING,
    issHistCurrent1DayOutDrops          OCTET STRING
}

issHistCurrent1DayPortIndex OBJECT-TYPE
    SYNTAX      INTEGER (1..65535)
    ACCESS      not-accessible
    STATUS      mandatory
    DESCRIPTION 
        "Interface index of the port for which the information
         in this entry applies.
         
         	ALCATEL NOTE:
         
          	ACCESS	:   NA         		USAGE		:    NA
         	PERSIST :   YES          	INSRVMOD	:    NA
         	RANGE	:   DEP  	        DEFVALUE	:    NA
         	UNITS	:   NA           	SPARSE		:    NO
         	DESCR	:   DEP(RANGE) The range is the maximum number of physical
         		    ports available in the system. The value can be got 
         		    from the object issSystemNumberOfPorts in this mib file - fsiss.mib."
    ::= { issHistCurrent1DayIntervalEntry 1 }

issHistCurrent1DayTimeElapsed OBJECT-TYPE
    SYNTAX      INTEGER (0..86400)
    ACCESS      read-only
    STATUS      mandatory
    DESCRIPTION 
        "The Elapsed Time is the Amount of time from the start of the Current Interval to the
         instant when a Get Request for this Object was received.
         
         		ALCATEL NOTE:
         
          	ACCESS :   NA           USAGE   :    NA
          	PERSIST:   NO           INSRVMOD:    NA
          	RANGE  :   (0..86400)  	DEFVALUE:    NA
          	UNITS  :   NA           SPARSE  :    NA
          	DESCR  :   NA"
    ::= { issHistCurrent1DayIntervalEntry 2 }

issHistCurrent1DayTimeMeasured OBJECT-TYPE
    SYNTAX      INTEGER (0..86400)
    ACCESS      read-only
    STATUS      mandatory
    DESCRIPTION 
        "The actual time (in seconds) for which the statistics collection was done successfully
         for the given port and for the given bin. This value will be ZERO if the statistics collection
         status is disabled from the start of the Current interval to the instant when the Get of this 
         Object is done.
         
         ALCATEL NOTE:
         
         ACCESS :   NA           USAGE   :    NA
         PERSIST:   NO           INSRVMOD:    NA
         RANGE  :   (0..86400)  	DEFVALUE:    NA
         UNITS  :   NA           SPARSE  :    NA
         DESCR  :   NA"
    ::= { issHistCurrent1DayIntervalEntry 3 }

issHistCurrent1DayInvldDataFlg OBJECT-TYPE
    SYNTAX      TruthValue
    ACCESS      read-only
    STATUS      mandatory
    DESCRIPTION 
        "This flag indicates that the counter values may be
         inaccurate due to any event which might disrupt the 
         normal statistics collection. 
         This flag is expected to be set in the following cases:
         
         o	For the Current bin, after the system has come up
         o	For the Current bin, after the system has come up after a Hot
         	Application Reset	
         o	For the Current bin after the system come up after a switchover
         o	For the Current bin after a SNTP time modification
         o	For the bin in which the statistics collection is enabled /disabled
         	once or multiple times within the bin’s interval of 24 hours.
         o	For the interval in which the port type has been changed to UNUSED 
         	once or multiple times.
         o	For the bin in which the port admin status has been changed/toggled
         	(up and down), once or multiple times.
         o	For the bin in which the port status goes oper down for any reason.
         o	For the bin is which the Counters were cleared via SNMP Manager or
         	the LANX CLI.
         
         ALCATEL NOTE:
         
         ACCESS :   NA           USAGE   :    NA
         PERSIST:   NO           INSRVMOD:    NA
         RANGE  :   1,2       	DEFVALUE:    true
         UNITS  :   NA           SPARSE  :    NA
         DESCR  :   NA"
    DEFVAL      { true }
    ::= { issHistCurrent1DayIntervalEntry 4 }

issHistCurrent1DayValidIntervals OBJECT-TYPE
    SYNTAX      INTEGER (0..7)
    ACCESS      read-only
    STATUS      mandatory
    DESCRIPTION 
        "This object is the count of Previous 24 Hour / 1 Day Intervals (or History Bins)  for which the statistics
         collection was done, atleast for some time ‘x‘ seconds in the interval 
         (such that 0 < x < 86400 seconds), irrespective of whether the counter
         statistics for that interval is valid or not.
         ALCATEL NOTE:
         
         ACCESS :   NA           USAGE   :    NA
         PERSIST:   NO           INSRVMOD:    NA
         RANGE  :   0..7       	DEFVALUE:    NA
         UNITS  :   NA           SPARSE  :    NA
         DESCR  :   NA"
    ::= { issHistCurrent1DayIntervalEntry 5 }

issHistCurrent1DayInErrors OBJECT-TYPE
    SYNTAX      OCTET STRING (SIZE(8))
    ACCESS      read-only
    STATUS      mandatory
    DESCRIPTION 
        "The total number of error frames received on the 
         given ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent1DayIntervalEntry 6 }

issHistCurrent1DayOutErrors OBJECT-TYPE
    SYNTAX      OCTET STRING (SIZE(8))
    ACCESS      read-only
    STATUS      mandatory
    DESCRIPTION 
        "The number of error frames transmitted on the given 
         ethernet interface(port) for the given interval.
         
         	ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent1DayIntervalEntry 7 }

issHistCurrent1DayInFrames OBJECT-TYPE
    SYNTAX      OCTET STRING (SIZE(8))
    ACCESS      read-only
    STATUS      mandatory
    DESCRIPTION 
        "The total number of frames (includes good and bad frames)
         received on the given ethernet interface(port) for the 
         given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent1DayIntervalEntry 8 }

issHistCurrent1DayOutFrames OBJECT-TYPE
    SYNTAX      OCTET STRING (SIZE(8))
    ACCESS      read-only
    STATUS      mandatory
    DESCRIPTION 
        "The total number of frames (includes good and bad frames)
         transmitted on the given ethernet interface(port) for the 
         given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent1DayIntervalEntry 9 }

issHistCurrent1DayInOctets OBJECT-TYPE
    SYNTAX      OCTET STRING (SIZE(8))
    ACCESS      read-only
    STATUS      mandatory
    DESCRIPTION 
        "The number of octets(bytes) received on the given 
         ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent1DayIntervalEntry 10 }

issHistCurrent1DayOutOctets OBJECT-TYPE
    SYNTAX      OCTET STRING (SIZE(8))
    ACCESS      read-only
    STATUS      mandatory
    DESCRIPTION 
        "The number of octets(bytes) transmitted on the given 
         ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent1DayIntervalEntry 11 }

issHistCurrent1DayInDiscards OBJECT-TYPE
    SYNTAX      OCTET STRING (SIZE(8))
    ACCESS      read-only
    STATUS      mandatory
    DESCRIPTION 
        "The number of received frames that are discarded on the 
         given ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent1DayIntervalEntry 12 }

issHistCurrent1DayOutDiscards OBJECT-TYPE
    SYNTAX      OCTET STRING (SIZE(8))
    ACCESS      read-only
    STATUS      mandatory
    DESCRIPTION 
        "The number of frames discarded when transmitting on the  
         given ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent1DayIntervalEntry 13 }

issHistCurrent1DayInDrops OBJECT-TYPE
    SYNTAX      OCTET STRING (SIZE(8))
    ACCESS      read-only
    STATUS      mandatory
    DESCRIPTION 
        "The number of received frames that are dropped on the given 
         ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistCurrent1DayIntervalEntry 14 }

issHistCurrent1DayOutDrops OBJECT-TYPE
    SYNTAX      OCTET STRING (SIZE(8))
    ACCESS      read-only
    STATUS      mandatory
    DESCRIPTION 
        "The number of frames dropped when transmitting on the given 
         ethernet interface(port) for the given interval."
    ::= { issHistCurrent1DayIntervalEntry 15 }

issHistPrevious15MinIntervalTable OBJECT-TYPE
    SYNTAX      SEQUENCE OF IssHistPrevious15MinIntervalEntry
    ACCESS      not-accessible
    STATUS      mandatory
    DESCRIPTION 
        "A table containing port statistics, on a per port basis. 
         This statistics is supported for all the ports in the system. 
         This table is indexed on the port index and the interval number. 
         When a Get for this Object is done, the values stored in this
         table will be retrieved.
         
         LANX will collect the statistics for all the ports for every
         15 Minutes (Compile time constant - not a configurable value).
         These counter values are stored for a maximum of 24 Hours (Compile
         time constant - not a configurable value) in LANX.
         
         The counter values at a particular time slot is not cumulative in
         nature. It contains statistics for the last 15 Minutes only.
         
         At any given point of time LANX will have the counter statistics for
         the past 24 Hours or lesser(in case the system has been up for less 
         than a day). This leads to 96 Counter intervals for every port.
         
         The counter values will be taken only for individual ports regardless 
         of whether the port is in trunk or not."
    ::= { issHistEthFrameCounters 3 }

issHistPrevious15MinIntervalEntry OBJECT-TYPE
    SYNTAX      IssHistPrevious15MinIntervalEntry
    ACCESS      not-accessible
    STATUS      mandatory
    DESCRIPTION 
        "Entry table for 15 Min Ethernet Frame Counter"
    INDEX       { issHistPrevious15MinPortIndex, 
                  issHistPrevious15MinInterval }
    ::= { issHistPrevious15MinIntervalTable 1 }

IssHistPrevious15MinIntervalEntry ::= SEQUENCE {
    issHistPrevious15MinPortIndex       INTEGER,
    issHistPrevious15MinInterval        INTEGER,
    issHistPrevious15MinTimeMeasured    INTEGER,
    issHistPrevious15MinInvldDataFlg    TruthValue,
    issHistPrevious15MinInErrors        OCTET STRING,
    issHistPrevious15MinOutErrors       OCTET STRING,
    issHistPrevious15MinInFrames        OCTET STRING,
    issHistPrevious15MinOutFrames       OCTET STRING,
    issHistPrevious15MinInOctets        OCTET STRING,
    issHistPrevious15MinOutOctets       OCTET STRING,
    issHistPrevious15MinInDiscards      OCTET STRING,
    issHistPrevious15MinOutDiscards     OCTET STRING,
    issHistPrevious15MinInDrops         OCTET STRING,
    issHistPrevious15MinOutDrops        OCTET STRING
}

issHistPrevious15MinPortIndex OBJECT-TYPE
    SYNTAX      INTEGER (1..65535)
    ACCESS      not-accessible
    STATUS      mandatory
    DESCRIPTION 
        "Interface index of the port for which the information
         in this entry applies.
         	
         ALCATEL NOTE:
         
         ACCESS	:   NA         		USAGE		:    NA
         PERSIST :   YES          	INSRVMOD	:    NA
         RANGE	:   DEP  	        DEFVALUE	:    NA
         UNITS	:   NA           	SPARSE		:    NO
         DESCR	:   DEP(RANGE) The range is the maximum number of physical ports available in 
         	    the system. The value can be got from the object issSystemNumberOfPorts
         	    in this mib file - fsiss.mib."
    ::= { issHistPrevious15MinIntervalEntry 1 }

issHistPrevious15MinInterval OBJECT-TYPE
    SYNTAX      INTEGER (1..96)
    ACCESS      not-accessible
    STATUS      mandatory
    DESCRIPTION 
        "The Interval Number. Atmost 96 intervals of 15 min period are stored. Specifying the
         interval number retrieves the counter values for that particular interval. It is to 
         be noted that, after expiry of the timer, the Interval Number changes for the Bins. 
         Bin 1 would now be Bin 2, Bin 2 would be Bin 3 and so on and the 96th Bin would no 
         more be available.
         
         	ALCATEL NOTE:
         
         ACCESS :   NA           USAGE   :    NA
         PERSIST:   NO           INSRVMOD:    NA
         RANGE  :   (1..96)      DEFVALUE:    NA
         UNITS  :   seconds      SPARSE  :    NA
         DESCR  :   NA"
    ::= { issHistPrevious15MinIntervalEntry 2 }

issHistPrevious15MinTimeMeasured OBJECT-TYPE
    SYNTAX      INTEGER (0..900)
    ACCESS      read-only
    STATUS      mandatory
    DESCRIPTION 
        "The actual time (in seconds) for which the statistics collection was done successfully
         for the given port and for the given bin. This value will be ZERO if the statistics collection
         status is disabled.
         
         When the statistics collection status is enabled for the specifed port thoughout the given interval,
         the measured time, in most cases, will be the same as the period of the interval (i.e. 15 Mins / 900 seconds)
         for each bin. However, if some internal or external event caused the statistics collection
         to be interrupted, the measured time would reflect only the time over which actual statistics
         collection was carried out and hence might be less than the interval period (i.e., 15 Mins / 900 seconds). 
         
         ALCATEL NOTE:
         
         ACCESS :   NA           USAGE   :    NA
         PERSIST:   NO           INSRVMOD:    NA
         RANGE  :   (0..900)    	DEFVALUE:    NA
         UNITS  :   Seconds      SPARSE  :    NA
         DESCR  :   NA"
    ::= { issHistPrevious15MinIntervalEntry 3 }

issHistPrevious15MinInvldDataFlg OBJECT-TYPE
    SYNTAX      TruthValue
    ACCESS      read-only
    STATUS      mandatory
    DESCRIPTION 
        "This flag indicates that the counter values may be
         inaccurate due to any event which might disrupt the 
         normal statistics collection. 
         
         The flag may be set in the following cases:
         
         o	For the Current bin, after the system has come up
         o	For the Current bin, after the system has come up after a Hot 
         	Application Reset	
         o	For the Current bin after the system come up after a switchover
         o	For the Current bin after a SNTP time modification
         o	For the bin in which the statistics collection is enabled /disabled
         	once or multiple times within the bin’s interval of 15 minutes
         o	For the interval in which the port type has been changed to UNUSED 
         	once or multiple times.
         o	For the bin in which the port admin status has been changed/toggled 
         	(up and down), once or multiple times.
         o	For the bin in which the port status goes oper down for any reason.
         o	For the bin is which the Counters were cleared via SNMP Manager 
         	or the LANX CLI.
         
         
         
         ALCATEL NOTE:
         
         ACCESS :   NA           USAGE   :    NA
         PERSIST:   NO           INSRVMOD:    NA
         RANGE  :   1,2       	DEFVALUE:    true
         UNITS  :   NA           SPARSE  :    NA
         DESCR  :   NA"
    DEFVAL      { true }
    ::= { issHistPrevious15MinIntervalEntry 4 }

issHistPrevious15MinInErrors OBJECT-TYPE
    SYNTAX      OCTET STRING (SIZE(8))
    ACCESS      read-only
    STATUS      mandatory
    DESCRIPTION 
        "The total number of error frames received on the 
         given ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious15MinIntervalEntry 5 }

issHistPrevious15MinOutErrors OBJECT-TYPE
    SYNTAX      OCTET STRING (SIZE(8))
    ACCESS      read-only
    STATUS      mandatory
    DESCRIPTION 
        "The number of error frames transmitted on the given 
         ethernet interface(port) for the given interval.
         
         	ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious15MinIntervalEntry 6 }

issHistPrevious15MinInFrames OBJECT-TYPE
    SYNTAX      OCTET STRING (SIZE(8))
    ACCESS      read-only
    STATUS      mandatory
    DESCRIPTION 
        "The total number of frames (includes good and bad frames)
         received on the given ethernet interface(port) for the 
         given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious15MinIntervalEntry 7 }

issHistPrevious15MinOutFrames OBJECT-TYPE
    SYNTAX      OCTET STRING (SIZE(8))
    ACCESS      read-only
    STATUS      mandatory
    DESCRIPTION 
        "The total number of frames (includes good and bad frames)
         transmitted on the given ethernet interface(port) for the 
         given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious15MinIntervalEntry 8 }

issHistPrevious15MinInOctets OBJECT-TYPE
    SYNTAX      OCTET STRING (SIZE(8))
    ACCESS      read-only
    STATUS      mandatory
    DESCRIPTION 
        "The number of octets(bytes) received on the given 
         ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious15MinIntervalEntry 9 }

issHistPrevious15MinOutOctets OBJECT-TYPE
    SYNTAX      OCTET STRING (SIZE(8))
    ACCESS      read-only
    STATUS      mandatory
    DESCRIPTION 
        "The number of octets(bytes) transmitted on the given 
         ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious15MinIntervalEntry 10 }

issHistPrevious15MinInDiscards OBJECT-TYPE
    SYNTAX      OCTET STRING (SIZE(8))
    ACCESS      read-only
    STATUS      mandatory
    DESCRIPTION 
        "The number of received frames that are discarded on 
         the given ethernet interface(port) for the given 
         interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious15MinIntervalEntry 11 }

issHistPrevious15MinOutDiscards OBJECT-TYPE
    SYNTAX      OCTET STRING (SIZE(8))
    ACCESS      read-only
    STATUS      mandatory
    DESCRIPTION 
        "The number of frames discarded when transmitting on the 
         given ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious15MinIntervalEntry 12 }

issHistPrevious15MinInDrops OBJECT-TYPE
    SYNTAX      OCTET STRING (SIZE(8))
    ACCESS      read-only
    STATUS      mandatory
    DESCRIPTION 
        "The number of received frames that are dropped on the given 
         ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious15MinIntervalEntry 13 }

issHistPrevious15MinOutDrops OBJECT-TYPE
    SYNTAX      OCTET STRING (SIZE(8))
    ACCESS      read-only
    STATUS      mandatory
    DESCRIPTION 
        "The number of frames dropped when transmitting on the given  
         ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious15MinIntervalEntry 14 }

issHistPrevious1DayIntervalTable OBJECT-TYPE
    SYNTAX      SEQUENCE OF IssHistPrevious1DayIntervalEntry
    ACCESS      not-accessible
    STATUS      mandatory
    DESCRIPTION 
        "A table containing port statistics, on a per port basis. 
         This statistics is supported for all the ports in the system. 
         This table is indexed on the port index and the interval number. 
         When a Get fot this Object is received, the values stored in the 
         24 Hour History table will be retreived.
         
         LANX will collect the statistics for all the ports for every
         24 Hours (Compile time constant - not a configurable value).
         These counter values are stored for a maximum of 7 days (Compile
         time constant - not a configurable value) in LANX.
         
         The counter values at a particular time slot is not cumulative in
         nature. It contains statistics for the last 24 Hours only.
         
         At any given point of time LANX will have the counter statistics for
         the past 7 days or lesser(in case the system has been up for less 
         than a week). This leads to 7 Counter intervals for every port.
         
         The counter values will be taken only for individual ports regardless 
         of whether the port is in trunk or not."
    ::= { issHistEthFrameCounters 4 }

issHistPrevious1DayIntervalEntry OBJECT-TYPE
    SYNTAX      IssHistPrevious1DayIntervalEntry
    ACCESS      not-accessible
    STATUS      mandatory
    DESCRIPTION 
        "Entry table for Previous 24 Hours Ethernet Frame Counter"
    INDEX       { issHistPrevious1DayPortIndex, 
                  issHistPrevious1DayInterval }
    ::= { issHistPrevious1DayIntervalTable 1 }

IssHistPrevious1DayIntervalEntry ::= SEQUENCE {
    issHistPrevious1DayPortIndex        INTEGER,
    issHistPrevious1DayInterval         INTEGER,
    issHistPrevious1DayTimeMeasured     INTEGER,
    issHistPrevious1DayInvldDataFlg     TruthValue,
    issHistPrevious1DayInErrors         OCTET STRING,
    issHistPrevious1DayOutErrors        OCTET STRING,
    issHistPrevious1DayInFrames         OCTET STRING,
    issHistPrevious1DayOutFrames        OCTET STRING,
    issHistPrevious1DayInOctets         OCTET STRING,
    issHistPrevious1DayOutOctets        OCTET STRING,
    issHistPrevious1DayInDiscards       OCTET STRING,
    issHistPrevious1DayOutDiscards      OCTET STRING,
    issHistPrevious1DayInDrops          OCTET STRING,
    issHistPrevious1DayOutDrops         OCTET STRING
}

issHistPrevious1DayPortIndex OBJECT-TYPE
    SYNTAX      INTEGER (1..65535)
    ACCESS      not-accessible
    STATUS      mandatory
    DESCRIPTION 
        "Interface index of the port for which the information
         in this entry applies.
         
         ALCATEL NOTE:
         
         ACCESS	:   NA         		USAGE		:    NA
         PERSIST :   YES          	INSRVMOD	:    NA
         RANGE	:   DEP  	        DEFVALUE	:    NA
         UNITS	:   NA           	SPARSE		:    NO
         DESCR	:   DEP(RANGE) The range is the maximum number of physical ports available in 
         	    the system. The value can be got from the object issSystemNumberOfPorts
         	    in this mib file - fsiss.mib."
    ::= { issHistPrevious1DayIntervalEntry 1 }

issHistPrevious1DayInterval OBJECT-TYPE
    SYNTAX      INTEGER (1..7)
    ACCESS      not-accessible
    STATUS      mandatory
    DESCRIPTION 
        "The Interval Number. Atmost 7 intervals of 24 Hour period are stored. Specifying 
         the interval number retrieves the counter values for that particular interval. 
         It is to be noted that, after expiry of the timer, the Interval Number changes
         for the Bins. Bin 1 would now be Bin 2, Bin 2 would be Bin 3 and so on and the
         7th Bin would no more be available.
         
         	ALCATEL NOTE:
         
         ACCESS :   NA           USAGE   :    NA
         PERSIST:   NO           INSRVMOD:    NA
         RANGE  :   (1..7)       DEFVALUE:    NA
         UNITS  :   seconds      SPARSE  :    NA
         DESCR  :   NA"
    ::= { issHistPrevious1DayIntervalEntry 2 }

issHistPrevious1DayTimeMeasured OBJECT-TYPE
    SYNTAX      INTEGER (0..86400)
    ACCESS      read-only
    STATUS      mandatory
    DESCRIPTION 
        "The actual time (in seconds) for which the statistics collection was done successfully
         for the given port and for the given bin. This value will be ZERO if the statistics collection
         status is disabled.
         
         When the statistics collection status is enabled for the specified port, the measured time, 
         in most cases, will be the same as the period of the interval (i.e. 24 Hours / 86400 seconds)
         for each bin. However, if some internal or external event caused the statistics collection
         to be interrupted, the measured time would reflect only the time over which actual statistics
         collection was carried out and hence might be less than the interval period (i.e., 24 Hours / 86400 seconds). 
         
         ALCATEL NOTE:
         
         ACCESS :   NA           USAGE   :    NA
         PERSIST:   NO           INSRVMOD:    NA
         RANGE  :   (0..86400)   DEFVALUE:    NA
         UNITS  :   Seconds      SPARSE  :    NA
         DESCR  :   NA"
    ::= { issHistPrevious1DayIntervalEntry 3 }

issHistPrevious1DayInvldDataFlg OBJECT-TYPE
    SYNTAX      TruthValue
    ACCESS      read-only
    STATUS      mandatory
    DESCRIPTION 
        "This flag indicates that the counter values may be
         inaccurate due to any event which might disrupt the 
         normal statistics collection. 
         
         The flag may be set in the following cases:
         
         o	For the Current bin, after the system has come up
         o	For the Current bin, after the system has come up after a Hot Application Reset	
         o	For the Current bin after the system come up after a switchover
         o	For the Current bin after a SNTP time modification
         o	For the bin in which the statistics collection is enabled /disabled once or multiple times within the bin’s interval of 24 Hours
         o	For the interval in which the port type has been changed to UNUSED once or multiple times.
         o	For the bin in which the port admin status has been changed/toggled (up and down), once or multiple times.
         o	For the bin in which the port status goes oper down for any reason.
         o	For the bin is which the Counters were cleared via SNMP Manager or the LANX CLI.
         
         
         ALCATEL NOTE:
         
         ACCESS :   NA           USAGE   :    NA
         PERSIST:   NO           INSRVMOD:    NA
         RANGE  :   1,2       	DEFVALUE:    true
         UNITS  :   NA           SPARSE  :    NA
         DESCR  :   NA"
    DEFVAL      { true }
    ::= { issHistPrevious1DayIntervalEntry 4 }

issHistPrevious1DayInErrors OBJECT-TYPE
    SYNTAX      OCTET STRING (SIZE(8))
    ACCESS      read-only
    STATUS      mandatory
    DESCRIPTION 
        "The total number of error frames received on the 
         given ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious1DayIntervalEntry 5 }

issHistPrevious1DayOutErrors OBJECT-TYPE
    SYNTAX      OCTET STRING (SIZE(8))
    ACCESS      read-only
    STATUS      mandatory
    DESCRIPTION 
        "The number of error frames transmitted on the given 
         ethernet interface(port) for the given interval.
         
         	ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious1DayIntervalEntry 6 }

issHistPrevious1DayInFrames OBJECT-TYPE
    SYNTAX      OCTET STRING (SIZE(8))
    ACCESS      read-only
    STATUS      mandatory
    DESCRIPTION 
        "The total number of frames (includes good and bad frames)
         received on the given ethernet interface(port) for the 
         given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious1DayIntervalEntry 7 }

issHistPrevious1DayOutFrames OBJECT-TYPE
    SYNTAX      OCTET STRING (SIZE(8))
    ACCESS      read-only
    STATUS      mandatory
    DESCRIPTION 
        "The total number of frames (includes good and bad frames)
         transmitted on the given ethernet interface(port) for the 
         given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious1DayIntervalEntry 8 }

issHistPrevious1DayInOctets OBJECT-TYPE
    SYNTAX      OCTET STRING (SIZE(8))
    ACCESS      read-only
    STATUS      mandatory
    DESCRIPTION 
        "The number of octets(bytes) received on the given 
         ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious1DayIntervalEntry 9 }

issHistPrevious1DayOutOctets OBJECT-TYPE
    SYNTAX      OCTET STRING (SIZE(8))
    ACCESS      read-only
    STATUS      mandatory
    DESCRIPTION 
        "The number of octets(bytes) transmitted on the given 
         ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious1DayIntervalEntry 10 }

issHistPrevious1DayInDiscards OBJECT-TYPE
    SYNTAX      OCTET STRING (SIZE(8))
    ACCESS      read-only
    STATUS      mandatory
    DESCRIPTION 
        "The number of received frames that are discarded 
         on the given ethernet interface(port) for the
         given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious1DayIntervalEntry 11 }

issHistPrevious1DayOutDiscards OBJECT-TYPE
    SYNTAX      OCTET STRING (SIZE(8))
    ACCESS      read-only
    STATUS      mandatory
    DESCRIPTION 
        "The number of frames discarded when transmitting 
         on the given ethernet interface(port) for the given
         interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious1DayIntervalEntry 12 }

issHistPrevious1DayInDrops OBJECT-TYPE
    SYNTAX      OCTET STRING (SIZE(8))
    ACCESS      read-only
    STATUS      mandatory
    DESCRIPTION 
        "The number of received frames that are dropped on the given 
         ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious1DayIntervalEntry 13 }

issHistPrevious1DayOutDrops OBJECT-TYPE
    SYNTAX      OCTET STRING (SIZE(8))
    ACCESS      read-only
    STATUS      mandatory
    DESCRIPTION 
        "The number of frames dropped when transmitting on the given 
         ethernet interface(port) for the given interval.
         
         ALCATEL NOTE:
         
         ACCESS :   NA           USAGE   :    NA
         PERSIST:   NO           INSRVMOD:    NA
         RANGE  :   NA       	DEFVALUE:    NA
         UNITS  :   NA           SPARSE  :    NA
         DESCR  :   NA"
    ::= { issHistPrevious1DayIntervalEntry 14 }

issHistStatsControlTable OBJECT-TYPE
    SYNTAX      SEQUENCE OF IssHistStatsControlEntry
    ACCESS      not-accessible
    STATUS      mandatory
    DESCRIPTION 
        "This table is used for statistics control for the 
         15 Min Counter and the 24 Hr Counter. 
         
         This table is indexed on the port index.
         
         The statistics collection can be enabled or disabled
         for a particular port. When the status of statistics  
         collection is disabled for any port, the counter values
         (in the software) will be cleared from the Current and the
         History Tables of both, the 15 min counter and the 24 hour 
         counter."
    ::= { issHistEthFrameCounters 5 }

issHistStatsControlEntry OBJECT-TYPE
    SYNTAX      IssHistStatsControlEntry
    ACCESS      not-accessible
    STATUS      mandatory
    DESCRIPTION 
        "For each (ethernet interface) port in the system, there exists an entry 
         which contains the issHistStatsCollectionStatus object
         which allows enabling or disabling the statistics collection for the
         specified port index and issHistStatsClears object which provides
         the support for clearing the counters (both 15 Min and the 24 Hour Counters)
         for the specified port index."
    INDEX       { issHistStatsPortIndex }
    ::= { issHistStatsControlTable 1 }

IssHistStatsControlEntry ::= SEQUENCE {
    issHistStatsPortIndex           INTEGER,
    issHistStatsCollectionStatus    INTEGER
}

issHistStatsPortIndex OBJECT-TYPE
    SYNTAX      INTEGER (1..65535)
    ACCESS      not-accessible
    STATUS      mandatory
    DESCRIPTION 
        "Interface index of the port for which the information
         in this entry applies.
           
         	ALCATEL NOTE:
         
         	ACCESS	:   NA         		USAGE		:    NA
         	PERSIST :   YES          	INSRVMOD	:    NA
         	RANGE	:   DEP  	        DEFVALUE	:    NA
         	UNITS	:   NA           	SPARSE		:    NA
         	DESCR	:   DEP(RANGE) The range is the maximum number of physical ports available in 
         		    the system. The value can be got from the object issSystemNumberOfPorts
         		    in this mib file - fsiss.mib."
    ::= { issHistStatsControlEntry 1 }

issHistStatsCollectionStatus OBJECT-TYPE
    SYNTAX      INTEGER { disable(1), enable(2) }
    ACCESS      read-write
    STATUS      mandatory
    DESCRIPTION 
        "The collection status of the port statistics can be either enabled or 
         disabled on a per port basis.
         
         When Disabled, the counters collected will be cleared (only in the software)
         for both the current and the history bins of 15 Min counter and the 24 hour counter.
         
         
         ALCATEL NOTE:
         
         ACCESS :   NA           USAGE   :    OPT
         PERSIST:   YES          INSRVMOD:    NA
         RANGE  :   1,2          DEFVALUE:    disable (1)
         UNITS  :   NA           SPARSE  :    NA
         DESCR  :   NA"
    DEFVAL      { disable }
    ::= { issHistStatsControlEntry 2 }

issL2CollisionMonitoring OBJECT IDENTIFIER
    ::= { iss 15 }

issL2CollisionThreshold OBJECT-TYPE
    SYNTAX      Gauge (0..4294967295)
    ACCESS      read-write
    STATUS      mandatory
    DESCRIPTION 
        "This value is configurable by the user.
         
         This value is the limit beyond which, if the number of 
         collisions exceeds within the 15-minute interval, an alarm is raised.
         This alarm is cleared at the expiry of any following 15-minute interval,
         provided the collision-count is below the threshold during that interval.
         
         A threshold value of 0 will mean that no alarm will be raised for 
         L2 collisions.
         
         ALCATEL NOTE:
         
         ACCESS :   NA                  USAGE   :    NA
         PERSIST:   YES                 INSRVMOD:    NA
         RANGE  :   (0..4294967295)     DEFVALUE:    0
         UNITS  :   NA                  SPARSE  :    NA
         DESCR  :   NA"
    DEFVAL      { 0 }
    ::= { issL2CollisionMonitoring 1 }

issL2CollisionCur15MinValue OBJECT-TYPE
    SYNTAX      Gauge (0..4294967295)
    ACCESS      read-only
    STATUS      mandatory
    DESCRIPTION 
        "The number of collisions that occured in the current 15-minute interval.
         This value is reset to 0 after the current 15-minute interval.
         
         ALCATEL NOTE:
         
         ACCESS :   NA                  USAGE   :    NA
         PERSIST:   NA                  INSRVMOD:    NA
         RANGE  :   (0..4294967295)     DEFVALUE:    NA
         UNITS  :   NA                  SPARSE  :    NA
         DESCR  :   NA"
    ::= { issL2CollisionMonitoring 2 }

issL2CollisionCur15MinTimeMeasured OBJECT-TYPE
    SYNTAX      INTEGER (0..900)
    ACCESS      read-only
    STATUS      mandatory
    DESCRIPTION 
        "The time (in seconds) within the 15-minute interval during which
         the L2 collision monitoring was done successfully.
         
         ALCATEL NOTE:
         
         ACCESS :   NA               USAGE   :    NA
         PERSIST:   NA               INSRVMOD:    NA
         RANGE  :   (0..900)         DEFVALUE:    NA
         UNITS  :   NA               SPARSE  :    NA
         DESCR  :   NA"
    ::= { issL2CollisionMonitoring 3 }

issL2CollisionCur15MinTimeElapsed OBJECT-TYPE
    SYNTAX      INTEGER (0..900)
    ACCESS      read-only
    STATUS      mandatory
    DESCRIPTION 
        "The time (in seconds) from the start of the interval to the instant
         when a Get is done on this object (from the SNMP manager) within the 
         interval.
         
         ALCATEL NOTE:
         
         ACCESS :   NA               USAGE   :    NA
         PERSIST:   NA               INSRVMOD:    NA
         RANGE  :   (0..900)         DEFVALUE:    NA
         UNITS  :   NA               SPARSE  :    NA
         DESCR  :   NA"
    ::= { issL2CollisionMonitoring 4 }

issL2CollisionCur15MinInvldDataFlag OBJECT-TYPE
    SYNTAX      TruthValue
    ACCESS      read-only
    STATUS      mandatory
    DESCRIPTION 
        "This flag indicates whether any event has disrupted the monitoring of
         L2 collisions.
         
         This flag is set under the following conditions.
         
         o	For the Current bin, after the system has come up
         o	For the Current bin, after the system has come up after a Hot Application Reset	
         o	For the Current bin after the system come up after a switchover
         o	For the Current bin after a SNTP time modification
         
         ALCATEL NOTE:
         
         ACCESS :   NA           USAGE   :    NA
         PERSIST:   NA           INSRVMOD:    NA
         RANGE  :   1,2          DEFVALUE:    true
         UNITS  :   NA           SPARSE  :    NA
         DESCR  :   NA"
    DEFVAL      { true }
    ::= { issL2CollisionMonitoring 5 }

issL2Collision15MinValidIntervals OBJECT-TYPE
    SYNTAX      INTEGER (0..192)
    ACCESS      read-only
    STATUS      mandatory
    DESCRIPTION 
        "The number of intervals from the start of the system
         for which the L2 collision monitoring was done
         successfully.
         
         The intervals are counted as valid even if the Invalid Data
         flag is set.
         
         ALCATEL NOTE:
         
         ACCESS :   NA              USAGE   :    NA
         PERSIST:   NA              INSRVMOD:    NA
         RANGE  :   0..192          DEFVALUE:    NA
         UNITS  :   NA              SPARSE  :    NA
         DESCR  :   NA"
    ::= { issL2CollisionMonitoring 6 }

issL2CollisionCur1DayValue OBJECT-TYPE
    SYNTAX      Gauge (0..4294967295)
    ACCESS      read-only
    STATUS      mandatory
    DESCRIPTION 
        "The number of collisions that occured in the current 1-day interval.
         This value is reset to 0 after the current day.
         
         ALCATEL NOTE:
         
         ACCESS :   NA                  USAGE   :    NA
         PERSIST:   NA                  INSRVMOD:    NA
         RANGE  :   (0..4294967295)     DEFVALUE:    NA
         UNITS  :   NA                  SPARSE  :    NA
         DESCR  :   NA"
    ::= { issL2CollisionMonitoring 7 }

issL2CollisionCur1DayTimeMeasured OBJECT-TYPE
    SYNTAX      INTEGER (0..86400)
    ACCESS      read-only
    STATUS      mandatory
    DESCRIPTION 
        "The time (in seconds) within the 1-day interval during which
         the L2 collision monitoring was done successfully.
         
         ALCATEL NOTE:
         
         ACCESS :   NA               USAGE   :    NA
         PERSIST:   NA               INSRVMOD:    NA
         RANGE  :   (0..86400)       DEFVALUE:    NA
         UNITS  :   NA               SPARSE  :    NA
         DESCR  :   NA"
    ::= { issL2CollisionMonitoring 8 }

issL2CollisionCur1DayTimeElapsed OBJECT-TYPE
    SYNTAX      INTEGER (0..86400)
    ACCESS      read-only
    STATUS      mandatory
    DESCRIPTION 
        "The time (in seconds) from the start of the 1-day interval to the instant
         when a Get is done on this object (from the SNMP manager).
         
         ALCATEL NOTE:
         
         ACCESS :   NA               USAGE   :    NA
         PERSIST:   NA               INSRVMOD:    NA
         RANGE  :   (0..86400)       DEFVALUE:    NA
         UNITS  :   NA               SPARSE  :    NA
         DESCR  :   NA"
    ::= { issL2CollisionMonitoring 9 }

issL2CollisionCur1DayInvldDataFlag OBJECT-TYPE
    SYNTAX      TruthValue
    ACCESS      read-only
    STATUS      mandatory
    DESCRIPTION 
        "This flag indicates whether any event has disrupted the monitoring of
         L2 collisions in the current day.
         
         This flag is set under the following conditions.
         
         o	For the Current bin, after the system has come up
         o	For the Current bin, after the system has come up after a Hot Application Reset	
         o	For the Current bin after the system come up after a switchover
         o	For the Current bin after a SNTP time modification
         
         ALCATEL NOTE:
         
         ACCESS :   NA           USAGE   :    NA
         PERSIST:   NA           INSRVMOD:    NA
         RANGE  :   1,2          DEFVALUE:    true
         UNITS  :   NA           SPARSE  :    NA
         DESCR  :   NA"
    DEFVAL      { true }
    ::= { issL2CollisionMonitoring 10 }

issL2CollisionPrev1DayValue OBJECT-TYPE
    SYNTAX      Gauge (0..4294967295)
    ACCESS      read-only
    STATUS      mandatory
    DESCRIPTION 
        "The number of collisions that occured in the previous 1-day interval.
         
         ALCATEL NOTE:
         
         ACCESS :   NA                  USAGE   :    NA
         PERSIST:   NA                  INSRVMOD:    NA
         RANGE  :   (0..4294967295)     DEFVALUE:    NA
         UNITS  :   NA                  SPARSE  :    NA
         DESCR  :   NA"
    ::= { issL2CollisionMonitoring 11 }

issL2CollisionPrev1DayTimeMeasured OBJECT-TYPE
    SYNTAX      INTEGER (0..86400)
    ACCESS      read-only
    STATUS      mandatory
    DESCRIPTION 
        "The time (in seconds) within the past 1-day interval during which
         the L2 collision monitoring was done successfully.
         
         ALCATEL NOTE:
         
         ACCESS :   NA               USAGE   :    NA
         PERSIST:   NA               INSRVMOD:    NA
         RANGE  :   (0..86400)       DEFVALUE:    NA
         UNITS  :   NA               SPARSE  :    NA
         DESCR  :   NA"
    ::= { issL2CollisionMonitoring 12 }

issL2CollisionPrev1DayInvldDataFlag OBJECT-TYPE
    SYNTAX      TruthValue
    ACCESS      read-only
    STATUS      mandatory
    DESCRIPTION 
        "This flag indicates whether any event has disrupted the monitoring of
         L2 collisions in the previous day.
         
         This flag is set under the following conditions.
         
         o	For the Current bin, after the system has come up
         o	For the Current bin, after the system has come up after a Hot Application Reset	
         o	For the Current bin after the system come up after a switchover
         o	For the Current bin after a SNTP time modification
         
         ALCATEL NOTE:
         
         ACCESS :   NA           USAGE   :    NA
         PERSIST:   NA           INSRVMOD:    NA
         RANGE  :   1,2          DEFVALUE:    true
         UNITS  :   NA           SPARSE  :    NA
         DESCR  :   NA"
    DEFVAL      { true }
    ::= { issL2CollisionMonitoring 13 }

issL2CollisionPrevTable OBJECT-TYPE
    SYNTAX      SEQUENCE OF IssL2CollisionPrevEntry
    ACCESS      not-accessible
    STATUS      mandatory
    DESCRIPTION 
        "This table is used to store the number of collisions that 
         occured during the past 15-minute intervals. 
         
         This table is indexed on the past 15-minute interval index.
         
         When the current 15-minute timer expires, the current bin
         becomes history bin and the previous history bin moves to 
         the next history bin and so on"
    ::= { issL2CollisionMonitoring 14 }

issL2CollisionPrevEntry OBJECT-TYPE
    SYNTAX      IssL2CollisionPrevEntry
    ACCESS      not-accessible
    STATUS      mandatory
    DESCRIPTION 
        "For each past 15-minute interval, there exists an entry 
         which contains the number of collisions that occured 
         during that interval"
    INDEX       { issL2CollisionPrevIntervalIndex }
    ::= { issL2CollisionPrevTable 1 }

IssL2CollisionPrevEntry ::= SEQUENCE {
    issL2CollisionPrevIntervalIndex     INTEGER,
    issL2CollisionPrevTimeMeasured      INTEGER,
    issL2CollisionPrevInvldDataFlag     TruthValue,
    issL2CollisionPrevValue             Gauge
}

issL2CollisionPrevIntervalIndex OBJECT-TYPE
    SYNTAX      INTEGER (1..192)
    ACCESS      not-accessible
    STATUS      mandatory
    DESCRIPTION 
        "The bin number or the interval number for the past 15-minute intervals.
         
         ALCATEL NOTE:
         
         ACCESS :   NA           USAGE   :    NA
         PERSIST:   NA           INSRVMOD:    NA
         RANGE  :   (1..192)     DEFVALUE:    NA
         UNITS  :   NA           SPARSE  :    NA
         DESCR  :   NA"
    ::= { issL2CollisionPrevEntry 1 }

issL2CollisionPrevTimeMeasured OBJECT-TYPE
    SYNTAX      INTEGER (0..900)
    ACCESS      read-only
    STATUS      mandatory
    DESCRIPTION 
        "The time (in seconds) for the past 15-minute intervals during which
         the L2 collision monitoring was done successfully.
         
         ALCATEL NOTE:
         
         ACCESS :   NA               USAGE   :    NA
         PERSIST:   NA               INSRVMOD:    NA
         RANGE  :   (0..900)         DEFVALUE:    NA
         UNITS  :   NA               SPARSE  :    NA
         DESCR  :   NA"
    ::= { issL2CollisionPrevEntry 2 }

issL2CollisionPrevInvldDataFlag OBJECT-TYPE
    SYNTAX      TruthValue
    ACCESS      read-only
    STATUS      mandatory
    DESCRIPTION 
        "This flag indicates whether any event has disrupted the monitoring of
         L2 collisions for the past 15-minute interval.
         
         This flag is set under the following conditions.
         
         o	For the Current bin, after the system has come up
         o	For the Current bin, after the system has come up after a Hot Application Reset	
         o	For the Current bin after the system come up after a switchover
         o	For the Current bin after a SNTP time modification
         
         ALCATEL NOTE:
         
         ACCESS :   NA           USAGE   :    NA
         PERSIST:   NA           INSRVMOD:    NA
         RANGE  :   1,2          DEFVALUE:    true
         UNITS  :   NA           SPARSE  :    NA
         DESCR  :   NA"
    DEFVAL      { true }
    ::= { issL2CollisionPrevEntry 3 }

issL2CollisionPrevValue OBJECT-TYPE
    SYNTAX      Gauge (0..4294967295)
    ACCESS      read-only
    STATUS      mandatory
    DESCRIPTION 
        "The number of collisions that occured during the past 15-minute
         interval.
         
         ALCATEL NOTE:
         
         ACCESS :   NA                   USAGE   :    NA
         PERSIST:   NA                   INSRVMOD:    NA
         RANGE  :   (0..4294967295)      DEFVALUE:    NA
         UNITS  :   NA                   SPARSE  :    NA
         DESCR  :   NA"
    ::= { issL2CollisionPrevEntry 4 }

issL2CollisionCyclicBufferTbl OBJECT-TYPE
    SYNTAX      SEQUENCE OF IssL2CollisionCyclicBufferEntry
    ACCESS      not-accessible
    STATUS      mandatory
    DESCRIPTION 
        "This table is used to store the information about collisions
         that have occured in the past. This table can contain 
         information about maximum of 100 collisions.
         
         When a L2 collision occurs, the ninth entry is not learnt.
         So this entry is recorded with its vlan, mac and bucket id 
         it was hashed into this table.
         
         Once all the buffers are filled, the index rolls over, so 
         this buffer is a cyclic buffer.
         
         This table is indexed on the buffer number."
    ::= { issL2CollisionMonitoring 15 }

issL2CollisionCyclicBufferEntry OBJECT-TYPE
    SYNTAX      IssL2CollisionCyclicBufferEntry
    ACCESS      not-accessible
    STATUS      mandatory
    DESCRIPTION 
        "For each collision that has occured in the past, there exists
         an entry which contains information about that collision"
    INDEX       { issL2CollisionCyclBufferIndex }
    ::= { issL2CollisionCyclicBufferTbl 1 }

IssL2CollisionCyclicBufferEntry ::= SEQUENCE {
    issL2CollisionCyclBufferIndex   INTEGER,
    issL2CollisionVlan              INTEGER,
    issL2CollisionMacAddr           MacAddress,
    issL2CollisionTimestamp         Gauge,
    issL2CollisionBkt               INTEGER
}

issL2CollisionCyclBufferIndex OBJECT-TYPE
    SYNTAX      INTEGER (1..100)
    ACCESS      not-accessible
    STATUS      mandatory
    DESCRIPTION 
        "The bin number or the interval number for the cyclic buffer 
         containing information on the previous collisions that have
         occured in the system.
            	
         ALCATEL NOTE:
         
         ACCESS :   NA           USAGE   :    NA
         PERSIST:   NA           INSRVMOD:    NA
         RANGE  :   (1..100)     DEFVALUE:    NA
         UNITS  :   NA           SPARSE  :    NA
         DESCR  :   NA"
    ::= { issL2CollisionCyclicBufferEntry 1 }

issL2CollisionVlan OBJECT-TYPE
    SYNTAX      INTEGER (0..4094)
    ACCESS      read-only
    STATUS      mandatory
    DESCRIPTION 
        "A ninth entry into a hash bucket will cause a collision.
         This object stores the ninth entry VLAN which caused collision
         in a particular bucket.
         
         ALCATEL NOTE:
         
         ACCESS :   NA           USAGE   :    NA
         PERSIST:   NA           INSRVMOD:    NA
         RANGE  :   (0..4094)    DEFVALUE:    0
         UNITS  :   NA           SPARSE  :    NA
         DESCR  :   NA"
    ::= { issL2CollisionCyclicBufferEntry 2 }

issL2CollisionMacAddr OBJECT-TYPE
    SYNTAX      MacAddress
    ACCESS      read-only
    STATUS      mandatory
    DESCRIPTION 
        "A ninth entry into a hash bucket will cause a collision.
         This object stores the ninth entry MAC address which caused 
         collision in a particular bucket.
         
         ALCATEL NOTE:
         
         ACCESS :   NA           USAGE   :    NA
         PERSIST:   NA           INSRVMOD:    NA
         RANGE  :   NA           DEFVALUE:    NA
         UNITS  :   NA           SPARSE  :    NA
         DESCR  :   NA"
    ::= { issL2CollisionCyclicBufferEntry 3 }

issL2CollisionTimestamp OBJECT-TYPE
    SYNTAX      Gauge (0..4294967295)
    ACCESS      read-only
    STATUS      mandatory
    DESCRIPTION 
        "This object stores the time at which collision occured.
         
         The timestamp is obtained by XAPI call.
         
         ALCATEL NOTE:
         
         ACCESS :   NA                    USAGE   :    NA
         PERSIST:   NA                    INSRVMOD:    NA
         RANGE  :   (0..4294967295)       DEFVALUE:    NA
         UNITS  :   NA                    SPARSE  :    NA
         DESCR  :   NA"
    ::= { issL2CollisionCyclicBufferEntry 4 }

issL2CollisionBkt OBJECT-TYPE
    SYNTAX      INTEGER (0..4096)
    ACCESS      read-only
    STATUS      mandatory
    DESCRIPTION 
        "This object stores the bucket Id in which collision occured.
         
         The range is dependent on board type. It is (0..4096) for ECNT-E
         and ERAM-A and it is (0..2048) for other boards.
         
         ALCATEL NOTE:
         
         ACCESS :   NA           USAGE   :    NA
         PERSIST:   NA           INSRVMOD:    NA
         RANGE  :   (0..4096)    DEFVALUE:    0
         UNITS  :   NA           SPARSE  :    NA
         DESCR  :   NA"
    ::= { issL2CollisionCyclicBufferEntry 5 }

issL2CollisionCyclicBufferEntryTbl OBJECT-TYPE
    SYNTAX      SEQUENCE OF IssL2CollisionCyclicBufferBktEntry
    ACCESS      not-accessible
    STATUS      mandatory
    DESCRIPTION 
        "This table is used to store the bucket entries of the buckets
         in which collision occurred in the past.
         
         Suppose L2 collisions occur in a single bucket only with multiple 
         combinations of MAC address and VLAN, the contents of all the 
         bins will be the same (provided the eight bucket entries 
         do not age out)
         
         Once all the buffers are filled, the index rolls over, so 
         this buffer is a cyclic buffer.
         
         This table is indexed on the buffer number and bucket entry number."
    ::= { issL2CollisionMonitoring 16 }

issL2CollisionCyclicBufferBktEntry OBJECT-TYPE
    SYNTAX      IssL2CollisionCyclicBufferBktEntry
    ACCESS      not-accessible
    STATUS      mandatory
    DESCRIPTION 
        "For each collision that has occured in the past, there exists
         an entry which contains the bucket entries of the bucket 
         in which collision occured."
    INDEX       { issL2CollisionCyclBufferEntryIndex, 
                  issL2CollisionBktEntryIndex }
    ::= { issL2CollisionCyclicBufferEntryTbl 1 }

IssL2CollisionCyclicBufferBktEntry ::= SEQUENCE {
    issL2CollisionCyclBufferEntryIndex  INTEGER,
    issL2CollisionBktEntryIndex         INTEGER,
    issL2CollisionBktId                 INTEGER,
    issL2CollisionBktVlan               INTEGER,
    issL2CollisionBktMac                MacAddress
}

issL2CollisionCyclBufferEntryIndex OBJECT-TYPE
    SYNTAX      INTEGER (1..100)
    ACCESS      not-accessible
    STATUS      mandatory
    DESCRIPTION 
        "The bin number or the interval number for the cyclic buffer 
         containing information on the previous collisions that have
         occured in the system.
            	
         ALCATEL NOTE:
         
         ACCESS :   NA           USAGE   :    NA
         PERSIST:   NA           INSRVMOD:    NA
         RANGE  :   (1..100)     DEFVALUE:    NA
         UNITS  :   NA           SPARSE  :    NA
         DESCR  :   NA"
    ::= { issL2CollisionCyclicBufferBktEntry 1 }

issL2CollisionBktEntryIndex OBJECT-TYPE
    SYNTAX      INTEGER (1..8)
    ACCESS      not-accessible
    STATUS      mandatory
    DESCRIPTION 
        "Whenever a L2 collision occurs, the collision information (VLAN Id,
         MAC Address, Bucket Id, Timestamp etc.) are stored.
         
         The bucket entries for that particular bucket are also stored. At 
         any point of collision, there will be 8 bucket entries. So, 
         for every issL2CollisionCyclBufferEntryIndex, there will be 
         8 entries of VLAN Id and MAC address. This index is referred here.
         
         ALCATEL NOTE:
         
         ACCESS :   NA           USAGE   :    NA
         PERSIST:   NA           INSRVMOD:    NA
         RANGE  :   (1..8)       DEFVALUE:    NA
         UNITS  :   NA           SPARSE  :    NA
         DESCR  :   NA"
    ::= { issL2CollisionCyclicBufferBktEntry 2 }

issL2CollisionBktId OBJECT-TYPE
    SYNTAX      INTEGER (0..4096)
    ACCESS      read-only
    STATUS      mandatory
    DESCRIPTION 
        "The bucket in which collision happened.
         
         This table stores the particular bucket entries at the point of 
         collision.
         
         The range is dependent on board type. It is (0..4096) for ECNT-E
         and ERAM-A and it is (0..2048) for other boards.
         
         ALCATEL NOTE:
         
         ACCESS :   NA           USAGE   :    NA
         PERSIST:   NA           INSRVMOD:    NA
         RANGE  :   (0..4096)    DEFVALUE:    0
         UNITS  :   NA           SPARSE  :    NA
         DESCR  :   NA"
    ::= { issL2CollisionCyclicBufferBktEntry 3 }

issL2CollisionBktVlan OBJECT-TYPE
    SYNTAX      INTEGER (0..4094)
    ACCESS      read-only
    STATUS      mandatory
    DESCRIPTION 
        "This object stores the VLAN of the bucket entry.
         
         ALCATEL NOTE:
         
         ACCESS :   NA           USAGE   :    NA
         PERSIST:   NA           INSRVMOD:    NA
         RANGE  :   (0..4094)    DEFVALUE:    0
         UNITS  :   NA           SPARSE  :    NA
         DESCR  :   NA"
    ::= { issL2CollisionCyclicBufferBktEntry 4 }

issL2CollisionBktMac OBJECT-TYPE
    SYNTAX      MacAddress
    ACCESS      read-only
    STATUS      mandatory
    DESCRIPTION 
        "This object stores the MAC Address of the bucket entry.
         
         ALCATEL NOTE:
         
         ACCESS :   NA           USAGE   :    NA
         PERSIST:   NA           INSRVMOD:    NA
         RANGE  :   NA           DEFVALUE:    NA
         UNITS  :   NA           SPARSE  :    NA
         DESCR  :   NA"
    ::= { issL2CollisionCyclicBufferBktEntry 5 }

systemReset TRAP-TYPE
    ENTERPRISE  issTraps
--     STATUS      mandatory
    DESCRIPTION 
        "In dual processor architecture (ex. ECNT-A) the systemReset
         trap signifies that switch is going to restart. This TRAP will
         be genarated when user initiates the switch restart or when
         some uncotrolled failure happens in switch.
         This is an internal trap."
    ::= 1

systemInitComplete TRAP-TYPE
    ENTERPRISE  issTraps
--     STATUS      mandatory
    DESCRIPTION 
        "systemInitComplete trap signifies that switch   
         initialization is successfully completed. This TRAP will
         be generated when switch is restarted not with 
         application reset (controlled failures) and initialized 
         successfully. This is an internal trap."
    ::= 2

applicationReset TRAP-TYPE
    ENTERPRISE  issTraps
--     STATUS      mandatory
    DESCRIPTION 
        "In dual processor architecture (ex. ECNT-A) hot application
         reset the applicationReset trap signifies that the application
         modules are going to restart while for warm application reset
         the trap signifies that application modules and BCM hardware
         are going to restart. 
         In single processor architecture (ex. ECNT-C) warm application
         reset the trap signifies that application modules and BCM
         hardware are going to restart.             
         This is an internal trap."
    ::= 3

applicationInitComplete TRAP-TYPE
    ENTERPRISE  issTraps
--     STATUS      mandatory
    DESCRIPTION 
        "In dual processor architecture (ex. ECNT-A) hot application
         reset the applicationInitComplete trap signifies that
         application modules are successfully initialized while for warm
         application reset the trap signifies that application modules
         and BCM hardware are successfully initialized.
         In single processor architecture (ex. ECNT-C) hot application
         reset the applicationInitComplete trap signifies that the
         application modules are successfully initialized while for warm
         application reset the trap signifies that application modules
         and BCM hardware are successfully initialized.
         This is an internal trap."
    ::= 4

dataBaseRestoreFail TRAP-TYPE
    ENTERPRISE  issTraps
--     STATUS      mandatory
    DESCRIPTION 
        "dataBaseRestoreFail trap signifies that data base 
         restoration is unsuccessful. This TRAP will
         be generated when configuration of switch
         as per the data base file is failed.
         This is an internal trap."
    ::= 5

dataBaseSaveComplete TRAP-TYPE
    ENTERPRISE  issTraps
--     STATUS      mandatory
    DESCRIPTION 
        "dataBaseSaveComplete trap signifies that saving of 
         data base file to (remote(NT)) location is successful.
         This TRAP will be generated when user initiated the configuration
         save and data base file is saved at remote(NT) location successfully.
         It will be also used by the standby LANX to indicate save complete.
         This is an internal trap."
    ::= 6

lanxCfgFileError TRAP-TYPE
    ENTERPRISE  issTraps
--     STATUS      mandatory
    DESCRIPTION 
        "lanxCfgFileError trap signifies inconsistencies have occurred in the lanx.cfg file .
         i.e., the syntax of the file is wrong or corrupted . Inconsistencies can arise due to many reasons such as
         invalid Port Types , non-consecutive logical port numbering , non-contiguous Port Types ,etc .
         This TRAP generated thus will be sent to the NT. This is an internal trap."
    ::= 7

ntioConfigurationError TRAP-TYPE
    ENTERPRISE  issTraps
--     STATUS      mandatory
    DESCRIPTION 
        " ntioConfigurationError trap signifies configuration failure of NTIO.
         The possible reasons include inconsistent parameters from the call table API
         or a configuration error. This TRAP generated thus will be sent to the NT.
         This is an internal trap."
    ::= 8

sdkNonRecovFailure TRAP-TYPE
    ENTERPRISE  issTraps
--     STATUS      mandatory
    DESCRIPTION 
        "sdkNonRecovFailure trap signifies sdk failure which cannot be recovered.
         This is an internal Trap."
    ::= 20

sdkRecovFailure TRAP-TYPE
    ENTERPRISE  issTraps
--     STATUS      mandatory
    DESCRIPTION 
        "sdkRecovFailure trap signifies sdk failure raised due to sdk failure after it exceeds the threshold counter.
         This is an internal Trap."
    ::= 21

dynamicDataSyncFailure TRAP-TYPE
    ENTERPRISE  issTraps
    VARIABLES   { issSyncFailureCause }
--     STATUS      mandatory
    DESCRIPTION 
        "dynamicDataSyncFailure trap signifies dynamic data synchronization failed.
         This is an internal Trap."
    ::= 22

bcmFailure TRAP-TYPE
    ENTERPRISE  issTraps
--     STATUS      mandatory
    DESCRIPTION 
        "bcmFailure trap signifies the hardware failure.
         This is an internal Trap."
    ::= 23

staticDataSyncFailure TRAP-TYPE
    ENTERPRISE  issTraps
    VARIABLES   { issSyncFailureCause }
--     STATUS      mandatory
    DESCRIPTION 
        "staticDataSyncFailure trap signifies static data sync failure.
         This is an internal Trap."
    ::= 24

peerCommFailure TRAP-TYPE
    ENTERPRISE  issTraps
--     STATUS      mandatory
    DESCRIPTION 
        "peerCommFailure trap signifies that the peer LANX is down.
         This is an internal Trap."
    ::= 25

dynamicDataSynced TRAP-TYPE
    ENTERPRISE  issTraps
--     STATUS      mandatory
    DESCRIPTION 
        "lanxMovedToHotStandby trap signifies the state of the standby 
         lanx has changed from cold to hot standby.
         This is an internal Trap."
    ::= 26

switchoverComplete TRAP-TYPE
    ENTERPRISE  issTraps
--     STATUS      mandatory
    DESCRIPTION 
        "switchoverComplete trap signifies the completion of switchover in lanx before going for HotReset.
         This is an internal Trap."
    ::= 27

intermediateConfigSaveAbort TRAP-TYPE
    ENTERPRISE  issTraps
--     STATUS      mandatory
    DESCRIPTION 
        "intermediateConfigSaveAbort trap signifies the abort of IntermediateConfigSave process 
         upon SNMPSET request in Active/Standby Lanx. This is an internal Trap."
    ::= 28

snmpQueueFlushed TRAP-TYPE
    ENTERPRISE  issTraps
--     STATUS      mandatory
    DESCRIPTION 
        "snmpQueueFlushed trap signifies the dropping of any pending SNMP packets after SwitchOver trigger
         in Standby Lanx. This is an internal Trap."
    ::= 29

dataBaseChange TRAP-TYPE
    ENTERPRISE  issTraps
--     STATUS      mandatory
    DESCRIPTION 
        "dataBaseChange trap signifies that there is a change 
         in LANX configuration after a database save.
         This TRAP will be generated for the first change after the 
          database save. This is an internal Trap."
    ::= 50

issPCCPGroupUp TRAP-TYPE
    ENTERPRISE  issPCCPTraps
    VARIABLES   { issPCCPGroupID, issPCCPPingCheckDestIPAdress, 
                  issPCCPPingCheckInterval }
--     STATUS      mandatory
    DESCRIPTION 
        "Generated when Path Connectivity Check & Protection Group Switchover happens."
    ::= 1

issPCCPGroupDown TRAP-TYPE
    ENTERPRISE  issPCCPTraps
    VARIABLES   { issPCCPGroupID }
--     STATUS      mandatory
    DESCRIPTION 
        "Generated when Path Connectivity Check & Protection Group is Operationally Down."
    ::= 2

END -- end of module ISS-MIB.
