--
-- This SMIv1 module has been generated by smidump 0.4.8. Do not edit.
--

IF-MIB DEFINITIONS ::= BEGIN

IMPORTS
    IANAifType
        FROM IANAifType-MIB
    OBJECT-TYPE
        FROM RFC-1212
    TRAP-TYPE
        FROM RFC-1215
    Counter, Gauge, TimeTicks, snmpModules
        FROM RFC1155-SMI
    mib-2
        FROM RFC1213-MIB
    DisplayString, PhysAddress, RowStatus, TimeStamp, TruthValue
        FROM SNMPv2-TC;

ifMIB OBJECT IDENTIFIER
    ::= { mib-2 31 }

-- ifMIB MODULE-IDENTITY
--     LAST-UPDATED "199611031355Z"
--     ORGANIZATION 
--         "IETF Interfaces MIB Working Group"
--     CONTACT-INFO 
--         "   Keith McCloghrie
--          
--          Cisco Systems, Inc.
--          
--          170 West Tasman Drive
--          
--          San Jose, CA  95134-1706
--          
--          US
--          
--          
--          
--          408-526-5260
--          
--          kzm@cisco.com"
--     DESCRIPTION 
--         "The MIB module to describe generic objects for
--          
--          network interface sub-layers.  This MIB is an updated
--          
--          version of MIB-II's ifTable, and incorporates the
--          
--          extensions defined in RFC 1229."
--     REVISION    "199611031355Z"
--     DESCRIPTION 
--         "Revisions made by the Interfaces MIB WG."
--     ::= { mib-2 31 }


OwnerString ::=
    OCTET STRING (SIZE(0..255))

-- OwnerString ::= TEXTUAL-CONVENTION
--     DISPLAY-HINT "255a"
--     STATUS      mandatory
--     DESCRIPTION 
--         "This data type is used to model an administratively
--          
--          assigned name of the owner of a resource.  This
--          
--          information is taken from the NVT ASCII character set.
--          
--          It is suggested that this name contain one or more of
--          
--          the following: ASCII form of the manager station's
--          
--          transport address, management station name (e.g.,
--          
--          domain name), network management personnel's name,
--          
--          location, or phone number.  In some cases the agent
--          
--          itself will be the owner of an entry.  In these cases,
--          
--          this string shall be set to a string starting with
--          
--          'agent'."
--     SYNTAX      OCTET STRING (SIZE(0..255))

InterfaceIndex ::=
    INTEGER (1..2147483647)

-- InterfaceIndex ::= TEXTUAL-CONVENTION
--     DISPLAY-HINT "d"
--     STATUS      mandatory
--     DESCRIPTION 
--         "A unique value, greater than zero, for each interface
--          
--          or interface sub-layer in the managed system.  It is
--          
--          recommended that values are assigned contiguously
--          
--          starting from 1.  The value for each interface sub-
--          
--          layer must remain constant at least from one re-
--          
--          initialization of the entity's network management
--          
--          system to the next re-initialization."
--     SYNTAX      INTEGER (1..2147483647)

InterfaceIndexOrZero ::=
    INTEGER (0..2147483647)

-- InterfaceIndexOrZero ::= TEXTUAL-CONVENTION
--     DISPLAY-HINT "d"
--     STATUS      mandatory
--     DESCRIPTION 
--         "This textual convention is an extension of the
--          
--          InterfaceIndex convention.  The latter defines a
--          
--          greater than zero value used to identify an interface
--          
--          or interface sub-layer in the managed system.  This
--          
--          extension permits the additional value of zero.  the
--          
--          value zero is object-specific and must therefore be
--          
--          defined as part of the description of any object which
--          
--          uses this syntax.  Examples of the usage of zero might
--          
--          include situations where interface was unknown, or
--          
--          when none or all interfaces need to be referenced."
--     SYNTAX      INTEGER (0..2147483647)

interfaces OBJECT IDENTIFIER
    ::= { mib-2 2 }

ifNumber OBJECT-TYPE
    SYNTAX      INTEGER
    ACCESS      read-only
    STATUS      mandatory
    DESCRIPTION 
        "The number of network interfaces (regardless of their
         
         current state) present on this system.
         
         	ALCATEL NOTE:
         
         ACCESS:      NA           USAGE:       NA
         
         PERSIST:     NO           INSRVMOD:    NA
         
         RANGE:       DEP          DEFVALUE:    0
         
         UNITS:       NA           SPARSE:      NA
         
         DESCR:       DEP(RANGE): The range is from 0 to the (total number of IP interfaces in the system 
         
         		  + maximum value of number of physical interfaces available in the system). 
         
         		 The maximum number of physical interfaces is obtained from the object issSystemNumberOfPorts in fsiss.mib. 
         
         		 The total number of IP interfaces in the system is obtained from the object fsVrfMaxIpInterfaces in fsvrf.mib."
    ::= { interfaces 1 }

ifTable OBJECT-TYPE
    SYNTAX      SEQUENCE OF IfEntry
    ACCESS      not-accessible
    STATUS      mandatory
    DESCRIPTION 
        "A list of interface entries.  The number of entries
         
         is given by the value of ifNumber.
         
         	ALCATEL NOTE:
         
         TABLESIZE: DEP
         
         DESCR:  DEP(TABLESIZE) The range of the table is the maximum number of 
         
         	            physical ports + total number of IP interfaces in the system.
         
         		    The number of ports can be got from the object issSystemNumberOfPorts in fsiss.mib.
         
         		    The total number of IP interfaces in the is obtained from fsVrfMaxIpInterfaces in fsvrf.mib."
    ::= { interfaces 2 }

ifEntry OBJECT-TYPE
    SYNTAX      IfEntry
    ACCESS      not-accessible
    STATUS      mandatory
    DESCRIPTION 
        "An entry containing management information applicable
         
         to a particular interface.
         
         Row creation : Entries for Maximum number of physical interfaces (obtained from issSystemNumberOfPorts in fsiss.mib)
         
         		and 2 logical interfaces (vlan 4093 & 4094) will be created during system startup. 
         
         		Other entries shall be created in one step by a set-request with all necessary parameter values 
         
         		and  ifMainRowStatus set to createAndGo(4).
         
         Row deletion : The default entries for Maximum number of physical interfaces (obtained from issSystemNumberOfPorts in fsiss.mib)
         
         		and 2 logical interfaces (vlan 4093 & 4094) cannot be deleted. 
         
         		Other entries shall be deleted by setting the ifMainRowStatus of the specific entry to destroy(6)
         
         Index usage : the index is the if index.
         
         Note that entries will be presented to the SNMP manager in full
         
         lexicographical order :  sorted on if index."
    INDEX       { ifIndex }
    ::= { ifTable 1 }

IfEntry ::= SEQUENCE {
    ifIndex             InterfaceIndex,
    ifDescr             DisplayString,
    ifType              IANAifType,
    ifMtu               INTEGER,
    ifSpeed             Gauge,
    ifPhysAddress       PhysAddress,
    ifAdminStatus       INTEGER,
    ifOperStatus        INTEGER,
    ifLastChange        TimeTicks,
    ifInOctets          Counter,
    ifInUcastPkts       Counter,
    ifInNUcastPkts      Counter,
    ifInDiscards        Counter,
    ifInErrors          Counter,
    ifInUnknownProtos   Counter,
    ifOutOctets         Counter,
    ifOutUcastPkts      Counter,
    ifOutNUcastPkts     Counter,
    ifOutDiscards       Counter,
    ifOutErrors         Counter,
    ifOutQLen           Gauge,
    ifSpecific          OBJECT IDENTIFIER
}

ifIndex OBJECT-TYPE
    SYNTAX      InterfaceIndex
    ACCESS      read-only
    STATUS      mandatory
    DESCRIPTION 
        "A unique value, greater than zero, for each
         
         interface.  It is recommended that values are assigned
         
         contiguously starting from 1.  The value for each
         
         interface sub-layer must remain constant at least from
         
         one re-initialization of the entity's network
         
         management system to the next re-initialization.
         
         	ALCATEL NOTE:
         
         ACCESS:      NA           USAGE:       NA
         
         PERSIST:     NO           INSRVMOD:    NA
         
         RANGE:       DEP          DEFVALUE:    NA
         
         UNITS:       NA           SPARSE:      NO
         
         DESCR:       DEP(RANGE): The range is from 1 to the (total number of IP interfaces in the system 
         
         		  + maximum value of number of physical interfaces available in the system). 
         
         		 The maximum number of physical interfaces is obtained from the object issSystemNumberOfPorts in fsiss.mib. 
         
         		 The total number of IP interfaces in the system is obtained from the object fsVrfMaxIpInterfaces in fsvrf.mib
         
                   The IP interfaces will start from 65536 to the total number of IP interfaces in the system
         
                   The indices 81920 & 81921 are reserved for vlan 4094 & 4093 respectively."
    ::= { ifEntry 1 }

ifDescr OBJECT-TYPE
    SYNTAX      DisplayString
    ACCESS      read-only
    STATUS      mandatory
    DESCRIPTION 
        "A textual string containing information about the
         
         interface.  This string should include the name of the
         
         manufacturer, the product name and the version of the
         
         interface hardware/software.
         
         	ALCATEL NOTE:
         
         ACCESS:      NA           USAGE:       NA
         
         PERSIST:     NO           INSRVMOD:    NA
         
         RANGE:       NA           DEFVALUE:    'Ethernet Interface'
         
         UNITS:       NA           SPARSE:      NO
         
         DESCR:       NA"
    ::= { ifEntry 2 }

ifType OBJECT-TYPE
    SYNTAX      IANAifType
    ACCESS      read-only
    STATUS      mandatory
    DESCRIPTION 
        "The type of interface.  Additional values for ifType
         
         are assigned by the Internet Assigned Numbers
         
         Authority (IANA), through updating the syntax of the
         
         IANAifType textual convention.
         
         	ALCATEL NOTE:
         
         ACCESS:      NA           USAGE:       NA
         
         PERSIST:     NO           INSRVMOD:    NA
         
         RANGE:       NA           DEFVALUE:    'ethernetCsmacd'
         
         UNITS:       NA           SPARSE:      NO
         
         DESCR:       NA"
    ::= { ifEntry 3 }

ifMtu OBJECT-TYPE
    SYNTAX      INTEGER
    ACCESS      read-only
    STATUS      mandatory
    DESCRIPTION 
        "The size of the largest packet which can be
         
         sent/received on the interface, specified in octets.
         
         For interfaces that are used for transmitting network
         
         datagrams, this is the size of the largest network
         
         datagram that can be sent on the interface.
         
         	ALCATEL NOTE:
         
         ACCESS:      NA           USAGE:       NA
         
         PERSIST:     NO           INSRVMOD:    NA
         
         RANGE:       NA           DEFVALUE:    1500
         
         UNITS:       bytes        SPARSE:      NO
         
         DESCR:       NA"
    ::= { ifEntry 4 }

ifSpeed OBJECT-TYPE
    SYNTAX      Gauge
    ACCESS      read-only
    STATUS      mandatory
    DESCRIPTION 
        "An estimate of the interface's current bandwidth in
         
         bits per second.  For interfaces which do not vary in
         
         bandwidth or for those where no accurate estimation
         
         can be made, this object should contain the nominal
         
         bandwidth.  If the bandwidth of the interface is
         
         greater than the maximum value reportable by this
         
         object then this object should report its maximum
         
         value (4,294,967,295) and ifHighSpeed must be used to
         
         report the interace's speed.  For a sub-layer which
         
         has no concept of bandwidth, this object should be
         
         zero.
         
         	ALCATEL NOTE:
         
         ACCESS:      NA           USAGE:       NA
         
         PERSIST:     NO           INSRVMOD:    NA
         
         RANGE:       NA           DEFVALUE:    1000000000
         
         UNITS:       bits/sec     SPARSE:      NO
         
         DESCR:       NA"
    ::= { ifEntry 5 }

ifPhysAddress OBJECT-TYPE
    SYNTAX      PhysAddress
    ACCESS      read-only
    STATUS      mandatory
    DESCRIPTION 
        "The interface's address at its protocol sub-layer.
         
         For example, for an 802.x interface, this object
         
         normally contains a MAC address.  The interface's
         
         media-specific MIB must define the bit and byte
         
         ordering and the format of the value of this object.
         
         For interfaces which do not have such an address
         
         (e.g., a serial line), this object should contain an
         
         octet string of zero length.
         
         	ALCATEL NOTE:
         
         ACCESS:      NA           USAGE:       NA
         
         PERSIST:     NO           INSRVMOD:    NA
         
         RANGE:       NA           DEFVALUE:    NA
         
         UNITS:       NA           SPARSE:      NO
         
         DESCR:       NA"
    ::= { ifEntry 6 }

ifAdminStatus OBJECT-TYPE
    SYNTAX      INTEGER { up(1), down(2), testing(3) }
    ACCESS      read-write
    STATUS      mandatory
    DESCRIPTION 
        "The desired state of the interface.  The testing(3)
         
         state indicates that no operational packets can be
         
         passed.  When a managed system initializes, all
         
         interfaces start with ifAdminStatus in the down(2)
         
         state.  As a result of either explicit management
         
         action or per configuration information retained by
         
         the managed system, ifAdminStatus is then changed to
         
         either the up(1) or testing(3) states (or remains in
         
         the down(2) state).
         
         	ALCATEL NOTE:
         
         ACCESS:      NA           USAGE:       NA
         
         PERSIST:     NO           INSRVMOD:    YES
         
         RANGE:       1,2,3,4      DEFVALUE:    up
         
         UNITS:       NA           SPARSE:      NO
         
         DESCR:       NA"
    ::= { ifEntry 7 }

ifOperStatus OBJECT-TYPE
    SYNTAX      INTEGER { up(1), down(2), testing(3), unknown(4), 
                    dormant(5), notPresent(6), lowerLayerDown(7) }
    ACCESS      read-only
    STATUS      mandatory
    DESCRIPTION 
        "The current operational state of the interface.  The
         
         testing(3) state indicates that no operational packets
         
         can be passed.  If ifAdminStatus is down(2) then
         
         ifOperStatus should be down(2).  If ifAdminStatus is
         
         changed to up(1) then ifOperStatus should change to
         
         up(1) if the interface is ready to transmit and
         
         receive network traffic; it should change to
         
         dormant(5) if the interface is waiting for external
         
         actions (such as a serial line waiting for an incoming
         
         connection); it should remain in the down(2) state if
         
         and only if there is a fault that prevents it from
         
         going to the up(1) state; it should remain in the
         
         notPresent(6) state if the interface has missing
         
         (typically, hardware) components.
         
         	ALCATEL NOTE:
         
         ACCESS:      NA           USAGE:       NA
         
         PERSIST:     NO           INSRVMOD:    NA
         
         RANGE:       NA           DEFVALUE:    down
         
         UNITS:       NA           SPARSE:      NO
         
         DESCR:       NA"
    ::= { ifEntry 8 }

ifLastChange OBJECT-TYPE
    SYNTAX      TimeTicks
    ACCESS      read-only
    STATUS      mandatory
    DESCRIPTION 
        "The value of sysUpTime at the time the interface
         
         entered its current operational state.  If the current
         
         state was entered prior to the last re-initialization
         
         of the local network management subsystem, then this
         
         object contains a zero value.
         
         	ALCATEL NOTE:
         
         ACCESS:      NA           USAGE:       NA
         
         PERSIST:     NO           INSRVMOD:    NA
         
         RANGE:       NA           DEFVALUE:    NA
         
         UNITS:       TimeTicks    SPARSE:      NO
         
         DESCR:       NA"
    ::= { ifEntry 9 }

ifInOctets OBJECT-TYPE
    SYNTAX      Counter
    ACCESS      read-only
    STATUS      mandatory
    DESCRIPTION 
        "The total number of octets received on the interface,
         
         including framing characters.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NA           INSRVMOD:    NA
         
         RANGE:       NA           DEFVALUE:    NA 
         
         UNITS:       NA           SPARSE:      NA
         
         DESCR:       This object is not used by Alcatel"
    ::= { ifEntry 10 }

ifInUcastPkts OBJECT-TYPE
    SYNTAX      Counter
    ACCESS      read-only
    STATUS      mandatory
    DESCRIPTION 
        "The number of packets, delivered by this sub-layer to
         
         a higher (sub-)layer, which were not addressed to a
         
         multicast or broadcast address at this sub-layer.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NA           INSRVMOD:    NA
         
         RANGE:       NA           DEFVALUE:    NA
         
         UNITS:       NA           SPARSE:      NA
         
         DESCR:       This object is not used by Alcatel"
    ::= { ifEntry 11 }

ifInNUcastPkts OBJECT-TYPE
    SYNTAX      Counter
    ACCESS      read-only
    STATUS      deprecated
    DESCRIPTION 
        "The number of packets, delivered by this sub-layer to
         
         a higher (sub-)layer, which were addressed to a
         
         multicast or broadcast address at this sub-layer.
         
         
         
         Discontinuities in the value of this counter can occur
         
         at re-initialization of the management system, and at
         
         other times as indicated by the value of
         
         ifCounterDiscontinuityTime.
         
         
         
         This object is deprecated in favour of
         
         ifInMulticastPkts and ifInBroadcastPkts.
         
         	ALCATEL NOTE:
         
         ACCESS:      NA           USAGE:       NA
         
         PERSIST:     NA           INSRVMOD:    NA
         
         RANGE:       NA           DEFVALUE:    NA
         
         UNITS:       NA           SPARSE:      NA
         
         DESCR:       This object is not used by Alcatel"
    ::= { ifEntry 12 }

ifInDiscards OBJECT-TYPE
    SYNTAX      Counter
    ACCESS      read-only
    STATUS      mandatory
    DESCRIPTION 
        "The number of inbound packets which were chosen to be
         
         discarded even though no errors had been detected to
         
         prevent their being deliverable to a higher-layer
         
         protocol.  One possible reason for discarding such a
         
         packet could be to free up buffer space.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       packets      SPARSE:      NO
         
         DESCR:       NA"
    ::= { ifEntry 13 }

ifInErrors OBJECT-TYPE
    SYNTAX      Counter
    ACCESS      read-only
    STATUS      mandatory
    DESCRIPTION 
        "For packet-oriented interfaces, the number of inbound
         
         packets that contained errors preventing them from
         
         being deliverable to a higher-layer protocol.  For
         
         character-oriented or fixed-length interfaces, the
         
         number of inbound transmission units that contained
         
         errors preventing them from being deliverable to a
         
         higher-layer protocol.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       packets      SPARSE:      NO
         
         DESCR:       NA"
    ::= { ifEntry 14 }

ifInUnknownProtos OBJECT-TYPE
    SYNTAX      Counter
    ACCESS      read-only
    STATUS      mandatory
    DESCRIPTION 
        "For packet-oriented interfaces, the number of packets
         
         received via the interface which were discarded
         
         because of an unknown or unsupported protocol.  For
         
         character-oriented or fixed-length interfaces that
         
         support protocol multiplexing the number of
         
         transmission units received via the interface which
         
         were discarded because of an unknown or unsupported
         
         protocol.  For any interface that does not support
         
         protocol multiplexing, this counter will always be 0.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       packets      SPARSE:      NO
         
         DESCR:       NA"
    ::= { ifEntry 15 }

ifOutOctets OBJECT-TYPE
    SYNTAX      Counter
    ACCESS      read-only
    STATUS      mandatory
    DESCRIPTION 
        "The total number of octets transmitted out of the
         
         interface, including framing characters.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NA           INSRVMOD:    NA
         
         RANGE:       NA           DEFVALUE:    NA
         
         UNITS:       NA           SPARSE:      NA
         
         DESCR:       This object is not used by Alcatel"
    ::= { ifEntry 16 }

ifOutUcastPkts OBJECT-TYPE
    SYNTAX      Counter
    ACCESS      read-only
    STATUS      mandatory
    DESCRIPTION 
        "The total number of packets that higher-level
         
         protocols requested be transmitted, and which were not
         
         addressed to a multicast or broadcast address at this
         
         sub-layer, including those that were discarded or not
         
         sent.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NA           INSRVMOD:    NA
         
         RANGE:       NA           DEFVALUE:    NA
         
         UNITS:       NA           SPARSE:      NA
         
         DESCR:       This object is not used by Alcatel"
    ::= { ifEntry 17 }

ifOutNUcastPkts OBJECT-TYPE
    SYNTAX      Counter
    ACCESS      read-only
    STATUS      deprecated
    DESCRIPTION 
        "The total number of packets that higher-level
         
         protocols requested be transmitted, and which were
         
         addressed to a multicast or broadcast address at this
         
         sub-layer, including those that were discarded or not
         
         sent.
         
         
         
         Discontinuities in the value of this counter can occur
         
         at re-initialization of the management system, and at
         
         other times as indicated by the value of
         
         ifCounterDiscontinuityTime.
         
         
         
         This object is deprecated in favour of
         
         ifOutMulticastPkts and ifOutBroadcastPkts.
         
         	ALCATEL NOTE:
         
         ACCESS:      NA           USAGE:       NA
         
         PERSIST:     NA           INSRVMOD:    NA
         
         RANGE:       NA           DEFVALUE:    NA
         
         UNITS:       NA           SPARSE:      NA
         
         DESCR:       This object is not used by Alcatel"
    ::= { ifEntry 18 }

ifOutDiscards OBJECT-TYPE
    SYNTAX      Counter
    ACCESS      read-only
    STATUS      mandatory
    DESCRIPTION 
        "The number of outbound packets which were chosen to
         
         be discarded even though no errors had been detected
         
         to prevent their being transmitted.  One possible
         
         reason for discarding such a packet could be to free
         
         up buffer space.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       packets      SPARSE:      NO
         
         DESCR:       NA"
    ::= { ifEntry 19 }

ifOutErrors OBJECT-TYPE
    SYNTAX      Counter
    ACCESS      read-only
    STATUS      mandatory
    DESCRIPTION 
        "For packet-oriented interfaces, the number of
         
         outbound packets that could not be transmitted because
         
         of errors.  For character-oriented or fixed-length
         
         interfaces, the number of outbound transmission units
         
         that could not be transmitted because of errors.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       packets      SPARSE:      NO
         
         DESCR:       NA"
    ::= { ifEntry 20 }

ifOutQLen OBJECT-TYPE
    SYNTAX      Gauge
    ACCESS      read-only
    STATUS      deprecated
    DESCRIPTION 
        "The length of the output packet queue (in packets).
         
         ALCATEL NOTE:
         
            ACCESS:      NA           USAGE:       NA
         
            PERSIST:     NO           INSRVMOD:    NA
         
            RANGE:       NA           DEFVALUE:    0
         
            UNITS:       packets      SPARSE:      NO
         
            DESCR:       NA"
    ::= { ifEntry 21 }

ifSpecific OBJECT-TYPE
    SYNTAX      OBJECT IDENTIFIER
    ACCESS      read-only
    STATUS      deprecated
    DESCRIPTION 
        "A reference to MIB definitions specific to the
         
         particular media being used to realize the interface.
         
         It is recommended that this value point to an instance
         
         of a MIB object in the media-specific MIB, i.e., that
         
         this object have the semantics associated with the
         
         InstancePointer textual convention defined in RFC
         
         1903.  In fact, it is recommended that the media-
         
         specific MIB specify what value ifSpecific should/can
         
         take for values of ifType.  If no MIB definitions
         
         specific to the particular media are available, the
         
         value should be set to the OBJECT IDENTIFIER { 0 0 }.
         
         	ALCATEL NOTE:
         
         ACCESS:      NA           USAGE:       NA
         
         PERSIST:     NO           INSRVMOD:    NA
         
         RANGE:       NA           DEFVALUE:    .0.0
         
         UNITS:       NA           SPARSE:      NO
         
         DESCR:       NA"
    ::= { ifEntry 22 }

ifMIBObjects OBJECT IDENTIFIER
    ::= { ifMIB 1 }

ifXTable OBJECT-TYPE
    SYNTAX      SEQUENCE OF IfXEntry
    ACCESS      not-accessible
    STATUS      mandatory
    DESCRIPTION 
        "A list of interface entries.  The number of entries
         
         is given by the value of ifNumber.  This table
         
         contains additional objects for the interface table.
         
         	ALCATEL NOTE:
         
         		TABLESIZE: DEP 
         
         	DESCR:  DEP(TABLESIZE) The range of the table is the maximum number of 
         
         	            physical ports + total number of IP interfaces in the system.
         
         		    The number of ports can be got from the object issSystemNumberOfPorts in fsiss.mib.
         
         		    The total number of IP interfaces in the is obtained from fsVrfMaxIpInterfaces in fsvrf.mib."
    ::= { ifMIBObjects 1 }

ifXEntry OBJECT-TYPE
    SYNTAX      IfXEntry
    ACCESS      not-accessible
    STATUS      mandatory
    DESCRIPTION 
        "An entry containing additional management information
         
         applicable to a particular interface.
         
         Row creation : Entries for Maximum number of physical interfaces (obtained from issSystemNumberOfPorts in fsiss.mib)
         
         		and 2 logical interfaces (vlan 4093 & 4094) will be created during system startup. 
         
         		Other entries shall be created in one step by a set-request with all necessary parameter values 
         
         		and  ifMainRowStatus set to createAndGo(4).
         
         Row deletion : The default entries for Maximum number of physical interfaces (obtained from issSystemNumberOfPorts in fsiss.mib)
         
         		and 2 logical interfaces (vlan 4093 & 4094) cannot be deleted. 
         
         		Other entries shall be deleted by setting the ifMainRowStatus of the specific entry to destroy(6)
         
         Index usage : the index is the if index.
         
         Note that entries will be presented to the SNMP manager in full
         
         lexicographical order :  sorted on if index."
    INDEX       { ifIndex }
--     AUGMENTS    { ifEntry }
    ::= { ifXTable 1 }

IfXEntry ::= SEQUENCE {
    ifName                      DisplayString,
    ifInMulticastPkts           Counter,
    ifInBroadcastPkts           Counter,
    ifOutMulticastPkts          Counter,
    ifOutBroadcastPkts          Counter,
    ifHCInOctets                Counter,
    ifHCInUcastPkts             Counter,
    ifHCInMulticastPkts         Counter,
    ifHCInBroadcastPkts         Counter,
    ifHCOutOctets               Counter,
    ifHCOutUcastPkts            Counter,
    ifHCOutMulticastPkts        Counter,
    ifHCOutBroadcastPkts        Counter,
    ifLinkUpDownTrapEnable      INTEGER,
    ifHighSpeed                 Gauge,
    ifPromiscuousMode           TruthValue,
    ifConnectorPresent          TruthValue,
    ifAlias                     DisplayString,
    ifCounterDiscontinuityTime  TimeStamp
}

ifName OBJECT-TYPE
    SYNTAX      DisplayString
    ACCESS      read-only
    STATUS      mandatory
    DESCRIPTION 
        "The textual name of the interface.  The value of this
         
         object should be the name of the interface as assigned
         
         by the local device and should be suitable for use in
         
         commands entered at the device's `console'.  This
         
         might be a text name, such as `le0' or a simple port
         
         number, such as `1', depending on the interface naming
         
         syntax of the device.  If several entries in the
         
         ifTable together represent a single interface as named
         
         by the device, then each will have the same value of
         
         ifName.  Note that for an agent which responds to SNMP
         
         queries concerning an interface on some other
         
         (proxied) device, then the value of ifName for such an
         
         interface is the proxied device's local name for it.
         
         
         
         If there is no local name, or this object is otherwise
         
         not applicable, then this object contains a zero-
         
         length string.
         
         	ALCATEL NOTE:
         
         ACCESS:      NA           USAGE:       NA
         
         PERSIST:     NO           INSRVMOD:    NA
         
         RANGE:       NA           DEFVALUE:    '\0'
         
         UNITS:       NA           SPARSE:      NO
         
         DESCR:       NA"
    ::= { ifXEntry 1 }

ifInMulticastPkts OBJECT-TYPE
    SYNTAX      Counter
    ACCESS      read-only
    STATUS      mandatory
    DESCRIPTION 
        "The number of packets, delivered by this sub-layer to
         
         a higher (sub-)layer, which were addressed to a
         
         multicast address at this sub-layer.  For a MAC layer
         
         protocol, this includes both Group and Functional
         
         addresses.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       packets      SPARSE:      NO
         
         DESCR:       NA"
    ::= { ifXEntry 2 }

ifInBroadcastPkts OBJECT-TYPE
    SYNTAX      Counter
    ACCESS      read-only
    STATUS      mandatory
    DESCRIPTION 
        "The number of packets, delivered by this sub-layer to
         
         a higher (sub-)layer, which were addressed to a
         
         broadcast address at this sub-layer.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       packets      SPARSE:      NO
         
         DESCR:       NA"
    ::= { ifXEntry 3 }

ifOutMulticastPkts OBJECT-TYPE
    SYNTAX      Counter
    ACCESS      read-only
    STATUS      mandatory
    DESCRIPTION 
        "The total number of packets that higher-level
         
         protocols requested be transmitted, and which were
         
         addressed to a multicast address at this sub-layer,
         
         including those that were discarded or not sent.  For
         
         a MAC layer protocol, this includes both Group and
         
         Functional addresses.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       packets      SPARSE:      NO
         
         DESCR:       NA"
    ::= { ifXEntry 4 }

ifOutBroadcastPkts OBJECT-TYPE
    SYNTAX      Counter
    ACCESS      read-only
    STATUS      mandatory
    DESCRIPTION 
        "The total number of packets that higher-level
         
         protocols requested be transmitted, and which were
         
         addressed to a broadcast address at this sub-layer,
         
         including those that were discarded or not sent.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       packets      SPARSE:      NO
         
         DESCR:       NA"
    ::= { ifXEntry 5 }

ifHCInOctets OBJECT-TYPE
    SYNTAX      Counter
    ACCESS      read-only
    STATUS      mandatory
    DESCRIPTION 
        "The total number of octets received on the interface,
         
         including framing characters.  This object is a 64-bit
         
         version of ifInOctets.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       octets       SPARSE:      NO
         
         DESCR:       NA"
    ::= { ifXEntry 6 }

ifHCInUcastPkts OBJECT-TYPE
    SYNTAX      Counter
    ACCESS      read-only
    STATUS      mandatory
    DESCRIPTION 
        "The number of packets, delivered by this sub-layer to
         
         a higher (sub-)layer, which were not addressed to a
         
         multicast or broadcast address at this sub-layer.
         
         This object is a 64-bit version of ifInUcastPkts.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       packets      SPARSE:      NO
         
         DESCR:       NA"
    ::= { ifXEntry 7 }

ifHCInMulticastPkts OBJECT-TYPE
    SYNTAX      Counter
    ACCESS      read-only
    STATUS      mandatory
    DESCRIPTION 
        "The number of packets, delivered by this sub-layer to
         
         a higher (sub-)layer, which were addressed to a
         
         multicast address at this sub-layer.  For a MAC layer
         
         protocol, this includes both Group and Functional
         
         addresses.  This object is a 64-bit version of
         
         ifInMulticastPkts.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       packets      SPARSE:      NO
         
         DESCR:       NA"
    ::= { ifXEntry 8 }

ifHCInBroadcastPkts OBJECT-TYPE
    SYNTAX      Counter
    ACCESS      read-only
    STATUS      mandatory
    DESCRIPTION 
        "The number of packets, delivered by this sub-layer to
         
         a higher (sub-)layer, which were addressed to a
         
         broadcast address at this sub-layer.  This object is a
         
         64-bit version of ifInBroadcastPkts.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       packets      SPARSE:      NO
         
         DESCR:       NA"
    ::= { ifXEntry 9 }

ifHCOutOctets OBJECT-TYPE
    SYNTAX      Counter
    ACCESS      read-only
    STATUS      mandatory
    DESCRIPTION 
        "The total number of octets transmitted out of the
         
         interface, including framing characters.  This object
         
         is a 64-bit version of ifOutOctets.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       octets       SPARSE:      NO
         
         DESCR:       NA"
    ::= { ifXEntry 10 }

ifHCOutUcastPkts OBJECT-TYPE
    SYNTAX      Counter
    ACCESS      read-only
    STATUS      mandatory
    DESCRIPTION 
        "The total number of packets that higher-level
         
         protocols requested be transmitted, and which were not
         
         addressed to a multicast or broadcast address at this
         
         sub-layer, including those that were discarded or not
         
         sent.  This object is a 64-bit version of
         
         ifOutUcastPkts.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       packets      SPARSE:      NO
         
         DESCR:       NA"
    ::= { ifXEntry 11 }

ifHCOutMulticastPkts OBJECT-TYPE
    SYNTAX      Counter
    ACCESS      read-only
    STATUS      mandatory
    DESCRIPTION 
        "The total number of packets that higher-level
         
         protocols requested be transmitted, and which were
         
         addressed to a multicast address at this sub-layer,
         
         including those that were discarded or not sent.  For
         
         a MAC layer protocol, this includes both Group and
         
         Functional addresses.  This object is a 64-bit version
         
         of ifOutMulticastPkts.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       packets      SPARSE:      NO
         
         DESCR:       NA"
    ::= { ifXEntry 12 }

ifHCOutBroadcastPkts OBJECT-TYPE
    SYNTAX      Counter
    ACCESS      read-only
    STATUS      mandatory
    DESCRIPTION 
        "The total number of packets that higher-level
         
         protocols requested be transmitted, and which were
         
         addressed to a broadcast address at this sub-layer,
         
         including those that were discarded or not sent.  This
         
         object is a 64-bit version of ifOutBroadcastPkts.
         
         
         
         Discontinuities in the value of this counter can occur
         
         at re-initialization of the management system, and at
         
         other times as indicated by the value of
         
         ifCounterDiscontinuityTime.
         
         	ALCATEL NOTE:
         
         ACCESS:      NA           USAGE:       NA
         
         PERSIST:     NO           INSRVMOD:    NA
         
         RANGE:       NA           DEFVALUE:    0
         
         UNITS:       packets      SPARSE:      NO
         
         DESCR:       NA"
    ::= { ifXEntry 13 }

ifLinkUpDownTrapEnable OBJECT-TYPE
    SYNTAX      INTEGER { enabled(1), disabled(2) }
    ACCESS      read-write
    STATUS      mandatory
    DESCRIPTION 
        "Indicates whether linkUp/linkDown traps should be
         
         generated for this interface.
         
         
         
         By default, this object should have the value
         
         enabled(1) for interfaces which do not operate on
         
         'top' of any other interface (as defined in the
         
         ifStackTable), and disabled(2) otherwise.
         
         	ALCATEL NOTE:
         
         ACCESS:      NA           USAGE:       NA
         
         PERSIST:     YES          INSRVMOD:    YES
         
         RANGE:       NA           DEFVALUE:    enabled
         
         UNITS:       NA           SPARSE:      NO
         
         DESCR:       NA"
    ::= { ifXEntry 14 }

ifHighSpeed OBJECT-TYPE
    SYNTAX      Gauge
    ACCESS      read-only
    STATUS      mandatory
    DESCRIPTION 
        "An estimate of the interface's current bandwidth in
         
         units of 1,000,000 bits per second.  If this object
         
         reports a value of `n' then the speed of the interface
         
         is somewhere in the range of `n-500,000' to
         
         `n+499,999'.  For interfaces which do not vary in
         
         bandwidth or for those where no accurate estimation
         
         can be made, this object should contain the nominal
         
         bandwidth.  For a sub-layer which has no concept of
         
         bandwidth, this object should be zero.
         
         	ALCATEL NOTE:
         
         ACCESS:      NA           USAGE:       NA
         
         PERSIST:     NO           INSRVMOD:    NA
         
         RANGE:       NA           DEFVALUE:    0
         
         UNITS:       1,000,000 bits per second           SPARSE:      NO
         
         DESCR:       NA"
    ::= { ifXEntry 15 }

ifPromiscuousMode OBJECT-TYPE
    SYNTAX      TruthValue
    ACCESS      read-write
    STATUS      mandatory
    DESCRIPTION 
        "This object has a value of false(2) if this interface
         
         only accepts packets/frames that are addressed to this
         
         station.  This object has a value of true(1) when the
         
         station accepts all packets/frames transmitted on the
         
         media.  The value true(1) is only legal on certain
         
         types of media.  If legal, setting this object to a
         
         value of true(1) may require the interface to be reset
         
         before becoming effective.
         
         
         
         The value of ifPromiscuousMode does not affect the
         
         reception of broadcast and multicast packets/frames by
         
         the interface.
         
         	ALCATEL NOTE:
         
         ACCESS:      NA           USAGE:       NA
         
         PERSIST:     YES          INSRVMOD:    YES
         
         RANGE:       1,2          DEFVALUE:    false
         
         UNITS:       NA           SPARSE:      NO
         
         DESCR:       NA"
    ::= { ifXEntry 16 }

ifConnectorPresent OBJECT-TYPE
    SYNTAX      TruthValue
    ACCESS      read-only
    STATUS      mandatory
    DESCRIPTION 
        "This object has the value 'true(1)' if the interface
         
         sublayer has a physical connector and the value
         
         'false(2)' otherwise.
         
         	ALCATEL NOTE:
         
         ACCESS:      NA           USAGE:       NA
         
         PERSIST:     NO           INSRVMOD:    NA
         
         RANGE:       1,2          DEFVALUE:    true
         
         UNITS:       NA           SPARSE:      NO
         
         DESCR:       NA"
    ::= { ifXEntry 17 }

ifAlias OBJECT-TYPE
    SYNTAX      DisplayString (SIZE(0..15))
    ACCESS      read-write
    STATUS      mandatory
    DESCRIPTION 
        "This object is an 'alias' name for the interface as
         
         specified by a network manager, and provides a non-
         
         volatile 'handle' for the interface.
         
         
         
         On the first instantiation of an interface, the value
         
         of ifAlias associated with that interface is the
         
         zero-length string.  As and when a value is written
         
         into an instance of ifAlias through a network
         
         management set operation, then the agent must retain
         
         the supplied value in the ifAlias instance associated
         
         with the same interface for as long as that interface
         
         remains instantiated, including across all re-
         
         initializations/reboots of the network management
         
         system, including those which result in a change of
         
         the interface's ifIndex value.
         
         
         
         An example of the value which a network manager might
         
         store in this object for a WAN interface is the
         
         (Telco's) circuit number/identifier of the interface.
         
         
         
         Some agents may support write-access only for
         
         interfaces having particular values of ifType.  An
         
         agent which supports write access to this object is
         
         required to keep the value in non-volatile storage,
         
         but it may limit the length of new values depending on
         
         how much storage is already occupied by the current
         
         values for other interfaces.
         
         	ALCATEL NOTE:
         
         ACCESS:      NA           USAGE:       NA
         
         PERSIST:     YES          INSRVMOD:    YES
         
         RANGE:       NA           DEFVALUE:    NA
         
         UNITS:       NA           SPARSE:      NO
         
         DESCR:       NA"
    ::= { ifXEntry 18 }

ifCounterDiscontinuityTime OBJECT-TYPE
    SYNTAX      TimeStamp
    ACCESS      read-only
    STATUS      mandatory
    DESCRIPTION 
        "The value of sysUpTime on the most recent occasion at
         
         which any one or more of this interface's counters
         
         suffered a discontinuity.  The relevant counters are
         
         the specific instances associated with this interface
         
         of any Counter32 or Counter64 object contained in the
         
         ifTable or ifXTable.  If no such discontinuities have
         
         occurred since the last re-initialization of the local
         
         management subsystem, then this object contains a zero
         
         value.
         
         	ALCATEL NOTE:
         
         ACCESS:      NA           USAGE:       NA
         
         PERSIST:     NO           INSRVMOD:    NA
         
         RANGE:       NA           DEFVALUE:    0
         
         UNITS:       TimeTicks    SPARSE:      NO
         
         DESCR:       NA"
    ::= { ifXEntry 19 }

ifStackTable OBJECT-TYPE
    SYNTAX      SEQUENCE OF IfStackEntry
    ACCESS      not-accessible
    STATUS      mandatory
    DESCRIPTION 
        "The table containing information on the relationships
         
         between the multiple sub-layers of network interfaces.
         
         In particular, it contains information on which sub-
         
         layers run 'on top of' which other sub-layers, where
         
         each sub-layer corresponds to a conceptual row in the
         
         ifTable.  For example, when the sub-layer with ifIndex
         
         value x runs over the sub-layer with ifIndex value y,
         
         then this table contains:
         
         
         
           ifStackStatus.x.y=active
         
         
         
         For each ifIndex value, I, which identifies an active
         
         interface, there are always at least two instantiated
         
         rows in this table associated with I.  For one of
         
         these rows, I is the value of n; for
         
         the other, I is the value of ifStackLowerLayer.  (If I
         
         is not involved in multiplexing, then these are the
         
         only two rows associated with I.)
         
         
         
         For example, two rows exist even for an interface
         
         which has no others stacked on top or below it:
         
         
         
           ifStackStatus.0.x=active
         
           ifStackStatus.x.0=active
         
         ALCATEL NOTE:
         
         	TABLESIZE: NA 
         
         	DESCR:	This object is not used by Alcatel"
    ::= { ifMIBObjects 2 }

ifStackEntry OBJECT-TYPE
    SYNTAX      IfStackEntry
    ACCESS      not-accessible
    STATUS      mandatory
    DESCRIPTION 
        "Information on a particular relationship between two
         
         sub-layers, specifying that one sub-layer runs on
         
         'top' of the other sub-layer.  Each sub-layer
         
         corresponds to a conceptual row in the ifTable.
         
         Row creation : NA
         
         Row deletion : NA
         
         Index usage : NA
         
         lexicographical order :  NA
         
         This object is not used by Alcatel"
    INDEX       { ifStackHigherLayer, ifStackLowerLayer }
    ::= { ifStackTable 1 }

IfStackEntry ::= SEQUENCE {
    ifStackHigherLayer  INTEGER,
    ifStackLowerLayer   INTEGER,
    ifStackStatus       RowStatus
}

ifStackHigherLayer OBJECT-TYPE
    SYNTAX      INTEGER (0..2147483647)
    ACCESS      not-accessible
    STATUS      mandatory
    DESCRIPTION 
        "The value of ifIndex corresponding to the higher
         
         sub-layer of the relationship, i.e., the sub-layer
         
         which runs on 'top' of the sub-layer identified by the
         
         corresponding instance of ifStackLowerLayer.  If there
         
         is no higher sub-layer (below the internetwork layer),
         
         then this object has the value 0.
         
         ALCATEL NOTE:
         
         ACCESS:      NA           USAGE:       NA
         
         PERSIST:     NA           INSRVMOD:    NA
         
         RANGE:       NA           DEFVALUE:    NA
         
         UNITS:       NA           SPARSE:      NA
         
         DESCR:       This object is not used by Alcatel"
    ::= { ifStackEntry 1 }

ifStackLowerLayer OBJECT-TYPE
    SYNTAX      INTEGER (0..2147483647)
    ACCESS      not-accessible
    STATUS      mandatory
    DESCRIPTION 
        "The value of ifIndex corresponding to the lower sub-
         
         layer of the relationship, i.e., the sub-layer which
         
         runs 'below' the sub-layer identified by the
         
         corresponding instance of ifStackHigherLayer.  If
         
         there is no lower sub-layer, then this object has the
         
         value 0.
         
         ALCATEL NOTE:
         
         ACCESS:      NA           USAGE:       NA
         
         PERSIST:     NA           INSRVMOD:    NA
         
         RANGE:       NA           DEFVALUE:    NA
         
         UNITS:       NA           SPARSE:      NA
         
         DESCR:       This object is not used by Alcatel"
    ::= { ifStackEntry 2 }

ifStackStatus OBJECT-TYPE
    SYNTAX      RowStatus
    ACCESS      read-write
    STATUS      mandatory
    DESCRIPTION 
        "The status of the relationship between two sub-
         
         layers.
         
         
         
         Changing the value of this object from 'active' to
         
         'notInService' or 'destroy' will likely have
         
         consequences up and down the interface stack.  Thus,
         
         write access to this object is likely to be
         
         inappropriate for some types of interfaces, and many
         
         implementations will choose not to support write-
         
         access for any type of interface.
         
         ALCATEL NOTE:
         
         ACCESS:      NA           USAGE:       NA
         
         PERSIST:     NA           INSRVMOD:    NA
         
         RANGE:       NA           DEFVALUE:    NA
         
         UNITS:       NA           SPARSE:      NA
         
         DESCR:       This object is not used by Alcatel"
    ::= { ifStackEntry 3 }

ifRcvAddressTable OBJECT-TYPE
    SYNTAX      SEQUENCE OF IfRcvAddressEntry
    ACCESS      not-accessible
    STATUS      mandatory
    DESCRIPTION 
        "This table contains an entry for each address
         
         (broadcast, multicast, or uni-cast) for which the
         
         system will receive packets/frames on a particular
         
         interface, except as follows:
         
         
         
         - for an interface operating in promiscuous mode,
         
         entries are only required for those addresses for
         
         which the system would receive frames were it not
         
         operating in promiscuous mode.
         
         
         
         - for 802.5 functional addresses, only one entry is
         
         required, for the address which has the functional
         
         address bit ANDed with the bit mask of all functional
         
         addresses for which the interface will accept frames.
         
         
         
         A system is normally able to use any unicast address
         
         which corresponds to an entry in this table as a
         
         source address.
         
         ALCATEL NOTE:
         
         	TABLESIZE: NA 
         
         	DESCR:	This object is not used by Alcatel"
    ::= { ifMIBObjects 4 }

ifRcvAddressEntry OBJECT-TYPE
    SYNTAX      IfRcvAddressEntry
    ACCESS      not-accessible
    STATUS      mandatory
    DESCRIPTION 
        "A list of objects identifying an address for which
         
         the system will accept packets/frames on the
         
         particular interface identified by the index value
         
         ifIndex.
         
         Row creation : NA
         
         Row deletion : NA
         
         Index usage : NA
         
         lexicographical order :  NA
         
         This object is not used by Alcatel"
    INDEX       { ifIndex, ifRcvAddressAddress }
    ::= { ifRcvAddressTable 1 }

IfRcvAddressEntry ::= SEQUENCE {
    ifRcvAddressAddress     PhysAddress,
    ifRcvAddressStatus      RowStatus,
    ifRcvAddressType        INTEGER
}

ifRcvAddressAddress OBJECT-TYPE
    SYNTAX      PhysAddress (SIZE(6))
    ACCESS      not-accessible
    STATUS      mandatory
    DESCRIPTION 
        "An address for which the system will accept
         
         packets/frames on this entry's interface.
         
         ALCATEL NOTE:
         
         ACCESS:      NA           USAGE:       NA
         
         PERSIST:     NA           INSRVMOD:    NA
         
         RANGE:       NA           DEFVALUE:    NA
         
         UNITS:       NA           SPARSE:      NA
         
         DESCR:       This object is not used by Alcatel"
    ::= { ifRcvAddressEntry 1 }

ifRcvAddressStatus OBJECT-TYPE
    SYNTAX      RowStatus
    ACCESS      read-write
    STATUS      mandatory
    DESCRIPTION 
        "This object is used to create and delete rows in the
         
         ifRcvAddressTable.
         
         ALCATEL NOTE:
         
         ACCESS:      NA           USAGE:       NA
         
         PERSIST:     NA           INSRVMOD:    NA
         
         RANGE:       NA           DEFVALUE:    NA
         
         UNITS:       NA           SPARSE:      NA
         
         DESCR:       This object is not used by Alcatel"
    ::= { ifRcvAddressEntry 2 }

ifRcvAddressType OBJECT-TYPE
    SYNTAX      INTEGER { other(1), volatile(2), nonVolatile(3) }
    ACCESS      read-write
    STATUS      mandatory
    DESCRIPTION 
        "This object has the value nonVolatile(3) for those
         
         entries in the table which are valid and will not be
         
         deleted by the next restart of the managed system.
         
         Entries having the value volatile(2) are valid and
         
         exist, but have not been saved, so that will not exist
         
         after the next restart of the managed system.  Entries
         
         having the value other(1) are valid and exist but are
         
         not classified as to whether they will continue to
         
         exist after the next restart.
         
         ALCATEL NOTE:
         
         ACCESS:      NA           USAGE:       NA
         
         PERSIST:     NA           INSRVMOD:    NA
         
         RANGE:       NA           DEFVALUE:    NA
         
         UNITS:       NA           SPARSE:      NA
         
         DESCR:       This object is not used by Alcatel"
    DEFVAL      { volatile }
    ::= { ifRcvAddressEntry 3 }

ifTableLastChange OBJECT-TYPE
    SYNTAX      TimeTicks
    ACCESS      read-only
    STATUS      mandatory
    DESCRIPTION 
        "The value of sysUpTime at the time of the last
         
         creation or deletion of an entry in the ifTable.  If
         
         the number of entries has been unchanged since the
         
         last re-initialization of the local network management
         
         subsystem, then this object contains a zero value.
         
         	ALCATEL NOTE:
         
         ACCESS:      NA           USAGE:       NA
         
         PERSIST:     NO           INSRVMOD:    NA
         
         RANGE:       NA           DEFVALUE:    0
         
         UNITS:       TimeTicks    SPARSE:      NA
         
         DESCR:       NA"
    ::= { ifMIBObjects 5 }

ifStackLastChange OBJECT-TYPE
    SYNTAX      TimeTicks
    ACCESS      read-only
    STATUS      mandatory
    DESCRIPTION 
        "The value of sysUpTime at the time of the last change
         
         of the (whole) interface stack.  A change of the
         
         interface stack is defined to be any creation,
         
         deletion, or change in value of any instance of
         
         ifStackStatus.  If the interface stack has been
         
         unchanged since the last re-initialization of the
         
         local network management subsystem, then this object
         
         contains a zero value.
         
         	ALCATEL NOTE:
         
         ACCESS:      NA           USAGE:       NA
         
         PERSIST:     NO           INSRVMOD:    NA
         
         RANGE:       NA           DEFVALUE:    0
         
         UNITS:       TimeTicks    SPARSE:      NA
         
         DESCR:       NA"
    ::= { ifMIBObjects 6 }

snmpMIB OBJECT IDENTIFIER
    ::= { snmpModules 1 }

snmpMIBObjects OBJECT IDENTIFIER
    ::= { snmpMIB 1 }

snmpTraps OBJECT IDENTIFIER
    ::= { snmpMIBObjects 5 }

linkDown TRAP-TYPE
    ENTERPRISE  snmpTraps
    VARIABLES   { ifIndex, ifAdminStatus, ifOperStatus }
--     STATUS      mandatory
    DESCRIPTION 
        "A linkDown trap signifies that the SNMPv2 entity,
         
         acting in an agent role, has detected that the
         
         ifOperStatus object for one of its communication links
         
         is about to enter the down state from some other state
         
         (but not from the notPresent state).  This other state
         
         is indicated by the included value of ifOperStatus."
    ::= 3

linkUp TRAP-TYPE
    ENTERPRISE  snmpTraps
    VARIABLES   { ifIndex, ifAdminStatus, ifOperStatus }
--     STATUS      mandatory
    DESCRIPTION 
        "A linkDown trap signifies that the SNMPv2 entity,
         
         acting in an agent role, has detected that the
         
         ifOperStatus object for one of its communication links
         
         left the down state and transitioned into some other
         
         state (but not into the notPresent state).  This other
         
         state is indicated by the included value of
         
         ifOperStatus."
    ::= 4

END -- end of module IF-MIB.
