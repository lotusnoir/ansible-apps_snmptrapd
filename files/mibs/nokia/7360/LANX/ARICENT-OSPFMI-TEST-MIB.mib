--
-- This SMIv1 module has been generated by smidump 0.4.8. Do not edit.
--

ARICENT-OSPFMI-TEST-MIB DEFINITIONS ::= BEGIN

IMPORTS
    BigMetric, fsMIStdOspfContextId
        FROM ARICENT-MISTDOSPF-MIB
    InterfaceIndex
        FROM IF-MIB
    OBJECT-TYPE
        FROM RFC-1212
    Gauge, IpAddress, enterprises
        FROM RFC1155-SMI;

fsMIOspfTestGroup OBJECT IDENTIFIER
    ::= { enterprises futuresoftware(2076) 147 }

-- fsMIOspfTestGroup MODULE-IDENTITY
--     LAST-UPDATED "200702230000Z"
--     ORGANIZATION 
--         "ARICENT COMMUNICATIONS SOFTWARE"
--     CONTACT-INFO 
--         "ARICENT COMMUNICATIONS SOFTWARE
--          3460 Hillview Avenue,
--          Palo Alto, CA 94304-1388, USA,
--          Phone : +1-650-391-1088
--          E-mail:support@aricent.com"
--     DESCRIPTION 
--         "The enterprise ID 2076 was originally assigned to Future Software Pvt Limited.
--          Future Software is a part of Aricent."
--     REVISION    "200702230000Z"
--     DESCRIPTION 
--         "The Aricent Proprietary OSPFMI TEST MIB"
--     ::= { enterprises futuresoftware(2076) 147 }


fsMIOspfBRRouteTable OBJECT-TYPE
    SYNTAX      SEQUENCE OF FsMIOspfBRRouteEntry
    ACCESS      not-accessible
    STATUS      mandatory
    DESCRIPTION 
        "A table of routing information.
         ALCATEL NOTE:
         		TABLE SIZE:   1000
         		DESCR     :   NA"
    ::= { fsMIOspfTestGroup 1 }

fsMIOspfBRRouteEntry OBJECT-TYPE
    SYNTAX      FsMIOspfBRRouteEntry
    ACCESS      not-accessible
    STATUS      mandatory
    DESCRIPTION 
        "The information regarding a single route.
         Row creation : An entry shall be created automatically by the protocol.
         Row deletion : An entry shall be deleted automatically.
         Index usage : the index is the Context Id, Ip Address,Ip Address Mask,Ip Type Of Service,Ip Next Hop,Route Dest Type.
           Note that entries will be presented to the SNMP manager in full
           lexicographical order :  sorted on Context Id then on Ip Address,Ip Address Mask,Ip Type Of Service,Ip Next Hop,Route Dest Type."
    INDEX       { fsMIStdOspfContextId, fsMIOspfBRRouteIpAddr, 
                  fsMIOspfBRRouteIpAddrMask, fsMIOspfBRRouteIpTos, 
                  fsMIOspfBRRouteIpNextHop, fsMIOspfBRRouteDestType }
    ::= { fsMIOspfBRRouteTable 1 }

FsMIOspfBRRouteEntry ::= SEQUENCE {
    fsMIOspfBRRouteIpAddr           IpAddress,
    fsMIOspfBRRouteIpAddrMask       IpAddress,
    fsMIOspfBRRouteIpTos            Gauge,
    fsMIOspfBRRouteIpNextHop        IpAddress,
    fsMIOspfBRRouteDestType         INTEGER,
    fsMIOspfBRRouteType             INTEGER,
    fsMIOspfBRRouteAreaId           IpAddress,
    fsMIOspfBRRouteCost             BigMetric,
    fsMIOspfBRRouteInterfaceIndex   InterfaceIndex
}

fsMIOspfBRRouteIpAddr OBJECT-TYPE
    SYNTAX      IpAddress
    ACCESS      not-accessible
    STATUS      mandatory
    DESCRIPTION 
        " Router Id of the destination router. 
         ABR/ASBR entries will have Router Id as 
         the destination network Id. 
         ALCATEL NOTE:
         ACCESS:      NA          USAGE:       NA
         PERSIST:     NO          INSRVMOD:    NA
         RANGE:       NA          DEFVALUE:    NA
         UNITS:       NA          SPARSE:      NO
         DESCR:       NA"
    ::= { fsMIOspfBRRouteEntry 1 }

fsMIOspfBRRouteIpAddrMask OBJECT-TYPE
    SYNTAX      IpAddress
    ACCESS      not-accessible
    STATUS      mandatory
    DESCRIPTION 
        " IP Address Mask of the route. This will be 
         0.0.0.0 for all routes, because for ABR/ASBR 
         route entries netmask is 0.0.0.0 
         ALCATEL NOTE:
         ACCESS:      NA          USAGE:       NA
         PERSIST:     NO          INSRVMOD:    NA
         RANGE:       NA          DEFVALUE:    NA
         UNITS:       NA          SPARSE:      NO
         DESCR:       NA"
    ::= { fsMIOspfBRRouteEntry 2 }

fsMIOspfBRRouteIpTos OBJECT-TYPE
    SYNTAX      Gauge
    ACCESS      not-accessible
    STATUS      mandatory
    DESCRIPTION 
        " IP TOS of the route 
         ALCATEL NOTE:
              ACCESS:      NA                  USAGE:       NA
              PERSIST:     NO                  INSRVMOD:    NA
              RANGE:       1,2,3,5,7,9,11..31  DEFVALUE:    NA
              UNITS:       NA                  SPARSE:      NO
              DESCR:       NA"
    ::= { fsMIOspfBRRouteEntry 3 }

fsMIOspfBRRouteIpNextHop OBJECT-TYPE
    SYNTAX      IpAddress
    ACCESS      not-accessible
    STATUS      mandatory
    DESCRIPTION 
        " IP Next Hop of the route 
         ALCATEL NOTE:
              ACCESS:      NA          USAGE:       NA
              PERSIST:     NO          INSRVMOD:    NA
              RANGE:       NA          DEFVALUE:    NA
              UNITS:       NA          SPARSE:      NO
              DESCR:       NA"
    ::= { fsMIOspfBRRouteEntry 4 }

fsMIOspfBRRouteDestType OBJECT-TYPE
    SYNTAX      INTEGER { areaBorder(2), asBoundary(3) }
    ACCESS      not-accessible
    STATUS      mandatory
    DESCRIPTION 
        " Type of the route. The route can be ABR route
         entry or ASBR route entry.
         ALCATEL NOTE:
         ACCESS:      NA          USAGE:       NA
         PERSIST:     NO          INSRVMOD:    NA
         RANGE:       NA          DEFVALUE:    NA
         UNITS:       NA          SPARSE:      NO
         DESCR:       NA"
    ::= { fsMIOspfBRRouteEntry 5 }

fsMIOspfBRRouteType OBJECT-TYPE
    SYNTAX      INTEGER { intraArea(1), interArea(2) }
    ACCESS      read-only
    STATUS      mandatory
    DESCRIPTION 
        " Type of the route 
         ALCATEL NOTE:
              ACCESS:      NA          USAGE:       NA
              PERSIST:     NO          INSRVMOD:    NA
              RANGE:       NA          DEFVALUE:    NA
              UNITS:       NA          SPARSE:      NO
              DESCR:       NA"
    ::= { fsMIOspfBRRouteEntry 6 }

fsMIOspfBRRouteAreaId OBJECT-TYPE
    SYNTAX      IpAddress
    ACCESS      read-only
    STATUS      mandatory
    DESCRIPTION 
        " Area ID associated with the route 
         ALCATEL NOTE:
              ACCESS:      NA          USAGE:       NA
              PERSIST:     NO          INSRVMOD:    NA
              RANGE:       NA          DEFVALUE:    NA
              UNITS:       NA          SPARSE:      NO
         	    DESCR:       NA"
    ::= { fsMIOspfBRRouteEntry 7 }

fsMIOspfBRRouteCost OBJECT-TYPE
    SYNTAX      BigMetric
    ACCESS      read-only
    STATUS      mandatory
    DESCRIPTION 
        " The cost associated with the route
         ALCATEL NOTE:
              ACCESS:      NA           USAGE:       NA
              PERSIST:     NO           INSRVMOD:    NA
              RANGE:       0..16777215  DEFVALUE:    NA
              UNITS:       NA           SPARSE:      NO
              DESCR:       NA"
    ::= { fsMIOspfBRRouteEntry 8 }

fsMIOspfBRRouteInterfaceIndex OBJECT-TYPE
    SYNTAX      InterfaceIndex
    ACCESS      read-only
    STATUS      mandatory
    DESCRIPTION 
        " Interface Index associated with the route
         ALCATEL NOTE:
            ACCESS:      NA          USAGE:       NA
            PERSIST:     NO          INSRVMOD:    NA
            RANGE:       DEP         DEFVALUE:    NA
            UNITS:       NA          SPARSE:      NO
             DESCR:	 DEP(TABLESIZE):The range is 1 to the max number of physical interfaces + 
         		       total number of IP interfaces in the system .
         		       The max number of physical interfaces can be got from the object issSystemNumberOfPorts
         		       in fsiss.mib.
         		       The total number of IP interfaces in the system  is obtained from
         		       the object fsVrfMaxIpInterfaces in fsvrf.mib"
    ::= { fsMIOspfBRRouteEntry 9 }

END -- end of module ARICENT-OSPFMI-TEST-MIB.
