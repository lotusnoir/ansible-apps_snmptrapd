--
-- This SMIv1 module has been generated by smidump 0.4.8. Do not edit.
--

RADIUSRELAY-MIB DEFINITIONS ::= BEGIN

IMPORTS
    OBJECT-TYPE
        FROM RFC-1212
    Counter, Gauge, IpAddress, enterprises
        FROM RFC1155-SMI;

futureRadiusRelay OBJECT IDENTIFIER
    ::= { enterprises futuresoftware(2076) 92 }

-- futureRadiusRelay MODULE-IDENTITY
--     LAST-UPDATED "200404230000Z"
--     ORGANIZATION 
--         "FUTURE SOFTWARE  LIMITED"
--     CONTACT-INFO 
--         " Phone : +91-44-4330550
--          E-mail: support@future.futsoft.com"
--     DESCRIPTION 
--         "The Radius Relay agent MIB "
--     REVISION    "200404230000Z"
--     DESCRIPTION 
--         "The initial revision of this MIB module was published as
--          RFC 1450."
--     ::= { enterprises futuresoftware(2076) 92 }


radiusRelay OBJECT IDENTIFIER
    ::= { futureRadiusRelay 1 }

radiusRelaying OBJECT-TYPE
    SYNTAX      INTEGER { enable(1), disable(2) }
    ACCESS      read-write
    STATUS      mandatory
    DESCRIPTION 
        "The Radius Relay will always be active by default.
         ALCATEL NOTE:
         ACCESS:      NA           USAGE:       NA
         PERSIST:     YES          INSRVMOD:    YES
         RANGE:       NA           DEFVALUE:    NA
         UNITS:       NA           SPARSE:      NA
         DESCR:       NA"
    DEFVAL      { enable }
    ::= { radiusRelay 1 }

radiusRelayConfigTraceLevel OBJECT-TYPE
    SYNTAX      INTEGER (0..255)
    ACCESS      read-write
    STATUS      mandatory
    DESCRIPTION 
        "The Trace level Object which has bit masks for 
         various levels of tracing 
         ALCATEL NOTE:
         ACCESS:      NA           USAGE:       NA
         PERSIST:     YES          INSRVMOD:    YES
         RANGE:       NA           DEFVALUE:    NA
         UNITS:       NA           SPARSE:      NA
         DESCR:       NA"
    DEFVAL      { 0 }
    ::= { radiusRelay 2 }

radiusRelayLanxCommandPort1 OBJECT-TYPE
    SYNTAX      INTEGER (1..65535)
    ACCESS      read-write
    STATUS      mandatory
    DESCRIPTION 
        " Specifies the udp command port  to be used in disconnect mode 
         ALCATEL NOTE:
         ACCESS:      NA           USAGE:       NA
         PERSIST:     YES          INSRVMOD:    YES
         RANGE:       NA           DEFVALUE:    NA
         UNITS:       NA           SPARSE:      NA
         DESCR:       NA"
    DEFVAL      { 3799 }
    ::= { radiusRelay 3 }

radiusRelayLanxCommandPort2 OBJECT-TYPE
    SYNTAX      INTEGER (1..65535)
    ACCESS      read-write
    STATUS      mandatory
    DESCRIPTION 
        " Specifies the udp command port  to be used in disconnect mode 
         ALCATEL NOTE:
         ACCESS:      NA           USAGE:       NA
         PERSIST:     YES          INSRVMOD:    YES
         RANGE:       NA           DEFVALUE:    NA
         UNITS:       NA           SPARSE:      NA
         DESCR:       NA"
    DEFVAL      { 1813 }
    ::= { radiusRelay 4 }

radiusRelayLanxCommandPort3 OBJECT-TYPE
    SYNTAX      INTEGER (1..65535)
    ACCESS      read-write
    STATUS      mandatory
    DESCRIPTION 
        " Specifies the udp command port  to be used in disconnect mode 
         ALCATEL NOTE:
         ACCESS:      NA           USAGE:       NA
         PERSIST:     YES          INSRVMOD:    YES
         RANGE:       NA           DEFVALUE:    NA
         UNITS:       NA           SPARSE:      NA
         DESCR:       NA"
    DEFVAL      { 1700 }
    ::= { radiusRelay 5 }

END -- end of module RADIUSRELAY-MIB.
