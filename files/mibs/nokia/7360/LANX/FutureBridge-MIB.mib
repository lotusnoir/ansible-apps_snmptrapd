--
-- This SMIv1 module has been generated by smidump 0.4.8. Do not edit.
--

FutureBridge-MIB DEFINITIONS ::= BEGIN

IMPORTS
    OBJECT-TYPE
        FROM RFC-1212
    TRAP-TYPE
        FROM RFC-1215
    Counter, Gauge, enterprises
        FROM RFC1155-SMI
    MacAddress
        FROM SNMPv2-TC;

futureBridgeMIB OBJECT IDENTIFIER
    ::= { enterprises futuresoftware(2076) 26 }

-- futureBridgeMIB MODULE-IDENTITY
--     LAST-UPDATED "200112190130Z"
--     ORGANIZATION 
--         "FUTURE SOFTWARE PVT. LIMITED"
--     CONTACT-INFO 
--         " FUTURE SOFTWARE PVT. LIMITED
--          481 Mount Road
--          Madras - 600 035
--          Phone : +91-44-433 055 0 
--          support@futsoft.com"
--     DESCRIPTION 
--         "This mib module is for Future Software Proprietory
--          Bridge mib"
--     REVISION    "200112190130Z"
--     DESCRIPTION 
--         "The initial revision of this MIB module was published as
--          RFC 1450."
--     ::= { enterprises futuresoftware(2076) 26 }


BridgeId ::=
    OCTET STRING (SIZE(8))

-- BridgeId ::= TEXTUAL-CONVENTION
--     STATUS      mandatory
--     DESCRIPTION 
--         " Identifier of Bridge in 8 byte format"
--     SYNTAX      OCTET STRING (SIZE(8))

dot1dFutureBridge OBJECT IDENTIFIER
    ::= { futureBridgeMIB 1 }

dot1dFutureBase OBJECT IDENTIFIER
    ::= { dot1dFutureBridge 1 }

dot1dBridgeSystemControl OBJECT-TYPE
    SYNTAX      INTEGER { start(1), shutdown(2) }
    ACCESS      read-write
    STATUS      mandatory
    DESCRIPTION 
        "The administrative system control status requested by management for
         the TB feature. The value 'start'(1) indicates that all resources 
         required by TB should be allocated and TB should be supported 
         in the device on all ports. The value shutdown(2) indicates that TB 
         should be shutdown in the device on all ports and all allocated memory 
         must be released.
         ALCATEL NOTE:
               ACCESS:      NA           USAGE:       NA
               PERSIST:     NO           INSRVMOD:    YES
               RANGE:       NA           DEFVALUE:    NA
               UNITS:       NA           SPARSE:      NA
               DESCR:       NA"
    DEFVAL      { start }
    ::= { dot1dFutureBase 1 }

dot1dBaseBridgeStatus OBJECT-TYPE
    SYNTAX      INTEGER { up(1), down(2), downwithallinterfacesdown(3) }
    ACCESS      read-write
    STATUS      mandatory
    DESCRIPTION 
        "Control for Bridging services.
         Setting this object to down-with-all-interfaces-down(3),
           assigns down(2) value to dot1dBasePortAdminiStatus in 
           all entries of dot1dBasePortTable
         ALCATEL NOTE:
         ACCESS:      NA            USAGE:       NA
         PERSIST:     YES           INSRVMOD:    YES
         RANGE:       NA            DEFVALUE:    NA
         UNITS:       NA            SPARSE:      NA
         DESCR:       NA"
    DEFVAL      { down }
    ::= { dot1dFutureBase 2 }

dot1dBaseBridgeCRCStatus OBJECT-TYPE
    SYNTAX      INTEGER { withCRC(1), withoutCRC(2) }
    ACCESS      read-write
    STATUS      mandatory
    DESCRIPTION 
        "Setting this object to with-CRC(1) expects all LAN 
         frames to be received with CRC, and transmits through 
         WAN and LAN interface with the same CRC without 
         regeneration.
         ALCATEL NOTE:
         ACCESS:      NA             USAGE:       NA
         PERSIST:     YES            INSRVMOD:    YES
         RANGE:       NA             DEFVALUE:    NA
         UNITS:       NA             SPARSE:      NA
         DESCR:       NA"
    DEFVAL      { withoutCRC }
    ::= { dot1dFutureBase 3 }

dot1dBaseBridgeUpTraps OBJECT-TYPE
    SYNTAX      Counter
    ACCESS      read-only
    STATUS      mandatory
    DESCRIPTION 
        "The number of times a BRIDGE Up Trap was generated.
         ALCATEL NOTE:
                  ACCESS:      NA            USAGE:       NA
                  PERSIST:     NO            INSRVMOD:     NA
                  RANGE:       NA            DEFVALUE:    0
                  UNITS:       TRAP MESSAGE  SPARSE:      NA
                  DESCR:       NA"
    ::= { dot1dFutureBase 4 }

dot1dBaseBridgeDnTraps OBJECT-TYPE
    SYNTAX      Counter
    ACCESS      read-only
    STATUS      mandatory
    DESCRIPTION 
        "The number of times a BRIDGE Down Trap was generated.
         ALCATEL NOTE:
                  ACCESS:      NA             USAGE:        NA
                  PERSIST:     NO             INSRVMOD:     NA
                  RANGE:       NA             DEFVALUE:     0
                  UNITS:       TRAP MESSAGE   SPARSE:       NA
                  DESCR:       NA"
    ::= { dot1dFutureBase 5 }

dot1dBaseBridgeGenTraps OBJECT-TYPE
    SYNTAX      Counter
    ACCESS      read-only
    STATUS      mandatory
    DESCRIPTION 
        "The number of times a BRIDGE GenTrap was generated.
         ALCATEL NOTE:
                  ACCESS:      NA             USAGE:        NA
                  PERSIST:     NO             INSRVMOD:     NA
                  RANGE:       NA             DEFVALUE:     0
                  UNITS:       TRAP MESSAGE   SPARSE:       NA
                  DESCR:       NA"
    ::= { dot1dFutureBase 6 }

dot1dBaseBridgeNoMPRBufferTraps OBJECT-TYPE
    SYNTAX      Counter
    ACCESS      read-only
    STATUS      mandatory
    DESCRIPTION 
        "The number of times a BRIDGE No More Buffers Trap was 
         generated, with the reason as MPR buffers being exhausted.
         ALCATEL NOTE:
         ACCESS:      NA            USAGE:       NA
         PERSIST:     NO            INSRVMOD:     NA
         RANGE:       NA            DEFVALUE:    0
         UNITS:       TRAP MESSAGE  SPARSE:      NA
         DESCR:       NA"
    ::= { dot1dFutureBase 7 }

dot1dBaseBridgeMemAllocFailTraps OBJECT-TYPE
    SYNTAX      Counter
    ACCESS      read-only
    STATUS      mandatory
    DESCRIPTION 
        "The number of times a Bridge No More Buffers Trap was 
         generated, with the reason being a memory allocation failure.
         ALCATEL NOTE:
               ACCESS:      NA            USAGE:       NA
               PERSIST:     NO            INSRVMOD:    NA
               RANGE:       NA            DEFVALUE:    0
               UNITS:       TRAP MESSAGE  SPARSE:      NA
               DESCR:       NA"
    ::= { dot1dFutureBase 8 }

dot1dBaseBridgeDebug OBJECT-TYPE
    SYNTAX      INTEGER (0..255)
    ACCESS      read-write
    STATUS      mandatory
    DESCRIPTION 
        "To enable debugging facility for FutureTB/STP.
         ALCATEL NOTE:
         ACCESS:      NA           USAGE:       NA
         PERSIST:     YES          INSRVMOD:    YES
         RANGE:       NA           DEFVALUE:    0
         UNITS:       NA           SPARSE:      NA
         DESCR:       NA"
    ::= { dot1dFutureBase 9 }

dot1dBaseBridgeTrace OBJECT-TYPE
    SYNTAX      INTEGER (0..255)
    ACCESS      read-write
    STATUS      mandatory
    DESCRIPTION 
        "This object is used to enable Trace Statements in  
         FutureTB/STP module. 
         
         A FOUR BYTE integer is used for enabling the level of tracing.  
         Each BIT in the four byte integer, represents a particular  
         level of Trace.  
         
         The maping between the bit positions & the level of trace is  
         as follows:  
         0 - Init and Shutdown Traces 
         1 - Management Traces 
         2 - Data Path Traces 
         3 - Control Plane Traces 
         4 - Packet Dump Traces 
         5 - Traces related to All Resources except Buffers 
         6 - All Failure Traces 
         7 - Buffer Traces 
         
         The remaining bits are unused. Combination of levels are  
         also allowed. 
         
         For example if the bits 0 and 1 are set, then the Trace 
         statements related to Init-Shutdown and management  
         will be printed. 
         
         The user has to enter the corresponding INTEGER VALUE for the 
         bits set. For example if bits 0 and 1 are set then user has to  
         give the value 3.
         ALCATEL NOTE:
               ACCESS:      NA           USAGE:       NA
               PERSIST:     YES          INSRVMOD:    YES
               RANGE:       NA           DEFVALUE:    0
               UNITS:       NA           SPARSE:      NA
               DESCR:       NA"
    ::= { dot1dFutureBase 10 }

dot1dBaseBridgeMaxFwdDbEntries OBJECT-TYPE
    SYNTAX      INTEGER (1..65535)
    ACCESS      read-write
    STATUS      mandatory
    DESCRIPTION 
        "Maximum Entries in the Forwarding Database.
         ALCATEL NOTE:
                  ACCESS:      NA           USAGE:       NA
                  PERSIST:     NO           INSRVMOD:    YES
                  RANGE:       NA           DEFVALUE:    16384
                  UNITS:       NA           SPARSE:      NA
                  DESCR:       NA"
    ::= { dot1dFutureBase 11 }

dot1dBaseBridgeMaxFilterEntries OBJECT-TYPE
    SYNTAX      INTEGER (1..65535)
    ACCESS      read-write
    STATUS      mandatory
    DESCRIPTION 
        "Maximum Entries in the Filtering Table.
         ALCATEL NOTE:
                  ACCESS:      NA           USAGE:       NA
                  PERSIST:     NO           INSRVMOD:    YES
                  RANGE:       NA           DEFVALUE:    0
                  UNITS:       NA           SPARSE:      NA
                  DESCR:       NA"
    ::= { dot1dFutureBase 12 }

dot1dFutureBasePortTable OBJECT-TYPE
    SYNTAX      SEQUENCE OF Dot1dFutureBasePortEntry
    ACCESS      not-accessible
    STATUS      mandatory
    DESCRIPTION 
        "A table that contains generic information about
         every port that is associated with this bridge.
         Transparent, source-route, and srt ports are
         included.
         ALCATEL NOTE:
         TABLESIZE: DEP
         
         DESCR: DEP(TABLESIZE) The table size is derived from the number of ports
         	         in the system. This value can be got from the object
         		 issSystemNumberOfPorts in fsiss.mib."
    ::= { dot1dFutureBase 13 }

dot1dFutureBasePortEntry OBJECT-TYPE
    SYNTAX      Dot1dFutureBasePortEntry
    ACCESS      not-accessible
    STATUS      mandatory
    DESCRIPTION 
        "A list of information for each port of the
         bridge.
         Row creation : This entry can be created automatically when the system comes up. 
         Row deletion : This entry can be deleted automatically when the system shuts down.
         Index usage : The indices are Base Port.
         lexicographical order :  Sorted on Base port."
--     REFERENCE   
--         "P802.1d/D9, July 14, 1989: Section 6.4.2, 6.6.1"
    INDEX       { dot1dFutureBasePort }
    ::= { dot1dFutureBasePortTable 1 }

Dot1dFutureBasePortEntry ::= SEQUENCE {
    dot1dFutureBasePort             INTEGER,
    dot1dBasePortAdminStatus        INTEGER,
    dot1dBasePortOperStatus         INTEGER,
    dot1dBasePortBcastStatus        INTEGER,
    dot1dBasePortFilterNumber       INTEGER,
    dot1dBasePortMcastNumber        INTEGER,
    dot1dBasePortBcastOutFrames     Counter,
    dot1dBasePortMcastOutFrames     Counter
}

dot1dFutureBasePort OBJECT-TYPE
    SYNTAX      INTEGER (1..65535)
    ACCESS      not-accessible
    STATUS      mandatory
    DESCRIPTION 
        "The port number of the port for which this entry contains
         bridge management information 
         ALCATEL NOTE:
         ACCESS:      NA            USAGE:       NA
         PERSIST:     YES           INSRVMOD:    NA
         RANGE:       NA            DEFVALUE:    NA
         UNITS:       NA            SPARSE:      NO
         DESCR:       NA"
    ::= { dot1dFutureBasePortEntry 1 }

dot1dBasePortAdminStatus OBJECT-TYPE
    SYNTAX      INTEGER { up(1), down(2) }
    ACCESS      read-write
    STATUS      mandatory
    DESCRIPTION 
        "Control for Bridging services for this interface.
         An entry in the dot1dBasePortTable, dot1dStpPortTable and 
         dot1dTpPortTable will be created during the first indication 
         of this Interface Oper Up. Such a created Interface can be 
         made BasePortAdminUp or BasePortAdminDown by setting this 
         object to  up (1) or down (2) respectively.
         
         When this object is configured with dot1dBasePortCircuit         
         equal to 0xffff, the value specified is assigned to all
         circuits corresponding to the interface identified by 
         the dot1dBasePortIndex.
         ALCATEL NOTE:
               ACCESS:      NA           USAGE:       NA
               PERSIST:     YES          INSRVMOD:    YES
               RANGE:       NA           DEFVALUE:    NA
               UNITS:       NA           SPARSE:      NO
               DESCR:       NA"
    DEFVAL      { up }
    ::= { dot1dFutureBasePortEntry 2 }

dot1dBasePortOperStatus OBJECT-TYPE
    SYNTAX      INTEGER { up(1), down(2) }
    ACCESS      read-only
    STATUS      mandatory
    DESCRIPTION 
        "The operational counterpart of the dot1dBasePortAdminStatus. 
         This object is valid only if the administration status of the
         corresponding interface is up (1).
         ALCATEL NOTE:
              ACCESS:      NA           USAGE:       NA
              PERSIST:     NO           INSRVMOD:    NA
              RANGE:       NA           DEFVALUE:    NA
              UNITS:       NA           SPARSE:      NO
              DESCR:       NA"
    ::= { dot1dFutureBasePortEntry 3 }

dot1dBasePortBcastStatus OBJECT-TYPE
    SYNTAX      INTEGER { up(1), down(2) }
    ACCESS      read-write
    STATUS      mandatory
    DESCRIPTION 
        "Control for Broadcast frame forwarding over this 
         interface.  Setting this object to down (2) restricts forwarding
         Broadcast frames over this interface.
         ALCATEL NOTE:
               ACCESS:      NA           USAGE:       NA
               PERSIST:     YES          INSRVMOD:    YES
               RANGE:       NA           DEFVALUE:    NA
               UNITS:       NA           SPARSE:      NO
               DESCR:       NA"
    DEFVAL      { up }
    ::= { dot1dFutureBasePortEntry 4 }

dot1dBasePortFilterNumber OBJECT-TYPE
    SYNTAX      INTEGER (0..99)
    ACCESS      read-write
    STATUS      mandatory
    DESCRIPTION 
        "The  number specifying the set of filter entries (dot1dFilterEntry)
         to be used on this interface.  Setting this object to zero 
         deassigns the filter table entries assigned to this interface.
         ALCATEL NOTE:
          ACCESS:      NA           USAGE:       NA
          PERSIST:     YES          INSRVMOD:    YES
          RANGE:       NA           DEFVALUE:    NA
          UNITS:       NA           SPARSE:      NO
          DESCR:       NA"
    DEFVAL      { 0 }
    ::= { dot1dFutureBasePortEntry 5 }

dot1dBasePortMcastNumber OBJECT-TYPE
    SYNTAX      INTEGER (0..99)
    ACCESS      read-write
    STATUS      mandatory
    DESCRIPTION 
        "The number specifying the set of multicast entries 
         (dot1dMCastEntry) to be used on this interface.  Setting this 
         object to zero deassigns the multicast table entries assigned 
         to this interface.
         ALCATEL NOTE:
          ACCESS:      NA            USAGE:       NA
          PERSIST:     YES           INSRVMOD:    YES
          RANGE:       NA            DEFVALUE:    NA
          UNITS:       NA            SPARSE:      NO
          DESCR:       NA"
    DEFVAL      { 0 }
    ::= { dot1dFutureBasePortEntry 6 }

dot1dBasePortBcastOutFrames OBJECT-TYPE
    SYNTAX      Counter
    ACCESS      read-only
    STATUS      mandatory
    DESCRIPTION 
        "Count of broadcasted frame that are transmitted through
         this interface. This object is updated only for frames with
         broadcast destination address (ff.ff.ff.ff.ff.ff) and frames 
         which are broadcasted because of no learned entry in the 
         dot1dTpFdbTable.
         ALCATEL NOTE:
         ACCESS:      NA            USAGE:       NA
         PERSIST:     NO            INSRVMOD:    NA
         RANGE:       NA            DEFVALUE:    0
         UNITS:       frames        SPARSE:      NO
         DESCR:       NA"
    ::= { dot1dFutureBasePortEntry 7 }

dot1dBasePortMcastOutFrames OBJECT-TYPE
    SYNTAX      Counter
    ACCESS      read-only
    STATUS      mandatory
    DESCRIPTION 
        "Count of frames transmitted through this interface with 
         destination address in which the Mac layer multicast bit set.
         This object is not updated for frames tranmitted with broadcast
         destination address (i.e ff.ff.ff.ff.ff.ff).
         ALCATEL NOTE:
         ACCESS:      NA            USAGE:       NA
         PERSIST:     NO            INSRVMOD:    NA
         RANGE:       NA            DEFVALUE:    0
         UNITS:       frames        SPARSE:      NO
         DESCR:       NA"
    ::= { dot1dFutureBasePortEntry 8 }

dot1dFutureTp OBJECT IDENTIFIER
    ::= { dot1dFutureBridge 2 }

dot1dFutureTpPortTable OBJECT-TYPE
    SYNTAX      SEQUENCE OF Dot1dFutureTpPortEntry
    ACCESS      not-accessible
    STATUS      mandatory
    DESCRIPTION 
        "A table that contains information about every
         port that is associated with this transparent
         bridge.
         ALCATEL NOTE:
         TABLESIZE:DEP
         DESCR    : DEP(TABLESIZE)The table size is derived from the number of ports
         	            in the system. This value can be got from the object
         		    issSystemNumberOfPorts in fsiss.mib."
    ::= { dot1dFutureTp 1 }

dot1dFutureTpPortEntry OBJECT-TYPE
    SYNTAX      Dot1dFutureTpPortEntry
    ACCESS      not-accessible
    STATUS      mandatory
    DESCRIPTION 
        "A list of information for each port of a
         transparent bridge.
         Row creation : This entry can be created automatically when the system comes up. 
         Row deletion : This entry can be deleted automatically when the system shuts down.
         Index usage : The indices are Transparent Port.
         lexicographical order :  Sorted Transparent Port."
    INDEX       { dot1dFutureTpPort }
    ::= { dot1dFutureTpPortTable 1 }

Dot1dFutureTpPortEntry ::= SEQUENCE {
    dot1dFutureTpPort               INTEGER,
    dot1dTpPortInProtoDiscards      Counter,
    dot1dTpPortInFilterDiscards     Counter,
    dot1dTpPortProtocolFilterMask   INTEGER
}

dot1dFutureTpPort OBJECT-TYPE
    SYNTAX      INTEGER (1..65535)
    ACCESS      not-accessible
    STATUS      mandatory
    DESCRIPTION 
        "The port number of the port for which this entry contains
         Transparent Bridging management information 
         ALCATEL NOTE:
         ACCESS:      NA           USAGE:       NA
         PERSIST:     NO           INSRVMOD:    NA
         RANGE:       NA           DEFVALUE:    NA
         UNITS:       NA           SPARSE:      NO
         DESCR:       NA"
    ::= { dot1dFutureTpPortEntry 1 }

dot1dTpPortInProtoDiscards OBJECT-TYPE
    SYNTAX      Counter
    ACCESS      read-only
    STATUS      mandatory
    DESCRIPTION 
        "Count of valid frames received by this port
         which were discarded  due to the protocol filter mask
         (dot1dTpPortProtocolFilterMask).
         ALCATEL NOTE:
         ACCESS:      NA           USAGE:       NA
         PERSIST:     NO           INSRVMOD:     NA
         RANGE:       NA           DEFVALUE:    0
         UNITS:       frames       SPARSE:      NO
         DESCR:       NA"
    ::= { dot1dFutureTpPortEntry 2 }

dot1dTpPortInFilterDiscards OBJECT-TYPE
    SYNTAX      Counter
    ACCESS      read-only
    STATUS      mandatory
    DESCRIPTION 
        "Count of valid frames received which were
         discarded  (i.e filtered) by the forwarding process
           this  includes frames discarded by Max-Size
           and frames discarded by protocol filter mask.
         ALCATEL NOTE:
         ACCESS:      NA           USAGE:       NA
         PERSIST:     NO           INSRVMOD:     NA
         RANGE:       NA           DEFVALUE:    0
         UNITS:       frames       SPARSE:      NO
         DESCR:       NA"
    ::= { dot1dFutureTpPortEntry 3 }

dot1dTpPortProtocolFilterMask OBJECT-TYPE
    SYNTAX      INTEGER
    ACCESS      read-write
    STATUS      mandatory
    DESCRIPTION 
        "The protocol type filtering mask for this interface.
         The possible  masks are :
         IP          0x0004
         IPX         0x0008
         XNS         0x0010
         DECNET      0x0020
         CLNP        0x0040
         ATALK       0x0080
         PPPOE       0x0100 
         For eg. to filter IP and IPX  frames, set the  
         dot1dTpPortProtocolFilterMask to ( IP | IPX ).
         ALCATEL NOTE:
         ACCESS:      NA           USAGE:       NA
         PERSIST:     NO            INSRVMOD:    YES
         RANGE:       NA             DEFVALUE:    NA
         UNITS:       NA               SPARSE:      NA
         DESCR:       NA"
    DEFVAL      { 0 }
    ::= { dot1dFutureTpPortEntry 4 }

dot1dFilter OBJECT IDENTIFIER
    ::= { dot1dFutureBridge 3 }

dot1dFilterTable OBJECT-TYPE
    SYNTAX      SEQUENCE OF Dot1dFilterEntry
    ACCESS      not-accessible
    STATUS      mandatory
    DESCRIPTION 
        "This entity's Bridge Filter  Table.
         ALCATEL NOTE:
                  TABLESIZE:NA
         	         DESCR:THIS TABLE IS NOT SUPPORTED BY ALCATEL."
    ::= { dot1dFilter 1 }

dot1dFilterEntry OBJECT-TYPE
    SYNTAX      Dot1dFilterEntry
    ACCESS      not-accessible
    STATUS      mandatory
    DESCRIPTION 
        "Contains the information about the packets to be filtered.
         Row creation :   NA
         Row deletion :   NA
         Index usage :    NA
         lexicographical order :  NA.
         	          THIS TABLE IS NOT SUPPORTED BY ALCATEL."
    INDEX       { dot1dFilterNumber, dot1dFilterSrcAddress, 
                  dot1dFilterDstAddress }
    ::= { dot1dFilterTable 1 }

Dot1dFilterEntry ::= SEQUENCE {
    dot1dFilterNumber       INTEGER,
    dot1dFilterSrcAddress   MacAddress,
    dot1dFilterSrcMask      MacAddress,
    dot1dFilterDstAddress   MacAddress,
    dot1dFilterDstMask      MacAddress,
    dot1dFilterPermiss      INTEGER
}

dot1dFilterNumber OBJECT-TYPE
    SYNTAX      INTEGER (1..99)
    ACCESS      not-accessible
    STATUS      mandatory
    DESCRIPTION 
        "The number assigned to this particular filter table.
         ALCATEL NOTE:
                  ACCESS:      NA           USAGE:       NA
                  PERSIST:     NA           INSRVMOD:    NA
                  RANGE:       NA           DEFVALUE:    NA
                  UNITS:       NA           SPARSE:      NA
                  DESCR:       THIS TABLE IS NOT SUPPORTED BY ALCATEL."
    ::= { dot1dFilterEntry 1 }

dot1dFilterSrcAddress OBJECT-TYPE
    SYNTAX      MacAddress
    ACCESS      not-accessible
    STATUS      mandatory
    DESCRIPTION 
        "The Source address of the packet to be filtered.
         ALCATEL NOTE:
                  ACCESS:      NA           USAGE:       NA
                  PERSIST:     NA           INSRVMOD:    NA
                  RANGE:       NA           DEFVALUE:    NA
                  UNITS:       NA           SPARSE:      NA
                  DESCR:       THIS TABLE IS NOT SUPPORTED BY ALCATEL."
    ::= { dot1dFilterEntry 2 }

dot1dFilterSrcMask OBJECT-TYPE
    SYNTAX      MacAddress
    ACCESS      read-write
    STATUS      mandatory
    DESCRIPTION 
        "The Mask to be used with the Source address. F's in the mask
         correspond to bits to be ignored while comparing the source
         address in the packet with that in the filter entry.
         ALCATEL NOTE:
               ACCESS:      NA           USAGE:       NA
               PERSIST:     NA           INSRVMOD:    NA
               RANGE:       NA           DEFVALUE:    NA
               UNITS:       NA           SPARSE:      NA
               DESCR:       THIS TABLE IS NOT SUPPORTED BY ALCATEL."
    DEFVAL      { 'ffffffffffff'H }
    ::= { dot1dFilterEntry 3 }

dot1dFilterDstAddress OBJECT-TYPE
    SYNTAX      MacAddress
    ACCESS      not-accessible
    STATUS      mandatory
    DESCRIPTION 
        "The Destination address of the packet to be filtered.
         ALCATEL NOTE:
                  ACCESS:      NA           USAGE:       NA
                  PERSIST:     NA           INSRVMOD:    NA
                  RANGE:       NA           DEFVALUE:    NA
                  UNITS:       NA           SPARSE:      NA
                  DESCR:       THIS TABLE IS NOT SUPPORTED BY ALCATEL."
    ::= { dot1dFilterEntry 4 }

dot1dFilterDstMask OBJECT-TYPE
    SYNTAX      MacAddress
    ACCESS      read-write
    STATUS      mandatory
    DESCRIPTION 
        "The Mask to be used with the Destination address. F's in 
         the mask correspond to bits to be ignored while comparing the 
         destination address in the packet with that in the filter 
         entry.
         ALCATEL NOTE:
               ACCESS:      NA           USAGE:       NA
               PERSIST:     NA           INSRVMOD:    NA
               RANGE:       NA           DEFVALUE:    NA
               UNITS:       NA           SPARSE:      NA
               DESCR:       THIS TABLE IS NOT SUPPORTED BY ALCATEL."
    DEFVAL      { 'ffffffffffff'H }
    ::= { dot1dFilterEntry 5 }

dot1dFilterPermiss OBJECT-TYPE
    SYNTAX      INTEGER { block(1), allow(2), invalid(3) }
    ACCESS      read-write
    STATUS      mandatory
    DESCRIPTION 
        "Specifies whether to discard the packet or not when a match
         occurs with the source and destination addresses of this filter
         entry. Setting this variable to 'invalid' amounts to 
         invalidating the filter list entry.
         ALCATEL NOTE:
               ACCESS:      NA           USAGE:       NA
               PERSIST:     NA           INSRVMOD:    NA
               RANGE:       NA           DEFVALUE:    NA
               UNITS:       NA           SPARSE:      NA
               DESCR:       THIS TABLE IS NOT SUPPORTED BY ALCATEL."
    DEFVAL      { allow }
    ::= { dot1dFilterEntry 6 }

dot1dMcast OBJECT IDENTIFIER
    ::= { dot1dFutureBridge 4 }

dot1dMcastTable OBJECT-TYPE
    SYNTAX      SEQUENCE OF Dot1dMcastEntry
    ACCESS      not-accessible
    STATUS      mandatory
    DESCRIPTION 
        "This entity's Bridge Multicast table.
         ALCATEL NOTE:
                   TABLESIZE: NA
                   DESCR:     THIS TABLE IS NOT SUPPORTED BY ALCATEL."
    ::= { dot1dMcast 1 }

dot1dMcastEntry OBJECT-TYPE
    SYNTAX      Dot1dMcastEntry
    ACCESS      not-accessible
    STATUS      mandatory
    DESCRIPTION 
        "Contains the multicast address.
         Row creation : NA
         Row deletion : NA
         Index usage :  NA
         lexicographical order :  NA
               THIS TABLE IS NOT SUPPORTED BY ALCATEL."
    INDEX       { dot1dMcastMacaddress, dot1dMlistNumber }
    ::= { dot1dMcastTable 1 }

Dot1dMcastEntry ::= SEQUENCE {
    dot1dMlistNumber        INTEGER,
    dot1dMcastMacaddress    MacAddress,
    dot1dMcastPermiss       INTEGER
}

dot1dMlistNumber OBJECT-TYPE
    SYNTAX      INTEGER (1..99)
    ACCESS      not-accessible
    STATUS      mandatory
    DESCRIPTION 
        "The Number assigned to this particular multicast table.
         ALCATEL NOTE:
                  ACCESS:      NA           USAGE:       NA
                  PERSIST:     NA           INSRVMOD:    NA
                  RANGE:       NA           DEFVALUE:    NA
                  UNITS:       NA           SPARSE:      NA	
                  DESCR:       THIS TABLE IS NOT SUPPORTED BY ALCATEL."
    ::= { dot1dMcastEntry 1 }

dot1dMcastMacaddress OBJECT-TYPE
    SYNTAX      MacAddress
    ACCESS      not-accessible
    STATUS      mandatory
    DESCRIPTION 
        "The multicast macaddress that is valid for an interface.
         ALCATEL NOTE:
                  ACCESS:      NA           USAGE:       NA
                  PERSIST:     NA           INSRVMOD:    NA
                  RANGE:       NA           DEFVALUE:    NA
                  UNITS:       NA           SPARSE:      NA	
                  DESCR:       THIS TABLE IS NOT SUPPORTED BY ALCATEL."
    ::= { dot1dMcastEntry 2 }

dot1dMcastPermiss OBJECT-TYPE
    SYNTAX      INTEGER { block(1), allow(2), invalid(3) }
    ACCESS      read-write
    STATUS      mandatory
    DESCRIPTION 
        "Specifies whether to discard the packet with this multicast address
         or to forward it.  Setting this variable to 'invalid' amounts to 
         invalidating the multicast entry.
         ALCATEL NOTE:
               ACCESS:      NA           USAGE:       NA
               PERSIST:     NA           INSRVMOD:    NA
               RANGE:       NA           DEFVALUE:    NA
               UNITS:       NA           SPARSE:      NA	
               DESCR:       THIS TABLE IS NOT SUPPORTED BY ALCATEL."
    DEFVAL      { allow }
    ::= { dot1dMcastEntry 3 }

dot1dFsBrgTrapControl OBJECT IDENTIFIER
    ::= { dot1dFutureBridge 5 }

dot1dFsBaseBrgSetTraps OBJECT-TYPE
    SYNTAX      INTEGER (0..255)
    ACCESS      read-write
    STATUS      mandatory
    DESCRIPTION 
        "A four-octet string serving as a bit  map  for
         the trap events defined by the base bridge traps. This
         object is used to enable and  disable  specific
         Base Bridge traps   where  a  1  in  the  bit  field
         represents enabled.  The right-most bit  (least
         significant) represents trap 0.
         trap 1 - General Traps
         trap 2 - Abnormal Traps
         trap 3 - All Traps 
         ALCATEL NOTE:
          ACCESS:      NA           USAGE:       NA
          PERSIST:     NA           INSRVMOD:    NA
          RANGE:       NA           DEFVALUE:    NA
          UNITS:       NA           SPARSE:      NA
          DESCR:       THIS IS NOT SUPPORTED BY ALCATEL."
    ::= { dot1dFsBrgTrapControl 1 }

dot1dFsBrgTrapsTime OBJECT-TYPE
    SYNTAX      INTEGER
    ACCESS      read-only
    STATUS      mandatory
    DESCRIPTION 
        "Time at which the trap event is generated.
         ALCATEL NOTE:
                   ACCESS:      NA           USAGE:       NA
                   PERSIST:     NA           INSRVMOD:    NA
                   RANGE:       NA           DEFVALUE:    NA
                   UNITS:       NA           SPARSE:      NA
                   DESCR:       THIS IS NOT SUPPORTED BY ALCATEL."
    ::= { dot1dFsBrgTrapControl 2 }

dot1dFsBrgTrapsGenType OBJECT-TYPE
    SYNTAX      INTEGER { none(0), up(1), down(2) }
    ACCESS      read-only
    STATUS      mandatory
    DESCRIPTION 
        " Indicates the general events like UP or DOWN.
         ALCATEL NOTE:
                   ACCESS:      NA           USAGE:       NA
                   PERSIST:     NA           INSRVMOD:    NA
                   RANGE:       NA           DEFVALUE:    NA
                   UNITS:       NA           SPARSE:      NA
                   DESCR:       THIS IS NOT SUPPORTED BY ALCATEL."
    ::= { dot1dFsBrgTrapControl 3 }

dot1dFsBrgTrapsErrType OBJECT-TYPE
    SYNTAX      INTEGER { none(0), memfail(1), bufffail(2) }
    ACCESS      read-only
    STATUS      mandatory
    DESCRIPTION 
        "Indicates the error event that is generated like 
         memfail - memory allocation failure
         bufffail - buffer allocation failure .
         ALCATEL NOTE:
         ACCESS:      NA           USAGE:       NA
         PERSIST:     NA           INSRVMOD:    NA
         RANGE:       NA           DEFVALUE:    NA
         UNITS:       NA           SPARSE:      NA
         DESCR:       THIS IS NOT SUPPORTED BY ALCATEL."
    ::= { dot1dFsBrgTrapControl 4 }

brgtraps OBJECT IDENTIFIER
    ::= { dot1dFutureBridge 6 }

dot1dFsBrgTraps OBJECT IDENTIFIER
    ::= { brgtraps 0 }

dot1dFsBaseBrgGenTraps TRAP-TYPE
    ENTERPRISE  brgtraps
    VARIABLES   { dot1dFsBrgTrapsGenType, dot1dFsBrgTrapsTime }
--     STATUS      mandatory
    DESCRIPTION 
        " This is generated when any of the general events occurs in the base bridge "
    ::= 1

dot1dFsBaseBrgErrTraps TRAP-TYPE
    ENTERPRISE  brgtraps
    VARIABLES   { dot1dFsBrgTrapsErrType, dot1dFsBrgTrapsTime }
--     STATUS      mandatory
    DESCRIPTION 
        " This is generated when any of the error events occurs in the base bridge"
    ::= 2

END -- end of module FutureBridge-MIB.
