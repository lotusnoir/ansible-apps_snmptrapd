--
-- This SMIv1 module has been generated by smidump 0.4.8. Do not edit.
--

FutureMst-MIB DEFINITIONS ::= BEGIN

IMPORTS
    OBJECT-TYPE
        FROM RFC-1212
    TRAP-TYPE
        FROM RFC-1215
    Counter, Gauge, TimeTicks, enterprises
        FROM RFC1155-SMI
    MacAddress, RowStatus, TruthValue
        FROM SNMPv2-TC;

futureMstMIB OBJECT IDENTIFIER
    ::= { enterprises futuresoftware(2076) 80 }

-- futureMstMIB MODULE-IDENTITY
--     LAST-UPDATED "200203060000Z"
--     ORGANIZATION 
--         "FUTURE SOFTWARE LIMITED"
--     CONTACT-INFO 
--         "FUTURE SOFTWARE LIMITED 
--          481 Mount Road 
--          Madras - 600 035 
--          Phone : +91-44-433 0550"
--     DESCRIPTION 
--         "||||||"
--     REVISION    "200203060000Z"
--     DESCRIPTION 
--         "The initial revision of this MIB module was published as
--          RFC 1450."
--     ::= { enterprises futuresoftware(2076) 80 }


VlanId ::=
    INTEGER (1..4094)

-- VlanId ::= TEXTUAL-CONVENTION
--     STATUS      mandatory
--     DESCRIPTION 
--         "A 12-bit VLAN ID used in the VLAN Tag header."
--     SYNTAX      INTEGER (1..4094)

BridgeId ::=
    OCTET STRING (SIZE(8))

-- BridgeId ::= TEXTUAL-CONVENTION
--     STATUS      mandatory
--     DESCRIPTION 
--         " Identifier of Bridge in 8 byte format"
--     SYNTAX      OCTET STRING (SIZE(8))

Timeout ::=
    INTEGER

-- Timeout ::= TEXTUAL-CONVENTION
--     DISPLAY-HINT "d4"
--     STATUS      mandatory
--     DESCRIPTION 
--         " Time out value in 4 byte"
--     SYNTAX      INTEGER

EnabledStatus ::=
    INTEGER { enabled(1), disabled(2) }

-- EnabledStatus ::= TEXTUAL-CONVENTION
--     STATUS      mandatory
--     DESCRIPTION 
--         "A simple status value for the object."
--     SYNTAX      INTEGER
--                   { enabled(1), disabled(2) }

dot1sFutureMst OBJECT IDENTIFIER
    ::= { futureMstMIB 1 }

fsMstSystemControl OBJECT-TYPE
    SYNTAX      INTEGER { start(1), shutdown(2) }
    ACCESS      read-write
    STATUS      mandatory
    DESCRIPTION 
        "The administrative shutdown status requested by management for the MST  
         feature. The value start (1) indicates that MST should be active in 
         the device on all ports. The value shutdown (2) indicates that MST 
         should be shutdown in the device on all ports. All memory should 
         be released on all ports.
         	ALCATEL NOTE:
               ACCESS:      NA           USAGE:       NA
               PERSIST:     YES          INSRVMOD:    YES
               RANGE:       NA           DEFVALUE:    NA
               UNITS:       NA           SPARSE:      NA
               DESCR:       NA"
    DEFVAL      { start }
    ::= { dot1sFutureMst 1 }

fsMstModuleStatus OBJECT-TYPE
    SYNTAX      EnabledStatus
    ACCESS      read-write
    STATUS      mandatory
    DESCRIPTION 
        "The administrative status requested by management for the MST  
         feature. The value enabled(1) indicates that Mst should be enabled  
         in the device on all ports. The value disabled(2) indicates that 
         Mst should be disabled in the device on all ports. The object can 
         be set to enabled(1) if and only if, fsMstSystemControl set to start.
         	ALCATEL NOTE:
               ACCESS:      NA           USAGE:       NA
               PERSIST:     YES          INSRVMOD:    YES
               RANGE:       1,2          DEFVALUE:    NA
               UNITS:       NA           SPARSE:      NA
               DESCR:       NA"
    DEFVAL      { enabled }
    ::= { dot1sFutureMst 2 }

fsMstMaxMstInstanceNumber OBJECT-TYPE
    SYNTAX      INTEGER
    ACCESS      read-write
    STATUS      mandatory
    DESCRIPTION 
        "The Maximun number of spanning trees to be allowed.
         A User may limit the Number of Spanning Tree instance 
         to be allowed in the Bridge.
         	ALCATEL NOTE:
              ACCESS:      NA           USAGE:       NA
              PERSIST:     YES          INSRVMOD:    YES
              RANGE:       DEP          DEFVALUE:    NA
              UNITS:       NA           SPARSE:      NA
              DESCR:       fsMstMaxMstInstanceNumber should not be less than
         			 fsMstNoOfMstiSupported."
    DEFVAL      { 17 }
    ::= { dot1sFutureMst 3 }

fsMstNoOfMstiSupported OBJECT-TYPE
    SYNTAX      INTEGER
    ACCESS      read-only
    STATUS      mandatory
    DESCRIPTION 
        "Indicates Maximum number of spanning tree Instances supported.
         ALCATEL NOTE:
            ACCESS:      NA           USAGE:       NA
            PERSIST:     NO           INSRVMOD:    NA
            RANGE:       0..16        DEFVALUE:    0
            UNITS:       NA           SPARSE:      NA
            DESCR:       NA"
    ::= { dot1sFutureMst 4 }

fsMstMaxHopCount OBJECT-TYPE
    SYNTAX      INTEGER (600..4000)
    ACCESS      read-write
    STATUS      mandatory
    DESCRIPTION 
        "Indicates the Maximum Hop Count value.
         The granularity of this timer is specified 
         to be 1 second.  An agent may return a badValue 
         error if a set is attempted to a value which is 
         not a whole number of seconds.
         	ALCATEL NOTE:
              ACCESS:      NA           		USAGE:       NA
              PERSIST:     YES          		INSRVMOD:    YES
              RANGE:       NA           		DEFVALUE:    NA
              UNITS:       1/100th of Second      SPARSE:      NA
              DESCR:       NA"
    DEFVAL      { 2000 }
    ::= { dot1sFutureMst 5 }

fsMstBrgAddress OBJECT-TYPE
    SYNTAX      MacAddress
    ACCESS      read-only
    STATUS      mandatory
    DESCRIPTION 
        "The MAC address used by this bridge when it must
         be referred to in a unique fashion.   It is
         recommended that this be the numerically smallest
         MAC address of all ports that belong to this
         bridge.  However it is only required to be unique.
         When concatenated with fsMstCistBridgePriority or 
         fsMstMstiBridgePriority a unique BridgeIdentifier 
         is formed which is used in the Spanning Tree Protocol.
         ALCATEL NOTE:
           ACCESS:      NA           USAGE:       NA
           PERSIST:     NO           INSRVMOD:    NA
           RANGE:       NA           DEFVALUE:    NA
           UNITS:       NA           SPARSE:      NA
           DESCR:       NA"
    ::= { dot1sFutureMst 6 }

fsMstCistRoot OBJECT-TYPE
    SYNTAX      BridgeId
    ACCESS      read-only
    STATUS      mandatory
    DESCRIPTION 
        "The bridge identifier of the Root of the common spanning
         tree as determined by the Spanning Tree Protocol
         as executed by this node.  This value is used as
         the CIST Root Identifier parameter in all Configuration
         Bridge PDUs originated by this node.
         ALCATEL NOTE:
            ACCESS:      NA           USAGE:       NA
            PERSIST:     NO           INSRVMOD:    NA
            RANGE:       NA           DEFVALUE:    NA
            UNITS:       NA           SPARSE:      NA
            DESCR:       NA"
    ::= { dot1sFutureMst 7 }

fsMstCistRegionalRoot OBJECT-TYPE
    SYNTAX      BridgeId
    ACCESS      read-only
    STATUS      mandatory
    DESCRIPTION 
        "The bridge identifier of the Root of the Multiple
         spanning tree region as determined by the Spanning Tree
         Protocol as executed by this node.  This value is used as
         the CIST Regional Root Identifier parameter in all Configuration
         Bridge PDUs originated by this node.
         ALCATEL NOTE:
            ACCESS:      NA           USAGE:       NA
            PERSIST:     NO           INSRVMOD:    NA
            RANGE:       NA           DEFVALUE:    NA
            UNITS:       NA           SPARSE:      NA
            DESCR:       NA"
    ::= { dot1sFutureMst 8 }

fsMstCistRootCost OBJECT-TYPE
    SYNTAX      INTEGER
    ACCESS      read-only
    STATUS      mandatory
    DESCRIPTION 
        "The Cost of the path to the CIST Root as seen 
         from this bridge.
         	ALCATEL NOTE:
             ACCESS:      NA           USAGE:       NA
             PERSIST:     NO           INSRVMOD:    NA
             RANGE:       NA           DEFVALUE:    NA
             UNITS:       NA           SPARSE:      NA
             DESCR:       NA"
    ::= { dot1sFutureMst 9 }

fsMstCistRegionalRootCost OBJECT-TYPE
    SYNTAX      INTEGER
    ACCESS      read-only
    STATUS      mandatory
    DESCRIPTION 
        "The Cost of the path to the CIST Regional Root 
         as seen from this bridge.
         	ALCATEL NOTE:
             ACCESS:      NA           USAGE:       NA
             PERSIST:     NO           INSRVMOD:    NA
             RANGE:       NA           DEFVALUE:    NA
             UNITS:       NA           SPARSE:      NA
             DESCR:       NA"
    ::= { dot1sFutureMst 10 }

fsMstCistRootPort OBJECT-TYPE
    SYNTAX      INTEGER
    ACCESS      read-only
    STATUS      mandatory
    DESCRIPTION 
        "The Port Number of the Port which offers the lowest    
         path cost from this bridge to the CIST Root Bridge.
         	ALCATEL NOTE:
              ACCESS:      NA           USAGE:       NA
              PERSIST:     NO           INSRVMOD:    NA
              RANGE:       DEP        DEFVALUE:    NA
              UNITS:       NA           SPARSE:      NA
              DESCR:       DEP(RANGE): This object will return 0 when it  is acting as a Root Bridge.
         		In all other cases it will return the Root Port ID, having a value in 
         		the range 1 to maximum number of physical interfaces available in the system. 
         		Maximum number of physical interfaces is obtained from the object issSystemNumberOfPorts in fsiss.mib"
    ::= { dot1sFutureMst 11 }

fsMstCistBridgePriority OBJECT-TYPE
    SYNTAX      INTEGER (0..61440)
    ACCESS      read-write
    STATUS      mandatory
    DESCRIPTION 
        "The Value of the writable portion of the Bridge
         Identifier comprising of the first two octets.
         The values that are set for Bridge Priority must be 
         in steps of 4096.
         	ALCATEL NOTE:
             ACCESS:      NA           USAGE:       NA
             PERSIST:     YES          INSRVMOD:    YES
             RANGE:       NA           DEFVALUE:    NA
             UNITS:       NA           SPARSE:      NA
             DESCR:       NA"
    DEFVAL      { 32768 }
    ::= { dot1sFutureMst 12 }

fsMstCistBridgeMaxAge OBJECT-TYPE
    SYNTAX      Timeout (600..4000)
    ACCESS      read-write
    STATUS      mandatory
    DESCRIPTION 
        "The value that all bridges use for MaxAge when
         this bridge is acting as the root.  Note that
         802.1D specifies that the range for this
         parameter is related to the value of
         BridgeHelloTime. The granularity of this
         timer is specified to be 1 second.
         An agent may return a badValue error if a set is
         attempted to a value which is not a whole number
         of seconds.
         ALCATEL NOTE:
            ACCESS:      NA           		USAGE:       NA
            PERSIST:     YES          		INSRVMOD:    YES
            RANGE:       NA           		DEFVALUE:    NA
            UNITS:       1/100th of Second      SPARSE:      NA
            DESCR:       fsMstCistBridgeMaxAge should be less than or equal to 
         		 (2 * ((fsMstCistBridgeForwardDelay/100)-1) and 
         		 fsMstCistBridgeMaxAge should be greater than or equal 
         		 to (2 * ((fsMstCistPortHelloTime/100) + 1))"
    DEFVAL      { 2000 }
    ::= { dot1sFutureMst 13 }

fsMstCistBridgeHelloTime OBJECT-TYPE
    SYNTAX      Timeout (100..1000)
    ACCESS      read-write
    STATUS      mandatory
    DESCRIPTION 
        "The value that all bridges use for HelloTime when
         this bridge is acting as the root.  The
         granularity of this timer is specified to be 1 second.  
         An agent may return a badValue error if a set is attempted 
         to a value which is not a whole number of seconds.
         ALCATEL NOTE:
            ACCESS:      NA           		USAGE:       NA
            PERSIST:     YES          		INSRVMOD:    YES
            RANGE:       NA           		DEFVALUE:    NA
            UNITS:       1/100th of Second      SPARSE:      NA
            DESCR:       (2 * ((fsMstCistBridgeHelloTime/100) + 1)) should be 
         		 less than or equal to fsMstCistBridgeMaxAge. This object can be set 
         		 only when fsMstForceProtocolVersion is stp(0) or rstp(2)"
    DEFVAL      { 200 }
    ::= { dot1sFutureMst 14 }

fsMstCistBridgeForwardDelay OBJECT-TYPE
    SYNTAX      Timeout (400..3000)
    ACCESS      read-write
    STATUS      mandatory
    DESCRIPTION 
        "The value that all bridges use for ForwardDelay
         when this bridge is acting as the root.  Note that
         802.1D specifies that the range for this
         parameter is related to the value of
         BridgeMaxAge.  The granularity of this
         timer is specified to be 1 second.
         An agent may return a badValue error if a set is
         attempted to a value which is not a whole number
         of seconds.
         ALCATEL NOTE:
            ACCESS:      NA           		USAGE:       NA
            PERSIST:     YES          		INSRVMOD:    YES
            RANGE:       NA           		DEFVALUE:    NA
            UNITS:       1/100th of Second      SPARSE:      NA
            DESCR:       (2 * ((fsMstCistBridgeForwardDelay/100) - 1) should be greater than 
         		 or equal to fsMstCistBridgeMaxAge."
    DEFVAL      { 1500 }
    ::= { dot1sFutureMst 15 }

fsMstCistHoldTime OBJECT-TYPE
    SYNTAX      INTEGER
    ACCESS      read-only
    STATUS      mandatory
    DESCRIPTION 
        "This time value determines the interval length
         during which no more than two Configuration bridge
         PDUs shall be transmitted by this node, in units
         of hundredths of a second.
         ALCATEL NOTE:
           ACCESS:      NA           		USAGE:       NA
           PERSIST:     NO           		INSRVMOD:    NA
           RANGE:       NA           		DEFVALUE:    NA
           UNITS:       1/100th of Second      SPARSE:      NA
           DESCR:       NA"
    ::= { dot1sFutureMst 16 }

fsMstCistMaxAge OBJECT-TYPE
    SYNTAX      Timeout
    ACCESS      read-only
    STATUS      mandatory
    DESCRIPTION 
        "The maximum age of Spanning Tree Protocol
         information learned from the network on any port
         before it is discarded, in units of hundredths of
         a second.  This is the actual value that this
         bridge is currently using.
         ALCATEL NOTE:
           ACCESS:      NA           		USAGE:       NA
           PERSIST:     NO           		INSRVMOD:    NA
           RANGE:       NA           		DEFVALUE:    NA
           UNITS:       1/100th of Second      SPARSE:      NA
           DESCR:       NA"
    ::= { dot1sFutureMst 17 }

fsMstCistHelloTime OBJECT-TYPE
    SYNTAX      Timeout
    ACCESS      read-only
    STATUS      mandatory
    DESCRIPTION 
        "The amount of time between the transmission of
         Configuration bridge PDUs by this node on any port
         when it is the root of the spanning tree or trying
         to become so, in units of hundredths of a second.
         This is the actual value that this bridge is
         currently using.
         ALCATEL NOTE:
         ACCESS:      NA           		USAGE:       NA
         PERSIST:     NO           		INSRVMOD:    NA
         RANGE:       NA           		DEFVALUE:    NA
         UNITS:       1/100th of Second      SPARSE:      NA
         DESCR:       NA"
    ::= { dot1sFutureMst 18 }

fsMstCistForwardDelay OBJECT-TYPE
    SYNTAX      Timeout
    ACCESS      read-only
    STATUS      mandatory
    DESCRIPTION 
        "This time value, measured in units of hundredths
         of a second, controls how fast a port changes its
         spanning state when moving towards the Forwarding
         state.  The value determines how long the port
         stays in a particular state before moving to the
         next state.
         ALCATEL NOTE:
         ACCESS:      NA           		USAGE:       NA
         PERSIST:     NO           		INSRVMOD:    NA
         RANGE:       NA           		DEFVALUE:    NA
         UNITS:       1/100th of Second      SPARSE:      NA
         DESCR:       NA"
    ::= { dot1sFutureMst 19 }

fsMstMstpUpCount OBJECT-TYPE
    SYNTAX      Counter
    ACCESS      read-only
    STATUS      mandatory
    DESCRIPTION 
        "The number of times MSTP Module has been enabled.
         ALCATEL NOTE:
            ACCESS:      NA           USAGE:       NA
            PERSIST:     NO           INSRVMOD:    NA
            RANGE:       NA           DEFVALUE:    0
            UNITS:       NA           SPARSE:      NA
            DESCR:       NA"
    ::= { dot1sFutureMst 20 }

fsMstMstpDownCount OBJECT-TYPE
    SYNTAX      Counter
    ACCESS      read-only
    STATUS      mandatory
    DESCRIPTION 
        "The number of times MSTP Module has been disabled.
         ALCATEL NOTE:
            ACCESS:      NA           USAGE:       NA
            PERSIST:     NO           INSRVMOD:    NA
            RANGE:       NA           DEFVALUE:    0
            UNITS:       NA           SPARSE:      NA
            DESCR:       NA"
    ::= { dot1sFutureMst 21 }

fsMstPathCostDefaultType OBJECT-TYPE
    SYNTAX      INTEGER { stp8021d1998(1), stp8021t2001(2) }
    ACCESS      read-write
    STATUS      mandatory
    DESCRIPTION 
        "The version of the Spanning Tree default Path Costs that
         are to be used by this Bridge.  A value of 8021d1998(1)
         uses the 16-bit default Path Costs from IEEE Std. 802.1D-1998.
         A value of stp8021t2001(2) uses the 32-bit default Path
         Costs from IEEE Std. 802.1t.
         ALCATEL NOTE:
            ACCESS:      NA           USAGE:       NA
            PERSIST:     YES          INSRVMOD:    YES
            RANGE:       NA           DEFVALUE:    NA
            UNITS:       NA           SPARSE:      NA
            DESCR:       NA"
    DEFVAL      { stp8021t2001 }
    ::= { dot1sFutureMst 22 }

fsMstTrace OBJECT-TYPE
    SYNTAX      INTEGER (0..255)
    ACCESS      read-only
    STATUS      mandatory
    DESCRIPTION 
        "This object indicates the Trace value in the MSTP Module.
         
         A FOUR BYTE integer is used for enabling the level of tracing. 
         Each BIT in the four byte integer, represents a particular 
         level of Trace. 
         
         The mapping between the bit positions & the level of trace is 
         as follows: 
         0 - Init and Shutdown Traces
         1 - Management Traces
         2 - Data Path Traces
         3 - Control Plane Traces
         4 - Packet Dump Traces
         5 - Traces related to All Resources except Buffers
         6 - All Failure Traces
         7 - Buffer Traces
         
         The remaining bits are unused.
         
         For example if the bits 0 and 1 are set, then the Trace
         statements related to Init-Shutdown and management 
         will be printed.
         	ALCATEL NOTE:
               ACCESS:      NA           USAGE:       NA
               PERSIST:     NO           INSRVMOD:    NA
               RANGE:       NA           DEFVALUE:    0
               UNITS:       NA           SPARSE:      NA
               DESCR:       NA"
    ::= { dot1sFutureMst 23 }

fsMstDebug OBJECT-TYPE
    SYNTAX      INTEGER (0..65535)
    ACCESS      read-only
    STATUS      mandatory
    DESCRIPTION 
        "This object indicates the Debug value in the MSTP Module.
         
         A FOUR BYTE integer is used for enabling the level of debugging. 
         Each BIT in the four byte integer, represents a particular 
         level of Debug. 
         
         The mapping between the bit positions & the level of debug is 
         as follows: 
         0 - Init and Shutdown Debug statements
         1 - Management Debug statements
         2 - Memory related Debug statements
         3 - BPDU related Debug statements
         4 - Event Handling Debug statements
         5 - Timer Module Debug statements
         6 - Port Information SEM Debug statements
         7 - Port Receive SEM Debug statements (valid in the case of MSTP alone)
         8 - Role Selection SEM Debug statements
         9 - Role Transition SEM Debug statements
         10 - State Transition SEM Debug statements
         11 - Protocol Migration SEM Debug statements
         12 - Topology Change SEM Debug statements
         13 - Port Transmit SEM Debug statements
         14 - Bridge Detection SEM Debug statements
         15 - All Failure Debug statements
         
         The remaining bits are unused. Combination of debug levels are 
         also allowed.
         
         For example if the bits 0 and 1 are set, then the Debug
         statements related to Init-Shutdown and management 
         will be printed.
         	ALCATEL NOTE:
               ACCESS:      NA           USAGE:       NA
               PERSIST:     NO           INSRVMOD:    NA
               RANGE:       NA           DEFVALUE:    0
               UNITS:       NA           SPARSE:      NA
               DESCR:       NA"
    ::= { dot1sFutureMst 24 }

fsMstForceProtocolVersion OBJECT-TYPE
    SYNTAX      INTEGER { stpCompatible(0), rstp(2), mstp(3) }
    ACCESS      read-write
    STATUS      mandatory
    DESCRIPTION 
        "The version of Spanning Tree Protocol the bridge is
         currently running.  The value 'stpCompatible(0)'
         indicates the Spanning Tree Protocol specified in
         IEEE 802.1D and 'rstp(2)' indicates the Rapid Spanning
         Tree Protocol specified in IEEE 802.1w and 'mstp(3)'
         indicates the Multiple Spanning Tree Protocol Specified
         in IEEE 802.1s.
         ALCATEL NOTE:
            ACCESS:      NA           USAGE:       NA
            PERSIST:     YES          INSRVMOD:    YES
            RANGE:       NA           DEFVALUE:    NA
            UNITS:       NA           SPARSE:      NA
            DESCR:       NA"
    DEFVAL      { rstp }
    ::= { dot1sFutureMst 25 }

fsMstTxHoldCount OBJECT-TYPE
    SYNTAX      INTEGER (1..10)
    ACCESS      read-write
    STATUS      mandatory
    DESCRIPTION 
        "The value used by the Port Transmit state machine to limit
         the maximum transmission rate.
         ALCATEL NOTE:
            ACCESS:      NA           USAGE:       NA
            PERSIST:     YES          INSRVMOD:    YES
            RANGE:       NA           DEFVALUE:    NA
            UNITS:       NA           SPARSE:      NA
            DESCR:       NA"
    DEFVAL      { 3 }
    ::= { dot1sFutureMst 26 }

fsMstMstiConfigIdSel OBJECT-TYPE
    SYNTAX      INTEGER (0..255)
    ACCESS      read-write
    STATUS      mandatory
    DESCRIPTION 
        "The Configuration Identifier Format Selector used 
         by the Bridge. This has a fixed value of 0 to indicate
         RegionName, RegionVersion are specified as in Standard.
         	ALCATEL NOTE:
              ACCESS:      NA           USAGE:       NA
              PERSIST:     YES          INSRVMOD:    YES
              RANGE:       NA           DEFVALUE:    NA
              UNITS:       NA           SPARSE:      NA
              DESCR:       NA"
    DEFVAL      { 0 }
    ::= { dot1sFutureMst 27 }

fsMstMstiRegionName OBJECT-TYPE
    SYNTAX      OCTET STRING (SIZE(0..32))
    ACCESS      read-write
    STATUS      mandatory
    DESCRIPTION 
        "The Name for the Region's configuration. By Default 
         Region Name will be equal to the Bridge Mac Address.
         	ALCATEL NOTE:
              ACCESS:      NA           USAGE:       NA
              PERSIST:     YES          INSRVMOD:    YES
              RANGE:       NA           DEFVALUE:    NA
              UNITS:       NA           SPARSE:      NA
              DESCR:       NA"
    ::= { dot1sFutureMst 28 }

fsMstMstiRegionVersion OBJECT-TYPE
    SYNTAX      INTEGER (0..65535)
    ACCESS      read-write
    STATUS      mandatory
    DESCRIPTION 
        "Version of the MST Region.
         ALCATEL NOTE:
            ACCESS:      NA           USAGE:       NA
            PERSIST:     YES          INSRVMOD:    YES
            RANGE:       NA           DEFVALUE:    NA
            UNITS:       NA           SPARSE:      NA
            DESCR:       NA"
    DEFVAL      { 0 }
    ::= { dot1sFutureMst 29 }

fsMstMstiConfigDigest OBJECT-TYPE
    SYNTAX      OCTET STRING (SIZE(0..32))
    ACCESS      read-only
    STATUS      mandatory
    DESCRIPTION 
        "The Configuration Digest value for this Region.
         ALCATEL NOTE:
            ACCESS:      NA           USAGE:       NA
            PERSIST:     NO           INSRVMOD:    NA
            RANGE:       NA           DEFVALUE:    NA
            UNITS:       NA           SPARSE:      NA
            DESCR:       NA"
    ::= { dot1sFutureMst 30 }

fsMstBufferOverFlowCount OBJECT-TYPE
    SYNTAX      Counter
    ACCESS      read-only
    STATUS      mandatory
    DESCRIPTION 
        "The number of times Buffer overflows/failures have occured.
         A Trap is generated on the occurence of this event.
         	ALCATEL NOTE:
             ACCESS:      NA           USAGE:       NA
             PERSIST:     NO           INSRVMOD:    NA
             RANGE:       NA           DEFVALUE:    0
             UNITS:       NA           SPARSE:      NA
             DESCR:       NA"
    ::= { dot1sFutureMst 31 }

fsMstMemAllocFailureCount OBJECT-TYPE
    SYNTAX      Counter
    ACCESS      read-only
    STATUS      mandatory
    DESCRIPTION 
        "The number of times memory allocation failures have occured.
         A Trap is generated on the occurence of this event.
         	ALCATEL NOTE:
             ACCESS:      NA           USAGE:       NA
             PERSIST:     NO           INSRVMOD:    NA
             RANGE:       NA           DEFVALUE:    0
             UNITS:       NA           SPARSE:      NA
             DESCR:       NA"
    ::= { dot1sFutureMst 32 }

fsMstRegionConfigChangeCount OBJECT-TYPE
    SYNTAX      Counter
    ACCESS      read-only
    STATUS      mandatory
    DESCRIPTION 
        "The number of times a Region Configuration Identifier Change 
         was detected. 
         A Trap is generated on the occurence of this event.
         ALCATEL NOTE:
         ACCESS:      NA           USAGE:       NA
         PERSIST:     NO           INSRVMOD:    NA
         RANGE:       NA           DEFVALUE:    0
         UNITS:       NA           SPARSE:      NA
         DESCR:       NA"
    ::= { dot1sFutureMst 33 }

fsMstCistBridgeRoleSelectionSemState OBJECT-TYPE
    SYNTAX      INTEGER { initbridge(0), roleselection(1) }
    ACCESS      read-only
    STATUS      mandatory
    DESCRIPTION 
        "Current state of the Port Role Selection State Machine          
         of this bridge in Common Spanning Tree context
         ALCATEL NOTE:
          ACCESS:      NA           USAGE:       NA
          PERSIST:     NO           INSRVMOD:    NA
          RANGE:       NA           DEFVALUE:    NA
          UNITS:       NA           SPARSE:      NA
          DESCR:       NA"
    ::= { dot1sFutureMst 34 }

fsMstCistTimeSinceTopologyChange OBJECT-TYPE
    SYNTAX      TimeTicks
    ACCESS      read-only
    STATUS      mandatory
    DESCRIPTION 
        "The time (in hundredths of a second) since the
         TcWhile Timer for any port in this Bridge was 
         non-zero for Common Spanning Tree context.
         ALCATEL NOTE:
            ACCESS:      NA           		USAGE:       NA
            PERSIST:     NO           		INSRVMOD:    NA
            RANGE:       NA           		DEFVALUE:    0
            UNITS:       1/100th of Second      SPARSE:      NA
            DESCR:       NA"
    ::= { dot1sFutureMst 35 }

fsMstCistTopChanges OBJECT-TYPE
    SYNTAX      Counter
    ACCESS      read-only
    STATUS      mandatory
    DESCRIPTION 
        "The number of times that there have been atleast
         one non-zero TcWhile Timer on this Bridge for Common
         Spanning Tree context.
         ALCATEL NOTE:
            ACCESS:      NA           USAGE:       NA
            PERSIST:     NO           INSRVMOD:    NA
            RANGE:       NA           DEFVALUE:    0
            UNITS:       NA           SPARSE:      NA
            DESCR:       NA"
    ::= { dot1sFutureMst 36 }

fsMstCistNewRootBridgeCount OBJECT-TYPE
    SYNTAX      Counter
    ACCESS      read-only
    STATUS      mandatory
    DESCRIPTION 
        "The number of times this Bridge has detected a Root
         Bridge change for Common Spanning Tree context.
         A Trap is generated on the occurence of this event.
         ALCATEL NOTE:
           ACCESS:      NA           USAGE:       NA
           PERSIST:     NO           INSRVMOD:    NA
           RANGE:       NA           DEFVALUE:    0
           UNITS:       NA           SPARSE:      NA
           DESCR:       NA"
    ::= { dot1sFutureMst 37 }

fsMstMstiBridgeTable OBJECT-TYPE
    SYNTAX      SEQUENCE OF FsMstMstiBridgeEntry
    ACCESS      not-accessible
    STATUS      mandatory
    DESCRIPTION 
        "Table containing Bridge Information specific to Spanning 
         Tree Instance.
          ALCATEL NOTE:
              TABLESIZE: 	16
         	  	DESCR: 	NA"
    ::= { dot1sFutureMst 38 }

fsMstMstiBridgeEntry OBJECT-TYPE
    SYNTAX      FsMstMstiBridgeEntry
    ACCESS      not-accessible
    STATUS      mandatory
    DESCRIPTION 
        "Entry indicating the Bridge Information.
         Row creation : A fsMstMstiBridgeEntry entry shall be created in one 
         		        step by a set-request with fsMstMstiBridgeRowStatus 
         			set to createAndGo(4) or createAndWait(5).
         Row deletion : A fsMstMstiBridgeEntry entry shall be deleted by setting
             		the fsMstMstiBridgeRowStatus of the specific entry
         			to destroy(6).
         Index usage : the index is fsMstMstiInstanceIndex.
           Note that entries will be presented to the SNMP manager in full
           lexicographical order :  sorted on fsMstMstiInstanceIndex."
    INDEX       { fsMstMstiInstanceIndex }
    ::= { fsMstMstiBridgeTable 1 }

FsMstMstiBridgeEntry ::= SEQUENCE {
    fsMstMstiInstanceIndex                  INTEGER,
    fsMstMstiBridgeRegionalRoot             BridgeId,
    fsMstMstiBridgePriority                 INTEGER,
    fsMstMstiRootCost                       INTEGER,
    fsMstMstiRootPort                       INTEGER,
    fsMstMstiTimeSinceTopologyChange        TimeTicks,
    fsMstMstiTopChanges                     Counter,
    fsMstMstiNewRootBridgeCount             Counter,
    fsMstMstiBridgeRoleSelectionSemState    INTEGER,
    fsMstInstanceUpCount                    Counter,
    fsMstInstanceDownCount                  Counter,
    fsMstOldDesignatedRoot                  BridgeId,
    fsMstMstiBridgeRowStatus                RowStatus
}

fsMstMstiInstanceIndex OBJECT-TYPE
    SYNTAX      INTEGER (1..16)
    ACCESS      read-only
    STATUS      mandatory
    DESCRIPTION 
        "Spanning Tree Instance to which the information belongs.
         ALCATEL NOTE:
             ACCESS:      NA           USAGE:       NA
             PERSIST:     YES          INSRVMOD:    NA
             RANGE:       NA           DEFVALUE:    NA
             UNITS:       NA           SPARSE:      NO
             DESCR:       NA"
    ::= { fsMstMstiBridgeEntry 1 }

fsMstMstiBridgeRegionalRoot OBJECT-TYPE
    SYNTAX      BridgeId
    ACCESS      read-only
    STATUS      mandatory
    DESCRIPTION 
        "MSTI Regional Root Identifier value for the Instance. This value 
         is used as the MSTI Regional Root Identifier parameter in all
         Configuration Bridge PDUs originated by this node
          ALCATEL NOTE:
              ACCESS:      NA           USAGE:       NA
              PERSIST:     NO           INSRVMOD:    NA
              RANGE:       NA           DEFVALUE:    NA
              UNITS:       NA           SPARSE:      NO
              DESCR:       NA"
    ::= { fsMstMstiBridgeEntry 2 }

fsMstMstiBridgePriority OBJECT-TYPE
    SYNTAX      INTEGER (0..61440)
    ACCESS      read-write
    STATUS      mandatory
    DESCRIPTION 
        "The writable portion of the MSTI Bridge Identifier.
         comprising of the first two octets.
         The values that are set for Bridge Priority must be 
         in steps of 4096.
          ALCATEL NOTE:
              ACCESS:      NA           USAGE:       OPT
              PERSIST:     YES          INSRVMOD:    YES
              RANGE:       NA           DEFVALUE:    NA
              UNITS:       NA           SPARSE:      NO
              DESCR:       NA"
    DEFVAL      { 32768 }
    ::= { fsMstMstiBridgeEntry 3 }

fsMstMstiRootCost OBJECT-TYPE
    SYNTAX      INTEGER
    ACCESS      read-only
    STATUS      mandatory
    DESCRIPTION 
        "The Cost of the path to the MSTI Regional Root as seen 
         by this bridge.
          ALCATEL NOTE:
              ACCESS:      NA           USAGE:       NA
              PERSIST:     NO           INSRVMOD:    NA
              RANGE:       NA           DEFVALUE:    NA
              UNITS:       NA           SPARSE:      NO
              DESCR:       NA"
    ::= { fsMstMstiBridgeEntry 4 }

fsMstMstiRootPort OBJECT-TYPE
    SYNTAX      INTEGER
    ACCESS      read-only
    STATUS      mandatory
    DESCRIPTION 
        "The Port Number of the Port which offers the lowest    
         path cost from this bridge to the MSTI Region Root Bridge.
          ALCATEL NOTE:
              ACCESS:      NA           USAGE:       NA
              PERSIST:     NO           INSRVMOD:    NA
              RANGE:      DEP        DEFVALUE:    NA
              UNITS:       NA           SPARSE:      NO
              DESCR:       DEP(RANGE): This object will return 0 when it  is acting as a Root Bridge.
         		In all other cases it will return the Root Port ID, having a value in 
         		the range 1 to maximum number of physical interfaces available in the system. 
         		Maximum number of physical interfaces is obtained from the object issSystemNumberOfPorts in fsiss.mib"
    ::= { fsMstMstiBridgeEntry 5 }

fsMstMstiTimeSinceTopologyChange OBJECT-TYPE
    SYNTAX      TimeTicks
    ACCESS      read-only
    STATUS      mandatory
    DESCRIPTION 
        "The time (in hundredths of a second) since the
         TcWhile Timer for any port in this Bridge was 
         non-zero for this spanning tree instance.
         ALCATEL NOTE:
            ACCESS:      NA           		USAGE:       NA
            PERSIST:     NO           		INSRVMOD:    NA
            RANGE:       NA           		DEFVALUE:    0
            UNITS:       1/100th of Second      SPARSE:      NO
            DESCR:       NA"
    ::= { fsMstMstiBridgeEntry 6 }

fsMstMstiTopChanges OBJECT-TYPE
    SYNTAX      Counter
    ACCESS      read-only
    STATUS      mandatory
    DESCRIPTION 
        "The number of times that there have been atleast
         one non-zero TcWhile Timer on this Bridge for this
         spanning tree instance.
         ALCATEL NOTE:
            ACCESS:      NA           USAGE:       NA
            PERSIST:     NO           INSRVMOD:    NA
            RANGE:       NA           DEFVALUE:    0
            UNITS:       NA           SPARSE:      NO
            DESCR:       NA"
    ::= { fsMstMstiBridgeEntry 7 }

fsMstMstiNewRootBridgeCount OBJECT-TYPE
    SYNTAX      Counter
    ACCESS      read-only
    STATUS      mandatory
    DESCRIPTION 
        "The number of times this Bridge has detected a Root
         Bridge change for this spanning tree instance.
         A Trap is generated on the occurence of this event.
         ALCATEL NOTE:
           ACCESS:      NA           USAGE:       NA
           PERSIST:     NO           INSRVMOD:    NA
           RANGE:       NA           DEFVALUE:    0
           UNITS:       NA           SPARSE:      NO
           DESCR:       NA"
    ::= { fsMstMstiBridgeEntry 8 }

fsMstMstiBridgeRoleSelectionSemState OBJECT-TYPE
    SYNTAX      INTEGER { initbridge(0), roleselection(1) }
    ACCESS      read-only
    STATUS      mandatory
    DESCRIPTION 
        "Current state of the Port Role Selection State Machine          
         for this spanning tree instance for this bridge.
         ALCATEL NOTE:
          ACCESS:      NA           USAGE:       NA
          PERSIST:     NO           INSRVMOD:    NA
          RANGE:       NA           DEFVALUE:    NA
          UNITS:       NA           SPARSE:      NO
          DESCR:       NA"
    ::= { fsMstMstiBridgeEntry 9 }

fsMstInstanceUpCount OBJECT-TYPE
    SYNTAX      Counter
    ACCESS      read-only
    STATUS      mandatory
    DESCRIPTION 
        "The number of times a new spanning tree instance has
         been created.
         A Trap is generated on the occurence of this event.
         ALCATEL NOTE:
            ACCESS:      NA           USAGE:       NA
            PERSIST:     NO           INSRVMOD:    NA
            RANGE:       NA           DEFVALUE:    0
            UNITS:       NA           SPARSE:      NO
            DESCR:       NA"
    ::= { fsMstMstiBridgeEntry 10 }

fsMstInstanceDownCount OBJECT-TYPE
    SYNTAX      Counter
    ACCESS      read-only
    STATUS      mandatory
    DESCRIPTION 
        "The number of times a spanning tree instance has
         been deleted.
         A Trap is generated on the occurence of this event.
         ALCATEL NOTE:
            ACCESS:      NA           USAGE:       NA
            PERSIST:     NO           INSRVMOD:    NA
            RANGE:       NA           DEFVALUE:    0
            UNITS:       NA           SPARSE:      NO
            DESCR:       NA"
    ::= { fsMstMstiBridgeEntry 11 }

fsMstOldDesignatedRoot OBJECT-TYPE
    SYNTAX      BridgeId
    ACCESS      read-only
    STATUS      mandatory
    DESCRIPTION 
        "The bridge identifier of the old root of the spanning
         tree instance as determined by the Spanning Tree Protocol
         as executed by this node. 
         ALCATEL NOTE:
         ACCESS:      NA           USAGE:       NA
         PERSIST:     NO           INSRVMOD:    NA
         RANGE:       NA           DEFVALUE:    NA
         UNITS:       NA           SPARSE:      NO
         DESCR:       NA"
    ::= { fsMstMstiBridgeEntry 12 }

fsMstMstiBridgeRowStatus OBJECT-TYPE
    SYNTAX      RowStatus
    ACCESS      read-write
    STATUS      mandatory
    DESCRIPTION 
        "Specifies the Row Status of the MSTI Bridge entry. 
         To create a new entry this has to be created with the
         CREAT-AND-WAIT or with CREATE-AND-GO. To delete the entry from this
         table, the row status should be set to Destroy.
         ALCATEL NOTE:
         ACCESS:      NA           USAGE:       MAND
         PERSIST:     YES          INSRVMOD:    YES
         RANGE:       1,4,5,6      DEFVALUE:    NA
         UNITS:       NA           SPARSE:      NO
         DESCR:       NA"
    ::= { fsMstMstiBridgeEntry 13 }

fsMstVlanInstanceMappingTable OBJECT-TYPE
    SYNTAX      SEQUENCE OF FsMstVlanInstanceMappingEntry
    ACCESS      not-accessible
    STATUS      mandatory
    DESCRIPTION 
        "This table contains one entry for each instance of MSTP.
         ALCATEL NOTE:
             TABLESIZE: 	16
         	  	DESCR: 	NA"
    ::= { dot1sFutureMst 39 }

fsMstVlanInstanceMappingEntry OBJECT-TYPE
    SYNTAX      FsMstVlanInstanceMappingEntry
    ACCESS      not-accessible
    STATUS      mandatory
    DESCRIPTION 
        "A conceptual row containing the status of the MSTP instance.
         Row creation : A fsMstVlanInstanceMappingEntry shall be created in one 
         		        step by a set-request with fsMstMstiBridgeRowStatus 
         			set to createAndGo(4) or createAndWait(5).
         Row deletion : A fsMstVlanInstanceMappingEntry entry shall be deleted 
         			by setting the fsMstMstiBridgeRowStatus of the specific 
         			entry to destroy(6).
         Index usage : the index is fsMstInstanceIndex.
           Note that entries will be presented to the SNMP manager in full
           lexicographical order :  sorted on fsMstInstanceIndex."
    INDEX       { fsMstInstanceIndex }
    ::= { fsMstVlanInstanceMappingTable 1 }

FsMstVlanInstanceMappingEntry ::= SEQUENCE {
    fsMstInstanceIndex          INTEGER,
    fsMstSetVlanList            OCTET STRING,
    fsMstResetVlanList          OCTET STRING,
    fsMstInstanceVlanMapped     OCTET STRING
}

fsMstInstanceIndex OBJECT-TYPE
    SYNTAX      INTEGER (1..16)
    ACCESS      not-accessible
    STATUS      mandatory
    DESCRIPTION 
        "An arbitrary integer within the range from 1 to the value of
         Max Instance Number that uniquely identifies an instance.
         ALCATEL NOTE:
          ACCESS:      NA           USAGE:       NA
          PERSIST:     YES          INSRVMOD:    NA
          RANGE:       NA           DEFVALUE:    NA
          UNITS:       NA           SPARSE:      NO
          DESCR:       NA"
    ::= { fsMstVlanInstanceMappingEntry 1 }

fsMstSetVlanList OBJECT-TYPE
    SYNTAX      OCTET STRING (SIZE(0..512))
    ACCESS      read-write
    STATUS      mandatory
    DESCRIPTION 
        "A string of octets containing one bit per VLAN for
         the VlanIndex Ranges from 2 through 4094. The
          first octet corresponds to VLANs with VlanIndex values
          1 through 8; the second octet to VLANs 9 through
          16 etc.  The most significant bit of each octet
          corresponds to the lowest VlanIndex value in that octet.
          The set vlans configured by management to map for this 
          Instance. A vlans may not be mapped to this instance if 
          it is already a mapped to this Instance.
         ALCATEL NOTE:
           ACCESS:      NA           USAGE:       NA
           PERSIST:     YES          INSRVMOD:    YES
           RANGE:       NA           DEFVALUE:    NA
           UNITS:       NA           SPARSE:      NO
           DESCR:       Valid VlanIndex Range 2 through 4094"
    ::= { fsMstVlanInstanceMappingEntry 2 }

fsMstResetVlanList OBJECT-TYPE
    SYNTAX      OCTET STRING (SIZE(0..512))
    ACCESS      read-write
    STATUS      mandatory
    DESCRIPTION 
        "A string of octets containing one bit per VLAN for
         the VlanIndex Ranges from 2 through 4094. The
          first octet corresponds to VLANs with VlanIndex values
          1 through 8; the second octet to VLANs 9 through
          16 etc.  The most significant bit of each octet
          corresponds to the lowest VlanIndex value in that octet.
          The set vlans configured by management to unmap from this 
          Instance. A vlans may not be unmapped from this instance if 
          it is not mapped to this Instance.
         ALCATEL NOTE:
           ACCESS:      NA           USAGE:       NA
           PERSIST:     YES          INSRVMOD:    YES
           RANGE:       NA           DEFVALUE:    NA
           UNITS:       NA           SPARSE:      NO
           DESCR:       Valid VlanIndex Range 2 through 4094"
    ::= { fsMstVlanInstanceMappingEntry 3 }

fsMstInstanceVlanMapped OBJECT-TYPE
    SYNTAX      OCTET STRING (SIZE(0..512))
    ACCESS      read-only
    STATUS      mandatory
    DESCRIPTION 
        "A string of octets containing one bit per VLAN for
         the VlanIndex Ranges from 2 through 4094. The
         first octet corresponds to VLANs with VlanIndex values
         1 through 8; the second octet to VLANs 9 through
         16 etc.  The most significant bit of each octet
         corresponds to the lowest VlanIndex value in that octet.
         
         For each VLAN that is mapped to this MSTP instance,
         the bit corresponding to that VLAN is set to '1'.
         ALCATEL NOTE:
         ACCESS:      NA           USAGE:       NA
         PERSIST:     NO           INSRVMOD:    NA
         RANGE:       NA           DEFVALUE:    NA
         UNITS:       NA           SPARSE:      NO
         DESCR:       Valid VlanIndex Range 2 through 4094"
    ::= { fsMstVlanInstanceMappingEntry 4 }

fsMstCistPortTable OBJECT-TYPE
    SYNTAX      SEQUENCE OF FsMstCistPortEntry
    ACCESS      not-accessible
    STATUS      mandatory
    DESCRIPTION 
        "This table contains Common Spanning Tree Port
         Information.
         ALCATEL NOTE:
          TABLESIZE: DEP 
         DESCR: DEP (TABLESIZE)  The range of this table is the maximum number of ports in the
         		  system. This value can be got from the object issSystemNumberOfPorts
         		  in fsiss.mib.	"
    ::= { dot1sFutureMst 40 }

fsMstCistPortEntry OBJECT-TYPE
    SYNTAX      FsMstCistPortEntry
    ACCESS      not-accessible
    STATUS      mandatory
    DESCRIPTION 
        "A list of information maintained by every port for 
         Common Spanning tree.
         Row creation : All entries will be created when a MSTP module is
           		enabled.
         Row deletion : All entries will be deleted when a MSTP module is
                 	   disabled.
         Index usage : the index is fsMstCistPort.
         Note that entries will be presented to the SNMP manager in full
         lexicographical order :  sorted on fsMstCistPort."
    INDEX       { fsMstCistPort }
    ::= { fsMstCistPortTable 1 }

FsMstCistPortEntry ::= SEQUENCE {
    fsMstCistPort                           INTEGER,
    fsMstCistPortPathCost                   INTEGER,
    fsMstCistPortPriority                   INTEGER,
    fsMstCistPortDesignatedRoot             BridgeId,
    fsMstCistPortDesignatedBridge           BridgeId,
    fsMstCistPortDesignatedPort             OCTET STRING,
    fsMstCistPortAdminP2P                   INTEGER,
    fsMstCistPortOperP2P                    TruthValue,
    fsMstCistPortAdminEdgeStatus            TruthValue,
    fsMstCistPortOperEdgeStatus             TruthValue,
    fsMstCistPortProtocolMigration          TruthValue,
    fsMstCistPortState                      INTEGER,
    fsMstCistForcePortState                 INTEGER,
    fsMstCistPortForwardTransitions         Counter,
    fsMstCistPortReceivedBPDUs              Counter,
    fsMstCistPortTransmittedBPDUs           Counter,
    fsMstCistPortInvalidBPDUsRcvd           Counter,
    fsMstCistPortTransmitSemState           INTEGER,
    fsMstCistPortReceiveSemState            INTEGER,
    fsMstCistPortProtMigrationSemState      INTEGER,
    fsMstCistProtocolMigrationCount         Counter,
    fsMstCistPortDesignatedCost             INTEGER,
    fsMstCistPortRegionalRoot               BridgeId,
    fsMstCistPortRegionalPathCost           INTEGER,
    fsMstCistSelectedPortRole               INTEGER,
    fsMstCistCurrentPortRole                INTEGER,
    fsMstCistPortInfoSemState               INTEGER,
    fsMstCistPortRoleTransitionSemState     INTEGER,
    fsMstCistPortStateTransitionSemState    INTEGER,
    fsMstCistPortTopologyChangeSemState     INTEGER,
    fsMstCistPortHelloTime                  Timeout
}

fsMstCistPort OBJECT-TYPE
    SYNTAX      INTEGER (1..24)
    ACCESS      not-accessible
    STATUS      mandatory
    DESCRIPTION 
        "The Port number of the port for which this entry contains   
         spanning tree information.
         ALCATEL NOTE:
          ACCESS:      NA           USAGE:       NA
          PERSIST:     YES          INSRVMOD:    NA
          RANGE:       NA           DEFVALUE:    NA
          UNITS:       NA           SPARSE:      NO
          DESCR:       NA"
    ::= { fsMstCistPortEntry 1 }

fsMstCistPortPathCost OBJECT-TYPE
    SYNTAX      INTEGER (1..200000000)
    ACCESS      read-write
    STATUS      mandatory
    DESCRIPTION 
        "The contribution of this port to the path cost of
         paths towards the CIST Root which include this port.
         ALCATEL NOTE:
         ACCESS:      NA           USAGE:       NA
         PERSIST:     YES          INSRVMOD:    YES
         RANGE:       NA           DEFVALUE:    NA
         UNITS:       NA           SPARSE:      NO
         DESCR:       NA"
    ::= { fsMstCistPortEntry 2 }

fsMstCistPortPriority OBJECT-TYPE
    SYNTAX      INTEGER (0..240)
    ACCESS      read-write
    STATUS      mandatory
    DESCRIPTION 
        "The four most significant bits of the Port Identifier 
         of the Spanning Tree instance can be modified by setting 
         the CistPortPriority value. The values that are set for Port 
         Priority must be in steps of 16.
         ALCATEL NOTE:
           ACCESS:      NA           USAGE:       NA
           PERSIST:     YES          INSRVMOD:    YES
           RANGE:       NA           DEFVALUE:    NA
           UNITS:       NA           SPARSE:      NO
           DESCR:       NA"
    DEFVAL      { 128 }
    ::= { fsMstCistPortEntry 3 }

fsMstCistPortDesignatedRoot OBJECT-TYPE
    SYNTAX      BridgeId
    ACCESS      read-only
    STATUS      mandatory
    DESCRIPTION 
        "The unique Bridge Identifier of the bridge recorded as the  
         CIST Root in the configuration BPDUs transmitted.
         ALCATEL NOTE:
          ACCESS:      NA           USAGE:       NA
          PERSIST:     NO           INSRVMOD:    NA
          RANGE:       NA           DEFVALUE:    NA
          UNITS:       NA           SPARSE:      NO
          DESCR:       NA"
    ::= { fsMstCistPortEntry 4 }

fsMstCistPortDesignatedBridge OBJECT-TYPE
    SYNTAX      BridgeId
    ACCESS      read-only
    STATUS      mandatory
    DESCRIPTION 
        "The unique Bridge Identifier of the bridge which this port  
         considers to be the Designated Bridge for the port's segment.
         ALCATEL NOTE:
          ACCESS:      NA           USAGE:       NA
          PERSIST:     NO           INSRVMOD:    NA
          RANGE:       NA           DEFVALUE:    NA
          UNITS:       NA           SPARSE:      NO
          DESCR:       NA"
    ::= { fsMstCistPortEntry 5 }

fsMstCistPortDesignatedPort OBJECT-TYPE
    SYNTAX      OCTET STRING (SIZE(2))
    ACCESS      read-only
    STATUS      mandatory
    DESCRIPTION 
        "The Port identifier of the port on the Designated Bridge    
         for this port's segment.
         ALCATEL NOTE:
          ACCESS:      NA           USAGE:       NA
          PERSIST:     NO           INSRVMOD:    NA
          RANGE:       NA           DEFVALUE:    NA
          UNITS:       NA           SPARSE:      NO
          DESCR:       NA"
    ::= { fsMstCistPortEntry 6 }

fsMstCistPortAdminP2P OBJECT-TYPE
    SYNTAX      INTEGER { forceTrue(0), forceFalse(1), auto(2) }
    ACCESS      read-write
    STATUS      mandatory
    DESCRIPTION 
        "The administrative point-to-point status of the LAN segment
         attached to this port.  A value of forceTrue(0) indicates that
         this port should always be treated as if it is connected to
         a point-to-point link.  A value of forceFalse(1) indicates
         that this port should be treated as having a shared media
         connection.  A value of auto(2) indicates that this port is
         considered to have a point-to-point link if it is an Aggregator
         and all of its members are aggregatable, or if the MAC entity
         is configured for full duplex operation, either through
         auto-negotiation or by management means.
         ALCATEL NOTE:
           ACCESS:      NA           USAGE:       NA
           PERSIST:     YES          INSRVMOD:    YES
           RANGE:       NA           DEFVALUE:    NA
           UNITS:       NA           SPARSE:      NO
           DESCR:       NA"
    DEFVAL      { auto }
    ::= { fsMstCistPortEntry 7 }

fsMstCistPortOperP2P OBJECT-TYPE
    SYNTAX      TruthValue
    ACCESS      read-only
    STATUS      mandatory
    DESCRIPTION 
        "The operational point-to-point status of the LAN segment
         attached to this port.  It indicates whether a port is
         considered to have a point-to-point connection or not.
         The value is determined by management or by auto-detection,
         as described in the fsMstCistPortAdminP2P object.
         ALCATEL NOTE:
           ACCESS:      NA           USAGE:       NA
           PERSIST:     NO           INSRVMOD:    NA
           RANGE:       1,2          DEFVALUE:    NA
           UNITS:       NA           SPARSE:      NO
           DESCR:       NA"
    ::= { fsMstCistPortEntry 8 }

fsMstCistPortAdminEdgeStatus OBJECT-TYPE
    SYNTAX      TruthValue
    ACCESS      read-write
    STATUS      mandatory
    DESCRIPTION 
        "The administrative value of the Edge Port parameter.  A
         value of TRUE(1) indicates that this port should be
         assumed as an edge-port and a value of FALSE(2) indicates
         that this port should be assumed as a non-edge-port.
         ALCATEL NOTE:
           ACCESS:      NA           USAGE:       NA
           PERSIST:     YES          INSRVMOD:    YES
           RANGE:       1,2          DEFVALUE:    NA
           UNITS:       NA           SPARSE:      NO
           DESCR:       NA"
    DEFVAL      { false }
    ::= { fsMstCistPortEntry 9 }

fsMstCistPortOperEdgeStatus OBJECT-TYPE
    SYNTAX      TruthValue
    ACCESS      read-only
    STATUS      mandatory
    DESCRIPTION 
        "The operational value of the Edge Port parameter.  The
         object is initialized to the value of
         fsMstCistPortAdminEdgeStatus and is set FALSE on reception 
         of a BPDU.
         ALCATEL NOTE:
           ACCESS:      NA           USAGE:       NA
           PERSIST:     NO           INSRVMOD:    NA
           RANGE:       1,2          DEFVALUE:    NA
           UNITS:       NA           SPARSE:      NO
           DESCR:       NA"
    ::= { fsMstCistPortEntry 10 }

fsMstCistPortProtocolMigration OBJECT-TYPE
    SYNTAX      TruthValue
    ACCESS      read-write
    STATUS      mandatory
    DESCRIPTION 
        "The value of state machine variable mcheck for the port.         
         When operating in RSTP/MSTP (version >= 2) mode, writing 
         TRUE(1) to this object forces this port to transmit MSTP 
         BPDUs.
         Any other operation on this object has no effect and
         it always returns FALSE(2) when read.
         ALCATEL NOTE:
          ACCESS:      NA           USAGE:       NA
          PERSIST:     YES          INSRVMOD:    YES
          RANGE:       1,2          DEFVALUE:    NA
          UNITS:       NA           SPARSE:      NO
          DESCR:       NA"
    ::= { fsMstCistPortEntry 11 }

fsMstCistPortState OBJECT-TYPE
    SYNTAX      INTEGER { disabled(1), discarding(2), learning(4), 
                    forwarding(5) }
    ACCESS      read-only
    STATUS      mandatory
    DESCRIPTION 
        "Current state of the Port as defined by the Common    
         spanning tree protocol.
         ALCATEL NOTE:
          ACCESS:      NA           USAGE:       NA
          PERSIST:     NO           INSRVMOD:    NA
          RANGE:       NA           DEFVALUE:    NA
          UNITS:       NA           SPARSE:      NO
          DESCR:       NA"
    ::= { fsMstCistPortEntry 12 }

fsMstCistForcePortState OBJECT-TYPE
    SYNTAX      INTEGER { disabled(0), enabled(1) }
    ACCESS      read-write
    STATUS      mandatory
    DESCRIPTION 
        "Current state of the Port which can be changed to either 
         Disabled or Enabled for the base spanning tree   
         instance.
         ALCATEL NOTE:
          ACCESS:      NA           USAGE:       NA
          PERSIST:     YES          INSRVMOD:    YES
          RANGE:       NA           DEFVALUE:    NA
          UNITS:       NA           SPARSE:      NO
          DESCR:       NA"
    DEFVAL      { enabled }
    ::= { fsMstCistPortEntry 13 }

fsMstCistPortForwardTransitions OBJECT-TYPE
    SYNTAX      Counter
    ACCESS      read-only
    STATUS      mandatory
    DESCRIPTION 
        "Number of times this port has transitioned to the     
         Forwarding State.
         ALCATEL NOTE:
          ACCESS:      NA           USAGE:       NA
          PERSIST:     NO           INSRVMOD:    NA
          RANGE:       NA           DEFVALUE:    0
          UNITS:       NA           SPARSE:      NO
          DESCR:       NA"
    ::= { fsMstCistPortEntry 14 }

fsMstCistPortReceivedBPDUs OBJECT-TYPE
    SYNTAX      Counter
    ACCESS      read-only
    STATUS      mandatory
    DESCRIPTION 
        "Number of BPDUs received on this port.
         ALCATEL NOTE:
            ACCESS:      NA           USAGE:       NA
            PERSIST:     NO           INSRVMOD:    NA
            RANGE:       NA           DEFVALUE:    0
            UNITS:       BPDU         SPARSE:      NO
            DESCR:       NA"
    ::= { fsMstCistPortEntry 15 }

fsMstCistPortTransmittedBPDUs OBJECT-TYPE
    SYNTAX      Counter
    ACCESS      read-only
    STATUS      mandatory
    DESCRIPTION 
        "Number of BPDUs transmitted on this port.
         ALCATEL NOTE:
            ACCESS:      NA           USAGE:       NA
            PERSIST:     NO           INSRVMOD:    NA
            RANGE:       NA           DEFVALUE:    0
            UNITS:       BPDU         SPARSE:      NO
            DESCR:       NA"
    ::= { fsMstCistPortEntry 16 }

fsMstCistPortInvalidBPDUsRcvd OBJECT-TYPE
    SYNTAX      Counter
    ACCESS      read-only
    STATUS      mandatory
    DESCRIPTION 
        "Number of Invalid BPDUs received on this port.
         ALCATEL NOTE:
            ACCESS:      NA           USAGE:       NA
            PERSIST:     NO           INSRVMOD:    NA
            RANGE:       NA           DEFVALUE:    0
            UNITS:       BPDU         SPARSE:      NO
            DESCR:       NA"
    ::= { fsMstCistPortEntry 17 }

fsMstCistPortTransmitSemState OBJECT-TYPE
    SYNTAX      INTEGER { transmitinit(0), transmitperiodic(1), 
                    transmitconfig(2), transmittcn(3), transmitrstp(4), 
                    idle(5) }
    ACCESS      read-only
    STATUS      mandatory
    DESCRIPTION 
        "Indicates current State of the Port Transmit state machine.
         ALCATEL NOTE:
            ACCESS:      NA           USAGE:       NA
            PERSIST:     NO           INSRVMOD:    NA
            RANGE:       NA           DEFVALUE:    NA
            UNITS:       NA           SPARSE:      NO
            DESCR:       NA"
    ::= { fsMstCistPortEntry 18 }

fsMstCistPortReceiveSemState OBJECT-TYPE
    SYNTAX      INTEGER { discard(0), receive(1) }
    ACCESS      read-only
    STATUS      mandatory
    DESCRIPTION 
        "Indicates current State of the Port Receive state machine.
         ALCATEL NOTE:
            ACCESS:      NA           USAGE:       NA
            PERSIST:     NO           INSRVMOD:    NA
            RANGE:       NA           DEFVALUE:    NA
            UNITS:       NA           SPARSE:      NO
            DESCR:       NA"
    ::= { fsMstCistPortEntry 19 }

fsMstCistPortProtMigrationSemState OBJECT-TYPE
    SYNTAX      INTEGER { init(0), sendrstp(1), sendingrstp(2), 
                    sendstp(3), sendingstp(4) }
    ACCESS      read-only
    STATUS      mandatory
    DESCRIPTION 
        "Indicates current State of the Port Protocol Migration
         State machine.
         ALCATEL NOTE:
          ACCESS:      NA           USAGE:       NA
          PERSIST:     NO           INSRVMOD:    NA
          RANGE:       NA           DEFVALUE:    NA
          UNITS:       NA           SPARSE:      NO
          DESCR:       NA"
    ::= { fsMstCistPortEntry 20 }

fsMstCistProtocolMigrationCount OBJECT-TYPE
    SYNTAX      Counter
    ACCESS      read-only
    STATUS      mandatory
    DESCRIPTION 
        "The number of times this Port has migrated from one STP protocol 
         version to another. The relevant protocols are STP-COMPATIBLE and 
         RSTP/MSTP.
         A Trap is generated on the occurence of this event.
         	ALCATEL NOTE:
             ACCESS:      NA           USAGE:       NA
             PERSIST:     NO           INSRVMOD:    NA
             RANGE:       NA           DEFVALUE:    0
             UNITS:       NA           SPARSE:      NO
             DESCR:       NA"
    ::= { fsMstCistPortEntry 21 }

fsMstCistPortDesignatedCost OBJECT-TYPE
    SYNTAX      INTEGER
    ACCESS      read-only
    STATUS      mandatory
    DESCRIPTION 
        "The path cost of the Designated Port of the
         segment connected to this port.
         ALCATEL NOTE:
         ACCESS:      NA           USAGE:       NA
         PERSIST:     NO           INSRVMOD:    NA
         RANGE:       NA           DEFVALUE:    NA
         UNITS:       NA           SPARSE:      NO
         DESCR:       NA"
    ::= { fsMstCistPortEntry 22 }

fsMstCistPortRegionalRoot OBJECT-TYPE
    SYNTAX      BridgeId
    ACCESS      read-only
    STATUS      mandatory
    DESCRIPTION 
        "The unique Bridge Identifier of the bridge recorded as the  
         CIST Regional Root Identifier in the configuration BPDUs 
         transmitted.
         ALCATEL NOTE:
          ACCESS:      NA           USAGE:       NA
          PERSIST:     NO           INSRVMOD:    NA
          RANGE:       NA           DEFVALUE:    NA
          UNITS:       NA           SPARSE:      NO
          DESCR:       NA"
    ::= { fsMstCistPortEntry 23 }

fsMstCistPortRegionalPathCost OBJECT-TYPE
    SYNTAX      INTEGER
    ACCESS      read-only
    STATUS      mandatory
    DESCRIPTION 
        "The contribution of this port to the path cost of paths     
         towards the CIST Regional Root which include this port.
         ALCATEL NOTE:
          ACCESS:      NA           USAGE:       NA
          PERSIST:     NO           INSRVMOD:    NA
          RANGE:       NA           DEFVALUE:    NA
          UNITS:       NA           SPARSE:      NO
          DESCR:       NA"
    ::= { fsMstCistPortEntry 24 }

fsMstCistSelectedPortRole OBJECT-TYPE
    SYNTAX      INTEGER { disabled(0), alternate(1), backup(2), root(3), 
                    designated(4) }
    ACCESS      read-only
    STATUS      mandatory
    DESCRIPTION 
        "Selected Port Role of the port for this spanning 
         tree instance.
         ALCATEL NOTE:
           ACCESS:      NA           USAGE:       NA
           PERSIST:     NO           INSRVMOD:    NA
           RANGE:       NA           DEFVALUE:    NA
           UNITS:       NA           SPARSE:      NO
           DESCR:       NA"
    ::= { fsMstCistPortEntry 25 }

fsMstCistCurrentPortRole OBJECT-TYPE
    SYNTAX      INTEGER { disabled(0), alternate(1), backup(2), root(3), 
                    designated(4) }
    ACCESS      read-only
    STATUS      mandatory
    DESCRIPTION 
        "Current Port Role of the port for this spanning 
         tree instance.
         ALCATEL NOTE:
           ACCESS:      NA           USAGE:       NA
           PERSIST:     NO           INSRVMOD:    NA
           RANGE:       NA           DEFVALUE:    NA
           UNITS:       NA           SPARSE:      NO
           DESCR:       NA"
    ::= { fsMstCistPortEntry 26 }

fsMstCistPortInfoSemState OBJECT-TYPE
    SYNTAX      INTEGER { disabled(0), enabled(1), aged(2), update(3), 
                    superiordesg(4), repeatdesg(5), root(6), other(7), 
                    present(8), receive(9) }
    ACCESS      read-only
    STATUS      mandatory
    DESCRIPTION 
        "Current state of the Port Information State Machine          
         for this port in this spanning tree context.
         ALCATEL NOTE:
          ACCESS:      NA           USAGE:       NA
          PERSIST:     NO           INSRVMOD:    NA
          RANGE:       NA           DEFVALUE:    NA
          UNITS:       NA           SPARSE:      NO
          DESCR:       NA"
    ::= { fsMstCistPortEntry 27 }

fsMstCistPortRoleTransitionSemState OBJECT-TYPE
    SYNTAX      INTEGER { init(0), blockport(1), blockedport(2), 
                    activeport(3) }
    ACCESS      read-only
    STATUS      mandatory
    DESCRIPTION 
        "Current state of the Port Role Transition State Machine          
         for this port in this spanning tree context.
         ALCATEL NOTE:
          ACCESS:      NA           USAGE:       NA
          PERSIST:     NO           INSRVMOD:    NA
          RANGE:       NA           DEFVALUE:    NA
          UNITS:       NA           SPARSE:      NO
          DESCR:       NA"
    ::= { fsMstCistPortEntry 28 }

fsMstCistPortStateTransitionSemState OBJECT-TYPE
    SYNTAX      INTEGER { discarding(0), learning(1), forwarding(2) }
    ACCESS      read-only
    STATUS      mandatory
    DESCRIPTION 
        "Current state of the Port State Transition State Machine          
         for this port in this spanning tree context.
         ALCATEL NOTE:
          ACCESS:      NA           USAGE:       NA
          PERSIST:     NO           INSRVMOD:    NA
          RANGE:       NA           DEFVALUE:    NA
          UNITS:       NA           SPARSE:      NO
          DESCR:       NA"
    ::= { fsMstCistPortEntry 29 }

fsMstCistPortTopologyChangeSemState OBJECT-TYPE
    SYNTAX      INTEGER { init(0), inactive(1), active(2), detected(3), 
                    notifiedtcn(4), notifiedtc(5), propagating(6), 
                    acknowledged(7) }
    ACCESS      read-only
    STATUS      mandatory
    DESCRIPTION 
        "Current state of the Topology Change State Machine          
         for this port in this spanning tree context.
         ALCATEL NOTE:
          ACCESS:      NA           USAGE:       NA
          PERSIST:     NO           INSRVMOD:    NA
          RANGE:       NA           DEFVALUE:    NA
          UNITS:       NA           SPARSE:      NO
          DESCR:       NA"
    ::= { fsMstCistPortEntry 30 }

fsMstCistPortHelloTime OBJECT-TYPE
    SYNTAX      Timeout (100..1000)
    ACCESS      read-write
    STATUS      mandatory
    DESCRIPTION 
        "The amount of time between the transmission of
         Configuration bridge PDUs by this node on this port
         in units of hundredths of a second.
         ALCATEL NOTE:
         ACCESS:      NA           		USAGE:       NA
         PERSIST:     YES          		INSRVMOD:    YES
         RANGE:       NA           		DEFVALUE:    NA
         UNITS:       1/100th of Second      SPARSE:      NO
         DESCR:       (2 * ((fsMstCistPortHelloTime/100) + 1)) should be 
         		 less than or equal to fsMstCistBridgeMaxAge. This object can be set 
         		 only when fsMstForceProtocolVersion is mstp(3)"
    DEFVAL      { 200 }
    ::= { fsMstCistPortEntry 31 }

fsMstMstiPortTable OBJECT-TYPE
    SYNTAX      SEQUENCE OF FsMstMstiPortEntry
    ACCESS      not-accessible
    STATUS      mandatory
    DESCRIPTION 
        "This table contains Spanning Tree Instance Specific Port
         Information.
         ALCATEL NOTE:
          TABLESIZE: DEP
         DESCR: DEP(TABLESIZE)	The range of this table is the number of msti instances
         			multiplied by the number of ports. The number of ports
         			can be obtained from the object issSystemNumberOfPorts 
         			in fsiss.mib."
    ::= { dot1sFutureMst 41 }

fsMstMstiPortEntry OBJECT-TYPE
    SYNTAX      FsMstMstiPortEntry
    ACCESS      not-accessible
    STATUS      mandatory
    DESCRIPTION 
        "A list of information maintained by every port for each 
         and every spanning tree instance.
         Row creation : An fsMstMstiPortEntry will be created for all the Member 
         		Ports associated with the VLAN of an MST Instance.
         Row deletion : An fsMstMstiPortEntry will be deleted if the Member 
         		port is disassociated from the VLAN of an MST Instance or 
         		when the MST Instance is deleted.
         Index usage : the index is fsMstMstiPort and fsMstInstanceIndex.
         Note that entries will be presented to the SNMP manager in full
         lexicographical order :  sorted on fsMstMstiPort, then on fsMstInstanceIndex."
    INDEX       { fsMstMstiPort, fsMstInstanceIndex }
    ::= { fsMstMstiPortTable 1 }

FsMstMstiPortEntry ::= SEQUENCE {
    fsMstMstiPort                           INTEGER,
    fsMstMstiPortPathCost                   INTEGER,
    fsMstMstiPortPriority                   INTEGER,
    fsMstMstiPortDesignatedRoot             BridgeId,
    fsMstMstiPortDesignatedBridge           BridgeId,
    fsMstMstiPortDesignatedPort             OCTET STRING,
    fsMstMstiPortState                      INTEGER,
    fsMstMstiForcePortState                 INTEGER,
    fsMstMstiPortForwardTransitions         Counter,
    fsMstMstiPortReceivedBPDUs              Counter,
    fsMstMstiPortTransmittedBPDUs           Counter,
    fsMstMstiPortInvalidBPDUsRcvd           Counter,
    fsMstMstiPortDesignatedCost             INTEGER,
    fsMstMstiSelectedPortRole               INTEGER,
    fsMstMstiCurrentPortRole                INTEGER,
    fsMstMstiPortInfoSemState               INTEGER,
    fsMstMstiPortRoleTransitionSemState     INTEGER,
    fsMstMstiPortStateTransitionSemState    INTEGER,
    fsMstMstiPortTopologyChangeSemState     INTEGER
}

fsMstMstiPort OBJECT-TYPE
    SYNTAX      INTEGER (1..24)
    ACCESS      not-accessible
    STATUS      mandatory
    DESCRIPTION 
        "The Port number of the port for which this entry contains   
         spanning tree information.
         ALCATEL NOTE:
          ACCESS:      NA           USAGE:       NA
          PERSIST:     YES          INSRVMOD:    NA
          RANGE:       NA           DEFVALUE:    NA
          UNITS:       NA           SPARSE:      NO
          DESCR:       NA"
    ::= { fsMstMstiPortEntry 1 }

fsMstMstiPortPathCost OBJECT-TYPE
    SYNTAX      INTEGER (1..200000000)
    ACCESS      read-write
    STATUS      mandatory
    DESCRIPTION 
        "The contribution of this port to the path cost of
         paths towards the MSTI Root which include this port.
         ALCATEL NOTE:
          ACCESS:      NA           USAGE:       NA
          PERSIST:     YES          INSRVMOD:    YES
          RANGE:       NA           DEFVALUE:    NA
          UNITS:       NA           SPARSE:      NO
          DESCR:       NA"
    ::= { fsMstMstiPortEntry 2 }

fsMstMstiPortPriority OBJECT-TYPE
    SYNTAX      INTEGER (0..240)
    ACCESS      read-write
    STATUS      mandatory
    DESCRIPTION 
        "The four most significant bits of the Port Identifier 
         for a given Spanning Tree instance can be modified 
         independently for each Spanning Tree instance 
         supported by the Bridge. The values that are set for Port 
         Priority must be in steps of 16.
         ALCATEL NOTE:
           ACCESS:      NA           USAGE:       NA
           PERSIST:     YES          INSRVMOD:    YES
           RANGE:       NA           DEFVALUE:    NA
           UNITS:       NA           SPARSE:      NO
           DESCR:       NA"
    DEFVAL      { 128 }
    ::= { fsMstMstiPortEntry 3 }

fsMstMstiPortDesignatedRoot OBJECT-TYPE
    SYNTAX      BridgeId
    ACCESS      read-only
    STATUS      mandatory
    DESCRIPTION 
        "The unique Bridge Identifier of the bridge recorded as the  
         MSTI Regional Root in the configuration BPDUs transmitted.
         ALCATEL NOTE:
          ACCESS:      NA           USAGE:       NA
          PERSIST:     NO           INSRVMOD:    NA
          RANGE:       NA           DEFVALUE:    NA
          UNITS:       NA           SPARSE:      NO
          DESCR:       NA"
    ::= { fsMstMstiPortEntry 4 }

fsMstMstiPortDesignatedBridge OBJECT-TYPE
    SYNTAX      BridgeId
    ACCESS      read-only
    STATUS      mandatory
    DESCRIPTION 
        "The unique Bridge Identifier of the bridge which this port  
         considers to be the Designated Bridge for the port's segment.
         ALCATEL NOTE:
          ACCESS:      NA           USAGE:       NA
          PERSIST:     NO           INSRVMOD:    NA
          RANGE:       NA           DEFVALUE:    NA
          UNITS:       NA           SPARSE:      NO
          DESCR:       NA"
    ::= { fsMstMstiPortEntry 5 }

fsMstMstiPortDesignatedPort OBJECT-TYPE
    SYNTAX      OCTET STRING (SIZE(2))
    ACCESS      read-only
    STATUS      mandatory
    DESCRIPTION 
        "The Port identifier of the port on the Designated Bridge    
         for this port's segment.
         ALCATEL NOTE:
          ACCESS:      NA           USAGE:       NA
          PERSIST:     NO           INSRVMOD:    NA
          RANGE:       NA           DEFVALUE:    NA
          UNITS:       NA           SPARSE:      NO
          DESCR:       NA"
    ::= { fsMstMstiPortEntry 6 }

fsMstMstiPortState OBJECT-TYPE
    SYNTAX      INTEGER { disabled(1), discarding(2), learning(4), 
                    forwarding(5) }
    ACCESS      read-only
    STATUS      mandatory
    DESCRIPTION 
        "Current state of the Port as defined by the Multiple  
         spanning tree protocol. Port which is Forwarding state
         in one instance can be in Discarding (Blocking) state 
         in another instance.
         ALCATEL NOTE:
          ACCESS:      NA           USAGE:       NA
          PERSIST:     NO           INSRVMOD:    NA
          RANGE:       NA           DEFVALUE:    NA
          UNITS:       NA           SPARSE:      NO
          DESCR:       NA"
    ::= { fsMstMstiPortEntry 7 }

fsMstMstiForcePortState OBJECT-TYPE
    SYNTAX      INTEGER { disabled(0), enabled(1) }
    ACCESS      read-write
    STATUS      mandatory
    DESCRIPTION 
        "Current state of the Port which can be changed to either 
         Disabled or Enabled for the specific spanning tree   
         instance.
         ALCATEL NOTE:
          ACCESS:      NA           USAGE:       NA
          PERSIST:     YES          INSRVMOD:    YES
          RANGE:       NA           DEFVALUE:    NA
          UNITS:       NA           SPARSE:      NO
          DESCR:       NA"
    DEFVAL      { enabled }
    ::= { fsMstMstiPortEntry 8 }

fsMstMstiPortForwardTransitions OBJECT-TYPE
    SYNTAX      Counter
    ACCESS      read-only
    STATUS      mandatory
    DESCRIPTION 
        "Number of times this port has transitioned to the     
         Forwarding State for specific instance.
         ALCATEL NOTE:
          ACCESS:      NA           USAGE:       NA
          PERSIST:     NO           INSRVMOD:    NA
          RANGE:       NA           DEFVALUE:    0
          UNITS:       NA           SPARSE:      NO
          DESCR:       NA"
    ::= { fsMstMstiPortEntry 9 }

fsMstMstiPortReceivedBPDUs OBJECT-TYPE
    SYNTAX      Counter
    ACCESS      read-only
    STATUS      mandatory
    DESCRIPTION 
        "Number of BPDUs received by this port for this 
         spanning tree instance.
         ALCATEL NOTE:
           ACCESS:      NA           USAGE:       NA
           PERSIST:     NO           INSRVMOD:    NA
           RANGE:       NA           DEFVALUE:    0
           UNITS:       BPDU         SPARSE:      NO
           DESCR:       NA"
    ::= { fsMstMstiPortEntry 10 }

fsMstMstiPortTransmittedBPDUs OBJECT-TYPE
    SYNTAX      Counter
    ACCESS      read-only
    STATUS      mandatory
    DESCRIPTION 
        "Number of BPDUs transmitted on this port for 
         this spanning tree instance.
         ALCATEL NOTE:
           ACCESS:      NA           USAGE:       NA
           PERSIST:     NO           INSRVMOD:    NA
           RANGE:       NA           DEFVALUE:    0
           UNITS:       BPDU         SPARSE:      NO
           DESCR:       NA"
    ::= { fsMstMstiPortEntry 11 }

fsMstMstiPortInvalidBPDUsRcvd OBJECT-TYPE
    SYNTAX      Counter
    ACCESS      read-only
    STATUS      mandatory
    DESCRIPTION 
        "Number of Invalid BPDUs received on this Port
         for this spanning tree instance.
         ALCATEL NOTE:
          ACCESS:      NA           USAGE:       NA
          PERSIST:     NO           INSRVMOD:    NA
          RANGE:       NA           DEFVALUE:    0
          UNITS:       BPDU         SPARSE:      NO
          DESCR:       NA"
    ::= { fsMstMstiPortEntry 12 }

fsMstMstiPortDesignatedCost OBJECT-TYPE
    SYNTAX      INTEGER
    ACCESS      read-only
    STATUS      mandatory
    DESCRIPTION 
        "The path cost of the Designated Port of the
         segment connected to this port.
         ALCATEL NOTE:
         ACCESS:      NA           USAGE:       NA
         PERSIST:     NO           INSRVMOD:    NA
         RANGE:       NA           DEFVALUE:    NA
         UNITS:       NA           SPARSE:      NO
         DESCR:       NA"
    ::= { fsMstMstiPortEntry 13 }

fsMstMstiSelectedPortRole OBJECT-TYPE
    SYNTAX      INTEGER { disabled(0), alternate(1), backup(2), root(3), 
                    designated(4), master(5) }
    ACCESS      read-only
    STATUS      mandatory
    DESCRIPTION 
        "Selected Port Role of the port for this spanning 
         tree instance.
         ALCATEL NOTE:
           ACCESS:      NA           USAGE:       NA
           PERSIST:     NO           INSRVMOD:    NA
           RANGE:       NA           DEFVALUE:    NA
           UNITS:       NA           SPARSE:      NO
           DESCR:       NA"
    ::= { fsMstMstiPortEntry 14 }

fsMstMstiCurrentPortRole OBJECT-TYPE
    SYNTAX      INTEGER { disabled(0), alternate(1), backup(2), root(3), 
                    designated(4), master(5) }
    ACCESS      read-only
    STATUS      mandatory
    DESCRIPTION 
        "Current Port Role of the port for this spanning 
         tree instance.
         ALCATEL NOTE:
           ACCESS:      NA           USAGE:       NA
           PERSIST:     NO           INSRVMOD:    NA
           RANGE:       NA           DEFVALUE:    NA
           UNITS:       NA           SPARSE:      NO
           DESCR:       NA"
    ::= { fsMstMstiPortEntry 15 }

fsMstMstiPortInfoSemState OBJECT-TYPE
    SYNTAX      INTEGER { disabled(0), enabled(1), aged(2), update(3), 
                    superiordesg(4), repeatdesg(5), root(6), other(7), 
                    present(8), receive(9) }
    ACCESS      read-only
    STATUS      mandatory
    DESCRIPTION 
        "Current state of the Port Information State Machine          
         for this port in this spanning tree context.
         ALCATEL NOTE:
          ACCESS:      NA           USAGE:       NA
          PERSIST:     NO           INSRVMOD:    NA
          RANGE:       NA           DEFVALUE:    NA
          UNITS:       NA           SPARSE:      NO
          DESCR:       NA"
    ::= { fsMstMstiPortEntry 16 }

fsMstMstiPortRoleTransitionSemState OBJECT-TYPE
    SYNTAX      INTEGER { init(0), blockport(1), blockedport(2), 
                    activeport(3) }
    ACCESS      read-only
    STATUS      mandatory
    DESCRIPTION 
        "Current state of the Port Role Transition State Machine          
         for this port in this spanning tree context.
         ALCATEL NOTE:
          ACCESS:      NA           USAGE:       NA
          PERSIST:     NO           INSRVMOD:    NA
          RANGE:       NA           DEFVALUE:    NA
          UNITS:       NA           SPARSE:      NO
          DESCR:       NA"
    ::= { fsMstMstiPortEntry 17 }

fsMstMstiPortStateTransitionSemState OBJECT-TYPE
    SYNTAX      INTEGER { discarding(0), learning(1), forwarding(2) }
    ACCESS      read-only
    STATUS      mandatory
    DESCRIPTION 
        "Current state of the Port State Transition State Machine          
         for this port in this spanning tree context.
         ALCATEL NOTE:
          ACCESS:      NA           USAGE:       NA
          PERSIST:     NO           INSRVMOD:    NA
          RANGE:       NA           DEFVALUE:    NA
          UNITS:       NA           SPARSE:      NO
          DESCR:       NA"
    ::= { fsMstMstiPortEntry 18 }

fsMstMstiPortTopologyChangeSemState OBJECT-TYPE
    SYNTAX      INTEGER { init(0), inactive(1), active(2), detected(3), 
                    notifiedtcn(4), notifiedtc(5), propagating(6), 
                    acknowledged(7) }
    ACCESS      read-only
    STATUS      mandatory
    DESCRIPTION 
        "Current state of the Topology Change State Machine          
         for this port in this spanning tree context.
         ALCATEL NOTE:
          ACCESS:      NA           USAGE:       NA
          PERSIST:     NO           INSRVMOD:    NA
          RANGE:       NA           DEFVALUE:    NA
          UNITS:       NA           SPARSE:      NO
          DESCR:       NA"
    ::= { fsMstMstiPortEntry 19 }

fsMstNextFreeMSTiIndex OBJECT-TYPE
    SYNTAX      INTEGER
    ACCESS      read-only
    STATUS      mandatory
    DESCRIPTION 
        "A index to indicate the next free entry in the MSTI Bridge Table
         ALCATEL NOTE:
            ACCESS:      NA           								USAGE:       NA
            PERSIST:     NO           								INSRVMOD:    NA
            RANGE:       1..(fsMstMaxMstInstanceNumber-1)   DEFVALUE:    1
            UNITS:       NA           								SPARSE:      NA
            DESCR:       When there are no instances free the value returned 
         							 will be fsMstMaxMstInstanceNumber"
    ::= { dot1sFutureMst 42 }

dot1sFsMstTrapsControl OBJECT IDENTIFIER
    ::= { futureMstMIB 2 }

fsMstSetTraps OBJECT-TYPE
    SYNTAX      INTEGER (0..255)
    ACCESS      read-write
    STATUS      mandatory
    DESCRIPTION 
        "This object is used to enable and  disable  specific
         MSTP traps. Currently the following are defined
         0 - Traps are not enabled.
         1 - General Traps like protocol up or down 
         2 - Exception Traps like memory failure or buffer failure 
                  or port protocol migration or invalid packet rcvd in port
         3 - All the above Traps 
         ALCATEL NOTE:
          ACCESS:      NA           USAGE:       NA
          PERSIST:     YES          INSRVMOD:    YES
          RANGE:       NA           DEFVALUE:    NA
          UNITS:       NA           SPARSE:      NA
          DESCR:       NA"
    DEFVAL      { 0 }
    ::= { dot1sFsMstTrapsControl 1 }

fsMstGenTrapType OBJECT-TYPE
    SYNTAX      INTEGER { none(0), up(1), down(2) }
    ACCESS      read-only
    STATUS      mandatory
    DESCRIPTION 
        "The general events like 
         none - none of the below values
         up - protocol UP,
         down - protocol DOWN
         ALCATEL NOTE:
          ACCESS:      NA           USAGE:       NA
          PERSIST:     NO           INSRVMOD:    NA
          RANGE:       NA           DEFVALUE:    NA
          UNITS:       NA           SPARSE:      NA
          DESCR:       NA"
    ::= { dot1sFsMstTrapsControl 2 }

fsMstErrTrapType OBJECT-TYPE
    SYNTAX      INTEGER { none(0), memfail(1), bufffail(2) }
    ACCESS      read-only
    STATUS      mandatory
    DESCRIPTION 
        "The error event like
         none - none of the below values
         memfail - memory allocation failure
         bufffail - buffer allocation failure
         ALCATEL NOTE:
         ACCESS:      NA           USAGE:       NA
         PERSIST:     NO           INSRVMOD:    NA
         RANGE:       NA           DEFVALUE:    NA
         UNITS:       NA           SPARSE:      NA
         DESCR:       NA"
    ::= { dot1sFsMstTrapsControl 3 }

fsMstPortTrapNotificationTable OBJECT-TYPE
    SYNTAX      SEQUENCE OF FsMstPortNotificationEntry
    ACCESS      not-accessible
    STATUS      mandatory
    DESCRIPTION 
        "This table is used to store the notification information
         occured in each of the port for protocol migration and 
         invalid packet received
          ALCATEL NOTE:
              TABLESIZE: 	DEP
         	  	DESCR: 	DEP(TABLESIZE): The size of table is obtained from Maximum number of physical interfaces
         			available in the system (obtained from issSystemNumberOfPorts in fsiss.mib)"
    ::= { dot1sFsMstTrapsControl 4 }

fsMstPortNotificationEntry OBJECT-TYPE
    SYNTAX      FsMstPortNotificationEntry
    ACCESS      not-accessible
    STATUS      mandatory
    DESCRIPTION 
        " This entry is used to store the notification information
         Row creation : All entries will be created when a MSTP module is
         	   		enabled.
         Row deletion : All entries will be deleted when a MSTP module is
                     	   disabled.
         Index usage : the index is fsMstPortTrapIndex.
           Note that entries will be presented to the SNMP manager in full
           lexicographical order :  sorted on fsMstPortTrapIndex."
    INDEX       { fsMstPortTrapIndex }
    ::= { fsMstPortTrapNotificationTable 1 }

FsMstPortNotificationEntry ::= SEQUENCE {
    fsMstPortTrapIndex      INTEGER,
    fsMstPortMigrationType  INTEGER,
    fsMstPktErrType         INTEGER,
    fsMstPktErrVal          INTEGER
}

fsMstPortTrapIndex OBJECT-TYPE
    SYNTAX      INTEGER (1..2147483647)
    ACCESS      read-only
    STATUS      mandatory
    DESCRIPTION 
        "A unique value, greater than zero, indicating the Port number.
         ALCATEL NOTE:
            ACCESS:      NA           USAGE:       NA
            PERSIST:     NO           INSRVMOD:    NA
            RANGE:       DEP        DEFVALUE:    NA
            UNITS:       NA           SPARSE:      NO
            DESCR:       DEP(RANGE):  The rnage is the maximum number of physical interfaces available in the system. 
         	Maximum number of physical interfaces is obtained from the object issSystemNumberOfPorts in fsiss.mib"
    ::= { fsMstPortNotificationEntry 1 }

fsMstPortMigrationType OBJECT-TYPE
    SYNTAX      INTEGER { sendstp(0), sendrstp(1) }
    ACCESS      read-only
    STATUS      mandatory
    DESCRIPTION 
        "Port Protocol migration type occured in the port
         ALCATEL NOTE:
            ACCESS:      NA           USAGE:       NA
            PERSIST:     NO           INSRVMOD:    NA
            RANGE:       NA           DEFVALUE:    NA
            UNITS:       NA           SPARSE:      NO
            DESCR:       NA"
    ::= { fsMstPortNotificationEntry 2 }

fsMstPktErrType OBJECT-TYPE
    SYNTAX      INTEGER { protocolIdErr(0), invalidBpdu(1), 
                    configLengthErr(2), tcnLengthErr(3), 
                    rstpLengthErr(4), maxAgeErr(5), fwdDelayErr(6), 
                    helloTimeErr(7), mstpLengthErr(8) }
    ACCESS      read-only
    STATUS      mandatory
    DESCRIPTION 
        "Type of invalid packet received in each of the port 
         ALCATEL NOTE:
            ACCESS:      NA           USAGE:       NA
            PERSIST:     NO           INSRVMOD:    NA
            RANGE:       NA           DEFVALUE:    NA
            UNITS:       NA           SPARSE:      NO
            DESCR:       NA"
    ::= { fsMstPortNotificationEntry 3 }

fsMstPktErrVal OBJECT-TYPE
    SYNTAX      INTEGER
    ACCESS      read-only
    STATUS      mandatory
    DESCRIPTION 
        "Packet error value corresponding to the above type 
         ALCATEL NOTE:
            ACCESS:      NA           USAGE:       NA
            PERSIST:     NO           INSRVMOD:    NA
            RANGE:       NA           DEFVALUE:    NA
            UNITS:       NA           SPARSE:      NO
            DESCR:       NA"
    ::= { fsMstPortNotificationEntry 4 }

fsMstTrapCount OBJECT-TYPE
    SYNTAX      Counter
    ACCESS      read-only
    STATUS      mandatory
    DESCRIPTION 
        "The number of times MSTP Module has generated a TRAP.
         ALCATEL NOTE:
            ACCESS:      NA           USAGE:       NA
            PERSIST:     NO           INSRVMOD:    NA
            RANGE:       NA           DEFVALUE:    0
            UNITS:       NA           SPARSE:      NA
            DESCR:       NA"
    ::= { dot1sFsMstTrapsControl 5 }

dot1sFutureMstTraps OBJECT IDENTIFIER
    ::= { futureMstMIB 3 }

fsMstTraps OBJECT IDENTIFIER
    ::= { dot1sFutureMstTraps 0 }

fsMstGenTrap TRAP-TYPE
    ENTERPRISE  dot1sFutureMstTraps
    VARIABLES   { fsMstBrgAddress, fsMstGenTrapType }
--     STATUS      mandatory
    DESCRIPTION 
        "Generated when any of the general events like protocol up or 
         protocol down occurs"
    ::= 1

fsMstErrTrap TRAP-TYPE
    ENTERPRISE  dot1sFutureMstTraps
    VARIABLES   { fsMstBrgAddress, fsMstErrTrapType }
--     STATUS      mandatory
    DESCRIPTION 
        "Generated when any of the error events like memory failure or buffer failure
         or protocol migration or new root or topology change occurs "
    ::= 2

fsMstNewRootTrap TRAP-TYPE
    ENTERPRISE  dot1sFutureMstTraps
    VARIABLES   { fsMstBrgAddress, fsMstOldDesignatedRoot, 
                  fsMstMstiBridgeRegionalRoot, fsMstMstiInstanceIndex }
--     STATUS      mandatory
    DESCRIPTION 
        "Generated whenever a new root bridge is selected in the topology "
    ::= 3

fsMstTopologyChgTrap TRAP-TYPE
    ENTERPRISE  dot1sFutureMstTraps
    VARIABLES   { fsMstBrgAddress }
--     STATUS      mandatory
    DESCRIPTION 
        "Generated when topology change is detected "
    ::= 4

fsMstProtocolMigrationTrap TRAP-TYPE
    ENTERPRISE  dot1sFutureMstTraps
    VARIABLES   { fsMstBrgAddress, fsMstPortTrapIndex, 
                  fsMstForceProtocolVersion, fsMstPortMigrationType }
--     STATUS      mandatory
    DESCRIPTION 
        "Generated when port protocol migration happens in the port "
    ::= 5

fsMstInvalidBpduRxdTrap TRAP-TYPE
    ENTERPRISE  dot1sFutureMstTraps
    VARIABLES   { fsMstBrgAddress, fsMstPortTrapIndex, fsMstPktErrType, 
                  fsMstPktErrVal }
--     STATUS      mandatory
    DESCRIPTION 
        "Generated when the invalid packet is received for 
         bpdu/stp/rstp/maximum age/forward delay/hello time"
    ::= 6

fsMstRegionConfigChangeTrap TRAP-TYPE
    ENTERPRISE  dot1sFutureMstTraps
    VARIABLES   { fsMstBrgAddress, fsMstMstiConfigIdSel, 
                  fsMstMstiRegionName, fsMstMstiRegionVersion, 
                  fsMstMstiConfigDigest }
--     STATUS      mandatory
    DESCRIPTION 
        "Generated when the MST region's configuration     
         identifier changes."
    ::= 7

END -- end of module FutureMst-MIB.
