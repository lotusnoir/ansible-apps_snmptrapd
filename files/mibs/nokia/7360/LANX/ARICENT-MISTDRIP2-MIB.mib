--
-- This SMIv1 module has been generated by smidump 0.4.8. Do not edit.
--

ARICENT-MISTDRIP2-MIB DEFINITIONS ::= BEGIN

IMPORTS
    fsMIRip2GlobalEntry, fsMIRipContextId
        FROM ARICENT-MIRIP2-MIB
    OBJECT-TYPE
        FROM RFC-1212
    Counter, Gauge, IpAddress, TimeTicks, enterprises
        FROM RFC1155-SMI
    RowStatus
        FROM SNMPv2-TC;

fsMIStdRip OBJECT IDENTIFIER
    ::= { enterprises futuresoftware(2076) 152 }

-- fsMIStdRip MODULE-IDENTITY
--     LAST-UPDATED "200702230000Z"
--     ORGANIZATION 
--         "ARICENT COMMUNICATIONS SOFTWARE"
--     CONTACT-INFO 
--         "Postal: ARICENT COMMUNICATIONS SOFTWARE
--          3460 Hill Avenue,
--          Palo Alto, CA 94304-1388, USA,
--          Phone : +1-650-391-1088
--          E-mail: support@aricent.com"
--     DESCRIPTION 
--         "The enterprise ID 2076 was originally assigned to Future Software
--          Pvt Limited. Future Software is a part of Aricent."
--     REVISION    "200702230000Z"
--     DESCRIPTION 
--         " Changed the standard MIB for MI support"
--     ::= { enterprises futuresoftware(2076) 152 }


RouteTag ::=
    OCTET STRING (SIZE(2))

-- RouteTag ::= TEXTUAL-CONVENTION
--     STATUS      mandatory
--     DESCRIPTION 
--         "the RouteTag type represents the contents of the Route Domain 
--          field in the packet header or route entry"
--     SYNTAX      OCTET STRING (SIZE(2))

fsMIStdRip2Globals OBJECT IDENTIFIER
    ::= { fsMIStdRip 1 }

fsMIStdRip2GlobalTable OBJECT-TYPE
    SYNTAX      SEQUENCE OF FsMIStdRip2GlobalEntry
    ACCESS      not-accessible
    STATUS      mandatory
    DESCRIPTION 
        "This Table Contains the list of globals for a
         Context.
                TABLESIZE: 	64
         	  	DESCR: 	NA"
    ::= { fsMIStdRip2Globals 1 }

fsMIStdRip2GlobalEntry OBJECT-TYPE
    SYNTAX      FsMIStdRip2GlobalEntry
    ACCESS      not-accessible
    STATUS      mandatory
    DESCRIPTION 
        "An entry of fsMIStdRip2GlobalTable.
         Row creation : An entry will be created when  a rip instance is created. 
         Row deletion : An entry will be deleted when a rip instance is deleted.     .
         Index usage : the index is fsMIRip2GlobalEntry.
           Note that entries will be presented to the SNMP manager in full
           lexicographical order :  sorted on fsMIRipContextId."
    INDEX       { fsMIRipContextId }
--     AUGMENTS    { fsMIRip2GlobalEntry }
    ::= { fsMIStdRip2GlobalTable 1 }

FsMIStdRip2GlobalEntry ::= SEQUENCE {
    fsMIStdRip2GlobalRouteChanges   Counter,
    fsMIStdRip2GlobalQueries        Counter
}

fsMIStdRip2GlobalRouteChanges OBJECT-TYPE
    SYNTAX      Counter
    ACCESS      read-only
    STATUS      mandatory
    DESCRIPTION 
        "The number of route changes made to the IP Route 
         Database by RIP.  This does not include the refresh 
         of a route's age. 
         ALCATEL NOTE:
          ACCESS:      NA           USAGE:       NA
          PERSIST:     NO           INSRVMOD:    NA
          RANGE:       NA           DEFVALUE:    0
          UNITS:       NA           SPARSE:      NA
          DESCR:       NA"
    ::= { fsMIStdRip2GlobalEntry 1 }

fsMIStdRip2GlobalQueries OBJECT-TYPE
    SYNTAX      Counter
    ACCESS      read-only
    STATUS      mandatory
    DESCRIPTION 
        "The number of responses sent to RIP queries 
         from other systems. 
         ALCATEL NOTE:
          ACCESS:      NA           USAGE:       NA
          PERSIST:     NO           INSRVMOD:    NA
          RANGE:       NA           DEFVALUE:    0
          UNITS:       RIP Msgs     SPARSE:      NA
          DESCR:       NA"
    ::= { fsMIStdRip2GlobalEntry 2 }

fsMIStdRip2IfStatTable OBJECT-TYPE
    SYNTAX      SEQUENCE OF FsMIStdRip2IfStatEntry
    ACCESS      not-accessible
    STATUS      mandatory
    DESCRIPTION 
        "A list of subnets which require separate 
         status monitoring in RIP. 
         ALCATEL NOTE:
          TABLESIZE:  DEP	
           DESCR:      DEP(TABLESIZE):The range of the index is total number of IP interfaces in the system.
         		This is obtained from the object fsVrfMaxIpInterfaces in fsvrf.mib"
    ::= { fsMIStdRip 2 }

fsMIStdRip2IfStatEntry OBJECT-TYPE
    SYNTAX      FsMIStdRip2IfStatEntry
    ACCESS      not-accessible
    STATUS      mandatory
    DESCRIPTION 
        "A Single Routing Domain in a single Subnet. 
         Row creation : A rip2IfStat entry shall be created in one step by a
             		set-request with all necessary parameter values and
             		rip2IfStatStatus set to createAndGo(4).
         Row deletion : A rip2IfStat entry shall be deleted by setting
             		the rip2IfStatStatus of the specific entry to destroy(6).
         Index usage : the index is the fsMIRipContextId, rip2IfStatAddress.
         Note that entries will be presented to the SNMP manager in full
         lexicographical order :  sorted on fsMIRipContextId then on rip2IfStatAddress."
    INDEX       { fsMIRipContextId, fsMIStdRip2IfStatAddress }
    ::= { fsMIStdRip2IfStatTable 1 }

FsMIStdRip2IfStatEntry ::= SEQUENCE {
    fsMIStdRip2IfStatAddress        IpAddress,
    fsMIStdRip2IfStatRcvBadPackets  Counter,
    fsMIStdRip2IfStatRcvBadRoutes   Counter,
    fsMIStdRip2IfStatSentUpdates    Counter,
    fsMIStdRip2IfStatStatus         RowStatus
}

fsMIStdRip2IfStatAddress OBJECT-TYPE
    SYNTAX      IpAddress
    ACCESS      not-accessible
    STATUS      mandatory
    DESCRIPTION 
        "The IP Address of this system on the indicated 
         subnet. For unnumbered interfaces, the value 0.0.0.N, 
         where the least significant 24 bits (N) is the ifIndex 
         for the IP Interface in network byte order.
         ALCATEL NOTE:
          ACCESS:      NA           USAGE:       NA
          PERSIST:     NO           INSRVMOD:    NA 
          RANGE:       NA           DEFVALUE:    NA       
          UNITS:       NA           SPARSE:      NO
          DESCR:       NA"
    ::= { fsMIStdRip2IfStatEntry 1 }

fsMIStdRip2IfStatRcvBadPackets OBJECT-TYPE
    SYNTAX      Counter
    ACCESS      read-only
    STATUS      mandatory
    DESCRIPTION 
        "The number of RIP response packets received by 
         the RIP process which were subsequently discarded 
         for any reason (e.g. a version 0 packet, or an 
         unknown command type). 
         ALCATEL NOTE:
          ACCESS:      NA           USAGE:       NA 
          PERSIST:     NO           INSRVMOD:    NA  
          RANGE:       NA           DEFVALUE:    0
          UNITS:       RIP Msgs     SPARSE:      NO
          DESCR:       NA"
    ::= { fsMIStdRip2IfStatEntry 2 }

fsMIStdRip2IfStatRcvBadRoutes OBJECT-TYPE
    SYNTAX      Counter
    ACCESS      read-only
    STATUS      mandatory
    DESCRIPTION 
        "The number of routes, in valid RIP packets, 
         which were ignored for any reason (e.g. unknown 
         address family, or invalid metric). 
         ALCATEL NOTE:
          ACCESS:      NA           USAGE:       NA 
          PERSIST:     NO           INSRVMOD:    NA  
          RANGE:       NA           DEFVALUE:    0
          UNITS:       routes       SPARSE:      NO
          DESCR:       NA"
    ::= { fsMIStdRip2IfStatEntry 3 }

fsMIStdRip2IfStatSentUpdates OBJECT-TYPE
    SYNTAX      Counter
    ACCESS      read-only
    STATUS      mandatory
    DESCRIPTION 
        "The number of triggered RIP updates actually 
         sent on this interface.  This explicitly does 
         NOT include full updates sent containing new 
         information. 
         ALCATEL NOTE:
          ACCESS:      NA           USAGE:       NA 
          PERSIST:     NO           INSRVMOD:    NA  
          RANGE:       NA           DEFVALUE:    0
          UNITS:       RIP Msgs     SPARSE:      NO
          DESCR:       NA"
    ::= { fsMIStdRip2IfStatEntry 4 }

fsMIStdRip2IfStatStatus OBJECT-TYPE
    SYNTAX      RowStatus
    ACCESS      read-write
    STATUS      mandatory
    DESCRIPTION 
        "Writing invalid has the effect of deleting 
         this interface. 
         ALCATEL NOTE:
          ACCESS:      NA           USAGE:       MAND
          PERSIST:     NO           INSRVMOD:    YES  
          RANGE:       1,2,4,5,6    DEFVALUE:    NA
          UNITS:       NA           SPARSE:      NO
          DESCR:       NA"
    ::= { fsMIStdRip2IfStatEntry 5 }

fsMIStdRip2IfConfTable OBJECT-TYPE
    SYNTAX      SEQUENCE OF FsMIStdRip2IfConfEntry
    ACCESS      not-accessible
    STATUS      mandatory
    DESCRIPTION 
        "A list of subnets which require separate 
         configuration in RIP. 
         ALCATEL NOTE:
          TABLESIZE: DEP 
          DESCR:   DEP(TABLESIZE): The Value is the total number of RIP interfaces in the system.
         		The total number of RIP interfaces is obtained from fsVrfNoOfRipInterfaces in fsvrf.mib"
    ::= { fsMIStdRip 3 }

fsMIStdRip2IfConfEntry OBJECT-TYPE
    SYNTAX      FsMIStdRip2IfConfEntry
    ACCESS      not-accessible
    STATUS      mandatory
    DESCRIPTION 
        "A Single Routing Domain in a single Subnet. 
         Row creation : A rip2IfConf entry shall be created in one step by a
            		set-request with all necessary parameter values and
            		rip2IfConfStatus set to createAndGo(4).
         Row deletion : A rip2IfConf entry shall be deleted by setting
            		the rip2IfConfStatus of the specific entry to destroy(6).
         Index usage : the index is the fsMIRipContextId, rip2IfConfAddress.
         Note that entries will be presented to the SNMP manager in full
         lexicographical order :  sorted on fsMIRipContextId then on rip2IfConfAddress."
    INDEX       { fsMIRipContextId, fsMIStdRip2IfConfAddress }
    ::= { fsMIStdRip2IfConfTable 1 }

FsMIStdRip2IfConfEntry ::= SEQUENCE {
    fsMIStdRip2IfConfAddress        IpAddress,
    fsMIStdRip2IfConfDomain         RouteTag,
    fsMIStdRip2IfConfAuthType       INTEGER,
    fsMIStdRip2IfConfAuthKey        OCTET STRING,
    fsMIStdRip2IfConfSend           INTEGER,
    fsMIStdRip2IfConfReceive        INTEGER,
    fsMIStdRip2IfConfDefaultMetric  INTEGER,
    fsMIStdRip2IfConfStatus         RowStatus,
    fsMIStdRip2IfConfSrcAddress     IpAddress
}

fsMIStdRip2IfConfAddress OBJECT-TYPE
    SYNTAX      IpAddress
    ACCESS      not-accessible
    STATUS      mandatory
    DESCRIPTION 
        "The IP Address of this system on the indicated 
         subnet.  For unnumbered interfaces, the value 0.0.0.N, 
         where the least significant 24 bits (N) is the ifIndex 
         for the IP Interface in network byte order.
         ALCATEL NOTE:
          ACCESS:      NA           USAGE:       NA
          PERSIST:     YES          INSRVMOD:    NA
          RANGE:       NA           DEFVALUE:    NA       
          UNITS:       NA           SPARSE:      NO
          DESCR:       NA"
    ::= { fsMIStdRip2IfConfEntry 1 }

fsMIStdRip2IfConfDomain OBJECT-TYPE
    SYNTAX      RouteTag
    ACCESS      read-write
    STATUS      obsolete
    DESCRIPTION 
        "Value inserted into the Routing Domain field 
         of all RIP packets sent on this interface. 
         ALCATEL NOTE:
          ACCESS:      NA           USAGE:       OPT
          PERSIST:     YES          INSRVMOD:    YES
          RANGE:       NA           DEFVALUE:    NA       
          UNITS:       NA           SPARSE:      NO
          DESCR:       NA"
    DEFVAL      { '0000'H }
    ::= { fsMIStdRip2IfConfEntry 2 }

fsMIStdRip2IfConfAuthType OBJECT-TYPE
    SYNTAX      INTEGER { noAuthentication(1), simplePassword(2), md5(3) }
    ACCESS      read-write
    STATUS      mandatory
    DESCRIPTION 
        "The type of Authentication used on this 
         interface. 
         ALCATEL NOTE:
          ACCESS:      NA           USAGE:       OPT
          PERSIST:     YES          INSRVMOD:    YES
          RANGE:       NA           DEFVALUE:    NA       
          UNITS:       NA           SPARSE:      NO
          DESCR:       NA"
    DEFVAL      { noAuthentication }
    ::= { fsMIStdRip2IfConfEntry 3 }

fsMIStdRip2IfConfAuthKey OBJECT-TYPE
    SYNTAX      OCTET STRING (SIZE(0..16))
    ACCESS      read-write
    STATUS      mandatory
    DESCRIPTION 
        "The value to be used as the Authentication Key 
         whenever the corresponding instance of 
         fsMIStdRip2IfConfAuthType has a value other than 
         noAuthentication.  A modification of the corresponding 
         instance of fsMIStdRip2IfConfAuthType does not modify 
         the fsMIStdRip2IfConfAuthKey value.  If a string shorter 
         than 16 octets is supplied, it will be left- 
         justified and padded to 16 octets, on the right, 
         with nulls (0x00). 
         
         Reading this object always results in an encrypted  
         key of maximum length 32; authentication may not 
         be bypassed by reading the MIB object. 
         ALCATEL NOTE:
          ACCESS:      NA           USAGE:       OPT
          PERSIST:     YES          INSRVMOD:    YES
          RANGE:       NA           DEFVALUE:    NA       
          UNITS:       NA           SPARSE:      NO
          DESCR:       NA"
    DEFVAL      { "" }
    ::= { fsMIStdRip2IfConfEntry 4 }

fsMIStdRip2IfConfSend OBJECT-TYPE
    SYNTAX      INTEGER { doNotSend(1), ripVersion1(2), 
                    rip1Compatible(3), ripVersion2(4), ripV1Demand(5), 
                    ripV2Demand(6) }
    ACCESS      read-write
    STATUS      mandatory
    DESCRIPTION 
        "What the router sends on this interface. 
         ripVersion1 implies sending RIP updates compliant 
         with  RFC  1058.   rip1Compatible implies 
         broadcasting RIP-2 updates using RFC 1058 route 
         subsumption rules.  ripVersion2 implies 
         multicasting RIP-2 updates.  ripV1Demand indicates 
         the use of Demand RIP on a WAN interface under RIP 
         Version 1 rules.  ripV2Demand indicates the use of 
         Demand RIP on a WAN interface under Version 2 rules.
         ALCATEL NOTE:
          ACCESS:      NA           USAGE:       OPT
          PERSIST:     YES          INSRVMOD:    YES
          RANGE:       NA           DEFVALUE:    NA       
          UNITS:       NA           SPARSE:      NO
          DESCR:       NA"
    DEFVAL      { rip1Compatible }
    ::= { fsMIStdRip2IfConfEntry 5 }

fsMIStdRip2IfConfReceive OBJECT-TYPE
    SYNTAX      INTEGER { rip1(1), rip2(2), rip1OrRip2(3), 
                    doNotRecieve(4) }
    ACCESS      read-write
    STATUS      mandatory
    DESCRIPTION 
        "This indicates which version of RIP updates 
         are to be accepted.  Note that fsMIStdRip2 and 
         rip1OrRip2 implies reception of multicast 
         packets. 
         ALCATEL NOTE:
          ACCESS:      NA           USAGE:       OPT
          PERSIST:     YES          INSRVMOD:    YES
          RANGE:       NA           DEFVALUE:    NA       
          UNITS:       NA           SPARSE:      NO
          DESCR:       NA"
    DEFVAL      { rip1OrRip2 }
    ::= { fsMIStdRip2IfConfEntry 6 }

fsMIStdRip2IfConfDefaultMetric OBJECT-TYPE
    SYNTAX      INTEGER (0..15)
    ACCESS      read-write
    STATUS      mandatory
    DESCRIPTION 
        "This variable indicates the metric that is to 
         be used for the default route entry in RIP updates 
         originated on this interface.  A value of zero 
         indicates that no default route should be 
         originated; in this case, a default route via 
         another router may be propagated. 
         ALCATEL NOTE:
          ACCESS:      NA           USAGE:       MAND
          PERSIST:     YES          INSRVMOD:    YES
          RANGE:       NA           DEFVALUE:    NA       
          UNITS:       NA           SPARSE:      NO
          DESCR:       NA"
    ::= { fsMIStdRip2IfConfEntry 7 }

fsMIStdRip2IfConfStatus OBJECT-TYPE
    SYNTAX      RowStatus
    ACCESS      read-write
    STATUS      mandatory
    DESCRIPTION 
        "Writing invalid has  the  effect  of  deleting 
         this interface. 
         ALCATEL NOTE:
          ACCESS:      NA           USAGE:       MAND
          PERSIST:     YES          INSRVMOD:    YES
          RANGE:       1,2,4,5,6    DEFVALUE:    NA
          UNITS:       NA           SPARSE:      NO
          DESCR:       NA"
    ::= { fsMIStdRip2IfConfEntry 8 }

fsMIStdRip2IfConfSrcAddress OBJECT-TYPE
    SYNTAX      IpAddress
    ACCESS      read-write
    STATUS      mandatory
    DESCRIPTION 
        "The IP Address this system will use as a source 
         address on this interface.  If it is a numbered 
         interface, this MUST be the same value as 
         fsMIStdRip2IfConfAddress.  On unnumbered interfaces, 
         it must be the value of fsMIStdRip2IfConfAddress for 
         some interface on the system. 
         ALCATEL NOTE:
         ACCESS:      NA           USAGE:       MAND
         PERSIST:     YES          INSRVMOD:    YES
         RANGE:       NA           DEFVALUE:    NA     
         UNITS:       NA           SPARSE:      NO
         DESCR:       NA"
    ::= { fsMIStdRip2IfConfEntry 9 }

fsMIStdRip2PeerTable OBJECT-TYPE
    SYNTAX      SEQUENCE OF FsMIStdRip2PeerEntry
    ACCESS      not-accessible
    STATUS      mandatory
    DESCRIPTION 
        "A list of RIP Peers. 
         ALCATEL NOTE:
             TABLESIZE: 	DEP
         	  	DESCR: 	The Default Table size is 25 and it can be changed Dynamically using the object fsRip2Peers"
    ::= { fsMIStdRip 4 }

fsMIStdRip2PeerEntry OBJECT-TYPE
    SYNTAX      FsMIStdRip2PeerEntry
    ACCESS      not-accessible
    STATUS      mandatory
    DESCRIPTION 
        "Information regarding a single routing peer. 
         Row creation : A entry will be created by the System when it receives a RIP Packet from the PEER.
         Row deletion : A entry will be deleted when then RIP Interface is deleted/disabled.
         Index usage : the indexes are fsMIRipContextId, rip2PeerAddress and rip2PeerDomain
         Note that entries will be presented to the SNMP manager in full
         lexicographical order :  sorted on rfsMIRipContextId then on ip2PeerAddress,then on rip2PeerDomain."
    INDEX       { fsMIRipContextId, fsMIStdRip2PeerAddress, 
                  fsMIStdRip2PeerDomain }
    ::= { fsMIStdRip2PeerTable 1 }

FsMIStdRip2PeerEntry ::= SEQUENCE {
    fsMIStdRip2PeerAddress          IpAddress,
    fsMIStdRip2PeerDomain           RouteTag,
    fsMIStdRip2PeerLastUpdate       TimeTicks,
    fsMIStdRip2PeerVersion          INTEGER,
    fsMIStdRip2PeerRcvBadPackets    Counter,
    fsMIStdRip2PeerRcvBadRoutes     Counter
}

fsMIStdRip2PeerAddress OBJECT-TYPE
    SYNTAX      IpAddress
    ACCESS      not-accessible
    STATUS      mandatory
    DESCRIPTION 
        "The IP Address that the peer is using as its source 
         address.  Note that on an unnumbered link, this may 
         not be a member of any subnet on the system.
         ALCATEL NOTE:
         ACCESS:      NA           USAGE:       NA
         PERSIST:     NO           INSRVMOD:    NA 
         RANGE:       NA           DEFVALUE:    NA       
         UNITS:       NA           SPARSE:      NO
         DESCR:       NA"
    ::= { fsMIStdRip2PeerEntry 1 }

fsMIStdRip2PeerDomain OBJECT-TYPE
    SYNTAX      RouteTag
    ACCESS      not-accessible
    STATUS      mandatory
    DESCRIPTION 
        "The value in the Routing Domain field  in  RIP 
         packets received from the peer.  As domain suuport 
         is deprecated, this must be zero.
         ALCATEL NOTE:
          ACCESS:      NA           USAGE:       NA
          PERSIST:     NO           INSRVMOD:    NA 
          RANGE:       NA           DEFVALUE:    NA       
          UNITS:       NA           SPARSE:      NO
          DESCR:       NA"
    ::= { fsMIStdRip2PeerEntry 2 }

fsMIStdRip2PeerLastUpdate OBJECT-TYPE
    SYNTAX      TimeTicks
    ACCESS      read-only
    STATUS      mandatory
    DESCRIPTION 
        "The value of sysUpTime when the most recent 
         RIP update was received from this system. 
         ALCATEL NOTE:
          ACCESS:      NA           USAGE:       NA
          PERSIST:     NO           INSRVMOD:    NA 
          RANGE:       NA           DEFVALUE:    0
          UNITS:       NA           SPARSE:      NO
          DESCR:       NA"
    ::= { fsMIStdRip2PeerEntry 3 }

fsMIStdRip2PeerVersion OBJECT-TYPE
    SYNTAX      INTEGER (0..255)
    ACCESS      read-only
    STATUS      mandatory
    DESCRIPTION 
        "The RIP version number in the header of the 
         last RIP packet received. 
         ALCATEL NOTE:
          ACCESS:      NA           USAGE:       NA
          PERSIST:     NO           INSRVMOD:    NA 
          RANGE:       NA           DEFVALUE:    NA
          UNITS:       NA           SPARSE:      NO
          DESCR:       NA"
    ::= { fsMIStdRip2PeerEntry 4 }

fsMIStdRip2PeerRcvBadPackets OBJECT-TYPE
    SYNTAX      Counter
    ACCESS      read-only
    STATUS      mandatory
    DESCRIPTION 
        "The number of RIP response packets from this 
         peer discarded as invalid. 
         ALCATEL NOTE:
          ACCESS:      NA           USAGE:       NA 
          PERSIST:     NO           INSRVMOD:    NA  
          RANGE:       NA           DEFVALUE:    0
          UNITS:       packets      SPARSE:      NO
          DESCR:       NA"
    ::= { fsMIStdRip2PeerEntry 5 }

fsMIStdRip2PeerRcvBadRoutes OBJECT-TYPE
    SYNTAX      Counter
    ACCESS      read-only
    STATUS      mandatory
    DESCRIPTION 
        "The number of routes from this peer that were 
         ignored because the entry format was invalid. 
         ALCATEL NOTE:
          ACCESS:      NA           USAGE:       NA 
          PERSIST:     NO           INSRVMOD:    NA  
          RANGE:       NA           DEFVALUE:    0
          UNITS:       routes       SPARSE:      NO
          DESCR:       NA"
    ::= { fsMIStdRip2PeerEntry 6 }

END -- end of module ARICENT-MISTDRIP2-MIB.
