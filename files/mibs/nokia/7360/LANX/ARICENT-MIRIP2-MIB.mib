--
-- This SMIv1 module has been generated by smidump 0.4.8. Do not edit.
--

ARICENT-MIRIP2-MIB DEFINITIONS ::= BEGIN

IMPORTS
    OBJECT-TYPE
        FROM RFC-1212
    Counter, Gauge, IpAddress, enterprises
        FROM RFC1155-SMI
    RowStatus, TruthValue
        FROM SNMPv2-TC;

fsMIRip OBJECT IDENTIFIER
    ::= { enterprises futuresoftware(2076) 151 }

-- fsMIRip MODULE-IDENTITY
--     LAST-UPDATED "200702230000Z"
--     ORGANIZATION 
--         "ARICENT COMMUNICATIONS SOFTWARE"
--     CONTACT-INFO 
--         "Postal: ARICENT COMMUNICATIONS SOFTWARE
--          3460 Hill Avenue,
--          Palo Alto, CA 94304-1388, USA,
--          Phone  : +1-650-391-1088
--          E-mail : support@aricent.com"
--     DESCRIPTION 
--         "The enterprise ID 2076 was originally assigned to Future Software
--          Pvt Limited. Future Software is a part of Aricent."
--     REVISION    "200702230000Z"
--     DESCRIPTION 
--         " The ARICENT Proprietary RIP MI MIB"
--     ::= { enterprises futuresoftware(2076) 151 }


fsMIRip2GeneralGroup OBJECT IDENTIFIER
    ::= { fsMIRip 1 }

fsMIRip2GlobalTable OBJECT-TYPE
    SYNTAX      SEQUENCE OF FsMIRip2GlobalEntry
    ACCESS      not-accessible
    STATUS      mandatory
    DESCRIPTION 
        "This Table Contains the list of globals for a
         Context.
         TABLESIZE:  64
         DESCR: 	  NA"
    ::= { fsMIRip2GeneralGroup 1 }

fsMIRip2GlobalEntry OBJECT-TYPE
    SYNTAX      FsMIRip2GlobalEntry
    ACCESS      not-accessible
    STATUS      mandatory
    DESCRIPTION 
        " An entry of fsMIRip2GlobalTable.
         Each entry denotes a RIP parameters for each RIP instance.
         Row creation : An entry will be created when the object fsMIRipRowStatus
                    is set to CreateAndGo.
         Row deletion : An entry will be deleted when the object fsMIRipRowStatus
                    is set to Destroy.     .
         Index usage : the index is fsMIRipContextId.
         Note that entries will be presented to the SNMP manager in full
         lexicographical order :  sorted on fsMIRipContextId."
    INDEX       { fsMIRipContextId }
    ::= { fsMIRip2GlobalTable 1 }

FsMIRip2GlobalEntry ::= SEQUENCE {
    fsMIRipContextId                    INTEGER,
    fsMIRip2Security                    INTEGER,
    fsMIRip2Peers                       INTEGER,
    fsMIRip2TrustNBRListEnable          INTEGER,
    fsMIRip2NumberOfDroppedPkts         Counter,
    fsMIRip2SpacingEnable               INTEGER,
    fsMIRip2RetransTimeoutInt           INTEGER,
    fsMIRip2MaxRetransmissions          INTEGER,
    fsMIRip2OverSubscriptionTimeout     INTEGER,
    fsMIRip2Propagate                   INTEGER,
    fsMIRipTrcFlag                      INTEGER,
    fsMIRipRowStatus                    RowStatus,
    fsMIRipAdminStatus                  INTEGER,
    fsMIRipMaxRoutesPerVrf              INTEGER,
    fsMIRipNumRoutesPerVrf              INTEGER,
    fsMIRipRouteOverflowCount           Counter,
    fsMIRipRouteOverflowReset           TruthValue,
    fsMIRip2GlobalPeriodicUpdates       Counter,
    fsMIRip2NumRedistrRoutesPerVrf      INTEGER
}

fsMIRipContextId OBJECT-TYPE
    SYNTAX      INTEGER (1..65535)
    ACCESS      not-accessible
    STATUS      mandatory
    DESCRIPTION 
        "Identifies the Rip Domain Context.
         ALCATEL NOTE:
                  ACCESS:      NA           USAGE:       NA
                  PERSIST:     YES          INSRVMOD:    YES
                  RANGE:       0..127       DEFVALUE:    NA      
                  UNITS:       NA           SPARSE:      NA
                  DESCR:       NA"
    ::= { fsMIRip2GlobalEntry 1 }

fsMIRip2Security OBJECT-TYPE
    SYNTAX      INTEGER { minimumSecurity(1), maximumSecurity(2) }
    ACCESS      read-write
    STATUS      mandatory
    DESCRIPTION 
        "A variable denotes the security level of RIP-2
         in the system. The value `minimumSecurity` denotes
         that the RIP1 packets will be accepted even when
         authentication is in use. The value `maximumSecurity`
         denotes that RIP1 packets will be ignored when
         authentication is in use
         ALCATEL NOTE:
                 ACCESS:      NA           USAGE:       NA
                 PERSIST:     YES          INSRVMOD:    YES
                 RANGE:       NA           DEFVALUE:    NA      
                 UNITS:       NA           SPARSE:      NA
                 DESCR:       NA"
    DEFVAL      { maximumSecurity }
    ::= { fsMIRip2GlobalEntry 2 }

fsMIRip2Peers OBJECT-TYPE
    SYNTAX      INTEGER
    ACCESS      read-only
    STATUS      mandatory
    DESCRIPTION 
        "The maximum number of peers that can be in conversation
         with the RIP2 system simultaneously
         ALCATEL NOTE:
                 ACCESS:      NA           USAGE:       NA
                 PERSIST:     NO           INSRVMOD:    NA
                 RANGE:       NA           DEFVALUE:    25
                 UNITS:       NA           SPARSE:      NA
                 DESCR:       NA"
    ::= { fsMIRip2GlobalEntry 3 }

fsMIRip2TrustNBRListEnable OBJECT-TYPE
    SYNTAX      INTEGER { enabled(1), disabled(2) }
    ACCESS      read-write
    STATUS      mandatory
    DESCRIPTION 
        "The status of neighbor list in the router.
         The value 'enabled' denotes that a list of
         router's IP address can be configured and 
         RIP Packets from those router's will be processed 
         by RIP and packets from other Routers will be dropped.
         'Disabled' denotes that RIP Packet from all the
         router's will be processed.
         ALCATEL NOTE:
             ACCESS:      NA           USAGE:       NA
             PERSIST:     YES          INSRVMOD:    YES
             RANGE:       NA           DEFVALUE:    NA      
             UNITS:       NA           SPARSE:      NA
             DESCR:       NA"
    DEFVAL      { disabled }
    ::= { fsMIRip2GlobalEntry 4 }

fsMIRip2NumberOfDroppedPkts OBJECT-TYPE
    SYNTAX      Counter
    ACCESS      read-only
    STATUS      mandatory
    DESCRIPTION 
        "Number of RIP Packets dropped because of
         neighbor list check.
         ALCATEL NOTE:
             ACCESS:      NA           USAGE:       NA
             PERSIST:     NO           INSRVMOD:    NA
             RANGE:       NA           DEFVALUE:    0       
             UNITS:       RIP packets  SPARSE:      NA
             DESCR:       NA"
    ::= { fsMIRip2GlobalEntry 5 }

fsMIRip2SpacingEnable OBJECT-TYPE
    SYNTAX      INTEGER { enabled(1), disabled(2) }
    ACCESS      read-write
    STATUS      mandatory
    DESCRIPTION 
        "Whether spacing is enabled or not. If spacing 
         is enabled, generation of periodic update packet 
         will be split and send.
         ALCATEL NOTE:
             ACCESS:      NA           USAGE:       NA
             PERSIST:     YES          INSRVMOD:    YES
             RANGE:       NA           DEFVALUE:    NA      
             UNITS:       NA           SPARSE:      NA
             DESCR:       NA"
    DEFVAL      { disabled }
    ::= { fsMIRip2GlobalEntry 6 }

fsMIRip2RetransTimeoutInt OBJECT-TYPE
    SYNTAX      INTEGER (5..10)
    ACCESS      read-write
    STATUS      mandatory
    DESCRIPTION 
        "The timeout interval to be used to retransmit the Update 
         request packet or an unacknowledged update response packet.
         ALCATEL NOTE:
              ACCESS:      NA           USAGE:       NA
              PERSIST:     YES          INSRVMOD:    YES
              RANGE:       NA           DEFVALUE:    NA      
              UNITS:       seconds      SPARSE:      NA
              DESCR:       NA"
    DEFVAL      { 5 }
    ::= { fsMIRip2GlobalEntry 8 }

fsMIRip2MaxRetransmissions OBJECT-TYPE
    SYNTAX      INTEGER (10..40)
    ACCESS      read-write
    STATUS      mandatory
    DESCRIPTION 
        "The maximum number of retransmissions of the update request and 
         update response packets. If no response is received then the routes 
         via the next hop router are marked unreachable. 
         ALCATEL NOTE:
             ACCESS:      NA           USAGE:       NA
             PERSIST:     YES          INSRVMOD:    YES
             RANGE:       NA           DEFVALUE:    NA      
             UNITS:       NA           SPARSE:      NA
             DESCR:       NA"
    DEFVAL      { 36 }
    ::= { fsMIRip2GlobalEntry 9 }

fsMIRip2OverSubscriptionTimeout OBJECT-TYPE
    SYNTAX      INTEGER (100..300)
    ACCESS      read-write
    STATUS      mandatory
    DESCRIPTION 
        "Over subscription timeout value as mentioned in RFC 2091.When a
         Circuit DOWN message is received from the circuit manager, this 
         timer will be started for the specified timeout value.
         ALCATEL NOTE:
             ACCESS:      NA           USAGE:       NA
             PERSIST:     YES          INSRVMOD:    YES
             RANGE:       NA           DEFVALUE:    NA      
             UNITS:       seconds      SPARSE:      NA
             DESCR:       NA"
    DEFVAL      { 180 }
    ::= { fsMIRip2GlobalEntry 10 }

fsMIRip2Propagate OBJECT-TYPE
    SYNTAX      INTEGER { enable(1), disable(2) }
    ACCESS      read-write
    STATUS      mandatory
    DESCRIPTION 
        "Is propagation of static route is enabled or not. If it
         is enabled then routing protocols (like RIP) are allowed
         to include static routes in the update messages.
         ALCATEL NOTE:
             ACCESS:      NA           USAGE:       NA
             PERSIST:     YES          INSRVMOD:    YES
             RANGE:       NA           DEFVALUE:    NA      
             UNITS:       NA	      SPARSE:      NA
             DESCR:       NA"
    DEFVAL      { disable }
    ::= { fsMIRip2GlobalEntry 11 }

fsMIRipTrcFlag OBJECT-TYPE
    SYNTAX      INTEGER
    ACCESS      read-write
    STATUS      mandatory
    DESCRIPTION 
        "Enables the tracing in the RIP. A 32 bit integer
         is used to store the Tracing level in the specified module.
         Different Tracing Levels -
         BIT 0 - Initialisation and Shutdown Trace.
         BIT 1 - Management trace.
         BIT 2 - Data path trace.
         BIT 3 - Control Plane trace.
         BIT 4 - Packet Dump.
         BIT 5 - OS Resource trace.
         BIT 6 - All Failure trace (All failures including Packet Validation)
         BIT 7 - Buffer Trace.
         ALCATEL NOTE:
             ACCESS:      NA           USAGE:       NA
             PERSIST:     YES          INSRVMOD:    YES
             RANGE:       NA           DEFVALUE:    NA      
             UNITS:       NA	        SPARSE:      NA
             DESCR:       This should not used by the operator and it is only for debugging purpose"
    DEFVAL      { 0 }
    ::= { fsMIRip2GlobalEntry 12 }

fsMIRipRowStatus OBJECT-TYPE
    SYNTAX      RowStatus
    ACCESS      read-write
    STATUS      mandatory
    DESCRIPTION 
        "The row status variable, used according to
         row installation and removal conventions. 
         ALCATEL NOTE:
                 ACCESS:      NA           USAGE:       NA
                 PERSIST:     YES          INSRVMOD:    NA
                 RANGE:       NA           DEFVALUE:    NA      
                 UNITS:       NA	      SPARSE:      NA
                 DESCR:       In ECNTA, Get of this object will always return 1 (Active), Set of this object will always return success for both creation and deletion, since Multiple instance is not supported in ECNTA"
    ::= { fsMIRip2GlobalEntry 13 }

fsMIRipAdminStatus OBJECT-TYPE
    SYNTAX      INTEGER { enabled(1), disabled(2) }
    ACCESS      read-write
    STATUS      mandatory
    DESCRIPTION 
        "The administrative status of RIP in a particular 
         router context. The value 'enabled' denotes that 
         the RIP Process is active; 'disabled' disables it 
         on all inter-faces.
         ALCATEL NOTE:
             ACCESS:      NA           USAGE:       NA
             PERSIST:     YES          INSRVMOD:    NA
             RANGE:       NA           DEFVALUE:    NA      
             UNITS:       NA	      SPARSE:      NA
             DESCR:       In ECNTA, Get of this object will always return 1 (Enabled), Set of this object will always return success, since Multiple instance is not supported in ECNTA"
    DEFVAL      { disabled }
    ::= { fsMIRip2GlobalEntry 14 }

fsMIRipMaxRoutesPerVrf OBJECT-TYPE
    SYNTAX      INTEGER (-1..27648)
    ACCESS      read-write
    STATUS      mandatory
    DESCRIPTION 
        "The maximum number of RIP routes per VRF instance
         ALCATEL NOTE:
                 ACCESS:      NA           USAGE:       NA
                 PERSIST:     YES	      INSRVMOD:    NA
                 RANGE:       NA   	      DEFVALUE:    NA      
                 UNITS:       NA           SPARSE:      NA
                 DESCR:       In ECNTA, Get of this object will always return -1, Set of this object will always return failure, since Multiple instance is not supported in ECNTA"
    DEFVAL      { -1 }
    ::= { fsMIRip2GlobalEntry 15 }

fsMIRipNumRoutesPerVrf OBJECT-TYPE
    SYNTAX      INTEGER (-1..27648)
    ACCESS      read-only
    STATUS      mandatory
    DESCRIPTION 
        "The current number of RIP routes per VRF instance
         ALCATEL NOTE:
                 ACCESS:      NA           USAGE:       NA
                 PERSIST:     NO	      INSRVMOD:    NA
                 RANGE:       NA   	      DEFVALUE:    NA      
                 UNITS:       NA           SPARSE:      NA
                 DESCR:       In ECNTA, Get of this object will always return 0, since Multiple instance is not supported in ECNTA"
    DEFVAL      { 0 }
    ::= { fsMIRip2GlobalEntry 16 }

fsMIRipRouteOverflowCount OBJECT-TYPE
    SYNTAX      Counter
    ACCESS      read-only
    STATUS      mandatory
    DESCRIPTION 
        "The number of discarded RIP routes due to RIP Routing 
         table overflow, per VRF instance
         ALCATEL NOTE:
                 ACCESS:      NA           USAGE:       NA
                 PERSIST:     NO	      INSRVMOD:    NA
                 RANGE:       NA   	      DEFVALUE:    0      
                 UNITS:       NA           SPARSE:      NA
                 DESCR:       In ECNTA, Get of this object will always return 0, since Multiple instance is not supported in ECNTA"
    ::= { fsMIRip2GlobalEntry 17 }

fsMIRipRouteOverflowReset OBJECT-TYPE
    SYNTAX      TruthValue
    ACCESS      read-write
    STATUS      mandatory
    DESCRIPTION 
        " This object is a button-like object to reset the
         number of discarded rip routes counter. When it is 
         set to Reset value, counter is cleared.
         ALCATEL NOTE:
         ACCESS:      NA           USAGE:       NA
         PERSIST:     NO	      INSRVMOD:    NA
         RANGE:       NA   	      DEFVALUE:    0      
         UNITS:       NA           SPARSE:      NA
         DESCR:       In ECNTA, Get of this object will always return false, Set of this object with True will always return failure, with False will always return Success, since Multiple instance is not supported in ECNTA. The default values mentioned are internal values and cannot be set by the operator."
    DEFVAL      { false }
    ::= { fsMIRip2GlobalEntry 18 }

fsMIRip2GlobalPeriodicUpdates OBJECT-TYPE
    SYNTAX      Counter
    ACCESS      read-only
    STATUS      mandatory
    DESCRIPTION 
        "The total number of Periodic RIP updates actually 
         sent from this router.
         ALCATEL NOTE:
          ACCESS:      NA           USAGE:       NA
          PERSIST:     NO           INSRVMOD:    NA
          RANGE:       NA           DEFVALUE:    0      
          UNITS:       RIP packets  SPARSE:      NA
          DESCR:       NA"
    ::= { fsMIRip2GlobalEntry 19 }

fsMIRip2NumRedistrRoutesPerVrf OBJECT-TYPE
    SYNTAX      INTEGER
    ACCESS      read-only
    STATUS      mandatory
    DESCRIPTION 
        "This gives the Total number of Redistributed routes in RIP in the particular VRF.
         ALCATEL NOTE:
             ACCESS:      NA           USAGE:       NA
             PERSIST:     NO           INSRVMOD:    NA
             RANGE:       NA           DEFVALUE:    NA      
             UNITS:       NA           SPARSE:      NA
             DESCR:       In ECNTA, Get of this object will always return 0, since Multiple instance is not supported in ECNTA"
    DEFVAL      { 0 }
    ::= { fsMIRip2GlobalEntry 20 }

fsMIRipGlobalTrcFlag OBJECT-TYPE
    SYNTAX      INTEGER
    ACCESS      read-write
    STATUS      mandatory
    DESCRIPTION 
        "Enables Global tracing in the RIP. A 32 bit integer
         is used to store the Tracing level in the specified module.
         Different Tracing Levels -
         BIT 0 - Initialisation and Shutdown Trace.
         BIT 1 - Management trace.
         BIT 2 - Data path trace.
         BIT 3 - Control Plane trace.
         BIT 4 - Packet Dump.
         BIT 5 - OS Resource trace.
         BIT 6 - All Failure trace (All failures including Packet Validation)
         BIT 7 - Buffer Trace.
         ALCATEL NOTE:
             ACCESS:      NA           USAGE:       NA
             PERSIST:     YES          INSRVMOD:    NA
             RANGE:       NA           DEFVALUE:    NA
             UNITS:       NA	      SPARSE:      NO
             DESCR:       This should not used by the operator and it is only for debugging purpose.
         	    In ECNTA, Get of this object will always return 0, Set of this object will always return failure, since Multiple instance is not supported in ECNTA"
    DEFVAL      { 0 }
    ::= { fsMIRip2GeneralGroup 2 }

fsMIRip2NBRTrustListTable OBJECT-TYPE
    SYNTAX      SEQUENCE OF FsMIRip2NBRTrustListEntry
    ACCESS      not-accessible
    STATUS      mandatory
    DESCRIPTION 
        "This table contains a list of Router addresses 
         from which you can receive RIP Packets
         ALCATEL NOTE:
         	    TABLESIZE:	 10
             DESCR:       NA"
    ::= { fsMIRip2GeneralGroup 3 }

fsMIRip2NBRTrustListEntry OBJECT-TYPE
    SYNTAX      FsMIRip2NBRTrustListEntry
    ACCESS      not-accessible
    STATUS      mandatory
    DESCRIPTION 
        "An entry of fsMIRip2NBRTrustListTable.
         Row creation : A fsRip2NBRTrustList Entry shall be created in one step by a
             		set-request with all necessary parameter values and
             		fsRip2TrustNBRRowStatus set to createAndGo(4).
         Row deletion : A fsRip2NBRTrustList Entry shall be deleted by setting
             		the fsRip2TrustNBRRowStatus of the specific entry to destroy(6).
         Index usage : the index are fsMIRipContextId and fsRip2TrustNBRIpAddr.
         Note that entries will be presented to the SNMP manager in full
         lexicographical order :  sorted on fsMIRipContextId then on fsRip2TrustNBRIpAddr."
    INDEX       { fsMIRipContextId, fsMIRip2TrustNBRIpAddr }
    ::= { fsMIRip2NBRTrustListTable 1 }

FsMIRip2NBRTrustListEntry ::= SEQUENCE {
    fsMIRip2TrustNBRIpAddr      IpAddress,
    fsMIRip2TrustNBRRowStatus   RowStatus
}

fsMIRip2TrustNBRIpAddr OBJECT-TYPE
    SYNTAX      IpAddress
    ACCESS      not-accessible
    STATUS      mandatory
    DESCRIPTION 
        "Ipaddress of the Router from which this router 
         can accept RIP Packets
         ALCATEL NOTE:
             ACCESS:      NA           USAGE:       NA
             PERSIST:     YES          INSRVMOD:    NA
             RANGE:       NA           DEFVALUE:    NA
             UNITS:       NA	      SPARSE:      NO
             DESCR:       NA"
    ::= { fsMIRip2NBRTrustListEntry 1 }

fsMIRip2TrustNBRRowStatus OBJECT-TYPE
    SYNTAX      RowStatus
    ACCESS      read-write
    STATUS      mandatory
    DESCRIPTION 
        "The row status variable, used according to
         row installation and removal conventions.
         ALCATEL NOTE:
                 ACCESS:      NA           USAGE:       MAND
                 PERSIST:     YES          INSRVMOD:    YES
                 RANGE:       1,2,4,5,6    DEFVALUE:    NA
                 UNITS:       NA	      SPARSE:      NO
                 DESCR:       NA"
    ::= { fsMIRip2NBRTrustListEntry 2 }

fsMIRip2IfConfTable OBJECT-TYPE
    SYNTAX      SEQUENCE OF FsMIRip2IfConfEntry
    ACCESS      not-accessible
    STATUS      mandatory
    DESCRIPTION 
        "A list of subnets which require separate
         configuration in RIP.
         ALCATEL NOTE:
         	    TABLESIZE:	DEP 
             DESCR:   DEP(TABLESIZE): The Value is the total number of RIP interfaces in the system.
         			The total number of RIP interfaces is obtained from fsVrfNoOfRipInterfaces in fsvrf.mib"
    ::= { fsMIRip2GeneralGroup 4 }

fsMIRip2IfConfEntry OBJECT-TYPE
    SYNTAX      FsMIRip2IfConfEntry
    ACCESS      not-accessible
    STATUS      mandatory
    DESCRIPTION 
        "A Single Routing Domain in a single Subnet.
         Row creation : A fsRip2IfConf entry will be created by the system when an 
         			entry is created in the rip2IfConf Table.
         Row deletion : A fsRip2IfConf entry will be deleted by the system when an 
         			entry is deleted in the rip2IfConf Table.
         Index usage : the index are fsMIRipContextId and fsRip2IfConfAddress.
         Note that entries will be presented to the SNMP manager in full
         lexicographical order :  sorted on fsMIRipContextId and then on fsRip2IfConfAddress."
    INDEX       { fsMIRipContextId, fsMIRip2IfConfAddress }
    ::= { fsMIRip2IfConfTable 1 }

FsMIRip2IfConfEntry ::= SEQUENCE {
    fsMIRip2IfConfAddress                   IpAddress,
    fsMIRip2IfAdminStat                     INTEGER,
    fsMIRip2IfConfOperState                 INTEGER,
    fsMIRip2IfConfUpdateTmr                 INTEGER,
    fsMIRip2IfConfGarbgCollectTmr           INTEGER,
    fsMIRip2IfConfRouteAgeTmr               INTEGER,
    fsMIRip2IfSplitHorizonStatus            INTEGER,
    fsMIRip2IfConfDefRtInstall              INTEGER,
    fsMIRip2IfPeriodicUpdates               Counter,
    fsMIRip2IfReceptionStatus               INTEGER,
    fsMIRip2IfConfDefEgrRouteMapAction      INTEGER,
    fsMIRip2IfConfDefIngrRouteMapAction     INTEGER
}

fsMIRip2IfConfAddress OBJECT-TYPE
    SYNTAX      IpAddress
    ACCESS      not-accessible
    STATUS      mandatory
    DESCRIPTION 
        "The IP Address of this system on the indicated
         subnet.  For unnumbered interfaces, the value 0.0.0.N,
         where the least significant 24 bits (N) is the ifIndex
         for the IP Interface in network byte order.
         ALCATEL NOTE:
             ACCESS:      NA           USAGE:       NA
             PERSIST:     YES          INSRVMOD:    NA
             RANGE:       NA           DEFVALUE:    NA
             UNITS:       NA	      SPARSE:      NO
             DESCR:       NA"
    ::= { fsMIRip2IfConfEntry 1 }

fsMIRip2IfAdminStat OBJECT-TYPE
    SYNTAX      INTEGER { enabled(1), disabled(2), passive(3) }
    ACCESS      read-write
    STATUS      mandatory
    DESCRIPTION 
        "The  administrative  status  of  RIP-2  in  the
         router.   The  value 'enabled' denotes that the
         RIP2 Process is active throughout the system.
         'disabled'	 disables RIP2 Process in the system.
         'passive'	denotes that the RIP2 Process runs as
         a passive one
         ALCATEL NOTE:
              ACCESS:      NA           USAGE:       MAND
              PERSIST:     YES          INSRVMOD:    YES
              RANGE:       NA           DEFVALUE:    NA
              UNITS:       NA	      SPARSE:      NO
              DESCR:       NA"
    ::= { fsMIRip2IfConfEntry 2 }

fsMIRip2IfConfOperState OBJECT-TYPE
    SYNTAX      INTEGER { operup(1), operdown(2) }
    ACCESS      read-only
    STATUS      mandatory
    DESCRIPTION 
        " This gives the Operational Status of the Interface 
         ALCATEL NOTE:
                 ACCESS:      NA           USAGE:       NA
                 PERSIST:     NO           INSRVMOD:    NA
                 RANGE:       NA           DEFVALUE:    2
                 UNITS:       NA	      SPARSE:      NO
                 DESCR:       NA"
    DEFVAL      { operdown }
    ::= { fsMIRip2IfConfEntry 3 }

fsMIRip2IfConfUpdateTmr OBJECT-TYPE
    SYNTAX      INTEGER (10..3600)
    ACCESS      read-write
    STATUS      mandatory
    DESCRIPTION 
        "Interval Time Between Updates
         ALCATEL NOTE:
                 ACCESS:      NA           USAGE:       OPT
                 PERSIST:     YES          INSRVMOD:    YES
                 RANGE:       NA           DEFVALUE:    NA
                 UNITS:       seconds      SPARSE:      NO
                 DESCR:       NA"
    DEFVAL      { 30 }
    ::= { fsMIRip2IfConfEntry 4 }

fsMIRip2IfConfGarbgCollectTmr OBJECT-TYPE
    SYNTAX      INTEGER (120..180)
    ACCESS      read-write
    STATUS      mandatory
    DESCRIPTION 
        " Interval before deleting an entry after not hearing
         it. Also the advertisements of this entry is set to
         INFINITY while sending to others
         ALCATEL NOTE:
             ACCESS:      NA           USAGE:       OPT
             PERSIST:     YES          INSRVMOD:    YES
             RANGE:       NA           DEFVALUE:    NA
             UNITS:       seconds      SPARSE:      NO
             DESCR:       NA"
    DEFVAL      { 120 }
    ::= { fsMIRip2IfConfEntry 5 }

fsMIRip2IfConfRouteAgeTmr OBJECT-TYPE
    SYNTAX      INTEGER (30..500)
    ACCESS      read-write
    STATUS      mandatory
    DESCRIPTION 
        " Time after which the entry is put into garbage collect
         interval 
         ALCATEL NOTE:
             ACCESS:      NA           USAGE:       OPT
             PERSIST:     YES          INSRVMOD:    YES
             RANGE:       NA           DEFVALUE:    NA
             UNITS:       seconds      SPARSE:      NO
             DESCR:       NA"
    DEFVAL      { 180 }
    ::= { fsMIRip2IfConfEntry 6 }

fsMIRip2IfSplitHorizonStatus OBJECT-TYPE
    SYNTAX      INTEGER { splitHorizon(1), splitHorizonWithPoisRev(2), 
                    disable(3) }
    ACCESS      read-write
    STATUS      mandatory
    DESCRIPTION 
        "A flag to denote the split horizon operational status
         in the system. The value `splitHorizon` denotes that
         splitHorizon should be applied in the response packets
         that are going out
         ALCATEL NOTE:
            ACCESS:      NA           USAGE:       OPT
            PERSIST:     YES          INSRVMOD:    YES
            RANGE:       NA           DEFVALUE:    NA
            UNITS:       NA	      SPARSE:      NO
            DESCR:       NA"
    DEFVAL      { splitHorizonWithPoisRev }
    ::= { fsMIRip2IfConfEntry 7 }

fsMIRip2IfConfDefRtInstall OBJECT-TYPE
    SYNTAX      INTEGER { installDefRt(1), doNotInstallDefRt(2) }
    ACCESS      read-write
    STATUS      mandatory
    DESCRIPTION 
        "A flag that decides whether the default route received over this 
         interface should be installed to rip database or not.
         ALCATEL NOTE:
             ACCESS:      NA           USAGE:       OPT
             PERSIST:     YES          INSRVMOD:    YES
             RANGE:       NA           DEFVALUE:    NA
             UNITS:       NA	      SPARSE:      NO
             DESCR:       In ECNTA, Get of this object will always return 1, Set of this object will always return failure, since Multiple instance is not supported in ECNTA"
    DEFVAL      { installDefRt }
    ::= { fsMIRip2IfConfEntry 8 }

fsMIRip2IfPeriodicUpdates OBJECT-TYPE
    SYNTAX      Counter
    ACCESS      read-only
    STATUS      mandatory
    DESCRIPTION 
        "The total number of Periodic RIP updates actually 
         sent on this interface.
         ALCATEL NOTE:
            ACCESS:      NA           USAGE:       NA
            PERSIST:     NO           INSRVMOD:    NA
            RANGE:       NA           DEFVALUE:    0 
            UNITS:       RIP packets  SPARSE:      NO
            DESCR:       NA"
    ::= { fsMIRip2IfConfEntry 9 }

fsMIRip2IfReceptionStatus OBJECT-TYPE
    SYNTAX      INTEGER { enable(1), disable(2) }
    ACCESS      read-write
    STATUS      mandatory
    DESCRIPTION 
        "The reception status of the RIP interface. When 
         it is enabled the RIP updates will be received 
         and processed. when the status is disabled the
         updates will not be processed.
         ALCATEL NOTE:
          ACCESS:      NA           USAGE:       MAND
          PERSIST:     YES          INSRVMOD:    YES
          RANGE:       NA           DEFVALUE:    NA
          UNITS:       NA           SPARSE:      NO
          DESCR:       NA"
    ::= { fsMIRip2IfConfEntry 10 }

fsMIRip2IfConfDefEgrRouteMapAction OBJECT-TYPE
    SYNTAX      INTEGER { permit(1), deny(2) }
    ACCESS      read-write
    STATUS      mandatory
    DESCRIPTION 
        "This MIB object is used to set the default Egress action for RIP Route map algorithm to permit or deny.
         Permit - The route will be advertised by RIP over 
               the interface in transmit direction. In direction 
               receive this route will be accepted by RIP for 
               advertisement.
         Deny - The route will not be advertised by RIP over the 
         	      interface in transmit direction. In the direction
         	      receive this route will not be accepted by RIP for advertisement. 
         ALCATEL NOTE:
         ACCESS:      NA           USAGE:       OPT
         PERSIST:     YES          INSRVMOD:    YES
         RANGE:       NA           DEFVALUE:    0
         UNITS:       NA	      SPARSE:      NO
         DESCR:       The default values mentioned are internal values and cannot be set by the operator."
    DEFVAL      { permit }
    ::= { fsMIRip2IfConfEntry 11 }

fsMIRip2IfConfDefIngrRouteMapAction OBJECT-TYPE
    SYNTAX      INTEGER { permit(1), deny(2) }
    ACCESS      read-write
    STATUS      mandatory
    DESCRIPTION 
        "This MIB object is used to set the default Ingress action for RIP Route map algorithm to permit or deny.
         Permit - The route will be advertised by RIP over 
               the interface in transmit direction. In direction 
               receive this route will be accepted by RIP for 
               advertisement.
         Deny - The route will not be advertised by RIP over the 
         	      interface in transmit direction. In the direction
         	      receive this route will not be accepted by RIP for advertisement. 
         ALCATEL NOTE:
         ACCESS:      NA           USAGE:       OPT
         PERSIST:     YES          INSRVMOD:    YES
         RANGE:       NA           DEFVALUE:    0
         UNITS:       NA	      SPARSE:      NO
         DESCR:       The default values mentioned  are internal Values and cannot be set by the operator."
    DEFVAL      { permit }
    ::= { fsMIRip2IfConfEntry 12 }

fsMIRipMd5AuthTable OBJECT-TYPE
    SYNTAX      SEQUENCE OF FsMIRipMd5AuthEntry
    ACCESS      not-accessible
    STATUS      mandatory
    DESCRIPTION 
        "The MD5 Authentication table for RIP.
         ALCATEL NOTE:
         	    TABLESIZE:	 NA
             DESCR:       NA"
    ::= { fsMIRip2GeneralGroup 5 }

fsMIRipMd5AuthEntry OBJECT-TYPE
    SYNTAX      FsMIRipMd5AuthEntry
    ACCESS      not-accessible
    STATUS      mandatory
    DESCRIPTION 
        "An entry in to the MD5 Authentiaction table. More than one
         entry can be configured for an interface.
         Row creation : A fsRipMd5Auth entry shall be created in one step by a
           		set-request with all necessary parameter values and
           		fsRipMd5KeyRowStatus set to createAndGo(4).
         Row deletion : A fsRipMd5Auth entry shall be deleted by setting
           		the fsRipMd5KeyRowStatus of the specific entry to destroy(6).
         Index usage : the indexes are fsMIRipContextId, fsRipMd5AuthAddress and fsRipMd5AuthKeyId.
         Note that entries will be presented to the SNMP manager in full
         lexicographical order :  sorted on fsMIRipContextId then on fsRipMd5AuthAddress,then on fsRipMd5AuthKeyId."
    INDEX       { fsMIRipContextId, fsMIRipMd5AuthAddress, 
                  fsMIRipMd5AuthKeyId }
    ::= { fsMIRipMd5AuthTable 1 }

FsMIRipMd5AuthEntry ::= SEQUENCE {
    fsMIRipMd5AuthAddress       IpAddress,
    fsMIRipMd5AuthKeyId         INTEGER,
    fsMIRipMd5AuthKey           OCTET STRING,
    fsMIRipMd5KeyStartTime      INTEGER,
    fsMIRipMd5KeyExpiryTime     INTEGER,
    fsMIRipMd5KeyRowStatus      RowStatus
}

fsMIRipMd5AuthAddress OBJECT-TYPE
    SYNTAX      IpAddress
    ACCESS      not-accessible
    STATUS      mandatory
    DESCRIPTION 
        "The IP Address of this system on the indicated
         subnet.  For unnumbered interfaces, the value 0.0.0.N,
         where the least significant 24 bits (N) is the ifIndex
         for the IP Interface in network byte order. RIP should
         have been enabled for this IP address and the rip2IfConfAuthType 
         should be MD5 for creating this entry.
         ALCATEL NOTE:
             ACCESS:      NA           USAGE:       NA
             PERSIST:     YES          INSRVMOD:    NA
             RANGE:       NA           DEFVALUE:    NA
             UNITS:       NA	      SPARSE:      NO
             DESCR:       NA"
    ::= { fsMIRipMd5AuthEntry 1 }

fsMIRipMd5AuthKeyId OBJECT-TYPE
    SYNTAX      INTEGER (0..255)
    ACCESS      not-accessible
    STATUS      mandatory
    DESCRIPTION 
        "The key ID for this key. This should be unique for the same 
         fsMIRipMd5AuthAddress. This enables the configuration of more than
         one key for an interface.
         ALCATEL NOTE:
             ACCESS:      NA           USAGE:       NA
             PERSIST:     YES          INSRVMOD:    NA
             RANGE:       NA           DEFVALUE:    NA
             UNITS:       NA	      SPARSE:      NO
             DESCR:       NA"
    ::= { fsMIRipMd5AuthEntry 2 }

fsMIRipMd5AuthKey OBJECT-TYPE
    SYNTAX      OCTET STRING (SIZE(1..16))
    ACCESS      read-write
    STATUS      mandatory
    DESCRIPTION 
        "The value to be used as the Authentication Key.
         If a string shorter than 16 octets is supplied, it will be 
         left- justified and padded to 16 octets, on the right,
               with nulls (0x00).authentication may not
         be bypassed by reading the MIB object.
         	
         	When read, fsMIRipMd5AuthKey always returns the 
         encrypted key of maximum length 32.
         
         	Note: The operator can enter a maximum of 16 octets
         as a MD5 key
         	
         ALCATEL NOTE:
             ACCESS:      NA           	USAGE:       MAND
             PERSIST:     YES          	INSRVMOD:    YES
             RANGE:       NA		DEFVALUE:    NA
             UNITS:       NA		SPARSE:      NO
             DESCR:       NA"
    ::= { fsMIRipMd5AuthEntry 3 }

fsMIRipMd5KeyStartTime OBJECT-TYPE
    SYNTAX      INTEGER
    ACCESS      read-write
    STATUS      mandatory
    DESCRIPTION 
        "The time the router will start accepting or generating the 
         packets that have been created with this key. 
         The start time of the key should be less than the expiry time of
         the previous key.
         During the overlap interval, the next key will be used in the 
         generation of the authentication messages.
         ALCATEL NOTE:
             ACCESS:      NA           	USAGE:       MAND
             PERSIST:     YES          	INSRVMOD:    YES
             RANGE:       -1..2147483647	DEFVALUE:    NA
             UNITS:       seconds	SPARSE:      NO
             DESCR:       The start time of the key should be greater than the start time  
             of the previous key. And start time should be less than the
             previous expiry time as absolute time(sum of previous start time and relative
             value of expiry time)."
    ::= { fsMIRipMd5AuthEntry 4 }

fsMIRipMd5KeyExpiryTime OBJECT-TYPE
    SYNTAX      INTEGER
    ACCESS      read-write
    STATUS      mandatory
    DESCRIPTION 
        "The time the router will stop accepting the packets that have
         been created with this key. This time will be indicated (in the 
         number of seconds) from the start time of the key. If the expiry time    
         of a key is zero, it means that, the key should be used for the           
         infinite amount of time. If this key is the last key then that key
         will be used for the infinite amount of time or until the new key 
         is configured.
         ALCATEL NOTE:
             ACCESS:      NA           	USAGE:       MAND
             PERSIST:     YES          	INSRVMOD:    YES
             RANGE:       -1..2147483647	DEFVALUE:    NA
             UNITS:       seconds	SPARSE:      NO
             DESCR:       Expiry time is relative time with respect to start
             time."
    ::= { fsMIRipMd5AuthEntry 5 }

fsMIRipMd5KeyRowStatus OBJECT-TYPE
    SYNTAX      RowStatus
    ACCESS      read-write
    STATUS      mandatory
    DESCRIPTION 
        "The status of this row by which a new entry can be created or
         deleted by setting this object to the appropriate value as 
         mentioned in SMI-v2.If this entry is made active, then no other 
         entry in the table will be allowed to modify. The entry can be in     
         deleted from the table.
         ALCATEL NOTE:
             ACCESS:      NA           USAGE:       MAND
             PERSIST:     YES          INSRVMOD:    YES
             RANGE:       1,2,4,5,6    DEFVALUE:    NA
             UNITS:       NA	      SPARSE:      NO
             DESCR:       NA"
    ::= { fsMIRipMd5AuthEntry 6 }

fsMIRip2NBRUnicastListTable OBJECT-TYPE
    SYNTAX      SEQUENCE OF FsMIRip2NBRUnicastListEntry
    ACCESS      not-accessible
    STATUS      mandatory
    DESCRIPTION 
        "This table contains a list of Router addresses 
         from which you can receive RIP Packets
         ALCATEL NOTE:
         	    TABLESIZE:	 NA
         DESCR:       NA"
    ::= { fsMIRip2GeneralGroup 6 }

fsMIRip2NBRUnicastListEntry OBJECT-TYPE
    SYNTAX      FsMIRip2NBRUnicastListEntry
    ACCESS      not-accessible
    STATUS      mandatory
    DESCRIPTION 
        "An entry of fsMIRip2NBRUnicastListTable.
         Row creation : A fsRip2NBRUnicastList Entry shall be created in one step by a
               		set-request with all necessary parameter values and
               		fsRip2NBRUnicastNBRRowStatus set to createAndGo(4).
           Row deletion : A fsRip2NBRUnicastList Entry shall be deleted by setting
               		the fsRip2NBRUnicastNBRRowStatus of the specific entry to destroy(6).
           Index usage : the index are fsMIRipContextId and fsRip2NBRUnicastIpAddr.
           Note that entries will be presented to the SNMP manager in full
           lexicographical order :  sorted on fsMIRipContextId then on fsRip2NBRUnicastIpAddr."
    INDEX       { fsMIRipContextId, fsMIRip2NBRUnicastIpAddr }
    ::= { fsMIRip2NBRUnicastListTable 1 }

FsMIRip2NBRUnicastListEntry ::= SEQUENCE {
    fsMIRip2NBRUnicastIpAddr        IpAddress,
    fsMIRip2NBRUnicastNBRRowStatus  RowStatus
}

fsMIRip2NBRUnicastIpAddr OBJECT-TYPE
    SYNTAX      IpAddress
    ACCESS      not-accessible
    STATUS      mandatory
    DESCRIPTION 
        "Ipaddress of the neighbour Router to which unicast 
         update has to be sent
         ALCATEL NOTE:
             ACCESS:      NA           USAGE:       NA
             PERSIST:     YES          INSRVMOD:    NA
             RANGE:       NA           DEFVALUE:    NA
             UNITS:       NA	      SPARSE:      NO
             DESCR:       NA"
    ::= { fsMIRip2NBRUnicastListEntry 1 }

fsMIRip2NBRUnicastNBRRowStatus OBJECT-TYPE
    SYNTAX      RowStatus
    ACCESS      read-write
    STATUS      mandatory
    DESCRIPTION 
        "The row status variable, used according to
         row installation and removal conventions.
         ALCATEL NOTE:
            ACCESS:      NA           USAGE:       MAND
            PERSIST:     YES          INSRVMOD:    YES
            RANGE:       1,2,4,5,6    DEFVALUE:    NA
            UNITS:       NA	      SPARSE:      NO
            DESCR:       NA"
    ::= { fsMIRip2NBRUnicastListEntry 2 }

fsMIRip2LocalRouteTable OBJECT-TYPE
    SYNTAX      SEQUENCE OF FsMIRip2LocalRouteEntry
    ACCESS      not-accessible
    STATUS      mandatory
    DESCRIPTION 
        "This table contain Local routing table entries 
         ALCATEL NOTE:
         	    TABLESIZE:	 1000
             DESCR:       NA"
    ::= { fsMIRip2GeneralGroup 7 }

fsMIRip2LocalRouteEntry OBJECT-TYPE
    SYNTAX      FsMIRip2LocalRouteEntry
    ACCESS      not-accessible
    STATUS      mandatory
    DESCRIPTION 
        "A list of routes in local routing table
         Row creation : A fsRip2LocalRoute Entry will be created by the system
             		when an IP Interface is enabled,when it receives RIP Route Updates
             		and when an RIP static Entry is added.
         Row deletion : A fsRip2LocalRoute Entry will be deleted by the system
             		when an IP Interface is disabled/deleted,when the RIP route timer 
         			expires and when an RIP static Entry is deleted.
         Index usage : the indexes are fsMIRipContextId, fsRip2DestNet,fsRip2DestMask,fsRip2Tos and fsRip2NextHop.
         Note that entries will be presented to the SNMP manager in full
         lexicographical order :  sorted on fsMIRipContextId then on fsRip2DestNet, then on fsRip2DestMask,
         					then on fsRip2Tos, then on fsRip2NextHop."
    INDEX       { fsMIRipContextId, fsMIRip2DestNet, fsMIRip2DestMask, 
                  fsMIRip2Tos, fsMIRip2NextHop }
    ::= { fsMIRip2LocalRouteTable 1 }

FsMIRip2LocalRouteEntry ::= SEQUENCE {
    fsMIRip2DestNet     IpAddress,
    fsMIRip2DestMask    IpAddress,
    fsMIRip2Tos         INTEGER,
    fsMIRip2NextHop     IpAddress,
    fsMIRip2RtIfIndex   INTEGER,
    fsMIRip2RtType      INTEGER,
    fsMIRip2Proto       INTEGER,
    fsMIRip2ChgTime     INTEGER,
    fsMIRip2Metric      INTEGER,
    fsMIRip2RowStatus   INTEGER,
    fsMIRip2Gateway     IpAddress
}

fsMIRip2DestNet OBJECT-TYPE
    SYNTAX      IpAddress
    ACCESS      not-accessible
    STATUS      mandatory
    DESCRIPTION 
        "The IP Address of the destination network
         ALCATEL NOTE:
             ACCESS:      NA           USAGE:       NA
             PERSIST:     NO           INSRVMOD:    NA
             RANGE:       NA           DEFVALUE:    NA
             UNITS:       NA	      SPARSE:      NO
             DESCR:       NA"
    ::= { fsMIRip2LocalRouteEntry 1 }

fsMIRip2DestMask OBJECT-TYPE
    SYNTAX      IpAddress
    ACCESS      not-accessible
    STATUS      mandatory
    DESCRIPTION 
        "The Destination mask for the destination network
         ALCATEL NOTE:
             ACCESS:      NA           USAGE:       NA
             PERSIST:     NO           INSRVMOD:    NA
             RANGE:       NA           DEFVALUE:    NA
             UNITS:       NA	      SPARSE:      NO
             DESCR:       NA"
    ::= { fsMIRip2LocalRouteEntry 2 }

fsMIRip2Tos OBJECT-TYPE
    SYNTAX      INTEGER (0..2147483647)
    ACCESS      not-accessible
    STATUS      mandatory
    DESCRIPTION 
        "The  value for Rip is always zero
         ALCATEL NOTE:
             ACCESS:      NA           USAGE:       NA
             PERSIST:     NO           INSRVMOD:    NA
             RANGE:       NA           DEFVALUE:    NA
             UNITS:       NA	      SPARSE:      NO
             DESCR:       NA"
    ::= { fsMIRip2LocalRouteEntry 3 }

fsMIRip2NextHop OBJECT-TYPE
    SYNTAX      IpAddress
    ACCESS      not-accessible
    STATUS      mandatory
    DESCRIPTION 
        "The The nexthop address to which any datagrams 
         destined to the destination,to be 
         forwarded. (In some special cases)
         ALCATEL NOTE:
             ACCESS:      NA           USAGE:       NA
             PERSIST:     NO           INSRVMOD:    NA
             RANGE:       NA           DEFVALUE:    NA
             UNITS:       NA	      SPARSE:      NO
             DESCR:       NA"
    ::= { fsMIRip2LocalRouteEntry 4 }

fsMIRip2RtIfIndex OBJECT-TYPE
    SYNTAX      INTEGER
    ACCESS      read-only
    STATUS      mandatory
    DESCRIPTION 
        " The interface through which the route is learnt
         ALCATEL NOTE:
                 ACCESS:      NA           USAGE:       NA
                 PERSIST:     NO           INSRVMOD:    NA
                 RANGE:       DEP       DEFVALUE:    NA
                 UNITS:       NA           SPARSE:      NO
         	    DESCR:	 DEP(RANGE):The range is from 1 to the (max number of physical interfaces  +  
         			 total number of IP interfaces in the system ).
         			 The max number of physical interfaces is obtained from the object issSystemNumberOfPorts in fsiss.mib.
         			 The total number of IP interfaces in the system  is 
         			 obtained from the object fsVrfMaxIpInterfaces in fsvrf.mib."
    ::= { fsMIRip2LocalRouteEntry 5 }

fsMIRip2RtType OBJECT-TYPE
    SYNTAX      INTEGER
    ACCESS      read-only
    STATUS      mandatory
    DESCRIPTION 
        "The  value for Rip is always zero 
         ALCATEL NOTE:
                 ACCESS:      NA           USAGE:       NA
                 PERSIST:     NO           INSRVMOD:    NA
                 RANGE:       0..4	      DEFVALUE:    NA
                 UNITS:       NA	      SPARSE:      NO
                 DESCR:       NA"
    ::= { fsMIRip2LocalRouteEntry 6 }

fsMIRip2Proto OBJECT-TYPE
    SYNTAX      INTEGER
    ACCESS      read-only
    STATUS      mandatory
    DESCRIPTION 
        "The protocol id   == RIP (8 - 1)here 
         ALCATEL NOTE:
                 ACCESS:      NA           USAGE:       NA
                 PERSIST:     NO           INSRVMOD:    NA
                 RANGE:       1..3|8	      DEFVALUE:    NA
                 UNITS:       NA	      	  SPARSE:      NO
                 DESCR:       NA"
    ::= { fsMIRip2LocalRouteEntry 7 }

fsMIRip2ChgTime OBJECT-TYPE
    SYNTAX      INTEGER
    ACCESS      read-only
    STATUS      mandatory
    DESCRIPTION 
        "The time when the route is installed 
         ALCATEL NOTE:
                 ACCESS:      NA           USAGE:       NA
                 PERSIST:     NO           INSRVMOD:    NA
                 RANGE:       NA	      DEFVALUE:    0
                 UNITS:       TimeTicks    SPARSE:      NO
                 DESCR:       NA"
    ::= { fsMIRip2LocalRouteEntry 8 }

fsMIRip2Metric OBJECT-TYPE
    SYNTAX      INTEGER
    ACCESS      read-only
    STATUS      mandatory
    DESCRIPTION 
        "The reachability cost for the destination 
         ALCATEL NOTE:
                 ACCESS:      NA           USAGE:       NA
                 PERSIST:     NO           INSRVMOD:    NA
                 RANGE:       1..16        DEFVALUE:    NA
                 UNITS:       NA	      SPARSE:      NO
                 DESCR:       NA"
    ::= { fsMIRip2LocalRouteEntry 9 }

fsMIRip2RowStatus OBJECT-TYPE
    SYNTAX      INTEGER
    ACCESS      read-only
    STATUS      mandatory
    DESCRIPTION 
        "Row status for perticular route entry 
         ALCATEL NOTE:
                 ACCESS:      NA           USAGE:       NA
                 PERSIST:     NO           INSRVMOD:    NA
                 RANGE:       1,2	      DEFVALUE:    NA
                 UNITS:       NA	      SPARSE:      NO
                 DESCR:       NA"
    ::= { fsMIRip2LocalRouteEntry 10 }

fsMIRip2Gateway OBJECT-TYPE
    SYNTAX      IpAddress
    ACCESS      read-only
    STATUS      mandatory
    DESCRIPTION 
        "The gateway address to which any datagrams
         destined to the destination, to be forwarded 
         ALCATEL NOTE:
             ACCESS:      NA           USAGE:       NA
             PERSIST:     NO           INSRVMOD:    NA
             RANGE:       NA	      	  DEFVALUE:    NA
             UNITS:       NA	          SPARSE:      NO
             DESCR:       NA"
    ::= { fsMIRip2LocalRouteEntry 11 }

fsMIRipAggTable OBJECT-TYPE
    SYNTAX      SEQUENCE OF FsMIRipAggEntry
    ACCESS      not-accessible
    STATUS      mandatory
    DESCRIPTION 
        "The (conceptual) table listing the router's
         supernet routes.RIP advertises only supernet
         routes on the speicified interface. And it
         suppresses all routes which are subset of the supernet.
         ALCATEL NOTE:
         	    TABLESIZE:	 DEP
             DESCR: The Default Table size is 12 and can be changed Dynamically using the object FsNoOfAggregatedRoutes"
    ::= { fsMIRip2GeneralGroup 8 }

fsMIRipAggEntry OBJECT-TYPE
    SYNTAX      FsMIRipAggEntry
    ACCESS      not-accessible
    STATUS      mandatory
    DESCRIPTION 
        "An entry (conceptual row) in the
         fsRipAggTable representing supertnet route for
         the domain.
         Row creation : A fsRipAgg Entry shall be created in one step by a
         	set-request with all necessary parameter values and
         	fsRipAggStatus set to Enabled(1).
         Row deletion : A fsRipAgg Entry shall be deleted by setting
         	the fsRipAggStatus of the specific entry to Disabled(2).
         Index usage : the indexes are fsMIRipContextId, fsRipAggAddress and fsRipAggAddressMask.
         Note that entries will be presented to the SNMP manager in full
         lexicographical order :  sorted on fsMIRipContextId then on fsRipAggAddress, then on fsRipAggAddressMask"
    INDEX       { fsMIRipContextId, fsMIRipAggAddress, 
                  fsMIRipAggAddressMask }
    ::= { fsMIRipAggTable 1 }

FsMIRipAggEntry ::= SEQUENCE {
    fsMIRipAggAddress       IpAddress,
    fsMIRipAggAddressMask   IpAddress,
    fsMIRipAggStatus        RowStatus
}

fsMIRipAggAddress OBJECT-TYPE
    SYNTAX      IpAddress
    ACCESS      not-accessible
    STATUS      mandatory
    DESCRIPTION 
        "The aggregated address which when combined with the
         corresponding value of fsRipAggAddressMask
         identifies the supernet route for this domain.
         ALCATEL NOTE:
         ACCESS:      RO           USAGE:       NA
         PERSIST:     YES          INSRVMOD:    NA
         RANGE:       NA           DEFVALUE:    NA
         UNITS:       NA	      SPARSE:      NO
         DESCR:       NA"
    ::= { fsMIRipAggEntry 2 }

fsMIRipAggAddressMask OBJECT-TYPE
    SYNTAX      IpAddress
    ACCESS      not-accessible
    STATUS      mandatory
    DESCRIPTION 
        "The aggregated address mask which when combined with
         the corresponding value of fsRipAggAddress
         identifies the supernet route for the domain.
         ALCATEL NOTE:
         ACCESS:      RO           USAGE:       NA
         PERSIST:     YES          INSRVMOD:    NA
         RANGE:       NA           DEFVALUE:    NA
         UNITS:       NA	      SPARSE:      NO
         DESCR:       NA"
    ::= { fsMIRipAggEntry 3 }

fsMIRipAggStatus OBJECT-TYPE
    SYNTAX      RowStatus
    ACCESS      read-write
    STATUS      mandatory
    DESCRIPTION 
        "The object specifies the aggrigation status.
         ALCATEL NOTE:
             ACCESS:      NA           USAGE:       MAND
             PERSIST:     YES          INSRVMOD:    YES
             RANGE:       NA           DEFVALUE:    NA
             UNITS:       NA	      SPARSE:      NO
             DESCR:       NA"
    ::= { fsMIRipAggEntry 4 }

fsMIRipRouteMapTable OBJECT-TYPE
    SYNTAX      SEQUENCE OF FsMIRipRouteMapEntry
    ACCESS      not-accessible
    STATUS      mandatory
    DESCRIPTION 
        "The route map table of RIP lists the filters applied on RIP route advertisements. 
         ALCATEL NOTE:
         	    TABLESIZE:	 6400
               DESCR:       NA"
    ::= { fsMIRip2GeneralGroup 9 }

fsMIRipRouteMapEntry OBJECT-TYPE
    SYNTAX      FsMIRipRouteMapEntry
    ACCESS      not-accessible
    STATUS      mandatory
    DESCRIPTION 
        "An entry represents the route that can or cannot be propagated by RIP over an interface.
         Row creation : A fsMIRipRouteMap Entry shall be created in one step by a
             		set-request with all necessary parameter values and
             		fsMIRipRouteMapStatus set to createAndGo(4)/createAndWait(5).
         Row deletion : A fsMIRipRouteMap Entry shall be deleted by setting
             		the fsMIRipRouteMapStatus of the specific entry to destroy(6).
         Index usage : the indexes are fsMIRipRouteMapIfIndex and fsMIRipRouteMapSubIndex.
         Note that entries will be presented to the SNMP manager in full
         lexicographical order :  sorted on fsMIRipRouteMapIfIndex,then on fsMIRipRouteMapSubIndex"
    INDEX       { fsMIRipRouteMapIfIndex, fsMIRipRouteMapSubIndex }
    ::= { fsMIRipRouteMapTable 1 }

FsMIRipRouteMapEntry ::= SEQUENCE {
    fsMIRipRouteMapIfIndex      INTEGER,
    fsMIRipRouteMapSubIndex     INTEGER,
    fsMIRipRouteMapIpAddress    IpAddress,
    fsMIRipRouteMapDirection    INTEGER,
    fsMIRipRouteMapAction       INTEGER,
    fsMIRipRouteMapSubnetMask   IpAddress,
    fsMIRipRouteMapStatus       RowStatus
}

fsMIRipRouteMapIfIndex OBJECT-TYPE
    SYNTAX      INTEGER (1..2147483647)
    ACCESS      read-only
    STATUS      mandatory
    DESCRIPTION 
        "The IP interface to which the route map filter is to be applied
         ALCATEL NOTE:
             ACCESS:      NA           USAGE:       NA
             PERSIST:     YES          INSRVMOD:    NA
             RANGE:       NA           DEFVALUE:    NA
             UNITS:       NA	      SPARSE:      NO
             DESCR:       The IP interfaces will start from 65536 to the total number of IP interfaces 
                          in the system is obtained from the object fsVrfMaxIpInterfaces in fsvrf.mib.  
                          The indices 81920 & 81921 are reserved for vlan 4094 & 4093 respectively."
    ::= { fsMIRipRouteMapEntry 1 }

fsMIRipRouteMapSubIndex OBJECT-TYPE
    SYNTAX      INTEGER (1..2147483647)
    ACCESS      read-only
    STATUS      mandatory
    DESCRIPTION 
        "The entry sub-index. Each route map entry may have rules for multiple IP addresses.
         This sub index identifies the rule for each IP address.
         ALCATEL NOTE:
         ACCESS:      NA           USAGE:       NA
         PERSIST:     YES          INSRVMOD:    NA
         RANGE:       NA       DEFVALUE:    NA
         UNITS:       NA	      SPARSE:      NO
         DESCR:       NA"
    ::= { fsMIRipRouteMapEntry 2 }

fsMIRipRouteMapIpAddress OBJECT-TYPE
    SYNTAX      IpAddress
    ACCESS      read-write
    STATUS      mandatory
    DESCRIPTION 
        "The IpAddress of the subnet that can be allowed or disallowed to be propagated by RIP over the interface
         ALCATEL NOTE:
             ACCESS:      NA           USAGE:       MAND
             PERSIST:     YES          INSRVMOD:    YES
             RANGE:       NA           DEFVALUE:    NA
             UNITS:       NA	      SPARSE:      NO
             DESCR:       NA"
    ::= { fsMIRipRouteMapEntry 3 }

fsMIRipRouteMapDirection OBJECT-TYPE
    SYNTAX      INTEGER { transmit(1), receive(2) }
    ACCESS      read-write
    STATUS      mandatory
    DESCRIPTION 
        "This MIB object specifes the direction in which the RIP routes are advertised over an IP interface. Only direction TRANSMIT is supported. Direction receive is not supported.
         ALCATEL NOTE:
             ACCESS:      NA           USAGE:       OPT
             PERSIST:     YES          INSRVMOD:    YES
             RANGE:       1            DEFVALUE:    NA
             UNITS:       NA	      SPARSE:      NO
             DESCR:       NA"
    DEFVAL      { transmit }
    ::= { fsMIRipRouteMapEntry 4 }

fsMIRipRouteMapAction OBJECT-TYPE
    SYNTAX      INTEGER { permit(1), deny(2) }
    ACCESS      read-write
    STATUS      mandatory
    DESCRIPTION 
        "This MIB object specifes the action to be allowed.
         Permit - The route will be advertised by RIP over 
         the interface in transmit direction. In direction 
         receive this route will be accepted by RIP for 
         advertisement. Deny - The route will not be 
         advertised by RIP over the interface in transmit 
         direction. In the direction receive this route 
         will not be accepted by RIP for advertisement 
         ALCATEL NOTE:
         ACCESS:      NA           USAGE:       OPT
         PERSIST:     YES          INSRVMOD:    YES
         RANGE:       NA           DEFVALUE:    NA
         UNITS:       NA	      SPARSE:      NO
         DESCR:       NA"
    DEFVAL      { permit }
    ::= { fsMIRipRouteMapEntry 5 }

fsMIRipRouteMapSubnetMask OBJECT-TYPE
    SYNTAX      IpAddress
    ACCESS      read-write
    STATUS      mandatory
    DESCRIPTION 
        "The SubnetMask of the subnet that can be allowed or disallowed to be propagated by RIP over the interface
         ALCATEL NOTE:
             ACCESS:      NA           USAGE:       MAND
             PERSIST:     YES          INSRVMOD:    YES
             RANGE:       NA           DEFVALUE:    NA
             UNITS:       NA	      SPARSE:      NO
             DESCR:       NA"
    ::= { fsMIRipRouteMapEntry 6 }

fsMIRipRouteMapStatus OBJECT-TYPE
    SYNTAX      RowStatus
    ACCESS      read-write
    STATUS      mandatory
    DESCRIPTION 
        "The row status variable, used according to
         row installation and removal conventions.
         ALCATEL NOTE:
         ACCESS:      NA           USAGE:       MAND
         PERSIST:     YES          INSRVMOD:    YES
         RANGE:       1,4,5,6      DEFVALUE:    NA
         UNITS:       NA	      SPARSE:      NO
         DESCR:       NA"
    ::= { fsMIRipRouteMapEntry 7 }

fsMIRip2NumRoutesAllVrf OBJECT-TYPE
    SYNTAX      INTEGER
    ACCESS      read-only
    STATUS      mandatory
    DESCRIPTION 
        "This gives the Total number of RIP routes in all the VRFs.
         ALCATEL NOTE:
             ACCESS:      NA           USAGE:       NA
             PERSIST:     NO           INSRVMOD:    NA
             RANGE:       NA           DEFVALUE:    NA      
             UNITS:       NA           SPARSE:      NA
             DESCR:       In ECNTA, Get of this object will always return -1, since Multiple instance is not supported in ECNTA"
    DEFVAL      { 0 }
    ::= { fsMIRip2GeneralGroup 10 }

fsMIRip2NumRedistrRoutesAllVrf OBJECT-TYPE
    SYNTAX      INTEGER
    ACCESS      read-only
    STATUS      mandatory
    DESCRIPTION 
        "This gives the Total number of Redistributed routes in RIP in all the VRFs.
         ALCATEL NOTE:
             ACCESS:      NA           USAGE:       NA
             PERSIST:     NO           INSRVMOD:    NA
             RANGE:       NA           DEFVALUE:    NA      
             UNITS:       NA           SPARSE:      NA
             DESCR:       In ECNTA, Get of this object will always return -1, since Multiple instance is not supported in ECNTA"
    DEFVAL      { 0 }
    ::= { fsMIRip2GeneralGroup 11 }

fsMIRip2RouteMapAvailableSubIndex OBJECT-TYPE
    SYNTAX      INTEGER (1..6400)
    ACCESS      read-only
    STATUS      mandatory
    DESCRIPTION 
        "Shows the next available free sub index for  creating the route map.
         This is related to the fsMIRipRouteMapSubIndex in fsMIRipRouteMapTable
         ALCATEL NOTE:
            ACCESS:      NA           USAGE:       NA
            PERSIST:     NO           INSRVMOD:    NA
            RANGE:       NA           DEFVALUE:    NA      
            UNITS:       NA	      SPARSE:      NA
            DESCR:       NA"
    ::= { fsMIRip2GeneralGroup 12 }

fsMINewRipRouteMapAvailableRouteMapIndex OBJECT-TYPE
    SYNTAX      INTEGER
    ACCESS      read-only
    STATUS      mandatory
    DESCRIPTION 
        "Shows the next available free RouteMap Index for creating the route map.
         This object relates to fsMINewRipRouteMapIndex in fsMINewRipRouteMapTable.
         
         ALCATEL NOTE:
         ACCESS:      NA           USAGE:       NA
         PERSIST:     NO           INSRVMOD:    NA
         RANGE:       NA           DEFVALUE:    NA      
         UNITS:       NA	      SPARSE:      NA
         DESCR:       NA"
    ::= { fsMIRip2GeneralGroup 13 }

fsMINewRipRouteMapTable OBJECT-TYPE
    SYNTAX      SEQUENCE OF FsMINewRipRouteMapEntry
    ACCESS      not-accessible
    STATUS      mandatory
    DESCRIPTION 
        "The route map table of RIP lists the filters applied on RIP route advertisements on 
         both Egress and Ingress ports.
         ALCATEL NOTE:
          TABLESIZE:	0..12800
          DESCR:       NA"
    ::= { fsMIRip2GeneralGroup 14 }

fsMINewRipRouteMapEntry OBJECT-TYPE
    SYNTAX      FsMINewRipRouteMapEntry
    ACCESS      not-accessible
    STATUS      mandatory
    DESCRIPTION 
        "An entry represents the route that can or cannot be propogated by RIP over an interface.
         Row creation : A fsMINewRipRouteMap Entry shall be created in one step by a
             		set-request with all necessary parameter values and
             		fsMINewRipRouteMapStatus set to createAndGo(4)/createAndWait(5).
         Row deletion : A fsMINewRipRouteMap Entry shall be deleted by setting
             		the fsMINewRipRouteMapStatus of the specific entry to destroy(6).
         Index usage : the indexes are fsMIRipContextId,fsMIRip2IfConfAddress,fsMINewRipRouteMapDirection,
         			  fsMINewRipRouteMapIndex
         Note that entries will be presented to the SNMP manager in full lexicographical order:
         			sorted on fsMIRipContextId,fsMIRip2IfConfAddress, fsMINewRipRouteMapDirection,
         			fsMINewRipRouteMapIndex. "
    INDEX       { fsMIRipContextId, fsMIRip2IfConfAddress, 
                  fsMINewRipRouteMapDirection, fsMINewRipRouteMapIndex }
    ::= { fsMINewRipRouteMapTable 1 }

FsMINewRipRouteMapEntry ::= SEQUENCE {
    fsMINewRipRouteMapDirection     INTEGER,
    fsMINewRipRouteMapIndex         INTEGER,
    fsMINewRipRouteMapIpAddress     IpAddress,
    fsMINewRipRouteMapSubnetMask    IpAddress,
    fsMINewRipRouteMapMatch         INTEGER,
    fsMINewRipRouteMapAction        INTEGER,
    fsMINewRipRouteMapStatus        RowStatus
}

fsMINewRipRouteMapDirection OBJECT-TYPE
    SYNTAX      INTEGER { egress(1), ingress(2) }
    ACCESS      read-only
    STATUS      mandatory
    DESCRIPTION 
        "This MIB object specifes the direction in which the RIP routes are advertised over an IP interface.
         ALCATEL NOTE:
            ACCESS:      NA           USAGE:       MAND
            PERSIST:     YES          INSRVMOD:    YES
            RANGE:       NA            DEFVALUE:    NA
            UNITS:       NA	      SPARSE:      NO
            DESCR:       NA"
    ::= { fsMINewRipRouteMapEntry 1 }

fsMINewRipRouteMapIndex OBJECT-TYPE
    SYNTAX      INTEGER (1..2147483647)
    ACCESS      read-only
    STATUS      mandatory
    DESCRIPTION 
        "This MIB Object identifies the rule number uniquely in the RipRouteMap 
         Table
         	
         ALCATEL NOTE:
         ACCESS:      NA                  USAGE:       NA
         PERSIST:     YES                 INSRVMOD:    NA
         RANGE:       1..TABLESIZE        DEFVALUE:    NA
         UNITS:       NA	             SPARSE:      NO
         DESCR:       NA"
    ::= { fsMINewRipRouteMapEntry 2 }

fsMINewRipRouteMapIpAddress OBJECT-TYPE
    SYNTAX      IpAddress
    ACCESS      read-write
    STATUS      mandatory
    DESCRIPTION 
        "The IpAddress of the subnet that can be allowed or disallowed to be propagated by RIP over the interface
         ALCATEL NOTE:
             ACCESS:      NA           USAGE:       MAND
             PERSIST:     YES          INSRVMOD:    YES
             RANGE:       NA           DEFVALUE:    NA
             UNITS:       NA	      SPARSE:      NO
             DESCR:       NA"
    ::= { fsMINewRipRouteMapEntry 3 }

fsMINewRipRouteMapSubnetMask OBJECT-TYPE
    SYNTAX      IpAddress
    ACCESS      read-write
    STATUS      mandatory
    DESCRIPTION 
        "The SubnetMask of the subnet that can be allowed or disallowed to be propagated by RIP over the interface
         ALCATEL NOTE:
             ACCESS:      NA           USAGE:       MAND
             PERSIST:     YES          INSRVMOD:    YES
             RANGE:       NA           DEFVALUE:    NA
             UNITS:       NA	    SPARSE:      NO
             DESCR:       NA"
    ::= { fsMINewRipRouteMapEntry 4 }

fsMINewRipRouteMapMatch OBJECT-TYPE
    SYNTAX      INTEGER { exactmatch(1), mostspecificmatch(2) }
    ACCESS      read-write
    STATUS      mandatory
    DESCRIPTION 
        "This MIB object specifes the match type required for selecting  the RIP routes to be 
         advertised over an IP interface. 
         ALCATEL NOTE:
           ACCESS:      NA           USAGE:       OPT
           PERSIST:     YES          INSRVMOD:    YES
           RANGE:       NA            DEFVALUE:    NA
           UNITS:       NA	      SPARSE:     NO
           DESCR:       NA"
    DEFVAL      { exactmatch }
    ::= { fsMINewRipRouteMapEntry 5 }

fsMINewRipRouteMapAction OBJECT-TYPE
    SYNTAX      INTEGER { permit(1), deny(2) }
    ACCESS      read-write
    STATUS      mandatory
    DESCRIPTION 
        "This MIB object specifes the action to be allowed.
         Permit - The route will be advertised by RIP over 
               the interface in transmit direction. In direction 
               receive this route will be accepted by RIP for 
               advertisement.
         Deny - The route will not be advertised by RIP over the 
         	      interface in transmit direction. In the direction
         	      receive this route will not be accepted by RIP for advertisement. 
         ALCATEL NOTE:
         ACCESS:      NA           USAGE:       OPT
         PERSIST:     YES          INSRVMOD:    YES
         RANGE:       NA           DEFVALUE:    NA
         UNITS:       NA	      SPARSE:      NO
         DESCR:       NA"
    DEFVAL      { permit }
    ::= { fsMINewRipRouteMapEntry 6 }

fsMINewRipRouteMapStatus OBJECT-TYPE
    SYNTAX      RowStatus
    ACCESS      read-write
    STATUS      mandatory
    DESCRIPTION 
        "The row status variable, used according to row installation and removal conventions.
         ALCATEL NOTE:
            ACCESS:      NA           USAGE:       MAND
            PERSIST:     YES          INSRVMOD:    YES
            RANGE:       1,4,5,6      DEFVALUE:    NA
            UNITS:       NA	      SPARSE:      NO
            DESCR:       NA"
    ::= { fsMINewRipRouteMapEntry 7 }

fsMIRipRRDGeneralGroup OBJECT IDENTIFIER
    ::= { fsMIRip 2 }

fsMIRipRRDGlobalTable OBJECT-TYPE
    SYNTAX      SEQUENCE OF FsMIRipRRDGlobalEntry
    ACCESS      not-accessible
    STATUS      mandatory
    DESCRIPTION 
        "This Table Contains the list of globals for a
         Context.
         ALCATEL NOTE:
            TABLESIZE:   64	
            DESCR:       NA"
    ::= { fsMIRipRRDGeneralGroup 1 }

fsMIRipRRDGlobalEntry OBJECT-TYPE
    SYNTAX      FsMIRipRRDGlobalEntry
    ACCESS      not-accessible
    STATUS      mandatory
    DESCRIPTION 
        "An entry of fsMIRip2GlobalTable.
         Row creation : An entry will be created when a RIP instance is created 
                        by creating an entry in fsMIStdRip2IfConfTable and FsMIRip2IfConfTable  . 
         Row deletion : An entry will be deleted when an entry is deleted in tables 
                        fsMIStdRip2IfConfTable and FsMIRip2IfConfTable  .
           Index usage : the index is fsMIRipContextId.
           Note that entries will be presented to the SNMP manager in full
           lexicographical order :  sorted on fsMIRipContextId."
    INDEX       { fsMIRipContextId }
    ::= { fsMIRipRRDGlobalTable 1 }

FsMIRipRRDGlobalEntry ::= SEQUENCE {
    fsMIRipRRDGlobalStatus          INTEGER,
    fsMIRipRRDSrcProtoMaskEnable    INTEGER,
    fsMIRipRRDSrcProtoMaskDisable   INTEGER,
    fsMIRipRRDRouteTagType          INTEGER,
    fsMIRipRRDRouteTag              INTEGER,
    fsMIRipRRDRouteDefMetric        INTEGER
}

fsMIRipRRDGlobalStatus OBJECT-TYPE
    SYNTAX      INTEGER { enabled(1), disabled(2) }
    ACCESS      read-write
    STATUS      mandatory
    DESCRIPTION 
        "This MIB object enables / disables RIP to participate
         in Route Redistribution. If set to enabled then RIP will start 
         advertising the routes learned by other protocols. If set to
         disabled then RIP will stop redistribution of routes
         but will continue to send updates to the RTM.
         ALCATEL NOTE:
             ACCESS:      NA           USAGE:       NA
             PERSIST:     YES          INSRVMOD:    YES
             RANGE:       NA	      DEFVALUE:    NA
             UNITS:       NA	      SPARSE:      NA
             DESCR:       NA"
    DEFVAL      { disabled }
    ::= { fsMIRipRRDGlobalEntry 1 }

fsMIRipRRDSrcProtoMaskEnable OBJECT-TYPE
    SYNTAX      INTEGER (0..65535)
    ACCESS      read-write
    STATUS      mandatory
    DESCRIPTION 
        "This object determines the protocols from which the routes 
         have to be imported to RIP
         Bit 1, if set indicates the routes have to be imported from the 
         local interface.
         Bit 2, if set indicates the routes have to be imported from static route.
         Bit 12, if set indicates the routes have to be imported from OSPF.
         Bit 13, if set indicates the routes have to be imported from BGP.
         ALCATEL NOTE:
             ACCESS:      NA           USAGE:       NA
             PERSIST:     YES          INSRVMOD:    YES
             RANGE:       NA	      DEFVALUE:    NA
             UNITS:       NA	      SPARSE:      NA
             DESCR:       NA"
    DEFVAL      { 0 }
    ::= { fsMIRipRRDGlobalEntry 2 }

fsMIRipRRDSrcProtoMaskDisable OBJECT-TYPE
    SYNTAX      INTEGER (0..65535)
    ACCESS      read-write
    STATUS      mandatory
    DESCRIPTION 
        "This object determines the protocols from which the importing of 
         routes should be stopped to RIP
         Bit 1, if set indicates the routes have to be imported from the 
         local interface.
         Bit 2, if set indicates the routes have to be imported from static route.
         Bit 12, if set indicates the routes have to be imported from OSPF.
         Bit 13,if set indicates the routes have to be imported from BGP.
         ALCATEL NOTE:
             ACCESS:      NA           USAGE:       NA
             PERSIST:     YES          INSRVMOD:    YES
             RANGE:       NA	      DEFVALUE:    NA
             UNITS:       NA	      SPARSE:      NA
             DESCR:       NA"
    DEFVAL      { 0 }
    ::= { fsMIRipRRDGlobalEntry 3 }

fsMIRipRRDRouteTagType OBJECT-TYPE
    SYNTAX      INTEGER { manual(1), automatic(2) }
    ACCESS      read-write
    STATUS      mandatory
    DESCRIPTION 
        "The Tag Type MIB object describes whether Tags
         will be automatically generated or will be manually 
         configured. If tags are manually configured , the 
         fsMIRipMIRRDRouteTag MIB has to be set with the Tag
         value needed.
         ALCATEL NOTE:
             ACCESS:      NA           USAGE:       NA
             PERSIST:     YES          INSRVMOD:    YES
             RANGE:       NA	      DEFVALUE:    NA
             UNITS:       NA	      SPARSE:      NA
             DESCR:       NA"
    DEFVAL      { manual }
    ::= { fsMIRipRRDGlobalEntry 4 }

fsMIRipRRDRouteTag OBJECT-TYPE
    SYNTAX      INTEGER (0..65535)
    ACCESS      read-write
    STATUS      mandatory
    DESCRIPTION 
        " The Route Tag in case the user configures a Manual option for
         the tags .
         ALCATEL NOTE:
             ACCESS:      NA           USAGE:       NA
             PERSIST:     YES          INSRVMOD:    YES
             RANGE:       NA	      DEFVALUE:    NA
             UNITS:       NA	      SPARSE:      NA
             DESCR:       NA"
    DEFVAL      { 0 }
    ::= { fsMIRipRRDGlobalEntry 5 }

fsMIRipRRDRouteDefMetric OBJECT-TYPE
    SYNTAX      INTEGER (1..16)
    ACCESS      read-write
    STATUS      mandatory
    DESCRIPTION 
        "The default metric to be used for the imported routes from RTM.
         ALCATEL NOTE:
                 ACCESS:      NA           USAGE:       NA
                 PERSIST:     YES          INSRVMOD:    YES
                 RANGE:       NA	      DEFVALUE:    NA
                 UNITS:       NA	      SPARSE:      NA
                 DESCR:       NA"
    DEFVAL      { 3 }
    ::= { fsMIRipRRDGlobalEntry 6 }

END -- end of module ARICENT-MIRIP2-MIB.
