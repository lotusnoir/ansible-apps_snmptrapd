--
-- This SMIv1 module has been generated by smidump 0.4.8. Do not edit.
--

DHCP-MIB DEFINITIONS ::= BEGIN

IMPORTS
    ifIndex
        FROM IF-MIB
    OBJECT-TYPE
        FROM RFC-1212
    Counter, Gauge, IpAddress, enterprises
        FROM RFC1155-SMI
    RowStatus, TruthValue
        FROM SNMPv2-TC
    lanxVrfId
        FROM VRF-MIB;

futureDhcpRelay OBJECT IDENTIFIER
    ::= { enterprises futuresoftware(2076) 24 }

-- futureDhcpRelay MODULE-IDENTITY
--     LAST-UPDATED "200204230000Z"
--     ORGANIZATION 
--         "FUTURE SOFTWARE  LIMITED"
--     CONTACT-INFO 
--         " Phone : +91-44-4330550
--          E-mail: support@future.futsoft.com"
--     DESCRIPTION 
--         "The Dhcp Relay agent MIB "
--     REVISION    "200204230000Z"
--     DESCRIPTION 
--         "Theis description is added to avoid error
--          RFC 1450."
--     ::= { enterprises futuresoftware(2076) 24 }


lanxdhcpRelay OBJECT IDENTIFIER
    ::= { futureDhcpRelay 3 }

fsDhcpRelaying OBJECT-TYPE
    SYNTAX      INTEGER { enable(1), disable(2) }
    ACCESS      read-write
    STATUS      mandatory
    DESCRIPTION 
        "Only when enabled, the Relay Agent shall become active.
         ALCATEL NOTE:
             ACCESS:      NA            USAGE:       NA
             PERSIST:     YES           INSRVMOD:    YES
             RANGE:       NA            DEFVALUE:    NA
             UNITS:       NA            SPARSE:      NA
             DESCR:       NA"
    DEFVAL      { disable }
    ::= { lanxdhcpRelay 1 }

fsDhcpConfigTraceLevel OBJECT-TYPE
    SYNTAX      INTEGER (0..255)
    ACCESS      read-write
    STATUS      mandatory
    DESCRIPTION 
        "The Trace level Object which has bit masks for 
         various levels of tracing.
         The Following are the bit masks for each level
         
         INIT_SHUT_TRC       0x00000001 
         MGMT_TRC            0x00000002 
         DATA_PATH_TRC       0x00000004 
         CONTROL_PLANE_TRC   0x00000008 
         DUMP_TRC            0x00000010 
         OS_RESOURCE_TRC     0x00000020 
         ALL_FAILURE_TRC     0x00000040 
         BUFFER_TRC          0x00000080 
         ALCATEL NOTE:
         ACCESS:      NA            USAGE:       NA
         PERSIST:     YES           INSRVMOD:    YES
         RANGE:       NA            DEFVALUE:    NA
         UNITS:       NA            SPARSE:      NA
         DESCR:       NA"
    DEFVAL      { 0 }
    ::= { lanxdhcpRelay 16 }

fsDhcpRelayServerTable OBJECT-TYPE
    SYNTAX      SEQUENCE OF FsDhcpRelayServerEntry
    ACCESS      not-accessible
    STATUS      mandatory
    DESCRIPTION 
        "A list of servers configured for the particular VRF.
         ALCATEL NOTE:
            TABLESIZE: 512-Number of Entries in fsDhcpRelayServerInstanceTable
            DESCR: NA"
    ::= { lanxdhcpRelay 18 }

fsDhcpRelayServerEntry OBJECT-TYPE
    SYNTAX      FsDhcpRelayServerEntry
    ACCESS      not-accessible
    STATUS      mandatory
    DESCRIPTION 
        "A Single Server Entry for the particular VRF.
         Row creation : An entry shall be created by a set-request with Vrf Ip Address,VrfID and fsDhcpRelayServerRowStatus set to createAndGo(4).
         Row deletion : An entry shall be deleted by deleting VfrId.
         Index usage : The index is Relay server VrfId and Relay server Ip Address.
         lexicographical order :  sorted on Relay server VrfId , then on Relay server Ip Address"
    INDEX       { fsDhcpRelayServerIpAddrIndex, fsDhcpRelayServerVrfId }
    ::= { fsDhcpRelayServerTable 1 }

FsDhcpRelayServerEntry ::= SEQUENCE {
    fsDhcpRelayServerIpAddrIndex    IpAddress,
    fsDhcpRelayServerVrfId          INTEGER,
    fsDhcpRelayServerName           OCTET STRING,
    fsDhcpRelayServerRowStatus      RowStatus
}

fsDhcpRelayServerIpAddrIndex OBJECT-TYPE
    SYNTAX      IpAddress
    ACCESS      read-only
    STATUS      mandatory
    DESCRIPTION 
        "The IP address of the DHCP server being
         configured on this VRF.
         ALCATEL NOTE:
         ACCESS:      NA           USAGE:       NA
         PERSIST:     YES          INSRVMOD:    NA
         RANGE:       NA           DEFVALUE:    NA
         UNITS:       NA           SPARSE:      NO
         DESCR:       NA"
    ::= { fsDhcpRelayServerEntry 1 }

fsDhcpRelayServerVrfId OBJECT-TYPE
    SYNTAX      INTEGER (0..127)
    ACCESS      read-only
    STATUS      mandatory
    DESCRIPTION 
        "Virtual Router identifier to which this server belongs.
         ALCATEL NOTE:
         	ACCESS:      NA           USAGE:       NA
         	PERSIST:     YES          INSRVMOD:    NA
         	RANGE:       NA           DEFVALUE:    NA
         	UNITS:       NA           SPARSE:      NO
         	DESCR:       NA"
    ::= { fsDhcpRelayServerEntry 2 }

fsDhcpRelayServerName OBJECT-TYPE
    SYNTAX      OCTET STRING (SIZE(0..32))
    ACCESS      read-write
    STATUS      mandatory
    DESCRIPTION 
        "The name of the DHCP server
         ALCATEL NOTE:
         	ACCESS:      NA           USAGE:       NA
         	PERSIST:     YES          INSRVMOD:    YES
         	RANGE:       NA           DEFVALUE:    NA                
         	UNITS:       NA           SPARSE:      NO
         	DESCR:       NA"
    ::= { fsDhcpRelayServerEntry 3 }

fsDhcpRelayServerRowStatus OBJECT-TYPE
    SYNTAX      RowStatus
    ACCESS      read-write
    STATUS      mandatory
    DESCRIPTION 
        "A dhcp server entry can be created or deleted by 
         using this variable. Three operations 'Create and go', 
         Create and wait' and destroy operation has been 
         supported for DHCP server table.
         ALCATEL NOTE:
         ACCESS:      NA           USAGE:       MAND
         PERSIST:     YES          INSRVMOD:    YES
         RANGE:       1,4,5,6      DEFVALUE:    NA                        
         UNITS:       NA           SPARSE:      NO                        
         DESCR:       NA"
    ::= { fsDhcpRelayServerEntry 4 }

fsDhcpRelayNumInPackets OBJECT-TYPE
    SYNTAX      INTEGER
    ACCESS      read-only
    STATUS      mandatory
    DESCRIPTION 
        "Gives the number of DHCP relay packets received.
         ALCATEL NOTE:
             ACCESS:      NA            		USAGE:       NA
             PERSIST:     NO            		INSRVMOD:    NA
             RANGE:       NA            		DEFVALUE:    0                  
             UNITS:       DHCP relay packets    	SPARSE:      NA
             DESCR:       NA"
    ::= { lanxdhcpRelay 20 }

fsDhcpRelayNumOutPackets OBJECT-TYPE
    SYNTAX      INTEGER
    ACCESS      read-only
    STATUS      mandatory
    DESCRIPTION 
        "Gives the number of DHCP relay packets Sent.
         ALCATEL NOTE:
             ACCESS:      NA            		USAGE:       NA
             PERSIST:     NO            		INSRVMOD:    NA
             RANGE:       NA            		DEFVALUE:    0
             UNITS:       DHCP relay packets     SPARSE:      NA             
             DESCR:       NA"
    ::= { lanxdhcpRelay 21 }

fsDhcpRelayNumDropPackets OBJECT-TYPE
    SYNTAX      INTEGER
    ACCESS      read-only
    STATUS      mandatory
    DESCRIPTION 
        "Gives the number of DHCP relay packets dropped.
         ALCATEL NOTE:
             ACCESS:      NA            		USAGE:       NA
             PERSIST:     NO            		INSRVMOD:    NA
             RANGE:       NA            		DEFVALUE:    0               
             UNITS:       DHCP relay packets     SPARSE:      NA
             DESCR:       NA"
    ::= { lanxdhcpRelay 22 }

fsDhcpRelayVrfTable OBJECT-TYPE
    SYNTAX      SEQUENCE OF FsDhcpRelayVrfEntry
    ACCESS      not-accessible
    STATUS      mandatory
    DESCRIPTION 
        "DHCP related configuration for the VRF.
         ALCATEL NOTE:
           TABLESIZE: 128
           DESCR: NA"
    ::= { lanxdhcpRelay 23 }

fsDhcpRelayVrfEntry OBJECT-TYPE
    SYNTAX      FsDhcpRelayVrfEntry
    ACCESS      not-accessible
    STATUS      mandatory
    DESCRIPTION 
        "A Single DHCP Relay Agent configuration Entry for the
         particular VRF.
           Row creation : All entries will be created when a lanx Vrf  is
         		created.
         Row deletion : All entries will be deleted when a lanx Vrf is
             	   deleted.
         Index usage : The index is the Lanx VrfID.
         lexicographical order :  Sorted on Lanx VrfID"
    INDEX       { lanxVrfId }
    ::= { fsDhcpRelayVrfTable 1 }

FsDhcpRelayVrfEntry ::= SEQUENCE {
    fsDhcpRelayVrfRelayStatus       INTEGER,
    fsDhcpRelayAgentIpAddr          IpAddress,
    fsDhcpRelayVrfSecsThreshold     INTEGER,
    fsDhcpRelayVrfHopsThreshold     INTEGER,
    fsDhcpRelayVrfContextLifeTime   INTEGER
}

fsDhcpRelayVrfRelayStatus OBJECT-TYPE
    SYNTAX      INTEGER { enable(1), disable(2) }
    ACCESS      read-write
    STATUS      mandatory
    DESCRIPTION 
        "Only when enabled, the DHCP Relay Agent shall become active
         on the VRF.
         ALCATEL NOTE:
          	ACCESS:      NA           USAGE:       NA
         	PERSIST:     YES           INSRVMOD:    YES                      
         	RANGE:       NA           DEFVALUE:    NA                       
         	UNITS:       NA           SPARSE:      NO
         	DESCR:       NA"
    DEFVAL      { disable }
    ::= { fsDhcpRelayVrfEntry 1 }

fsDhcpRelayAgentIpAddr OBJECT-TYPE
    SYNTAX      IpAddress
    ACCESS      read-write
    STATUS      mandatory
    DESCRIPTION 
        "Gateway IP address that will be used by the DHCP Relay Agent to
         fill the DHCP packets for this VRF.
         ALCATEL NOTE:
               ACCESS:      NA           USAGE:       NA
         	PERSIST:     YES           INSRVMOD:    YES                   
         	RANGE:       NA           DEFVALUE:    0.0.0.0
         	UNITS:       NA           SPARSE:      NO
         	DESCR:       NA"
    ::= { fsDhcpRelayVrfEntry 2 }

fsDhcpRelayVrfSecsThreshold OBJECT-TYPE
    SYNTAX      INTEGER (0..5)
    ACCESS      read-write
    STATUS      mandatory
    DESCRIPTION 
        "The time(in Seconds) within which a request must be answered.
         ALCATEL NOTE:
         	      	ACCESS:      NA           USAGE:       NA
             	PERSIST:     YES           INSRVMOD:    YES              
             	RANGE:       NA           DEFVALUE:    0             
             	UNITS:       Seconds      SPARSE:      NO
             	DESCR:       NA"
    DEFVAL      { 0 }
    ::= { fsDhcpRelayVrfEntry 3 }

fsDhcpRelayVrfHopsThreshold OBJECT-TYPE
    SYNTAX      INTEGER (0..16)
    ACCESS      read-write
    STATUS      mandatory
    DESCRIPTION 
        "The maximum number of routers/nodes the request may be sent
         through. Default value is 4.
          ALCATEL NOTE:
                ACCESS:      NA           USAGE:       NA
         	PERSIST:     YES           INSRVMOD:    YES
         	RANGE:       NA           DEFVALUE:    4                     
         	UNITS:       NA           SPARSE:      NO
         	DESCR:       NA"
    DEFVAL      { 4 }
    ::= { fsDhcpRelayVrfEntry 4 }

fsDhcpRelayVrfContextLifeTime OBJECT-TYPE
    SYNTAX      INTEGER (1..120)
    ACCESS      read-write
    STATUS      mandatory
    DESCRIPTION 
        "This object specifies the maximum time(in Seconds) for which
         the Application Contexts stored on this VRF will be valid.
         Default value is 30 sec.
         --================= LANX_R3_6 ==================================================
         This object is no longer configurable. The value is internally 
         maintained as a constant.     
         
          ALCATEL NOTE:
                ACCESS:      NA           USAGE:       NA
         	PERSIST:     YES          INSRVMOD:    NA                     
         	RANGE:       NA           DEFVALUE:    NA
         	UNITS:       Seconds      SPARSE:      NO
         	DESCR:       This object is not used by Alcatel"
    DEFVAL      { 30 }
    ::= { fsDhcpRelayVrfEntry 5 }

fsDhcpRelayStatisticsTable OBJECT-TYPE
    SYNTAX      SEQUENCE OF FsDhcpRelayStatisticsEntry
    ACCESS      not-accessible
    STATUS      mandatory
    DESCRIPTION 
        "This Table displays the Statistics of DHCP Relay Agent per VRF.
         ALCATEL NOTE:
            TABLESIZE: 64
            DESCR: NA"
    ::= { lanxdhcpRelay 24 }

fsDhcpRelayStatisticsEntry OBJECT-TYPE
    SYNTAX      FsDhcpRelayStatisticsEntry
    ACCESS      not-accessible
    STATUS      mandatory
    DESCRIPTION 
        "A Single DHCP Relay Agent Statistics Collection for the particular VRF.
         Row creation : All entries will be created when a lanx Vrf  is
         		created.
         Row deletion : All entries will be deleted when a lanx Vrf is
              	   deleted.
         Index usage : The index is the Lanx VrfID.
         lexicographical order :  Sorted on Lanx VrfID"
    INDEX       { lanxVrfId }
    ::= { fsDhcpRelayStatisticsTable 1 }

FsDhcpRelayStatisticsEntry ::= SEQUENCE {
    fsDhcpRelayAgentForwardedUpstreamCounter        Gauge,
    fsDhcpRelayAgentForwardedDownstreamCounter      Gauge,
    fsDhcpRelayAgentErrorCounter                    Gauge,
    fsDhcpRelayAgentUserUpstreamInCounter           Gauge,
    fsDhcpRelayAgentNetworkDownstreamInCounter      Gauge,
    fsDhcpRelayAgentInternalCntxtErrCounter         Counter,
    fsDhcpRelayAgentPacketExpiredCounter            Counter,
    fsDhcpRelayAgentTooManyHopsCounter              Counter,
    fsDhcpRelayAgentMalformedPacketsCounter         Counter,
    fsDhcpRelayAgentDuplicateChaddrCounter          Counter,
    fsDhcpRelayAgentNoFreeContextCounter            Counter,
    fsDhcpRelayAgentUpStreamInvalidGiAddrCounter    Counter,
    fsDhcpRelayAgentNoRouteToServerCounter          Counter,
    fsDhcpRelayAgentDownstreamInvalidGiaddrCounter  Counter,
    fsDhcpRelayAgentDownstreamNoContxtFoundCounter  Counter,
    fsDhcpRelayAgentInvalidPacketTypeCounter        Counter,
    fsDhcpRelayAgentCounterReset                    TruthValue,
    fsDhcpRelayAgentInvalidHopsCounter              Counter,
    fsDhcpRelayAgentInvalidChaddrCounter            Counter,
    fsDhcpRelayAgentInterfaceDownCounter            Counter
}

fsDhcpRelayAgentForwardedUpstreamCounter OBJECT-TYPE
    SYNTAX      Gauge
    ACCESS      read-only
    STATUS      mandatory
    DESCRIPTION 
        "This counter is incremented with 1 every time that the DHCP
         Relay Agent transmits a DHCP/BOOTP message upstream towards
         a DHCP/BOOTP server. In case the same DHCP/BOOTP message is
         transmitted to more than one DHCP server, every transmitted
         copy of this DHCP/BOOTP message is counted.
         ALCATEL NOTE:
            ACCESS:      NA                       USAGE:       NA
            PERSIST:     NO                       INSRVMOD:    NA
            RANGE:       NA                       DEFVALUE:    0
            UNITS:       DHCP/BOOTP message       SPARSE:      NO
            DESCR:       NA"
    ::= { fsDhcpRelayStatisticsEntry 1 }

fsDhcpRelayAgentForwardedDownstreamCounter OBJECT-TYPE
    SYNTAX      Gauge
    ACCESS      read-only
    STATUS      mandatory
    DESCRIPTION 
        "This counter is incremented with 1 every time that the DHCP
         Relay Agent transmits a DHCP/BOOTP message downstream towards
         a DHCP/BOOTP client.
         ALCATEL NOTE:
            ACCESS:      NA                       USAGE:       NA
            PERSIST:     NO                       INSRVMOD:    NA
            RANGE:       NA                       DEFVALUE:    0
            UNITS:       DHCP/BOOTP message       SPARSE:      NO
            DESCR:       NA"
    ::= { fsDhcpRelayStatisticsEntry 2 }

fsDhcpRelayAgentErrorCounter OBJECT-TYPE
    SYNTAX      Gauge
    ACCESS      read-only
    STATUS      mandatory
    DESCRIPTION 
        "This counter is incremented with 1 every time that the DHCP
         relay agent discards a DHCP/BOOTP message that could not be
         forwarded because of missing or wrong routing information.
         ALCATEL NOTE:
            ACCESS:      NA                       USAGE:       NA
            PERSIST:     NO                       INSRVMOD:    NA
            RANGE:       NA                       DEFVALUE:    0
            UNITS:       DHCP/BOOTP message       SPARSE:      NO
            DESCR:       NA"
    ::= { fsDhcpRelayStatisticsEntry 3 }

fsDhcpRelayAgentUserUpstreamInCounter OBJECT-TYPE
    SYNTAX      Gauge
    ACCESS      read-only
    STATUS      mandatory
    DESCRIPTION 
        "Counter upcounting when a BOOTP request is received by the
         DHCP/BOOTP Relay Agent from ASAM/subtending side.
         ALCATEL NOTE:
            ACCESS:      NA                  USAGE:       NA
            PERSIST:     NO                  INSRVMOD:    NA
            RANGE:       NA                  DEFVALUE:    0
            UNITS:       BOOTP request       SPARSE:      NO
            DESCR:       NA"
    ::= { fsDhcpRelayStatisticsEntry 4 }

fsDhcpRelayAgentNetworkDownstreamInCounter OBJECT-TYPE
    SYNTAX      Gauge
    ACCESS      read-only
    STATUS      mandatory
    DESCRIPTION 
        "Counter upcounting when a BOOTP reply is received by the
         DHCP/BOOTP Relay Agent from network side.
         ALCATEL NOTE:
            ACCESS:      NA                  USAGE:       NA
            PERSIST:     NO                  INSRVMOD:    NA
            RANGE:       NA                  DEFVALUE:    0
            UNITS:       BOOTP reply         SPARSE:      NO
            DESCR:       NA"
    ::= { fsDhcpRelayStatisticsEntry 5 }

fsDhcpRelayAgentInternalCntxtErrCounter OBJECT-TYPE
    SYNTAX      Counter
    ACCESS      read-only
    STATUS      mandatory
    DESCRIPTION 
        "Number of DHCP packets dropped because of invalid internal contexts
         ALCATEL NOTE:
            ACCESS:      NA                       USAGE:       NA
            PERSIST:     NO                       INSRVMOD:    NA
            RANGE:       NA                       DEFVALUE:    0
            UNITS:       DHCP/BOOTP message       SPARSE:      NO
            DESCR:       NA"
    ::= { fsDhcpRelayStatisticsEntry 6 }

fsDhcpRelayAgentPacketExpiredCounter OBJECT-TYPE
    SYNTAX      Counter
    ACCESS      read-only
    STATUS      mandatory
    DESCRIPTION 
        "Number of DHCP request packets dropped because time stamp on packet
         is less than the threshold time.
         ALCATEL NOTE:
           ACCESS:      NA                       USAGE:       NA
           PERSIST:     NO                       INSRVMOD:    NA
           RANGE:       NA                       DEFVALUE:    0
           UNITS:       DHCP/BOOTP message       SPARSE:      NO
           DESCR:       NA"
    ::= { fsDhcpRelayStatisticsEntry 7 }

fsDhcpRelayAgentTooManyHopsCounter OBJECT-TYPE
    SYNTAX      Counter
    ACCESS      read-only
    STATUS      mandatory
    DESCRIPTION 
        "Number of DHCP request packets dropped because packet hops exceeded
         configured max hops.This check is done only if giaddr of incoming 
         Packet is not = Zero.
         ALCATEL NOTE:
           ACCESS:      NA                       USAGE:       NA
           PERSIST:     NO                       INSRVMOD:    NA
           RANGE:       NA                       DEFVALUE:    0
           UNITS:       DHCP/BOOTP message       SPARSE:      NO
           DESCR:       NA"
    ::= { fsDhcpRelayStatisticsEntry 8 }

fsDhcpRelayAgentMalformedPacketsCounter OBJECT-TYPE
    SYNTAX      Counter
    ACCESS      read-only
    STATUS      mandatory
    DESCRIPTION 
        "Number of DHCP request packets dropped because of packet corruption.The packet corruption 
         occurs when the magic cookie verification fails.Magic cookie is 4 byte field before 
         the Options field  in Dhcp packet .
         
         ALCATEL NOTE:
            ACCESS:      NA                       USAGE:       NA
            PERSIST:     NO                       INSRVMOD:    NA
            RANGE:       NA                       DEFVALUE:    0
            UNITS:       DHCP/BOOTP message       SPARSE:      NO
            DESCR:       NA"
    ::= { fsDhcpRelayStatisticsEntry 9 }

fsDhcpRelayAgentDuplicateChaddrCounter OBJECT-TYPE
    SYNTAX      Counter
    ACCESS      read-only
    STATUS      mandatory
    DESCRIPTION 
        "Number of DHCP packets dropped because the packet matches 
         an existing context in the relay agent, but on a different port.
         ALCATEL NOTE:
           ACCESS:      NA                       USAGE:       NA
           PERSIST:     NO                       INSRVMOD:    NA
           RANGE:       NA                       DEFVALUE:    0
           UNITS:       DHCP/BOOTP message       SPARSE:      NO
           DESCR:       NA"
    ::= { fsDhcpRelayStatisticsEntry 10 }

fsDhcpRelayAgentNoFreeContextCounter OBJECT-TYPE
    SYNTAX      Counter
    ACCESS      read-only
    STATUS      mandatory
    DESCRIPTION 
        "Number of DHCP packets dropped because of failure to add a new 
         context for an incoming packet.Max number of Contexts for LANX globally 
         across vrfs is 512.
         
         ALCATEL NOTE:
           ACCESS:      NA                       USAGE:       NA
           PERSIST:     NO                       INSRVMOD:    NA
           RANGE:       NA                       DEFVALUE:    0
           UNITS:       DHCP/BOOTP message       SPARSE:      NO
           DESCR:       NA"
    ::= { fsDhcpRelayStatisticsEntry 11 }

fsDhcpRelayAgentUpStreamInvalidGiAddrCounter OBJECT-TYPE
    SYNTAX      Counter
    ACCESS      read-only
    STATUS      mandatory
    DESCRIPTION 
        "Number of DHCP request packets dropped because GiAddr matches 
         one of the interfaces' address in the VRF.
         ALCATEL NOTE:
           ACCESS:      NA                       USAGE:       NA
           PERSIST:     NO                       INSRVMOD:    NA
           RANGE:       NA                       DEFVALUE:    0
           UNITS:       DHCP/BOOTP message       SPARSE:      NO
           DESCR:       NA"
    ::= { fsDhcpRelayStatisticsEntry 12 }

fsDhcpRelayAgentNoRouteToServerCounter OBJECT-TYPE
    SYNTAX      Counter
    ACCESS      read-only
    STATUS      mandatory
    DESCRIPTION 
        "Number of DHCP packets dropped because no route is present for DHCP 
         server. i.e unreachable server.
         ALCATEL NOTE:
           ACCESS:      NA                       USAGE:       NA
           PERSIST:     NO                       INSRVMOD:    NA
           RANGE:       NA                       DEFVALUE:    0
           UNITS:       DHCP/BOOTP message       SPARSE:      NO
           DESCR:       NA"
    ::= { fsDhcpRelayStatisticsEntry 13 }

fsDhcpRelayAgentDownstreamInvalidGiaddrCounter OBJECT-TYPE
    SYNTAX      Counter
    ACCESS      read-only
    STATUS      mandatory
    DESCRIPTION 
        "Number of DHCP response packets dropped because DHCP reply does not 
         contain interface address as GiAddr.
         ALCATEL NOTE:
           ACCESS:      NA                       USAGE:       NA
           PERSIST:     NO                       INSRVMOD:    NA
           RANGE:       NA                       DEFVALUE:    0
           UNITS:       DHCP/BOOTP message       SPARSE:      NO
           DESCR:       NA"
    ::= { fsDhcpRelayStatisticsEntry 14 }

fsDhcpRelayAgentDownstreamNoContxtFoundCounter OBJECT-TYPE
    SYNTAX      Counter
    ACCESS      read-only
    STATUS      mandatory
    DESCRIPTION 
        "Number of DHCP response packets dropped because DHCP reply does not
         contain a context.
         ALCATEL NOTE:
           ACCESS:      NA                       USAGE:       NA
           PERSIST:     NO                       INSRVMOD:    NA
           RANGE:       NA                       DEFVALUE:    0
           UNITS:       DHCP/BOOTP message       SPARSE:      NO
           DESCR:       NA"
    ::= { fsDhcpRelayStatisticsEntry 15 }

fsDhcpRelayAgentInvalidPacketTypeCounter OBJECT-TYPE
    SYNTAX      Counter
    ACCESS      read-only
    STATUS      mandatory
    DESCRIPTION 
        "Number of DHCP response packets dropped because DHCP packet does not
         contain a valid message type . The message type should be either 
         BootRequest / BootReply. Otherwise the packet will be dropped and
         this counter gets incremented.
         
         ALCATEL NOTE:
           ACCESS:      NA                       USAGE:       NA
           PERSIST:     NO                       INSRVMOD:    NA
           RANGE:       NA                       DEFVALUE:    0
           UNITS:       DHCP/BOOTP message       SPARSE:      NO
           DESCR:       NA"
    ::= { fsDhcpRelayStatisticsEntry 16 }

fsDhcpRelayAgentCounterReset OBJECT-TYPE
    SYNTAX      TruthValue
    ACCESS      read-write
    STATUS      mandatory
    DESCRIPTION 
        "This object is a button-like object to reset all the counters
         in the VRF. When it is set to Reset value, all counters are
         cleared.
         ALCATEL NOTE:
          ACCESS:      NA                       USAGE:       OPT
          PERSIST:     NO                       INSRVMOD:    NA
          RANGE:       NA                       DEFVALUE:    2
          UNITS:       DHCP/BOOTP message       SPARSE:      NO
          DESCR:       NA"
    DEFVAL      { false }
    ::= { fsDhcpRelayStatisticsEntry 17 }

fsDhcpRelayAgentInvalidHopsCounter OBJECT-TYPE
    SYNTAX      Counter
    ACCESS      read-only
    STATUS      mandatory
    DESCRIPTION 
        "Number of DHCP request  packets dropped when the Giaddr ==0 and received
         hops count in the packet is > 0
         ALCATEL NOTE:
           ACCESS:      NA                       USAGE:       NA
           PERSIST:     NO                       INSRVMOD:    NA
           RANGE:       NA                       DEFVALUE:    0
           UNITS:       DHCP/BOOTP message       SPARSE:      NO
           DESCR:       NA"
    ::= { fsDhcpRelayStatisticsEntry 18 }

fsDhcpRelayAgentInvalidChaddrCounter OBJECT-TYPE
    SYNTAX      Counter
    ACCESS      read-only
    STATUS      mandatory
    DESCRIPTION 
        "This objects value specifies the InvalidChaddrCounter. This counter denotes the
         number of DHCP packets discarded because the 'htype' and 'hlen'  fields of the 
         received DHCP packet do not correspond to Ethernet type and Ethernet mac length or  
         when the chaddr field in the packet is equal to ZERO
         ALCATEL NOTE:
            ACCESS:      NA                       USAGE:       NA
            PERSIST:     NO                       INSRVMOD:    NA
            RANGE:       NA                       DEFVALUE:    0
            UNITS:       DHCP/BOOTP message       SPARSE:      NO
            DESCR:       NA"
    ::= { fsDhcpRelayStatisticsEntry 19 }

fsDhcpRelayAgentInterfaceDownCounter OBJECT-TYPE
    SYNTAX      Counter
    ACCESS      read-only
    STATUS      mandatory
    DESCRIPTION 
        "This counter denotes the number of Dhcp request packets discarded
         because the interface corresponding to the GIADDR is operationally
         down.
         ALCATEL NOTE:
           ACCESS:      NA                       USAGE:       NA
           PERSIST:     NO                       INSRVMOD:    NA
           RANGE:       NA                       DEFVALUE:    0
           UNITS:       DHCP/BOOTP message       SPARSE:      NO
           DESCR:       NA"
    ::= { fsDhcpRelayStatisticsEntry 20 }

fsDhcpRelayVrfInstanceTable OBJECT-TYPE
    SYNTAX      SEQUENCE OF FsDhcpRelayVrfInstanceEntry
    ACCESS      not-accessible
    STATUS      mandatory
    DESCRIPTION 
        "DHCP related configuration for the Multiple Instances in VRF.
         ALCATEL NOTE:
         TABLESIZE:128
         DESCR: NA"
    ::= { lanxdhcpRelay 25 }

fsDhcpRelayVrfInstanceEntry OBJECT-TYPE
    SYNTAX      FsDhcpRelayVrfInstanceEntry
    ACCESS      not-accessible
    STATUS      mandatory
    DESCRIPTION 
        " Multiple DHCP Relay Agent configuration Entries for each VRF
         Row creation :Entries will be created on Activating the row-status.
         Row deletion :Entries will be deleted when RowStatus object is
                       destroyed. Also when the VRF is deleted, all the 
                       instances inthe VRF will be destroyed automatically.
         Index usage : The index is the VrfID and Gateway IpAddress for the
                       relay agent.
         lexicographical order :  Sorted on vrf id and RelayAgentIpAddress "
    INDEX       { lanxVrfId, fsDhcpRelayVrfInstanceAgentIpAddr }
    ::= { fsDhcpRelayVrfInstanceTable 1 }

FsDhcpRelayVrfInstanceEntry ::= SEQUENCE {
    fsDhcpRelayVrfInstanceAgentIpAddr       IpAddress,
    fsDhcpRelayVrfInstanceRelayStatus       INTEGER,
    fsDhcpRelayVrfInstanceName              OCTET STRING,
    fsDhcpRelayVrfInstanceSecsThreshold     INTEGER,
    fsDhcpRelayVrfInstanceHopsThreshold     INTEGER,
    fsDhcpRelayVrfInstanceRowStatus         RowStatus
}

fsDhcpRelayVrfInstanceAgentIpAddr OBJECT-TYPE
    SYNTAX      IpAddress
    ACCESS      read-only
    STATUS      mandatory
    DESCRIPTION 
        "The Gateway Ip Address in which relay agent instance is created.
         ALCATEL NOTE:
           ACCESS:      NA           USAGE:       NA
           PERSIST:     YES          INSRVMOD:    NA
           RANGE:       NA           DEFVALUE:    NA
           UNITS:       NA           SPARSE:      NO
           DESCR:       NA"
    ::= { fsDhcpRelayVrfInstanceEntry 1 }

fsDhcpRelayVrfInstanceRelayStatus OBJECT-TYPE
    SYNTAX      INTEGER { enable(1), disable(2) }
    ACCESS      read-write
    STATUS      mandatory
    DESCRIPTION 
        "The object to enable/disable the relay agent instance.
         ALCATEL NOTE:
           ACCESS:      NA           USAGE:       NA
           PERSIST:     YES          INSRVMOD:    YES
           RANGE:       1-2          DEFVALUE:    NA
           UNITS:       NA           SPARSE:      NO
           DESCR:       NA"
    DEFVAL      { disable }
    ::= { fsDhcpRelayVrfInstanceEntry 2 }

fsDhcpRelayVrfInstanceName OBJECT-TYPE
    SYNTAX      OCTET STRING (SIZE(32))
    ACCESS      read-write
    STATUS      mandatory
    DESCRIPTION 
        "The name of the DHCP Relay Instance. 
         ALCATEL NOTE:
           ACCESS:      NA           USAGE:       NA
           PERSIST:     YES          INSRVMOD:    YES
           RANGE:       NA           DEFVALUE:    NA
           UNITS:       NA           SPARSE:      NO
           DESCR:       NA"
    ::= { fsDhcpRelayVrfInstanceEntry 3 }

fsDhcpRelayVrfInstanceSecsThreshold OBJECT-TYPE
    SYNTAX      INTEGER (0..5)
    ACCESS      read-write
    STATUS      mandatory
    DESCRIPTION 
        "The minimum threshold time(in Seconds) passed since a request
         from client is originated.
         ALCATEL NOTE:
         ACCESS:      NA           USAGE:       NA
         PERSIST:     YES          INSRVMOD:    YES
         RANGE:       NA           DEFVALUE:    0
         UNITS:       Seconds      SPARSE:      NO
         DESCR:       NA"
    DEFVAL      { 0 }
    ::= { fsDhcpRelayVrfInstanceEntry 4 }

fsDhcpRelayVrfInstanceHopsThreshold OBJECT-TYPE
    SYNTAX      INTEGER (0..16)
    ACCESS      read-write
    STATUS      mandatory
    DESCRIPTION 
        "The maximum number of routers/nodes the request may be sent
         through. Default value is 4.
         ALCATEL NOTE:
         ACCESS:      NA           USAGE:       NA
         PERSIST:     YES          INSRVMOD:    YES
         RANGE:       NA           DEFVALUE:    4 
         UNITS:       NA           SPARSE:      NO
         DESCR:       NA"
    DEFVAL      { 4 }
    ::= { fsDhcpRelayVrfInstanceEntry 5 }

fsDhcpRelayVrfInstanceRowStatus OBJECT-TYPE
    SYNTAX      RowStatus
    ACCESS      read-write
    STATUS      mandatory
    DESCRIPTION 
        "A dhcp instance entry can be created or deleted by
         using this variable. The operations Create and go,
         Create and wait, Active and Destroy operation are supported
         for DHCP Relay VRF instance table. The default DHCP relay agent
         instances for each VRF is available in the fsDhcpRelayVrfTable
         ALCATEL NOTE:
         ACCESS:      NA           USAGE:       MAND
         PERSIST:     YES          INSRVMOD:    YES
         RANGE:       1,4,5,6      DEFVALUE:    NA                        
         UNITS:       NA           SPARSE:      NO                        
         DESCR:       NA"
    ::= { fsDhcpRelayVrfInstanceEntry 6 }

fsDhcpRelayServerInstanceTable OBJECT-TYPE
    SYNTAX      SEQUENCE OF FsDhcpRelayServerInstanceEntry
    ACCESS      not-accessible
    STATUS      mandatory
    DESCRIPTION 
        "A list of servers configured for the particular relay agent instance.
         ALCATEL NOTE:
           TABLESIZE:512- Number of entries in fsDhcpRelayServerTable
                     (The number of servers is 512 including the servers in
                      fsDhcpRelayServerTable) 
           DESCR: NA"
    ::= { lanxdhcpRelay 26 }

fsDhcpRelayServerInstanceEntry OBJECT-TYPE
    SYNTAX      FsDhcpRelayServerInstanceEntry
    ACCESS      not-accessible
    STATUS      mandatory
    DESCRIPTION 
        "A Single Server Entry for the particular instance in a VRF.
         Row creation :Entries will be created on Activating the row-status.
         Row deletion: An entry shall be deleted by setting the RowStatus 
                       object to Destroy. The server entry will also get 
                       deleted when corresponding Instance entry is removed.  
         Index usage : The index is Relay server VrfId, Relay server Ip Address
                       and Relay agent Ip address.
         lexicographical order : sorted on Relay server VrfId,
                                RelayInstanceAgentIpaddress then on Relay
                                server Ip Address"
    INDEX       { lanxVrfId, fsDhcpRelayVrfInstanceAgentIpAddr, 
                  fsDhcpRelayServerInstanceIpAddrIndex }
    ::= { fsDhcpRelayServerInstanceTable 1 }

FsDhcpRelayServerInstanceEntry ::= SEQUENCE {
    fsDhcpRelayServerInstanceIpAddrIndex    IpAddress,
    fsDhcpRelayServerInstanceName           OCTET STRING,
    fsDhcpRelayServerInstanceRowStatus      RowStatus
}

fsDhcpRelayServerInstanceIpAddrIndex OBJECT-TYPE
    SYNTAX      IpAddress
    ACCESS      read-only
    STATUS      mandatory
    DESCRIPTION 
        "The IP address of the DHCP server being configured on this instance.
         ALCATEL NOTE:
           ACCESS:      NA           USAGE:       NA
           PERSIST:     YES          INSRVMOD:    NA
           RANGE:       NA           DEFVALUE:    NA
           UNITS:       NA           SPARSE:      NO
           DESCR:       NA"
    ::= { fsDhcpRelayServerInstanceEntry 1 }

fsDhcpRelayServerInstanceName OBJECT-TYPE
    SYNTAX      OCTET STRING (SIZE(32))
    ACCESS      read-write
    STATUS      mandatory
    DESCRIPTION 
        "The name of the DHCP server
         ALCATEL NOTE:
             ACCESS:      NA           USAGE:       NA
             PERSIST:     YES          INSRVMOD:    YES
             RANGE:       NA           DEFVALUE:    NA
             UNITS:       NA           SPARSE:      NO
             DESCR:       NA"
    ::= { fsDhcpRelayServerInstanceEntry 2 }

fsDhcpRelayServerInstanceRowStatus OBJECT-TYPE
    SYNTAX      RowStatus
    ACCESS      read-write
    STATUS      mandatory
    DESCRIPTION 
        "A dhcp server entry for the multiple instances in the VRF can be
         created or deleted by using this variable. The operations
         Create and go, Create and wait, Active and Destroy are supported 
         for DHCP server table. The default DHCP servers on a per VRF is 
         available in fsDhcpRelayServerTable. 
         ALCATEL NOTE:
         ACCESS:      NA           USAGE:       MAND
         PERSIST:     YES          INSRVMOD:    YES
         RANGE:       1,4,5,6      DEFVALUE:    NA
         UNITS:       NA           SPARSE:      NO
         DESCR:       NA"
    ::= { fsDhcpRelayServerInstanceEntry 3 }

fsDhcpRelayInstanceMappingTable OBJECT-TYPE
    SYNTAX      SEQUENCE OF FsDhcpRelayInstanceMappingEntry
    ACCESS      not-accessible
    STATUS      mandatory
    DESCRIPTION 
        "A table for mapping each VLAN interface index to the relay agent Ip
         address which is configured in fsDhcpRelayVrfInstanceTable. If there 
         is no mapping entry available, the default relay agent IP address of
         the VRF is applied.  
         ALCATEL NOTE:
          DESCR: NA"
    ::= { lanxdhcpRelay 27 }

fsDhcpRelayInstanceMappingEntry OBJECT-TYPE
    SYNTAX      FsDhcpRelayInstanceMappingEntry
    ACCESS      not-accessible
    STATUS      mandatory
    DESCRIPTION 
        "A Single Instance Mapping Entry for each Vlan IfIndex.
         Row creation : Entries will be created on Activating the row-status.
         Row deletion : An entry shall be deleted by setting the RowStatus to
                        destroy or when the Vlan interface index is deleted or
                        when the corresponding relay instance node is deleted.
         Index usage  : The index is ifIndex
         lexicographical order : sorted on ifIndex"
    INDEX       { ifIndex }
    ::= { fsDhcpRelayInstanceMappingTable 1 }

FsDhcpRelayInstanceMappingEntry ::= SEQUENCE {
    fsDhcpRelayInstanceMappingRelayAgentIpAddress   IpAddress,
    fsDhcpRelayInstanceMappingRowStatus             RowStatus
}

fsDhcpRelayInstanceMappingRelayAgentIpAddress OBJECT-TYPE
    SYNTAX      IpAddress
    ACCESS      read-write
    STATUS      mandatory
    DESCRIPTION 
        "The relay-agent Ipaddress that should be used as GIADDR for the DHCP
         packets in the Vlan Interface. If the relay-agent IP address is not
         configured for the VLAN interface, then relay agent IP address for 
         the default instance is applied.
         ALCATEL NOTE:
         ACCESS:      NA           USAGE:       NA
         PERSIST:     YES          INSRVMOD:    NO
         RANGE:       NA           DEFVALUE:    NA
         UNITS:       NA           SPARSE:      NO
         DESCR:       NA"
    ::= { fsDhcpRelayInstanceMappingEntry 1 }

fsDhcpRelayInstanceMappingRowStatus OBJECT-TYPE
    SYNTAX      RowStatus
    ACCESS      read-write
    STATUS      mandatory
    DESCRIPTION 
        "A dhcp instance mapping entry for the multiple instances in the VRF
         can be created or deleted by using this variable. The operations
         Create and go, Create and wait, Active and Destroy are supported.
         ALCATEL NOTE:
         ACCESS:      NA           USAGE:       MAND
         PERSIST:     YES          INSRVMOD:    NA
         RANGE:       NA           DEFVALUE:    NA
         UNITS:       NA           SPARSE:      NO
         DESCR:       NA"
    ::= { fsDhcpRelayInstanceMappingEntry 2 }

END -- end of module DHCP-MIB.
