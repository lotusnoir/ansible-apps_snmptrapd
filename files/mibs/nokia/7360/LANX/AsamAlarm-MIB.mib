--
-- This SMIv1 module has been generated by smidump 0.4.8. Do not edit.
--

AsamAlarm-MIB DEFINITIONS ::= BEGIN

IMPORTS
    OBJECT-TYPE
        FROM RFC-1212
    TRAP-TYPE
        FROM RFC-1215
    Counter, Gauge, TimeTicks, enterprises
        FROM RFC1155-SMI
    DisplayString
        FROM SNMPv2-TC;

asam OBJECT IDENTIFIER
    ::= { enterprises alcatel(637) asd(61) 1 }

-- asam MODULE-IDENTITY
--     LAST-UPDATED "200401161000Z"
--     ORGANIZATION 
--         "Future Software Limited"
--     CONTACT-INFO 
--         "
--          Postal:     Future Software Ltd.,
--                      480-481, Anna Salai,
--                      Nandanam,
--                      Chennai,
--                      India  600 035.
--          Telephone: +91-44-4330550
--          E-Mail:     support@future.futsoft.com "
--     DESCRIPTION 
--         "The MIB for Alcatel ESAM LANX alarms"
--     REVISION    "200401161000Z"
--     DESCRIPTION 
--         "This description is added to avoid error
--          RFC 1450."
--     ::= { enterprises alcatel(637) asd(61) 1 }


AsamAlarmCategoryType ::=
    INTEGER { communications(1), qualityofService(2), processingError(3), 
                    equipment(4), environmental(5) }

-- AsamAlarmCategoryType ::= TEXTUAL-CONVENTION
--     STATUS      mandatory
--     DESCRIPTION 
--         "This object gives the description of different
--          alarm categories present in asam."
--     SYNTAX      INTEGER
--                   { communications(1), qualityofService(2), 
--                     processingError(3), equipment(4), 
--                     environmental(5) }

AsamAlarmSeverityType ::=
    INTEGER { indeterminate(1), warning(2), minor(3), major(4), 
                    critical(5) }

-- AsamAlarmSeverityType ::= TEXTUAL-CONVENTION
--     STATUS      mandatory
--     DESCRIPTION 
--         "severity type can be set as one the following,
--          indeterminate - Not a definite known severity level
--          warning - Just to inform as a warning
--          minor - Not service affecting
--          major - Service affecting
--          critical - Service breaking "
--     SYNTAX      INTEGER
--                   { indeterminate(1), warning(2), minor(3), major(4), 
--                     critical(5) }

AsamAlarmServAffType ::=
    INTEGER { serviceAffecting(1), notServiceAffecting(2) }

-- AsamAlarmServAffType ::= TEXTUAL-CONVENTION
--     STATUS      mandatory
--     DESCRIPTION 
--         "Service Affecting type can be as one the following,
--          serviceAffecting - Service Affecting
--          notServiceAffecting - Not Service Affecting."
--     SYNTAX      INTEGER
--                   { serviceAffecting(1), notServiceAffecting(2) }

AsamAlarmModeType ::=
    INTEGER { enabled(1), disabled(2) }

-- AsamAlarmModeType ::= TEXTUAL-CONVENTION
--     STATUS      mandatory
--     DESCRIPTION 
--         "Status of whether an alarm to be reported to the manager
--          see detailed description available at the alarm definition
--          table."
--     SYNTAX      INTEGER
--                   { enabled(1), disabled(2) }

AsamAlarmType ::=
    INTEGER { lanx(51), ethLanx(52) }

-- AsamAlarmType ::= TEXTUAL-CONVENTION
--     STATUS      mandatory
--     DESCRIPTION 
--         "Following are the alarm types identified for LANX,
--          lanx - alarms related with an equip
--          ethLanx - alarms related with the Ethernet Interface"
--     SYNTAX      INTEGER
--                   { lanx(51), ethLanx(52) }

asamAlarmMIB OBJECT IDENTIFIER
    ::= { asam 3 }

asamAlarmTraps OBJECT IDENTIFIER
    ::= { asamAlarmMIB 0 }

asamAlarmTable OBJECT-TYPE
    SYNTAX      SEQUENCE OF AsamAlarmEntry
    ACCESS      not-accessible
    STATUS      mandatory
    DESCRIPTION 
        "This table defines all the possible alarms at the agent.
         For each alarm, there is an entry. Each entry consists of
         an index for the table, alarm id, alarm category, severity
         and reporting mode. The severity and reporting mode are
         manageable objects for the SNMP Manager.
         ALCATEL NOTE :
           TABLESIZE      : 19  
           DESCR          : NA"
    ::= { asamAlarmMIB 1 }

asamAlarmEntry OBJECT-TYPE
    SYNTAX      AsamAlarmEntry
    ACCESS      not-accessible
    STATUS      mandatory
    DESCRIPTION 
        "Entry for alarm table.                                  
         Row creation : A Asam-Alarm entry shall be created when the system is initialized.
         Row deletion : NA
         Index usage : The indexe is asamAlarmId.
            Note that entries will be presented to the SNMP manager in full
            lexicographical order :  sorted on asamAlarmId."
    INDEX       { asamAlarmId }
    ::= { asamAlarmTable 1 }

AsamAlarmEntry ::= SEQUENCE {
    asamAlarmId             INTEGER,
    asamAlarmCategory       AsamAlarmCategoryType,
    asamAlarmSeverity       AsamAlarmSeverityType,
    asamAlarmServAffect     AsamAlarmServAffType,
    asamAlarmReportMode     AsamAlarmModeType
}

asamAlarmId OBJECT-TYPE
    SYNTAX      INTEGER (1..2147483647)
    ACCESS      read-only
    STATUS      mandatory
    DESCRIPTION 
        "This is the unique id for an alarm. It is a combination of 2
         distinct parts of information : the alarm type and the
         alarm number. The first half represents the type and the
         second (most right) part the alarm number. This alarm number
         represents the bit position of an alarm in a bitmap of an
         active alarm entry. Thus the value of asamAlarmId can be
         found using a simple formula: (AlarmType x 2^16) + AlarmNumber.
         E.g. an alarm with alarm type 5 and alarm number 3 is
         represented as 0x00050003.
         ALCATEL NOTE:
            ACCESS	:  NA           	USAGE		:  NA
            PERSIST	:  YES          	INSRVMOD	:  NA
            RANGE	:  NA           	DEFVALUE	:  NA
            UNITS	:  NA           	SPARSE		:  NO
            DESCR	:  NA"
    ::= { asamAlarmEntry 1 }

asamAlarmCategory OBJECT-TYPE
    SYNTAX      AsamAlarmCategoryType
    ACCESS      read-only
    STATUS      mandatory
    DESCRIPTION 
        "This object defines the category of an alarm.
         Alarm categories as Communications, QualityOfService,
         Processing Error, Equipment and Environmental.
         ALCATEL NOTE:
         ACCESS	:  NA           	USAGE		:  NA
         PERSIST	:  NO          		INSRVMOD	:  NA
         RANGE	:  1..5          	DEFVALUE	:  NA 
         UNITS	:  NA           	SPARSE		:  NO
         DESCR	:  NA"
    ::= { asamAlarmEntry 2 }

asamAlarmSeverity OBJECT-TYPE
    SYNTAX      AsamAlarmSeverityType
    ACCESS      read-write
    STATUS      mandatory
    DESCRIPTION 
        "This object is defined to assign a severity level
         to an alarm. This object may be indeterminate, warning, minor, major
         and critical.
         ALCATEL NOTE:
         ACCESS	:  NA           	USAGE		:  NA
         PERSIST	:  YES          	INSRVMOD	:  YES
         RANGE	:  1..5          	DEFVALUE	:  NA 
         UNITS	:  NA           	SPARSE		:  NO
         DESCR	:  NA"
    ::= { asamAlarmEntry 3 }

asamAlarmServAffect OBJECT-TYPE
    SYNTAX      AsamAlarmServAffType
    ACCESS      read-write
    STATUS      mandatory
    DESCRIPTION 
        "This object defines whether an alarm is service affecting or not.
         ALCATEL NOTE:
         ACCESS	:  NA           	USAGE		:  NA
         PERSIST	:  YES          	INSRVMOD	:  YES
         RANGE	:  1,2          	DEFVALUE	:  NA 
         UNITS	:  NA           	SPARSE		:  NO
         DESCR	:  NA"
    ::= { asamAlarmEntry 4 }

asamAlarmReportMode OBJECT-TYPE
    SYNTAX      AsamAlarmModeType
    ACCESS      read-write
    STATUS      mandatory
    DESCRIPTION 
        "This object is defined to manage the reporting of the alarm.
         If it is disabled, the alarm is not reported to the SNMP
         Trap Manager. If it is enabled, reporting to the manager is
         possible (provided it has a high enough severity(MJ,MI,CRITICAL)).
         ALCATEL NOTE:
         ACCESS	:  NA           	USAGE		:  NA
         PERSIST	:  YES          	INSRVMOD	:  YES
         RANGE	:  1,2          	DEFVALUE	:  NA 
         UNITS	:  NA           	SPARSE		:  NO
         DESCR	:  NA"
    ::= { asamAlarmEntry 9 }

asamNumberofAlarmChanges OBJECT-TYPE
    SYNTAX      Counter
    ACCESS      read-only
    STATUS      mandatory
    DESCRIPTION 
        "This object gives the number of changes that have occurred at
         the CurrentAlarmtable since startup. It is a wrap around
         counter between 0 and MAX.
         ALCATEL NOTE:
         ACCESS	:  NA           	USAGE		:  NA
         PERSIST	:  NO          		INSRVMOD	:  NA
         RANGE	:  NA         		DEFVALUE	:  0
         UNITS	:  NA           	SPARSE		:  NA
         DESCR	:  NA"
    ::= { asamAlarmMIB 3 }

asamNumberofAlarmEntries OBJECT-TYPE
    SYNTAX      Gauge
    ACCESS      read-only
    STATUS      mandatory
    DESCRIPTION 
        "This object gives the number of entries in the Current Alarm Table.
         ALCATEL NOTE:
         ACCESS	:  NA           	USAGE		:  NA
         PERSIST	:  NO          		INSRVMOD	:  NA
         RANGE	:  NA         		DEFVALUE	:  0
         UNITS	:  NA           	SPARSE		:  NA
         DESCR	:  NA"
    ::= { asamAlarmMIB 4 }

asamCurrentAlarmTable OBJECT-TYPE
    SYNTAX      SEQUENCE OF AsamCurrentAlarmEntry
    ACCESS      not-accessible
    STATUS      mandatory
    DESCRIPTION 
        "This table contains the current active alarms, ordered by
         severity (highest first). Each entry contains information
         on the alarm type, alarm status, two indexes and the last
         time that the entry was changed. Only alarms with a
         reporting mode set to ON are entered in this table.
         ALCATEL NOTE :
           TABLESIZE    :  NA
           DESCR        :  This object is not used by Alcatel"
    ::= { asamAlarmMIB 7 }

asamCurrentAlarmEntry OBJECT-TYPE
    SYNTAX      AsamCurrentAlarmEntry
    ACCESS      not-accessible
    STATUS      mandatory
    DESCRIPTION 
        "Entry for CurrentAlarmTable.
         Row creation : NA
         Row deletion : NA
         Index usage  : NA
            lexicographical order :  NA"
    INDEX       { asamCurrentAlarmIndex }
    ::= { asamCurrentAlarmTable 1 }

AsamCurrentAlarmEntry ::= SEQUENCE {
    asamCurrentAlarmIndex       INTEGER,
    asamCurrentAlarmType        AsamAlarmType,
    asamCurrentAlarmStatus      INTEGER,
    asamCurrentAlarmIndex1      INTEGER,
    asamCurrentAlarmIndex2      INTEGER,
    asamCurrentAlarmTime        INTEGER,
    asamCurrentAlarmAddInfo     DisplayString
}

asamCurrentAlarmIndex OBJECT-TYPE
    SYNTAX      INTEGER (1..2147483647)
    ACCESS      read-only
    STATUS      mandatory
    DESCRIPTION 
        "Index for a Current Alarm Entry.
         ALCATEL NOTE:
         ACCESS	:  NA           USAGE		:  NA
         PERSIST	:  NA          	INSRVMOD	:  NA
         RANGE	:  NA         	DEFVALUE	:  NA
         UNITS	:  NA           SPARSE		:  NA
         DESCR	:  This object is not used by Alcatel"
    ::= { asamCurrentAlarmEntry 1 }

asamCurrentAlarmType OBJECT-TYPE
    SYNTAX      AsamAlarmType
    ACCESS      read-only
    STATUS      mandatory
    DESCRIPTION 
        "This object defines the type of the alarms that are active
         in this entry.
          ALCATEL NOTE:
          ACCESS	:  NA           USAGE		:  NA
         PERSIST	:  NA          	INSRVMOD	:  NA
         RANGE	:  NA         	DEFVALUE	:  NA
         UNITS	:  NA           SPARSE		:  NA
         DESCR	:  This object is not used by Alcatel"
    ::= { asamCurrentAlarmEntry 2 }

asamCurrentAlarmStatus OBJECT-TYPE
    SYNTAX      INTEGER (1..2147483647)
    ACCESS      read-only
    STATUS      mandatory
    DESCRIPTION 
        "This object defines the current status of all alarms within
         one alarm type and one index1-index2 combination at
         that time. The alarms are represented in a bitmap with the
         following bitpositions :
         1 NoDefect
         2 AlarmNumber 1
         4 AlarmNumber 2
         8 AlarmNumber 3
         16 AlarmNumber 4
         .. ..............
         For a definition of the bitmap refer, LANX Alarm manager module
         design document
         ALCATEL NOTE:
          ACCESS	:  NA           USAGE		:  NA
         PERSIST	:  NA          	INSRVMOD	:  NA
         RANGE	:  NA         	DEFVALUE	:  NA
         UNITS	:  NA           SPARSE		:  NA
         DESCR	:  This object is not used by Alcatel"
    ::= { asamCurrentAlarmEntry 3 }

asamCurrentAlarmIndex1 OBJECT-TYPE
    SYNTAX      INTEGER
    ACCESS      read-only
    STATUS      mandatory
    DESCRIPTION 
        "This object is used in conjunction with Index2. Together they
         provide more details about the alarm occurred. For more information
         regarding the index definition refer, Alarm manager module design
         document.
         ALCATEL NOTE:
         ACCESS	:  NA           USAGE		:  NA
         PERSIST	:  NA          	INSRVMOD	:  NA
         RANGE	:  NA         	DEFVALUE	:  NA
         UNITS	:  NA           SPARSE		:  NA
         DESCR	:  This object is not used by Alcatel"
    ::= { asamCurrentAlarmEntry 4 }

asamCurrentAlarmIndex2 OBJECT-TYPE
    SYNTAX      INTEGER
    ACCESS      read-only
    STATUS      mandatory
    DESCRIPTION 
        "This object is used in conjunction with Index1. See
         description of Index1 for further info.
         ALCATEL NOTE:
         ACCESS	:  NA           USAGE		:  NA
         PERSIST	:  NA          	INSRVMOD	:  NA
         RANGE	:  NA         	DEFVALUE	:  NA
         UNITS	:  NA           SPARSE		:  NA
         DESCR	:  This object is not used by Alcatel"
    ::= { asamCurrentAlarmEntry 5 }

asamCurrentAlarmTime OBJECT-TYPE
    SYNTAX      INTEGER (1..2147483647)
    ACCESS      read-only
    STATUS      mandatory
    DESCRIPTION 
        "This object gives the time information in seconds elapsed since the 1st	 January 1970, when the entry was updated/added.
         ALCATEL NOTE:
         ACCESS	:  NA           USAGE		:  NA
         PERSIST	:  NA          	INSRVMOD	:  NA
         RANGE	:  NA         	DEFVALUE	:  NA
         UNITS	:  NA           SPARSE		:  NA
         DESCR	:  This object is not used by Alcatel"
    ::= { asamCurrentAlarmEntry 7 }

asamCurrentAlarmAddInfo OBJECT-TYPE
    SYNTAX      DisplayString
    ACCESS      read-only
    STATUS      mandatory
    DESCRIPTION 
        "This object is used to keep some additional information about
         the considered table entry.
         ALCATEL NOTE:
         ACCESS	:  NA           USAGE		:  NA
         PERSIST	:  NA          	INSRVMOD	:  NA
         RANGE	:  NA         	DEFVALUE	:  NA
         UNITS	:  NA           SPARSE		:  NA
         DESCR	:  This object is not used by Alcatel"
    ::= { asamCurrentAlarmEntry 8 }

asamAlarmSnapshotTableStatus OBJECT-TYPE
    SYNTAX      INTEGER { notInUse(1), inUse(2) }
    ACCESS      read-write
    STATUS      mandatory
    DESCRIPTION 
        "Before reading the snapshot table, one must try to set this
         object to inUse first. When it is already in this state,
         the set will fail; when in the notInUse state, the set
         will succeed. The inUse state is only kept for a limited
         time, which is defined by the asamAlarmSnapshotTimeout
         object. When the timeout expires, this object is
         automatically reset to the notInUse state and the
         snapshot table is emptied.
         Scenario for taking a snapshot :
         ================================
         * Try to set the asamAlarmSnapshotTableStatus to
         inUse. Proceed only if successfull;
         * optionally set the owner string to enable other
         managers to identify the current snapshot table
         user;
         * set the snapshot table severity level;
         * read the number of entries in the snapshot table;
         * optionally read the severity status bitmap to
         identify the active severity levels in the snapshot
         table;
         * read out the snapshot table using GET or GETNEXT
         SNMP commands;
         * free the snapshot table for other managers by
         setting the status to notInUse.
         ALCATEL NOTE:
         ACCESS	:  NA          	USAGE		:  NA
         PERSIST	:  NO         	INSRVMOD	:  YES
         RANGE	:  NA         	DEFVALUE	:  NA
         UNITS	:  NA          	SPARSE		:  NA
         DESCR	:  NA"
    DEFVAL      { notInUse }
    ::= { asamAlarmMIB 16 }

asamAlarmSnapshotOwner OBJECT-TYPE
    SYNTAX      OCTET STRING
    ACCESS      read-write
    STATUS      mandatory
    DESCRIPTION 
        "This string can contain an identification of the owner who
         took the snapshot. When a manager wants to use the
         snapshot table, he can set this string with a meaningful
         value. When the snapshot table is not in use, the owner
         string cannot be set
         ALCATEL NOTE:
         ACCESS	:  NA           USAGE		:  NA
         PERSIST	:  NO          INSRVMOD	:  NO
         RANGE	:  NA         	DEFVALUE	:  NA
         UNITS	:  NA           SPARSE		:  NA
         DESCR	:  If the snapshot table is not in use, the owner string 
         		    cannot be set.  So INSRVMOD is NO"
    ::= { asamAlarmMIB 17 }

asamAlarmSnapshotTimeout OBJECT-TYPE
    SYNTAX      TimeTicks
    ACCESS      read-only
    STATUS      mandatory
    DESCRIPTION 
        "This object gives the timeout in hunderdth of a second
         on the snapshot table. The timer is started from the 
         moment the snapshot table status is set to inUse. It 
         will be set to a default value cannot be changed by the manager.
         ALCATEL NOTE:
         ACCESS	:  NA           		USAGE		:  NA
         PERSIST	:  NO          			INSRVMOD	:  NA
         RANGE	: 12000         		DEFVALUE	:  NA
         UNITS	:  hundredth of a second        SPARSE		:  NA
         DESCR	:  NA"
    DEFVAL      { 12000 }
    ::= { asamAlarmMIB 18 }

asamAlarmSnapshotSeverityLevel OBJECT-TYPE
    SYNTAX      AsamAlarmSeverityType
    ACCESS      read-write
    STATUS      mandatory
    DESCRIPTION 
        "This object indicates the lowest severity level of alarms
         that should be visible in the snapshot table. When the
         snapshot table status is in the notInUse state, the
         severity cannot be read or set. When the snapshot table
         status is in the InUse state, the severity level can
         only be set once to prevent confusion as to the lowest
         severity in the snapshot table. After successfully
         setting the severity level, the snapshot table and its
         related objects will contain valid data as long as the
         snapshot table is in the inUse state.
         ALCATEL NOTE:
         ACCESS	:  NA           		USAGE		:  NA
         PERSIST	:  NO          		INSRVMOD	:  NO
         RANGE	:  1..5         		DEFVALUE	:  NA
         UNITS	:  NA		         	SPARSE		:  NA
         DESCR	:  When the snapshot table status is in the notInUse state, the  severity 
         		  cannot be read or set. When the snapshot table status is in the InUse state, 
         		  the severity level can only be set once to prevent confusion as to the lowest
         		  severity in the snapshot table so INSERVMOD is NO"
    ::= { asamAlarmMIB 19 }

asamNumberOfAlarmSnapshotEntries OBJECT-TYPE
    SYNTAX      Gauge
    ACCESS      read-only
    STATUS      mandatory
    DESCRIPTION 
        "When the snapshot table status is in the inUse state, this
         object reflects the number of entries in the snapshot
         table. If the snapshot table status is set to notInUse,
         this object can not be read.
         ALCATEL NOTE:
         ACCESS	:  NA           		USAGE		:  NA
         PERSIST	:  NO          			INSRVMOD	:  NA
         RANGE	:  1..2048	         	DEFVALUE	:  0
         UNITS	:  NA		         	SPARSE		:  NA
         DESCR	:  NA"
    ::= { asamAlarmMIB 20 }

asamAlarmSnapshotTable OBJECT-TYPE
    SYNTAX      SEQUENCE OF AsamAlarmSnapshotEntry
    ACCESS      not-accessible
    STATUS      mandatory
    DESCRIPTION 
        "This table is empty when the snapshot table status is set to
         notInUse. When a snapshot is taken (see the description
         of the snapshot table status object for a complete
         scenario), this table will contain all active alarms, at
         the time the snapshot was taken, ordered by severity.
         The lowest viewable severity is set with the snapshot
         severity object.
         ALCATEL NOTE :
           TABLESIZE    : 2048                    
           DESCR        : NA"
    ::= { asamAlarmMIB 22 }

asamAlarmSnapshotEntry OBJECT-TYPE
    SYNTAX      AsamAlarmSnapshotEntry
    ACCESS      not-accessible
    STATUS      mandatory
    DESCRIPTION 
        "Entry for asamAlarmSnapshotTable.
         Row creation : A Asam-Alarm-Snapshot entry shall be created when 
         	         the alarm is generated.
         Row deletion : A ASAM-ALARM-SNAPSHOT entry shall be deleted when 
         	        the alarm is cleared.
         Index usage : the indexe is asamAlarmSnapshotIndex.
            Note that entries will be presented to the SNMP manager in full
            lexicographical order :  sorted on asamAlarmSnapshotIndex"
    INDEX       { asamAlarmSnapshotIndex }
    ::= { asamAlarmSnapshotTable 1 }

AsamAlarmSnapshotEntry ::= SEQUENCE {
    asamAlarmSnapshotIndex      INTEGER,
    asamAlarmSnapshotType       AsamAlarmType,
    asamAlarmSnapshotStatus     INTEGER,
    asamAlarmSnapshotIndex1     INTEGER,
    asamAlarmSnapshotIndex2     INTEGER,
    asamAlarmSnapshotTime       INTEGER,
    asamAlarmSnapshotAddInfo    DisplayString
}

asamAlarmSnapshotIndex OBJECT-TYPE
    SYNTAX      INTEGER (1..2147483647)
    ACCESS      read-only
    STATUS      mandatory
    DESCRIPTION 
        "Index for an Alarm Snapshot Entry.
         ALCATEL NOTE:
         ACCESS	:  NA           		USAGE		:  NA
         PERSIST	:  NO          		INSRVMOD	:  NA
         RANGE	:  1..2048	         		DEFVALUE	:  NA
         UNITS		:  NA		         	SPARSE		:  NO
         DESCR	:  NA"
    ::= { asamAlarmSnapshotEntry 1 }

asamAlarmSnapshotType OBJECT-TYPE
    SYNTAX      AsamAlarmType
    ACCESS      read-only
    STATUS      mandatory
    DESCRIPTION 
        "This object defines the type of the alarms in this entry.
         ALCATEL NOTE:
         ACCESS	:  NA           		USAGE		:  NA
         PERSIST	:  NO          		INSRVMOD	:  NA
         RANGE	:  51,52,69,70,75       		DEFVALUE	:  NA
         UNITS	:  NA		         	SPARSE		:  NO
         DESCR	:  NA"
    ::= { asamAlarmSnapshotEntry 2 }

asamAlarmSnapshotStatus OBJECT-TYPE
    SYNTAX      INTEGER (1..2147483647)
    ACCESS      read-only
    STATUS      mandatory
    DESCRIPTION 
        "This object defines the status of alarms in an alarm type at
         the time the snapshot was taken. The alarms are
         represented in a bitmap with the following
         bitpositions :
         1 NoDefect
         2 AlarmNumber 1
         4 AlarmNumber 2
         8 AlarmNumber 3
         16 AlarmNumber 4
         .. ..............
         For more information
         regarding the index definition refer,
         LANX Alarm manager module design document
         ALCATEL NOTE:
         ACCESS	:  NA           		USAGE		:  NA
         PERSIST	:  NO          		        INSRVMOD	:  NA
         RANGE	:  NA	         		DEFVALUE	:  NA
         UNITS	:  NA		         	SPARSE		:  NO
         DESCR	:  NA"
    ::= { asamAlarmSnapshotEntry 3 }

asamAlarmSnapshotIndex1 OBJECT-TYPE
    SYNTAX      INTEGER
    ACCESS      read-only
    STATUS      mandatory
    DESCRIPTION 
        "This object is used in conjunction with Index2. Together they
         identify where the alarm occurred. For more information
         regarding the index definition refer to the
         LANX Alarm manager module design document.
         ALCATEL NOTE:
         ACCESS	:  NA           		USAGE		:  NA
         PERSIST	:  NO          		INSRVMOD	:  NA
         RANGE	:  1..2048	         		DEFVALUE	:  NA
         UNITS		:  NA		         	SPARSE		:  NO
         DESCR	:  NA"
    ::= { asamAlarmSnapshotEntry 4 }

asamAlarmSnapshotIndex2 OBJECT-TYPE
    SYNTAX      INTEGER
    ACCESS      read-only
    STATUS      mandatory
    DESCRIPTION 
        "This object is used in conjunction with Index1. See
         description of Index1 for further info.
         ALCATEL NOTE:
         ACCESS	:  NA           		USAGE		:  NA
         PERSIST	:  NO          		INSRVMOD	:  NA
         RANGE	:  1..2048	         		DEFVALUE	:  NA
         UNITS		:  NA		         	SPARSE		:  NO
         DESCR	:  NA"
    ::= { asamAlarmSnapshotEntry 5 }

asamAlarmSnapshotTime OBJECT-TYPE
    SYNTAX      INTEGER (0..2147483647)
    ACCESS      read-only
    STATUS      mandatory
    DESCRIPTION 
        "This object gives the time information in seconds elapsed since the 1st January 1970, when the entry was updated/added.
         ALCATEL NOTE:
         ACCESS	:  NA           		USAGE		:  NA
         PERSIST	:  NO          		INSRVMOD	:  NA
         RANGE	:  0..2208988800         	DEFVALUE	:  NA
         UNITS		:  seconds		         	SPARSE		:  NO
         DESCR	:  NA"
    ::= { asamAlarmSnapshotEntry 7 }

asamAlarmSnapshotAddInfo OBJECT-TYPE
    SYNTAX      DisplayString
    ACCESS      read-only
    STATUS      mandatory
    DESCRIPTION 
        "This object is used to keep some additional information about
         the considered table entry.
         ALCATEL NOTE:
         ACCESS	:  NA           		USAGE		:  NA
         PERSIST	:  NO          		INSRVMOD	:  NA
         RANGE	:  NA	         		DEFVALUE	:  NA
         UNITS		:  NA		         	SPARSE		:  NO
         DESCR	:  NA"
    ::= { asamAlarmSnapshotEntry 8 }

asamNumberOfTotalChanges OBJECT-TYPE
    SYNTAX      Counter
    ACCESS      read-only
    STATUS      mandatory
    DESCRIPTION 
        "This counter represents the total number of changes of all
         alarms since startup. It is equivalent to asamNumberofAlarmChanges
         level presently.
         ALCATEL NOTE:
         ACCESS	:  NA           		USAGE		:  NA
         PERSIST	:  NO          		INSRVMOD	:  NA
         RANGE	:  NA	         		DEFVALUE	:  0
         UNITS		:  NA		         	SPARSE		:  NA
         DESCR	:  NA"
    ::= { asamAlarmMIB 23 }

asamNumberOfIndeterminateChanges OBJECT-TYPE
    SYNTAX      Counter
    ACCESS      read-only
    STATUS      mandatory
    DESCRIPTION 
        "This counter represents the total number of changes of all alarms
         with severity level indeterminate since startup.
         ALCATEL NOTE:
         ACCESS	:  NA           		USAGE		:  NA
         PERSIST	:  NO          		INSRVMOD	:  NA
         RANGE	:  NA	         		DEFVALUE	:  0
         UNITS		:  NA		         	SPARSE		:  NA
         DESCR	:  NA"
    ::= { asamAlarmMIB 24 }

asamNumberOfWarningChanges OBJECT-TYPE
    SYNTAX      Counter
    ACCESS      read-only
    STATUS      mandatory
    DESCRIPTION 
        "This counter represents the total number of changes of all alarms
         with severity level warning since startup.
         ALCATEL NOTE:
         ACCESS	:  NA           		USAGE		:  NA
         PERSIST	:  NO          		INSRVMOD	:  NA
         RANGE	:  NA	         		DEFVALUE	:  0
         UNITS		:  NA		         	SPARSE		:  NA
         DESCR	:  NA"
    ::= { asamAlarmMIB 25 }

asamNumberOfMinorChanges OBJECT-TYPE
    SYNTAX      Counter
    ACCESS      read-only
    STATUS      mandatory
    DESCRIPTION 
        "This counter represents the total number of changes of all alarms
         with severity level minor since startup.
         ALCATEL NOTE:
         ACCESS	:  NA           		USAGE		:  NA
         PERSIST	:  NO          		INSRVMOD	:  NA
         RANGE	:  NA	         		DEFVALUE	:  0
         UNITS		:  NA		         	SPARSE		:  NA
         DESCR	:  NA"
    ::= { asamAlarmMIB 26 }

asamNumberOfMajorChanges OBJECT-TYPE
    SYNTAX      Counter
    ACCESS      read-only
    STATUS      mandatory
    DESCRIPTION 
        "This counter represents the total number of changes of all alarms
         with severity level major since startup.
         ALCATEL NOTE:
         ACCESS	:  NA           		USAGE		:  NA
         PERSIST	:  NO          		INSRVMOD	:  NA
         RANGE	:  NA	         		DEFVALUE	:  0
         UNITS		:  NA		         	SPARSE		:  NA
         DESCR	:  NA"
    ::= { asamAlarmMIB 27 }

asamNumberOfCriticalChanges OBJECT-TYPE
    SYNTAX      Counter
    ACCESS      read-only
    STATUS      mandatory
    DESCRIPTION 
        "This counter represents the total number of changes of all alarms
         with severity level critical since startup.
         ALCATEL NOTE:
         ACCESS	:  NA           		USAGE		:  NA
         PERSIST	:  NO          		INSRVMOD	:  NA
         RANGE	:  NA	         		DEFVALUE	:  0
         UNITS		:  NA		         	SPARSE		:  NA
         DESCR	:  NA"
    ::= { asamAlarmMIB 28 }

changeOccured TRAP-TYPE
    ENTERPRISE  asamAlarmMIB
    VARIABLES   { asamNumberOfTotalChanges, 
                  asamNumberOfIndeterminateChanges, 
                  asamNumberOfMinorChanges, asamNumberOfWarningChanges, 
                  asamNumberOfMajorChanges, asamNumberOfCriticalChanges }
--     STATUS      mandatory
    DESCRIPTION 
        "This trap is sent when the total number of alarms
         in LANX has changed."
    ::= 1

END -- end of module AsamAlarm-MIB.
