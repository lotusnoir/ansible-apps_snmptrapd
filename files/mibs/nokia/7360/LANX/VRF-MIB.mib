--
-- This SMIv1 module has been generated by smidump 0.4.8. Do not edit.
--

VRF-MIB DEFINITIONS ::= BEGIN

IMPORTS
    OBJECT-TYPE
        FROM RFC-1212
    Gauge, IpAddress, enterprises
        FROM RFC1155-SMI
    DisplayString, RowStatus
        FROM SNMPv2-TC;

lanxVrfMIB OBJECT IDENTIFIER
    ::= { enterprises futuresoftware(2076) 91 }

-- lanxVrfMIB MODULE-IDENTITY
--     LAST-UPDATED "200401031200Z"
--     ORGANIZATION 
--         "FUTURE SOFTWARE PVT. LIMITED"
--     CONTACT-INFO 
--         " FUTURE SOFTWARE PVT. LIMITED
--          481 Mount Road
--          Madras - 600 035
--          Phone : 44-2433 0550 
--          support@futsoft.com"
--     DESCRIPTION 
--         "The LANX VRF MIB "
--     REVISION    "200401031200Z"
--     DESCRIPTION 
--         "The initial revision of this MIB module was published as
--          RFC 1450."
--     ::= { enterprises futuresoftware(2076) 91 }


VrfId ::=
    Gauge

-- VrfId ::= TEXTUAL-CONVENTION
--     STATUS      mandatory
--     DESCRIPTION 
--         "Virtual Routing Forwarding (VRF) Identifier.
--          VRF ID 1 is reserved for default VRF instance and 
--          it can not be used to create a VRF instance"
--     SYNTAX      Gauge

VlanId ::=
    INTEGER (1..4094)

-- VlanId ::= TEXTUAL-CONVENTION
--     STATUS      mandatory
--     DESCRIPTION 
--         "A 12-bit VLAN ID used in the VLAN Tag header."
--     SYNTAX      INTEGER (1..4094)

EnabledStatus ::=
    INTEGER { enabled(1), disabled(2) }

-- EnabledStatus ::= TEXTUAL-CONVENTION
--     STATUS      mandatory
--     DESCRIPTION 
--         "A simple status value for the object."
--     SYNTAX      INTEGER
--                   { enabled(1), disabled(2) }

lanxVrfConfigTable OBJECT-TYPE
    SYNTAX      SEQUENCE OF LanxVrfConfigEntry
    ACCESS      not-accessible
    STATUS      mandatory
    DESCRIPTION 
        "A table containing configuration information of the 
         Virtual Routing Forwarding(VRF) instances
         ALCATEL NOTE :
         	TABLE SIZE :  128
         	DESCR :       NA"
    ::= { lanxVrfMIB 1 }

lanxVrfConfigEntry OBJECT-TYPE
    SYNTAX      LanxVrfConfigEntry
    ACCESS      not-accessible
    STATUS      mandatory
    DESCRIPTION 
        "Each entry contains VRF instance configuration information
         Row creation : An entry shall be created in one step by a
             set-request with all necessary parameter values and
             lanxVrfRowStatus set to createAndGo(4).
         Row deletion : An entry shall be deleted by setting
             the lanxVrfRowStatus of the specific entry to destroy(6).
         Index usage : the index is the Vrf Id.
           Note that entries will be presented to the SNMP manager in full
           lexicographical order :  sorted on VRF ID."
    INDEX       { lanxVrfId }
    ::= { lanxVrfConfigTable 1 }

LanxVrfConfigEntry ::= SEQUENCE {
    lanxVrfId                               VrfId,
    lanxVrfName                             DisplayString,
    lanxVrfRowStatus                        RowStatus,
    lanxVrfMode                             INTEGER,
    lanxVrfUserToUserCommunicationStatus    EnabledStatus,
    lanxVrfTtlZeroPacket                    INTEGER,
    lanxVrfMaxRoutes                        INTEGER,
    lanxVrfRouteCount                       INTEGER
}

lanxVrfId OBJECT-TYPE
    SYNTAX      VrfId
    ACCESS      not-accessible
    STATUS      mandatory
    DESCRIPTION 
        "A unique value assigned for each VRF instance
         ALCATEL NOTE:
            ACCESS:    NA            USAGE:     NA  
            PERSIST:   YES           INSRVMOD:  NA  
            RANGE:     0..127        DEFVALUE:  NA  
            UNITS:     NA            SPARSE:    NO  
            DESCR:     NA"
    ::= { lanxVrfConfigEntry 1 }

lanxVrfName OBJECT-TYPE
    SYNTAX      DisplayString
    ACCESS      read-write
    STATUS      mandatory
    DESCRIPTION 
        "The Name of the VRF 
         ALCATEL NOTE:
            ACCESS:    NA          USAGE:      OPT       
            PERSIST:   YES         INSRVMOD:   YES 
            RANGE:     0..32       DEFVALUE:   '\0' 
            UNITS:     NA          SPARSE:     NO 
            DESCR:     NA"
    ::= { lanxVrfConfigEntry 2 }

lanxVrfRowStatus OBJECT-TYPE
    SYNTAX      RowStatus
    ACCESS      read-write
    STATUS      mandatory
    DESCRIPTION 
        "The row status column supports following values:
         
         - `active', which indicates that the entry  is available for use 
         
         - `createAndGo', which is used to create a new instance and to 
            have its status automatically set to active
         
         - 'CreateAndWait', which is used to create an new instance and wait for the status to 
              be set to active by the user 
         
         - `destroy', which is used to delete a VRF instance
         ALCATEL NOTE:
         ACCESS:    NA          USAGE:      MAND 
         PERSIST:   YES         INSRVMOD:   YES 
         RANGE:     1,4,5,6     DEFVALUE:   NA 
         UNITS:     NA          SPARSE:     NO 
         DESCR:     NA"
    ::= { lanxVrfConfigEntry 3 }

lanxVrfMode OBJECT-TYPE
    SYNTAX      INTEGER { slowpath(1), fastpath(2) }
    ACCESS      read-write
    STATUS      mandatory
    DESCRIPTION 
        " The Mode in which the VRF is functioning. The status of this
         object can not be changed when the Row Staus is Active
         ALCATEL NOTE:
         ACCESS:    NA          USAGE:     OPT 
         PERSIST:   YES         INSRVMOD:  NO  
         RANGE:     NA          DEFVALUE:  NA  
         UNITS:     NA          SPARSE:    NO  
         DESCR:     NA"
    DEFVAL      { slowpath }
    ::= { lanxVrfConfigEntry 4 }

lanxVrfUserToUserCommunicationStatus OBJECT-TYPE
    SYNTAX      EnabledStatus
    ACCESS      read-write
    STATUS      mandatory
    DESCRIPTION 
        "This object is only used to enable/disable the user to user 
         communiation across ASAM ports in a Fast Path VRF. This object 
         is not a Row Status behaviour. 
         enabled - The users connected through the ASAM ports of this
                  Fast path VRF can communicate through L3 Switching
          disabled - The Users of a Fast Path VRF can not communicate
                    among themself
         	ALCATEL NOTE:
              ACCESS:   NA         USAGE:       OPT 
              PERSIST:  YES        INSRVMOD:    YES
              RANGE:    1,2        DEFVALUE:    NA 
              UNITS:    NA         SPARSE:      NO
              DESCR:    This object can be set to Enabled(1) only when lanxVrfMode is
         		      fastpath(2)"
    DEFVAL      { disabled }
    ::= { lanxVrfConfigEntry 5 }

lanxVrfTtlZeroPacket OBJECT-TYPE
    SYNTAX      INTEGER { enabled(1), disabled(2) }
    ACCESS      read-write
    STATUS      mandatory
    DESCRIPTION 
        " This object is used to enable/disable the IP forwarding of
         L3 unicast packets having TTL value is 0, i.e LANX shall forward the packets   
         having TTL value is 0, if the forwarding is enabled in the VRF.
         enabled - L3 unicast packet of TTL value zero will be forwarded.
         disabled - L3 unicast packet of TTL value zero will be dropped.
         ALCATEL NOTE:
         ACCESS:   NA         USAGE:       OPT 
         PERSIST:  YES        INSRVMOD:    YES
         RANGE:    NA         DEFVALUE:    NA 
         UNITS:    NA         SPARSE:      NO
         DESCR:    NA "
    DEFVAL      { disabled }
    ::= { lanxVrfConfigEntry 6 }

lanxVrfMaxRoutes OBJECT-TYPE
    SYNTAX      INTEGER (-1..41984)
    ACCESS      read-write
    STATUS      mandatory
    DESCRIPTION 
        "The  maximum   number   of   Routes that 
         can be associated with a particular VRF instance, 
         If the value is -1,  then there is no limit..
         
         An alarm will be raised when the current number of 
         routes on a VRF reaches T-Routing-Up % of the configured limit,
         which is turned off once the number of routes goes 
         down to T-Routing-Down % of the configured limit.
                     
         If a new route is received once the max limit is reached, then 
         the corresponding OSPF/RIP instance is shut down and a timer is started,
         Upon the expiry of timer the OSPF/RIP instance is restarted.
         
         When the value of this object is configured/reduced, 
         if the current number of routes on that VRF instance
         is already above the configured value then alarm is generated, 
         current routes are kept and no new routes are accepted until 
         the current number of routes goes down to 100 % of the configured limit.
         
         ALCATEL NOTE:
         ACCESS:      NA           USAGE:       NA
         PERSIST:     YES          INSRVMOD:    YES
         RANGE:       -1..fsVrfMaxHWRoutes      DEFVALUE:     -1
         UNITS:       NA           SPARSE:      NA
         DESCR:       RANGE:The configurable max value for this object is fsVrfMaxHWRoutes which is 12288.This is the
         max number of routes supported in H/W.Any value greater than 12288 is not accepted by H/W."
    DEFVAL      { -1 }
    ::= { lanxVrfConfigEntry 7 }

lanxVrfRouteCount OBJECT-TYPE
    SYNTAX      INTEGER
    ACCESS      read-only
    STATUS      mandatory
    DESCRIPTION 
        "This gives the number of routes that are 
         actually present on a VRF instance,
                   
         ALCATEL NOTE:
         ACCESS:      NA           USAGE:       NA
         PERSIST:     YES          INSRVMOD:    YES
         RANGE:       NA            DEFVALUE:   NA
         UNITS:       NA           SPARSE:      NA
         DESCR:       NA"
    ::= { lanxVrfConfigEntry 8 }

lanxVrfRouteTable OBJECT-TYPE
    SYNTAX      SEQUENCE OF LanxVrfRouteEntry
    ACCESS      not-accessible
    STATUS      mandatory
    DESCRIPTION 
        "A table containg the IP routes for the VRF instances
         ALCATEL NOTE:
         	TABLE SIZE:   8928
         	DESCR:        NA"
    ::= { lanxVrfMIB 2 }

lanxVrfRouteEntry OBJECT-TYPE
    SYNTAX      LanxVrfRouteEntry
    ACCESS      not-accessible
    STATUS      mandatory
    DESCRIPTION 
        "A particular route to  a  particular  destina-
         tion for a VRF instance.
         Row creation : An entry shall be created in one step by a 
            set-request with all necessary parameter values and  
            lanxVrfRouteStatus set to createAndGo(4) and can be created dynamically by learning the route protocols .
         Row deletion : An entry shall be deleted by setting
            the lanxVrfRouteStatus of the specific entry to destroy(6).
         Index usage : the index is the Vrf Id,Route Destination,Route mask,Route Tos,Route Next Hop.
          Note that entries will be presented to the SNMP manager in full
          lexicographical order :  sorted on VRF ID,Route Destination,Route mask,Route Tos,Route Next Hop."
    INDEX       { lanxVrfId, lanxVrfRouteDest, lanxVrfRouteMask, 
                  lanxVrfRouteTos, lanxVrfRouteNextHop }
    ::= { lanxVrfRouteTable 1 }

LanxVrfRouteEntry ::= SEQUENCE {
    lanxVrfRouteDest        IpAddress,
    lanxVrfRouteMask        IpAddress,
    lanxVrfRouteTos         INTEGER,
    lanxVrfRouteNextHop     IpAddress,
    lanxVrfRouteIfIndex     INTEGER,
    lanxVrfRouteType        INTEGER,
    lanxVrfRouteProto       INTEGER,
    lanxVrfRouteAge         INTEGER,
    lanxVrfRouteInfo        OBJECT IDENTIFIER,
    lanxVrfRouteNextHopAS   INTEGER,
    lanxVrfRouteMetric1     INTEGER,
    lanxVrfRouteMetric2     INTEGER,
    lanxVrfRouteMetric3     INTEGER,
    lanxVrfRouteMetric4     INTEGER,
    lanxVrfRouteMetric5     INTEGER,
    lanxVrfRouteStatus      RowStatus
}

lanxVrfRouteDest OBJECT-TYPE
    SYNTAX      IpAddress
    ACCESS      not-accessible
    STATUS      mandatory
    DESCRIPTION 
        "The destination IP address of this route
         ALCATEL NOTE:
            ACCESS:    NA          USAGE:     NA      
            PERSIST:   YES         INSRVMOD:  NA  
            RANGE:     NA          DEFVALUE:  NA
            UNITS:     NA          SPARSE:    NO  
            DESCR:     NA"
    ::= { lanxVrfRouteEntry 1 }

lanxVrfRouteMask OBJECT-TYPE
    SYNTAX      IpAddress
    ACCESS      not-accessible
    STATUS      mandatory
    DESCRIPTION 
        "The subnet mask of this route
         ALCATEL NOTE:
            ACCESS:    NA          USAGE:     NA     
            PERSIST:   YES         INSRVMOD:  NA  
            RANGE:     NA          DEFVALUE:  NA  
            UNITS:     NA          SPARSE:    NO  
            DESCR:     NA"
    ::= { lanxVrfRouteEntry 2 }

lanxVrfRouteTos OBJECT-TYPE
    SYNTAX      INTEGER (0..16)
    ACCESS      not-accessible
    STATUS      mandatory
    DESCRIPTION 
        "The ToS bits from the IP header for this route
         ALCATEL NOTE:
            ACCESS:    NA          USAGE:     NA  
            PERSIST:   YES         INSRVMOD:  NA  
            RANGE:     NA          DEFVALUE:  NA
            UNITS:     NA          SPARSE:    NO  
            DESCR:     NA"
    ::= { lanxVrfRouteEntry 3 }

lanxVrfRouteNextHop OBJECT-TYPE
    SYNTAX      IpAddress
    ACCESS      not-accessible
    STATUS      mandatory
    DESCRIPTION 
        "The next hop ip address of this  route. 
         For remote routes, this represents the ip address of the next router.
         Otherwise 0.0.0.0.
         	ALCATEL NOTE:
             ACCESS:   NA          USAGE:      NA     
             PERSIST:  YES         INSRVMOD:   NA 
             RANGE:    NA          DEFVALUE:   NA 
             UNITS:    NA          SPARSE:     NO 
             DESCR:    NA "
    ::= { lanxVrfRouteEntry 4 }

lanxVrfRouteIfIndex OBJECT-TYPE
    SYNTAX      INTEGER
    ACCESS      read-write
    STATUS      mandatory
    DESCRIPTION 
        "The ifIndex value which identifies  the  local
         interface  through  which  the next hop of this
         route should be reached.
         	ALCATEL NOTE:
              ACCESS:    NA          USAGE:      MAND  
              PERSIST:   YES         INSRVMOD:   YES
              RANGE:     DEP      DEFVALUE:   4294967295 
              UNITS:     NA          SPARSE:     NO 
              DESCR:     DEP(RANGE): If this object is not set, it will be 4294967295. 
         					Range for setting is 1 to the (total number of IP interfaces in the 
         					system  + 
         					maximum value of number of physical interfaces available in the system). 
         					The maximum number of physical interfaces is obtained from the 
         					object issSystemNumberOfPorts in fsiss.mib. 
         					The total number of IP interfaces in the system is obtained from the 
         					object fsVrfMaxIpInterfaces in fsvrf.mib
         					The IP interfaces will start from 65536 to the total number of 
         					IP interfaces in the system. The indices 81920 & 81921 are reserved 
         					for vlan 4094 & 4093 respectively."
    DEFVAL      { 65535 }
    ::= { lanxVrfRouteEntry 5 }

lanxVrfRouteType OBJECT-TYPE
    SYNTAX      INTEGER { other(1), reject(2), local(3), remote(4) }
    ACCESS      read-write
    STATUS      mandatory
    DESCRIPTION 
        "The type of route
         ALCATEL NOTE:
            ACCESS:    NA          USAGE:      MAND      
            PERSIST:   YES         INSRVMOD:   YES  
            RANGE:     NA          DEFVALUE:   NA
            UNITS:     NA          SPARSE:     NO  
            DESCR:     NA"
    ::= { lanxVrfRouteEntry 6 }

lanxVrfRouteProto OBJECT-TYPE
    SYNTAX      INTEGER { other(1), local(2), netmgmt(3), rip(8), 
                    ospf(13) }
    ACCESS      read-only
    STATUS      mandatory
    DESCRIPTION 
        "The routing mechanism that was responsible for adding this route
         ALCATEL NOTE:
            ACCESS:    NA          USAGE:      NA         
            PERSIST:   NO          INSRVMOD:   NA  
            RANGE:     NA          DEFVALUE:   3 
            UNITS:     NA          SPARSE:     NO  
            DESCR:     NA "
    ::= { lanxVrfRouteEntry 7 }

lanxVrfRouteAge OBJECT-TYPE
    SYNTAX      INTEGER
    ACCESS      read-only
    STATUS      mandatory
    DESCRIPTION 
        "The number of seconds  since  this  route  was
         last  updated
         	ALCATEL NOTE:
              ACCESS:    NA          USAGE:      NA     
              PERSIST:   NO          INSRVMOD:   NA 
              RANGE:     NA          DEFVALUE:   NA      
              UNITS:     SECONDS     SPARSE:     NO 
              DESCR:     NA"
    DEFVAL      { 0 }
    ::= { lanxVrfRouteEntry 8 }

lanxVrfRouteInfo OBJECT-TYPE
    SYNTAX      OBJECT IDENTIFIER
    ACCESS      read-write
    STATUS      mandatory
    DESCRIPTION 
        "A reference to MIB definitions specific to the particular  
         routing protocol which is responsible for this route. 
         This object is not supported and always returns nullOID (0.0).
         	ALCATEL NOTE:
             ACCESS:    NA        USAGE:      NA
             PERSIST:   NA        INSRVMOD:   NA 
             RANGE:     NA        DEFVALUE:   NA
             UNITS:     NA        SPARSE:     NA 
             DESCR:     THIS OBJECT IS NOT USED BY ALCATEL"
    ::= { lanxVrfRouteEntry 9 }

lanxVrfRouteNextHopAS OBJECT-TYPE
    SYNTAX      INTEGER
    ACCESS      read-write
    STATUS      mandatory
    DESCRIPTION 
        "The Autonomous System number of the next hop for this route. 
         This object is not supported and always returns 0.
         	ALCATEL NOTE:
             ACCESS:    NA        USAGE:      NA
             PERSIST:   NA        INSRVMOD:   NA 
             RANGE:     NA        DEFVALUE:   NA
             UNITS:     NA        SPARSE:     NA 
             DESCR:     THIS OBJECT IS NOT USED BY ALCATEL"
    DEFVAL      { 0 }
    ::= { lanxVrfRouteEntry 10 }

lanxVrfRouteMetric1 OBJECT-TYPE
    SYNTAX      INTEGER
    ACCESS      read-write
    STATUS      mandatory
    DESCRIPTION 
        "The primary routing  metric  for  this  route.
         ALCATEL NOTE:
            ACCESS:    NA        USAGE:      NA
            PERSIST:   YES       INSRVMOD:   YES 
            RANGE:     0..254    DEFVALUE:   1 
            UNITS:     NA        SPARSE:     NO 
            DESCR:     NA"
    DEFVAL      { 1 }
    ::= { lanxVrfRouteEntry 11 }

lanxVrfRouteMetric2 OBJECT-TYPE
    SYNTAX      INTEGER
    ACCESS      read-write
    STATUS      mandatory
    DESCRIPTION 
        "An alternate routing metric  for  this  route.
         ALCATEL NOTE:
            ACCESS:   RO         USAGE:     NA 
            PERSIST:  NO         INSRVMOD:  NA
            RANGE:    NA         DEFVALUE:  NA
            UNITS:    NA         SPARSE:    NO  
            DESCR:    NA "
    DEFVAL      { -1 }
    ::= { lanxVrfRouteEntry 12 }

lanxVrfRouteMetric3 OBJECT-TYPE
    SYNTAX      INTEGER
    ACCESS      read-write
    STATUS      mandatory
    DESCRIPTION 
        "An alternate routing metric  for  this  route.
         ALCATEL NOTE:
            ACCESS:    RO          USAGE:      NA
            PERSIST:   NO          INSRVMOD:   NA
            RANGE:     NA          DEFVALUE:   NA
            UNITS:     NA          SPARSE:     NO 
            DESCR:     NA"
    DEFVAL      { -1 }
    ::= { lanxVrfRouteEntry 13 }

lanxVrfRouteMetric4 OBJECT-TYPE
    SYNTAX      INTEGER
    ACCESS      read-write
    STATUS      mandatory
    DESCRIPTION 
        "An alternate routing metric  for  this  route.
         ALCATEL NOTE:
            ACCESS:   RO           USAGE:      NA
            PERSIST:  NO           INSRVMOD:   NA
            RANGE:    NA           DEFVALUE:   NA
            UNITS:    NA           SPARSE:     NO 
            DESCR:    NA"
    DEFVAL      { -1 }
    ::= { lanxVrfRouteEntry 14 }

lanxVrfRouteMetric5 OBJECT-TYPE
    SYNTAX      INTEGER
    ACCESS      read-write
    STATUS      mandatory
    DESCRIPTION 
        "An alternate routing metric  for  this  route.
         ALCATEL NOTE:
            ACCESS:   RO           USAGE:      NA
            PERSIST:  NO           INSRVMOD:   NA
            RANGE:    NA           DEFVALUE:   NA
            UNITS:    NA           SPARSE:     NO  
            DESCR:    NA"
    DEFVAL      { -1 }
    ::= { lanxVrfRouteEntry 15 }

lanxVrfRouteStatus OBJECT-TYPE
    SYNTAX      RowStatus
    ACCESS      read-write
    STATUS      mandatory
    DESCRIPTION 
        "The row status variable, used according to
         row installation and removal conventions.
         	ALCATEL NOTE:
              ACCESS:   NA         USAGE:     MAND 
              PERSIST:  YES        INSRVMOD:  YES  
              RANGE:    1,4,5,6    DEFVALUE:  NA  
              UNITS:    NA         SPARSE:    NO  
              DESCR:    NA"
    ::= { lanxVrfRouteEntry 16 }

lanxVrfIpIfTable OBJECT-TYPE
    SYNTAX      SEQUENCE OF LanxVrfIpIfEntry
    ACCESS      not-accessible
    STATUS      mandatory
    DESCRIPTION 
        "A table showing details of the VLAN/LOOPBACK IP interfaces information associated with the VRF 
         instances.
         ALCATEL NOTE:
           TABLE SIZE:     System level constant. 
                          It can be obtained from fsVrfMaxIpInterfaces.
           DESCR:          NA"
    ::= { lanxVrfMIB 3 }

lanxVrfIpIfEntry OBJECT-TYPE
    SYNTAX      LanxVrfIpIfEntry
    ACCESS      not-accessible
    STATUS      mandatory
    DESCRIPTION 
        "Each entry represents VLAN/LOOPBACK IP interface information associated with a VRF instance
         Row creation : An entry is created by the system when a VRF is created.
         Row deletion : An entry is deleted by the system when a VRF is deleted.
         Index usage : the index is the Vrf Id and Ip If index.
           Note that entries will be presented to the SNMP manager in full
           lexicographical order :  sorted on Vrf Id and Ip If index."
    INDEX       { lanxVrfId, lanxVrfIpIfIndex }
    ::= { lanxVrfIpIfTable 1 }

LanxVrfIpIfEntry ::= SEQUENCE {
    lanxVrfIpIfIndex        INTEGER,
    lanxVrfIpIfAdminStatus  INTEGER,
    lanxVrfIpIfOperStatus   INTEGER,
    lanxVrfIpIfName         DisplayString
}

lanxVrfIpIfIndex OBJECT-TYPE
    SYNTAX      INTEGER (1..2147483647)
    ACCESS      not-accessible
    STATUS      mandatory
    DESCRIPTION 
        "The MIB-II interface index which identifies VLAN IP interface.
         ALCATEL NOTE:
            ACCESS:   NA         USAGE:      NA
            PERSIST:  NO         INSRVMOD:   NA
            RANGE:    DEP        DEFVALUE:   NA 
            UNITS:    NA         SPARSE:     NO 
            DESCR:    DEP(RANGE):Range for setting is 1 to the (total number of IP interfaces in the 
         				system  + 
         				maximum value of number of physical interfaces available in the system). 
         				The maximum number of physical interfaces is obtained from the 
         				object issSystemNumberOfPorts in fsiss.mib. 
         				The total number of IP interfaces in the system is obtained from the 
         				object fsVrfMaxIpInterfaces in fsvrf.mib.
                                        The IP interfaces will start from 65536 to the total number of 
         				IP interfaces in the system. The indices 81920 & 81921 are reserved 
         				for vlan 4094 & 4093 respectively."
    ::= { lanxVrfIpIfEntry 1 }

lanxVrfIpIfAdminStatus OBJECT-TYPE
    SYNTAX      INTEGER { up(1), down(2), testing(3) }
    ACCESS      read-only
    STATUS      mandatory
    DESCRIPTION 
        "The administrative status of this VLAN/LOOPBACK IP  interface.
         ALCATEL NOTE:
            ACCESS:    NA        USAGE:     NA 
            PERSIST:   NO        INSRVMOD:  NA  
            RANGE:     NA        DEFVALUE:  1  
            UNITS:     NA        SPARSE:    NO  
            DESCR:     NA"
    ::= { lanxVrfIpIfEntry 2 }

lanxVrfIpIfOperStatus OBJECT-TYPE
    SYNTAX      INTEGER { up(1), down(2), testing(3) }
    ACCESS      read-only
    STATUS      mandatory
    DESCRIPTION 
        "The current operational status of this VLAN/LOOPBACK IP interface.
         ALCATEL NOTE:
            ACCESS:   NA         USAGE:      NA
            PERSIST:  NO         INSRVMOD:   NA  
            RANGE:    NA         DEFVALUE:   NA 
            UNITS:    NA         SPARSE:     NO 
            DESCR:    NA"
    ::= { lanxVrfIpIfEntry 3 }

lanxVrfIpIfName OBJECT-TYPE
    SYNTAX      DisplayString
    ACCESS      read-only
    STATUS      mandatory
    DESCRIPTION 
        "The Name of this VLAN/LOOPBACK IP interface 
         ALCATEL NOTE:
            ACCESS:   NA         USAGE:      NA
            PERSIST:  NO         INSRVMOD:   NA 
            RANGE:    NA         DEFVALUE:   NA
            UNITS:    NA         SPARSE:     NO 
            DESCR:    NA"
    ::= { lanxVrfIpIfEntry 4 }

lanxVrfIpifMultiNetTable OBJECT-TYPE
    SYNTAX      SEQUENCE OF LanxVrfIpifMultiNetEntry
    ACCESS      not-accessible
    STATUS      mandatory
    DESCRIPTION 
        "A list of all the IP address assigned to the interfaces 
         which are associated with the VRF.
         ALCATEL NOTE:
         	TABLE SIZE:   NA
         	DESCR:        NA"
    ::= { lanxVrfMIB 4 }

lanxVrfIpifMultiNetEntry OBJECT-TYPE
    SYNTAX      LanxVrfIpifMultiNetEntry
    ACCESS      not-accessible
    STATUS      mandatory
    DESCRIPTION 
        "An entry containing the IP address configured for an 
         interface which is associated with a VRF.
         Row creation : An entry is created by the system when a entry
         is created in the LanxCfaValidateMultiNetIpTable.
         Row deletion : An entry is deleted by the system when a  entry
         is deleted in the LanxCfaValidateMultiNetIpTable.
         Index usage : the index is the IP address and Subnet Mask.
         Note that entries will be presented to the SNMP manager in full
         lexicographical order :  sorted on IP address, then on Subnet Mask."
    INDEX       { lanxVrfId, lanxVrfIpIfIndex, lanxVrfIpifMultiNetIpAddr }
    ::= { lanxVrfIpifMultiNetTable 1 }

LanxVrfIpifMultiNetEntry ::= SEQUENCE {
    lanxVrfIpifMultiNetIpAddr           IpAddress,
    lanxVrfIpifMultiNetIpSubnetMask     IpAddress
}

lanxVrfIpifMultiNetIpAddr OBJECT-TYPE
    SYNTAX      IpAddress
    ACCESS      read-only
    STATUS      mandatory
    DESCRIPTION 
        "Specifies the IP address given to this
         interface.
         ALCATEL NOTE:
         ACCESS:   NA         USAGE:     NA 
         PERSIST:  NO         INSRVMOD:  NA  
         RANGE:    NA         DEFVALUE:  NA  
         UNITS:    NA         SPARSE:    NO  
         DESCR:    NA"
    ::= { lanxVrfIpifMultiNetEntry 1 }

lanxVrfIpifMultiNetIpSubnetMask OBJECT-TYPE
    SYNTAX      IpAddress
    ACCESS      read-only
    STATUS      mandatory
    DESCRIPTION 
        "Specifies the IP Subnet Mask for this
         interface."
    ::= { lanxVrfIpifMultiNetEntry 2 }

fsVrfScalars OBJECT IDENTIFIER
    ::= { lanxVrfMIB 5 }

fsVrfMaxVrfs OBJECT-TYPE
    SYNTAX      INTEGER
    ACCESS      read-only
    STATUS      mandatory
    DESCRIPTION 
        "Total number of vrfs in the system.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 1 }

fsVrfMaxFastPathVrfs OBJECT-TYPE
    SYNTAX      INTEGER
    ACCESS      read-only
    STATUS      mandatory
    DESCRIPTION 
        "Total Number of fast path vrfs in the system.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 2 }

fsVrfMaxIpInterfaces OBJECT-TYPE
    SYNTAX      INTEGER
    ACCESS      read-only
    STATUS      mandatory
    DESCRIPTION 
        "Total number of IP interfaces in the system (including slow path and fast path).
         ALCATEL NOTE:
         ACCESS:      NA           USAGE:       NA
         PERSIST:     NO           INSRVMOD:    NA
         RANGE:       NA           DEFVALUE:    NA       
         UNITS:       NA           SPARSE:      NA
         DESCR:       The total number of logical interfaces that can be
                      created. This is dependant on the type of NT board, due
                      to diverse capabilities of the different NT boards."
    ::= { fsVrfScalars 3 }

fsVrfMaxSubnets OBJECT-TYPE
    SYNTAX      INTEGER
    ACCESS      read-only
    STATUS      mandatory
    DESCRIPTION 
        "Total number of subnets in the system (including slow path and fast path).
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 4 }

fsVrfMaxHWRoutes OBJECT-TYPE
    SYNTAX      INTEGER
    ACCESS      read-only
    STATUS      mandatory
    DESCRIPTION 
        "Total number of routes supported in Hardware.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 5 }

fsVrfMaxStaticRoutes OBJECT-TYPE
    SYNTAX      INTEGER
    ACCESS      read-only
    STATUS      mandatory
    DESCRIPTION 
        "Total number of static routes per vrf,both slow and fast path.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 6 }

fsVrfMaxStaticRoutesInFastPathVrf OBJECT-TYPE
    SYNTAX      INTEGER
    ACCESS      read-only
    STATUS      mandatory
    DESCRIPTION 
        "Total number of static routes in fast path vrf.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 7 }

fsVrfNoOfRtmRouteMaps OBJECT-TYPE
    SYNTAX      INTEGER
    ACCESS      read-only
    STATUS      mandatory
    DESCRIPTION 
        "Number of route maps from RTM to Routing protocols.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 8 }

fsVrfNoOfRipInterfaces OBJECT-TYPE
    SYNTAX      INTEGER
    ACCESS      read-only
    STATUS      mandatory
    DESCRIPTION 
        "Total number of RIP interfaces.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 9 }

fsVrfNoOfRipPeers OBJECT-TYPE
    SYNTAX      INTEGER
    ACCESS      read-only
    STATUS      mandatory
    DESCRIPTION 
        "Total Number of RIP peers.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 10 }

fsVrfNoOfRipRedisRoutes OBJECT-TYPE
    SYNTAX      INTEGER
    ACCESS      read-only
    STATUS      mandatory
    DESCRIPTION 
        "Number of routes redistributed to RIP (local subnet, 
         static and OSPF routes).
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 11 }

fsVrfRipRTSize OBJECT-TYPE
    SYNTAX      INTEGER
    ACCESS      read-only
    STATUS      mandatory
    DESCRIPTION 
        "The size of RIP Routing table. This includes RIP routes that
         can be received from the neighbours and routes that can be 
         redistributed to RIP from static and OSPF.
         ALCATEL NOTE:
         ACCESS:      NA          USAGE:       NA
         PERSIST:     NO          INSRVMOD:    NA
         RANGE:       NA	     	 DEFVALUE:    NA    
         UNITS:       NA		     SPARSE:      NA
         DESCR:       NA"
    ::= { fsVrfScalars 12 }

fsVrfNoOfRipAggrSubnets OBJECT-TYPE
    SYNTAX      INTEGER
    ACCESS      read-only
    STATUS      mandatory
    DESCRIPTION 
        "Number of RIP aggregatable subnets.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 13 }

fsVrfNoOfRipERouteMaps OBJECT-TYPE
    SYNTAX      INTEGER
    ACCESS      read-only
    STATUS      mandatory
    DESCRIPTION 
        "Number of RIP egress route maps.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 14 }

fsVrfNoOfOspfAreas OBJECT-TYPE
    SYNTAX      INTEGER
    ACCESS      read-only
    STATUS      mandatory
    DESCRIPTION 
        "it displays the total number of non-backbone areas that
         can be configured by the operator.
         
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 15 }

fsVrfNoOfOspfInterfaces OBJECT-TYPE
    SYNTAX      INTEGER
    ACCESS      read-only
    STATUS      mandatory
    DESCRIPTION 
        "Total Number of OSPF interfaces.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 16 }

fsVrfNoOfOspfNeighbours OBJECT-TYPE
    SYNTAX      INTEGER
    ACCESS      read-only
    STATUS      mandatory
    DESCRIPTION 
        "Total number of OSPF neighbours.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 17 }

fsVrfNoOfOspfLSAEntries OBJECT-TYPE
    SYNTAX      INTEGER
    ACCESS      read-only
    STATUS      mandatory
    DESCRIPTION 
        "Total number of OSPF LSA DB entries.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 18 }

fsVrfNoOfECMPRoutes OBJECT-TYPE
    SYNTAX      INTEGER
    ACCESS      read-only
    STATUS      mandatory
    DESCRIPTION 
        "Number of ECMP routes.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 19 }

fsVrfNoOfOspfBestRoutes OBJECT-TYPE
    SYNTAX      INTEGER
    ACCESS      read-only
    STATUS      mandatory
    DESCRIPTION 
        "Number of OSPF best routes.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 20 }

fsVrfOspfRTSize OBJECT-TYPE
    SYNTAX      INTEGER
    ACCESS      read-only
    STATUS      mandatory
    DESCRIPTION 
        "The size of OSPF Routing table.
         ALCATEL NOTE:
         ACCESS:      NA          USAGE:       NA
         PERSIST:     NO          INSRVMOD:    NA
         RANGE:       NA	     	 DEFVALUE:    NA    
         UNITS:       NA		     SPARSE:      NA
         DESCR:       NA"
    ::= { fsVrfScalars 21 }

fsVrfNoOfOspfRedisRoutes OBJECT-TYPE
    SYNTAX      INTEGER
    ACCESS      read-only
    STATUS      mandatory
    DESCRIPTION 
        "Number of routes redistributed to OSFP (local subnet, 
         static and RIP routes).
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 22 }

fsVrfNoOfOspfAggSubnetsPerArea OBJECT-TYPE
    SYNTAX      INTEGER
    ACCESS      read-only
    STATUS      mandatory
    DESCRIPTION 
        "Total number of aggregatable subnets per area(summary LSA type-3).
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 23 }

fsVrfNoOfOspfAggSubnetsRedisRoutes OBJECT-TYPE
    SYNTAX      INTEGER
    ACCESS      read-only
    STATUS      mandatory
    DESCRIPTION 
        "Total number of aggregatable subnets for redistributed 
         routes(type-5 and type-7 LSA).
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 24 }

fsVrfNoOfOspfMD5Key OBJECT-TYPE
    SYNTAX      INTEGER
    ACCESS      read-only
    STATUS      mandatory
    DESCRIPTION 
        "Total number of OSPF MD5 Authentication keys per interface.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 25 }

fsVrfNoOfOspfSOLSA OBJECT-TYPE
    SYNTAX      INTEGER
    ACCESS      read-only
    STATUS      mandatory
    DESCRIPTION 
        "Total number of self originated LSAs.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 26 }

fsVrfNoOfOspfSOSumLSA OBJECT-TYPE
    SYNTAX      INTEGER
    ACCESS      read-only
    STATUS      mandatory
    DESCRIPTION 
        "Total number of self originated summary LSAs.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 27 }

fsVrfArpTableSize OBJECT-TYPE
    SYNTAX      INTEGER
    ACCESS      read-only
    STATUS      mandatory
    DESCRIPTION 
        "The size of ARP Table.
         ALCATEL NOTE:
         ACCESS:      NA          USAGE:       NA
         PERSIST:     NO          INSRVMOD:    NA
         RANGE:       NA	     	 DEFVALUE:    NA    
         UNITS:       NA		     SPARSE:      NA
         DESCR:       NA"
    ::= { fsVrfScalars 28 }

fsVrfNoOfDhcpRelayAgent OBJECT-TYPE
    SYNTAX      INTEGER
    ACCESS      read-only
    STATUS      mandatory
    DESCRIPTION 
        "The total number of DHCP relay agent instances.
         ALCATEL NOTE:
           ACCESS:      NA       USAGE:       NA
           PERSIST:     NO       INSRVMOD:    NA
           RANGE:       NA	      DEFVALUE:    NA    
           UNITS:       NA       SPARSE:      NA
           DESCR:       NA"
    ::= { fsVrfScalars 29 }

fsVrfSingleFastPathVrfId OBJECT-TYPE
    SYNTAX      INTEGER
    ACCESS      read-only
    STATUS      mandatory
    DESCRIPTION 
        "The id of the VRF which is configured as fast-path
         The value of this object is set to -1 (unknown) when no fast-path VRF configured
         The value of this object is set to -2 (not-applicable) when there are more than one fast-path VRFs
         ALCATEL NOTE:
           ACCESS:      NA           USAGE:       NA
           PERSIST:     YES          INSRVMOD:    YES
           RANGE:       NA	      DEFVALUE:    NA    
           UNITS:       NA    	      SPARSE:      NA
           DESCR:       NA"
    DEFVAL      { -1 }
    ::= { fsVrfScalars 30 }

fsVrfNoOfOspfRNLsa OBJECT-TYPE
    SYNTAX      INTEGER
    ACCESS      read-only
    STATUS      mandatory
    DESCRIPTION 
        "Total number of Router and Network LSAs.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 31 }

fsVrfNoOfRipMD5Key OBJECT-TYPE
    SYNTAX      INTEGER
    ACCESS      read-only
    STATUS      mandatory
    DESCRIPTION 
        "Total number of RIP MD5 Authentication keys per interface.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 32 }

fsVrfNoOfRipIRouteMaps OBJECT-TYPE
    SYNTAX      INTEGER
    ACCESS      read-only
    STATUS      mandatory
    DESCRIPTION 
        "Number of RIP ingress route maps.
         ALCATEL NOTE:
         ACCESS:      NA           USAGE:       NA
         PERSIST:     NO           INSRVMOD:    NA
         RANGE:       NA           DEFVALUE:    NA       
         UNITS:       NA           SPARSE:      NA
         DESCR:       NA"
    ::= { fsVrfScalars 33 }

END -- end of module VRF-MIB.
