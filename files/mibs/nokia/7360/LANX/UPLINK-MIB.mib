--
-- This SMIv1 module has been generated by smidump 0.4.8. Do not edit.
--

UPLINK-MIB DEFINITIONS ::= BEGIN

IMPORTS
    OBJECT-TYPE
        FROM RFC-1212
    TRAP-TYPE
        FROM RFC-1215
    Gauge, TimeTicks, enterprises
        FROM RFC1155-SMI
    RowStatus
        FROM SNMPv2-TC;

fsuplinkgroup OBJECT IDENTIFIER
    ::= { enterprises futuresoftware(2076) 93 }

-- fsuplinkgroup MODULE-IDENTITY
--     LAST-UPDATED "200411250000Z"
--     ORGANIZATION 
--         "Future Software Private Limited"
--     CONTACT-INFO 
--         " 
--          Postal:     Future Software Pvt. Ltd.,
--                      480-481, Anna Salai,
--                      Nandanam,
--                      Chennai,
--                      India  600 035
--          Telephone:  44-24330550
--          E-Mail:     support@future.futsoft.com "
--     DESCRIPTION 
--         "The proprietary MIB module for FutureUpLinkGroup."
--     REVISION    "200411250000Z"
--     DESCRIPTION 
--         "The initial revision of this MIB module was published as
--          RFC 1450."
--     ::= { enterprises futuresoftware(2076) 93 }


PortList ::=
    OCTET STRING

-- PortList ::= TEXTUAL-CONVENTION
--     STATUS      mandatory
--     DESCRIPTION 
--         "Each octet within this value specifies a set of eight
--          ports, with the first octet specifying ports 1 through
--          8, the second octet specifying ports 9 through 16, etc.
--          Within each octet, the most significant bit represents
--          the lowest numbered port, and the least significant bit
--          represents the highest numbered port.  Thus, each port
--          of the system is represented by a single bit within the
--          value of this object. If that bit has a value of '1'
--          then that port is included in the set of ports; the port
--          is not included if its bit has a value of '0'."
--     SYNTAX      OCTET STRING

fsUpLinkGroupTable OBJECT-TYPE
    SYNTAX      SEQUENCE OF FsUpLinkGroupEntry
    ACCESS      not-accessible
    STATUS      mandatory
    DESCRIPTION 
        "A table contains the logical groups defined for the uplink ports 
         in the system.
         ALCATEL NOTE:
         TABLESIZE	:  DEP 
         DESCR	:  DEP(TABLESIZE):The table size is dependant on the maximum number of
         		   physical interfaces available in the system. This value can be got from
         		   the object issSystemNumberOfPorts in fsiss.mib"
    ::= { fsuplinkgroup 1 }

fsUpLinkGroupEntry OBJECT-TYPE
    SYNTAX      FsUpLinkGroupEntry
    ACCESS      not-accessible
    STATUS      mandatory
    DESCRIPTION 
        "An entry containing information about the uplink groups present 
         in the system.
         Row creation : A UPLINK-GROUP entry shall be created in one step by a
         		set-request with all necessary parameter values and
         		fsUpLinkGroupRowStatus set to createAndGo(4).
         Row deletion : A UPLINK-GROUP entry shall be deleted by setting
         		the fsUpLinkGroupRowStatus of the specific entry to destroy(6).
         Index usage : the indexe is fsUpLinkGroupId.
         Note that entries will be presented to the SNMP manager in full
         lexicographical order :  sorted on fsUpLinkGroupId."
    INDEX       { fsUpLinkGroupId }
    ::= { fsUpLinkGroupTable 1 }

FsUpLinkGroupEntry ::= SEQUENCE {
    fsUpLinkGroupId                 INTEGER,
    fsUpLinkGroupPortList           PortList,
    fsUpLinkGroupThreshold          INTEGER,
    fsUpLinkGroupNumberOfLinks      INTEGER,
    fsUpLinkGroupLastChange         TimeTicks,
    fsUpLinkGroupNumberOfChanges    INTEGER,
    fsUpLinkGroupStatus             INTEGER,
    fsUpLinkGroupRowStatus          RowStatus
}

fsUpLinkGroupId OBJECT-TYPE
    SYNTAX      INTEGER (1..7)
    ACCESS      read-only
    STATUS      mandatory
    DESCRIPTION 
        "A unique number for each logical uplink group.
         ALCATEL NOTE:
         ACCESS	:   NA          	USAGE		:    NA
         PERSIST	:   YES         	INSRVMOD	:    NA 
         RANGE	:   NA           	DEFVALUE	:    NA   
         UNITS	:   NA            	SPARSE		:    NO
         DESCR	:   NA"
    ::= { fsUpLinkGroupEntry 1 }

fsUpLinkGroupPortList OBJECT-TYPE
    SYNTAX      PortList
    ACCESS      read-write
    STATUS      mandatory
    DESCRIPTION 
        "The set of ports members of the uplink group.
         ALCATEL NOTE:
         ACCESS	:   NA           	USAGE		:   MAND
         PERSIST	:   YES          	INSRVMOD	:   YES 
         RANGE	:   0..8   	 	DEFVALUE	:   NA 	
         UNITS	:   NA           	SPARSE		:   NO
         DESCR	:   NA"
    ::= { fsUpLinkGroupEntry 2 }

fsUpLinkGroupThreshold OBJECT-TYPE
    SYNTAX      INTEGER
    ACCESS      read-write
    STATUS      mandatory
    DESCRIPTION 
        "This value indicates the minimum number of links to be operationally 
         UP in the group. 
         
         The number of links, which are operational UP in the group goes 
         below the threshold value needs to be notified.
         
         when configured the threshold of a group to zero, then will never 
         notify about the group.
         ALCATEL NOTE:
         ACCESS	:    NA           USAGE		:    MAND
         PERSIST	:    YES          INSRVMOD	:    YES 
         RANGE	:    0..7         DEFVALUE	:    NA  
         UNITS	:    NA           SPARSE	:    NO
         DESCR	:    NA"
    DEFVAL      { 0 }
    ::= { fsUpLinkGroupEntry 3 }

fsUpLinkGroupNumberOfLinks OBJECT-TYPE
    SYNTAX      INTEGER
    ACCESS      read-only
    STATUS      mandatory
    DESCRIPTION 
        "This object specifies currently available number of links in the group 
         configured that are operational UP.
         ALCATEL NOTE:
         ACCESS	:   NA           	USAGE		:    NA
         PERSIST	:   NO          	INSRVMOD	:    NA 
         RANGE	:   1..7		DEFVALUE	:    0    
         UNITS	:   NA           	SPARSE		:    NO
         DESCR	:   NA"
    ::= { fsUpLinkGroupEntry 4 }

fsUpLinkGroupLastChange OBJECT-TYPE
    SYNTAX      TimeTicks
    ACCESS      read-only
    STATUS      mandatory
    DESCRIPTION 
        "The value since sysUpTime when last uplink group notification 
         is sent.
         ALCATEL NOTE:
         ACCESS	:   NA           	USAGE		:   NA
         PERSIST	:   NO          	INSRVMOD	:   NA 
         RANGE	:   NA           	DEFVALUE	:   0  
         UNITS	:   NA           	SPARSE		:   NO
         DESCR	:   NA"
    ::= { fsUpLinkGroupEntry 5 }

fsUpLinkGroupNumberOfChanges OBJECT-TYPE
    SYNTAX      INTEGER
    ACCESS      read-only
    STATUS      mandatory
    DESCRIPTION 
        "This object contains the total number of times the uplink group 
         notification is sent either group down/up for the particular group.
         ALCATEL NOTE:
         ACCESS	:   NA           	USAGE		:    NA
         PERSIST	:   NO          	INSRVMOD	:    NA 
         RANGE	:   NA           	DEFVALUE	:    0  
         UNITS	:   NA           	SPARSE		:    NO
         DESCR	:   NA"
    ::= { fsUpLinkGroupEntry 6 }

fsUpLinkGroupStatus OBJECT-TYPE
    SYNTAX      INTEGER { up(1), down(2), invalid(3) }
    ACCESS      read-only
    STATUS      mandatory
    DESCRIPTION 
        "This object indicates the current uplink group status.
         
         If the fsUpLinkGroupNumberOfLinks >= fsUpLinkGroupThreshold value 
         then the value of this object will be up.
         
         If the fsUpLinkGroupNumberOfLinks < fsUpLinkGroupThreshold value 
         then the value of this object will be down.
         
         If fsUpLinkGroupThreshold is configured as zero then the value 
         of this object will be invalid
         ALCATEL NOTE:
         ACCESS	:    NA           USAGE		:    NA
         PERSIST	:    NO           INSRVMOD	:    NA 
         RANGE	:    NA        	DEFVALUE	:    NA   
         UNITS	:    NA           SPARSE	:    NO
         DESCR	:    NA"
    ::= { fsUpLinkGroupEntry 7 }

fsUpLinkGroupRowStatus OBJECT-TYPE
    SYNTAX      RowStatus
    ACCESS      read-write
    STATUS      mandatory
    DESCRIPTION 
        "This object indicates the status of this entry.
         ALCATEL NOTE:
         ACCESS	:   NA           	USAGE		:    MAND
         PERSIST	:   YES          	INSRVMOD	:    YES 
         RANGE	:   1,2,4,5,6		DEFVALUE	:    NA 
         UNITS	:   NA           	SPARSE		:    NO
         DESCR	:   NA"
    ::= { fsUpLinkGroupEntry 8 }

fsUpLinkGroupGlobalChangeCount OBJECT-TYPE
    SYNTAX      INTEGER
    ACCESS      read-only
    STATUS      mandatory
    DESCRIPTION 
        "This object indicates the total number of times the uplink 
         group down / up notification is sent to NT
          ALCATEL NOTE:
          ACCESS	:   NA		USAGE   	:    NA
          PERSIST	:   NO      	INSRVMOD	:    NA
          RANGE	:   NA		DEFVALUE	:    0
          UNITS	:   NA		SPARSE		:    NA
          DESCR	:   NA"
    ::= { fsuplinkgroup 2 }

fsUpLinkGroupUp TRAP-TYPE
    ENTERPRISE  fsuplinkgroup
    VARIABLES   { fsUpLinkGroupId, fsUpLinkGroupThreshold, 
                  fsUpLinkGroupStatus }
--     STATUS      mandatory
    DESCRIPTION 
        "when the number of fsUpLinkGroupNumberOfLinks count 
         is equal to fsUpLinkGroupThreshold then fsUpLinkGroupUp 
         notification is generated. 
             
         When configured threshold value of a group to zero, then will never 
         notify the uplink group notifications.
             
         The notification carries the uplink group identifier fsUpLinkGroupId, 
         threshold configured for the group and the group status."
    ::= 3

fsUpLinkGroupDown TRAP-TYPE
    ENTERPRISE  fsuplinkgroup
    VARIABLES   { fsUpLinkGroupId, fsUpLinkGroupThreshold, 
                  fsUpLinkGroupStatus }
--     STATUS      mandatory
    DESCRIPTION 
        "when the number of fsUpLinkGroupNumberOfLinks count falls 
         below the fsUpLinkGroupThreshold then fsUpLinkGroupDown 
         notification is generated.
         
         When configured the threshold of a group to zero, then will never 
         notify the uplink group notifications.
         
         The notification carries the uplink group identifier fsUpLinkGroupId,
         threshold configured for the group and the group status."
    ::= 4

END -- end of module UPLINK-MIB.
