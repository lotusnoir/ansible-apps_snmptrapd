--
-- This SMIv1 module has been generated by smidump 0.4.8. Do not edit.
--

--
-- WARNING: this output may be incorrect due to significant parse errors
--

IGSCAC-MIB DEFINITIONS ::= BEGIN

IMPORTS
    OBJECT-TYPE
        FROM RFC-1212
    Counter, Gauge, IpAddress, enterprises
        FROM RFC1155-SMI
    RowStatus, TruthValue
        FROM SNMPv2-TC;

fsigscac OBJECT IDENTIFIER
    ::= { enterprises futuresoftware(2076) fsigs(74) 6 }

-- fsigscac MODULE-IDENTITY
--     LAST-UPDATED "200605070000Z"
--     ORGANIZATION 
--         "Future Software Private Limited"
--     CONTACT-INFO 
--         "  
--          Postal:     Future Software Pvt. Ltd., 
--                      480-481, Anna Salai, 
--                      Nandanam, 
--                      Chennai, 
--                      India  600 035 
--          Telephone: +91-44-4330550 
--          E-Mail:     support@future.futsoft.com "
--     DESCRIPTION 
--         " The proprietary MIB module for FutureIGS. "
--     REVISION    "200605070000Z"
--     DESCRIPTION 
--         "Revision history updated "
--     ::= { enterprises futuresoftware(2076) fsigs(74) 6 }


fsIgsMcastCacSystem OBJECT IDENTIFIER
    ::= { fsigscac 1 }

fsIgsMcastMaxCACBandWidth OBJECT-TYPE
    SYNTAX      INTEGER
    ACCESS      read-write
    STATUS      mandatory
    DESCRIPTION 
        "This is used to set Max Bandwidth for the system.When user sets zero CAC BW 
         functionality will be disabled.The bandwidth is accepted in kbps.
         This Object is depend on 
               - fsIgsMaxNonConfiguredMulticastLearn
               - fsIgsMaxMulticastLearn  
               
         ALCATEL NOTE:
         	ACCESS:      NA            USAGE:       NA
         	PERSIST:     YES           INSRVMOD:    YES
         	RANGE:       NA            DEFVALUE:    0
         	UNITS:       kbps          SPARSE:      NA
         	DESCR:Setting of dependency scalar objects with non-dependent objects is not recommended in a single PDU.This
           object is dependent on fsIgsMaxNonConfiguredMulticastLearn and fsIgsMaxMulticastLearn"
    DEFVAL      { 0 }
    ::= { fsIgsMcastCacSystem 1 }

fsIgsMaxNonConfiguredMulticastLearn OBJECT-TYPE
    SYNTAX      INTEGER
    ACCESS      read-write
    STATUS      mandatory
    DESCRIPTION 
        "This is the maximum number of non configured Multicast entries allowed to 
         learn. The value configured in this object includes only dynamically learnt                
         multicast streams.The configured value in this object must be less than or 
         equal to the value of the object fsIgsMaxMulticastLearn in fsigs.mib .
         This Object is depend on 
               - fsIgsMcastMaxCACBandWidth
               - fsIgsMaxMulticastLearn  
         
         ALCATEL NOTE:
         	ACCESS:      NA            USAGE:       NA
         	PERSIST:     YES           INSRVMOD:    YES
         	RANGE:       0..1024       DEFVALUE:    0
         	UNITS:       NA            SPARSE:      NA
         	DESCR:Setting of dependency scalar objects with non-dependent objects is not recommended in a single PDU.This
           object is dependent on fsIgsMcastMaxCACBandWidth and fsIgsMaxMulticastLearn"
    DEFVAL      { 0 }
    ::= { fsIgsMcastCacSystem 2 }

fsIgsOccupiedBWGuaranteed OBJECT-TYPE
    SYNTAX      INTEGER
    ACCESS      read-only
    STATUS      mandatory
    DESCRIPTION 
        "This is to provide the bandwidth occupied by the all active guaranteed 
         channels in Mcast Source Table.
         ALCATEL NOTE:
         	ACCESS:      NA            USAGE:       NA
         	PERSIST:     NO            INSRVMOD:    NA
         	RANGE:       NA            DEFVALUE:    0
         	UNITS:       kbps          SPARSE:      NA
         	DESCR:       NA"
    ::= { fsIgsMcastCacSystem 3 }

fsIgsOccupiedGuaranteedChannels OBJECT-TYPE
    SYNTAX      INTEGER
    ACCESS      read-only
    STATUS      mandatory
    DESCRIPTION 
        "This is to provide the number of active guaranteed channels connected to 
         LANX.
         ALCATEL NOTE:
         	ACCESS:      NA            USAGE:       NA
         	PERSIST:     NO            INSRVMOD:    NA
         	RANGE:       NA            DEFVALUE:    0
         	UNITS:       NA            SPARSE:      NA
         	DESCR:       NA"
    ::= { fsIgsMcastCacSystem 4 }

fsIgsOccupiedBWNonGuaranteed OBJECT-TYPE
    SYNTAX      INTEGER
    ACCESS      read-only
    STATUS      mandatory
    DESCRIPTION 
        "This is to provide the bandwidth occupied by the all active non-guaranteed 
         channels in LANX.
         ALCATEL NOTE:
         	ACCESS:      NA            USAGE:       NA
         	PERSIST:     NO            INSRVMOD:    NA
         	RANGE:       NA            DEFVALUE:    0
         	UNITS:       kbps          SPARSE:      NA
         	DESCR:       NA"
    ::= { fsIgsMcastCacSystem 5 }

fsIgsOccupiedNonGuaranteedChannels OBJECT-TYPE
    SYNTAX      INTEGER
    ACCESS      read-only
    STATUS      mandatory
    DESCRIPTION 
        "This is to provide the number of active non-guaranteed channels connected 
         to LANX.
         ALCATEL NOTE:
         	ACCESS:      NA            USAGE:       NA
         	PERSIST:     NO            INSRVMOD:    NA
         	RANGE:       NA            DEFVALUE:    0
         	UNITS:       NA            SPARSE:      NA
         	DESCR:       NA"
    ::= { fsIgsMcastCacSystem 6 }

fsIgsJoinsRejectedInsuffSysBW OBJECT-TYPE
    SYNTAX      Counter
    ACCESS      read-only
    STATUS      mandatory
    DESCRIPTION 
        "This is to provide the number of joins rejected for non-guaranteed channels due to 
         Insuffiecient bandwidth at the system level . 
         ALCATEL NOTE:
         	ACCESS:      NA            USAGE:       NA
         	PERSIST:     NO            INSRVMOD:    NA
         	RANGE:       NA            DEFVALUE:    0
         	UNITS:       NA            SPARSE:      NA
         	DESCR:       NA"
    ::= { fsIgsMcastCacSystem 7 }

fsIgsJoinsRejectedExceedsSysChannelLimit OBJECT-TYPE
    SYNTAX      Counter
    ACCESS      read-only
    STATUS      mandatory
    DESCRIPTION 
        "Provides statistics of Number of multicast Joins rejected for the non-guaranteed/non-configured
         channels as Max connections at the system level has reached.This counter will be incremented if
         the following cac check fails. 
         
         Number of active multicast streams < (fsIgsMaxMulticastLearn 	- total no of guaranteed MC channels) 
         where active multicast streams includes both fsIgsOccupiedNonGuaranteedChannels and 
         	  fsIgsActiveNonConfMulticastEntries.
         ALCATEL NOTE:
         	ACCESS:      NA            USAGE:       NA
         	PERSIST:     NO            INSRVMOD:    NA
         	RANGE:       NA            DEFVALUE:    0
         	UNITS:       NA            SPARSE:      NA
         	DESCR:       NA"
    ::= { fsIgsMcastCacSystem 8 }

fsIgsNonConfRejectedCount OBJECT-TYPE
    SYNTAX      Counter
    ACCESS      read-only
    STATUS      mandatory
    DESCRIPTION 
        "This is to provide the count of joins rejected  for non-configured multicast source since max Nonconfigured 
         Count has reached.
         ALCATEL NOTE:
         ACCESS:      NA            USAGE:       NA
         PERSIST:     NO            INSRVMOD:    NA
         RANGE:       NA            DEFVALUE:    0
         UNITS:       NA            SPARSE:      NA
         DESCR:       NA"
    ::= { fsIgsMcastCacSystem 9 }

fsIgsActiveNonConfMulticastEntries OBJECT-TYPE
    SYNTAX      INTEGER
    ACCESS      read-only
    STATUS      mandatory
    DESCRIPTION 
        "This is the number of active Non configured Multicast entries that are present. 
         This includes dynamic learnt entries and statically configured entries present 
         in the system.
         ALCATEL NOTE:
         	ACCESS:      NA            USAGE:       NA
         	PERSIST:     NO            INSRVMOD:    NA
         	RANGE:       NA            DEFVALUE:    0
         	UNITS:       NA            SPARSE:      NA
         	DESCR:       NA"
    ::= { fsIgsMcastCacSystem 10 }

fsIgsNextFreeBundleId OBJECT-TYPE
    SYNTAX      INTEGER
    ACCESS      read-only
    STATUS      mandatory
    DESCRIPTION 
        "This object is used  to retrieve the next free bundle id. The maximum number of bundles supported = 64.
         The bundleId ranges from 1 up to 64.The output of this object can be used to create a new row in the 
         fsIgsMcastBundleTable. If no bundle is currently free, then performing a get operation for this object 
         will return a value of zero.
         ALCATEL NOTE:
         	ACCESS:      NA            USAGE:       NA
         	PERSIST:     NO            INSRVMOD:    NA
         	RANGE:       0..64         DEFVALUE:    1
         	UNITS:       NA            SPARSE:      NA
         	DESCR:       NA"
    ::= { fsIgsMcastCacSystem 11 }

fsIgsClearCacStats OBJECT-TYPE
    SYNTAX      INTEGER { resetChannels(1), resetBundles(2), 
                    resetSystem(3), resetAll(4), resetCompleted(5) }
    ACCESS      read-write
    STATUS      mandatory
    DESCRIPTION 
        "This object is used to clear the CAC related counters.
         Objects that are used to maintain the state of the system like active bandwidth
         and active channel count at system and bundle level will not be cleared.i.e.,
         fsIgsActiveNonConfMulticastEntries, fsIgsOccupiedNonGuaranteedChannels, 
         fsIgsOccupiedGuaranteedChannels, fsIgsOccupiedBWGuaranteed and fsIgsOccupiedBWNonGuaranteed 
         will not be cleared when the following values are set.
         
         	  A value of
          (1)resetChannels - will clear statistics of all entries in the channel table.
                              All the counters maintained in the fsIgsMcastChannelStatsTable
                              for all the source entries are cleared.
         	   (2)resetBundles  - will clear statistics of all entries in the bundle table.
                              All the counters in the fsIgsMcastBundleStatsTable except 
         		                 fsIgsMcastBundleOccupiedBWGuaranteed, fsIgsMcastBundleOccupiedGuaranteed, 
                              fsIgsMcastBundleOccupiedBWNonGuaranteed, fsIgsMcastBundleOccupiedNonGuaranteed
                              will be cleared.
          (3)resetSystem   - will clear statistics of system objects only.
                              The counters maintained at system level - fsIgsJoinsRejectedInsuffSysBW,
                              fsIgsJoinsRejectedExceedsSysChannelLimit,fsIgsNonConfRejectedCount will be cleared.
          (4)resetAll       - will clear statistics of all entries in the channel table,statistics of all the entries 
                              in the bundle table and clear system objects.i.e setting (1),(2) and (3) simultaneously 
                              will be done once when this object is set.
          (5)resetCompleted - This value is returned when get operation is requested for this object.
         ALCATEL NOTE:
         	ACCESS:      NA            USAGE:       NA
         	PERSIST:     NO            INSRVMOD:    YES
         	RANGE:       NA            DEFVALUE:    1
         	UNITS:       NA            SPARSE:      NA
         	DESCR:       NA"
    DEFVAL      { resetCompleted }
    ::= { fsIgsMcastCacSystem 12 }

fsIgsMcastCacSource OBJECT IDENTIFIER
    ::= { fsigscac 2 }

fsIgsMcastSourceTable OBJECT-TYPE
    SYNTAX      SEQUENCE OF FsIgsMcastSourceEntry
    ACCESS      not-accessible
    STATUS      mandatory
    DESCRIPTION 
        "This table contains Mcast source related
         information as configured by the user.
         ALCATEL NOTE:
         	TABLESIZE:   1024..4096
         	DESCR:       NA"
    ::= { fsIgsMcastCacSource 1 }

fsIgsMcastSourceEntry OBJECT-TYPE
    SYNTAX      FsIgsMcastSourceEntry
    ACCESS      not-accessible
    STATUS      mandatory
    DESCRIPTION 
        "This table contains VlanId, multicast group IP address, source IP address, 
         Bandwidth allocated, a flag to configure the Mcast source as guaranteed/non-guaranteed,
         the BundleId to specify the bundle in which the Mcast channel belongs and RowStatus
         which are configured by the user.
         Row creation : This entry can be created by setting the fsIgsMcastSrcRowStatus to createandgo(4) with all necessary
              parameters.
         Row deletion : This entry can be deleted by setting the fsIgsMcastSrcRowStatus to destroy(6).                 
         Index usage : The indices are Multicast Source Vlan ID, Multicast Source Class D IP Address and Multicast Source IP 
             address.
         lexicographical order :  Sorted(hashed) on Multicast Source Vlan ID, Multicast Source Class D IP Address and 
                        Multicast Source IP address"
    INDEX       { fsIgsMcastSrcVlanId, fsIgsMcastSrcClassDIPAddress, 
                  fsIgsMcastSrcSourceIPAddress }
    ::= { fsIgsMcastSourceTable 1 }

FsIgsMcastSourceEntry ::= SEQUENCE {
    fsIgsMcastSrcVlanId                 INTEGER,
    fsIgsMcastSrcClassDIPAddress        IpAddress,
    fsIgsMcastSrcSourceIPAddress        IpAddress,
    fsIgsMcastSrcEtherSustainBitRate    INTEGER,
    fsIgsMcastSrcguaranteedFlag         INTEGER,
    fsIgsMcastSrcBundleID               INTEGER,
    fsIgsMcastSrcRowStatus              RowStatus
}

fsIgsMcastSrcVlanId OBJECT-TYPE
    SYNTAX      INTEGER (1..4094)
    ACCESS      not-accessible
    STATUS      mandatory
    DESCRIPTION 
        "This object specifies the VLAN in which the multicast source is.
         ALCATEL NOTE:
         	ACCESS:      NA            USAGE:       NA
         	PERSIST:     YES           INSRVMOD:    NA
         	RANGE:       NA            DEFVALUE:    NA
         	UNITS:       NA            SPARSE:      NO
         	DESCR:       NA"
    ::= { fsIgsMcastSourceEntry 1 }

fsIgsMcastSrcClassDIPAddress OBJECT-TYPE
    SYNTAX      IpAddress
    ACCESS      not-accessible
    STATUS      mandatory
    DESCRIPTION 
        "This is the address of a multicast source in network-byte
         order (big-endian). The class D address must be in the range of
         224.0.0.3 to 239.255.255.255, those IP addresses in this table 
         should be different each other in low-order 23 bits to avoid 
         MAC address conflict.
         ALCATEL NOTE:
         	ACCESS:      NA                 USAGE:       NA
         	PERSIST:     YES                INSRVMOD:    NA
         	RANGE:       NA                 DEFVALUE:    NA
         	UNITS:       NA                 SPARSE:      NO
         	DESCR:       NA"
    ::= { fsIgsMcastSourceEntry 2 }

fsIgsMcastSrcSourceIPAddress OBJECT-TYPE
    SYNTAX      IpAddress
    ACCESS      not-accessible
    STATUS      mandatory
    DESCRIPTION 
        "This object specifies the source address of the multicast server.
         ALCATEL NOTE:
         	ACCESS:      NA            USAGE:       NA
         	PERSIST:     YES           INSRVMOD:    NA
         	RANGE:       NA            DEFVALUE:    NA
         	UNITS:       NA            SPARSE:      NO
         	DESCR:       NA"
    ::= { fsIgsMcastSourceEntry 3 }

fsIgsMcastSrcEtherSustainBitRate OBJECT-TYPE
    SYNTAX      INTEGER (0..100000)
    ACCESS      read-write
    STATUS      mandatory
    DESCRIPTION 
        "Bandwidth accepted for each McastSource. The min value is 1 kbps and the
         maximum value is 100 mbps. The Bw is accepted in the kbps.
         	ALCATEL NOTE:
         	ACCESS:      NA            USAGE:       OPT
         	PERSIST:     YES           INSRVMOD:    YES
         	RANGE:       NA            DEFVALUE:    0
         	UNITS:       kbps          SPARSE:      NO
         	DESCR:       NA"
    ::= { fsIgsMcastSourceEntry 4 }

fsIgsMcastSrcguaranteedFlag OBJECT-TYPE
    SYNTAX      INTEGER { guaranteed(1), nonguaranteed(2) }
    ACCESS      read-write
    STATUS      mandatory
    DESCRIPTION 
        "This is used to set a McastSource as a guaranteed or non-guaranteed in 
         the Mcast source table.When the McastSource is set to guaranteed then 
         non-guaranteed or non-configured McastSource can not use the reserved
         resource for the guaranteed group.
         ALCATEL NOTE:
         	ACCESS:      NA            USAGE:       OPT
         	PERSIST:     YES           INSRVMOD:    YES
         	RANGE:       NA            DEFVALUE:    NA
         	UNITS:       NA            SPARSE:      NO
         	DESCR:       NA"
    DEFVAL      { nonguaranteed }
    ::= { fsIgsMcastSourceEntry 5 }

fsIgsMcastSrcBundleID OBJECT-TYPE
    SYNTAX      INTEGER
    ACCESS      read-write
    STATUS      mandatory
    DESCRIPTION 
        "This is used to associate a McastSource to a Bundle.By default it will be 
         assigned to Bundle zero indicating no bundle id assigned.When the value is zero, 
         no bundle CAC is applied.To associate a MC channel to a bundle, the bundle must 
         be present.
         ALCATEL NOTE:
         	ACCESS:      NA            USAGE:       OPT
         	PERSIST:     YES           INSRVMOD:    YES
         	RANGE:       0..64         DEFVALUE:    1
         	UNITS:       NA            SPARSE:      NO
         	DESCR:       NA"
    DEFVAL      { 0 }
    ::= { fsIgsMcastSourceEntry 6 }

fsIgsMcastSrcRowStatus OBJECT-TYPE
    SYNTAX      RowStatus
    ACCESS      read-write
    STATUS      mandatory
    DESCRIPTION 
        "This object is used to create a new row or delete an
         existing row in this table. The possible valid values are:
                 (1) active
                 (4) createdAndGo
                 (5) createdAndWait 
                 (6) destroy
         To create an entry in this table, this object should be set to
         CreateAndGo or CreateAndWait. To delete an entry from this table, RowStatus
         should be set to destroy value by the SNMP manager.
         ALCATEL NOTE:
         ACCESS:      NA            USAGE:       MAND
         PERSIST:     YES           INSRVMOD:    YES
         RANGE:       1,4,5,6       DEFVALUE:    NA
         UNITS:       NA            SPARSE:      NO
         DESCR:       NA"
    ::= { fsIgsMcastSourceEntry 7 }

fsIgsMcastChannelStatsTable OBJECT-TYPE
    SYNTAX      SEQUENCE OF FsIgsMcastChannelStatsEntry
    ACCESS      not-accessible
    STATUS      mandatory
    DESCRIPTION 
        "This table contains Multicast channel statistics maintained by LANX for CAC 
         functionality.The statistics are maintained per channel basis.
         ALCATEL NOTE:          
         	TABLESIZE:   1024..4096
         	DESCR:       NA"
    ::= { fsIgsMcastCacSource 2 }

fsIgsMcastChannelStatsEntry OBJECT-TYPE
    SYNTAX      FsIgsMcastChannelStatsEntry
    ACCESS      not-accessible
    STATUS      mandatory
    DESCRIPTION 
        "This table contains channel statistics for joins rejected when CAC conditios 
         are not satisfied like InsufficientsystemBW,InsufficientBundleBW,ExceedsSysChannelLimit,
         ExceedsBundleChannelLimit and SLA counter and a read-write object for clearing statistics 
         counters for the channel.
         	Row creation : This entry can be created by setting the FsIgsMcastSrcRowStatus to createandgo(4) with all necessary
                 parameters.
         Row deletion : This entry can be deleted by setting the fsIgsMcastSrcRowStatus to destroy(6).                
         Index usage  : The indices are Multicast Source Vlan ID, Multicast Source Class D IP Address and Multicast Source IP 
                  address.
         lexicographical order :  Sorted on Multicast Source Vlan ID, Multicast Source Class D IP Address and 
                            Multicast Source IP address"
    INDEX       { fsIgsMcastSrcVlanId, fsIgsMcastSrcClassDIPAddress, 
                  fsIgsMcastSrcSourceIPAddress }
    ::= { fsIgsMcastChannelStatsTable 1 }

FsIgsMcastChannelStatsEntry ::= SEQUENCE {
    fsIgsMcastJoinsRejectedInsuffSysBW                  Counter,
    fsIgsMcastJoinsRejectedInsuffBundleBW               Counter,
    fsIgsMcastJoinsRejectedExceedsSysChannelLimit       Counter,
    fsIgsMcastJoinsRejectedExceedsBundleChannelLimit    Counter,
    fsIgsMcastRejectedSLACounter                        Counter,
    fsIgsMcastChannelClearStats                         TruthValue
}

fsIgsMcastJoinsRejectedInsuffSysBW OBJECT-TYPE
    SYNTAX      Counter
    ACCESS      read-only
    STATUS      mandatory
    DESCRIPTION 
        "Provides statistics of Number of multicast Joins rejected for the non-
         guaranteed Mcast join since Bandwidth is not Available at the system 
         level.
         ALCATEL NOTE:
         	ACCESS:      NA            USAGE:       NA
         	PERSIST:     NO            INSRVMOD:    NA
         	RANGE:       NA            DEFVALUE:    0
         	UNITS:       multicast joins  SPARSE:      NO
         	DESCR:       NA"
    ::= { fsIgsMcastChannelStatsEntry 1 }

fsIgsMcastJoinsRejectedInsuffBundleBW OBJECT-TYPE
    SYNTAX      Counter
    ACCESS      read-only
    STATUS      mandatory
    DESCRIPTION 
        "Provides statistics of Number of multicast Joins rejected for the non-
         guaranteed Mcast join since Bandwidth is not Available in the 
         correponding bundle .
         ALCATEL NOTE:
         	ACCESS:      NA            USAGE:       NA
         	PERSIST:     NO            INSRVMOD:    NA
         	RANGE:       NA            DEFVALUE:    0
         	UNITS:       multicast Joins   SPARSE:      NO
         	DESCR:       NA"
    ::= { fsIgsMcastChannelStatsEntry 2 }

fsIgsMcastJoinsRejectedExceedsSysChannelLimit OBJECT-TYPE
    SYNTAX      Counter
    ACCESS      read-only
    STATUS      mandatory
    DESCRIPTION 
        "Provides statistics of Number of multicast Joins rejected for the non-
         guaranteed channel entry as Max connections at the system level has 
         reached.
         ALCATEL NOTE:
         	ACCESS:      NA            USAGE:       NA
         	PERSIST:     NO            INSRVMOD:    NA
         	RANGE:       NA            DEFVALUE:    0
         	UNITS:       multicast Joins  SPARSE:      NO
         	DESCR:       NA"
    ::= { fsIgsMcastChannelStatsEntry 3 }

fsIgsMcastJoinsRejectedExceedsBundleChannelLimit OBJECT-TYPE
    SYNTAX      Counter
    ACCESS      read-only
    STATUS      mandatory
    DESCRIPTION 
        "Provides statistics of Number of multicast Joins rejected for the non-
         guaranteed channel entry as max connections at bundle level has reached.
         ALCATEL NOTE:
         	ACCESS:      NA            USAGE:       NA
         	PERSIST:     NO            INSRVMOD:    NA
         	RANGE:       NA            DEFVALUE:    0
         	UNITS:       multicast Joins  SPARSE:      NO
         	DESCR:       NA"
    ::= { fsIgsMcastChannelStatsEntry 4 }

fsIgsMcastRejectedSLACounter OBJECT-TYPE
    SYNTAX      Counter
    ACCESS      read-only
    STATUS      mandatory
    DESCRIPTION 
        "Provides statistics of Number of multicast Joins rejected for the non-guaranteed 
         channel entry as a result of either of the following.
          1. system bandwidth not available
          2. Bundle bandwidth not available
          3. max system connections has reached 
          4. Max bundle connections has reached.
          If any of the four mentioned above is true, then this counter will also be incremented.
         ALCATEL NOTE:
         	ACCESS:      NA            USAGE:       NA
         	PERSIST:     NO            INSRVMOD:    NA
         	RANGE:       NA            DEFVALUE:    0
         	UNITS:       multicast Joins  SPARSE:      NO
         	DESCR:       NA"
    ::= { fsIgsMcastChannelStatsEntry 5 }

fsIgsMcastChannelClearStats OBJECT-TYPE
    SYNTAX      TruthValue
    ACCESS      read-write
    STATUS      mandatory
    DESCRIPTION 
        "This object is used to reset all the CAC related channel counters for the given 
         multicast source. When it is set to true(1), all the counters in this row will be
         cleared. Once resetting action is completed, agent sets the value to false(2). 
         If SNMP Manager sets this object to false(2), agent does not take any action. 
         A get operation for this object will always return a value of false(2).
         ALCATEL NOTE:
         	ACCESS:      NA            USAGE:       NA
         	PERSIST:     NO            INSRVMOD:    YES
         	RANGE:       1,2           DEFVALUE:    NA
         	UNITS:       NA            SPARSE:      NO
         	DESCR:       NA"
    DEFVAL      { false }
    ::= { fsIgsMcastChannelStatsEntry 6 }

fsIgsMcastCacBundle OBJECT IDENTIFIER
    ::= { fsigscac 3 }

fsIgsMcastBundleTable OBJECT-TYPE
    SYNTAX      SEQUENCE OF FsIgsMcastBundleEntry
    ACCESS      not-accessible
    STATUS      mandatory
    DESCRIPTION 
        "This table contains Mcast channel Bundle related information which are configured 
         by the user. A Bundle will group number of channels. Each Channel will be associated to
         only one bundle.For associating a channel to a bundle,the bundle should be present.
         ALCATEL NOTE:
         	TABLESIZE:     64
         	DESCR:         NA"
    ::= { fsIgsMcastCacBundle 1 }

fsIgsMcastBundleEntry OBJECT-TYPE
    SYNTAX      FsIgsMcastBundleEntry
    ACCESS      not-accessible
    STATUS      mandatory
    DESCRIPTION 
        "This table contains BundleId,allocated BW,Max group number,Bundle Name,Channel Status 
         and RowStatus which are configured by the user.
         Row creation : This entry can be created by setting the fsIgsMcastCACBundleRowStatus to createandgo(4) with all 
                 necessary parameters.
         Row deletion : This entry can be deleted by setting the fsIgsMcastCACBundleRowStatus to destroy(6).                 
         Index usage : The index is Multicast CAC Bundle Id.
         lexicographical order :  Sorted on Multicast CAC Bundle Id."
    INDEX       { fsIgsMcastCACBundleId }
    ::= { fsIgsMcastBundleTable 1 }

FsIgsMcastBundleEntry ::= SEQUENCE {
    fsIgsMcastCACBundleId                       INTEGER,
    fsIgsMcastCACBundleBandwidth                INTEGER,
    fsIgsMcastCACBundleMaxChannels              INTEGER,
    fsIgsMcastCACBundleName                     OCTET STRING,
    fsIgsMcastCACBundleChannelAssociatedCount   INTEGER,
    fsIgsMcastCACBundleRowStatus                RowStatus
}

fsIgsMcastCACBundleId OBJECT-TYPE
    SYNTAX      INTEGER
    ACCESS      not-accessible
    STATUS      mandatory
    DESCRIPTION 
        "BundleId pertaining to the Multicast channel CAC entry.The maximum number of bundles supported = 64.
         The bundleId ranges from 1 up to 64.
         ALCATEL NOTE:
         	ACCESS:      NA            USAGE:       NA
         	PERSIST:     YES           INSRVMOD:    NA
         	RANGE:       0..64         DEFVALUE:    NA
         	UNITS:       NA            SPARSE:      NO
         	DESCR:       NA"
    ::= { fsIgsMcastBundleEntry 1 }

fsIgsMcastCACBundleBandwidth OBJECT-TYPE
    SYNTAX      INTEGER
    ACCESS      read-write
    STATUS      mandatory
    DESCRIPTION 
        "The max bandwidth allowed for each bundle.When this object is set to zero 
         the CAC bandwidth check functionality will be disabled for this bundle.
         The bandwidth is accepted in kbps.
         ALCATEL NOTE:
         	ACCESS:      NA            USAGE:       OPT
         	PERSIST:     YES           INSRVMOD:    YES
         	RANGE:       NA            DEFVALUE:    NA
         	UNITS:       kbps          SPARSE:      NO
         	DESCR:       NA"
    DEFVAL      { 0 }
    ::= { fsIgsMcastBundleEntry 2 }

fsIgsMcastCACBundleMaxChannels OBJECT-TYPE
    SYNTAX      INTEGER
    ACCESS      read-write
    STATUS      mandatory
    DESCRIPTION 
        "This used to specify the maximum allowed channels per bundle. When this          
         object is set to zero, the CAC channel check functionality will be disabled 
         for this bundle.
         ALCATEL NOTE:
         	ACCESS:      NA            USAGE:       OPT
         	PERSIST:     YES           INSRVMOD:    YES
         	RANGE:       NA            DEFVALUE:    NA
         	UNITS:       NA            SPARSE:      NO
         	DESCR:       NA"
    DEFVAL      { 0 }
    ::= { fsIgsMcastBundleEntry 3 }

fsIgsMcastCACBundleName OBJECT-TYPE
    SYNTAX      OCTET STRING (SIZE(0..32))
    ACCESS      read-write
    STATUS      mandatory
    DESCRIPTION 
        "This is used to specify name for the bundle.The name shall be unique across
         all the bundles and not modifiable once the row is created.This is a mandatory object on 
         creation of a row.If the name of a bundle is not specified,then the row cannot 
         be made active by the agent.
         ALCATEL NOTE:
         	ACCESS:      NA            USAGE:       MAND
         	PERSIST:     YES           INSRVMOD:    YES
         	RANGE:       NA            DEFVALUE:    NA
         	UNITS:       NA            SPARSE:      NO
         	DESCR:       NA"
    ::= { fsIgsMcastBundleEntry 4 }

fsIgsMcastCACBundleChannelAssociatedCount OBJECT-TYPE
    SYNTAX      INTEGER
    ACCESS      read-only
    STATUS      mandatory
    DESCRIPTION 
        "This used to display a count of number of multicast channels that are configured in the bundle.
         Each time a new multicast channel is associated to the bundle, this will be incremented.
         A bundle shall be deleted only if this object value is zero,i.e no multicast channels 
         are presently associated to the bundle.
         ALCATEL NOTE:
         	ACCESS:      NA            USAGE:       NA
         	PERSIST:     NO            INSRVMOD:    NA
         	RANGE:       NA            DEFVALUE:    NA
         	UNITS:       NA            SPARSE:      NO
         	DESCR:       NA"
    ::= { fsIgsMcastBundleEntry 5 }

fsIgsMcastCACBundleRowStatus OBJECT-TYPE
    SYNTAX      RowStatus
    ACCESS      read-write
    STATUS      mandatory
    DESCRIPTION 
        "This object is used to create a new row or delete an
         existing row in this table. The possible valid values are:
                 (1) active
                 (2) not_in_service
                 (4) createdAndGo
                 (5) createdAndWait 
                 (6) destroy
         To create an entry in this table, this object should be set to
         CreateAndGo or CreateAndWait. To delete an entry from this table, RowStatus
         should be set to destroy value by the SNMP manager. 
         
         To create a new row in this table a free bundle should be present.
         The agent can make the row active,only if all mandatory columnar objects like 
         Bundle name have been assigned values. For deleting an existing row from this table,
         the columnar object fsIgsMcastCACBundleChannelAssociatedCount of the conceptual row 
         should have a value of zero,which implies no multicast channels presently associated 
         to the bundle.
         ALCATEL NOTE:
         	ACCESS:      NA            USAGE:       MAND
         	PERSIST:     YES           INSRVMOD:    YES
         	RANGE:       1,2,4,5,6     DEFVALUE:    NA
         	UNITS:       NA            SPARSE:      NO
         	DESCR:       NA"
    ::= { fsIgsMcastBundleEntry 6 }

fsIgsMcastBundleStatsTable OBJECT-TYPE
    SYNTAX      SEQUENCE OF FsIgsMcastBundleStatsEntry
    ACCESS      not-accessible
    STATUS      mandatory
    DESCRIPTION 
        "This table contains Multicast Bundle statistics maintained by LANX for 
         CAC functionality.The statistics are maintained per Bundle basis.
         ALCATEL NOTE:
         	TABLESIZE:64
         	DESCR:NA"
    ::= { fsIgsMcastCacBundle 2 }

fsIgsMcastBundleStatsEntry OBJECT-TYPE
    SYNTAX      FsIgsMcastBundleStatsEntry
    ACCESS      not-accessible
    STATUS      mandatory
    DESCRIPTION 
        "This table contains Bundle statistics i.e joins rejected when CAC condition is 
         not satisfied like InsufficientBundleBW,ExceedsBundleChannelLimit, BW and 
         number of channels occupied by guaranteed and non-guaranteed and a read-write 
         	  object for clearing the statistics counters for the bundle.This table is indexed 
         using bundle id.
         Row creation : This entry can be created by setting the fsIgsMcastCACBundleRowStatus to createandgo(4) with all 
                 necessary parameters.
         Row deletion : This entry can be deleted by setting the fsIgsMcastCACBundleRowStatus to destroy(6). 
         Index usage : The index is Multicast CAC Bundle Id.
         lexicographical order :  Sorted on Multicast CAC Bundle Id."
    INDEX       { fsIgsMcastCACBundleId }
    ::= { fsIgsMcastBundleStatsTable 1 }

FsIgsMcastBundleStatsEntry ::= SEQUENCE {
    fsIgsMcastBundleJoinsRejectedInsuffBundleBW             Counter,
    fsIgsMcastBundleJoinsRejectedExceedsBundleChannelLimit  Counter,
    fsIgsMcastBundleOccupiedBWGuaranteed                    INTEGER,
    fsIgsMcastBundleOccupiedGuaranteed                      INTEGER,
    fsIgsMcastBundleOccupiedBWNonGuaranteed                 INTEGER,
    fsIgsMcastBundleOccupiedNonGuaranteed                   INTEGER,
    fsIgsMcastBundleClearStats                              TruthValue
}

fsIgsMcastBundleJoinsRejectedInsuffBundleBW OBJECT-TYPE
    SYNTAX      Counter
    ACCESS      read-only
    STATUS      mandatory
    DESCRIPTION 
        "Provides statistics of Number of multicast Joins rejected for the non-
         guaranteed Mcast join since Bandwidth is not Available at the Bundle 
         level.
         ALCATEL NOTE:
         	ACCESS:      NA            USAGE:       NA
         	PERSIST:     NO            INSRVMOD:    NA
         	RANGE:       NA            DEFVALUE:    0
         	UNITS:       multicast Joins  SPARSE:      NO
         	DESCR:       NA"
    ::= { fsIgsMcastBundleStatsEntry 1 }

fsIgsMcastBundleJoinsRejectedExceedsBundleChannelLimit OBJECT-TYPE
    SYNTAX      Counter
    ACCESS      read-only
    STATUS      mandatory
    DESCRIPTION 
        "Provides statistics of Number of multicast Joins rejected for the non-
         guaranteed channel entry as max connections at bundle level has reached.
         ALCATEL NOTE:
         	ACCESS:      NA            USAGE:       NA
         	PERSIST:     NO            INSRVMOD:    NA
         	RANGE:       NA            DEFVALUE:    0
         	UNITS:       multicast Joins  SPARSE:      NO
         	DESCR:       NA"
    ::= { fsIgsMcastBundleStatsEntry 2 }

fsIgsMcastBundleOccupiedBWGuaranteed OBJECT-TYPE
    SYNTAX      INTEGER
    ACCESS      read-only
    STATUS      mandatory
    DESCRIPTION 
        "This is the total bandwidth currently occupied by guaranteed channels in 
         that bundle.
         ALCATEL NOTE:
         	ACCESS:      NA            USAGE:       NA
         	PERSIST:     NO            INSRVMOD:    NA
         	RANGE:       NA            DEFVALUE:    NA
         	UNITS:       kbps          SPARSE:      NO
         	DESCR:       NA"
    ::= { fsIgsMcastBundleStatsEntry 3 }

fsIgsMcastBundleOccupiedGuaranteed OBJECT-TYPE
    SYNTAX      INTEGER
    ACCESS      read-only
    STATUS      mandatory
    DESCRIPTION 
        "This is the number of guaranteed channels that are Active in that 
         bundle.
         ALCATEL NOTE:
         	ACCESS:      NA            USAGE:       NA
         	PERSIST:     NO            INSRVMOD:    NA
         	RANGE:       1..1024       DEFVALUE:    NA
         	UNITS:       NA            SPARSE:      NO
         	DESCR:       NA"
    ::= { fsIgsMcastBundleStatsEntry 4 }

fsIgsMcastBundleOccupiedBWNonGuaranteed OBJECT-TYPE
    SYNTAX      INTEGER
    ACCESS      read-only
    STATUS      mandatory
    DESCRIPTION 
        "This is the bandwidth currently occupied by active non guaranteed 
         channels.
         ALCATEL NOTE:
         	ACCESS:      NA            USAGE:       NA
         	PERSIST:     NO            INSRVMOD:    NA
         	RANGE:       NA            DEFVALUE:    NA
         	UNITS:       kbps          SPARSE:      NO
         	DESCR:       NA"
    ::= { fsIgsMcastBundleStatsEntry 5 }

fsIgsMcastBundleOccupiedNonGuaranteed OBJECT-TYPE
    SYNTAX      INTEGER
    ACCESS      read-only
    STATUS      mandatory
    DESCRIPTION 
        "This is the number of active non-guaranteed channels in a  bundle.
         ALCATEL NOTE:
         	ACCESS:      NA            USAGE:       NA
         	PERSIST:     NO            INSRVMOD:    NA
         	RANGE:       1..1024       DEFVALUE:    NA
         	UNITS:       NA            SPARSE:      NO
         	DESCR:       NA"
    ::= { fsIgsMcastBundleStatsEntry 6 }

fsIgsMcastBundleClearStats OBJECT-TYPE
    SYNTAX      TruthValue
    ACCESS      read-write
    STATUS      mandatory
    DESCRIPTION 
        "This object is used to reset the bundle level cac related counters for the given Bundle
         except the counters used to keep active bandwidth and active channel count.
         	  i.e, fsIgsMcastBundleOccupiedBWGuaranteed, fsIgsMcastBundleOccupiedGuaranteed, 
         fsIgsMcastBundleOccupiedBWNonGuaranteed, fsIgsMcastBundleOccupiedNonGuaranteed wont be cleared.
         When this object is set to true(1), counters are cleared. Once resetting action is completed, 
         agent sets the value to false(2). If SNMP Manager sets this object to false(2),agent does not take
         any action. A get operation for this object will always return false(2).
         ALCATEL NOTE:
         	ACCESS:      NA            USAGE:       NA
         	PERSIST:     NO            INSRVMOD:    YES
         	RANGE:       1,2           DEFVALUE:    NA
         	UNITS:       NA            SPARSE:      NO
         	DESCR:       NA"
    DEFVAL      { false }
    ::= { fsIgsMcastBundleStatsEntry 7 }

fsIgsMcastBundleNameTable OBJECT-TYPE
    SYNTAX      SEQUENCE OF FsIgsMcastBundleNameEntry
    ACCESS      not-accessible
    STATUS      mandatory
    DESCRIPTION 
        "The Table displays associated bundle id for a bundle name.
         ALCATEL NOTE:
          	TABLESIZE:   64
          	DESCR:       NA"
    ::= { fsIgsMcastCacBundle 3 }

fsIgsMcastBundleNameEntry OBJECT-TYPE
    SYNTAX      FsIgsMcastBundleNameEntry
    ACCESS      not-accessible
    STATUS      mandatory
    DESCRIPTION 
        "This table contains bundle name and associated bundle id.
         Row creation : This entry can be created by setting the fsIgsMcastCACBundleRowStatus to createandgo(4) with all 
                        necessary parameters.
         Row deletion : This entry can be deleted by setting the fsIgsMcastCACBundleRowStatus to destroy(6).                   
         Index usage : The index is Multicast Bundle Name.
         lexicographical order :  Sorted on Multicast Bundle Name."
    INDEX       { fsIgsMcastBundleName }
    ::= { fsIgsMcastBundleNameTable 1 }

FsIgsMcastBundleNameEntry ::= SEQUENCE {
    fsIgsMcastBundleName    OCTET STRING,
    fsIgsMcastBundleId      INTEGER
}

fsIgsMcastBundleName OBJECT-TYPE
    SYNTAX      OCTET STRING (SIZE(0..32))
    ACCESS      not-accessible
    STATUS      mandatory
    DESCRIPTION 
        "This used to display name for the bundle.
         ALCATEL NOTE:
         	ACCESS:      NA            USAGE:       NA
         	PERSIST:     NO            INSRVMOD:    NA
         	RANGE:       NA            DEFVALUE:    NA
         	UNITS:       NA            SPARSE:      NO
         	DESCR:       NA"
    ::= { fsIgsMcastBundleNameEntry 1 }

fsIgsMcastBundleId OBJECT-TYPE
    SYNTAX      INTEGER
    ACCESS      read-only
    STATUS      mandatory
    DESCRIPTION 
        "BundleId corresponding to the bundle name.
         ALCATEL NOTE:
         	ACCESS:      NA            USAGE:       NA
         	PERSIST:     NO            INSRVMOD:    NA
         	RANGE:       1..64         DEFVALUE:    NA
         	UNITS:       NA            SPARSE:      NO
         	DESCR:       NA"
    ::= { fsIgsMcastBundleNameEntry 2 }

fsIgsMcastBundleAssocClassDIPAddrTable OBJECT-TYPE
    SYNTAX      SEQUENCE OF FsIgsMcastBundleAssocClassDIPAddrEntry
    ACCESS      not-accessible
    STATUS      mandatory
    DESCRIPTION 
        "This table displays the multicast sources associated to a bundle.
         ALCATEL NOTE:
          	TABLESIZE:   1024..4096
          	DESCR:       NA"
    ::= { fsIgsMcastCacBundle 4 }

fsIgsMcastBundleAssocClassDIPAddrEntry OBJECT-TYPE
    SYNTAX      FsIgsMcastBundleAssocClassDIPAddrEntry
    ACCESS      not-accessible
    STATUS      mandatory
    DESCRIPTION 
        "This table contains BundleId, VlanId, source IP address and
         multicast IP address of the  associated channel which is
         configured in the bundle.
         Row creation : This entry can be created by setting the FsIgsMcastSrcRowStatus to createandgo(4) with all 
                 necessary parameters.
         Row deletion : This entry can be deleted by setting the FsIgsMcastSrcRowStatus to destroy(6).              
         Index usage : The indices are Multicast CAC Bundle ID, Multicast Source Vlan ID, Multicast Source Class D IP Address 
                and Multicast Associated Source IP address.
         lexicographical order :  Sorted on Multicast CAC Bundle ID, Multicast Source Vlan ID, Multicast Source Class D IP 
                           Address and Multicast Associated Source IP address"
    INDEX       { fsIgsMcastCACBundleId, fsIgsMcastSrcVlanId, 
                  fsIgsMcastSrcClassDIPAddress, 
                  fsIgsMcastBundleAssocSourceIPAddress }
    ::= { fsIgsMcastBundleAssocClassDIPAddrTable 1 }

FsIgsMcastBundleAssocClassDIPAddrEntry ::= SEQUENCE {
    fsIgsMcastBundleAssocSourceIPAddress    IpAddress
}

fsIgsMcastBundleAssocSourceIPAddress OBJECT-TYPE
    SYNTAX      IpAddress
    ACCESS      read-only
    STATUS      mandatory
    DESCRIPTION 
        "This is equivalent to fsIgsMcastSrcSourceIPAddress in fsIgsMcastSourceTable.
         ALCATEL NOTE:
         	ACCESS:      NA            USAGE:       NA
         	PERSIST:     NO            INSRVMOD:    NA
         	RANGE:       NA            DEFVALUE:    NA
         	UNITS:       NA            SPARSE:      NO
         	DESCR:       NA"
    ::= { fsIgsMcastBundleAssocClassDIPAddrEntry 1 }

END -- end of module IGSCAC-MIB.
