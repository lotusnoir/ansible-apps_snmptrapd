--
-- This SMIv1 module has been generated by smidump 0.4.8. Do not edit.
--

IGS-MIB DEFINITIONS ::= BEGIN

IMPORTS
    PortList
        FROM Q-BRIDGE-MIB
    OBJECT-TYPE
        FROM RFC-1212
    Gauge, IpAddress, enterprises
        FROM RFC1155-SMI
    RowStatus
        FROM SNMPv2-TC;

fsigs OBJECT IDENTIFIER
    ::= { enterprises futuresoftware(2076) 74 }

-- fsigs MODULE-IDENTITY
--     LAST-UPDATED "200203060000Z"
--     ORGANIZATION 
--         "Future Software Private Limited"
--     CONTACT-INFO 
--         "  
--          Postal:     Future Software Pvt. Ltd., 
--                      480-481, Anna Salai, 
--                      Nandanam, 
--                      Chennai, 
--                      India  600 035 
--          Telephone: +91-44-24330550 
--          E-Mail:     support@future.futsoft.com "
--     DESCRIPTION 
--         " The proprietary MIB module for FutureIGS. "
--     REVISION    "200203060000Z"
--     DESCRIPTION 
--         "Revision history updated "
--     ::= { enterprises futuresoftware(2076) 74 }


fsIgsSystem OBJECT IDENTIFIER
    ::= { fsigs 1 }

fsIgsSystemControl OBJECT-TYPE
    SYNTAX      INTEGER { start(1), shutdown(2) }
    ACCESS      read-write
    STATUS      mandatory
    DESCRIPTION 
        "IGMP snooping module is shutdown or restarted through 
         this object. When shutdown, all the resources are  
         released back to the system
         	ALCATEL NOTE:
         ACCESS:      NA           USAGE:       NA
                PERSIST:     YES          INSRVMOD:    YES
          RANGE:       NA           DEFVALUE:    NA
                UNITS:       NA           SPARSE:      NA
         DESCR:       NA"
    DEFVAL      { start }
    ::= { fsIgsSystem 1 }

fsIgsStatus OBJECT-TYPE
    SYNTAX      INTEGER { enabled(1), disabled(2) }
    ACCESS      read-write
    STATUS      mandatory
    DESCRIPTION 
        "Enables or disables IGMP snooping in the system
         ALCATEL NOTE:
         ACCESS:      NA           USAGE:       NA
         PERSIST:     YES          INSRVMOD:    NO
         RANGE:       NA           DEFVALUE:    NA
             UNITS:       NA           SPARSE:      NA
         DESCR:       Bridge module should be UP to set this 
                     object value to enabled(1)"
    DEFVAL      { disabled }
    ::= { fsIgsSystem 2 }

fsIgsSelfIpAddressMode OBJECT-TYPE
    SYNTAX      INTEGER { configure(1), fromIP(2) }
    ACCESS      read-write
    STATUS      mandatory
    DESCRIPTION 
        "Allows to configure the mode through which the source Ip@ used in 
         the generated IGMP messages (for both upstream and downstream) is 
         obtained :
         - Configure : the IP@ configured in the fsIgsSelfIpAddress object 
                       is used as the source IP@.
         - FromIP : the IP@ configured on top of the IP interface is used as 
                    the source IP@. 
                    If there is no IP Address configured or even no IP interface or Interface is not administratively UP, 
                    then it will take the self IP address.
         ALCATEL NOTE:
                 ACCESS:      NA           USAGE:       NA
         PERSIST:     YES          INSRVMOD:    YES
         RANGE:       NA           DEFVALUE:    NA
                 UNITS:       NA           SPARSE:      NA
         DESCR:       NA"
    DEFVAL      { fromIP }
    ::= { fsIgsSystem 3 }

fsIgsSelfIpAddress OBJECT-TYPE
    SYNTAX      IpAddress
    ACCESS      read-write
    STATUS      mandatory
    DESCRIPTION 
        "The IP address used as source IP@ in all IGMP 
         messages generated by the IGS subsystem when the value of
         the fsIgsSelfIpAddressMode object is set to configure.
         The IP address used as source IP@ in all IGMP messages generated by
         the IGS subsystem when the value of the fsIgsSelfIpAddressMode 
         object is set to fromIP but no IP interface or no IP address or interface is not administratively UP 
         has been configured on top of the VLAN for which the IGMP message is generated.
         	ALCATEL NOTE:
         ACCESS:      NA           USAGE:       NA
         PERSIST:     YES                          INSRVMOD:    YES
          RANGE:       0.0.0.0,1.0.0.1 .. 223.255.255.255	DEFVALUE:    NA
         UNITS:       IP address                   SPARSE:      NA
         DESCR:       Ip address in the range 127.0.0.0 .. 127.255.255.255 are invalid."
    DEFVAL      { '00000000'H }
    ::= { fsIgsSystem 4 }

fsIgsTraceOption OBJECT-TYPE
    SYNTAX      INTEGER
    ACCESS      read-write
    STATUS      mandatory
    DESCRIPTION 
        "This object is used to enable Trace Statements in  
         Igmp Snooping Module. 
         
         A FOUR BYTE integer is used for enabling the level of tracing.  
         Each BIT in the four byte integer, represents a particular                level of Trace.  
          
         The maping between the bit positions & the level of trace is as follows:  
                 0 - Init and Shutdown Traces 
                 1 - Management Traces 
                 2 - Data Path Traces 
                 3 - Control Plane Traces 
                 4 - Packet Dump Traces 
                 5 - Traces related to All Resources except Buffers 
                 6 - All Failure Traces 
                 7 - Buffer Traces 
         
         The remaining bits are unused. Combination of levels are  
         also allowed. 
         
         For example if the bits 0 and 1 are set, then the Trace 
         statements related to Init-Shutdown and management  
         will be printed. 
         
         The user has to enter the corresponding INTEGER VALUE for thebits set. 
          For example if bits 0 and 1 are set then user has to  
         give the value 3. 
         	ALCATEL NOTE:
         ACCESS:      NA           USAGE:       NA
         PERSIST:     YES          INSRVMOD:    YES
         RANGE:       0..7         DEFVALUE:    0
         UNITS:       NA           SPARSE:      NA
         DESCR:       NA"
    ::= { fsIgsSystem 5 }

fsIgsRouterPortPurgeInterval OBJECT-TYPE
    SYNTAX      INTEGER (1..900)
    ACCESS      read-write
    STATUS      mandatory
    DESCRIPTION 
        "This is the interval (in seconds) after which a learnt  
         (dynamic) router port entry will be purged.  
         
         For each (dynamic) router port learnt, a 'RouterPortPurgeTimer' 
         runs for 'RouterPortPurgeInterval'. 
         
         This timer will be restarted whenever a General Mutlicast Query (GMQ)  
         is received over that port. If no GMQ messages are received  
         for 'RouterPortPurgeInterval' time, the learnt (dynamic) router 
         port entry will be purged  
         
         	ALCATEL NOTE:
                 ACCESS:      NA           USAGE:       NA
         PERSIST:     YES          INSRVMOD:    YES
                 RANGE:       NA           DEFVALUE:    NA
         UNITS:       seconds      SPARSE:      NA
         DESCR:       NA"
    DEFVAL      { 125 }
    ::= { fsIgsSystem 6 }

fsIgsHostPortPurgeInterval OBJECT-TYPE
    SYNTAX      INTEGER (12..1825)
    ACCESS      read-write
    STATUS      mandatory
    DESCRIPTION 
        "This is the interval (in seconds) after which a learnt  
         host port entry will be purged.  
         
         For each host port learnt, a 'PortPurgeTimer' runs for  
         'HostPortPurgeInterval'. 
         
         This timer will be restarted whenever a report message from host is  
         received over that port. If no report messages are received  
         for 'HostPortPurgeInterval' time, the learnt host entry  
         will be purged from the multicast group 
         	ALCATEL NOTE:
         ACCESS:      NA           USAGE:       NA
         PERSIST:     YES          INSRVMOD:    YES
         RANGE:       NA           DEFVALUE:    NA
                 UNITS:       seconds      SPARSE:      NA
         DESCR:       NA"
    DEFVAL      { 260 }
    ::= { fsIgsSystem 7 }

fsIgsLeaveResponseTimerTable OBJECT-TYPE
    SYNTAX      SEQUENCE OF FsIgsLeaveResponseTimerEntry
    ACCESS      not-accessible
    STATUS      mandatory
    DESCRIPTION 
        "This table sets the Leave Response
         Timer on a per VLAN basis.
         	ALCATEL NOTE:
         		TABLESIZE: 4094 
                 	DESCR:	NA"
    ::= { fsIgsSystem 9 }

fsIgsLeaveResponseTimerEntry OBJECT-TYPE
    SYNTAX      FsIgsLeaveResponseTimerEntry
    ACCESS      not-accessible
    STATUS      mandatory
    DESCRIPTION 
        "Contains Vlan Id , Vlan Leave Response Timer.
         Row creation : Entries shall be created when vlan is created.
         Row deletion : Entries shall be deleted when vlan is deleted.
         Index usage : the index is the fsIgsLeaveResponseVlanId.
         Note that entries will be presented to the SNMP manager in full
         lexicographical order :  sorted on fsIgsLeaveResponseVlanId."
    INDEX       { fsIgsLeaveResponseVlanId }
    ::= { fsIgsLeaveResponseTimerTable 1 }

FsIgsLeaveResponseTimerEntry ::= SEQUENCE {
    fsIgsLeaveResponseVlanId    INTEGER,
    fsIgsLeaveResponseTimer     INTEGER
}

fsIgsLeaveResponseVlanId OBJECT-TYPE
    SYNTAX      INTEGER (1..4094)
    ACCESS      not-accessible
    STATUS      mandatory
    DESCRIPTION 
        " Vlan Id .
         ALCATEL NOTE:
         ACCESS:      NA           USAGE:       MAND
         PERSIST:     YES          INSRVMOD:    YES
             RANGE:       NA           DEFVALUE:    NA
         UNITS:       NA           SPARSE:      NO
             DESCR:       NA"
    ::= { fsIgsLeaveResponseTimerEntry 1 }

fsIgsLeaveResponseTimer OBJECT-TYPE
    SYNTAX      INTEGER (0..10)
    ACCESS      read-write
    STATUS      mandatory
    DESCRIPTION 
        "This is the maximum response time (in seconds) for the Group Specific Query message.
         When the value of this object is configured /= 0, 
         the switch will send fsIgsVlanRetryCount times a Group Specific Query 
         before (upon no reply from the host side) removing the port from 
         the forwarding database and generating a leave message towards the
         network side. It sends a leave message to upstream only if it is a last user.
         When the value of this object is configured = 0, the switch will 
         immediately apply fast leave i.e. will immediately remove the port 
         from the forwarding database and will immediately generate a leave  
         message towards the network side only if is a last user.   
         
         In case fsIgsVlanMode is set to enhancedperf the value of this 
         object is autonomously set to 0 and cannot be changed by the            
         operator : always fast leave is applied for the coloured proxy.
            ALCATEL NOTE:
          ACCESS:      NA           USAGE:       OPT
         PERSIST:     YES          INSRVMOD:    NO
         RANGE:       NA           DEFVALUE:    NA
         	    UNITS:       seconds      SPARSE:      NO
         DESCR:       Leave Response timer value will be always zero for 
                      enhanced performance vlan."
    DEFVAL      { 1 }
    ::= { fsIgsLeaveResponseTimerEntry 2 }

fsIgsMaxMulticastLearn OBJECT-TYPE
    SYNTAX      INTEGER (0..1024)
    ACCESS      read-write
    STATUS      mandatory
    DESCRIPTION 
        "This is the MAX number of Multicast entry LANX can learn for Channel context CAC.If this object
         is set to zero multicast channel context CAC is disabled.
         This Object is depend on 
               - fsIgsMcastMaxCACBandWidth     (fsigscac.mib)
               - fsIgsMaxNonConfiguredMulticastLearn (fsigscac.mib)
         
         	ALCATEL NOTE:
         ACCESS:      NA           USAGE:       NA
         PERSIST:     YES          INSRVMOD:    YES
         RANGE:       NA           DEFVALUE:    NA
                UNITS:       NA           SPARSE:      NA
               DESCR:Setting of dependency scalar objects with non-dependent objects is not recommended in a single PDU.
               This object is dependent on fsIgsMcastMaxCACBandWidth and fsIgsMaxNonConfiguredMulticastLearn"
    DEFVAL      { 0 }
    ::= { fsIgsSystem 10 }

fsIgsActiveMulticastEntries OBJECT-TYPE
    SYNTAX      INTEGER (0..1024)
    ACCESS      read-only
    STATUS      mandatory
    DESCRIPTION 
        "This is the number of active Multicast entries that
         are present in the IGS database. This includes both 
         static and dynamic entries present in the system.
         	ALCATEL NOTE:
         ACCESS:      NA           USAGE:       NA
         PERSIST:     NA           INSRVMOD:    NA
                RANGE:       NA           DEFVALUE:    NA
         UNITS:       NA           SPARSE:      NA
                DESCR:       NA"
    DEFVAL      { 0 }
    ::= { fsIgsSystem 11 }

fsIgsGlobalLeaveMessageStatus OBJECT-TYPE
    SYNTAX      INTEGER { enabled(1), disabled(2) }
    ACCESS      read-write
    STATUS      mandatory
    DESCRIPTION 
        "Enables or disables sending IGMP global leave messages
         when the LANX state changes from standby to active for every VLAN.
          ALCATEL NOTE:
          ACCESS:      NA           USAGE:       NA
         PERSIST:     YES          INSRVMOD:    YES
         RANGE:       NA           DEFVALUE:    NA
         UNITS:       NA           SPARSE:      NA
         DESCR:       NA"
    DEFVAL      { enabled }
    ::= { fsIgsSystem 13 }

fsIgsReducedResponseInterval OBJECT-TYPE
    SYNTAX      INTEGER (1..255)
    ACCESS      read-write
    STATUS      mandatory
    DESCRIPTION 
        "This timer is used to respond a report with in the 
         fsIgsReducedResponseInterval after receiving first GMQ's by LANX.
         Actually the applied interval shall be the minimum of the message 
         response interval and reduced response interval.
         The object fsIgsReducedResponseInterval expressed in seconds.
         ALCATEL NOTE:
           ACCESS:      NA                  USAGE:       NA
          PERSIST:     YES                 INSRVMOD:    YES
          RANGE:       NA                  DEFVALUE:    NA
          UNITS:       seconds             SPARSE:      NA
          DESCR:       NA"
    DEFVAL      { 125 }
    ::= { fsIgsSystem 15 }

fsIgsClearStats OBJECT-TYPE
    SYNTAX      INTEGER (0..4094)
    ACCESS      read-write
    STATUS      mandatory
    DESCRIPTION 
        "This field is used  to clear all the IGMP statistics for the given Vlan.
         In display, it always displays the vlan id as 1.
         When this object is set with 0 it will clear IGMP statistics of all vlans.
          ALCATEL NOTE:
          ACCESS:      NA           USAGE:       NA
         PERSIST:     NO           INSRVMOD:    YES
         RANGE:       NA           DEFVALUE:    1
         UNITS:       NA           SPARSE:      NA
         DESCR:       NA"
    ::= { fsIgsSystem 16 }

fsIgsRemoveRootTimer OBJECT-TYPE
    SYNTAX      INTEGER (0..128)
    ACCESS      read-write
    STATUS      mandatory
    DESCRIPTION 
        "This is the interval (in seconds) for which LANX will wait for 
         removing multicast root in the hardware after sending the leave message to router.
          ALCATEL NOTE:
          ACCESS:      NA           USAGE:       NA
         PERSIST:     YES          INSRVMOD:    YES
         RANGE:       NA           DEFVALUE:    NA
         UNITS:       seconds      SPARSE:      NA
         DESCR:       NA"
    DEFVAL      { 2 }
    ::= { fsIgsSystem 17 }

fsIgsMcastFlooding OBJECT-TYPE
    SYNTAX      INTEGER { enabled(1), disabled(2) }
    ACCESS      read-write
    STATUS      mandatory
    DESCRIPTION 
        "- By default all VLAN's are configured with 'FLOOD_UNKNOWN'.
         - If joins are received for leaf nodes, for which root is available in hw and sw, 
             leaf is updated in hw and sw immediately.
         
         Enabled case
             1.	No BulkSync of multicast forward table to Standby 
             2.	During set to Active: Removes the IGMP Filter.
                3. During set to Standby: Removes the IGMP Filter.
                4. Start of Hot Reset: 
                       a. Removes the IGMP filter (if already present), so that all 
                     IGMP Packets are transparently flooded to the 
                     user/network side and not lifted to the CPU.
                 b.	No ipmc entries in Hardware
                5. After completion of Hot Reset:
                       a. Re-inserts the IGMP filter.
                 b.	No ipmc entries in Hardware.
                 c.	Sends GMQ.
                 d.	Waits for max.response time, then configures all IGS 
                     entries (static and new entries) to  BCM hardware.              
         
         Disabled case
             1.	BulkSync of multicast forward table to Standby with STATIC, 
                 DYNAMIC and STATIC_DYNAMIC entries.
             2.	During set to Active: Installs the IGMP Filter.
               3. During set to Standby: Removes the IGMP Filter.
               4. Start of Hot Reset: 
                 a.	Remove IGMP filter (if already present), so that all
                     IGMP packets are transparently flooded to the user/network  
                     side and not lifted to the CPU.
                 b.	STATIC and dynamic entries will be available in hardware.
             5.	completion of Hot Reset:
                      a. Re-inserts the IGMP filter.
                 b.	STATIC and dynamic entries will be available in hardware.
                 c.	Sends GMQ
                 d.	Waits for max.response time, then configures all new 
                     mcast entries (root entries) to BCM hardware
         
         
         Note:  For boards which doesn't support Hitless Redundancy the default value will be 
               maintained as 'disabled' (this is taken care in the implementation).  For these boards SET 
               to 'enable' will be returned 'Failure' with error code 'Hitless Redundancy Not Supported'.
         
         ALCATEL NOTE:
         ACCESS	:   NA           	USAGE		:    NA
         PERSIST:   Yes          	INSRVMOD	:    NA
         RANGE	:   NA           	DEFVALUE	:   enabled 
         UNITS	:   NA           	SPARSE		:    NA
         DESCR	:   NA"
    DEFVAL      { enabled }
    ::= { fsIgsSystem 18 }

fsIgsBrg OBJECT IDENTIFIER
    ::= { fsigs 2 }

fsIgsVlan OBJECT IDENTIFIER
    ::= { fsigs 3 }

fsIgsVlanMcastFwdTable OBJECT-TYPE
    SYNTAX      SEQUENCE OF FsIgsVlanMcastFwdEntry
    ACCESS      not-accessible
    STATUS      mandatory
    DESCRIPTION 
        "This table contains VLAN based multicast forwarding 
         information learnt when VLAN is ENABLED in the system. 
         ALCATEL NOTE:
         TABLESIZE: 1024  
         DESCR:	NA"
    ::= { fsIgsVlan 1 }

fsIgsVlanMcastFwdEntry OBJECT-TYPE
    SYNTAX      FsIgsVlanMcastFwdEntry
    ACCESS      not-accessible
    STATUS      mandatory
    DESCRIPTION 
        "This table contains VlanId, multicast group  IP address and the  
         list of ports who have members for the multicast group.  
         Row creation : Entries can only be created dynamically.
         Row deletion : Entries can ony be deleted dynamically.
         Index usage : The index is the fsIgsVlanMcastFwdVlanId  and fsIgsVlanMcastFwdGroupAddress.
         Note that entries will be presented to the SNMP manager in full
         lexicographical order :  sorted on fsIgsVlanMcastFwdVlanId and fsIgsVlanMcastFwdGroupAddress."
    INDEX       { fsIgsVlanMcastFwdVlanId, fsIgsVlanMcastFwdGroupAddress }
    ::= { fsIgsVlanMcastFwdTable 1 }

FsIgsVlanMcastFwdEntry ::= SEQUENCE {
    fsIgsVlanMcastFwdVlanId             INTEGER,
    fsIgsVlanMcastFwdGroupAddress       IpAddress,
    fsIgsVlanMcastFwdPortList           PortList,
    fsIgsVlanMcastFwdConfigStatus       INTEGER,
    fsIgsVlanMcastFwdSourceIPAddress    IpAddress
}

fsIgsVlanMcastFwdVlanId OBJECT-TYPE
    SYNTAX      INTEGER (1..4094)
    ACCESS      not-accessible
    STATUS      mandatory
    DESCRIPTION 
        "Vlan Id pertaining to the Multicast forwarding entry
         ALCATEL NOTE:
            ACCESS:      NA           USAGE:       NA
               PERSIST:     NO           INSRVMOD:    NA
            RANGE:       NA           DEFVALUE:    NA
            UNITS:       NA           SPARSE:      NO
            DESCR:       NA"
    ::= { fsIgsVlanMcastFwdEntry 1 }

fsIgsVlanMcastFwdGroupAddress OBJECT-TYPE
    SYNTAX      IpAddress
    ACCESS      not-accessible
    STATUS      mandatory
    DESCRIPTION 
        "IP multicast group address.
         ALCATEL NOTE:
            ACCESS:      NA           USAGE:       NA
               PERSIST:     NO           INSRVMOD:    NA
            RANGE:       NA           DEFVALUE:    NA
            UNITS:       NA           SPARSE:      NO
            DESCR:       NA"
    ::= { fsIgsVlanMcastFwdEntry 2 }

fsIgsVlanMcastFwdPortList OBJECT-TYPE
    SYNTAX      PortList
    ACCESS      read-only
    STATUS      mandatory
    DESCRIPTION 
        "List of ports who have members for the  multicast  
         group and the Vlan Id.
         ALCATEL NOTE:
         ACCESS:      NA           USAGE:       NA
         PERSIST:     NO           INSRVMOD:    NA
         RANGE:       NA           DEFVALUE:    NA
         UNITS:       NA           SPARSE:      NO
         DESCR:       NA"
    ::= { fsIgsVlanMcastFwdEntry 3 }

fsIgsVlanMcastFwdConfigStatus OBJECT-TYPE
    SYNTAX      INTEGER { dynamic(2), staticDynamic(3) }
    ACCESS      read-only
    STATUS      mandatory
    DESCRIPTION 
        "If the multicast stream is dynamically learnt then the
         fsIgsVlanMcastFwdConfigStatus is displayed as dynamic.
         If multicast entry is configured as static using the table fsIgsVlanStaticMcastFwdTable and after 
         that the same entry as learnt as dynamic, then the
         fsIgsVlanMcastFwdConfigStatus is displayed as staticDynamic.
         ALCATEL NOTE:
         ACCESS:      NA           USAGE:       NA
         PERSIST:     NO           INSRVMOD:    NA
         RANGE:       NA           DEFVALUE:    NA
         UNITS:       NA           SPARSE:      NO
         DESCR:       NA"
    ::= { fsIgsVlanMcastFwdEntry 4 }

fsIgsVlanMcastFwdSourceIPAddress OBJECT-TYPE
    SYNTAX      IpAddress
    ACCESS      read-only
    STATUS      mandatory
    DESCRIPTION 
        "This is the Source IP Address for multicast stream, learned
         through control plane. This will take non-zero values for SSM
         signaling and zero for ASM signaling  
         
         ALCATEL NOTE:
         ACCESS:      NA                    USAGE:       NA
         PERSIST:     NO                    INSRVMOD:    NA
         RANGE:0.0.0.0 .. 255.255.255.255   DEFVALUE:    NA
         UNITS:       IP Address            SPARSE:      NO
         DESCR:       NA"
    ::= { fsIgsVlanMcastFwdEntry 6 }

fsIgsVlanRouterPortTable OBJECT-TYPE
    SYNTAX      SEQUENCE OF FsIgsVlanRouterPortEntry
    ACCESS      not-accessible
    STATUS      mandatory
    DESCRIPTION 
        "This table serves two purposes :
         1) For network topologies in which for the same VLAN, multiple 
            edge routers are connected to the iSAM and which use the LANX 
            switch as the LAN interface to perform querier election, it 
            allows to configure statically the router ports through which 
            the edge routers are reachable.
            This operation mode is only applicable to a VLAN for which the 
            fsIgsVlanMode is set to ProxyReporting. The configstatus can only be set to static. 
         2) For all other network topologies, the IGS system autonomously 
            creates an entry for each dynamically learnt router port.
         ALCATEL NOTE:
          TABLESIZE: DEP 
         DESCR:	 DEP(TABLESIZE):The size of the table is derived from the 
         		       total number of IP interfaces in the system .
         		       The total number of IP interfaces in the system  is obtained from the
         		       object fsVrfMaxIpInterfaces in fsvrf.mib"
    ::= { fsIgsVlan 2 }

fsIgsVlanRouterPortEntry OBJECT-TYPE
    SYNTAX      FsIgsVlanRouterPortEntry
    ACCESS      not-accessible
    STATUS      mandatory
    DESCRIPTION 
        "Contains VlanId of router, reachable router ports.
         Row creation : Entries shall be created in one step by a set-request 
                       with all necessary parameter values and 
         		fsIgsVlanRouterPortRowStatus set to createAndGo(4).
         Row deletion : Entries shall be deleted by setting fsIgsVlanRouterPortRowStatus
                       to destroy(6).
         Index usage : The index is the fsIgsVlanRouterPortVlanId and fsIgsVlanRouterPort.
         Note that entries will be presented to the SNMP manager in full
         lexicographical order :  sorted on fsIgsVlanRouterPortVlanId and fsIgsVlanRouterPort."
    INDEX       { fsIgsVlanRouterPortVlanId, fsIgsVlanRouterPort }
    ::= { fsIgsVlanRouterPortTable 1 }

FsIgsVlanRouterPortEntry ::= SEQUENCE {
    fsIgsVlanRouterPortVlanId           INTEGER,
    fsIgsVlanRouterPort                 INTEGER,
    fsIgsVlanRouterPortConfigStatus     INTEGER,
    fsIgsVlanRouterPortRowStatus        RowStatus
}

fsIgsVlanRouterPortVlanId OBJECT-TYPE
    SYNTAX      INTEGER (1..4094)
    ACCESS      not-accessible
    STATUS      mandatory
    DESCRIPTION 
        "Vlan Id  through which the edge routers are 
         reachable. 
         ALCATEL NOTE:
         ACCESS:      NA           USAGE:       NA
         PERSIST:     YES          INSRVMOD:    NA
         RANGE:       NA           DEFVALUE:    NA
         UNITS:       NA           SPARSE:      NO
         DESCR:       NA"
    ::= { fsIgsVlanRouterPortEntry 1 }

fsIgsVlanRouterPort OBJECT-TYPE
    SYNTAX      INTEGER (1..2147483647)
    ACCESS      not-accessible
    STATUS      mandatory
    DESCRIPTION 
        "The bridge port through which an edge router, 
         in a particular VLAN, is reachable.
         
         ALCATEL NOTE:
         ACCESS:      NA	        USAGE:       NA
         PERSIST:     YES          	INSRVMOD:    NA
         RANGE:       DEP           	DEFVALUE:    NA
         UNITS:       NA           	SPARSE:      NO
         DESCR:       DEP(RANGE):The range of the index is maximum number of physical interfaces
         			    available in the system. This is obtained from the object 
         			    issSystemNumberOfPorts in fsiss.mib"
    ::= { fsIgsVlanRouterPortEntry 2 }

fsIgsVlanRouterPortConfigStatus OBJECT-TYPE
    SYNTAX      INTEGER { static(1), dynamic(2), staticDynamic(3) }
    ACCESS      read-write
    STATUS      mandatory
    DESCRIPTION 
        "1) Static router ports created by the operator shall get 
         assigned a fsIgsVlanRouterPortConfigStatus = static.
         2) Dynamic router ports learnt by the IGS system shall get 
         assigned a fsIgsVlanRouterPortConfigStatus = dynamic.
         3) From the moment a GMQ is received at a statically created 
         router port, the fsIgsVlanRouterPortConfigStatus is changed 
         from static to staticDynamic and the router port purge 
         interval is started.
         4) Upon the expiry of the router port purge interval :
         - in case it concerns a dynamically created router port (i.e. 
           fsIgsVlanRouterPortConfigStatus = dynamic), the entry is 
           removed.
         - in case it concerns a statically created router port (i.e. 
           fsIgsVlanRouterPortConfigStatus = staticdynamic), the 
           fsIgsVlanRouterPortConfigStatus is changed from 
           staticdynamic to static.
         ALCATEL NOTE:
         ACCESS:      NA           USAGE:       OPT
         PERSIST:     YES          INSRVMOD:    YES
         RANGE:       NA           DEFVALUE:    NA
         UNITS:       NA           SPARSE:      NO
         DESCR:       NA"
    ::= { fsIgsVlanRouterPortEntry 3 }

fsIgsVlanRouterPortRowStatus OBJECT-TYPE
    SYNTAX      RowStatus
    ACCESS      read-write
    STATUS      mandatory
    DESCRIPTION 
        "An IGMP snooping static router port entry can be created                   or deleted by using this variable. The four operations                  'Create and go', Create and wait', active and destroy
         have been Supported.
         ALCATEL NOTE:
         ACCESS:      NA           USAGE:       MAND
         PERSIST:     YES          INSRVMOD:    YES
         RANGE:       4,5,6        DEFVALUE:    NA
         UNITS:       NA           SPARSE:      NO
         DESCR:       NA"
    ::= { fsIgsVlanRouterPortEntry 5 }

fsIgsVlanFilterTable OBJECT-TYPE
    SYNTAX      SEQUENCE OF FsIgsVlanFilterEntry
    ACCESS      not-accessible
    STATUS      mandatory
    DESCRIPTION 
        "This table contains configuration to disable IGMP snooping                on specific Vlans. This Table is valid only when VLAN is  
         enabled in the system.
         ALCATEL NOTE:
         TABLESIZE:  4094
         DESCR:    NA"
    ::= { fsIgsVlan 3 }

fsIgsVlanFilterEntry OBJECT-TYPE
    SYNTAX      FsIgsVlanFilterEntry
    ACCESS      not-accessible
    STATUS      mandatory
    DESCRIPTION 
        "Contains Vlan Id , Vlan Filter Status.
         Row creation : Entry is created when nmhSetDot1qVlanStaticRowStatus is set to active(1).
         Row deletion : Entry is deleted when nmhSetDot1qVlanStaticRowStatus is set to destroy(6).
         Index usage : The index is the vlan id.
         Note that entries will be presented to the SNMP manager in full
         lexicographical order :  sorted on fsIgsVlanFilterVlanId."
    INDEX       { fsIgsVlanFilterVlanId }
    ::= { fsIgsVlanFilterTable 1 }

FsIgsVlanFilterEntry ::= SEQUENCE {
    fsIgsVlanFilterVlanId               INTEGER,
    fsIgsVlanFilterStatus               INTEGER,
    fsIgsVlanVersion                    INTEGER,
    fsIgsVlanMode                       INTEGER,
    fsIgsVlanSelfIpAddressMode          INTEGER,
    fsIgsVlanSelfIpAddress              IpAddress,
    fsIgsVlanQuerier                    INTEGER,
    fsIgsVlanQueryInterval              INTEGER,
    fsIgsv2VlanMaxResponseTime          INTEGER,
    fsIgsv3VlanMaxResponseTime          INTEGER,
    fsIgsVlanMaxV3AllowedGrps           INTEGER,
    fsIgsReportAcptOnAllPorts           INTEGER,
    fsIgsVlanRobustnessVar              INTEGER,
    fsIgsVlanUnsolicitedReportInterval  INTEGER,
    fsIgsVlanRetryCount                 INTEGER
}

fsIgsVlanFilterVlanId OBJECT-TYPE
    SYNTAX      INTEGER (1..4094)
    ACCESS      not-accessible
    STATUS      mandatory
    DESCRIPTION 
        " Vlan Id for which IGMP snooping feature is to be 
         enabled/disabled.
         ALCATEL NOTE:
         ACCESS:      NA           USAGE:       NA
         PERSIST:     YES          INSRVMOD:    NA
         RANGE:       NA           DEFVALUE:    NA
         UNITS:       NA           SPARSE:      NO
         DESCR:       NA"
    ::= { fsIgsVlanFilterEntry 1 }

fsIgsVlanFilterStatus OBJECT-TYPE
    SYNTAX      INTEGER { enabled(1), disabled(2) }
    ACCESS      read-write
    STATUS      mandatory
    DESCRIPTION 
        "When status is set as enabled, IGMP snooping feature 
         is disabled for that Vlan Id.  
         When status is set as disabled, IGMP snooping feature 
         remains enabled for that Vlan.
         ALCATEL NOTE:
          ACCESS:      NA           USAGE:       MAND
         PERSIST:     YES          INSRVMOD:    YES
         RANGE:       NA           DEFVALUE:    NA
         UNITS:       NA           SPARSE:      NO
         DESCR:       NA"
    DEFVAL      { disabled }
    ::= { fsIgsVlanFilterEntry 2 }

fsIgsVlanVersion OBJECT-TYPE
    SYNTAX      INTEGER { igmpv2(1), igmpv3(2) }
    ACCESS      read-write
    STATUS      mandatory
    DESCRIPTION 
        "This object can be set only if fsIgsVlanFilterStatus is set
         to enabled, IGMP snooping feature is disbled for that Vlan Id.
         Indicates the operating IGMP version of the IGMP snooping switch 
         for a specific VLAN. The default operating IGMP version on a
         specific VLAN is IGMP version 3 i.e, igmpV3(3) 
         The fsIgsVlanVersion shall  be configured consistently 
         with the  IGMP version configured on the 
         edge router(s) present in the VLAN. 
         
         Lanx shall drop IGMP packets, when packet version is 
         greater from the configured IGMP version for this VLAN.
         
         The IGMP packets generated by LANX (generate GMQ's etc..) shall
         have the version as configured for the VLAN.
          ALCATEL NOTE:
          ACCESS:      NA           USAGE:       OPT
         PERSIST:     YES          INSRVMOD:    YES
         RANGE:       NA           DEFVALUE:    NA
         UNITS:       NA           SPARSE:      NO
         DESCR:       NA"
    DEFVAL      { igmpv3 }
    ::= { fsIgsVlanFilterEntry 3 }

fsIgsVlanMode OBJECT-TYPE
    SYNTAX      INTEGER { enhancedperf(1), proxyreporting(2) }
    ACCESS      read-write
    STATUS      mandatory
    DESCRIPTION 
        "This object can only be set if fsIgsVlanFilterStatus is set 
         to enabled, IGMP snooping feature is disbled for that Vlan Id.
         When this object is configured as EnhancedPerf,
         the IGMP system runs in the Transparent Snooper with enhanced 
         performance mode (coloured proxy) in 
         this particular VLAN.
         
         When this object is configured as 
         proxyReporting, the IGMP system runs in the 
         Snooper with Proxy reporting mode in this particular 
         Vlan.
         When the operator changes the mode from Proxyreporting to 
         EnhancedPerf then all static router ports for this vlan (if 
         existing will autonomously be removed by the IGMP System.
         ALCATEL NOTE:
          ACCESS:      NA           USAGE:       OPT
         PERSIST:     YES          INSRVMOD:    YES
         RANGE:       NA           DEFVALUE:    NA
         UNITS:       NA           SPARSE:      NO
         DESCR:       NA"
    DEFVAL      { proxyreporting }
    ::= { fsIgsVlanFilterEntry 4 }

fsIgsVlanSelfIpAddressMode OBJECT-TYPE
    SYNTAX      INTEGER { configure(1), fromIP(2), inherit(3) }
    ACCESS      read-write
    STATUS      mandatory
    DESCRIPTION 
        "Allows to configure the mode through which the source Ip@ used in 
         the generated IGMP messages (for bot upstream and downstream) is 
         obtained :
         - Configure : the IP@ configured in the fsIgsVlanSelfIpAddress 
                       object is used as the source IP@.
         - FromIP : the IP@ configured on top of the IP interface is used as 
                    the source IP@. This mode can only be set on the 
                    condition that an IP interface + ACTIVE IP @ has been 
                    created on top of this particular VLAN. In case lateron, 
                    either the IP@ status is changed to PASSIVE or the IP 
                    interface or IP address is deleted, the system will autonomously 
                    change this object to the value inherit. 
         - Inherit : the SelfIpAddressMode is inherited from the system level object i.e. fsIgsSelfIpAddressMode.
         ALCATEL NOTE:
          ACCESS:      NA           USAGE:       OPT
         PERSIST:     YES          INSRVMOD:    YES
         RANGE:       NA           DEFVALUE:    NA
         UNITS:       NA           SPARSE:      NO
         DESCR:       NA"
    DEFVAL      { inherit }
    ::= { fsIgsVlanFilterEntry 5 }

fsIgsVlanSelfIpAddress OBJECT-TYPE
    SYNTAX      IpAddress
    ACCESS      read-write
    STATUS      mandatory
    DESCRIPTION 
        "The IP address used as source IP@ in all IGMP 
         messages generated (for both upstream and downstream direction) by 
         the IGS subsystem when the value of
         the fsIgsVlanSelfIpAddressMode object is set to configure. 
          ALCATEL NOTE:
          ACCESS:      NA                           USAGE:       OPT
         PERSIST:     YES                          INSRVMOD:    YES
         RANGE:       0.0.0.0,1.0.0.1 .. 223.255.255.255  DEFVALUE:    NA
         UNITS:       IP address                          SPARSE:      NO
         DESCR:       Ip address in the range 127.0.0.0 .. 127.255.255.255 is invalid."
    DEFVAL      { '00000000'H }
    ::= { fsIgsVlanFilterEntry 6 }

fsIgsVlanQuerier OBJECT-TYPE
    SYNTAX      INTEGER { enabled(1), disabled(2) }
    ACCESS      read-write
    STATUS      mandatory
    DESCRIPTION 
        "This object is only valid when the fsIgsVlanMode is configured as 
         ProxyReporting. 
         Incase of Transparent snooping with enhanced performance mode, 
         this object will be displayed as  enabled and cannot be 
         modified by the operator.
         The snooping switch can be configured to send IGMP queries when no
         IGMP routers are present in the VLAN. When set to enabled the 
         switch will generate general query messages. The query messages 
         will be relayed if the switch receives a query message from
         any other router in the VLAN.
          ALCATEL NOTE:
          ACCESS:      NA           USAGE:       OPT
         PERSIST:     YES          INSRVMOD:    YES
         RANGE:       NA           DEFVALUE:    NA
         UNITS:       NA           SPARSE:      NO
         DESCR:       NA"
    DEFVAL      { disabled }
    ::= { fsIgsVlanFilterEntry 7 }

fsIgsVlanQueryInterval OBJECT-TYPE
    SYNTAX      INTEGER (60..600)
    ACCESS      read-write
    STATUS      mandatory
    DESCRIPTION 
        "This is the interval (in seconds) in which LANX will wait to send 
         the query message when acting as a querier. This timer will be 
         restarted whenever a query message is sent from the LANX.
          ALCATEL NOTE:
          ACCESS:      NA           USAGE:       OPT
         PERSIST:     YES          INSRVMOD:    YES
         RANGE:       NA           DEFVALUE:    NA
         UNITS:       seconds      SPARSE:      NO
         DESCR:       NA"
    DEFVAL      { 125 }
    ::= { fsIgsVlanFilterEntry 8 }

fsIgsv2VlanMaxResponseTime OBJECT-TYPE
    SYNTAX      INTEGER (1..25)
    ACCESS      read-write
    STATUS      mandatory
    DESCRIPTION 
        "The max response time (is expressed in seconds) inserted in the GMQ messages.
         This object will be used if the IGMP version of Vlan is configured as 
         IGMPv2.
         When Lanx starts up or changes from standby to active state (switch over),
         GMQ's are sent to the ASAM and subtending ports with Max Response Time 
         as 25 seconds instead of the configured value    
          ALCATEL NOTE:
          ACCESS:      NA                   USAGE:       OPT
         PERSIST:     YES                  INSRVMOD:    YES
         RANGE:       NA                   DEFVALUE:    NA
         UNITS:       seconds              SPARSE:      NO
         DESCR:       NA"
    DEFVAL      { 25 }
    ::= { fsIgsVlanFilterEntry 9 }

fsIgsv3VlanMaxResponseTime OBJECT-TYPE
    SYNTAX      INTEGER (1..600)
    ACCESS      read-write
    STATUS      mandatory
    DESCRIPTION 
        "The max response time (is expressed in seconds) inserted in the GMQ messages.
         This object will be used if the IGMP version of Vlan is 
          configured as IGMPv3.    
         When Lanx starts up or changes from standby to active state (switch over),
         GMQ's are sent to the ASAM and subtending ports with Max Response Time 
         as 25 seconds instead of the configured value    
          ALCATEL NOTE:
          ACCESS:      NA                   USAGE:       OPT
         PERSIST:     YES                  INSRVMOD:    YES
         RANGE:       NA                   DEFVALUE:    NA
         UNITS:       seconds              SPARSE:      NO
         DESCR:       NA"
    DEFVAL      { 125 }
    ::= { fsIgsVlanFilterEntry 10 }

fsIgsVlanMaxV3AllowedGrps OBJECT-TYPE
    SYNTAX      INTEGER (0..10)
    ACCESS      read-write
    STATUS      mandatory
    DESCRIPTION 
        "This object is used to send maximum number of allowed groups 
         per generated igmpv3 report on reception of GMQ's by LANX.
         The maximum number of reports shall be expressed as 2expN value(N=0 to 10). 
         This makes that the number of records included in a membership reports shall 
         be one of the following values : 1, 2, 4, 8, 16, 32, 64, 128, 256, 512, 1024.
         This value will be bounded by the MTU size.
          ALCATEL NOTE:
          ACCESS:      NA          USAGE:       OPT
         PERSIST:     YES         INSRVMOD:    YES
         RANGE:       NA          DEFVALUE:    NA
         UNITS:       NA          SPARSE:      NO
         DESCR:       NA"
    DEFVAL      { 3 }
    ::= { fsIgsVlanFilterEntry 11 }

fsIgsReportAcptOnAllPorts OBJECT-TYPE
    SYNTAX      INTEGER { enabled(1), disabled(2) }
    ACCESS      read-write
    STATUS      mandatory
    DESCRIPTION 
        "IGMP snooping module accepts reports/leave messages by default on Host network ports.
         When this object is set to enabled, IGMP can accept reports/leaves from all the host network ports.
         When this object is set to  disabled, IGMP can not accept report/leaves from the network ports.
          ALCATEL NOTE:
          ACCESS:      NA             USAGE:       OPT
         PERSIST:     YES            INSRVMOD:    YES
         RANGE:       NA             DEFVALUE:    NA
         UNITS:       NA             SPARSE:      NO
         DESCR:       NA"
    DEFVAL      { enabled }
    ::= { fsIgsVlanFilterEntry 12 }

fsIgsVlanRobustnessVar OBJECT-TYPE
    SYNTAX      INTEGER (1..10)
    ACCESS      read-write
    STATUS      mandatory
    DESCRIPTION 
        "When a host joins a multicast group, it should send unsolicited Membership Report 
         for that group, in case if it is the first member of that group.There is also a
         possibility of the report getting lost or damaged. so the unsolicited report is sent
         again after unsolicited report interval. The value of this object gives the
          number of times the unsolicited report should be sent on the network.
         For the performance issue, the default value is set to 1 instead of the standard recommends.
          ALCATEL NOTE:
          ACCESS:      NA            USAGE:       OPT
         PERSIST:     YES           INSRVMOD:    YES
         RANGE:       NA            DEFVALUE:    NA
         UNITS:       NA            SPARSE:      NO
         DESCR:       NA"
    DEFVAL      { 1 }
    ::= { fsIgsVlanFilterEntry 13 }

fsIgsVlanUnsolicitedReportInterval OBJECT-TYPE
    SYNTAX      INTEGER (1..255)
    ACCESS      read-write
    STATUS      mandatory
    DESCRIPTION 
        "This is the interval (in seconds) after which the Unsolicited Membership Report
         is sent.  For each Report (if it is the first report for this multicast group),
         a ReportTimer runs for UnsolicitedReportInterval. This timer will be restarted
         whenever the Robustness value for that group is greater than one.
         ALCATEL NOTE:
         ACCESS:      NA            USAGE:       OPT
         PERSIST:     YES           INSRVMOD:    YES
         RANGE:       NA            DEFVALUE:    NA
         UNITS:       seconds       SPARSE:      NO
         DESCR:       NA"
    DEFVAL      { 10 }
    ::= { fsIgsVlanFilterEntry 14 }

fsIgsVlanRetryCount OBJECT-TYPE
    SYNTAX      INTEGER (0..10)
    ACCESS      read-write
    STATUS      mandatory
    DESCRIPTION 
        "This timer is used when IGMP proxyreporting is enabled.
         When the switch receives leave message on a port, it
         sends group specific query to check if there any other 
         interested receivers for the group. This attribute defines 
         the maximum number of queries sent by the switch before deleting 
         the port from the group membership information in the forwarding 
         database. If the maximum retry count exceeds 'fsIgsVlanRetryCount', 
         then the port will be deleted from the multicast group membership
         information in the forwarding database and received leave message
         will be forwarded onto the router ports if there are no 
         interested receivers for the group.
         when this object is set to 0, It will use robustness(fsIgsVlanRobustnessVar) 
         value as the retry count 
          ALCATEL NOTE:
          ACCESS:      NA            USAGE:       OPT
         PERSIST:     YES           INSRVMOD:    YES
         RANGE:       NA            DEFVALUE:    NA
         UNITS:       NA            SPARSE:      NO
         DESCR:       NA"
    DEFVAL      { 0 }
    ::= { fsIgsVlanFilterEntry 15 }

fsIgsVlanStaticMcastFwdTable OBJECT-TYPE
    SYNTAX      SEQUENCE OF FsIgsVlanStaticMcastFwdEntry
    ACCESS      not-accessible
    STATUS      mandatory
    DESCRIPTION 
        "This table contains VLAN based multicast forwarding 
         information which is configured statically by the user.
         ALCATEL NOTE:
         TABLESIZE:  1024
         DESCR: NA"
    ::= { fsIgsVlan 4 }

fsIgsVlanStaticMcastFwdEntry OBJECT-TYPE
    SYNTAX      FsIgsVlanStaticMcastFwdEntry
    ACCESS      not-accessible
    STATUS      mandatory
    DESCRIPTION 
        "This table contains VlanId, multicast group Ip address and the  
         list of ports who have members for the multicast group which is
         configured statically by the user
          Row creation : Entries shall be created in one step by a set-request 
                        with all necessary parameter values and 
         		fsIgsVlanStaticMcastFwdRowStatus set to createAndGo(4).
         Row deletion : Entries shall be deleted by setting fsIgsVlanStaticMcastFwdRowStatus
                        to destroy(6). Entries can only be deleted if there is atleast
                        one member port in the group.
         Index usage : The index is vlan id and multicast group address.
         Note that entries will be presented to the SNMP manager in full
         lexicographical order :  sorted on fsIgsVlanStaticMcastFwdVlanId and fsIgsVlanStaticMcastFwdGroupAddress."
    INDEX       { fsIgsVlanStaticMcastFwdVlanId, 
                  fsIgsVlanStaticMcastFwdGroupAddress }
    ::= { fsIgsVlanStaticMcastFwdTable 1 }

FsIgsVlanStaticMcastFwdEntry ::= SEQUENCE {
    fsIgsVlanStaticMcastFwdVlanId           INTEGER,
    fsIgsVlanStaticMcastFwdGroupAddress     IpAddress,
    fsIgsVlanStaticMcastFwdPortList         PortList,
    fsIgsVlanStaticMcastFwdRowStatus        RowStatus,
    fsIgsVlanStaticMcastFwdConfigStatus     INTEGER
}

fsIgsVlanStaticMcastFwdVlanId OBJECT-TYPE
    SYNTAX      INTEGER (1..4094)
    ACCESS      not-accessible
    STATUS      mandatory
    DESCRIPTION 
        "Vlan Id pertaining to the Static Multicast forwarding entry.
         ALCATEL NOTE:
             ACCESS:      NA           USAGE:       NA
             PERSIST:     YES          INSRVMOD:    NA
                RANGE:       NA            DEFVALUE:    NA
             UNITS:       NA           SPARSE:      NO
             DESCR:       NA"
    ::= { fsIgsVlanStaticMcastFwdEntry 1 }

fsIgsVlanStaticMcastFwdGroupAddress OBJECT-TYPE
    SYNTAX      IpAddress
    ACCESS      not-accessible
    STATUS      mandatory
    DESCRIPTION 
        "IP multicast group address of the Statically configured 
         Multicast Forwarding entry.
         ALCATEL NOTE:
         ACCESS:      NA           USAGE:       NA
         PERSIST:     YES          INSRVMOD:    NA
         RANGE:       NA  	      DEFVALUE:    NA
         UNITS:       IP address    SPARSE:      NO
         DESCR:       NA"
    ::= { fsIgsVlanStaticMcastFwdEntry 2 }

fsIgsVlanStaticMcastFwdPortList OBJECT-TYPE
    SYNTAX      PortList
    ACCESS      read-write
    STATUS      mandatory
    DESCRIPTION 
        "List of ports who have members for the Static multicast  
         group and the Vlan Id.
          ALCATEL NOTE:
         ACCESS:      NA           USAGE:       OPT
         PERSIST:     YES           INSRVMOD:    YES
         RANGE:       NA            DEFVALUE:    NA
              UNITS:       NA           SPARSE:      NO
         DESCR:       NA"
    ::= { fsIgsVlanStaticMcastFwdEntry 3 }

fsIgsVlanStaticMcastFwdRowStatus OBJECT-TYPE
    SYNTAX      RowStatus
    ACCESS      read-write
    STATUS      mandatory
    DESCRIPTION 
        "An IGMP snooping static multicast group entry can be 
         created or deleted by using this variable. Four 
         operations CreateAndGo, CreateAndWait, active and destroy
         have been supported.
         ALCATEL NOTE:
         ACCESS:      NA           USAGE:       MAND
           PERSIST:     YES          INSRVMOD:    YES
         RANGE:       1,4,5,6      DEFVALUE:    NA
           UNITS:       NA           SPARSE:      NO
         DESCR:       NA"
    ::= { fsIgsVlanStaticMcastFwdEntry 4 }

fsIgsVlanStaticMcastFwdConfigStatus OBJECT-TYPE
    SYNTAX      INTEGER { static(1), staticDynamic(3) }
    ACCESS      read-only
    STATUS      mandatory
    DESCRIPTION 
        "The entry is added will be in static mode. 
         The entry can be in staticDynamic, which means that 
         	    entry was statically created but its learnt later or
         	    vice-versa.
          ALCATEL NOTE:
         ACCESS:      NA           USAGE:       NA
              PERSIST:     NO           INSRVMOD:    NA
         RANGE:       NA           DEFVALUE:    1
              UNITS:       NA           SPARSE:      NO
         DESCR:       NA"
    ::= { fsIgsVlanStaticMcastFwdEntry 5 }

fsIgsStats OBJECT IDENTIFIER
    ::= { fsigs 4 }

fsIgsStatsTable OBJECT-TYPE
    SYNTAX      SEQUENCE OF FsIgsStatsEntry
    ACCESS      not-accessible
    STATUS      mandatory
    DESCRIPTION 
        "This table contains IGMP snooping statistics  
         maintained by the switch. The statistics are
         maintained on a per VLAN basis.
          ALCATEL NOTE:
          TABLESIZE: 4094 
         DESCR: NA"
    ::= { fsIgsStats 1 }

fsIgsStatsEntry OBJECT-TYPE
    SYNTAX      FsIgsStatsEntry
    ACCESS      not-accessible
    STATUS      mandatory
    DESCRIPTION 
        "Contains IGMP snooping statistics for a particular VLAN.
         Row creation : Entry is created when nmhSetDot1qVlanStaticRowStatus is set to active(1).
         Row deletion : Entry is deleted when nmhSetDot1qVlanStaticRowStatus is set to destroy(6).
         Index usage : The index is the vlan id.
         Note that entries will be presented to the SNMP manager in full
         lexicographical order :  sorted on fsIgsStatsVlanId."
    INDEX       { fsIgsStatsVlanId }
    ::= { fsIgsStatsTable 1 }

FsIgsStatsEntry ::= SEQUENCE {
    fsIgsStatsVlanId                    INTEGER,
    fsIgsStatsRxGenQueries              INTEGER,
    fsIgsStatsRxGrpQueries              INTEGER,
    fsIgsStatsRxGrpAndSrcQueries        INTEGER,
    fsIgsStatsRxIgmpReports             INTEGER,
    fsIgsStatsRxIgmpv3Reports           INTEGER,
    fsIgsStatsRxIgmpv3IsInMsgs          INTEGER,
    fsIgsStatsRxIgmpv3IsExMsgs          INTEGER,
    fsIgsStatsRxIgmpv3ToInMsgs          INTEGER,
    fsIgsStatsRxIgmpv3ToExMsgs          INTEGER,
    fsIgsStatsRxIgmpv3AllowMsgs         INTEGER,
    fsIgsStatsRxIgmpv3BlockMsgs         INTEGER,
    fsIgsStatsRxIgmpLeaves              INTEGER,
    fsIgsStatsTxGenQueries              INTEGER,
    fsIgsStatsTxGrpQueries              INTEGER,
    fsIgsStatsTxIgmpReports             INTEGER,
    fsIgsStatsTxIgmpv3Reports           INTEGER,
    fsIgsStatsTxIgmpLeaves              INTEGER,
    fsIgsStatsIgmpDroppedPkts           INTEGER,
    fsIgsStatsTxGSSQ                    INTEGER,
    fsIgsStatsSourceIPAddressMismatch   INTEGER
}

fsIgsStatsVlanId OBJECT-TYPE
    SYNTAX      INTEGER (1..4094)
    ACCESS      not-accessible
    STATUS      mandatory
    DESCRIPTION 
        " VLAN ID for which IGMP snooping statistics are displayed.
         ALCATEL NOTE:
         ACCESS:      NA            USAGE:       NA
         PERSIST:     NO            INSRVMOD:    NA
         RANGE:       NA            DEFVALUE:    NA
         UNITS:       NA            SPARSE:      NO
         DESCR:       NA"
    ::= { fsIgsStatsEntry 1 }

fsIgsStatsRxGenQueries OBJECT-TYPE
    SYNTAX      INTEGER
    ACCESS      read-only
    STATUS      mandatory
    DESCRIPTION 
        "Provides statistics of General Queries received by the
         snooping switch on the network port. 
         This object will be incremented for every General Query received for the Vlan.
         The statistics includes number of received non-coloured and coloured GMQ by OBC from
         network side / hub (ring) iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 2 }

fsIgsStatsRxGrpQueries OBJECT-TYPE
    SYNTAX      INTEGER
    ACCESS      read-only
    STATUS      mandatory
    DESCRIPTION 
        "Provides statistics of Group Specific Queries received
         by the snooping switch on the network port.
         This object will be incremented for every Group Specific Query received for the Vlan.
         The statistics includes number of received non-coloured and coloured GSQ by OBC from
         network side / hub (ring) iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 3 }

fsIgsStatsRxGrpAndSrcQueries OBJECT-TYPE
    SYNTAX      INTEGER
    ACCESS      read-only
    STATUS      mandatory
    DESCRIPTION 
        "Provides statistics of Group And Source Specific Queries
         received by the snooping switch on the network port.
         This object will be incremented for every Group And Source Specific Query received for the Vlan.
         The statistics includes number of received non-coloured and coloured GSSQ by OBC from
         network side / hub (ring) iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 4 }

fsIgsStatsRxIgmpReports OBJECT-TYPE
    SYNTAX      INTEGER
    ACCESS      read-only
    STATUS      mandatory
    DESCRIPTION 
        "Provides statistics of IGMPv1/IGMPv2 Membership reports
         received by the snooping switch on the host port.
         The statistics includes number of received non-coloured and coloured IGMP reports by OBC from LT /
         subtending iSAM / ring iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 5 }

fsIgsStatsRxIgmpv3Reports OBJECT-TYPE
    SYNTAX      INTEGER
    ACCESS      read-only
    STATUS      mandatory
    DESCRIPTION 
        "Provides statistics of IGMPv3 Membership reports
         received by the snooping switch on the host port.
         The statistics includes number of received non-coloured and coloured IGMPv3 reports by OBC from LT /
         subtending iSAM / ring iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 6 }

fsIgsStatsRxIgmpv3IsInMsgs OBJECT-TYPE
    SYNTAX      INTEGER
    ACCESS      read-only
    STATUS      mandatory
    DESCRIPTION 
        "Provides statistics of IGMPv3 Membership reports
         of type IS_IN received by the snooping switch on the host port.
         The statistics includes number of received non-coloured and coloured IGMP reports by OBC from LT /
         subtending iSAM / ring iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 7 }

fsIgsStatsRxIgmpv3IsExMsgs OBJECT-TYPE
    SYNTAX      INTEGER
    ACCESS      read-only
    STATUS      mandatory
    DESCRIPTION 
        "Provides statistics of IGMPv3 Membership reports
         of type IS_EX received by the snooping switch on the host port.
         The statistics includes number of received non-coloured and coloured IGMP reports by OBC from LT /
         subtending iSAM / ring iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 8 }

fsIgsStatsRxIgmpv3ToInMsgs OBJECT-TYPE
    SYNTAX      INTEGER
    ACCESS      read-only
    STATUS      mandatory
    DESCRIPTION 
        "Provides statistics of IGMPv3 Membership reports
         of type TO_IN received by the snooping switch on the host port.
         The statistics includes number of received non-coloured and coloured IGMP reports by OBC from LT /
         subtending iSAM / ring iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 9 }

fsIgsStatsRxIgmpv3ToExMsgs OBJECT-TYPE
    SYNTAX      INTEGER
    ACCESS      read-only
    STATUS      mandatory
    DESCRIPTION 
        "Provides statistics of IGMPv3 Membership reports
         of type TO_EX received by the snooping switch on the host port.
         The statistics includes number of received non-coloured and coloured IGMP reports by OBC from LT /
         subtending iSAM / ring iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 10 }

fsIgsStatsRxIgmpv3AllowMsgs OBJECT-TYPE
    SYNTAX      INTEGER
    ACCESS      read-only
    STATUS      mandatory
    DESCRIPTION 
        "Provides statistics of IGMPv3 Membership reports
         of type ALLOW received by the snooping switch on the host port.
         The statistics includes number of received non-coloured and coloured IGMP reports by OBC from LT /
         subtending iSAM / ring iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 11 }

fsIgsStatsRxIgmpv3BlockMsgs OBJECT-TYPE
    SYNTAX      INTEGER
    ACCESS      read-only
    STATUS      mandatory
    DESCRIPTION 
        "Provides statistics of IGMPv3 Membership reports
         of type BLOCK received by the snooping switch on the host port.
         The statistics includes number of received non-coloured and coloured IGMP reports by OBC from LT /
         subtending iSAM / ring iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 12 }

fsIgsStatsRxIgmpLeaves OBJECT-TYPE
    SYNTAX      INTEGER
    ACCESS      read-only
    STATUS      mandatory
    DESCRIPTION 
        "Provides statistics of IGMPv2 Leave messages    
         received by the snooping switch on the host port.
         The statistics includes number of received non-coloured and coloured IGMPv2 leaves by OBC from LT /
         subtending iSAM / ring iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 13 }

fsIgsStatsTxGenQueries OBJECT-TYPE
    SYNTAX      INTEGER
    ACCESS      read-only
    STATUS      mandatory
    DESCRIPTION 
        "Provides statistics of General Queries transmitted by the
         snooping switch on the network port when it is acts as a querier.
         The statistics includes number of generated non-coloured and coloured IGMP GMQ by OBC from LT /
         subtending iSAM / ring iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 14 }

fsIgsStatsTxGrpQueries OBJECT-TYPE
    SYNTAX      INTEGER
    ACCESS      read-only
    STATUS      mandatory
    DESCRIPTION 
        "Provides statistics of Group Specific Queries transmitted
         by the snooping switch on the network port.
         The statistics includes number of generated non-coloured and coloured IGMP GSQ by OBC from LT /
         subtending iSAM / ring iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 15 }

fsIgsStatsTxIgmpReports OBJECT-TYPE
    SYNTAX      INTEGER
    ACCESS      read-only
    STATUS      mandatory
    DESCRIPTION 
        "Provides statistics of IGMPv1/IGMPv2 Membership reports
         transmitted by the snooping switch on the network port.
         This object will be incremented for every IGMPv1/IGMPv2 Membership report sent 
         by LANX for the Vlan for all the ports.
         The statistics includes number of generated non-coloured and coloured IGMP reports by OBC from LT /
         subtending iSAM / ring iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 16 }

fsIgsStatsTxIgmpv3Reports OBJECT-TYPE
    SYNTAX      INTEGER
    ACCESS      read-only
    STATUS      mandatory
    DESCRIPTION 
        "Provides statistics of IGMPv3 Membership reports
         transmitted by the snooping switch on the network port.
         This object will be incremented for every IGMPv3 Membership report sent 
         by LANX for the Vlan for all the ports.
         The statistics includes number of generated non-coloured and coloured IGMPv3 reports by OBC from LT /
         subtending iSAM / ring iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 17 }

fsIgsStatsTxIgmpLeaves OBJECT-TYPE
    SYNTAX      INTEGER
    ACCESS      read-only
    STATUS      mandatory
    DESCRIPTION 
        "Provides statistics of IGMPv2 Leave messages    
         transmitted by the snooping switch on the network port.
         This object will be incremented for every IGMPv2 Leave message sent 
         by LANX for the Vlan for all the ports.
         The statistics includes number of generated non-coloured and coloured IGMP v2 leaves by OBC from LT /
         subtending iSAM / ring iSAM.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 18 }

fsIgsStatsIgmpDroppedPkts OBJECT-TYPE
    SYNTAX      INTEGER
    ACCESS      read-only
    STATUS      mandatory
    DESCRIPTION 
        "Provides the number of erroneous IGMP packets dropped
         by the snooping switch due to failure in IGMP checksum 
         calculation Or Maximum multicast entries are exhausted.
         The statistics includes both  non-coloured and coloured messages dropped by OBC.
          ALCATEL NOTE:
          ACCESS:      NA            USAGE:       NA
         PERSIST:     NO            INSRVMOD:    NA
         RANGE:       NA            DEFVALUE:    NA
         UNITS:       NA            SPARSE:      NO
         DESCR:       NA"
    ::= { fsIgsStatsEntry 19 }

fsIgsStatsTxGSSQ OBJECT-TYPE
    SYNTAX      INTEGER
    ACCESS      read-only
    STATUS      mandatory
    DESCRIPTION 
        "Provides the number of GSSQ packets trasnsmitted
         by SHUB. 
         ALCATEL NOTE:
         ACCESS:      NA           USAGE:       NA
         PERSIST:     NO           INSRVMOD:    NA
         RANGE:       NA           DEFVALUE:    NA
         UNITS:       NA           SPARSE:      NO
         DESCR:       NA"
    ::= { fsIgsStatsEntry 20 }

fsIgsStatsSourceIPAddressMismatch OBJECT-TYPE
    SYNTAX      INTEGER
    ACCESS      read-only
    STATUS      mandatory
    DESCRIPTION 
        "Provides the number of dropped IGMP packet due
         to Source IP Address mismatch 
         ALCATEL NOTE:
         ACCESS:      NA           USAGE:       NA
         PERSIST:     NO           INSRVMOD:    NA
         RANGE:       NA           DEFVALUE:    NA
         UNITS:       NA           SPARSE:      NO
         DESCR:       NA"
    ::= { fsIgsStatsEntry 21 }

fsIgsEnhancedPerformance OBJECT IDENTIFIER
    ::= { fsigs 5 }

fsIgsVlanEnhancedPerformanceTable OBJECT-TYPE
    SYNTAX      SEQUENCE OF FsIgsVlanEnhancedPerformanceEntry
    ACCESS      not-accessible
    STATUS      mandatory
    DESCRIPTION 
        "This table contains configuration to specific to the EnhancedPerformance IGMP snooping feature.
         ALCATEL NOTE:
         TABLESIZE: NA
         DESCR: No seperate tables are maintained for enhanced performance vlan."
    ::= { fsIgsEnhancedPerformance 1 }

fsIgsVlanEnhancedPerformanceEntry OBJECT-TYPE
    SYNTAX      FsIgsVlanEnhancedPerformanceEntry
    ACCESS      not-accessible
    STATUS      mandatory
    DESCRIPTION 
        "Contains Vlan Id , Vlan Filter Status.
         Row creation : Entry is created when fsIgsVlanMode is set to enhancedperf(1).
         Row deletion : Entry is deleted when fsIgsVlanMode is set to proxyreporting(2).
         Index usage : The index is the fsIgsVlanEnhancedPerformanceVlanId.
         Note that entries will be presented to the SNMP manager in full
         lexicographical order :  sorted on fsIgsVlanEnhancedPerformanceVlanId."
    INDEX       { fsIgsVlanEnhancedPerformanceVlanId }
    ::= { fsIgsVlanEnhancedPerformanceTable 1 }

FsIgsVlanEnhancedPerformanceEntry ::= SEQUENCE {
    fsIgsVlanEnhancedPerformanceVlanId          INTEGER,
    fsIgsVlanEnhancedPerformancePktFwdState     INTEGER
}

fsIgsVlanEnhancedPerformanceVlanId OBJECT-TYPE
    SYNTAX      INTEGER (1..4094)
    ACCESS      not-accessible
    STATUS      mandatory
    DESCRIPTION 
        " Vlan Id for which IGMP snooping feature with the EnhancedPerformance is enabled.
         ALCATEL NOTE:
         ACCESS:      NA            USAGE:       NA
         PERSIST:     NO            INSRVMOD:    NA
         RANGE:       NA            DEFVALUE:    NA
         UNITS:       NA            SPARSE:      NO
         DESCR:       NA"
    ::= { fsIgsVlanEnhancedPerformanceEntry 1 }

fsIgsVlanEnhancedPerformancePktFwdState OBJECT-TYPE
    SYNTAX      INTEGER { enabled(1), disabled(2) }
    ACCESS      read-write
    STATUS      mandatory
    DESCRIPTION 
        " If it configured as enabled, the coloured the report messages will be forward in the upstream.
         If it is configured as disabled the coloured report messages will not be forwarded in the upstream.
         This object can be set if IGMP mode of the VLAN is enhanced performance mode.
          ALCATEL NOTE:
          ACCESS:      NA            USAGE:       OPT
         PERSIST:     YES           INSRVMOD:    YES
         RANGE:       NA            DEFVALUE:    NA
         UNITS:       NA            SPARSE:      NO
         DESCR:       NA"
    DEFVAL      { disabled }
    ::= { fsIgsVlanEnhancedPerformanceEntry 2 }

END -- end of module IGS-MIB.
