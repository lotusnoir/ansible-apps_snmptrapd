--
-- This SMIv1 module has been generated by smidump 0.4.8. Do not edit.
--

FUTUREIP-MIB DEFINITIONS ::= BEGIN

IMPORTS
    OBJECT-TYPE
        FROM RFC-1212
    Counter, Gauge, IpAddress, enterprises
        FROM RFC1155-SMI
    DisplayString, RowStatus, TruthValue
        FROM SNMPv2-TC
    lanxVrfId
        FROM VRF-MIB;

futureip OBJECT IDENTIFIER
    ::= { enterprises futuresoftware(2076) 2 }

-- futureip MODULE-IDENTITY
--     LAST-UPDATED "200208080000Z"
--     ORGANIZATION 
--         "FUTURE SOFTWARE LIMITED"
--     CONTACT-INFO 
--         " FUTURE SOFTWARE PVT. LIMITED
--          481 Mount Road
--           Madras - 600 035
--          Phone : +91-44-433 055 0 
--          support@futsoft.com"
--     DESCRIPTION 
--         " This mib module is for FutureIP module"
--     REVISION    "200208080000Z"
--     DESCRIPTION 
--         "The initial revision of this MIB module was published as
--          RFC 1450."
--     ::= { enterprises futuresoftware(2076) 2 }


fsip OBJECT IDENTIFIER
    ::= { futureip 1 }

fsIpInLengthErrors OBJECT-TYPE
    SYNTAX      Counter
    ACCESS      read-only
    STATUS      mandatory
    DESCRIPTION 
        "Total number of packets received by IP with length less
         than IP header length.
         ALCATEL NOTE:
         ACCESS:      NA           USAGE:       NA
         PERSIST:     NO           INSRVMOD:    NA
         RANGE:       NA           DEFVALUE:    0       
         UNITS:       packets      SPARSE:      NA
         DESCR:       NA"
    ::= { fsip 1 }

fsIpInCksumErrors OBJECT-TYPE
    SYNTAX      Counter
    ACCESS      read-only
    STATUS      mandatory
    DESCRIPTION 
        "Total Number of received packets those failed to pass
         checksum verification.
         ALCATEL NOTE:
         ACCESS:      NA           USAGE:       NA
         PERSIST:     NO           INSRVMOD:    NA
         RANGE:       NA           DEFVALUE:    0       
         UNITS:       packets      SPARSE:      NA
         DESCR:       NA"
    ::= { fsip 2 }

fsIpInVersionErrors OBJECT-TYPE
    SYNTAX      Counter
    ACCESS      read-only
    STATUS      mandatory
    DESCRIPTION 
        "Total number of received packets with different IP
         version from this entity.
         ALCATEL NOTE:
         ACCESS:      NA           USAGE:       NA
         PERSIST:     NO           INSRVMOD:    NA
         RANGE:       NA           DEFVALUE:    0       
         UNITS:       packets      SPARSE:      NA
         DESCR:       NA"
    ::= { fsip 3 }

fsIpInTTLErrors OBJECT-TYPE
    SYNTAX      Counter
    ACCESS      read-only
    STATUS      mandatory
    DESCRIPTION 
        "Number of IP packets received at this entity with
         'Time to Live' field equal to ZERO
         ALCATEL NOTE:
         ACCESS:      NA           USAGE:       NA
         PERSIST:     NO           INSRVMOD:    NA
         RANGE:       NA           DEFVALUE:    0       
         UNITS:       packets      SPARSE:      NA
         DESCR:       NA"
    ::= { fsip 4 }

fsIpInOptionErrors OBJECT-TYPE
    SYNTAX      Counter
    ACCESS      read-only
    STATUS      mandatory
    DESCRIPTION 
        "Number of IP packets received with improper options.
         ALCATEL NOTE:
             ACCESS:      NA           USAGE:       NA
             PERSIST:     NO           INSRVMOD:    NA
             RANGE:       NA           DEFVALUE:    0       
             UNITS:       packets      SPARSE:      NA
             DESCR:       NA"
    ::= { fsip 5 }

fsIpInBroadCasts OBJECT-TYPE
    SYNTAX      Counter
    ACCESS      read-only
    STATUS      mandatory
    DESCRIPTION 
        "Total number of IP broadcast packets received at this
         entity.
         ALCATEL NOTE:
         ACCESS:      NA           USAGE:       NA
         PERSIST:     NO           INSRVMOD:    NA
         RANGE:       NA           DEFVALUE:    0       
         UNITS:       packets      SPARSE:      NA
         DESCR:       NA"
    ::= { fsip 6 }

fsIpOutGenErrors OBJECT-TYPE
    SYNTAX      Counter
    ACCESS      read-only
    STATUS      mandatory
    DESCRIPTION 
        "Number of outgoing IP packets rejected due to general
         problems like interface down, forwarding disabled etc.
         ALCATEL NOTE:
         ACCESS:      NA           USAGE:       NA
         PERSIST:     NO           INSRVMOD:    NA
         RANGE:       NA           DEFVALUE:    0       
         UNITS:       packets      SPARSE:      NA
         DESCR:       NA"
    ::= { fsip 7 }

fsIpRouteCacheAge OBJECT-TYPE
    SYNTAX      INTEGER (1..3600)
    ACCESS      read-write
    STATUS      mandatory
    DESCRIPTION 
        " Route Cache  Age in seconds.
         ALCATEL NOTE:
             ACCESS:      NA           USAGE:       NA
             PERSIST:     YES          INSRVMOD:    YES
             RANGE:       NA           DEFVALUE:    NA    
             UNITS:       seconds      SPARSE:      NA
             DESCR:       NA"
    DEFVAL      { 180 }
    ::= { fsip 8 }

fsIpNumMultipath OBJECT-TYPE
    SYNTAX      INTEGER (1..16)
    ACCESS      read-write
    STATUS      mandatory
    DESCRIPTION 
        "The number of multi-paths in the routing table.
         ALCATEL NOTE:
             ACCESS:      NA           USAGE:       NA
             PERSIST:     YES          INSRVMOD:    YES
             RANGE:       NA           DEFVALUE:    NA    
             UNITS:       NA           SPARSE:      NA
             DESCR:       NA"
    DEFVAL      { 2 }
    ::= { fsip 10 }

fsIpLoadShareEnable OBJECT-TYPE
    SYNTAX      INTEGER { enabled(1), disabled(2) }
    ACCESS      read-write
    STATUS      mandatory
    DESCRIPTION 
        "Enabling this will distribute the load among
         available equal cost multi-paths.
         ALCATEL NOTE:
         ACCESS:      NA           USAGE:       NA
         PERSIST:     YES          INSRVMOD:    YES
         RANGE:       NA           DEFVALUE:    NA    
         UNITS:       NA           SPARSE:      NA
         DESCR:       NA"
    DEFVAL      { disabled }
    ::= { fsip 11 }

fsIpEnablePMTUD OBJECT-TYPE
    SYNTAX      INTEGER { enabled(1), disabled(2) }
    ACCESS      read-write
    STATUS      mandatory
    DESCRIPTION 
        "This Object Enables or Disables PMTU-D on all paths 
         globally. This MIB Object overrides the route-based and
         application-level requests for PMTU-D. When this object
         is set to disabled (2), PMTU-D is not done even if the 
         application requests to do so.
         ALCATEL NOTE:
         ACCESS:      NA           USAGE:       NA
         PERSIST:     NA           INSRVMOD:    NA
         RANGE:       NA           DEFVALUE:    NA
         UNITS:       NA	        SPARSE:      NA
         DESCR:       This object is not used by Alcatel"
    DEFVAL      { disabled }
    ::= { fsip 12 }

fsIpPmtuEntryAge OBJECT-TYPE
    SYNTAX      INTEGER (5..255)
    ACCESS      read-write
    STATUS      mandatory
    DESCRIPTION 
        "This object specifies the timeout in minutes, after which
         the estimate of a PMTU is considered stale. After the 
         configured minutes the estimate of the PMTU is increased.
         When Set to inifinity (255), detection in increase of 
         PMTU is not done.
         ALCATEL NOTE:
         ACCESS:      NA           USAGE:       NA
         PERSIST:     NA           INSRVMOD:    NA
         RANGE:       NA           DEFVALUE:    NA
         UNITS:       NA	        SPARSE:      NA
         DESCR:       This object is not used by Alcatel"
    DEFVAL      { 10 }
    ::= { fsip 13 }

fsIpPmtuTableSize OBJECT-TYPE
    SYNTAX      INTEGER (1..65535)
    ACCESS      read-write
    STATUS      mandatory
    DESCRIPTION 
        "PMTU-D Table size can be changed with this object.
         Changing the value of this object causes PMTU-D to 
         reboot. The module alone is restarted with the new 
         table size.
         ALCATEL NOTE:
         ACCESS:      NA           USAGE:       NA
         PERSIST:     NA           INSRVMOD:    NA
         RANGE:       NA           DEFVALUE:    NA
         UNITS:       NA	        SPARSE:      NA
         DESCR:       This object is not used by Alcatel"
    DEFVAL      { 10 }
    ::= { fsip 14 }

fsIpPingTable OBJECT-TYPE
    SYNTAX      SEQUENCE OF FsIpPingEntry
    ACCESS      not-accessible
    STATUS      mandatory
    DESCRIPTION 
        "This entity's IP Ping  Table.
         ALCATEL NOTE:
           TABLESIZE:  1
         	  DESCR: 	  NA"
    ::= { fsip 15 }

fsIpPingEntry OBJECT-TYPE
    SYNTAX      FsIpPingEntry
    ACCESS      not-accessible
    STATUS      mandatory
    DESCRIPTION 
        "Contains the information about a particular IP ping
         Operation.
         Row creation : Entry can be created by the setting any of the read-write 
         objects of fsIpPing Table.
         Row deletion : Entry can be deleted by Setting fsIpPingAdminStatus to off(2).
         Index usage : the index is the fsIpPingDest.
         Note that entries will be presented to the SNMP manager in full
         lexicographical order :  sorted on fsIpPingDest."
    INDEX       { fsIpPingDest }
    ::= { fsIpPingTable 1 }

FsIpPingEntry ::= SEQUENCE {
    fsIpPingDest            IpAddress,
    fsIpPingAdminStatus     INTEGER,
    fsIpPingTimeout         INTEGER,
    fsIpPingTries           INTEGER,
    fsIpPingMTU             INTEGER,
    fsIpPingSendCount       INTEGER,
    fsIpPingAverageTime     INTEGER,
    fsIpPingMaxTime         INTEGER,
    fsIpPingMinTime         INTEGER,
    fsIpPingOperStatus      INTEGER,
    fsIpPingSuccesses       Counter,
    fsIpPingPercentageLoss  INTEGER,
    fsIpPingVrfId           INTEGER
}

fsIpPingDest OBJECT-TYPE
    SYNTAX      IpAddress
    ACCESS      not-accessible
    STATUS      mandatory
    DESCRIPTION 
        "The IP address of the node to be pinged.
         ALCATEL NOTE:
             ACCESS:      NA           USAGE:       NA
             PERSIST:     NO           INSRVMOD:    NA
             RANGE:       NA           DEFVALUE:    NA    
             UNITS:       NA           SPARSE:      NO
             DESCR:       NA"
    ::= { fsIpPingEntry 1 }

fsIpPingAdminStatus OBJECT-TYPE
    SYNTAX      INTEGER { on(1), off(2) }
    ACCESS      read-write
    STATUS      mandatory
    DESCRIPTION 
        "The desired status for the ping operation. This
         variable has to be made 'on' for starting the
         operation. If this variable is set to on when
         fsIpPingOperStatus is in progress, then GEN_ERROR is
         returned. This variable is can be set to off in
         order to cancel a ping operation in progress.
         ALCATEL NOTE:
         ACCESS:      NA           USAGE:       MAND
         PERSIST:     NO           INSRVMOD:    YES
         RANGE:       NA           DEFVALUE:    2
         UNITS:       NA           SPARSE:      NO
         DESCR:       The Object cannot be set on(1) when fsIpPingOperStatus is inprogress(1)"
    DEFVAL      { on }
    ::= { fsIpPingEntry 2 }

fsIpPingTimeout OBJECT-TYPE
    SYNTAX      INTEGER (100..100000)
    ACCESS      read-write
    STATUS      mandatory
    DESCRIPTION 
        "The time in milliseconds after which the entity waiting
         for the ping response times out.The variable should be
         set with a granularity of 100.
         ALCATEL NOTE:
         ACCESS:      NA           USAGE:       OPT
         PERSIST:     NO           INSRVMOD:    NO
         RANGE:       NA           DEFVALUE:    NA
         UNITS:       milliseconds SPARSE:      NO
         DESCR:       NA"
    DEFVAL      { 5000 }
    ::= { fsIpPingEntry 3 }

fsIpPingTries OBJECT-TYPE
    SYNTAX      INTEGER (1..1000)
    ACCESS      read-write
    STATUS      mandatory
    DESCRIPTION 
        "The number of times the given node address is to be
         pinged.
         ALCATEL NOTE:
         ACCESS:      NA           USAGE:       OPT
         PERSIST:     NO           INSRVMOD:    NO
         RANGE:       NA           DEFVALUE:    NA
         UNITS:       NA           SPARSE:      NO
         DESCR:       NA"
    DEFVAL      { 5 }
    ::= { fsIpPingEntry 4 }

fsIpPingMTU OBJECT-TYPE
    SYNTAX      INTEGER (0..2080)
    ACCESS      read-write
    STATUS      mandatory
    DESCRIPTION 
        "The size of the data portion of the PING PDU.
         ALCATEL NOTE:
             ACCESS:      NA           USAGE:       OPT
             PERSIST:     NO           INSRVMOD:    NO
             RANGE:       NA           DEFVALUE:    64
             UNITS:       bytes        SPARSE:      NO
             DESCR:       NA"
    DEFVAL      { 500 }
    ::= { fsIpPingEntry 5 }

fsIpPingSendCount OBJECT-TYPE
    SYNTAX      INTEGER (0..2147483647)
    ACCESS      read-only
    STATUS      mandatory
    DESCRIPTION 
        "Total number of packets sent to destination.
         ALCATEL NOTE:
             ACCESS:      NA           USAGE:       NA
             PERSIST:     NO           INSRVMOD:    NA
             RANGE:       0..1000      DEFVALUE:    0
             UNITS:       packets      SPARSE:      NO
             DESCR:       NA"
    ::= { fsIpPingEntry 6 }

fsIpPingAverageTime OBJECT-TYPE
    SYNTAX      INTEGER (0..2147483647)
    ACCESS      read-only
    STATUS      mandatory
    DESCRIPTION 
        "The average value of the round trip time in milliseconds 
         to this
         destination.
         ALCATEL NOTE:
         ACCESS:      NA           USAGE:       NA
         PERSIST:     NO           INSRVMOD:    NA
         RANGE:       0..100       DEFVALUE:    0
         UNITS:       milliseconds      SPARSE:      NO
         DESCR:       NA"
    ::= { fsIpPingEntry 7 }

fsIpPingMaxTime OBJECT-TYPE
    SYNTAX      INTEGER (0..2147483647)
    ACCESS      read-only
    STATUS      mandatory
    DESCRIPTION 
        "The maximum value of the round trip time in milliseconds 
         to this
         destination.
         ALCATEL NOTE:
         ACCESS:      NA           USAGE:       NA
         PERSIST:     NO           INSRVMOD:    NA
         RANGE:       0..100       DEFVALUE:    0
         UNITS:       milliseconds      SPARSE:      NO
         DESCR:       NA"
    ::= { fsIpPingEntry 8 }

fsIpPingMinTime OBJECT-TYPE
    SYNTAX      INTEGER (0..2147483647)
    ACCESS      read-only
    STATUS      mandatory
    DESCRIPTION 
        "The minimum value of the round trip time in milliseconds 
         to this destination.
         ALCATEL NOTE:
         ACCESS:      NA           USAGE:       NA
         PERSIST:     NO           INSRVMOD:    NA
         RANGE:       0..100       DEFVALUE:    0
         UNITS:       milliseconds      SPARSE:      NO
         DESCR:       NA"
    ::= { fsIpPingEntry 9 }

fsIpPingOperStatus OBJECT-TYPE
    SYNTAX      INTEGER { inprogress(1), notinprogress(2) }
    ACCESS      read-only
    STATUS      mandatory
    DESCRIPTION 
        "The current status of this ping operation.
         ALCATEL NOTE:
             ACCESS:      NA           USAGE:       NA
             PERSIST:     NO           INSRVMOD:    NA
             RANGE:       NA           DEFVALUE:    2
             UNITS:       NA           SPARSE:      NO
             DESCR:       NA"
    ::= { fsIpPingEntry 10 }

fsIpPingSuccesses OBJECT-TYPE
    SYNTAX      Counter
    ACCESS      read-only
    STATUS      mandatory
    DESCRIPTION 
        "The number of ping responses received.
         ALCATEL NOTE:
             ACCESS:      NA           USAGE:       NA
             PERSIST:     NO           INSRVMOD:    NA
             RANGE:       0..1000      DEFVALUE:    0       
             UNITS:       PING Msgs    SPARSE:      NO
             DESCR:       NA"
    ::= { fsIpPingEntry 11 }

fsIpPingPercentageLoss OBJECT-TYPE
    SYNTAX      INTEGER (0..2147483647)
    ACCESS      read-only
    STATUS      mandatory
    DESCRIPTION 
        "Percentage of lost packets. That is packets not
         received till
         timeout.
         ALCATEL NOTE:
         ACCESS:      NA           USAGE:       NA
         PERSIST:     NO           INSRVMOD:    NA
         RANGE:       0..100       DEFVALUE:    NA       
         UNITS:       percentage   SPARSE:      NO
         DESCR:       NA"
    ::= { fsIpPingEntry 12 }

fsIpPingVrfId OBJECT-TYPE
    SYNTAX      INTEGER (0..127)
    ACCESS      read-write
    STATUS      mandatory
    DESCRIPTION 
        "The VRF in which the pinging is done.
         ALCATEL NOTE:
             ACCESS:      NA           USAGE:       OPT
             PERSIST:     NO           INSRVMOD:    NO
             RANGE:       NA           DEFVALUE:    NA
             UNITS:       NA           SPARSE:      NO
             DESCR:       NA"
    DEFVAL      { 0 }
    ::= { fsIpPingEntry 13 }

fsIpTraceConfigTable OBJECT-TYPE
    SYNTAX      SEQUENCE OF FsIpTraceConfigEntry
    ACCESS      not-accessible
    STATUS      mandatory
    DESCRIPTION 
        "This entity's IP Traceroute Configuration Table.
         ALCATEL NOTE:
           TABLESIZE:  1
         	  DESCR: 	  NA"
    ::= { fsip 16 }

fsIpTraceConfigEntry OBJECT-TYPE
    SYNTAX      FsIpTraceConfigEntry
    ACCESS      not-accessible
    STATUS      mandatory
    DESCRIPTION 
        "Contains the configuration information about a
         particular IP
         traceroute Operation.
         Row creation : Entry can be created by the setting any of the read-write 
         objects of fsIpTraceConfig Table.
         Row deletion : Entry can be deleted by Setting fsIpTraceConfigAdminStatus to off(2).
         Index usage : the index is the fsIpTraceConfigDest.
         Note that entries will be presented to the SNMP manager in full
         lexicographical order :  sorted on fsIpTraceConfigDest."
    INDEX       { fsIpTraceConfigDest }
    ::= { fsIpTraceConfigTable 1 }

FsIpTraceConfigEntry ::= SEQUENCE {
    fsIpTraceConfigDest         IpAddress,
    fsIpTraceConfigAdminStatus  INTEGER,
    fsIpTraceConfigMaxTTL       INTEGER,
    fsIpTraceConfigMinTTL       INTEGER,
    fsIpTraceConfigOperStatus   INTEGER,
    fsIpTraceConfigTimeout      INTEGER,
    fsIpTraceConfigMtu          INTEGER,
    fsIpTraceConfigVrfId        INTEGER
}

fsIpTraceConfigDest OBJECT-TYPE
    SYNTAX      IpAddress
    ACCESS      not-accessible
    STATUS      mandatory
    DESCRIPTION 
        "The destination IP address to which a route has to
         be traced.
         ALCATEL NOTE:
         ACCESS:      NA           USAGE:       NA
         PERSIST:     NO           INSRVMOD:    NA
         RANGE:       NA           DEFVALUE:    NA    
         UNITS:       NA           SPARSE:      NO
         DESCR:       NA"
    ::= { fsIpTraceConfigEntry 1 }

fsIpTraceConfigAdminStatus OBJECT-TYPE
    SYNTAX      INTEGER { on(1), off(2) }
    ACCESS      read-write
    STATUS      mandatory
    DESCRIPTION 
        "The desired status for the traceroute operation.
         This variable has to be made on (from off) for
         starting the operation. If this variable is set to
         on when fsIpTraceConfigOperStatus is inprogress,
         then GEN_ERROR is returned. This variable is set
         to off when the fsIpTraceConfigOperStatus becomes
         not inprogress.
         ALCATEL NOTE:
         ACCESS:      NA           USAGE:       MAND
         PERSIST:     NO           INSRVMOD:    YES
         RANGE:       NA           DEFVALUE:    2
         UNITS:       NA           SPARSE:      NO
         DESCR:       The Object cannot be set on(1) when fsIpTraceConfigOperStatus is inprogress(1)"
    DEFVAL      { on }
    ::= { fsIpTraceConfigEntry 2 }

fsIpTraceConfigMaxTTL OBJECT-TYPE
    SYNTAX      INTEGER (1..99)
    ACCESS      read-write
    STATUS      mandatory
    DESCRIPTION 
        "The maximum value of the TTL field to be filled up
         in the IP packets used for the traceroute & Max TTL value should be greater than Min TTL.
         ALCATEL NOTE:
         ACCESS:      NA           USAGE:       OPT
         PERSIST:     NO           INSRVMOD:    NO
         RANGE:       NA           DEFVALUE:    NA
         UNITS:       NA           SPARSE:      NO
         DESCR:       NA"
    DEFVAL      { 15 }
    ::= { fsIpTraceConfigEntry 3 }

fsIpTraceConfigMinTTL OBJECT-TYPE
    SYNTAX      INTEGER (1..99)
    ACCESS      read-write
    STATUS      mandatory
    DESCRIPTION 
        "The minimum value of the TTL field to be filled up
         in the IP packets used for the traceroute.
         ALCATEL NOTE:
         ACCESS:      NA           USAGE:       OPT
         PERSIST:     NO           INSRVMOD:    NO
         RANGE:       NA           DEFVALUE:    NA
         UNITS:       NA           SPARSE:      NO
         DESCR:       NA"
    DEFVAL      { 1 }
    ::= { fsIpTraceConfigEntry 4 }

fsIpTraceConfigOperStatus OBJECT-TYPE
    SYNTAX      INTEGER { inprogress(1), notinprogress(2) }
    ACCESS      read-only
    STATUS      mandatory
    DESCRIPTION 
        "The current status for the traceroute operation.
         ALCATEL NOTE:
             ACCESS:      NA           USAGE:       NA
             PERSIST:     NO           INSRVMOD:    NA
             RANGE:       NA           DEFVALUE:    2
             UNITS:       NA           SPARSE:      NO
             DESCR:       NA"
    ::= { fsIpTraceConfigEntry 5 }

fsIpTraceConfigTimeout OBJECT-TYPE
    SYNTAX      INTEGER (0..100)
    ACCESS      read-write
    STATUS      mandatory
    DESCRIPTION 
        "Interval between (in seconds) consecutive trace
         requests.
         ALCATEL NOTE:
         ACCESS:      NA           USAGE:       OPT
         PERSIST:     NO           INSRVMOD:    NO
         RANGE:       1..100       DEFVALUE:    1
         UNITS:       seconds      SPARSE:      NO
         DESCR:       NA"
    ::= { fsIpTraceConfigEntry 6 }

fsIpTraceConfigMtu OBJECT-TYPE
    SYNTAX      INTEGER (0..100)
    ACCESS      read-write
    STATUS      mandatory
    DESCRIPTION 
        "Number of octets of data to be sent in trace
         packets.
         ALCATEL NOTE:
         ACCESS:      NA           USAGE:       OPT
         PERSIST:     NO           INSRVMOD:    NO
         RANGE:       1..100       DEFVALUE:    1
         UNITS:       Bytes        SPARSE:      NO
         DESCR:       NA"
    ::= { fsIpTraceConfigEntry 7 }

fsIpTraceConfigVrfId OBJECT-TYPE
    SYNTAX      INTEGER (0..127)
    ACCESS      read-write
    STATUS      mandatory
    DESCRIPTION 
        "The VRF Id through which the IP packets for
         Traceroute has to be sent.
         ALCATEL NOTE:
         ACCESS:      NA           USAGE:       NA
         PERSIST:     NO           INSRVMOD:    NA
         RANGE:       NA           DEFVALUE:    NA    
         UNITS:       NA           SPARSE:      NO
         DESCR:       NA"
    DEFVAL      { 0 }
    ::= { fsIpTraceConfigEntry 8 }

fsIpTraceTable OBJECT-TYPE
    SYNTAX      SEQUENCE OF FsIpTraceEntry
    ACCESS      not-accessible
    STATUS      mandatory
    DESCRIPTION 
        "This entity's IP Traceroute Table containing the
         results of the traceroute operation(s).
         ALCATEL NOTE:
         TABLESIZE:  99
         DESCR: 	  The size of the table can vary from 1..99 based on the Hop Count"
    ::= { fsip 17 }

fsIpTraceEntry OBJECT-TYPE
    SYNTAX      FsIpTraceEntry
    ACCESS      not-accessible
    STATUS      mandatory
    DESCRIPTION 
        "Contains the	 information about a particular
         intermediate node on the way to the destination.
         Row creation : A Entry will be created by the system when it trace 
         routine reaches the next hop.
         Row deletion : All the Entries can be deleted by Setting the
         fsIpTraceConfigAdminStatus to off(2).
         Index usage : the index are fsIpTraceDest and fsIpTraceHopCount.
         Note that entries will be presented to the SNMP manager in full
         lexicographical order :  sorted on fsIpTraceDest, then on fsIpTraceHopCount"
    INDEX       { fsIpTraceDest, fsIpTraceHopCount }
    ::= { fsIpTraceTable 1 }

FsIpTraceEntry ::= SEQUENCE {
    fsIpTraceDest           IpAddress,
    fsIpTraceHopCount       INTEGER,
    fsIpTraceIntermHop      IpAddress,
    fsIpTraceReachTime1     INTEGER,
    fsIpTraceReachTime2     INTEGER,
    fsIpTraceReachTime3     INTEGER,
    fsIpTraceStatus         INTEGER
}

fsIpTraceDest OBJECT-TYPE
    SYNTAX      IpAddress
    ACCESS      not-accessible
    STATUS      mandatory
    DESCRIPTION 
        "The destination IP address to which a route was
         traced.
         ALCATEL NOTE:
         ACCESS:      NA           USAGE:       NA
         PERSIST:     NO           INSRVMOD:    NA
         RANGE:       NA           DEFVALUE:    NA    
         UNITS:       NA           SPARSE:      NO
         DESCR:       NA"
    ::= { fsIpTraceEntry 1 }

fsIpTraceHopCount OBJECT-TYPE
    SYNTAX      INTEGER (0..2147483647)
    ACCESS      not-accessible
    STATUS      mandatory
    DESCRIPTION 
        "The count of the number of hops required to reach
         this intermediate node.
         ALCATEL NOTE:
         ACCESS:      NA           USAGE:       NA
         PERSIST:     NO           INSRVMOD:    NA
         RANGE:       1..99        DEFVALUE:    NA    
         UNITS:       NA           SPARSE:      NO
         DESCR:       NA"
    ::= { fsIpTraceEntry 2 }

fsIpTraceIntermHop OBJECT-TYPE
    SYNTAX      IpAddress
    ACCESS      read-only
    STATUS      mandatory
    DESCRIPTION 
        "The IP address of the intermediate node/destination.
         ALCATEL NOTE:
             ACCESS:      NA           USAGE:       NA
             PERSIST:     NO           INSRVMOD:    NA
             RANGE:       NA           DEFVALUE:    NA    
             UNITS:       NA           SPARSE:      NO
             DESCR:       NA"
    ::= { fsIpTraceEntry 3 }

fsIpTraceReachTime1 OBJECT-TYPE
    SYNTAX      INTEGER (-1..1073741824)
    ACCESS      read-only
    STATUS      mandatory
    DESCRIPTION 
        "The time in milliseconds required to reach this
         intermediate node.The value of '-1' denotes that the
         response was not received from this node
         ALCATEL NOTE:
         ACCESS:      NA           USAGE:       NA
         PERSIST:     NO           INSRVMOD:    NA
         RANGE:       -1..100      DEFVALUE:    NA    
         UNITS:       seconds      SPARSE:      NO
         DESCR:       NA"
    ::= { fsIpTraceEntry 4 }

fsIpTraceReachTime2 OBJECT-TYPE
    SYNTAX      INTEGER (-1..1073741824)
    ACCESS      read-only
    STATUS      mandatory
    DESCRIPTION 
        "The time in milliseconds required to reach this
         intermediate node for the second time. The value of
         '-1' denotes that the response was not received
         from this node
         ALCATEL NOTE:
         ACCESS:      NA           USAGE:       NA
         PERSIST:     NO           INSRVMOD:    NA
         RANGE:       -1..100       DEFVALUE:    NA    
         UNITS:       seconds      SPARSE:      NO
         DESCR:       NA"
    ::= { fsIpTraceEntry 5 }

fsIpTraceReachTime3 OBJECT-TYPE
    SYNTAX      INTEGER (-1..1073741824)
    ACCESS      read-only
    STATUS      mandatory
    DESCRIPTION 
        "The time in milliseconds required to reach this
         intermediate node for the third time. The value of
         '-1' denotes that the response was not received from
         this node
         ALCATEL NOTE:
         ACCESS:      NA           USAGE:       NA
         PERSIST:     NO           INSRVMOD:    NA
         RANGE:       -1..100      DEFVALUE:    NA    
         UNITS:       seconds      SPARSE:      NO
         DESCR:       NA"
    ::= { fsIpTraceEntry 6 }

fsIpTraceStatus OBJECT-TYPE
    SYNTAX      INTEGER { intermediate(1), final(2), inprogress(3), 
                    error(4) }
    ACCESS      read-only
    STATUS      mandatory
    DESCRIPTION 
        "The current status for the Traceroute. 
         Intermediate - This is an intermediate result, the next hop will be tried.
         Final - This is the final result: no next hop will be tried because 
         fsIpTraceDest is reached or fsIpTraceConfigMaxTTL is reached.
         Error - This is a final result: fsIpTraceDest can never be reached 
         because there is no route to  it. 
         ALCATEL NOTE:
         ACCESS:      NA           USAGE:       NA
         PERSIST:     NO           INSRVMOD:    NA
         RANGE:       NA           DEFVALUE:    NA    
         UNITS:       NA           SPARSE:      NO
         DESCR:       NA"
    ::= { fsIpTraceEntry 7 }

fsIpAddressTable OBJECT-TYPE
    SYNTAX      SEQUENCE OF FsIpAddressEntry
    ACCESS      not-accessible
    STATUS      mandatory
    DESCRIPTION 
        "The table of IP addresses on every Interface.
         TABLESIZE:  NA
         	  DESCR: 	  This object is not used by Alcatel"
    ::= { fsip 18 }

fsIpAddressEntry OBJECT-TYPE
    SYNTAX      FsIpAddressEntry
    ACCESS      not-accessible
    STATUS      mandatory
    DESCRIPTION 
        "The individual entry in the above table.
         Row creation : NA
         Row deletion : NA
         Index usage :  NA
         Lexicographical order :  NA
         	This object is not used by Alcatel"
    INDEX       { fsIpAddrTabAddress }
    ::= { fsIpAddressTable 1 }

FsIpAddressEntry ::= SEQUENCE {
    fsIpAddrTabIfaceId      INTEGER,
    fsIpAddrTabAddress      IpAddress,
    fsIpAddrTabAdvertise    TruthValue,
    fsIpAddrTabPreflevel    INTEGER,
    fsIpAddrTabStatus       RowStatus
}

fsIpAddrTabIfaceId OBJECT-TYPE
    SYNTAX      INTEGER (0..2147483647)
    ACCESS      read-only
    STATUS      mandatory
    DESCRIPTION 
        "The interface number to which the IP address
         belongs to.
         ALCATEL NOTE:
         ACCESS:      NA           USAGE:       NA
         PERSIST:     NA           INSRVMOD:    NA
         RANGE:       NA           DEFVALUE:    NA
         UNITS:       NA	        SPARSE:      NA
         DESCR:       This object is not used by Alcatel"
    ::= { fsIpAddressEntry 1 }

fsIpAddrTabAddress OBJECT-TYPE
    SYNTAX      IpAddress
    ACCESS      not-accessible
    STATUS      mandatory
    DESCRIPTION 
        "One of the router's IP addresses.
         ALCATEL NOTE:
             ACCESS:      NA           USAGE:       NA
             PERSIST:     NA           INSRVMOD:    NA
             RANGE:       NA           DEFVALUE:    NA
             UNITS:       NA	        SPARSE:      NA
             DESCR:       This object is not used by Alcatel"
    ::= { fsIpAddressEntry 2 }

fsIpAddrTabAdvertise OBJECT-TYPE
    SYNTAX      TruthValue
    ACCESS      read-write
    STATUS      mandatory
    DESCRIPTION 
        "A flag indicating whether or not the address is
         to be advertised.
         ALCATEL NOTE:
         ACCESS:      NA           USAGE:       NA
         PERSIST:     NA           INSRVMOD:    NA
         RANGE:       NA           DEFVALUE:    NA
         UNITS:       NA	        SPARSE:      NA
         DESCR:       This object is not used by Alcatel"
    ::= { fsIpAddressEntry 3 }

fsIpAddrTabPreflevel OBJECT-TYPE
    SYNTAX      INTEGER (0..2147483647)
    ACCESS      read-write
    STATUS      mandatory
    DESCRIPTION 
        "The preferability of the address as a default
         router address, relative to other router addresses on
         the same subnet. A 32-bit, signed, twos-complement
         integer, with higher values meaning more preferable.
         ALCATEL NOTE:
         ACCESS:      NA           USAGE:       NA
         PERSIST:     NA           INSRVMOD:    NA
         RANGE:       NA           DEFVALUE:    NA
         UNITS:       NA	        SPARSE:      NA
         DESCR:       This object is not used by Alcatel"
    ::= { fsIpAddressEntry 4 }

fsIpAddrTabStatus OBJECT-TYPE
    SYNTAX      RowStatus
    ACCESS      read-only
    STATUS      mandatory
    DESCRIPTION 
        "The status of this row, by which new entries may be
         created, or old entries deleted from this table.
         ALCATEL NOTE:
         ACCESS:      NA           USAGE:       NA
         PERSIST:     NA           INSRVMOD:    NA
         RANGE:       NA           DEFVALUE:    NA
         UNITS:       NA	        SPARSE:      NA
         DESCR:       This object is not used by Alcatel"
    ::= { fsIpAddressEntry 5 }

fsIpRtrLstTable OBJECT-TYPE
    SYNTAX      SEQUENCE OF FsIpRtrLstEntry
    ACCESS      not-accessible
    STATUS      mandatory
    DESCRIPTION 
        "List of default router addresses. Used when system
         functions as a host.Maintained as per RFC 1122.
         ALCATEL NOTE:
         TABLESIZE:   NA
         DESCR:       This object is not used by Alcatel"
    ::= { fsip 19 }

fsIpRtrLstEntry OBJECT-TYPE
    SYNTAX      FsIpRtrLstEntry
    ACCESS      not-accessible
    STATUS      mandatory
    DESCRIPTION 
        "The individual entry in the above table.
         Row creation : NA
         Row deletion : NA
         Index usage :  NA
         Lexicographical order :  NA
         	This object is not used by Alcatel"
    INDEX       { fsIpRtrLstAddress }
    ::= { fsIpRtrLstTable 1 }

FsIpRtrLstEntry ::= SEQUENCE {
    fsIpRtrLstIface         INTEGER,
    fsIpRtrLstAddress       IpAddress,
    fsIpRtrLstPreflevel     INTEGER,
    fsIpRtrLstStatic        TruthValue,
    fsIpRtrLstStatus        RowStatus
}

fsIpRtrLstIface OBJECT-TYPE
    SYNTAX      INTEGER (0..2147483647)
    ACCESS      read-write
    STATUS      mandatory
    DESCRIPTION 
        "The interface via which the router could be
         reached.
         ALCATEL NOTE:
         ACCESS:      NA           USAGE:       NA
         PERSIST:     NA           INSRVMOD:    NA
         RANGE:       NA           DEFVALUE:    NA
         UNITS:       NA	        SPARSE:      NA
         DESCR:       This object is not used by Alcatel"
    ::= { fsIpRtrLstEntry 1 }

fsIpRtrLstAddress OBJECT-TYPE
    SYNTAX      IpAddress
    ACCESS      not-accessible
    STATUS      mandatory
    DESCRIPTION 
        "An IP address of a default router.
         ALCATEL NOTE:
             ACCESS:      NA           USAGE:       NA
             PERSIST:     NA           INSRVMOD:    NA
             RANGE:       NA           DEFVALUE:    NA
             UNITS:       NA	        SPARSE:      NA
             DESCR:       This object is not used by Alcatel"
    ::= { fsIpRtrLstEntry 2 }

fsIpRtrLstPreflevel OBJECT-TYPE
    SYNTAX      INTEGER (0..2147483647)
    ACCESS      read-write
    STATUS      mandatory
    DESCRIPTION 
        "The preferability of the RouterAddress as a default
         router address, relative to other router addresses
         on the same subnet.
         ALCATEL NOTE:
         ACCESS:      NA           USAGE:       NA
         PERSIST:     NA           INSRVMOD:    NA
         RANGE:       NA           DEFVALUE:    NA
         UNITS:       NA	        SPARSE:      NA
         DESCR:       This object is not used by Alcatel"
    ::= { fsIpRtrLstEntry 3 }

fsIpRtrLstStatic OBJECT-TYPE
    SYNTAX      TruthValue
    ACCESS      read-only
    STATUS      mandatory
    DESCRIPTION 
        "This entry states how the default router address
         was learned.
         ALCATEL NOTE:
         ACCESS:      NA           USAGE:       NA
         PERSIST:     NA           INSRVMOD:    NA
         RANGE:       NA           DEFVALUE:    NA
         UNITS:       NA	        SPARSE:      NA
         DESCR:       This object is not used by Alcatel"
    ::= { fsIpRtrLstEntry 4 }

fsIpRtrLstStatus OBJECT-TYPE
    SYNTAX      RowStatus
    ACCESS      read-write
    STATUS      mandatory
    DESCRIPTION 
        "The status of this row, by which new entries may be
         created, or old entries deleted from this table.
         ALCATEL NOTE:
         ACCESS:      NA           USAGE:       NA
         PERSIST:     NA           INSRVMOD:    NA
         RANGE:       NA           DEFVALUE:    NA
         UNITS:       NA	        SPARSE:      NA
         DESCR:       This object is not used by Alcatel"
    ::= { fsIpRtrLstEntry 5 }

fsIpPathMtuTable OBJECT-TYPE
    SYNTAX      SEQUENCE OF FsIpPathMtuEntry
    ACCESS      not-accessible
    STATUS      mandatory
    DESCRIPTION 
        "This Table shows the PMTU-D information for every path. 
         Administrator can enable or disable PMTU-D per 
         destination basis. This overrides the request from the 
         application.
         ALCATEL NOTE:
         TABLESIZE:   NA
         DESCR:       This object is not used by Alcatel"
    ::= { fsip 20 }

fsIpPathMtuEntry OBJECT-TYPE
    SYNTAX      FsIpPathMtuEntry
    ACCESS      not-accessible
    STATUS      mandatory
    DESCRIPTION 
        "This object forms the conceptual row of the PMTU Table.
         Row creation : NA
         Row deletion : NA
         Index usage :  NA
         Lexicographical order :  NA
         	This object is not used by Alcatel"
    INDEX       { fsIpPmtuDestination, fsIpPmtuTos }
    ::= { fsIpPathMtuTable 1 }

FsIpPathMtuEntry ::= SEQUENCE {
    fsIpPmtuDestination     IpAddress,
    fsIpPmtuTos             INTEGER,
    fsIpPathMtu             INTEGER,
    fsIpPmtuDisc            INTEGER,
    fsIpPmtuEntryStatus     RowStatus
}

fsIpPmtuDestination OBJECT-TYPE
    SYNTAX      IpAddress
    ACCESS      not-accessible
    STATUS      mandatory
    DESCRIPTION 
        "Specifies the Destination IP address of the Path for 
         which the discovery is made.
         ALCATEL NOTE:
         ACCESS:      NA           USAGE:       NA
         PERSIST:     NA           INSRVMOD:    NA
         RANGE:       NA           DEFVALUE:    NA
         UNITS:       NA	        SPARSE:      NA
         DESCR:       This object is not used by Alcatel"
    ::= { fsIpPathMtuEntry 1 }

fsIpPmtuTos OBJECT-TYPE
    SYNTAX      INTEGER (0..2147483647)
    ACCESS      not-accessible
    STATUS      mandatory
    DESCRIPTION 
        "Specifies the type of service of the path.
         ALCATEL NOTE:
             ACCESS:      NA           USAGE:       NA
             PERSIST:     NA           INSRVMOD:    NA
             RANGE:       NA           DEFVALUE:    NA
             UNITS:       NA	        SPARSE:      NA
             DESCR:       This object is not used by Alcatel"
    ::= { fsIpPathMtuEntry 2 }

fsIpPathMtu OBJECT-TYPE
    SYNTAX      INTEGER (68..65535)
    ACCESS      read-write
    STATUS      mandatory
    DESCRIPTION 
        "Value of the path mtu discovered. If the admin changes 
         this value, PMTU discovery on that path is stopped.
         ALCATEL NOTE:
         ACCESS:      NA           USAGE:       NA
         PERSIST:     NA           INSRVMOD:    NA
         RANGE:       NA           DEFVALUE:    NA
         UNITS:       NA	        SPARSE:      NA
         DESCR:       This object is not used by Alcatel"
    ::= { fsIpPathMtuEntry 3 }

fsIpPmtuDisc OBJECT-TYPE
    SYNTAX      INTEGER { enabled(1), disabled(2) }
    ACCESS      read-write
    STATUS      mandatory
    DESCRIPTION 
        "Enables or Disables PMTU discovery for the given path.
         This overrides the application request wrt to PMTU-D.
         ALCATEL NOTE:
         ACCESS:      NA           USAGE:       NA
         PERSIST:     NA           INSRVMOD:    NA
         RANGE:       NA           DEFVALUE:    NA
         UNITS:       NA	        SPARSE:      NA
         DESCR:       This object is not used by Alcatel"
    ::= { fsIpPathMtuEntry 4 }

fsIpPmtuEntryStatus OBJECT-TYPE
    SYNTAX      RowStatus
    ACCESS      read-write
    STATUS      mandatory
    DESCRIPTION 
        "Entry Status of the row in the PMTU table.
         ALCATEL NOTE:
             ACCESS:      NA           USAGE:       NA
             PERSIST:     NA           INSRVMOD:    NA
             RANGE:       NA           DEFVALUE:    NA
             UNITS:       NA	        SPARSE:      NA
             DESCR:       This object is not used by Alcatel"
    ::= { fsIpPathMtuEntry 5 }

fsIpRoutePrefTable OBJECT-TYPE
    SYNTAX      SEQUENCE OF FsIpRoutePrefEntry
    ACCESS      not-accessible
    STATUS      mandatory
    DESCRIPTION 
        "Preference Table, which contains information about the 
         preference for the routes learned from the dynamic routing
         protocols.
         ALCATEL NOTE:
         TABLESIZE:  3
         DESCR: 	  NA"
    ::= { fsip 21 }

fsIpRoutePrefEntry OBJECT-TYPE
    SYNTAX      FsIpRoutePrefEntry
    ACCESS      not-accessible
    STATUS      mandatory
    DESCRIPTION 
        "Preference table entry.
         Row creation : All the Entries are created by the system at the startup.
         Row deletion : All the Entries are deleted by the system when it shutdowns.
         Index usage : the index is the fsIpRoutingProtoId.
           Note that entries will be presented to the SNMP manager in full
           lexicographical order :  sorted on fsIpRoutingProtoId."
    INDEX       { fsIpRoutingProtoId }
    ::= { fsIpRoutePrefTable 1 }

FsIpRoutePrefEntry ::= SEQUENCE {
    fsIpRoutingProtoId      INTEGER,
    fsIpRoutingProtoPref    INTEGER
}

fsIpRoutingProtoId OBJECT-TYPE
    SYNTAX      INTEGER { other(1), local(2), netmgmt(3), icmp(4), 
                    egp(5), ggp(6), hello(7), rip(8), isIs(9), esIs(10), 
                    ciscoIgrp(11), bbnSpfIgp(12), ospf(13), bgp(14), 
                    idpr(15), ciscoEigrp(16) }
    ACCESS      not-accessible
    STATUS      mandatory
    DESCRIPTION 
        "The routing mechanism via which this route was
         learned.
         ALCATEL NOTE:
         ACCESS:      NA           USAGE:       NA
         PERSIST:     YES          INSRVMOD:    NA
         RANGE:       3,8,9,13,14  DEFVALUE:    NA
         UNITS:       NA           SPARSE:      NO
         DESCR:       NA"
    ::= { fsIpRoutePrefEntry 1 }

fsIpRoutingProtoPref OBJECT-TYPE
    SYNTAX      INTEGER (0..255)
    ACCESS      read-write
    STATUS      mandatory
    DESCRIPTION 
        "Preference of the route learned by a particular protocol. 
         This value is used while choosing the best path. 
         Lesser the value, highest is the preference. 
         ALCATEL NOTE:
         ACCESS:      NA           USAGE:       NA
         PERSIST:     YES          INSRVMOD:    YES
         RANGE:       1..254       DEFVALUE:    netmgmt(3) - 100
                                             rip(8)     - 119
                                             isIs(9)    - 120
                                             ospf(13)   - 121
                                             bgp(14)    - 122
         UNITS:       NA           SPARSE:      NO
         DESCR:       NA"
    ::= { fsIpRoutePrefEntry 2 }

fsIpifTable OBJECT-TYPE
    SYNTAX      SEQUENCE OF FsIpifEntry
    ACCESS      not-accessible
    STATUS      mandatory
    DESCRIPTION 
        "IP interface table which maintains the interface specific 
         configurable parameters of IP.
         ALCATEL NOTE:
         TABLESIZE: DEP 
         DESCR:	 DEP(TABLESIZE):The size of the table is derived from the 
         	       total number of IP interfaces in the system.
         	       The total number of IP interfaces in the system  is obtained from fsvrf.mib"
    ::= { fsip 23 }

fsIpifEntry OBJECT-TYPE
    SYNTAX      FsIpifEntry
    ACCESS      not-accessible
    STATUS      mandatory
    DESCRIPTION 
        "A particular interface specific IP information.
         Row creation : An entry will be created by the system when an entry
             		is created in the ifMultiNetIpTable.
         Row deletion : An entry will be deleted by the system when an entry
             		is deleted in the ifMultiNetIpTable.
         Index usage : the index is fsIpifIndex.
           Note that entries will be presented to the SNMP manager in full
           lexicographical order :  sorted on fsIpifIndex."
    INDEX       { fsIpifIndex }
    ::= { fsIpifTable 1 }

FsIpifEntry ::= SEQUENCE {
    fsIpifIndex                 INTEGER,
    fsIpifMaxReasmSize          INTEGER,
    fsIpifIcmpRedirectEnable    INTEGER,
    fsIpifDrtBcastFwdingEnable  INTEGER,
    fsIpifIcmpErrMsgSuppresion  INTEGER,
    fsIpifPingMsgSuppresion     INTEGER,
    fsIpifOptProcEnable         INTEGER,
    fsIpifIsamVEdgeRouterIp     IpAddress
}

fsIpifIndex OBJECT-TYPE
    SYNTAX      INTEGER (0..2147483647)
    ACCESS      not-accessible
    STATUS      mandatory
    DESCRIPTION 
        "The index value which identifies the
         interface to which this entry is applicable. The
         interface identified by a particular value of this
         index is the same interface as identified by the same
         value of ifIndex in MIB II. 
         ALCATEL NOTE:
         ACCESS:      NA           USAGE:       NA
         PERSIST:     YES          INSRVMOD:    NA
         RANGE:       DEP          DEFVALUE:    NA
         UNITS:       NA           SPARSE:      NO
         DESCR:       DEP(RANGE):The range is from 1 to maximum number of physical interfaces available in the system + 
         		    total number of IP interfaces in the system .
         		    The maximum number of physical interfaces (obtained from issSystemNumberOfPorts in fsiss.mib).
         		    The total number of IP interfaces in the system obtained from fsvrf.mib.
                     The IP interfaces will start from 65536 to the total number of IP interfaces 
         		    in the system.  
                     The indices 81920 & 81921 are reserved for vlan 4094 & 4093 respectively."
    ::= { fsIpifEntry 1 }

fsIpifMaxReasmSize OBJECT-TYPE
    SYNTAX      INTEGER (1024..9212)
    ACCESS      read-write
    STATUS      mandatory
    DESCRIPTION 
        "The maximum size of the fragmented IP datagram received 
         on this interface that can be considered for reassembly. 
         ALCATEL NOTE:
         ACCESS:      NA           USAGE:       NA
         PERSIST:     YES          INSRVMOD:    YES
         RANGE:       NA           DEFVALUE:    9212
         UNITS:       bytes        SPARSE:      NO
         DESCR:       NA"
    ::= { fsIpifEntry 2 }

fsIpifIcmpRedirectEnable OBJECT-TYPE
    SYNTAX      INTEGER { enabled(1), disabled(2) }
    ACCESS      read-write
    STATUS      mandatory
    DESCRIPTION 
        "Enabling or Diabling of the ICMP redirect messages on an 
         interface basis.
         ALCATEL NOTE:
         ACCESS:      NA           USAGE:       NA
         PERSIST:     YES          INSRVMOD:    YES
         RANGE:       NA           DEFVALUE:    1
         UNITS:       NA           SPARSE:      NO
         DESCR:       NA"
    ::= { fsIpifEntry 3 }

fsIpifDrtBcastFwdingEnable OBJECT-TYPE
    SYNTAX      INTEGER { enabled(1), disabled(2) }
    ACCESS      read-write
    STATUS      mandatory
    DESCRIPTION 
        "Enabling of Directed broadcast forwarding on that 
         interface.
         ALCATEL NOTE:
         ACCESS:      NA           USAGE:       NA
         PERSIST:     YES          INSRVMOD:    YES
         RANGE:       NA           DEFVALUE:    2
         UNITS:       NA           SPARSE:      NO
         DESCR:       NA"
    ::= { fsIpifEntry 4 }

fsIpifIcmpErrMsgSuppresion OBJECT-TYPE
    SYNTAX      INTEGER { enabled(1), disabled(2) }
    ACCESS      read-write
    STATUS      mandatory
    DESCRIPTION 
        "This object is used to enable/disable ICMP Error message
         sending.
         ALCATEL NOTE:
         ACCESS:      NA           USAGE:       NA
         PERSIST:     YES          INSRVMOD:    YES
         RANGE:       NA           DEFVALUE:    NA
         UNITS:       NA           SPARSE:      NO
         DESCR:       NA"
    DEFVAL      { disabled }
    ::= { fsIpifEntry 5 }

fsIpifPingMsgSuppresion OBJECT-TYPE
    SYNTAX      INTEGER { enabled(1), disabled(2) }
    ACCESS      read-write
    STATUS      mandatory
    DESCRIPTION 
        " When this object is enabled, PING to this interface
         fails.
         ALCATEL NOTE:
         ACCESS:      NA           USAGE:       NA
         PERSIST:     YES          INSRVMOD:    YES
         RANGE:       NA           DEFVALUE:    NA
         UNITS:       NA           SPARSE:      NO
         DESCR:       NA"
    DEFVAL      { disabled }
    ::= { fsIpifEntry 6 }

fsIpifOptProcEnable OBJECT-TYPE
    SYNTAX      INTEGER { enabled(1), disabled(2) }
    ACCESS      read-write
    STATUS      mandatory
    DESCRIPTION 
        "Indication as to if Option processing is active.
         ALCATEL NOTE:
             ACCESS:      NA           USAGE:       NA
             PERSIST:     YES          INSRVMOD:    YES
             RANGE:       NA           DEFVALUE:    NA
             UNITS:       NA           SPARSE:      NO
             DESCR:       NA"
    DEFVAL      { enabled }
    ::= { fsIpifEntry 7 }

fsIpifIsamVEdgeRouterIp OBJECT-TYPE
    SYNTAX      IpAddress
    ACCESS      read-write
    STATUS      mandatory
    DESCRIPTION 
        "This object specifies the IP address of the edge router. Once this IP is configured 
         to a non-zero value, LANX tries to resolve ARP for the configured IP. 
         If ARP is resolved, BCM will be configured to have a filter to redirect voice 
         packets to this edge router which means External packet forwarding (EPF) feature
         is enabled for the interface. Setting this IP address to zero, can disable EPF.
         ALCATEL NOTE:
         ACCESS:      NA           USAGE:       NA
         PERSIST:     YES          INSRVMOD:    YES
         RANGE:       NA           DEFVALUE:    NA    
         UNITS:       NA           SPARSE:      NA
         DESCR:       NA"
    DEFVAL      { '00000000'H }
    ::= { fsIpifEntry 8 }

fsIpLicensingFlag OBJECT-TYPE
    SYNTAX      INTEGER { false(0), true(1) }
    ACCESS      read-only
    STATUS      mandatory
    DESCRIPTION 
        "This is the Licensing Flag for checking the OSPF/RIP config Stats and returns 
         gu1IpRtLicenseFlag
         ALCATEL NOTE:
         ACCESS:      NA           USAGE:       NA
         PERSIST:     NO           INSRVMOD:    NA
         RANGE:       NA           DEFVALUE:    NA    
         UNITS:       NA           SPARSE:      NA
         DESCR:       NA"
    DEFVAL      { false }
    ::= { fsip 24 }

fsIpCruBuffThresholdPacketDrop OBJECT-TYPE
    SYNTAX      INTEGER
    ACCESS      read-only
    STATUS      mandatory
    DESCRIPTION 
        "If current usage of the cru buffer exceeds cru buffer threshold
         value then the IP packet drop count gets incremented, by dropping all non-reasmbled IP packet
         ALCATEL NOTE:
         ACCESS:      NA           USAGE:       NA
         PERSIST:     NO           INSRVMOD:    NA
         RANGE:       NA           DEFVALUE:    0
         UNITS:       NA           SPARSE:      NO
         DESCR:       NA"
    DEFVAL      { 0 }
    ::= { fsip 25 }

fsIpFragMaxSizeFragmentDrop OBJECT-TYPE
    SYNTAX      INTEGER
    ACCESS      read-only
    STATUS      mandatory
    DESCRIPTION 
        "If an IP packet with datagram more than fsIpifMaxReasmSize is received,
         then the corresponding IP packet is dropped by incrementing the drop 
         count to one.
         
         ALCATEL NOTE:
         ACCESS:      NA           USAGE:       NA
         PERSIST:     NO           INSRVMOD:    NA
         RANGE:       NA           DEFVALUE:    0
         UNITS:       NA           SPARSE:      NO
         DESCR:       NA"
    DEFVAL      { 0 }
    ::= { fsip 26 }

fsiparp OBJECT IDENTIFIER
    ::= { futureip 2 }

fsIpArpInPkts OBJECT-TYPE
    SYNTAX      Counter
    ACCESS      read-only
    STATUS      mandatory
    DESCRIPTION 
        "The total number of Arp datagrams received from
         interfaces, including those received in error.
         ALCATEL NOTE:
         ACCESS:      NA           USAGE:       NA
         PERSIST:     NO           INSRVMOD:    NA
         RANGE:       NA           DEFVALUE:    0       
         UNITS:       ARP Packets  SPARSE:      NA
         DESCR:       NA"
    ::= { fsiparp 4 }

fsIpArpDiscards OBJECT-TYPE
    SYNTAX      Counter
    ACCESS      read-only
    STATUS      mandatory
    DESCRIPTION 
        " Total number of packets discarded including,
         those with Bad Type, length, address, requests
         that were rejected 
         ALCATEL NOTE:
         ACCESS:      NA           USAGE:       NA
         PERSIST:     NO           INSRVMOD:    NA
         RANGE:       NA           DEFVALUE:    0       
         UNITS:       ARP Packets  SPARSE:      NA
         DESCR:       NA"
    ::= { fsiparp 5 }

fsIpArpInRequests OBJECT-TYPE
    SYNTAX      Counter
    ACCESS      read-only
    STATUS      mandatory
    DESCRIPTION 
        " Number of Arp request packets received 
         ALCATEL NOTE:
             ACCESS:      NA           USAGE:       NA
             PERSIST:     NO           INSRVMOD:    NA
             RANGE:       NA           DEFVALUE:    0       
             UNITS:       ARP Packets  SPARSE:      NA
             DESCR:       NA"
    ::= { fsiparp 6 }

fsIpArpInResponses OBJECT-TYPE
    SYNTAX      Counter
    ACCESS      read-only
    STATUS      mandatory
    DESCRIPTION 
        " Number of Arp response packets received 
         ALCATEL NOTE:
             ACCESS:      NA           USAGE:       NA
             PERSIST:     NO           INSRVMOD:    NA
             RANGE:       NA           DEFVALUE:    0       
             UNITS:       ARP Packets  SPARSE:      NA
             DESCR:       NA"
    ::= { fsiparp 7 }

fsIpArpOutRequests OBJECT-TYPE
    SYNTAX      Counter
    ACCESS      read-only
    STATUS      mandatory
    DESCRIPTION 
        " Number of Arp requests transmitted 
         ALCATEL NOTE:
             ACCESS:      NA           USAGE:       NA
             PERSIST:     NO           INSRVMOD:    NA
             RANGE:       NA           DEFVALUE:    0       
             UNITS:       ARP Packets  SPARSE:      NA
             DESCR:       NA"
    ::= { fsiparp 8 }

fsIpArpOutResponses OBJECT-TYPE
    SYNTAX      Counter
    ACCESS      read-only
    STATUS      mandatory
    DESCRIPTION 
        " Number of Arp responses transmitted 
         ALCATEL NOTE:
             ACCESS:      NA           USAGE:       NA
             PERSIST:     NO           INSRVMOD:    NA
             RANGE:       NA           DEFVALUE:    0       
             UNITS:       ARP Packets  SPARSE:      NA
             DESCR:       NA"
    ::= { fsiparp 9 }

fsIpArpHwTable OBJECT-TYPE
    SYNTAX      SEQUENCE OF FsIpArpHwEntry
    ACCESS      not-accessible
    STATUS      mandatory
    DESCRIPTION 
        "The ARP Hardware table used for mapping
         interfaces to the Protocol using them 
         ALCATEL NOTE:
         TABLESIZE:  1
         DESCR: 	  NA"
    ::= { fsiparp 11 }

fsIpArpHwEntry OBJECT-TYPE
    SYNTAX      FsIpArpHwEntry
    ACCESS      not-accessible
    STATUS      mandatory
    DESCRIPTION 
        "Each entry contains the Hardware type and the protocol
         supporting it 
         Row creation : All the Entries are created by the system at the startup.
         Row deletion : All the Entries are deleted by the system when it shutdowns.
         Index usage : the index is the fsIpArpHwHardwareType.
         Note that entries will be presented to the SNMP manager in full
         lexicographical order :  sorted on fsIpArpHwHardwareType."
    INDEX       { fsIpArpHwHardwareType }
    ::= { fsIpArpHwTable 1 }

FsIpArpHwEntry ::= SEQUENCE {
    fsIpArpHwHardwareType   INTEGER,
    fsIpArpHwProtocolType   INTEGER
}

fsIpArpHwHardwareType OBJECT-TYPE
    SYNTAX      INTEGER (0..2147483647)
    ACCESS      not-accessible
    STATUS      mandatory
    DESCRIPTION 
        " Hardware type supported 
         ALCATEL NOTE:
             ACCESS:      NA           USAGE:       NA
             PERSIST:     NO           INSRVMOD:    NA
             RANGE:       1            DEFVALUE:    NA       
             UNITS:       NA	        SPARSE:      NO
             DESCR:       NA"
    ::= { fsIpArpHwEntry 1 }

fsIpArpHwProtocolType OBJECT-TYPE
    SYNTAX      INTEGER (0..2147483647)
    ACCESS      read-only
    STATUS      mandatory
    DESCRIPTION 
        " Protocol supported by Arp for this hardware 
         ALCATEL NOTE:
             ACCESS:      NA           USAGE:       NA
             PERSIST:     NO           INSRVMOD:    NA
             RANGE:       2048         DEFVALUE:    2048       
             UNITS:       NA	        SPARSE:      NO
             DESCR:       NA"
    ::= { fsIpArpHwEntry 2 }

fsVrfIpArpStatisticTable OBJECT-TYPE
    SYNTAX      SEQUENCE OF FsVrfIpArpStatisticEntry
    ACCESS      not-accessible
    STATUS      mandatory
    DESCRIPTION 
        "The ARP Statistics table used for storing the  
         VRF level statistics for ARP
         TABLESIZE:  128
         DESCR: 	  NA"
    ::= { fsiparp 15 }

fsVrfIpArpStatisticEntry OBJECT-TYPE
    SYNTAX      FsVrfIpArpStatisticEntry
    ACCESS      not-accessible
    STATUS      mandatory
    DESCRIPTION 
        "Each entry contains the statistics of the ARP packets 
         coming in as well as sendout in a VRF
         Row creation : An entry will be created by the system when an entry
         		is created in the lanxVrfConfigTable.
         Row deletion : An entry will be deleted by the system when an entry
         		is deleted in the lanxVrfConfigTable.
         Index usage : the index is lanxVrfId.
         Note that entries will be presented to the SNMP manager in full
         lexicographical order :  sorted on lanxVrfId."
    INDEX       { lanxVrfId }
    ::= { fsVrfIpArpStatisticTable 1 }

FsVrfIpArpStatisticEntry ::= SEQUENCE {
    fsVrfIpArpInPkts                        Counter,
    fsVrfIpArpDiscards                      Counter,
    fsVrfIpArpInRequests                    Counter,
    fsVrfIpArpInResponses                   Counter,
    fsVrfIpArpOutRequests                   Counter,
    fsVrfIpArpOutResponses                  Counter,
    fsVrfIpArpInvalidOpCodeCounter          Counter,
    fsVrfIpArpUnsupportedHWTypeCounter      Counter,
    fsVrfIpArpUnsupportedL3ProtoCounter     Counter,
    fsVrfIpArpUnsupportedAddrLenCounter     Counter,
    fsVrfIpArpInvalidSrcMacCounter          Counter,
    fsVrfIpArpInternalContextErrCounter     Counter,
    fsVrfIpArpNoFreeArpEntryCounter         Counter,
    fsVrfIpArpInvalidUserMacCounter         Counter,
    fsVrfIpArpCounterReset                  TruthValue
}

fsVrfIpArpInPkts OBJECT-TYPE
    SYNTAX      Counter
    ACCESS      read-only
    STATUS      mandatory
    DESCRIPTION 
        "The total number of Arp datagrams received from
         interfaces, including those received in error in the VRF.
         ALCATEL NOTE:
         ACCESS:      NA           USAGE:       NA
         PERSIST:     NO           INSRVMOD:    NA
         RANGE:       NA           DEFVALUE:    0       
         UNITS:       ARP Packets  SPARSE:      NO
         DESCR:       NA"
    ::= { fsVrfIpArpStatisticEntry 1 }

fsVrfIpArpDiscards OBJECT-TYPE
    SYNTAX      Counter
    ACCESS      read-only
    STATUS      mandatory
    DESCRIPTION 
        " Total number of packets discarded including,
         those with Bad Type, length, address, requests
         that were rejected in the VRF
         ALCATEL NOTE:
         ACCESS:      NA           USAGE:       NA
         PERSIST:     NO           INSRVMOD:    NA
         RANGE:       NA           DEFVALUE:    0       
         UNITS:       ARP Packets  SPARSE:      NO
         DESCR:       NA"
    ::= { fsVrfIpArpStatisticEntry 2 }

fsVrfIpArpInRequests OBJECT-TYPE
    SYNTAX      Counter
    ACCESS      read-only
    STATUS      mandatory
    DESCRIPTION 
        " Number of Arp request packets received in the VRF
         ALCATEL NOTE:
             ACCESS:      NA           USAGE:       NA
             PERSIST:     NO           INSRVMOD:    NA
             RANGE:       NA           DEFVALUE:    0       
             UNITS:       ARP Packets  SPARSE:      NO
             DESCR:       NA"
    ::= { fsVrfIpArpStatisticEntry 3 }

fsVrfIpArpInResponses OBJECT-TYPE
    SYNTAX      Counter
    ACCESS      read-only
    STATUS      mandatory
    DESCRIPTION 
        " Number of Arp response packets received in the VRF 
         ALCATEL NOTE:
             ACCESS:      NA           USAGE:       NA
             PERSIST:     NO           INSRVMOD:    NA
             RANGE:       NA           DEFVALUE:    0       
             UNITS:       ARP Packets  SPARSE:      NO
             DESCR:       NA"
    ::= { fsVrfIpArpStatisticEntry 4 }

fsVrfIpArpOutRequests OBJECT-TYPE
    SYNTAX      Counter
    ACCESS      read-only
    STATUS      mandatory
    DESCRIPTION 
        " Number of Arp requests transmitted in the VRF
         ALCATEL NOTE:
             ACCESS:      NA           USAGE:       NA
             PERSIST:     NO           INSRVMOD:    NA
             RANGE:       NA           DEFVALUE:    0       
             UNITS:       ARP Packets  SPARSE:      NO
             DESCR:       NA"
    ::= { fsVrfIpArpStatisticEntry 5 }

fsVrfIpArpOutResponses OBJECT-TYPE
    SYNTAX      Counter
    ACCESS      read-only
    STATUS      mandatory
    DESCRIPTION 
        " Number of Arp responses transmitted in the VRF
         ALCATEL NOTE:
             ACCESS:      NA           USAGE:       NA
             PERSIST:     NO           INSRVMOD:    NA
             RANGE:       NA           DEFVALUE:    0       
             UNITS:       ARP Packets  SPARSE:      NO
             DESCR:       NA"
    ::= { fsVrfIpArpStatisticEntry 6 }

fsVrfIpArpInvalidOpCodeCounter OBJECT-TYPE
    SYNTAX      Counter
    ACCESS      read-only
    STATUS      mandatory
    DESCRIPTION 
        " Number of ARP packets discarded because the 
         packet opcode  is invalid
         ALCATEL NOTE:
         ACCESS:      NA           USAGE:       NA
         PERSIST:     NO           INSRVMOD:    NA
         RANGE:       NA           DEFVALUE:    0       
         UNITS:       ARP Packets  SPARSE:      NO
         DESCR:       NA"
    ::= { fsVrfIpArpStatisticEntry 8 }

fsVrfIpArpUnsupportedHWTypeCounter OBJECT-TYPE
    SYNTAX      Counter
    ACCESS      read-only
    STATUS      mandatory
    DESCRIPTION 
        " Number of ARP packets discarded because the packet 
         contains  unsupported hardware type
         ALCATEL NOTE:
         ACCESS:      NA           USAGE:       NA
         PERSIST:     NO           INSRVMOD:    NA
         RANGE:       NA           DEFVALUE:    0       
         UNITS:       ARP Packets  SPARSE:      NO
         DESCR:       NA"
    ::= { fsVrfIpArpStatisticEntry 9 }

fsVrfIpArpUnsupportedL3ProtoCounter OBJECT-TYPE
    SYNTAX      Counter
    ACCESS      read-only
    STATUS      mandatory
    DESCRIPTION 
        " Number of ARP packets discarded because the packet 
         contains unsupported layer 3 protocol
         ALCATEL NOTE:
         ACCESS:      NA           USAGE:       NA
         PERSIST:     NO           INSRVMOD:    NA
         RANGE:       NA           DEFVALUE:    0       
         UNITS:       ARP Packets  SPARSE:      NO
         DESCR:       NA"
    ::= { fsVrfIpArpStatisticEntry 10 }

fsVrfIpArpUnsupportedAddrLenCounter OBJECT-TYPE
    SYNTAX      Counter
    ACCESS      read-only
    STATUS      mandatory
    DESCRIPTION 
        " Number of ARP packets discarded because the packet 
         contains unsupported address length
         ALCATEL NOTE:
         ACCESS:      NA           USAGE:       NA
         PERSIST:     NO           INSRVMOD:    NA
         RANGE:       NA           DEFVALUE:    0       
         UNITS:       ARP Packets  SPARSE:      NO
         DESCR:       NA"
    ::= { fsVrfIpArpStatisticEntry 11 }

fsVrfIpArpInvalidSrcMacCounter OBJECT-TYPE
    SYNTAX      Counter
    ACCESS      read-only
    STATUS      mandatory
    DESCRIPTION 
        " Number of ARP packets dropped because the packet's 
         source MAC is multicast/broadcast.
         ALCATEL NOTE:
         ACCESS:      NA           USAGE:       NA
         PERSIST:     NO           INSRVMOD:    NA
         RANGE:       NA           DEFVALUE:    0       
         UNITS:       ARP Packets  SPARSE:      NO
         DESCR:       NA"
    ::= { fsVrfIpArpStatisticEntry 12 }

fsVrfIpArpInternalContextErrCounter OBJECT-TYPE
    SYNTAX      Counter
    ACCESS      read-only
    STATUS      mandatory
    DESCRIPTION 
        " Number of ARP packets dropped because of internal context
         errors .
         ALCATEL NOTE:
         ACCESS:      NA           USAGE:       NA
         PERSIST:     NO           INSRVMOD:    NA
         RANGE:       NA           DEFVALUE:    0       
         UNITS:       ARP Packets  SPARSE:      NO
         DESCR:       NA"
    ::= { fsVrfIpArpStatisticEntry 13 }

fsVrfIpArpNoFreeArpEntryCounter OBJECT-TYPE
    SYNTAX      Counter
    ACCESS      read-only
    STATUS      mandatory
    DESCRIPTION 
        " Number of ARP packets dropped because of errors in adding to
         ARP cache because of memory allocation failures.
         ALCATEL NOTE:
         ACCESS:      NA           USAGE:       NA
         PERSIST:     NO           INSRVMOD:    NA
         RANGE:       NA           DEFVALUE:    0       
         UNITS:       ARP Packets  SPARSE:      NO
         DESCR:       NA"
    ::= { fsVrfIpArpStatisticEntry 14 }

fsVrfIpArpInvalidUserMacCounter OBJECT-TYPE
    SYNTAX      Counter
    ACCESS      read-only
    STATUS      mandatory
    DESCRIPTION 
        "Total No of  Arp packets dropped, when the src MAC  in ARP header 
         and Ethernet header are not in sync.
         
         ALCATEL NOTE:
          ACCESS:      NA           USAGE:       NA
          PERSIST:     NO           INSRVMOD:    NA
          RANGE:       NA           DEFVALUE:    0       
          UNITS:       ARP Packets  SPARSE:      NO
          DESCR:       NA"
    ::= { fsVrfIpArpStatisticEntry 15 }

fsVrfIpArpCounterReset OBJECT-TYPE
    SYNTAX      TruthValue
    ACCESS      read-write
    STATUS      mandatory
    DESCRIPTION 
        " This object is a button-like object to reset all the
         counters in the VRF. When it is set to Reset value, all
         counters are cleared.
         ALCATEL NOTE:
         ACCESS:      NA           USAGE:       NA
         PERSIST:     NO           INSRVMOD:    NA
         RANGE:       NA           DEFVALUE:    2       
         UNITS:       ARP Packets  SPARSE:      NO
         DESCR:       NA"
    DEFVAL      { false }
    ::= { fsVrfIpArpStatisticEntry 17 }

fsIpArpProxyTable OBJECT-TYPE
    SYNTAX      SEQUENCE OF FsIpArpProxyEntry
    ACCESS      not-accessible
    STATUS      mandatory
    DESCRIPTION 
        "The proxy arp table 
         ALCATEL NOTE:
           TABLESIZE: DEP 
          	DESCR:	 DEP(TABLESIZE):The size of the table is derived from the 
         			       total number of IP addresses in the system."
    ::= { fsiparp 16 }

fsIpArpProxyEntry OBJECT-TYPE
    SYNTAX      FsIpArpProxyEntry
    ACCESS      not-accessible
    STATUS      mandatory
    DESCRIPTION 
        "An entry represents if proxy ARP can be enabled or disabled over an interface.
         Row creation : A entry shall be created in one step by a
             		set-request with all necessary parameter values and
             		fsIpArpProxyStatus set to Enabled(1) or Disabled(2). 
         			Note: It shall be created only on Fast Path VRF.
         Row deletion : All the Entries are deleted by the system when the 
         			IP Interface is deleted.
         Index usage : the index is fsIpArpProxyIfIndex and fsIpArpProxyIfAddr.
           Note that entries will be presented to the SNMP manager in full
           lexicographical order :  sorted on fsIpArpProxyIfIndex and fsIpArpProxyIfAddr."
    INDEX       { fsIpArpProxyIfIndex, fsIpArpProxyIfAddr }
    ::= { fsIpArpProxyTable 1 }

FsIpArpProxyEntry ::= SEQUENCE {
    fsIpArpProxyIfIndex     INTEGER,
    fsIpArpProxyIfAddr      IpAddress,
    fsIpArpProxyStatus      INTEGER
}

fsIpArpProxyIfIndex OBJECT-TYPE
    SYNTAX      INTEGER (1..2147483647)
    ACCESS      not-accessible
    STATUS      mandatory
    DESCRIPTION 
        " The Interface Index of the IP interface address on which Proxy ARP is 
         enabled or disabled.The IP interface must be associated with fast path VRF.
         ALCATEL NOTE:
         ACCESS:      NA           USAGE:       NA
         PERSIST:     YES          INSRVMOD:    NA
         RANGE:       DEP          DEFVALUE:    NA
         UNITS:       NA           SPARSE:      NO
         DESCR:       DEP(RANGE): The range is from (maximum value of number of physical interfaces available in the system + 1) 
         		to (the total number of IP interfaces in the system  + 
         		maximum value of number of physical interfaces available in the system). 
         		The maximum number of physical interfaces is obtained from the object issSystemNumberOfPorts in fsiss.mib. 
         		The total number of IP interfaces in the system is obtained from the object fsVrfMaxIpInterfaces in fsvrf.mib"
    ::= { fsIpArpProxyEntry 1 }

fsIpArpProxyIfAddr OBJECT-TYPE
    SYNTAX      IpAddress
    ACCESS      read-only
    STATUS      mandatory
    DESCRIPTION 
        "The IP interface address over which proxy ARP is enabled or disabled.
         This interface MUST be associated with a FAST PATH VRF.
         ALCATEL NOTE:
         ACCESS:      NA           USAGE:       NA
         PERSIST:     YES          INSRVMOD:    NA
         RANGE:       NA           DEFVALUE:    NA
         UNITS:       NA           SPARSE:      NO
         DESCR:       NA"
    ::= { fsIpArpProxyEntry 2 }

fsIpArpProxyStatus OBJECT-TYPE
    SYNTAX      INTEGER { enabled(1), disabled(2) }
    ACCESS      read-write
    STATUS      mandatory
    DESCRIPTION 
        " Indication if Proxy is enabled 
         ALCATEL NOTE:
             ACCESS:      NA           USAGE:       NA
             PERSIST:     YES          INSRVMOD:    YES
             RANGE:       NA           DEFVALUE:    2
             UNITS:       NA           SPARSE:      NO
             DESCR:       NA"
    DEFVAL      { disabled }
    ::= { fsIpArpProxyEntry 3 }

fsIpArpNumARPEntriesAllVrf OBJECT-TYPE
    SYNTAX      INTEGER
    ACCESS      read-only
    STATUS      mandatory
    DESCRIPTION 
        "The total number of ARP entries in all VRFs
         ALCATEL NOTE:
             ACCESS:      NA           USAGE:       NA
             PERSIST:     NO           INSRVMOD:    YES
             RANGE:       NA	      DEFVALUE:    NA    
             UNITS:       ARP Entries  SPARSE:      NA
             DESCR:       NA"
    DEFVAL      { 0 }
    ::= { fsiparp 17 }

fsVrfIpArpConfigTable OBJECT-TYPE
    SYNTAX      SEQUENCE OF FsVrfIpArpConfigEntry
    ACCESS      not-accessible
    STATUS      mandatory
    DESCRIPTION 
        "The ARP Config table used for storing the  
         VRF level configs for ARP
         TABLESIZE:  128
         DESCR: 	  NA"
    ::= { fsiparp 18 }

fsVrfIpArpConfigEntry OBJECT-TYPE
    SYNTAX      FsVrfIpArpConfigEntry
    ACCESS      not-accessible
    STATUS      mandatory
    DESCRIPTION 
        "Each entry contains the number of the ARP entries 
         that can be configured per VRF
         Row creation : An entry will be created by the system when an entry
         		is created in the lanxVrfConfigTable.
         Row deletion : An entry will be deleted by the system when an entry
         		is deleted in the lanxVrfConfigTable.
         Index usage : the index is lanxVrfId.
         Note that entries will be presented to the SNMP manager in full
         lexicographical order :  sorted on lanxVrfId."
    INDEX       { lanxVrfId }
    ::= { fsVrfIpArpConfigTable 1 }

FsVrfIpArpConfigEntry ::= SEQUENCE {
    fsVrfIpArpMaxEntriesPerVrf  INTEGER,
    fsVrfIpArpNumEntriesPerVrf  INTEGER
}

fsVrfIpArpMaxEntriesPerVrf OBJECT-TYPE
    SYNTAX      INTEGER (-1..8192)
    ACCESS      read-write
    STATUS      mandatory
    DESCRIPTION 
        "The Max number of Arp Entries that can be learned per VRF
         The '-1' indicates there is no restrction for this mib object.
         ALCATEL NOTE:
         ACCESS:      NA           USAGE:       NA
         PERSIST:     YES          INSRVMOD:    NA
         RANGE:       NA           DEFVALUE:    NA       
         UNITS:       ARP Entries  SPARSE:      NO
         DESCR:       NA"
    DEFVAL      { -1 }
    ::= { fsVrfIpArpConfigEntry 1 }

fsVrfIpArpNumEntriesPerVrf OBJECT-TYPE
    SYNTAX      INTEGER
    ACCESS      read-only
    STATUS      mandatory
    DESCRIPTION 
        "The Current number of Arp Entries learned per VRF.
         ALCATEL NOTE:
             ACCESS:      NA           USAGE:       NA
             PERSIST:     NO           INSRVMOD:    NA
             RANGE:       NA           DEFVALUE:    NA       
             UNITS:       ARP Entries  SPARSE:      NO
             DESCR:       NA"
    DEFVAL      { 0 }
    ::= { fsVrfIpArpConfigEntry 2 }

fsicmp OBJECT IDENTIFIER
    ::= { futureip 3 }

fsIcmpSendRedirectEnable OBJECT-TYPE
    SYNTAX      INTEGER { enabled(1), disabled(2) }
    ACCESS      read-write
    STATUS      mandatory
    DESCRIPTION 
        " Allow sending ICMP Redirect Message 
         ALCATEL NOTE:
             ACCESS:      NA           USAGE:       NA
             PERSIST:     YES          INSRVMOD:    YES
             RANGE:       NA	      DEFVALUE:    NA    
             UNITS:       NA	      SPARSE:      NA
             DESCR:       NA"
    DEFVAL      { enabled }
    ::= { fsicmp 1 }

fsIcmpSendUnreachableEnable OBJECT-TYPE
    SYNTAX      INTEGER { enabled(1), disabled(2) }
    ACCESS      read-write
    STATUS      mandatory
    DESCRIPTION 
        " Allow sending ICMP Unreachable Message  
         ALCATEL NOTE:
             ACCESS:      NA           USAGE:       NA
             PERSIST:     YES          INSRVMOD:    YES
             RANGE:       NA	      DEFVALUE:    NA    
             UNITS:       NA	      SPARSE:      NA
             DESCR:       NA"
    DEFVAL      { enabled }
    ::= { fsicmp 2 }

fsIcmpSendEchoReplyEnable OBJECT-TYPE
    SYNTAX      INTEGER { enabled(1), disabled(2) }
    ACCESS      read-write
    STATUS      mandatory
    DESCRIPTION 
        " Allow sending ICMP Echo Reply Message  
         ALCATEL NOTE:
             ACCESS:      NA           USAGE:       NA
             PERSIST:     YES          INSRVMOD:    YES
             RANGE:       NA	      DEFVALUE:    NA    
             UNITS:       NA	      SPARSE:      NA
             DESCR:       NA"
    DEFVAL      { enabled }
    ::= { fsicmp 3 }

fsIcmpNetMaskReplyEnable OBJECT-TYPE
    SYNTAX      INTEGER { enabled(1), disabled(2) }
    ACCESS      read-write
    STATUS      mandatory
    DESCRIPTION 
        " Allow sending ICMP Net Mask Reply Message  
         ALCATEL NOTE:
             ACCESS:      NA           USAGE:       NA
             PERSIST:     YES          INSRVMOD:    YES
             RANGE:       NA	      DEFVALUE:    NA    
             UNITS:       NA	      SPARSE:      NA
             DESCR:       NA"
    DEFVAL      { enabled }
    ::= { fsicmp 4 }

fsIcmpTimeStampReplyEnable OBJECT-TYPE
    SYNTAX      INTEGER { enabled(1), disabled(2) }
    ACCESS      read-write
    STATUS      mandatory
    DESCRIPTION 
        " Allow sending ICMP Time stamp reply Message  
         ALCATEL NOTE:
             ACCESS:      NA           USAGE:       NA
             PERSIST:     YES          INSRVMOD:    YES
             RANGE:       NA	      DEFVALUE:    NA    
             UNITS:       NA	      SPARSE:      NA
             DESCR:       NA"
    DEFVAL      { enabled }
    ::= { fsicmp 5 }

fsIcmpInDomainNameRequests OBJECT-TYPE
    SYNTAX      Counter
    ACCESS      read-only
    STATUS      mandatory
    DESCRIPTION 
        "The number of ICMP Domain Name Requests
         received.
         ALCATEL NOTE:
         ACCESS:      NA           USAGE:       NA
         PERSIST:     NO           INSRVMOD:    NA
         RANGE:       NA           DEFVALUE:    0       
         UNITS:       ICMP Packets SPARSE:      NA
         DESCR:       NA"
    ::= { fsicmp 6 }

fsIcmpInDomainNameReply OBJECT-TYPE
    SYNTAX      Counter
    ACCESS      read-only
    STATUS      mandatory
    DESCRIPTION 
        "The number of ICMP Domain Name Replies
         received.
         ALCATEL NOTE:
         ACCESS:      NA           USAGE:       NA
         PERSIST:     NO           INSRVMOD:    NA
         RANGE:       NA           DEFVALUE:    0       
         UNITS:       ICMP Packets SPARSE:      NA
         DESCR:       NA"
    ::= { fsicmp 7 }

fsIcmpOutDomainNameRequests OBJECT-TYPE
    SYNTAX      Counter
    ACCESS      read-only
    STATUS      mandatory
    DESCRIPTION 
        "The number of ICMP Domain Name Requests
         send.
         ALCATEL NOTE:
         ACCESS:      NA           USAGE:       NA
         PERSIST:     NO           INSRVMOD:    NA
         RANGE:       NA           DEFVALUE:    0       
         UNITS:       ICMP Packets SPARSE:      NA
         DESCR:       NA"
    ::= { fsicmp 8 }

fsIcmpOutDomainNameReply OBJECT-TYPE
    SYNTAX      Counter
    ACCESS      read-only
    STATUS      mandatory
    DESCRIPTION 
        "The number of ICMP Domain Name Replies
         send.
         ALCATEL NOTE:
         ACCESS:      NA           USAGE:       NA
         PERSIST:     NO           INSRVMOD:    NA
         RANGE:       NA           DEFVALUE:    0       
         UNITS:       ICMP Packets SPARSE:      NA
         DESCR:       NA"
    ::= { fsicmp 9 }

fsIcmpDirectQueryEnable OBJECT-TYPE
    SYNTAX      INTEGER { enabled(1), disabled(2) }
    ACCESS      read-write
    STATUS      mandatory
    DESCRIPTION 
        "DNS Direct Query will be enabled or disabled
         accordingly 
         ALCATEL NOTE:
         ACCESS:      NA           USAGE:       NA
         PERSIST:     YES          INSRVMOD:    YES
         RANGE:       NA	      DEFVALUE:    NA    
         UNITS:       NA	      SPARSE:      NA
         DESCR:       NA"
    DEFVAL      { disabled }
    ::= { fsicmp 10 }

fsDomainName OBJECT-TYPE
    SYNTAX      DisplayString
    ACCESS      read-write
    STATUS      mandatory
    DESCRIPTION 
        "Domain Name of the system, used to send when
         replies to DNS Direct Query.
         ALCATEL NOTE:
         ACCESS:      NA           USAGE:       NA
         PERSIST:     YES          INSRVMOD:    YES
         RANGE:       NA           DEFVALUE:    '\0'    
         UNITS:       NA	      SPARSE:      NA
         DESCR:       NA"
    ::= { fsicmp 11 }

fsTimeToLive OBJECT-TYPE
    SYNTAX      INTEGER (0..2147483647)
    ACCESS      read-write
    STATUS      mandatory
    DESCRIPTION 
        "The number of seconds untill which the name
         can be cached.
         ALCATEL NOTE:
         ACCESS:      NA           USAGE:       NA
         PERSIST:     YES          INSRVMOD:    YES
         RANGE:       NA	      DEFVALUE:    600
         UNITS:       seconds      SPARSE:      NA
         DESCR:       NA"
    ::= { fsicmp 12 }

fsIcmpInSecurityFailures OBJECT-TYPE
    SYNTAX      Counter
    ACCESS      read-only
    STATUS      mandatory
    DESCRIPTION 
        "The number of ICMP Security Failure messages
         received.
         ALCATEL NOTE:
         ACCESS:      NA           USAGE:       NA
         PERSIST:     NO           INSRVMOD:    NA
         RANGE:       NA           DEFVALUE:    0       
         UNITS:       ICMP Packets SPARSE:      NA
         DESCR:       NA"
    ::= { fsicmp 13 }

fsIcmpOutSecurityFailures OBJECT-TYPE
    SYNTAX      Counter
    ACCESS      read-only
    STATUS      mandatory
    DESCRIPTION 
        "The number of ICMP Security Failure messages
         sent.
         ALCATEL NOTE:
         ACCESS:      NA           USAGE:       NA
         PERSIST:     NO           INSRVMOD:    NA
         RANGE:       NA           DEFVALUE:    0       
         UNITS:       ICMP Packets SPARSE:      NA
         DESCR:       NA"
    ::= { fsicmp 14 }

fsIcmpSendSecurityFailuresEnable OBJECT-TYPE
    SYNTAX      INTEGER { enabled(1), disabled(2) }
    ACCESS      read-write
    STATUS      mandatory
    DESCRIPTION 
        "Allow sending Security Failure messages. 
         ALCATEL NOTE:
             ACCESS:      NA           USAGE:       NA
             PERSIST:     YES          INSRVMOD:    YES
             RANGE:       NA	      DEFVALUE:    NA    
             UNITS:       NA	      SPARSE:      NA
             DESCR:       NA"
    DEFVAL      { enabled }
    ::= { fsicmp 15 }

fsIcmpRecvSecurityFailuresEnable OBJECT-TYPE
    SYNTAX      INTEGER { enabled(1), disabled(2) }
    ACCESS      read-write
    STATUS      mandatory
    DESCRIPTION 
        "Allow Recieving Security Failure messages. 
         ALCATEL NOTE:
             ACCESS:      NA           USAGE:       NA
             PERSIST:     YES          INSRVMOD:    YES
             RANGE:       NA	      DEFVALUE:    NA    
             UNITS:       NA	      SPARSE:      NA
             DESCR:       NA"
    DEFVAL      { enabled }
    ::= { fsicmp 16 }

fsudp OBJECT IDENTIFIER
    ::= { futureip 4 }

fsUdpInNoCksum OBJECT-TYPE
    SYNTAX      Counter
    ACCESS      read-only
    STATUS      mandatory
    DESCRIPTION 
        " Number of UDP datagrams received without
         checksum 
         ALCATEL NOTE:
         ACCESS:      NA           USAGE:       NA
         PERSIST:     NO           INSRVMOD:    NA
         RANGE:       NA           DEFVALUE:    0       
         UNITS:       UDP Packets  SPARSE:      NA
         DESCR:       NA"
    ::= { fsudp 1 }

fsUdpInIcmpErr OBJECT-TYPE
    SYNTAX      Counter
    ACCESS      read-only
    STATUS      mandatory
    DESCRIPTION 
        " Number of ICMP error packets received 
         ALCATEL NOTE:
             ACCESS:      NA           USAGE:       NA
             PERSIST:     NO           INSRVMOD:    NA
             RANGE:       NA           DEFVALUE:    0       
             UNITS:       ICMP Packets SPARSE:      NA
             DESCR:       NA"
    ::= { fsudp 2 }

fsUdpInErrCksum OBJECT-TYPE
    SYNTAX      Counter
    ACCESS      read-only
    STATUS      mandatory
    DESCRIPTION 
        " Number of UDP packets received with wrong
         checksum 
         ALCATEL NOTE:
         ACCESS:      NA           USAGE:       NA
         PERSIST:     NO           INSRVMOD:    NA
         RANGE:       NA           DEFVALUE:    0       
         UNITS:       UDP Packets  SPARSE:      NA
         DESCR:       NA"
    ::= { fsudp 3 }

fsUdpInBcast OBJECT-TYPE
    SYNTAX      Counter
    ACCESS      read-only
    STATUS      mandatory
    DESCRIPTION 
        " Number of UDP packets received in broadcast mode 
         ALCATEL NOTE:
             ACCESS:      NA           USAGE:       NA
             PERSIST:     NO           INSRVMOD:    NA
             RANGE:       NA           DEFVALUE:    0       
             UNITS:       UDP Packets  SPARSE:      NA
             DESCR:       NA"
    ::= { fsudp 4 }

fscidr OBJECT IDENTIFIER
    ::= { futureip 5 }

fsCidrAggTable OBJECT-TYPE
    SYNTAX      SEQUENCE OF FsCidrAggEntry
    ACCESS      not-accessible
    STATUS      mandatory
    DESCRIPTION 
        "The (conceptual) table listing the router's
         supernet routes.RIP advertises only supernet
         routes on the speicified interface. And it
         suppresses all routes which are subset of the supernet.
         ALCATEL NOTE:
         TABLESIZE:   NA
         DESCR:       This object is not used by Alcatel"
    ::= { fscidr 1 }

fsCidrAggEntry OBJECT-TYPE
    SYNTAX      FsCidrAggEntry
    ACCESS      not-accessible
    STATUS      mandatory
    DESCRIPTION 
        "An entry (conceptual row) in the
         fsCidrAggTable representing supertnet route for
         the domain.
         Row creation : NA
         Row deletion : NA
         Index usage :  NA
         Lexicographical order :  NA
         This object is not used by Alcatel"
    INDEX       { fsCidrAggAddress, fsCidrAggAddressMask }
    ::= { fsCidrAggTable 1 }

FsCidrAggEntry ::= SEQUENCE {
    fsCidrAggAddress        IpAddress,
    fsCidrAggAddressMask    IpAddress,
    fsCidrAggStatus         RowStatus
}

fsCidrAggAddress OBJECT-TYPE
    SYNTAX      IpAddress
    ACCESS      not-accessible
    STATUS      mandatory
    DESCRIPTION 
        "The aggregated address which when combined with the
         corresponding value of fsCidrAggAddressMask
         identifies the supernet route for this domain.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsCidrAggEntry 1 }

fsCidrAggAddressMask OBJECT-TYPE
    SYNTAX      IpAddress
    ACCESS      not-accessible
    STATUS      mandatory
    DESCRIPTION 
        "The aggregated address mask which when combined with
         the corresponding value of fsCidrAggAddress
         identifies the supernet route for the domain.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsCidrAggEntry 2 }

fsCidrAggStatus OBJECT-TYPE
    SYNTAX      RowStatus
    ACCESS      read-write
    STATUS      mandatory
    DESCRIPTION 
        "The status of this row, by which new entries may be
         created, or old entries deleted from this table.
         ALCATEL NOTE:
         ACCESS:      NA           USAGE:       NA
         PERSIST:     NA           INSRVMOD:    NA
         RANGE:       NA           DEFVALUE:    NA
         UNITS:       NA	        SPARSE:      NA
         DESCR:       This object is not used by Alcatel"
    ::= { fsCidrAggEntry 3 }

fsCidrAdvertTable OBJECT-TYPE
    SYNTAX      SEQUENCE OF FsCidrAdvertEntry
    ACCESS      not-accessible
    STATUS      mandatory
    DESCRIPTION 
        "The (conceptual) table listing the routes that are to
         be explicitly advertised on a specific interface,
         for multi-homed reasons, or policy reasons 
         ALCATEL NOTE:
         TABLESIZE:   NA
         DESCR:       This object is not used by Alcatel"
    ::= { fscidr 2 }

fsCidrAdvertEntry OBJECT-TYPE
    SYNTAX      FsCidrAdvertEntry
    ACCESS      not-accessible
    STATUS      mandatory
    DESCRIPTION 
        "An entry (conceptual row) in the
         fsCidrAdvertTable representing a route to be explicitly
         advertised on a specific interface.
         Row creation : NA
         Row deletion : NA
         Index usage :  NA
         Lexicographical order :  NA
         This object is not used by Alcatel"
    INDEX       { fsCidrAdvertAddress, fsCidrAdvertAddressMask }
    ::= { fsCidrAdvertTable 1 }

FsCidrAdvertEntry ::= SEQUENCE {
    fsCidrAdvertAddress         IpAddress,
    fsCidrAdvertAddressMask     IpAddress,
    fsCidrAdvertStatus          RowStatus
}

fsCidrAdvertAddress OBJECT-TYPE
    SYNTAX      IpAddress
    ACCESS      not-accessible
    STATUS      mandatory
    DESCRIPTION 
        "The network address which when combined with the
         corresponding value of fsCidrAdvertAddressMask
         identifies the route that is to be explicitly advertised.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsCidrAdvertEntry 1 }

fsCidrAdvertAddressMask OBJECT-TYPE
    SYNTAX      IpAddress
    ACCESS      not-accessible
    STATUS      mandatory
    DESCRIPTION 
        "The destination network address mask which when
         combined with the corresponding value of
         fsCidrAdvertAddress identifies the route to be
         explicitly advertised.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsCidrAdvertEntry 2 }

fsCidrAdvertStatus OBJECT-TYPE
    SYNTAX      RowStatus
    ACCESS      read-write
    STATUS      mandatory
    DESCRIPTION 
        "The status of this row, by which new entries may be
         created, or old entries deleted from this table.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsCidrAdvertEntry 3 }

fsipinarp OBJECT IDENTIFIER
    ::= { futureip 6 }

fsIpInArpRetryInterval OBJECT-TYPE
    SYNTAX      INTEGER (30..3000)
    ACCESS      read-write
    STATUS      mandatory
    DESCRIPTION 
        " The interval after which an unanswered InArp
         request should be retransmitted  
         ALCATEL NOTE:
         ACCESS:      NA           USAGE:       NA
         PERSIST:     YES          INSRVMOD:    YES
         RANGE:       NA	      DEFVALUE:    NA    
         UNITS:       seconds      SPARSE:      NA
         DESCR:       NA"
    DEFVAL      { 30 }
    ::= { fsipinarp 1 }

fsIpInArpMaxRetries OBJECT-TYPE
    SYNTAX      INTEGER (2..10)
    ACCESS      read-write
    STATUS      mandatory
    DESCRIPTION 
        "Maximum number of retry attempts before aborting
         resolving   
         ALCATEL NOTE:
         ACCESS:      NA           USAGE:       NA
         PERSIST:     YES          INSRVMOD:    YES
         RANGE:       NA	      DEFVALUE:    NA    
         UNITS:       NA	      SPARSE:      NA
         DESCR:       NA"
    DEFVAL      { 3 }
    ::= { fsipinarp 2 }

fsIpInArpRequestsIn OBJECT-TYPE
    SYNTAX      Counter
    ACCESS      read-only
    STATUS      mandatory
    DESCRIPTION 
        "The total number of InArpReq datagrams received from
         interfaces, including those received in error.
         ALCATEL NOTE:
         ACCESS:      NA           USAGE:       NA
         PERSIST:     NO           INSRVMOD:    NA
         RANGE:       NA           DEFVALUE:    0       
         UNITS:       ARP Packets  SPARSE:      NA
         DESCR:       NA"
    ::= { fsipinarp 3 }

fsIpInArpRequestsOut OBJECT-TYPE
    SYNTAX      Counter
    ACCESS      read-only
    STATUS      mandatory
    DESCRIPTION 
        "The total number of InArpReq datagrams sent from
         interfaces, including those sent with error.
         ALCATEL NOTE:
         ACCESS:      NA           USAGE:       NA
         PERSIST:     NO           INSRVMOD:    NA
         RANGE:       NA           DEFVALUE:    0       
         UNITS:       ARP Packets  SPARSE:      NA
         DESCR:       NA"
    ::= { fsipinarp 4 }

fsIpInArpRepliesIn OBJECT-TYPE
    SYNTAX      Counter
    ACCESS      read-only
    STATUS      mandatory
    DESCRIPTION 
        "The total number of InArpReply datagrams got 
         ALCATEL NOTE:
             ACCESS:      NA           USAGE:       NA
             PERSIST:     NO           INSRVMOD:    NA
             RANGE:       NA           DEFVALUE:    0       
             UNITS:       ARP Packets  SPARSE:      NA
             DESCR:       NA"
    ::= { fsipinarp 5 }

fsIpInArpRepliesOut OBJECT-TYPE
    SYNTAX      Counter
    ACCESS      read-only
    STATUS      mandatory
    DESCRIPTION 
        "The total number of InArpReply datagrams sent
         ALCATEL NOTE:
             ACCESS:      NA           USAGE:       NA
             PERSIST:     NO           INSRVMOD:    NA
             RANGE:       NA           DEFVALUE:    0       
             UNITS:       ARP Packets  SPARSE:      NA
             DESCR:       NA"
    ::= { fsipinarp 6 }

fsIpInArpInvalidRequestsIn OBJECT-TYPE
    SYNTAX      Counter
    ACCESS      read-only
    STATUS      mandatory
    DESCRIPTION 
        "The total number of invalid InArpReq datagrams got,
         ie those for which a reply was not generated.
         ALCATEL NOTE:
         ACCESS:      NA           USAGE:       NA
         PERSIST:     NO           INSRVMOD:    NA
         RANGE:       NA           DEFVALUE:    0       
         UNITS:       ARP Packets  SPARSE:      NA
         DESCR:       NA"
    ::= { fsipinarp 7 }

fsIpInArpInvalidRequestsOut OBJECT-TYPE
    SYNTAX      Counter
    ACCESS      read-only
    STATUS      mandatory
    DESCRIPTION 
        "The total number of invalid InArpReq datagrams sent,
         ie those for which a reply was not got.
         ALCATEL NOTE:
         ACCESS:      NA           USAGE:       NA
         PERSIST:     NO           INSRVMOD:    NA
         RANGE:       NA           DEFVALUE:    0       
         UNITS:       ARP Packets  SPARSE:      NA
         DESCR:       NA"
    ::= { fsipinarp 8 }

fsigmp OBJECT IDENTIFIER
    ::= { futureip 7 }

fsIgmpGlobalStatus OBJECT-TYPE
    SYNTAX      INTEGER { up(1), down(2) }
    ACCESS      read-write
    STATUS      mandatory
    DESCRIPTION 
        "This variable controls the global status of 
         the IGMP protocol in the router. It must be
         made up for protocol functioning.Making this 
         object 'down' will remove all dynamic entries
          fsMcastRouteTable, stop all the timers for route 
         entries and disables IGMP on all the IGMP enabled 
         interfaces.  Default value of this entry will 
         be 'down'.
         ALCATEL NOTE:
         ACCESS:      NA           USAGE:       NA
         PERSIST:     NA           INSRVMOD:    NA
         RANGE:       NA           DEFVALUE:    NA
         UNITS:       NA	      SPARSE:      NA
         DESCR:       This object is not used by Alcatel"
    DEFVAL      { down }
    ::= { fsigmp 1 }

fsIgmpInterfaceTable OBJECT-TYPE
    SYNTAX      SEQUENCE OF FsIgmpInterfaceEntry
    ACCESS      not-accessible
    STATUS      mandatory
    DESCRIPTION 
        "This table contains the IGMP configuration for all the
         ports in the system.
         ALCATEL NOTE:
         TABLESIZE:	 NA
         DESCR:       This object is not used by Alcatel"
    ::= { fsigmp 2 }

fsIgmpInterfaceEntry OBJECT-TYPE
    SYNTAX      FsIgmpInterfaceEntry
    ACCESS      not-accessible
    STATUS      mandatory
    DESCRIPTION 
        "Each entry contains the necessary information of IGMP
         configuration on a logical interface.
         Row creation : NA
         Row deletion : NA
         Index usage :  NA
         Lexicographical order :  NA
         This object is not used by Alcatel"
    INDEX       { fsIgmpInterfaceIfIndex }
    ::= { fsIgmpInterfaceTable 1 }

FsIgmpInterfaceEntry ::= SEQUENCE {
    fsIgmpInterfaceIfIndex          INTEGER,
    fsIgmpInterfaceVersion          INTEGER,
    fsIgmpInterfaceQueryInterval    INTEGER,
    fsIgmpInterfaceMaxResponseTime  INTEGER,
    fsIgmpInterfaceAdminStatus      INTEGER,
    fsIgmpInterfaceIncomingPkts     Counter,
    fsIgmpInterfaceIncomingJoins    Counter,
    fsIgmpInterfaceIncomingLeaves   Counter,
    fsIgmpInterfaceIncomingQueries  Counter,
    fsIgmpInterfaceOutgoingQueries  Counter
}

fsIgmpInterfaceIfIndex OBJECT-TYPE
    SYNTAX      INTEGER (0..2147483647)
    ACCESS      not-accessible
    STATUS      mandatory
    DESCRIPTION 
        "The index value which identifies the
         interface to which this entry is applicable. The
         interface identified by a particular value of this
         index is the same interface as identified by the same
         value of ifIndex in MIB II.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsIgmpInterfaceEntry 1 }

fsIgmpInterfaceVersion OBJECT-TYPE
    SYNTAX      INTEGER { version1(1), version2(2) }
    ACCESS      read-write
    STATUS      mandatory
    DESCRIPTION 
        "The version of IGMP running on this interface.
         
         Version 1 of IGMP will disable the processing of Leave
         Reports and Group Membership Reports from IGMPV2 hosts
         on this interface.Also, the Max Response Time field in
         the IGMP packet will be made zero.
         ALCATEL NOTE:
         ACCESS:      NA           USAGE:       NA
         PERSIST:     NA           INSRVMOD:    NA
         RANGE:       NA           DEFVALUE:    NA
         UNITS:       NA	      SPARSE:      NA
         DESCR:       This object is not used by Alcatel"
    DEFVAL      { version2 }
    ::= { fsIgmpInterfaceEntry 2 }

fsIgmpInterfaceQueryInterval OBJECT-TYPE
    SYNTAX      INTEGER (60..600)
    ACCESS      read-write
    STATUS      mandatory
    DESCRIPTION 
        "The frequency at which IGMP Host-Query packets are
         transmitted on this interface.
         ALCATEL NOTE:
         ACCESS:      NA           USAGE:       NA
         PERSIST:     NA           INSRVMOD:    NA
         RANGE:       NA           DEFVALUE:    NA
         UNITS:       NA	      SPARSE:      NA
         DESCR:       This object is not used by Alcatel"
    DEFVAL      { 125 }
    ::= { fsIgmpInterfaceEntry 3 }

fsIgmpInterfaceMaxResponseTime OBJECT-TYPE
    SYNTAX      INTEGER (10..25)
    ACCESS      read-write
    STATUS      mandatory
    DESCRIPTION 
        "The maximum query response time advertised in IGMPv2
         queries on this interface. Smaller values allow a router
         to prune groups faster. If IGMP version 1 is chosen for
         this interface, this object will have the value of '0'
         only and cannot be changed.
         ALCATEL NOTE:
         ACCESS:      NA           USAGE:       NA
         PERSIST:     NA           INSRVMOD:    NA
         RANGE:       NA           DEFVALUE:    NA
         UNITS:       NA	      SPARSE:      NA
         DESCR:       This object is not used by Alcatel"
    DEFVAL      { 10 }
    ::= { fsIgmpInterfaceEntry 4 }

fsIgmpInterfaceAdminStatus OBJECT-TYPE
    SYNTAX      INTEGER { up(1), down(2), invalid(3) }
    ACCESS      read-write
    STATUS      mandatory
    DESCRIPTION 
        "To create an entry in the table, this object must be set
         to 'up'. Setting this object to 'invalid' will
         delete the entry.
         Setting this field to 'down' will disable IGMP on
         this interface.
         ALCATEL NOTE:
         ACCESS:      NA           USAGE:       NA
         PERSIST:     NA           INSRVMOD:    NA
         RANGE:       NA           DEFVALUE:    NA
         UNITS:       NA	      SPARSE:      NA
         DESCR:       This object is not used by Alcatel"
    DEFVAL      { up }
    ::= { fsIgmpInterfaceEntry 5 }

fsIgmpInterfaceIncomingPkts OBJECT-TYPE
    SYNTAX      Counter
    ACCESS      read-only
    STATUS      mandatory
    DESCRIPTION 
        "The Total Incoming igmp Packets counter.
         ALCATEL NOTE:
             ACCESS:      NA           USAGE:       NA
             PERSIST:     NA           INSRVMOD:    NA
             RANGE:       NA           DEFVALUE:    NA
             UNITS:       NA	      SPARSE:      NA
             DESCR:       This object is not used by Alcatel"
    ::= { fsIgmpInterfaceEntry 6 }

fsIgmpInterfaceIncomingJoins OBJECT-TYPE
    SYNTAX      Counter
    ACCESS      read-only
    STATUS      mandatory
    DESCRIPTION 
        "The Total Incoming JoinGroupMessage  counter.
         ALCATEL NOTE:
             ACCESS:      NA           USAGE:       NA
             PERSIST:     NA           INSRVMOD:    NA
             RANGE:       NA           DEFVALUE:    NA
             UNITS:       NA	      SPARSE:      NA
             DESCR:       This object is not used by Alcatel"
    ::= { fsIgmpInterfaceEntry 7 }

fsIgmpInterfaceIncomingLeaves OBJECT-TYPE
    SYNTAX      Counter
    ACCESS      read-only
    STATUS      mandatory
    DESCRIPTION 
        "The Total Incoming LeaveGroupMessage counter.
         ALCATEL NOTE:
             ACCESS:      NA           USAGE:       NA
             PERSIST:     NA           INSRVMOD:    NA
             RANGE:       NA           DEFVALUE:    NA
             UNITS:       NA	      SPARSE:      NA
             DESCR:       This object is not used by Alcatel"
    ::= { fsIgmpInterfaceEntry 8 }

fsIgmpInterfaceIncomingQueries OBJECT-TYPE
    SYNTAX      Counter
    ACCESS      read-only
    STATUS      mandatory
    DESCRIPTION 
        "The Total Incoming Queries counter.
         ALCATEL NOTE:
             ACCESS:      NA           USAGE:       NA
             PERSIST:     NA           INSRVMOD:    NA
             RANGE:       NA           DEFVALUE:    NA
             UNITS:       NA	      SPARSE:      NA
             DESCR:       This object is not used by Alcatel"
    ::= { fsIgmpInterfaceEntry 9 }

fsIgmpInterfaceOutgoingQueries OBJECT-TYPE
    SYNTAX      Counter
    ACCESS      read-only
    STATUS      mandatory
    DESCRIPTION 
        "The Total Outgoing Queries counter.
         ALCATEL NOTE:
             ACCESS:      NA           USAGE:       NA
             PERSIST:     NA           INSRVMOD:    NA
             RANGE:       NA           DEFVALUE:    NA
             UNITS:       NA	      SPARSE:      NA
             DESCR:       This object is not used by Alcatel"
    ::= { fsIgmpInterfaceEntry 10 }

fsMcastRouteTable OBJECT-TYPE
    SYNTAX      SEQUENCE OF FsMcastRouteEntry
    ACCESS      not-accessible
    STATUS      mandatory
    DESCRIPTION 
        "This table contains the existing entries of the
         multicast route table.
         ALCATEL NOTE:
         TABLESIZE:	 NA
         DESCR:       This object is not used by Alcatel"
    ::= { fsigmp 3 }

fsMcastRouteEntry OBJECT-TYPE
    SYNTAX      FsMcastRouteEntry
    ACCESS      not-accessible
    STATUS      mandatory
    DESCRIPTION 
        "Each entry contains an unique multicast group on a
         logical interface.
         Row creation : NA
         Row deletion : NA
         Index usage :  NA
         Lexicographical order :  NA
         This object is not used by Alcatel"
    INDEX       { fsMcastRouteAddress, fsMcastRouteIfIndex }
    ::= { fsMcastRouteTable 1 }

FsMcastRouteEntry ::= SEQUENCE {
    fsMcastRouteAddress         IpAddress,
    fsMcastRouteIfIndex         INTEGER,
    fsMcastRouteEntryStatus     INTEGER
}

fsMcastRouteAddress OBJECT-TYPE
    SYNTAX      IpAddress
    ACCESS      not-accessible
    STATUS      mandatory
    DESCRIPTION 
        "The IP multicast group address for which this entry
         contains information.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsMcastRouteEntry 1 }

fsMcastRouteIfIndex OBJECT-TYPE
    SYNTAX      INTEGER (0..2147483647)
    ACCESS      not-accessible
    STATUS      mandatory
    DESCRIPTION 
        "The index value which identifies the
         interface to which this entry is applicable. The
         interface identified by a particular value of this
         index is the same interface as identified by the same
         value of ifIndex in MIB II.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsMcastRouteEntry 2 }

fsMcastRouteEntryStatus OBJECT-TYPE
    SYNTAX      INTEGER { static(1), dynamic(2), disable(3), invalid(4) }
    ACCESS      read-write
    STATUS      mandatory
    DESCRIPTION 
        "Setting this object to 'static' will prevent Group
         Membership Timer being started for this entry and can
         be removed only through the manager by setting this
         object to 'invalid'.
         Only 'static' entries can be created from the SNMP
         manager. When the Group learnt through IGMP, this object
         will be 'dynamic'.
         Only 'static' entries can be set with the 'disable' or
         'invalid' values. Disabling the entry will stop the
         forwarding of datagrams destined for that group on that
         interface. Making the entry 'invalid' will remove the
         entry.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsMcastRouteEntry 3 }

fsirdp OBJECT IDENTIFIER
    ::= { futureip 8 }

fsIrdpInAdvertisements OBJECT-TYPE
    SYNTAX      Counter
    ACCESS      read-only
    STATUS      mandatory
    DESCRIPTION 
        "The total number of ICMP Router Advertisements		                      received.
         ALCATEL NOTE:
             ACCESS:      NA           USAGE:       NA
             PERSIST:     NA           INSRVMOD:    NA
             RANGE:       NA           DEFVALUE:    NA
             UNITS:       NA	      SPARSE:      NA
             DESCR:       This object is not used by Alcatel"
    ::= { fsirdp 1 }

fsIrdpInSolicitations OBJECT-TYPE
    SYNTAX      Counter
    ACCESS      read-only
    STATUS      mandatory
    DESCRIPTION 
        "The total number of ICMP Router Solicitations
         received.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsirdp 2 }

fsIrdpOutAdvertisements OBJECT-TYPE
    SYNTAX      Counter
    ACCESS      read-only
    STATUS      mandatory
    DESCRIPTION 
        "The number of ICMP Router Advertisements
         sent.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsirdp 3 }

fsIrdpOutSolicitations OBJECT-TYPE
    SYNTAX      Counter
    ACCESS      read-only
    STATUS      mandatory
    DESCRIPTION 
        "The number of ICMP Router Solicitations
         sent.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsirdp 4 }

fsIrdpSendAdvertisementsEnable OBJECT-TYPE
    SYNTAX      INTEGER { enabled(1), disabled(2) }
    ACCESS      read-write
    STATUS      mandatory
    DESCRIPTION 
        "Allow sending Router Advertisements.
         ALCATEL NOTE:
             ACCESS:      NA           USAGE:       NA
             PERSIST:     NA           INSRVMOD:    NA
             RANGE:       NA           DEFVALUE:    NA
             UNITS:       NA	      SPARSE:      NA
             DESCR:       This object is not used by Alcatel"
    DEFVAL      { enabled }
    ::= { fsirdp 5 }

fsIrdpIfConfTable OBJECT-TYPE
    SYNTAX      SEQUENCE OF FsIrdpIfConfEntry
    ACCESS      not-accessible
    STATUS      mandatory
    DESCRIPTION 
        "This table has interface specific irdp configurable
         objects.
         ALCATEL NOTE:
         TABLESIZE:   NA
         DESCR:       This object is not used by Alcatel"
    ::= { fsirdp 6 }

fsIrdpIfConfEntry OBJECT-TYPE
    SYNTAX      FsIrdpIfConfEntry
    ACCESS      not-accessible
    STATUS      mandatory
    DESCRIPTION 
        "The individual entry in the above table.
         Row creation : NA
         Row deletion : NA
         Index usage :  NA
         Lexicographical order :  NA
         	This object is not used by Alcatel"
    INDEX       { fsIrdpIfConfIfNum, fsIrdpIfConfSubref }
    ::= { fsIrdpIfConfTable 1 }

FsIrdpIfConfEntry ::= SEQUENCE {
    fsIrdpIfConfIfNum                       INTEGER,
    fsIrdpIfConfSubref                      INTEGER,
    fsIrdpIfConfAdvertisementAddress        IpAddress,
    fsIrdpIfConfMaxAdvertisementInterval    INTEGER,
    fsIrdpIfConfMinAdvertisementInterval    INTEGER,
    fsIrdpIfConfAdvertisementLifetime       INTEGER,
    fsIrdpIfConfPerformRouterDiscovery      TruthValue,
    fsIrdpIfConfSolicitationAddress         IpAddress
}

fsIrdpIfConfIfNum OBJECT-TYPE
    SYNTAX      INTEGER (0..2147483647)
    ACCESS      not-accessible
    STATUS      mandatory
    DESCRIPTION 
        "The number of interfaces present in this system.
         ALCATEL NOTE:
             ACCESS:      NA           USAGE:       NA
             PERSIST:     NA           INSRVMOD:    NA
             RANGE:       NA           DEFVALUE:    NA
             UNITS:       NA	      SPARSE:      NA
             DESCR:       This object is not used by Alcatel"
    ::= { fsIrdpIfConfEntry 1 }

fsIrdpIfConfSubref OBJECT-TYPE
    SYNTAX      INTEGER (0..2147483647)
    ACCESS      not-accessible
    STATUS      mandatory
    DESCRIPTION 
        "The subreference of this interface.
         ALCATEL NOTE:
             ACCESS:      NA           USAGE:       NA
             PERSIST:     NA           INSRVMOD:    NA
             RANGE:       NA           DEFVALUE:    NA
             UNITS:       NA	      SPARSE:      NA
             DESCR:       This object is not used by Alcatel"
    ::= { fsIrdpIfConfEntry 2 }

fsIrdpIfConfAdvertisementAddress OBJECT-TYPE
    SYNTAX      IpAddress
    ACCESS      read-write
    STATUS      mandatory
    DESCRIPTION 
        "The IP destination address to be used for
         multicast Rourter Advertisements sent from the
         interface. The only permissible values are the
         all-systems multicast address, 224.0.0.1, or
         limited-broadcast address, 255.255.255.255. 
         ALCATEL NOTE:
         ACCESS:      NA           USAGE:       NA
         PERSIST:     NA           INSRVMOD:    NA
         RANGE:       NA           DEFVALUE:    NA
         UNITS:       NA	      SPARSE:      NA
         DESCR:       This object is not used by Alcatel"
    DEFVAL      { 'e0000001'H }
    ::= { fsIrdpIfConfEntry 3 }

fsIrdpIfConfMaxAdvertisementInterval OBJECT-TYPE
    SYNTAX      INTEGER (4..1800)
    ACCESS      read-write
    STATUS      mandatory
    DESCRIPTION 
        "The maximum time allowed between sending multicast
         Advertisements from the interface, in seconds. 
         ALCATEL NOTE:
         ACCESS:      NA           USAGE:       NA
         PERSIST:     NA           INSRVMOD:    NA
         RANGE:       NA           DEFVALUE:    NA
         UNITS:       NA	      SPARSE:      NA
         DESCR:       This object is not used by Alcatel"
    DEFVAL      { 600 }
    ::= { fsIrdpIfConfEntry 4 }

fsIrdpIfConfMinAdvertisementInterval OBJECT-TYPE
    SYNTAX      INTEGER (4..1800)
    ACCESS      read-write
    STATUS      mandatory
    DESCRIPTION 
        "The minimum time allowed between sending unsolicited
         multicast Router Advertisements from the interface,
         in seconds. 
         ALCATEL NOTE:
         ACCESS:      NA           USAGE:       NA
         PERSIST:     NA           INSRVMOD:    NA
         RANGE:       NA           DEFVALUE:    NA
         UNITS:       NA	      SPARSE:      NA
         DESCR:       This object is not used by Alcatel"
    DEFVAL      { 450 }
    ::= { fsIrdpIfConfEntry 5 }

fsIrdpIfConfAdvertisementLifetime OBJECT-TYPE
    SYNTAX      INTEGER (1800..9000)
    ACCESS      read-write
    STATUS      mandatory
    DESCRIPTION 
        "The value to be placed in the Lifetim efield of Router
         Advertisements sent from the interface, in seconds. 
         ALCATEL NOTE:
         ACCESS:      NA           USAGE:       NA
         PERSIST:     NA           INSRVMOD:    NA
         RANGE:       NA           DEFVALUE:    NA
         UNITS:       NA	      SPARSE:      NA
         DESCR:       This object is not used by Alcatel"
    DEFVAL      { 1800 }
    ::= { fsIrdpIfConfEntry 6 }

fsIrdpIfConfPerformRouterDiscovery OBJECT-TYPE
    SYNTAX      TruthValue
    ACCESS      read-write
    STATUS      mandatory
    DESCRIPTION 
        "A flag indicating whether or not the host is to perform
         ICMP router discovery on the interface.
         ALCATEL NOTE:
         ACCESS:      NA           USAGE:       NA
         PERSIST:     NA           INSRVMOD:    NA
         RANGE:       NA           DEFVALUE:    NA
         UNITS:       NA	      SPARSE:      NA
         DESCR:       This object is not used by Alcatel"
    DEFVAL      { true }
    ::= { fsIrdpIfConfEntry 7 }

fsIrdpIfConfSolicitationAddress OBJECT-TYPE
    SYNTAX      IpAddress
    ACCESS      read-write
    STATUS      mandatory
    DESCRIPTION 
        "The IP destination address to be used for sending
         Router Solicitations from the interface. The only
         permissible values are the all-routers multicast
         address, 224.0.0.2, or the limited-broadcast
         address, 255.255.255.255.
         ALCATEL NOTE:
         ACCESS:      NA           USAGE:       NA
         PERSIST:     NA           INSRVMOD:    NA
         RANGE:       NA           DEFVALUE:    NA
         UNITS:       NA	      SPARSE:      NA
         DESCR:       This object is not used by Alcatel"
    DEFVAL      { 'e0000002'H }
    ::= { fsIrdpIfConfEntry 8 }

fsrarpclient OBJECT IDENTIFIER
    ::= { futureip 9 }

fsRarpClientRetransmissionTimeout OBJECT-TYPE
    SYNTAX      INTEGER (30..3000)
    ACCESS      read-write
    STATUS      mandatory
    DESCRIPTION 
        "The interval (in seconds) after which an unanswered RARP
         request should be retransmitted.  
         ALCATEL NOTE:
         ACCESS:      NA           USAGE:       NA
         PERSIST:     NA           INSRVMOD:    NA
         RANGE:       NA           DEFVALUE:    NA
         UNITS:       NA	      SPARSE:      NA
         DESCR:       This object is not used by Alcatel"
    DEFVAL      { 100 }
    ::= { fsrarpclient 1 }

fsRarpClientMaxRetries OBJECT-TYPE
    SYNTAX      INTEGER (2..10)
    ACCESS      read-write
    STATUS      mandatory
    DESCRIPTION 
        "The maximum number of retransmissions of RARP request
         packet after which no request should be sent.  
         ALCATEL NOTE:
         ACCESS:      NA           USAGE:       NA
         PERSIST:     NA           INSRVMOD:    NA
         RANGE:       NA           DEFVALUE:    NA
         UNITS:       NA	      SPARSE:      NA
         DESCR:       This object is not used by Alcatel"
    DEFVAL      { 4 }
    ::= { fsrarpclient 2 }

fsRarpClientPktsDiscarded OBJECT-TYPE
    SYNTAX      Counter
    ACCESS      read-only
    STATUS      mandatory
    DESCRIPTION 
        "Total number of RARP Reply packets discarded 
         by this client.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsrarpclient 3 }

fsrarpserver OBJECT IDENTIFIER
    ::= { futureip 10 }

fsRarpServerStatus OBJECT-TYPE
    SYNTAX      INTEGER { enabled(1), disabled(2) }
    ACCESS      read-write
    STATUS      mandatory
    DESCRIPTION 
        "Enables or Disables the RARP Server.
         ALCATEL NOTE:
             ACCESS:      NA           USAGE:       NA
             PERSIST:     NA           INSRVMOD:    NA
             RANGE:       NA           DEFVALUE:    NA
             UNITS:       NA	      SPARSE:      NA
             DESCR:       This object is not used by Alcatel"
    DEFVAL      { disabled }
    ::= { fsrarpserver 1 }

fsRarpServerPktsDiscarded OBJECT-TYPE
    SYNTAX      Counter
    ACCESS      read-only
    STATUS      mandatory
    DESCRIPTION 
        "Total number of RARP request packets discarded 
         by this server.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsrarpserver 2 }

fsRarpServerTableMaxEntries OBJECT-TYPE
    SYNTAX      INTEGER (0..25)
    ACCESS      read-write
    STATUS      mandatory
    DESCRIPTION 
        "Maximum number of entries in the RARP server table.
         ALCATEL NOTE:
             ACCESS:      NA           USAGE:       NA
             PERSIST:     NA           INSRVMOD:    NA
             RANGE:       NA           DEFVALUE:    NA
             UNITS:       NA	      SPARSE:      NA
             DESCR:       This object is not used by Alcatel"
    ::= { fsrarpserver 3 }

fsRarpServerDatabaseTable OBJECT-TYPE
    SYNTAX      SEQUENCE OF FsRarpServerDatabaseEntry
    ACCESS      not-accessible
    STATUS      mandatory
    DESCRIPTION 
        "The Server database which maps the Client's 
         hardware Address to IP Address .
         ALCATEL NOTE:
         TABLESIZE:   NA
         DESCR:       This object is not used by Alcatel"
    ::= { fsrarpserver 4 }

fsRarpServerDatabaseEntry OBJECT-TYPE
    SYNTAX      FsRarpServerDatabaseEntry
    ACCESS      not-accessible
    STATUS      mandatory
    DESCRIPTION 
        "Contains entry for a particular client.
         Row creation : NA
         Row deletion : NA
         Index usage :  NA
         Lexicographical order :  NA
         	This object is not used by Alcatel"
    INDEX       { fsHardwareAddress }
    ::= { fsRarpServerDatabaseTable 1 }

FsRarpServerDatabaseEntry ::= SEQUENCE {
    fsHardwareAddress   OCTET STRING,
    fsHardwareAddrLen   INTEGER,
    fsProtocolAddress   IpAddress,
    fsEntryStatus       RowStatus
}

fsHardwareAddress OBJECT-TYPE
    SYNTAX      OCTET STRING (SIZE(6))
    ACCESS      not-accessible
    STATUS      mandatory
    DESCRIPTION 
        "The Hardware address of the client.
         ALCATEL NOTE:
             ACCESS:      NA           USAGE:       NA
             PERSIST:     NA           INSRVMOD:    NA
             RANGE:       NA           DEFVALUE:    NA
             UNITS:       NA	      SPARSE:      NA
             DESCR:       This object is not used by Alcatel"
    ::= { fsRarpServerDatabaseEntry 1 }

fsHardwareAddrLen OBJECT-TYPE
    SYNTAX      INTEGER (1..6)
    ACCESS      read-write
    STATUS      mandatory
    DESCRIPTION 
        "The hardware address length of the spceified index.
         ALCATEL NOTE:
             ACCESS:      NA           USAGE:       NA
             PERSIST:     NA           INSRVMOD:    NA
             RANGE:       NA           DEFVALUE:    NA
             UNITS:       NA	      SPARSE:      NA
             DESCR:       This object is not used by Alcatel"
    ::= { fsRarpServerDatabaseEntry 2 }

fsProtocolAddress OBJECT-TYPE
    SYNTAX      IpAddress
    ACCESS      read-write
    STATUS      mandatory
    DESCRIPTION 
        "IP Address corresponding to the client's 
         Hardware Address.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsRarpServerDatabaseEntry 3 }

fsEntryStatus OBJECT-TYPE
    SYNTAX      RowStatus
    ACCESS      read-write
    STATUS      mandatory
    DESCRIPTION 
        "The status of this row,by which new entries may 
         be created or old entries can be deleted from 
         this server table as per SMIv2.
         ALCATEL NOTE:
         ACCESS:      NA           USAGE:       NA
         PERSIST:     NA           INSRVMOD:    NA
         RANGE:       NA           DEFVALUE:    NA
         UNITS:       NA	      SPARSE:      NA
         DESCR:       This object is not used by Alcatel"
    ::= { fsRarpServerDatabaseEntry 4 }

fssystemresize OBJECT IDENTIFIER
    ::= { futureip 16 }

fsNoOfStaticRoutes OBJECT-TYPE
    SYNTAX      INTEGER
    ACCESS      read-write
    STATUS      mandatory
    DESCRIPTION 
        "Number of static routes that can be configured in the system. 
         The configured value will come in to effect only after rebooting the 
         router.
           ALCATEL NOTE:
               ACCESS:      NA           		USAGE:       NA
               PERSIST:     NO          		INSRVMOD:    YES
               RANGE:       20..fsNoOfRoutes  	DEFVALUE:    10000
               UNITS:       routes	  		SPARSE:      NA
               DESCR:       NA"
    ::= { fssystemresize 1 }

fsNoOfAggregatedRoutes OBJECT-TYPE
    SYNTAX      INTEGER
    ACCESS      read-write
    STATUS      mandatory
    DESCRIPTION 
        "Number of aggregated routes that can be configured in the system.
         This value will come in to effect only after rebooting the router. 
         Minimum value is 5, if System Sizing is not enabled.
           ALCATEL NOTE:
               ACCESS:      NA           		USAGE:       NA
               PERSIST:     NO          		INSRVMOD:    YES
               RANGE:       5..fsNoOfRoutes  	DEFVALUE:    12
               UNITS:       routes	  		SPARSE:      NA
               DESCR:       NA"
    ::= { fssystemresize 2 }

fsNoOfRoutes OBJECT-TYPE
    SYNTAX      INTEGER
    ACCESS      read-write
    STATUS      mandatory
    DESCRIPTION 
        "Number of entries in the routing table. This is equal to the maximum 
         number of routes learned by any of the routing protocol.This value will 
         come in to effect only after rebooting the router. Cannot set below 500
         if System Sizing is disabled. 
           ALCATEL NOTE:
               ACCESS:      NA   	USAGE:       NA
               PERSIST:     NO   	INSRVMOD:    YES
               RANGE:       DEP	DEFVALUE:    10000
               UNITS:       routes	SPARSE:      NA
               DESCR:       Minimum of 10000 and it should not be less than fsNoOfStaticRoutes,fsNoOfAggregatedRoutes"
    ::= { fssystemresize 3 }

fsNoOfReassemblyLists OBJECT-TYPE
    SYNTAX      INTEGER
    ACCESS      read-write
    STATUS      mandatory
    DESCRIPTION 
        "Number of IP datagrams which are awaiting for reassembly.This value 
         will come in to effect only after rebooting the router. The Maximum 
         value is 150 when System Sizing is disabled
           ALCATEL NOTE:
               ACCESS:      NA         USAGE:       NA
               PERSIST:     NO         INSRVMOD:    YES
               RANGE:       1..150	    DEFVALUE:    10
               UNITS:       NA	    SPARSE:      NA
               DESCR:       NA"
    ::= { fssystemresize 4 }

fsNoOfFragmentsPerList OBJECT-TYPE
    SYNTAX      INTEGER
    ACCESS      read-write
    STATUS      mandatory
    DESCRIPTION 
        "Number of IP fragments that can be allowed in a single reassembly 
         list.This value will come in to effect only after rebooting the router.
           ALCATEL NOTE:
               ACCESS:      NA         USAGE:       NA
               PERSIST:     NO         INSRVMOD:    YES
               RANGE:       0..300	    DEFVALUE:    45
               UNITS:       NA	    SPARSE:      NA
               DESCR:       NA"
    ::= { fssystemresize 5 }

fsNoOfMcastGroups OBJECT-TYPE
    SYNTAX      INTEGER
    ACCESS      read-write
    STATUS      mandatory
    DESCRIPTION 
        "Number of Maximum multicast groups supported by IGMP. All multicast
         routing protocols running in the system MUST support this number of 
         multicast groups. This value will come in to effect only after rebooting 
         the router. The Maximum value when System Sizing is disabled is 100
           ALCATEL NOTE:
               ACCESS:      NA           USAGE:       NA
               PERSIST:     NA           INSRVMOD:    NA
               RANGE:       NA           DEFVALUE:    NA
               UNITS:       NA	      SPARSE:      NA
               DESCR:       This object is not used by Alcatel"
    ::= { fssystemresize 6 }

fslogandtrace OBJECT IDENTIFIER
    ::= { futureip 17 }

fsIpGlobalDebug OBJECT-TYPE
    SYNTAX      INTEGER
    ACCESS      read-write
    STATUS      mandatory
    DESCRIPTION 
        "Enables the tracing in the selected submodule in IP. A 32 bit integer
         is used to store the Tracing level in the specified module.
          Different Tracing Levels -
            BIT 0 - Initialisation and Shutdown Trace.
            BIT 1 - Management trace.
            BIT 2 - Data path trace.
            BIT 3 - Control Plane trace.
            BIT 4 - Packet Dump.
            BIT 5 - OS Resource trace.
            BIT 6 - All Failure trace (All failures including Packet Validation)
            BIT 7 - Buffer Trace.
         
          Different submodule Tracing -
            BIT 16 - Tracing in IP module.
            BIT 17 - Tracing in ICMP submodule.
            BIT 18 - Tracing in IGMP submodule.
            BIT 19 - Tracing in RIP submodule.
            BIT 20 - Tracing in ARP submodule.
            BIT 21 - Tracing in BOOTP submodule.
            BIT 22 - Tracing in UDP submodule.
         
          The remaining bits are used.The combination of levels and submodules 
          are allowed i.e. Tracing can be allowed at all failure and data path 
          level in All submodules by setting the BIT appropriately.
          For Example, setting the debug valut to 
             0b00000000000000010000000001000000 will enable all failure trace 
          prints in IP module.
           ALCATEL NOTE:
               ACCESS:      NA             USAGE:       NA
               PERSIST:     NO             INSRVMOD:    YES
               RANGE:       0..8388607	DEFVALUE:    0
               UNITS:       NA		SPARSE:      NA
               DESCR:       NA"
    ::= { fslogandtrace 1 }

fsrrd OBJECT IDENTIFIER
    ::= { futureip 18 }

fsVrfRrdConfigTable OBJECT-TYPE
    SYNTAX      SEQUENCE OF FsVrfRrdConfigEntry
    ACCESS      not-accessible
    STATUS      mandatory
    DESCRIPTION 
        " Config Table to configure RRD per  VRF Instance
         ALCATEL NOTE:
           TABLESIZE:  128
         	  DESCR: 	  NA"
    ::= { fsrrd 9 }

fsVrfRrdConfigEntry OBJECT-TYPE
    SYNTAX      FsVrfRrdConfigEntry
    ACCESS      not-accessible
    STATUS      mandatory
    DESCRIPTION 
        "An entry of fsRrdConfigTable.
         Row creation : An entry will be created by the system when an entry
             		is created in the lanxVrfConfigTable.
         Row deletion : An entry will be deleted by the system when an entry
             		is deleted in the lanxVrfConfigTable.
         Index usage : the index is lanxVrfId.
           Note that entries will be presented to the SNMP manager in full
           lexicographical order :  sorted on lanxVrfId."
    INDEX       { lanxVrfId }
    ::= { fsVrfRrdConfigTable 1 }

FsVrfRrdConfigEntry ::= SEQUENCE {
    fsVrfRrdRouterId            IpAddress,
    fsVrfRrdFilterByOspfTag     INTEGER,
    fsVrfRrdFilterOspfTag       INTEGER,
    fsVrfRrdFilterOspfTagMask   INTEGER,
    fsVrfRrdRouterASNumber      INTEGER,
    fsVrfRrdAdminStatus         INTEGER
}

fsVrfRrdRouterId OBJECT-TYPE
    SYNTAX      IpAddress
    ACCESS      read-write
    STATUS      mandatory
    DESCRIPTION 
        "The BGP/OSPF Router Id.
         ALCATEL NOTE:
             ACCESS:      NA           	USAGE:       NA
             PERSIST:     YES          	INSRVMOD:    NO
             RANGE:       NA             DEFVALUE:    0.0.0.0
             UNITS:       NA           	SPARSE:      NO
             DESCR:       NA"
    ::= { fsVrfRrdConfigEntry 1 }

fsVrfRrdFilterByOspfTag OBJECT-TYPE
    SYNTAX      INTEGER { enable(1), disable(2) }
    ACCESS      read-write
    STATUS      mandatory
    DESCRIPTION 
        "To enable distribution of routes from OSPF to BGP/IDRP based
         on the OSPF tag or the various subfields of the OSPF tag
         (ref RFC1745 sec 2.1). This filter takes precedence over the 
          common RRD control table.
         ALCATEL NOTE:
            ACCESS:      NA           	USAGE:       NA
            PERSIST:     YES          	INSRVMOD:    YES
            RANGE:       NA             DEFVALUE:    NA
            UNITS:       NA           	SPARSE:      NO
            DESCR:       NA"
    DEFVAL      { disable }
    ::= { fsVrfRrdConfigEntry 2 }

fsVrfRrdFilterOspfTag OBJECT-TYPE
    SYNTAX      INTEGER
    ACCESS      read-write
    STATUS      mandatory
    DESCRIPTION 
        "The OSPF tag based on which routes have to be filtered for
         export to BGP/IDRP
         ALCATEL NOTE:
            ACCESS:      NA           		USAGE:       NA
            PERSIST:     YES          		INSRVMOD:    YES
            RANGE:       2147483648..4294967295 DEFVALUE:    0
            UNITS:       NA           		SPARSE:      NO
            DESCR:       NA"
    ::= { fsVrfRrdConfigEntry 3 }

fsVrfRrdFilterOspfTagMask OBJECT-TYPE
    SYNTAX      INTEGER
    ACCESS      read-write
    STATUS      mandatory
    DESCRIPTION 
        "The bitmask to be applied to fsRrdFilterOspfTag for comparison.
         This bitmask specifies the fields of the OSPF tag to be
         considered for filtering.
         ALCATEL NOTE:
            ACCESS:      NA           		USAGE:       NA
            PERSIST:     YES          		INSRVMOD:    YES
            RANGE:       2147483648..4294967295	DEFVALUE:    0
            UNITS:       NA           		SPARSE:      NO
            DESCR:       NA"
    DEFVAL      { -1 }
    ::= { fsVrfRrdConfigEntry 4 }

fsVrfRrdRouterASNumber OBJECT-TYPE
    SYNTAX      INTEGER
    ACCESS      read-write
    STATUS      mandatory
    DESCRIPTION 
        "The Autonomous system number in which this router is running.
         ALCATEL NOTE:
             ACCESS:      NA           	USAGE:       NA
             PERSIST:     YES          	INSRVMOD:    NO
             RANGE:       0..65355       DEFVALUE:    NA
             UNITS:       NA           	SPARSE:      NO
             DESCR:       NA"
    DEFVAL      { 0 }
    ::= { fsVrfRrdConfigEntry 5 }

fsVrfRrdAdminStatus OBJECT-TYPE
    SYNTAX      INTEGER { enabled(1), disabled(2) }
    ACCESS      read-write
    STATUS      mandatory
    DESCRIPTION 
        "The Admin status of the RTM. This object can be set to 
         enabled only after setting the AS number and the Router ID to a valid
         value.
           ALCATEL NOTE:
               ACCESS:      NA           	USAGE:       NA
               PERSIST:     YES          	INSRVMOD:    YES
               RANGE:       NA         	DEFVALUE:    enabled
               UNITS:       NA           	SPARSE:      NO
               DESCR:       NA"
    DEFVAL      { disabled }
    ::= { fsVrfRrdConfigEntry 6 }

fsVrfRrdControlTable OBJECT-TYPE
    SYNTAX      SEQUENCE OF FsVrfRrdControlEntry
    ACCESS      not-accessible
    STATUS      mandatory
    DESCRIPTION 
        "Control Table for configuring routes allowed/denied
         for export.
         ALCATEL NOTE:
         TABLESIZE:  NA
           DESCR: 	  NA"
    ::= { fsrrd 10 }

fsVrfRrdControlEntry OBJECT-TYPE
    SYNTAX      FsVrfRrdControlEntry
    ACCESS      not-accessible
    STATUS      mandatory
    DESCRIPTION 
        "An entry of fsVrfRrdControlTable.
         Row creation : A fsVrfRrdControl Entry shall be created in one step by a
         		      set-request with all necessary parameter values and
             		fsVrfRrdControlRowStatus set to createAndGo(4).
         Row deletion : A fsVrfRrdControl Entry shall be deleted by setting
             		the fsVrfRrdControlRowStatus of the specific entry to destroy(6).
         Index usage : the indexes are lanxVrfId, fsVrfRrdControlDestIpAddress,
         			fsVrfRrdControlNetMask and fsVrfRrdControlSourceProto.
           Note that entries will be presented to the SNMP manager in full
           lexicographical order :  sorted on lanxVrfId, then on fsVrfRrdControlDestIpAddress,
         			then on fsVrfRrdControlNetMask, then on fsVrfRrdControlSourceProto."
    INDEX       { lanxVrfId, fsVrfRrdControlDestIpAddress, 
                  fsVrfRrdControlNetMask, fsVrfRrdControlSourceProto }
    ::= { fsVrfRrdControlTable 1 }

FsVrfRrdControlEntry ::= SEQUENCE {
    fsVrfRrdControlDestIpAddress    IpAddress,
    fsVrfRrdControlNetMask          IpAddress,
    fsVrfRrdControlSourceProto      INTEGER,
    fsVrfRrdControlDestProto        INTEGER,
    fsVrfRrdControlRouteExportFlag  INTEGER,
    fsVrfRrdControlRowStatus        RowStatus
}

fsVrfRrdControlDestIpAddress OBJECT-TYPE
    SYNTAX      IpAddress
    ACCESS      not-accessible
    STATUS      mandatory
    DESCRIPTION 
        "The destination IP address of this route.
         
         This object may not take a Multicast (Class  D)
         address or the reserved address (Class E) value.
         ALCATEL NOTE:
            ACCESS:      NA           USAGE:       NA
            PERSIST:     YES          INSRVMOD:    NA
            RANGE:       NA           DEFVALUE:    NA
            UNITS:       NA           SPARSE:      NO
            DESCR:       NA"
    ::= { fsVrfRrdControlEntry 1 }

fsVrfRrdControlNetMask OBJECT-TYPE
    SYNTAX      IpAddress
    ACCESS      not-accessible
    STATUS      mandatory
    DESCRIPTION 
        "Indicate an inverse mask. An inverse mask sets
         a zero for each bit of the address that should be
         exactly matched and a one for each bit where     
         anything will match- the one bits are referred to
         as dont-care bits. 
         The mask is used to specify the range of IP 
         addresses.
         For Eg. Destination Net = 128.11.0.0
                 Net Mask = 0.0.255.255 specifies the range of
         routes starting from 128.11.0.0 to 121.11.255.255.
         For specifying all routes give 
                 Destination Net = 0.0.0.0
                 Net Mask = 255.255.255.255
         ALCATEL NOTE:
            ACCESS:      NA           USAGE:       NA
            PERSIST:     YES          INSRVMOD:    NA
            RANGE:       NA           DEFVALUE:    NA
            UNITS:       NA           SPARSE:      NO
            DESCR:       NA"
    ::= { fsVrfRrdControlEntry 2 }

fsVrfRrdControlSourceProto OBJECT-TYPE
    SYNTAX      INTEGER { any(0), other(1), local(2), netmgmt(3), 
                    icmp(4), egp(5), ggp(6), hello(7), rip(8), isIs(9), 
                    esIs(10), ciscoIgrp(11), bbnSpfIgp(12), ospf(13), 
                    bgp(14), idpr(15), ciscoEigrp(16) }
    ACCESS      not-accessible
    STATUS      mandatory
    DESCRIPTION 
        "The Identifier of the source routing protocol.
         A value of zero will be interpreted as 'any',
         which may be used to configure interface based
         route redistribution.
         ALCATEL NOTE:
            ACCESS:      NA           USAGE:       NA
            PERSIST:     YES          INSRVMOD:    NA
            RANGE:       NA           DEFVALUE:    NA
            UNITS:       NA           SPARSE:      NO
            DESCR:       NA"
    ::= { fsVrfRrdControlEntry 3 }

fsVrfRrdControlDestProto OBJECT-TYPE
    SYNTAX      INTEGER
    ACCESS      read-write
    STATUS      mandatory
    DESCRIPTION 
        "The identifier of the destination routing protocol.
         This field is a bit mask, a 1 indicates that the route
         has to be exported to the routing protocol corresponding
         to the bit-position.
         +===================================================+
         | ciscoEigrp |    idpr    |    bgp     |    ospf    |
         +===================================================+
         |     15     |     14     |    13      |     12     |
         +===================================================+
         |  bbnSpfIgp | ciscoIgrp  |    esIs    |    isIs    |
         +===================================================+
         |     11     |     10     |     9      |      8     |
         +===================================================+
         |     rip    |   hello    |    ggp     |    egp     |
         +===================================================+
         |      7     |      6     |     5      |      4     |
         +===================================================+
         |    icmp    |   netmgmt  |   local    |   other    |
         +===================================================+
         |      3     |      2     |     1      |      0     |
         +===================================================+
         ALCATEL NOTE:
         ACCESS:      NA           	USAGE:       OPT
         PERSIST:     YES          	INSRVMOD:    YES
         RANGE:       NA 			DEFVALUE:    NA
         UNITS:       NA           	SPARSE:      NO
         DESCR:       The value 0 or rip(bit-7) or ospf(bit-12) or bgp(bit-13) should be set"
    DEFVAL      { 0 }
    ::= { fsVrfRrdControlEntry 4 }

fsVrfRrdControlRouteExportFlag OBJECT-TYPE
    SYNTAX      INTEGER { permit(1), deny(2) }
    ACCESS      read-write
    STATUS      mandatory
    DESCRIPTION 
        "This flag specifies whether the route is allowed
         for export or denied.
         ALCATEL NOTE:
            ACCESS:      NA           	USAGE:       MAND
            PERSIST:     YES          	INSRVMOD:    YES
            RANGE:       NA             DEFVALUE:    NA
            UNITS:       NA           	SPARSE:      NO
            DESCR:       NA"
    ::= { fsVrfRrdControlEntry 5 }

fsVrfRrdControlRowStatus OBJECT-TYPE
    SYNTAX      RowStatus
    ACCESS      read-write
    STATUS      mandatory
    DESCRIPTION 
        "The status of this row by which a new row can be created or deleted
         according to the SMIv2 conventions.
           ALCATEL NOTE:
               ACCESS:      NA           	USAGE:       MAND
               PERSIST:     YES          	INSRVMOD:    YES
               RANGE:       1,4,6          DEFVALUE:    NA
               UNITS:       NA           	SPARSE:      NO
               DESCR:       NA"
    ::= { fsVrfRrdControlEntry 6 }

fsVrfRrdRoutingProtoTable OBJECT-TYPE
    SYNTAX      SEQUENCE OF FsVrfRrdRoutingProtoEntry
    ACCESS      not-accessible
    STATUS      mandatory
    DESCRIPTION 
        "Registration Table for the different routing protocols.
         This table is read-only and reflects the information of 
         routing protocols held by the Route Table Manager.
         ALCATEL NOTE:
         TABLESIZE:  NA
           DESCR: 	  This object is not used by Alcatel"
    ::= { fsrrd 11 }

fsVrfRrdRoutingProtoEntry OBJECT-TYPE
    SYNTAX      FsVrfRrdRoutingProtoEntry
    ACCESS      not-accessible
    STATUS      mandatory
    DESCRIPTION 
        "An entry in to the fsVrfRrdRoutingProtoTable.
         Row creation : NA
         Row deletion : NA
         Index usage :  NA
         Lexicographical order :  NA
         	This object is not used by Alcatel"
    INDEX       { lanxVrfId, fsVrfRrdRoutingProtoId }
    ::= { fsVrfRrdRoutingProtoTable 1 }

FsVrfRrdRoutingProtoEntry ::= SEQUENCE {
    fsVrfRrdRoutingProtoId          INTEGER,
    fsVrfRrdRoutingRegnId           INTEGER,
    fsVrfRrdRoutingProtoTaskIdent   OCTET STRING,
    fsVrfRrdRoutingProtoQueueIdent  OCTET STRING,
    fsVrfRrdAllowOspfAreaRoutes     INTEGER,
    fsVrfRrdAllowOspfExtRoutes      INTEGER
}

fsVrfRrdRoutingProtoId OBJECT-TYPE
    SYNTAX      INTEGER { other(1), local(2), netmgmt(3), icmp(4), 
                    egp(5), ggp(6), hello(7), rip(8), isIs(9), esIs(10), 
                    ciscoIgrp(11), bbnSpfIgp(12), ospf(13), bgp(14), 
                    idpr(15), ciscoEigrp(16) }
    ACCESS      not-accessible
    STATUS      mandatory
    DESCRIPTION 
        "The Identifier of the routing protocol registered
         with the routing table manager
         ALCATEL NOTE:
            ACCESS:      NA           USAGE:       NA
            PERSIST:     NA           INSRVMOD:    NA
            RANGE:       NA           DEFVALUE:    NA
            UNITS:       NA	      SPARSE:      NA
            DESCR:       This object is not used by Alcatel"
    ::= { fsVrfRrdRoutingProtoEntry 1 }

fsVrfRrdRoutingRegnId OBJECT-TYPE
    SYNTAX      INTEGER
    ACCESS      read-only
    STATUS      mandatory
    DESCRIPTION 
        "The Registeration ID assigned by the RTM for this Routing Protocol 
         ALCATEL NOTE:
             ACCESS:      NA           USAGE:       NA
             PERSIST:     NA           INSRVMOD:    NA
             RANGE:       NA           DEFVALUE:    NA
             UNITS:       NA	      SPARSE:      NA
             DESCR:       This object is not used by Alcatel"
    ::= { fsVrfRrdRoutingProtoEntry 2 }

fsVrfRrdRoutingProtoTaskIdent OBJECT-TYPE
    SYNTAX      OCTET STRING
    ACCESS      read-only
    STATUS      mandatory
    DESCRIPTION 
        "The Name/Identifier of the Routing Task 
         ALCATEL NOTE:
             ACCESS:      NA           USAGE:       NA
             PERSIST:     NA           INSRVMOD:    NA
             RANGE:       NA           DEFVALUE:    NA
             UNITS:       NA	      SPARSE:      NA
             DESCR:       This object is not used by Alcatel"
    ::= { fsVrfRrdRoutingProtoEntry 3 }

fsVrfRrdRoutingProtoQueueIdent OBJECT-TYPE
    SYNTAX      OCTET STRING
    ACCESS      read-only
    STATUS      mandatory
    DESCRIPTION 
        "The Name/Identifier of the Message Queue to which messages
         to the Routing Task are posted. 
         ALCATEL NOTE:
            ACCESS:      NA           USAGE:       NA
            PERSIST:     NA           INSRVMOD:    NA
            RANGE:       NA           DEFVALUE:    NA
            UNITS:       NA	      SPARSE:      NA
            DESCR:       This object is not used by Alcatel"
    ::= { fsVrfRrdRoutingProtoEntry 4 }

fsVrfRrdAllowOspfAreaRoutes OBJECT-TYPE
    SYNTAX      INTEGER { enable(1), disable(2) }
    ACCESS      read-write
    STATUS      mandatory
    DESCRIPTION 
        "A single configuration to PERMIT all OSPF inter-area and intra-area
         address/mask pairs to be exported into this routing protocol.
         This configuration takes precedence over filtering based on
          the control table.  
         ALCATEL NOTE:
            ACCESS:      NA           USAGE:       NA
            PERSIST:     NA           INSRVMOD:    NA
            RANGE:       NA           DEFVALUE:    NA
            UNITS:       NA	      SPARSE:      NA
            DESCR:       This object is not used by Alcatel"
    DEFVAL      { disable }
    ::= { fsVrfRrdRoutingProtoEntry 5 }

fsVrfRrdAllowOspfExtRoutes OBJECT-TYPE
    SYNTAX      INTEGER { enable(1), disable(2) }
    ACCESS      read-write
    STATUS      mandatory
    DESCRIPTION 
        "A single configuration to PERMIT all OSPF Type 1 and Type 2
         Exteral address/mask pairs to be exported into this routing protocol.
          This configuration together with the control table, take care of 
          selective route export.  
         ALCATEL NOTE:
            ACCESS:      NA           USAGE:       NA
            PERSIST:     NA           INSRVMOD:    NA
            RANGE:       NA           DEFVALUE:    NA
            UNITS:       NA	      SPARSE:      NA
            DESCR:       This object is not used by Alcatel"
    DEFVAL      { disable }
    ::= { fsVrfRrdRoutingProtoEntry 6 }

END -- end of module FUTUREIP-MIB.
