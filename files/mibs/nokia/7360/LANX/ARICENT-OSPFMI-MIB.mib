--
-- This SMIv1 module has been generated by smidump 0.4.8. Do not edit.
--

ARICENT-OSPFMI-MIB DEFINITIONS ::= BEGIN

IMPORTS
    AreaID, BigMetric, PositiveInteger, RouterID, Status, TOSType, 
    fsMIStdOspfContextId, fsMIStdOspfEntry
        FROM ARICENT-MISTDOSPF-MIB
    InterfaceIndex
        FROM IF-MIB
    OBJECT-TYPE
        FROM RFC-1212
    Counter, Gauge, IpAddress, enterprises
        FROM RFC1155-SMI
    RowStatus, TruthValue
        FROM SNMPv2-TC;

fsMIOspf OBJECT IDENTIFIER
    ::= { enterprises futuresoftware(2076) 145 }

-- fsMIOspf MODULE-IDENTITY
--     LAST-UPDATED "200702230000Z"
--     ORGANIZATION 
--         "ARICENT COMMUNICATIONS SOFTWARE"
--     CONTACT-INFO 
--         "ARICENT COMMUNICATIONS SOFTWARE
--          3460 Hillview Avenue,
--          Palo Alto, CA 94304-1388, USA,
--          Phone : +1-650-391-1088
--          E-mail:support@aricent.com"
--     DESCRIPTION 
--         "The enterprise ID 2076 was originally assigned to Future Software Pvt Limited.
--          Future Software is a part of Aricent."
--     REVISION    "200702230000Z"
--     DESCRIPTION 
--         "The Aricent Proprietary OSPFMI MIB"
--     ::= { enterprises futuresoftware(2076) 145 }


fsMIOspfGeneralGroup OBJECT IDENTIFIER
    ::= { fsMIOspf 1 }

fsMIOspfGlobalTraceLevel OBJECT-TYPE
    SYNTAX      INTEGER
    ACCESS      read-write
    STATUS      mandatory
    DESCRIPTION 
        "This is the global trace and not specific to any context
         ALCATEL NOTE:
               ACCESS:      NA           USAGE:       NA
               PERSIST:     YES          INSRVMOD:    NA
               RANGE:       NA           DEFVALUE:    NA       
               UNITS:       NA           SPARSE:      NA
               DESCR:       This should not used by the operator and it is only for debugging purpose
         	    In ECNTA, Get of this object will always return 0, Set of this object will always return failure, since this object is not supported in ECNTA"
    DEFVAL      { 0 }
    ::= { fsMIOspfGeneralGroup 1 }

fsMIOspfVrfSpfInterval OBJECT-TYPE
    SYNTAX      INTEGER (0 | 10..1000)
    ACCESS      read-write
    STATUS      mandatory
    DESCRIPTION 
        "Minimum time between two consecutive SPF calculations across two ospf instances.
         Time is configured in milli seconds
         Currently this object is not supported in OSPF multiple instance.
         Setting the value to 0 is not allowed.
         ALCATEL NOTE:
          ACCESS:      NA           USAGE:       NA
          PERSIST:     YES          INSRVMOD:    NA
          RANGE:       NA           DEFVALUE:    NA       
          UNITS:       NA           SPARSE:      NA
          DESCR:       In ECNTA, Get of this object will always return 0, Set of this object will always return failure, since this object is not supported in ECNTA"
    DEFVAL      { 50 }
    ::= { fsMIOspfGeneralGroup 2 }

fsMIOspfTable OBJECT-TYPE
    SYNTAX      SEQUENCE OF FsMIOspfEntry
    ACCESS      not-accessible
    STATUS      mandatory
    DESCRIPTION 
        "Table to store different context specific ospf parameters
         ALCATEL NOTE:
         	TABLE SIZE:    64
         	DESCR:         NA"
    ::= { fsMIOspfGeneralGroup 3 }

fsMIOspfEntry OBJECT-TYPE
    SYNTAX      FsMIOspfEntry
    ACCESS      not-accessible
    STATUS      mandatory
    DESCRIPTION 
        "Each entry has that context specific OSPF routing information
         Row creation : An entry will be created by the system when an OSPF instance
              		is created in fsMIStdOspfTable.
         Row deletion : An entry will be deleted by the system when an OSPF instance
             		is deleted in fsMIStdOspfTable.
         Index usage : the index is fsMIStdOspfEntry.
           Note that entries will be presented to the SNMP manager in full
           lexicographical order :  sorted on fsMIStdOspfEntry."
    INDEX       { fsMIStdOspfContextId }
--     AUGMENTS    { fsMIStdOspfEntry }
    ::= { fsMIOspfTable 1 }

FsMIOspfEntry ::= SEQUENCE {
    fsMIOspfOverFlowState               TruthValue,
    fsMIOspfPktsRcvd                    Counter,
    fsMIOspfPktsTxed                    Counter,
    fsMIOspfPktsDisd                    Counter,
    fsMIOspfRFC1583Compatibility        Status,
    fsMIOspfTraceLevel                  INTEGER,
    fsMIOspfMinLsaInterval              INTEGER,
    fsMIOspfABRType                     INTEGER,
    fsMIOspfNssaAsbrDefRtTrans          INTEGER,
    fsMIOspfDefaultPassiveInterface     TruthValue,
    fsMIOspfSpfHoldtime                 INTEGER,
    fsMIOspfSpfDelay                    INTEGER,
    fsMIOspfInternalLsaCount            INTEGER,
    fsMIOspfRedisRouteCountPerVrf       INTEGER
}

fsMIOspfOverFlowState OBJECT-TYPE
    SYNTAX      TruthValue
    ACCESS      read-only
    STATUS      mandatory
    DESCRIPTION 
        "Indicates whether router is in overflow state or not.
         ALCATEL NOTE:
           ACCESS:      NA          USAGE:       NA
           PERSIST:     NO          INSRVMOD:    NA
           RANGE:       1,2         DEFVALUE:    NA
           UNITS:       NA          SPARSE:      NA
           DESCR:       NA"
    DEFVAL      { false }
    ::= { fsMIOspfEntry 1 }

fsMIOspfPktsRcvd OBJECT-TYPE
    SYNTAX      Counter
    ACCESS      read-only
    STATUS      mandatory
    DESCRIPTION 
        " This gives the Total no. of Packets received.
         ALCATEL NOTE:
           ACCESS:      NA          USAGE:       NA
           PERSIST:     NO          INSRVMOD:    NA
           RANGE:       NA          DEFVALUE:    0
           UNITS:       PACKETS     SPARSE:      NA
           DESCR:       NA"
    ::= { fsMIOspfEntry 2 }

fsMIOspfPktsTxed OBJECT-TYPE
    SYNTAX      Counter
    ACCESS      read-only
    STATUS      mandatory
    DESCRIPTION 
        " This gives the Total no. of Packets Transmitted.
         ALCATEL NOTE:
           ACCESS:      NA          USAGE:       NA
           PERSIST:     NO          INSRVMOD:    NA
           RANGE:       NA          DEFVALUE:    0
           UNITS:       PACKETS     SPARSE:      NA
           DESCR:       NA"
    ::= { fsMIOspfEntry 3 }

fsMIOspfPktsDisd OBJECT-TYPE
    SYNTAX      Counter
    ACCESS      read-only
    STATUS      mandatory
    DESCRIPTION 
        " This gives the Total no. of Packets Discarded.
         ALCATEL NOTE:
           ACCESS:      NA          USAGE:       NA
           PERSIST:     NO          INSRVMOD:    NA
           RANGE:       NA          DEFVALUE:    0
           UNITS:       PACKETS     SPARSE:      NA
           DESCR:       NA"
    ::= { fsMIOspfEntry 4 }

fsMIOspfRFC1583Compatibility OBJECT-TYPE
    SYNTAX      Status
    ACCESS      read-write
    STATUS      mandatory
    DESCRIPTION 
        " Controls the preference rules, when chossing among multiple AS external LSAs advertising the same destination.
         When set to enabled, the preference rules remain those specified
         by RFC1583. 
         When set to disabled the prference rules are those stated in RFC2178.
         Set to enabled by default.
         ALCATEL NOTE:
         ACCESS:      NA          USAGE:       NA
         PERSIST:     YES         INSRVMOD:    YES
         RANGE:       1,2         DEFVALUE:    NA
         UNITS:       NA          SPARSE:      NA
         DESCR:       NA"
--     REFERENCE   
--         " OSPF Version 2, Appendix on Demand Routing"
    DEFVAL      { enabled }
    ::= { fsMIOspfEntry 5 }

fsMIOspfTraceLevel OBJECT-TYPE
    SYNTAX      INTEGER
    ACCESS      read-write
    STATUS      mandatory
    DESCRIPTION 
        " This object is used to define level of trace required for OSPF. 
         Levels are defined as follows.
         0x00000100 -- Packet High Level Dump Trace.
         0x00000200 -- Packet Low Level Dump Trace.
         0x00000400 -- Packet Hex Dump Trace.
         0x00000800 -- Critical Trace.
         0x00001000 -- Function Entry Trace.
         0x00002000 -- Function Exit Trace.
         0x00004000 -- Memory Allocation Success Trace.
         0x00008000 -- Memory Allocation Failure Trace.
         0x00010000 -- Hello packet Trace.
         0x00020000 -- DDP packet Trace.
         0x00040000 -- Link State Request Packet Trace.
         0x00080000 -- Link State Update Packet Trace.
         0x00100000 -- Link State Acknowledge Packet Trace.
         0x00200000 -- Interface State Machine Trace.
         0x00400000 -- Neighbor State Machine Trace.
         0x00800000 -- Routing Table Calculation Trace.
         0x01000000 -- RTM Module Trace.  
         0x02000000 -- Interface Trace.  
         0x04000000 -- NSSA Trace.
         0x08000000 -- Route Aggregation Trace.
         0x10000000 -- Configuration Trace.
         0x20000000 -- Adjacency formation Trace.
         0x40000000 -- Link State Database Trace.
         0x80000000 -- Protocol Packet Processing Trace.
         ALCATEL NOTE:
         ACCESS:      NA          USAGE:       NA
         PERSIST:     YES         INSRVMOD:    YES
         RANGE:       NA          DEFVALUE:    NA
         UNITS:       NA          SPARSE:      NA
         DESCR:       This should not used by the operator and it is only for debugging purpose"
    DEFVAL      { 2048 }
    ::= { fsMIOspfEntry 12 }

fsMIOspfMinLsaInterval OBJECT-TYPE
    SYNTAX      INTEGER (1..65535)
    ACCESS      read-write
    STATUS      mandatory
    DESCRIPTION 
        "The minimum time between distinct originations of any particular LSA.
         ALCATEL NOTE:
              ACCESS:      NA          USAGE:       NA
              PERSIST:     YES         INSRVMOD:    YES
              RANGE:       NA          DEFVALUE:    NA
              UNITS:       SECONDS     SPARSE:      NA
              DESCR:       NA"
    DEFVAL      { 5 }
    ::= { fsMIOspfEntry 13 }

fsMIOspfABRType OBJECT-TYPE
    SYNTAX      INTEGER { standardABR(1), ciscoABR(2), ibmABR(3) }
    ACCESS      read-write
    STATUS      mandatory
    DESCRIPTION 
        "Different Types of ABRs supported
         ALCATEL NOTE:
           ACCESS:      NA          USAGE:       NA
           PERSIST:     YES         INSRVMOD:    YES
           RANGE:       NA          DEFVALUE:    NA
           UNITS:       NA          SPARSE:      NA
           DESCR:       NA"
--     REFERENCE   
--         "RFC-3509 - Alternative Implementations of OSPF Area Border 
--          Routers"
    DEFVAL      { standardABR }
    ::= { fsMIOspfEntry 14 }

fsMIOspfNssaAsbrDefRtTrans OBJECT-TYPE
    SYNTAX      INTEGER { enabled(1), disabled(2) }
    ACCESS      read-write
    STATUS      mandatory
    DESCRIPTION 
        "Specifies the P-Bit setting for the default Type-7
         LSA generated by ASBR(which is not ABR).When set 
         disabled, P-Bit is clear in the generated default Lsa.
         When set to enabled, P-Bit is set in the generated
         Type-7 default Lsa. 
         ALCATEL NOTE:
         ACCESS:      NA          USAGE:       NA
         PERSIST:     YES         INSRVMOD:    YES
         RANGE:       NA          DEFVALUE:    NA
         UNITS:       NA          SPARSE:      NA
         DESCR:       NA"
    DEFVAL      { disabled }
    ::= { fsMIOspfEntry 15 }

fsMIOspfDefaultPassiveInterface OBJECT-TYPE
    SYNTAX      TruthValue
    ACCESS      read-write
    STATUS      mandatory
    DESCRIPTION 
        "When set to true all OSPF interfaces created after this
         setting will be passive interfaces. 
         If set to false OSPF interfaces created after this setting 
         will not be passive.
         ALCATEL NOTE:
         ACCESS:      NA          USAGE:       NA
         PERSIST:     YES         INSRVMOD:    YES
         RANGE:       1,2         DEFVALUE:    NA
         UNITS:       NA          SPARSE:      NA
         DESCR:       NA"
    DEFVAL      { false }
    ::= { fsMIOspfEntry 16 }

fsMIOspfSpfHoldtime OBJECT-TYPE
    SYNTAX      INTEGER (0..65535000)
    ACCESS      read-write
    STATUS      mandatory
    DESCRIPTION 
        "Minimum time between two consecutive SPF calculations in one ospf instances.
         Time is configured in milli seconds.
         Setting the value to 0 is not allowed.
         ALCATEL NOTE:
          ACCESS:      NA           USAGE:       NA
          PERSIST:     YES          INSRVMOD:    NA
          RANGE:       NA           DEFVALUE:    NA       
          UNITS:       NA           SPARSE:      NA
          DESCR:       In ECNTA, Get of this object will always return 0, Set of this object will always return failure, since this object is not supported in ECNTA"
    DEFVAL      { 5000 }
    ::= { fsMIOspfEntry 17 }

fsMIOspfSpfDelay OBJECT-TYPE
    SYNTAX      INTEGER (0 | 10..1000)
    ACCESS      read-write
    STATUS      mandatory
    DESCRIPTION 
        "The Delay at which routing calculation is carried after a topology change in one ospf instance.
         Time is configured in milli seconds.
         Setting the value to 0 is not allowed.
         ALCATEL NOTE:
          ACCESS:      NA           USAGE:       NA
          PERSIST:     YES          INSRVMOD:    NA
          RANGE:       NA           DEFVALUE:    NA       
          UNITS:       NA           SPARSE:      NA
          DESCR:       In ECNTA, Get of this object will always return 0, Set of this object will always return failure, since this object is not supported in ECNTA"
    DEFVAL      { 100 }
    ::= { fsMIOspfEntry 18 }

fsMIOspfInternalLsaCount OBJECT-TYPE
    SYNTAX      INTEGER
    ACCESS      read-only
    STATUS      mandatory
    DESCRIPTION 
        "The number of internal LSA link-state
         advertisements in the link-state database.
         ALCATEL NOTE:
          ACCESS:      NA          USAGE:       NA
          PERSIST:     NO          INSRVMOD:    NA
          RANGE:       NA          DEFVALUE:    NA
          UNITS:       NA          SPARSE:      NA
          DESCR:       In ECNTA, Get of this object will always return -1, since this object is not supported in ECNTA"
    DEFVAL      { 0 }
    ::= { fsMIOspfEntry 19 }

fsMIOspfRedisRouteCountPerVrf OBJECT-TYPE
    SYNTAX      INTEGER
    ACCESS      read-only
    STATUS      mandatory
    DESCRIPTION 
        " This gives the total number of Routes Redistributed to OSPF
         in the particular VRF.
         ALCATEL NOTE:
             ACCESS:      NA           USAGE:       NA
             PERSIST:     NO           INSRVMOD:    NA
             RANGE:       NA           DEFVALUE:    NA       
             UNITS:       Routes       SPARSE:      NA
             DESCR:       In ECNTA, Get of this object will always return 0, since Multiple instance is not supported in ECNTA"
    DEFVAL      { 0 }
    ::= { fsMIOspfEntry 20 }

fsMIOspfExternalLSACountAllVrf OBJECT-TYPE
    SYNTAX      INTEGER
    ACCESS      read-only
    STATUS      mandatory
    DESCRIPTION 
        " This gives the total number of External LSAs in all the VRFs.
         ALCATEL NOTE:
             ACCESS:      NA           USAGE:       NA
             PERSIST:     NO           INSRVMOD:    NA
             RANGE:       NA           DEFVALUE:    NA       
             UNITS:       LSAs         SPARSE:      NA
             DESCR:       In ECNTA, Get of this object will always return -1, since Multiple instance is not supported in ECNTA"
    DEFVAL      { 0 }
    ::= { fsMIOspfGeneralGroup 4 }

fsMIOspfInternalLSACountAllVrf OBJECT-TYPE
    SYNTAX      INTEGER
    ACCESS      read-only
    STATUS      mandatory
    DESCRIPTION 
        " This gives the total number of Internal LSAs in all the VRFs.
         ALCATEL NOTE:
             ACCESS:      NA           USAGE:       NA
             PERSIST:     NO           INSRVMOD:    NA
             RANGE:       NA           DEFVALUE:    NA       
             UNITS:       LSAs         SPARSE:      NA
             DESCR:       In ECNTA, Get of this object will always return -1, since Multiple instance is not supported in ECNTA"
    DEFVAL      { 0 }
    ::= { fsMIOspfGeneralGroup 5 }

fsMIOspfRedisRouteCountAllVrf OBJECT-TYPE
    SYNTAX      INTEGER
    ACCESS      read-only
    STATUS      mandatory
    DESCRIPTION 
        " This gives the total number of Routes Redistributed to OSPF
         in all the VRFs.
         ALCATEL NOTE:
             ACCESS:      NA           USAGE:       NA
             PERSIST:     NO           INSRVMOD:    NA
             RANGE:       NA           DEFVALUE:    NA       
             UNITS:       Routes       SPARSE:      NA
             DESCR:       In ECNTA, Get of this object will always return -1, since Multiple instance is not supported in ECNTA"
    DEFVAL      { 0 }
    ::= { fsMIOspfGeneralGroup 6 }

fsMIOspfRedistributedRouteTable OBJECT-TYPE
    SYNTAX      SEQUENCE OF FsMIOspfRedistributedRouteEntry
    ACCESS      not-accessible
    STATUS      mandatory
    DESCRIPTION 
        "A table of Redistributed route information.
         ALCATEL NOTE
         	TABLE SIZE :  DEP
         	DESCR:	 DEP(TABLESIZE):The size of the table is derived from the 
         			object fsVrfNoOfOspfRedisRoutes in fsvrf.mib."
    ::= { fsMIOspfGeneralGroup 7 }

fsMIOspfRedistributedRouteEntry OBJECT-TYPE
    SYNTAX      FsMIOspfRedistributedRouteEntry
    ACCESS      not-accessible
    STATUS      mandatory
    DESCRIPTION 
        "The information regarding a single Redistributed route.
         Row creation : An entry shall be created in one step by a 
             set-request with all necessary parameter values and  
             fsMIOspfRedistributedRouteOrigin  set to createAndGo(4).
         Row deletion : An entry shall be deleted by setting
             the fsMIOspfRedistributedRouteOrigin  of the specific entry to destroy(6).
         Index usage : the index is the OSPF Context Id, Route Destination,Route Mask,Route Type Of Service.
           Note that entries will be presented to the SNMP manager in full
           lexicographical order :  sorted on OSPF Context Id, then on Route Destination,Route Mask,Route Type Of Service."
    INDEX       { fsMIStdOspfContextId, fsMIOspfRedistributedRouteDest, 
                  fsMIOspfRedistributedRouteMask, 
                  fsMIOspfRedistributedRouteTOS }
    ::= { fsMIOspfRedistributedRouteTable 1 }

FsMIOspfRedistributedRouteEntry ::= SEQUENCE {
    fsMIOspfRedistributedRouteDest          IpAddress,
    fsMIOspfRedistributedRouteMask          IpAddress,
    fsMIOspfRedistributedRouteTOS           TOSType,
    fsMIOspfRedistributedRouteMetric        BigMetric,
    fsMIOspfRedistributedRouteMetricType    INTEGER,
    fsMIOspfRedistributedRouteTag           INTEGER,
    fsMIOspfRedistributedRouteFwdAdr        IpAddress,
    fsMIOspfRedistributedRouteIfIndex       InterfaceIndex,
    fsMIOspfRedistributedRouteNextHop       IpAddress,
    fsMIOspfRedistributedRouteOrigin        INTEGER
}

fsMIOspfRedistributedRouteDest OBJECT-TYPE
    SYNTAX      IpAddress
    ACCESS      not-accessible
    STATUS      mandatory
    DESCRIPTION 
        " Net Id of the Redistributed route to Destination.
         ALCATEL NOTE:
            ACCESS:      NA          USAGE:       NA
            PERSIST:     NA          INSRVMOD:    NA
            RANGE:       NA          DEFVALUE:    NA
            UNITS:       NA          SPARSE:      NO
            DESCR:       NA"
    ::= { fsMIOspfRedistributedRouteEntry 1 }

fsMIOspfRedistributedRouteMask OBJECT-TYPE
    SYNTAX      IpAddress
    ACCESS      not-accessible
    STATUS      mandatory
    DESCRIPTION 
        " Mask of the Redistributed Route to Destination.
         ALCATEL NOTE:
            ACCESS:      NA          USAGE:       NA
            PERSIST:     NA          INSRVMOD:    NA
            RANGE:       NA          DEFVALUE:    NA
            UNITS:       NA          SPARSE:      NO
            DESCR:       NA"
    ::= { fsMIOspfRedistributedRouteEntry 2 }

fsMIOspfRedistributedRouteTOS OBJECT-TYPE
    SYNTAX      TOSType
    ACCESS      not-accessible
    STATUS      mandatory
    DESCRIPTION 
        " The  Type  of  Service  associated with the Redistributed Route.
         ALCATEL NOTE:
            ACCESS:      NA                   USAGE:       NA
            PERSIST:     NA                   INSRVMOD:    NA
            RANGE:       1,2,3,5,7,9,11..31   DEFVALUE:    NA
            UNITS:       NA                   SPARSE:      NO
            DESCR:       NA"
    ::= { fsMIOspfRedistributedRouteEntry 3 }

fsMIOspfRedistributedRouteMetric OBJECT-TYPE
    SYNTAX      BigMetric
    ACCESS      read-only
    STATUS      mandatory
    DESCRIPTION 
        " The metric value applied at the indicated type
         of  service.  By default, this equals the least
         metric at the type of service among the  inter-faces
         to other areas.
         ALCATEL NOTE:
         ACCESS:      NA           USAGE:       NA
         PERSIST:     NA           INSRVMOD:    NA
         RANGE:       0..16777215  DEFVALUE:    NA
         UNITS:       NA           SPARSE:      NO
         DESCR:       NA"
    ::= { fsMIOspfRedistributedRouteEntry 4 }

fsMIOspfRedistributedRouteMetricType OBJECT-TYPE
    SYNTAX      INTEGER { asexttype1(1), asexttype2(2) }
    ACCESS      read-only
    STATUS      mandatory
    DESCRIPTION 
        " The metric Type applied at the indicated type of service.
         ALCATEL NOTE:
            ACCESS:      NA         USAGE:       NA
            PERSIST:     NA         INSRVMOD:    NA 
            RANGE:       NA         DEFVALUE:    0
            UNITS:       NA         SPARSE:      NO
            DESCR:       NA"
    ::= { fsMIOspfRedistributedRouteEntry 5 }

fsMIOspfRedistributedRouteTag OBJECT-TYPE
    SYNTAX      INTEGER
    ACCESS      read-only
    STATUS      mandatory
    DESCRIPTION 
        " The route tag applied at the indicated type of service.
         ALCATEL NOTE:
                   ACCESS:      NA             USAGE:       NA
         	  PERSIST:     NA             INSRVMOD:    NA
         	  RANGE:       0..2147483647  DEFVALUE:    NA
           UNITS:       NA             SPARSE:      NO
         	  DESCR:       NA"
    ::= { fsMIOspfRedistributedRouteEntry 6 }

fsMIOspfRedistributedRouteFwdAdr OBJECT-TYPE
    SYNTAX      IpAddress
    ACCESS      read-only
    STATUS      mandatory
    DESCRIPTION 
        " This Indicates the IP Address to which Packets
         for the destinations should be forwarded.
         ALCATEL NOTE:
         ACCESS:      NA          USAGE:       NA
         PERSIST:     NA          INSRVMOD:    NA
         RANGE:       NA          DEFVALUE:    NA
         UNITS:       NA          SPARSE:      NO
         DESCR:       NA"
    ::= { fsMIOspfRedistributedRouteEntry 7 }

fsMIOspfRedistributedRouteIfIndex OBJECT-TYPE
    SYNTAX      InterfaceIndex (0..65535)
    ACCESS      read-only
    STATUS      mandatory
    DESCRIPTION 
        " The Interface to reach the destination.
         This will have a valid value for futOspfRedistributedRouteFwdAdr
         value being 0.0.0.0. Otherwise this has the
         value of 0.
         ALCATEL NOTE:
         ACCESS:      NA          USAGE:       NA
         PERSIST:     NA          INSRVMOD:    NA
         RANGE:       1..65535    DEFVALUE:    NA
         UNITS:       NA          SPARSE:      NO
         DESCR:       NA"
    ::= { fsMIOspfRedistributedRouteEntry 8 }

fsMIOspfRedistributedRouteNextHop OBJECT-TYPE
    SYNTAX      IpAddress
    ACCESS      read-only
    STATUS      mandatory
    DESCRIPTION 
        " IP address of the next hop to reach the destination.
         This will have a valid value for ospfRedistributedRouteFwdAdr
         value being 0.0.0.0. Otherwise this has the
         value of 0.0.0.0.
         ALCATEL NOTE:
         ACCESS:      NA          USAGE:       NA
         PERSIST:     NA          INSRVMOD:    NA
         RANGE:       NA          DEFVALUE:    NA
         UNITS:       NA          SPARSE:      NO
         DESCR:       NA"
    ::= { fsMIOspfRedistributedRouteEntry 9 }

fsMIOspfRedistributedRouteOrigin OBJECT-TYPE
    SYNTAX      INTEGER { local(2), static(3), rip(8), bgp(14) }
    ACCESS      read-only
    STATUS      mandatory
    DESCRIPTION 
        " This variable used to get the route origin which is local,static,RIP,BGP.
         ALCATEL NOTE:
            ACCESS:      NA          USAGE:       NA
            PERSIST:     NA          INSRVMOD:    NA
            RANGE:       NA          DEFVALUE:    NA
            UNITS:       NA          SPARSE:      NO
            DESCR:       NA"
    ::= { fsMIOspfRedistributedRouteEntry 10 }

fsMIOspfAreaTable OBJECT-TYPE
    SYNTAX      SEQUENCE OF FsMIOspfAreaEntry
    ACCESS      not-accessible
    STATUS      mandatory
    DESCRIPTION 
        "Information describing the configured  parame-
         ters  and cumulative statistics of the router's
         attached areas.
         ALCATEL NOTE:
         	TABLE SIZE:    DEP
         	DESCR:	 DEP(TABLESIZE):The size of the table is derived from the 
         			object fsVrfNoOfOspfAreas in fsvrf.mib."
    ::= { fsMIOspf 2 }

fsMIOspfAreaEntry OBJECT-TYPE
    SYNTAX      FsMIOspfAreaEntry
    ACCESS      not-accessible
    STATUS      mandatory
    DESCRIPTION 
        "Information describing the configured  parame-
         ters  and  cumulative  statistics of one of the
         router's attached areas.
         Row creation : An entry shall be created when the ospfAreaTable(ospfAreaStatus) is created.
         Row deletion : An entry shall be deleted when the ospfAreaTable(ospfAreaStatus) is deleted.
         Index usage : the index is the Area Id.
         Note that entries will be presented to the SNMP manager in full
         lexicographical order :  sorted on Area Id."
    INDEX       { fsMIStdOspfContextId, fsMIOspfAreaId }
    ::= { fsMIOspfAreaTable 1 }

FsMIOspfAreaEntry ::= SEQUENCE {
    fsMIOspfAreaId                                  AreaID,
    fsMIOspfAreaIfCount                             Gauge,
    fsMIOspfAreaNetCount                            Gauge,
    fsMIOspfAreaRtrCount                            Gauge,
    fsMIOspfAreaNSSATranslatorRole                  INTEGER,
    fsMIOspfAreaNSSATranslatorState                 INTEGER,
    fsMIOspfAreaNSSATranslatorStabilityInterval     PositiveInteger,
    fsMIOspfAreaNSSATranslatorEvents                Counter
}

fsMIOspfAreaId OBJECT-TYPE
    SYNTAX      AreaID
    ACCESS      not-accessible
    STATUS      mandatory
    DESCRIPTION 
        "A 32-bit integer uniquely identifying an area.
         Area ID 0.0.0.0 is used for the OSPF backbone.
         ALCATEL NOTE:
         ACCESS:      NA          USAGE:       NA
         PERSIST:     YES         INSRVMOD:    NA
         RANGE:       NA          DEFVALUE:    NA
         UNITS:       NA          SPARSE:      NO
         DESCR:       NA"
--     REFERENCE   
--         "OSPF Version 2, Appendix C.2 Area parameters"
    ::= { fsMIOspfAreaEntry 1 }

fsMIOspfAreaIfCount OBJECT-TYPE
    SYNTAX      Gauge
    ACCESS      read-only
    STATUS      mandatory
    DESCRIPTION 
        " This gives the Total no. of Ifaces in the Area 
         ALCATEL NOTE:
           ACCESS:      NA          USAGE:       NA
           PERSIST:     NO          INSRVMOD:    NA
           RANGE:       NA          DEFVALUE:    0
           UNITS:       INTERFACES  SPARSE:      NO
           DESCR:       NA"
    ::= { fsMIOspfAreaEntry 2 }

fsMIOspfAreaNetCount OBJECT-TYPE
    SYNTAX      Gauge
    ACCESS      read-only
    STATUS      mandatory
    DESCRIPTION 
        " This gives the Total no. of Networks in the Area. 
         ALCATEL NOTE:
           ACCESS:      NA          USAGE:       NA
           PERSIST:     NO          INSRVMOD:    NA
           RANGE:       NA          DEFVALUE:    0
           UNITS:       NETWORKS    SPARSE:      NO
           DESCR:       NA"
    ::= { fsMIOspfAreaEntry 3 }

fsMIOspfAreaRtrCount OBJECT-TYPE
    SYNTAX      Gauge
    ACCESS      read-only
    STATUS      mandatory
    DESCRIPTION 
        " This gives the Total no. of Routers in the Area. 
         ALCATEL NOTE:
           ACCESS:      NA          USAGE:       NA
           PERSIST:     NO          INSRVMOD:    NA
           RANGE:       NA          DEFVALUE:    0
           UNITS:       ROUTERS     SPARSE:      NO
           DESCR:       NA"
    ::= { fsMIOspfAreaEntry 4 }

fsMIOspfAreaNSSATranslatorRole OBJECT-TYPE
    SYNTAX      INTEGER { always(1), candidate(2) }
    ACCESS      read-write
    STATUS      mandatory
    DESCRIPTION 
        " Indicate's an NSSA Border router's ability
         to perform NSSA Translation of Type-7 LSAs
         to Type-5 LSAs. 
         ALCATEL NOTE:
         ACCESS:      NA          USAGE:       NA
         PERSIST:     YES         INSRVMOD:    YES
         RANGE:       NA          DEFVALUE:    NA
         UNITS:       NA          SPARSE:      NO
         DESCR:       NA"
    DEFVAL      { candidate }
    ::= { fsMIOspfAreaEntry 5 }

fsMIOspfAreaNSSATranslatorState OBJECT-TYPE
    SYNTAX      INTEGER { enabled(1), elected(2), disabled(3) }
    ACCESS      read-only
    STATUS      mandatory
    DESCRIPTION 
        " Indicate's if and how an NSSA Border router is
         performing NSSA translation of Type-7 to into Type-5
         LSAs.When this object is set to enabled, the NSSA border
         router's fsMIOspfAreaNssaTranslatorRole has been set to
         always.When this object is set to elected,a candidate
         NSSA border router is translating Type-7 to Type-5 LSAs.
         When this object is set to disabled, a candidate NSSA
         Border router is not performing translation. 
         ALCATEL NOTE:
         ACCESS:      NA          USAGE:       NA
         PERSIST:     NO          INSRVMOD:    NA
         RANGE:       NA          DEFVALUE:    NA
         UNITS:       NA          SPARSE:      NO
         DESCR:       NA"
    DEFVAL      { disabled }
    ::= { fsMIOspfAreaEntry 6 }

fsMIOspfAreaNSSATranslatorStabilityInterval OBJECT-TYPE
    SYNTAX      PositiveInteger
    ACCESS      read-write
    STATUS      mandatory
    DESCRIPTION 
        " The number of seconds after an elected translator
         determines its services are no longer required, that
         it should continue to perform its translation duties.
         ALCATEL NOTE:
         ACCESS:      NA          USAGE:       NA
         PERSIST:     YES         INSRVMOD:    YES
         RANGE:       0..65535    DEFVALUE:    NA
         UNITS:       SECONDS     SPARSE:      NO
         DESCR:       NA"
    DEFVAL      { 40 }
    ::= { fsMIOspfAreaEntry 7 }

fsMIOspfAreaNSSATranslatorEvents OBJECT-TYPE
    SYNTAX      Counter
    ACCESS      read-only
    STATUS      mandatory
    DESCRIPTION 
        " Indicates the number of  translator state
         changes that have occured since the last boot-up. 
         ALCATEL NOTE:
         ACCESS:      NA          USAGE:       NA
         PERSIST:     NO          INSRVMOD:    NA
         RANGE:       NA          DEFVALUE:    0
         UNITS:       NA          SPARSE:      NO
         DESCR:       NA"
    ::= { fsMIOspfAreaEntry 8 }

fsMIOspfHostTable OBJECT-TYPE
    SYNTAX      SEQUENCE OF FsMIOspfHostEntry
    ACCESS      not-accessible
    STATUS      mandatory
    DESCRIPTION 
        " The list of Hosts, and their metrics, that the
         router will advertise as host routes.
         ALCATEL NOTE:
         	TABLE SIZE:    8
         	DESCR:         NA"
--     REFERENCE   
--         "OSPF Version 2, Appendix C.6  Host route parameters"
    ::= { fsMIOspf 3 }

fsMIOspfHostEntry OBJECT-TYPE
    SYNTAX      FsMIOspfHostEntry
    ACCESS      not-accessible
    STATUS      mandatory
    DESCRIPTION 
        "A metric to be advertised, for a given type of
         service, when a given host is reachable.
         Row creation : An entry shall be created when stdOspfTable(ospfHostStatus) is created. .
         Row deletion : An entry shall be deleted when stdOspfTable(ospfHostStatus) is destroyed.
         Index usage : the index is the Ip Address,Type Of Service.
         Note that entries will be presented to the SNMP manager in full
         lexicographical order :  sorted on Ip Address,Type Of Service."
    INDEX       { fsMIStdOspfContextId, fsMIOspfHostIpAddress, 
                  fsMIOspfHostTOS }
    ::= { fsMIOspfHostTable 1 }

FsMIOspfHostEntry ::= SEQUENCE {
    fsMIOspfHostIpAddress       IpAddress,
    fsMIOspfHostTOS             TOSType,
    fsMIOspfHostRouteIfIndex    INTEGER
}

fsMIOspfHostIpAddress OBJECT-TYPE
    SYNTAX      IpAddress
    ACCESS      not-accessible
    STATUS      mandatory
    DESCRIPTION 
        "The IP Address of the Host.
         ALCATEL NOTE:
           ACCESS:      NA          USAGE:       NA
           PERSIST:     NO          INSRVMOD:    NA
           RANGE:       NA          DEFVALUE:    NA
           UNITS:       NA          SPARSE:      NO
           DESCR:       NA"
--     REFERENCE   
--         "OSPF Version 2, Appendix C.6 Host route parameters"
    ::= { fsMIOspfHostEntry 1 }

fsMIOspfHostTOS OBJECT-TYPE
    SYNTAX      TOSType
    ACCESS      not-accessible
    STATUS      mandatory
    DESCRIPTION 
        "The Type of Service of the route being configured.
         ALCATEL NOTE:
           ACCESS:      NA                      USAGE:       NA
           PERSIST:     NO                      INSRVMOD:    NA
           RANGE:       1,2,3,5,7,9,11..31      DEFVALUE:    NA
           UNITS:       NA                      SPARSE:      NO
           DESCR:       NA"
--     REFERENCE   
--         "OSPF Version 2, Appendix C.6 Host route parameters"
    ::= { fsMIOspfHostEntry 2 }

fsMIOspfHostRouteIfIndex OBJECT-TYPE
    SYNTAX      INTEGER (0..65535)
    ACCESS      read-write
    STATUS      mandatory
    DESCRIPTION 
        "The Interface to reach the host
         ALCATEL NOTE:
           ACCESS:      NA          USAGE:       NA
           PERSIST:     NO          INSRVMOD:    YES
           RANGE:       1..65535    DEFVALUE:    NA
           UNITS:       NA          SPARSE:      NO
           DESCR:       NA"
    ::= { fsMIOspfHostEntry 3 }

fsMIOspfIfTable OBJECT-TYPE
    SYNTAX      SEQUENCE OF FsMIOspfIfEntry
    ACCESS      not-accessible
    STATUS      mandatory
    DESCRIPTION 
        "The OSPF Interface Table describes the  inter-
         faces from the viewpoint of OSPF.
         ALCATEL NOTE:
         	TABLE SIZE:    DEP
         	DESCR:	 DEP(TABLESIZE):The size of the table is derived from the 
         			object fsVrfNoOfOspfInterfaces in fsvrf.mib."
--     REFERENCE   
--         "OSPF Version 2, Appendix C.3  Router  interface
--          parameters"
    ::= { fsMIOspf 4 }

fsMIOspfIfEntry OBJECT-TYPE
    SYNTAX      FsMIOspfIfEntry
    ACCESS      not-accessible
    STATUS      mandatory
    DESCRIPTION 
        "The OSPF Interface Entry describes one  inter-
         face from the viewpoint of OSPF.
         A metric to be advertised, for a given type of
         service, when a given host is reachable.
         Row creation : An entry shall be created when the stdOspfTable (ospfIfStatus) set to createAndGo(4).
         Row deletion : An entry shall be deleted when the stdOspfTable (ospfIfStatus) of the specific entry to destroy(6).
         Index usage : the index is the Ip Address,Adress Less Interface.
         Note that entries will be presented to the SNMP manager in full
         lexicographical order :  sorted on Ip Address,Adress Less Interface."
    INDEX       { fsMIStdOspfContextId, fsMIOspfIfIpAddress, 
                  fsMIOspfAddressLessIf }
    ::= { fsMIOspfIfTable 1 }

FsMIOspfIfEntry ::= SEQUENCE {
    fsMIOspfIfIpAddress     IpAddress,
    fsMIOspfAddressLessIf   InterfaceIndex,
    fsMIOspfIfOperState     INTEGER,
    fsMIOspfIfPassive       TruthValue,
    fsMIOspfIfNbrCount      Gauge,
    fsMIOspfIfAdjCount      Gauge,
    fsMIOspfIfHelloRcvd     Counter,
    fsMIOspfIfHelloTxed     Counter,
    fsMIOspfIfHelloDisd     Counter,
    fsMIOspfIfDdpRcvd       Counter,
    fsMIOspfIfDdpTxed       Counter,
    fsMIOspfIfDdpDisd       Counter,
    fsMIOspfIfLrqRcvd       Counter,
    fsMIOspfIfLrqTxed       Counter,
    fsMIOspfIfLrqDisd       Counter,
    fsMIOspfIfLsuRcvd       Counter,
    fsMIOspfIfLsuTxed       Counter,
    fsMIOspfIfLsuDisd       Counter,
    fsMIOspfIfLakRcvd       Counter,
    fsMIOspfIfLakTxed       Counter,
    fsMIOspfIfLakDisd       Counter
}

fsMIOspfIfIpAddress OBJECT-TYPE
    SYNTAX      IpAddress
    ACCESS      not-accessible
    STATUS      mandatory
    DESCRIPTION 
        "The IP address of this OSPF interface.
         ALCATEL NOTE:
           ACCESS:      NA          USAGE:       NA
           PERSIST:     YES         INSRVMOD:    NA
           RANGE:       NA          DEFVALUE:    NA
           UNITS:       NA          SPARSE:      NO
           DESCR:       NA"
    ::= { fsMIOspfIfEntry 1 }

fsMIOspfAddressLessIf OBJECT-TYPE
    SYNTAX      InterfaceIndex (0..65535)
    ACCESS      not-accessible
    STATUS      mandatory
    DESCRIPTION 
        "For the purpose of easing  the  instancing  of
         addressed   and  addressless  interfaces;  This
         variable takes the value 0 on  interfaces  with
         IP  Addresses,  and  the corresponding value of
         ifIndex for interfaces having no IP Address.
         ALCATEL NOTE:
         ACCESS:      NA          USAGE:       NA
         PERSIST:     YES         INSRVMOD:    NA
         RANGE:       NA          DEFVALUE:    NA
         UNITS:       NA          SPARSE:      NO
         DESCR:       NA"
    ::= { fsMIOspfIfEntry 2 }

fsMIOspfIfOperState OBJECT-TYPE
    SYNTAX      INTEGER { operup(1), operdown(2), loopback(3), unloop(4) }
    ACCESS      read-only
    STATUS      mandatory
    DESCRIPTION 
        " This gives the Operational Status of the Interface.
         ALCATEL NOTE:
           ACCESS:      NA          USAGE:       NA
           PERSIST:     NO          INSRVMOD:    NA
           RANGE:       NA          DEFVALUE:    1    
           UNITS:       NA          SPARSE:      NO
           DESCR:       NA"
    ::= { fsMIOspfIfEntry 3 }

fsMIOspfIfPassive OBJECT-TYPE
    SYNTAX      TruthValue
    ACCESS      read-write
    STATUS      mandatory
    DESCRIPTION 
        " This object is used to make the inteface as passive.
         If set to TRUE, then interface will be passive
         If set to FALSE then interface will be normal
         ALCATEL NOTE:
         ACCESS:      NA          USAGE:       NA
         PERSIST:     YES         INSRVMOD:    YES
         RANGE:       1,2         DEFVALUE:    2
         UNITS:       NA          SPARSE:      NO
         DESCR:       NA"
    DEFVAL      { false }
    ::= { fsMIOspfIfEntry 4 }

fsMIOspfIfNbrCount OBJECT-TYPE
    SYNTAX      Gauge
    ACCESS      read-only
    STATUS      mandatory
    DESCRIPTION 
        " This gives the Total number of Neighbour's through 
         that Interface.
         ALCATEL NOTE:
         ACCESS:      NA          USAGE:       NA
         PERSIST:     NO          INSRVMOD:    NA
         RANGE:       NA          DEFVALUE:    0
         UNITS:       NA          SPARSE:      NA
         DESCR:       NA"
    ::= { fsMIOspfIfEntry 5 }

fsMIOspfIfAdjCount OBJECT-TYPE
    SYNTAX      Gauge
    ACCESS      read-only
    STATUS      mandatory
    DESCRIPTION 
        " This gives the Total number of Adjacencies through 
         that Interface.
         ALCATEL NOTE:
         ACCESS:      NA          USAGE:       NA
         PERSIST:     NO          INSRVMOD:    NA
         RANGE:       NA          DEFVALUE:    0
         UNITS:       NA          SPARSE:      NO
         DESCR:       NA"
    ::= { fsMIOspfIfEntry 6 }

fsMIOspfIfHelloRcvd OBJECT-TYPE
    SYNTAX      Counter
    ACCESS      read-only
    STATUS      mandatory
    DESCRIPTION 
        " This gives the Total number of Hello packets received
         through that Interface.
         ALCATEL NOTE:
         ACCESS:      NA          USAGE:       NA
         PERSIST:     NO          INSRVMOD:    NA
         RANGE:       NA          DEFVALUE:    0
         UNITS:       PACKETS     SPARSE:      NO
         DESCR:       NA"
    ::= { fsMIOspfIfEntry 7 }

fsMIOspfIfHelloTxed OBJECT-TYPE
    SYNTAX      Counter
    ACCESS      read-only
    STATUS      mandatory
    DESCRIPTION 
        " This gives the Total number of Hello packets 
         transmitted through that Interface.
         ALCATEL NOTE:
         ACCESS:      NA          USAGE:       NA
         PERSIST:     NO          INSRVMOD:    NA
         RANGE:       NA          DEFVALUE:    0
         UNITS:       PACKETS     SPARSE:      NO
         DESCR:       NA"
    ::= { fsMIOspfIfEntry 8 }

fsMIOspfIfHelloDisd OBJECT-TYPE
    SYNTAX      Counter
    ACCESS      read-only
    STATUS      mandatory
    DESCRIPTION 
        " This gives the Total number of Hello packets 
         discarded through that Interface.
         ALCATEL NOTE:
         ACCESS:      NA          USAGE:       NA
         PERSIST:     NO          INSRVMOD:    NA
         RANGE:       NA          DEFVALUE:    0
         UNITS:       PACKETS     SPARSE:      NO
         DESCR:       NA"
    ::= { fsMIOspfIfEntry 9 }

fsMIOspfIfDdpRcvd OBJECT-TYPE
    SYNTAX      Counter
    ACCESS      read-only
    STATUS      mandatory
    DESCRIPTION 
        " This gives the Total number of Ddp packets received
         through that Interface.
         ALCATEL NOTE:
         ACCESS:      NA          USAGE:       NA
         PERSIST:     NO          INSRVMOD:    NA
         RANGE:       NA          DEFVALUE:    0
         UNITS:       PACKETS     SPARSE:      NO
         DESCR:       NA"
    ::= { fsMIOspfIfEntry 10 }

fsMIOspfIfDdpTxed OBJECT-TYPE
    SYNTAX      Counter
    ACCESS      read-only
    STATUS      mandatory
    DESCRIPTION 
        " This gives the Total number of Ddp packets 
         transmitted through that Interface.
         ALCATEL NOTE:
         ACCESS:      NA          USAGE:       NA
         PERSIST:     NO          INSRVMOD:    NA
         RANGE:       NA          DEFVALUE:    0
         UNITS:       PACKETS     SPARSE:      NO
         DESCR:       NA"
    ::= { fsMIOspfIfEntry 11 }

fsMIOspfIfDdpDisd OBJECT-TYPE
    SYNTAX      Counter
    ACCESS      read-only
    STATUS      mandatory
    DESCRIPTION 
        " This gives the Total number of Ddp packets discarded
         through that Interface.
         ALCATEL NOTE:
         ACCESS:      NA          USAGE:       NA
         PERSIST:     NO          INSRVMOD:    NA
         RANGE:       NA          DEFVALUE:    0
         UNITS:       PACKETS     SPARSE:      NO
         DESCR:       NA"
    ::= { fsMIOspfIfEntry 12 }

fsMIOspfIfLrqRcvd OBJECT-TYPE
    SYNTAX      Counter
    ACCESS      read-only
    STATUS      mandatory
    DESCRIPTION 
        " This gives the Total number of Lrq packets received
         through that Interface.
         ALCATEL NOTE:
         ACCESS:      NA          USAGE:       NA
         PERSIST:     NO          INSRVMOD:    NA
         RANGE:       NA          DEFVALUE:    0
         UNITS:       PACKETS     SPARSE:      NO
         DESCR:       NA"
    ::= { fsMIOspfIfEntry 13 }

fsMIOspfIfLrqTxed OBJECT-TYPE
    SYNTAX      Counter
    ACCESS      read-only
    STATUS      mandatory
    DESCRIPTION 
        " This gives the Total number of Lrq packets 
         transmitted through that Interface.
         ALCATEL NOTE:
         ACCESS:      NA          USAGE:       NA
         PERSIST:     NO          INSRVMOD:    NA
         RANGE:       NA          DEFVALUE:    0
         UNITS:       PACKETS     SPARSE:      NO
         DESCR:       NA"
    ::= { fsMIOspfIfEntry 14 }

fsMIOspfIfLrqDisd OBJECT-TYPE
    SYNTAX      Counter
    ACCESS      read-only
    STATUS      mandatory
    DESCRIPTION 
        " This gives the Total number of Lrq packets discarded
         through that Interface.
         ALCATEL NOTE:
         ACCESS:      NA          USAGE:       NA
         PERSIST:     NO          INSRVMOD:    NA
         RANGE:       NA          DEFVALUE:    0
         UNITS:       PACKETS     SPARSE:      NO
         DESCR:       NA"
    ::= { fsMIOspfIfEntry 15 }

fsMIOspfIfLsuRcvd OBJECT-TYPE
    SYNTAX      Counter
    ACCESS      read-only
    STATUS      mandatory
    DESCRIPTION 
        " This gives the Total number of Lsu packets received
         through that Interface.
         ALCATEL NOTE:
         ACCESS:      NA          USAGE:       NA
         PERSIST:     NO          INSRVMOD:    NA
         RANGE:       NA          DEFVALUE:    0
         UNITS:       PACKETS     SPARSE:      NO
         DESCR:       NA"
    ::= { fsMIOspfIfEntry 16 }

fsMIOspfIfLsuTxed OBJECT-TYPE
    SYNTAX      Counter
    ACCESS      read-only
    STATUS      mandatory
    DESCRIPTION 
        " This gives the Total number of Lsu packets 
         transmitted through that Interface.
         ALCATEL NOTE:
         ACCESS:      NA          USAGE:       NA
         PERSIST:     NO          INSRVMOD:    NA
         RANGE:       NA          DEFVALUE:    0
         UNITS:       PACKETS     SPARSE:      NO
         DESCR:       NA"
    ::= { fsMIOspfIfEntry 17 }

fsMIOspfIfLsuDisd OBJECT-TYPE
    SYNTAX      Counter
    ACCESS      read-only
    STATUS      mandatory
    DESCRIPTION 
        " This gives the Total number of Lsu packets discarded
         through that Interface.
         ALCATEL NOTE:
         ACCESS:      NA          USAGE:       NA
         PERSIST:     NO          INSRVMOD:    NA
         RANGE:       NA          DEFVALUE:    0
         UNITS:       PACKETS     SPARSE:      NO
         DESCR:       NA"
    ::= { fsMIOspfIfEntry 18 }

fsMIOspfIfLakRcvd OBJECT-TYPE
    SYNTAX      Counter
    ACCESS      read-only
    STATUS      mandatory
    DESCRIPTION 
        " This gives the Total number of Lak packets received
         through that Interface.
         ALCATEL NOTE:
         ACCESS:      NA          USAGE:       NA
         PERSIST:     NO          INSRVMOD:    NA
         RANGE:       NA          DEFVALUE:    0
         UNITS:       PACKETS     SPARSE:      NO
         DESCR:       NA"
    ::= { fsMIOspfIfEntry 19 }

fsMIOspfIfLakTxed OBJECT-TYPE
    SYNTAX      Counter
    ACCESS      read-only
    STATUS      mandatory
    DESCRIPTION 
        "This gives the Total number of Lak packets 
         transmitted through that Interface.
         ALCATEL NOTE:
         ACCESS:      NA          USAGE:       NA
         PERSIST:     NO          INSRVMOD:    NA
         RANGE:       NA          DEFVALUE:    0
         UNITS:       PACKETS     SPARSE:      NO
         DESCR:       NA"
    ::= { fsMIOspfIfEntry 20 }

fsMIOspfIfLakDisd OBJECT-TYPE
    SYNTAX      Counter
    ACCESS      read-only
    STATUS      mandatory
    DESCRIPTION 
        " This gives the Total number of Lak packets discarded
         on that Interface.
         ALCATEL NOTE:
         ACCESS:      NA          USAGE:       NA
         PERSIST:     NO          INSRVMOD:    NA
         RANGE:       NA          DEFVALUE:    0
         UNITS:       PACKETS     SPARSE:      NO
         DESCR:       NA"
    ::= { fsMIOspfIfEntry 21 }

fsMIOspfIfMD5AuthTable OBJECT-TYPE
    SYNTAX      SEQUENCE OF FsMIOspfIfMD5AuthEntry
    ACCESS      not-accessible
    STATUS      mandatory
    DESCRIPTION 
        "The OSPF Interface Authentication Table describes the parameters
         required for MD5 cryptographic Authentication.
         ALCATEL NOTE:
         	TABLE SIZE:   1280
         	DESCR:        NA"
--     REFERENCE   
--         "OSPF Version 2, Appendix D.3  Cryptographic Authentication"
    ::= { fsMIOspf 5 }

fsMIOspfIfMD5AuthEntry OBJECT-TYPE
    SYNTAX      FsMIOspfIfMD5AuthEntry
    ACCESS      not-accessible
    STATUS      mandatory
    DESCRIPTION 
        "The OSPF Interface MD5 Auththentication Entry describes one  
         Authentication Key from the viewpoint of OSPF.
         Row creation : An entry shall be created by setting a new futOspfIfMD5AuthKey.
         Row deletion : An entry shall be deleted by setting futOspfIfMD5AuthKeyStatus to delete(2).
         Index usage : the index is the Ip Address,Address Less Interface,Authentication.
         Note that entries will be presented to the SNMP manager in full
         lexicographical order :  sorted on Ip Address,Address Less Interface,Authentication."
    INDEX       { fsMIStdOspfContextId, fsMIOspfIfMD5AuthIpAddress, 
                  fsMIOspfIfMD5AuthAddressLessIf, fsMIOspfIfMD5AuthKeyId }
    ::= { fsMIOspfIfMD5AuthTable 1 }

FsMIOspfIfMD5AuthEntry ::= SEQUENCE {
    fsMIOspfIfMD5AuthIpAddress          IpAddress,
    fsMIOspfIfMD5AuthAddressLessIf      InterfaceIndex,
    fsMIOspfIfMD5AuthKeyId              INTEGER,
    fsMIOspfIfMD5AuthKey                OCTET STRING,
    fsMIOspfIfMD5AuthKeyStartAccept     INTEGER,
    fsMIOspfIfMD5AuthKeyStartGenerate   INTEGER,
    fsMIOspfIfMD5AuthKeyStopGenerate    INTEGER,
    fsMIOspfIfMD5AuthKeyStopAccept      INTEGER,
    fsMIOspfIfMD5AuthKeyStatus          INTEGER
}

fsMIOspfIfMD5AuthIpAddress OBJECT-TYPE
    SYNTAX      IpAddress
    ACCESS      not-accessible
    STATUS      mandatory
    DESCRIPTION 
        "The IP address of this OSPF interface.
         ALCATEL NOTE:
           ACCESS:      NA          USAGE:       NA
           PERSIST:     YES         INSRVMOD:    NA
           RANGE:       NA          DEFVALUE:    NA
           UNITS:       NA          SPARSE:      NO
           DESCR:       NA"
    ::= { fsMIOspfIfMD5AuthEntry 1 }

fsMIOspfIfMD5AuthAddressLessIf OBJECT-TYPE
    SYNTAX      InterfaceIndex (0..65535)
    ACCESS      not-accessible
    STATUS      mandatory
    DESCRIPTION 
        "For the purpose of easing  the  instancing  of
         addressed   and  addressless  interfaces;  This
         variable takes the value 0 on  interfaces  with
         IP  Addresses,  and  the corresponding value of
         ifIndex for interfaces having no IP Address.
         ALCATEL NOTE:
         ACCESS:      NA          USAGE:       NA
         PERSIST:     YES         INSRVMOD:    NA
         RANGE:       NA          DEFVALUE:    NA
         UNITS:       NA          SPARSE:      NO
         DESCR:       NA"
    ::= { fsMIOspfIfMD5AuthEntry 2 }

fsMIOspfIfMD5AuthKeyId OBJECT-TYPE
    SYNTAX      INTEGER (1..255)
    ACCESS      not-accessible
    STATUS      mandatory
    DESCRIPTION 
        " This object identifies the secret key used to create the 
         message digest appended to the OSPF packet.
         ALCATEL NOTE:
         ACCESS:      NA          USAGE:       NA
         PERSIST:     YES         INSRVMOD:    NA
         RANGE:       NA          DEFVALUE:    NA
         UNITS:       NA          SPARSE:      NO
         DESCR:       NA"
    ::= { fsMIOspfIfMD5AuthEntry 3 }

fsMIOspfIfMD5AuthKey OBJECT-TYPE
    SYNTAX      OCTET STRING (SIZE(0..16))
    ACCESS      read-write
    STATUS      mandatory
    DESCRIPTION 
        " This is the secret key which is used to create the 
         message digest appended to the OSPF packet.
         
         When read, fsMIOspfIfMD5AuthKey returns a maximum of 32  
         octets as an encrypted key.
         
          Note: The operator can enter a maximum of 16 octets
         as a MD5 key.
         
         ALCATEL NOTE:
         ACCESS:      NA          USAGE:       NA
         PERSIST:     YES         INSRVMOD:    YES
         RANGE:       NA          DEFVALUE:    '\0'
         UNITS:       NA          SPARSE:      NO
         DESCR:       NA"
    ::= { fsMIOspfIfMD5AuthEntry 4 }

fsMIOspfIfMD5AuthKeyStartAccept OBJECT-TYPE
    SYNTAX      INTEGER
    ACCESS      read-write
    STATUS      mandatory
    DESCRIPTION 
        " The absolute time in Seconds router will 
         start accepting packets that have been created with this key. The 
         value return is the time configured by the operator in Seconds.
         ALCATEL NOTE:
          ACCESS:      NA          USAGE:       NA
          PERSIST:     YES         INSRVMOD:    YES
          RANGE:       0..7fffffff DEFVALUE:    NA
          UNITS:       SECONDS     SPARSE:      NO
          DESCR:       NA"
    DEFVAL      { 0 }
    ::= { fsMIOspfIfMD5AuthEntry 5 }

fsMIOspfIfMD5AuthKeyStartGenerate OBJECT-TYPE
    SYNTAX      INTEGER
    ACCESS      read-write
    STATUS      mandatory
    DESCRIPTION 
        "The absolute time in Seconds the router will start using this 
         key for packets generation.The value return is the time configured
         by the operator in seconds.
         ALCATEL NOTE:
          ACCESS:      NA          USAGE:       NA
          PERSIST:     YES         INSRVMOD:    YES
          RANGE:       0..7fffffff DEFVALUE:    NA
          UNITS:       SECONDS     SPARSE:      NO
          DESCR:       NA"
    DEFVAL      { 0 }
    ::= { fsMIOspfIfMD5AuthEntry 6 }

fsMIOspfIfMD5AuthKeyStopGenerate OBJECT-TYPE
    SYNTAX      INTEGER
    ACCESS      read-write
    STATUS      mandatory
    DESCRIPTION 
        " The time (in relative format) the router will stop using this key 
         for  packets generation.  The value -1 indicates infinite lifetime.
         The value return is the duration(in seconds) from start time for which 
         the key is used to generate authentication.    
         
         
         ALCATEL NOTE:
          ACCESS:      NA          USAGE:       NA
          PERSIST:     YES         INSRVMOD:    YES
          RANGE:       -1..7fffffff DEFVALUE:    -1
          UNITS:       SECONDS     SPARSE:      NO
          DESCR:       NA"
    DEFVAL      { -1 }
    ::= { fsMIOspfIfMD5AuthEntry 7 }

fsMIOspfIfMD5AuthKeyStopAccept OBJECT-TYPE
    SYNTAX      INTEGER
    ACCESS      read-write
    STATUS      mandatory
    DESCRIPTION 
        " The time (in relative format) the router will stop accepting 
         packets that have been created with this key. The value -1 indicates
         infinite lifetime. The value return is the duration(in seconds) from 
         start time for which the key is used to verify authentication.
         ALCATEL NOTE:
          ACCESS:      NA          USAGE:       NA
          PERSIST:     YES         INSRVMOD:    YES
          RANGE:      -1..7fffffff DEFVALUE:    -1
          UNITS:       SECONDS     SPARSE:      NO
          DESCR:       NA"
    DEFVAL      { -1 }
    ::= { fsMIOspfIfMD5AuthEntry 8 }

fsMIOspfIfMD5AuthKeyStatus OBJECT-TYPE
    SYNTAX      INTEGER { valid(1), delete(3) }
    ACCESS      read-write
    STATUS      mandatory
    DESCRIPTION 
        " Identifies the status of the key. 
         NOTE:invalid (2) currently not supported
         ALCATEL NOTE:
         ACCESS:      NA          USAGE:       NA
         PERSIST:     YES         INSRVMOD:    YES
         RANGE:       NA          DEFVALUE:    1   
         UNITS:       NA          SPARSE:      NO
         DESCR:       NA"
    ::= { fsMIOspfIfMD5AuthEntry 9 }

fsMIOspfVirtIfMD5AuthTable OBJECT-TYPE
    SYNTAX      SEQUENCE OF FsMIOspfVirtIfMD5AuthEntry
    ACCESS      not-accessible
    STATUS      mandatory
    DESCRIPTION 
        "The OSPF Interface Authentication Table describes the parameters 
         required for MD5 cryptographic Authentication.
         ALCATEL NOTE:
         	TABLE SIZE:   NA
         	DESCR:        NA
         	   THIS TABLE IS NOT SUPPORTED BY ALCATEL."
--     REFERENCE   
--         "OSPF Version 2, Appendix D.3  Cryptographic Authentication"
    ::= { fsMIOspf 6 }

fsMIOspfVirtIfMD5AuthEntry OBJECT-TYPE
    SYNTAX      FsMIOspfVirtIfMD5AuthEntry
    ACCESS      not-accessible
    STATUS      mandatory
    DESCRIPTION 
        "The OSPF Interface MD5 Auththentication Entry describes one  
         Authentication Key from the viewpoint of OSPF.
         Row creation :    NA.
         Row deletion :    NA.
         Index usage :     NA
         lexicographical order :  NA.
         THIS IS NOT SUPPORTED BY ALCATEL."
    INDEX       { fsMIStdOspfContextId, fsMIOspfVirtIfMD5AuthAreaId, 
                  fsMIOspfVirtIfMD5AuthNeighbor, 
                  fsMIOspfVirtIfMD5AuthKeyId }
    ::= { fsMIOspfVirtIfMD5AuthTable 1 }

FsMIOspfVirtIfMD5AuthEntry ::= SEQUENCE {
    fsMIOspfVirtIfMD5AuthAreaId             AreaID,
    fsMIOspfVirtIfMD5AuthNeighbor           RouterID,
    fsMIOspfVirtIfMD5AuthKeyId              INTEGER,
    fsMIOspfVirtIfMD5AuthKey                OCTET STRING,
    fsMIOspfVirtIfMD5AuthKeyStartAccept     INTEGER,
    fsMIOspfVirtIfMD5AuthKeyStartGenerate   INTEGER,
    fsMIOspfVirtIfMD5AuthKeyStopGenerate    INTEGER,
    fsMIOspfVirtIfMD5AuthKeyStopAccept      INTEGER,
    fsMIOspfVirtIfMD5AuthKeyStatus          INTEGER
}

fsMIOspfVirtIfMD5AuthAreaId OBJECT-TYPE
    SYNTAX      AreaID
    ACCESS      not-accessible
    STATUS      mandatory
    DESCRIPTION 
        "  The  Transit  Area  that  the   Virtual   Link  
         traverses.  By definition, this should not be 0.0.0.0.
         ALCATEL NOTE:
         ACCESS:      NA          USAGE:       NA
         PERSIST:     NA          INSRVMOD:    NA
         RANGE:       NA          DEFVALUE:    NA
         UNITS:       NA          SPARSE:      NA
         DESCR:       THIS OBJECT IS NOT SUPPORTED BY ALCATEL."
    ::= { fsMIOspfVirtIfMD5AuthEntry 1 }

fsMIOspfVirtIfMD5AuthNeighbor OBJECT-TYPE
    SYNTAX      RouterID
    ACCESS      not-accessible
    STATUS      mandatory
    DESCRIPTION 
        " The Router ID of the Virtual Neighbor.
         ALCATEL NOTE:
           ACCESS:      NA          USAGE:       NA
           PERSIST:     NA          INSRVMOD:    NA
           RANGE:       NA          DEFVALUE:    NA
           UNITS:       NA          SPARSE:      NA
           DESCR:       THIS OBJECT IS NOT SUPPORTED BY ALCATEL."
    ::= { fsMIOspfVirtIfMD5AuthEntry 2 }

fsMIOspfVirtIfMD5AuthKeyId OBJECT-TYPE
    SYNTAX      INTEGER (1..65535)
    ACCESS      not-accessible
    STATUS      mandatory
    DESCRIPTION 
        " This object identifies the secret key used to create the 
         message digest appended to the OSPF packet.
         ALCATEL NOTE:
         ACCESS:      NA          USAGE:       NA
         PERSIST:     NA          INSRVMOD:    NA
         RANGE:       NA          DEFVALUE:    NA
         UNITS:       NA          SPARSE:      NA
         DESCR:       THIS OBJECT IS NOT SUPPORTED BY ALCATEL."
    ::= { fsMIOspfVirtIfMD5AuthEntry 3 }

fsMIOspfVirtIfMD5AuthKey OBJECT-TYPE
    SYNTAX      OCTET STRING (SIZE(0..16))
    ACCESS      read-write
    STATUS      mandatory
    DESCRIPTION 
        " This is the secret key which is used to create the 
         message digest appended to the OSPF packet.
         ALCATEL NOTE:
         ACCESS:      NA          USAGE:       NA
         PERSIST:     NA          INSRVMOD:    NA
         RANGE:       NA          DEFVALUE:    NA
         UNITS:       NA          SPARSE:      NA
         DESCR:       THIS OBJECT IS NOT SUPPORTED BY ALCATEL."
    ::= { fsMIOspfVirtIfMD5AuthEntry 4 }

fsMIOspfVirtIfMD5AuthKeyStartAccept OBJECT-TYPE
    SYNTAX      INTEGER
    ACCESS      read-write
    STATUS      mandatory
    DESCRIPTION 
        " The time the router will start accepting packets that have 
         been created with this key.The value shown will be configured
         time + system time at which the value is configured.
         ALCATEL NOTE:
         ACCESS:      NA          USAGE:       NA
         PERSIST:     NA          INSRVMOD:    NA
         RANGE:       NA          DEFVALUE:    NA
         UNITS:       NA          SPARSE:      NA
         DESCR:       THIS OBJECT IS NOT SUPPORTED BY ALCATEL."
    DEFVAL      { 0 }
    ::= { fsMIOspfVirtIfMD5AuthEntry 5 }

fsMIOspfVirtIfMD5AuthKeyStartGenerate OBJECT-TYPE
    SYNTAX      INTEGER
    ACCESS      read-write
    STATUS      mandatory
    DESCRIPTION 
        " The time the router will start using this key for  packet 
         generation.The value shown will be configured
         time + system time at which the value is configured.
         ALCATEL NOTE:
         ACCESS:      NA          USAGE:       NA
         PERSIST:     NA          INSRVMOD:    NA
         RANGE:       NA          DEFVALUE:    NA
         UNITS:       NA          SPARSE:      NA
         DESCR:       THIS OBJECT IS NOT SUPPORTED BY ALCATEL."
    DEFVAL      { 0 }
    ::= { fsMIOspfVirtIfMD5AuthEntry 6 }

fsMIOspfVirtIfMD5AuthKeyStopGenerate OBJECT-TYPE
    SYNTAX      INTEGER
    ACCESS      read-write
    STATUS      mandatory
    DESCRIPTION 
        "The time the router will stop using this key for  packets 
         generation. The value -1 indicates infinite lifetime.The value 
          shown will be configured time + system time at which the value is configured. 
         ALCATEL NOTE:
         ACCESS:      NA          USAGE:       NA
         PERSIST:     NA          INSRVMOD:    NA
         RANGE:       NA          DEFVALUE:    NA
         UNITS:       NA          SPARSE:      NA
         DESCR:       THIS OBJECT IS NOT SUPPORTED BY ALCATEL."
    DEFVAL      { -1 }
    ::= { fsMIOspfVirtIfMD5AuthEntry 7 }

fsMIOspfVirtIfMD5AuthKeyStopAccept OBJECT-TYPE
    SYNTAX      INTEGER
    ACCESS      read-write
    STATUS      mandatory
    DESCRIPTION 
        " The time the router will stop accepting packets that have 
         been created with this key. The value -1 indicates infinite 
          lifetime. The value shown will be configured
         time + system time at which the value is configured.
         ALCATEL NOTE:
         ACCESS:      NA          USAGE:       NA
         PERSIST:     NA          INSRVMOD:    NA
         RANGE:       NA          DEFVALUE:    NA
         UNITS:       NA          SPARSE:      NA
         DESCR:       THIS OBJECT IS NOT SUPPORTED BY ALCATEL."
    DEFVAL      { -1 }
    ::= { fsMIOspfVirtIfMD5AuthEntry 8 }

fsMIOspfVirtIfMD5AuthKeyStatus OBJECT-TYPE
    SYNTAX      INTEGER { valid(1), delete(3) }
    ACCESS      read-write
    STATUS      mandatory
    DESCRIPTION 
        " Identifies the status of the key. 
         NOTE: invalid (2) is currently not supported
         ALCATEL NOTE:
         ACCESS:      NA          USAGE:       NA
         PERSIST:     NA          INSRVMOD:    NA
         RANGE:       NA          DEFVALUE:    NA
         UNITS:       NA          SPARSE:      NA
         DESCR:       THIS OBJECT IS NOT SUPPORTED BY ALCATEL."
    ::= { fsMIOspfVirtIfMD5AuthEntry 9 }

fsMIOspfNbrTable OBJECT-TYPE
    SYNTAX      SEQUENCE OF FsMIOspfNbrEntry
    ACCESS      not-accessible
    STATUS      mandatory
    DESCRIPTION 
        "A table of non-virtual neighbor information.
         ALCATEL NOTE: 
         	TABLE SIZE:   DEP 
         	DESCR:	 DEP(TABLESIZE):The size of the table is derived from the 
         			object fsVrfNoOfOspfNeighbours in fsvrf.mib."
--     REFERENCE   
--         "OSPF Version 2, Section 10  The  Neighbor  Data
--          Structure"
    ::= { fsMIOspf 7 }

fsMIOspfNbrEntry OBJECT-TYPE
    SYNTAX      FsMIOspfNbrEntry
    ACCESS      not-accessible
    STATUS      mandatory
    DESCRIPTION 
        "The information regarding a single neighbor.
         Row creation : An entry shall be created in one step by a 
          set-request with all necessary parameter values and  
          ospfNbmaNbrStatus (ospfNbrTable) set to createAndGo(4).
         Row deletion : An entry shall be deleted by setting
          the ospfNbmaNbrStatus (ospfNbrTable) of the specific entry to destroy(6).
         Index usage : the index is the Ip Address,Address Less Index.
         Note that entries will be presented to the SNMP manager in full
         lexicographical order :  sorted on Ip Address,Address Less Index."
--     REFERENCE   
--         "OSPF Version 2, Section 10  The  Neighbor  Data
--          Structure"
    INDEX       { fsMIStdOspfContextId, fsMIOspfNbrIpAddr, 
                  fsMIOspfNbrAddressLessIndex }
    ::= { fsMIOspfNbrTable 1 }

FsMIOspfNbrEntry ::= SEQUENCE {
    fsMIOspfNbrIpAddr               IpAddress,
    fsMIOspfNbrAddressLessIndex     InterfaceIndex,
    fsMIOspfNbrDBSummaryQLen        Gauge,
    fsMIOspfNbrLSReqQLen            Gauge
}

fsMIOspfNbrIpAddr OBJECT-TYPE
    SYNTAX      IpAddress
    ACCESS      not-accessible
    STATUS      mandatory
    DESCRIPTION 
        " The IP address this neighbor is using  in  its
         IP  Source  Address.  Note that, on addressless
         links, this will not be 0.0.0.0,  but  the  ad-
         dress of another of the neighbor's interfaces.
         ALCATEL NOTE:
         ACCESS:      NA          USAGE:       NA
         PERSIST:     NO          INSRVMOD:    NA
         RANGE:       NA          DEFVALUE:    NA
         UNITS:       NA          SPARSE:      NO
         DESCR:       NA"
    ::= { fsMIOspfNbrEntry 1 }

fsMIOspfNbrAddressLessIndex OBJECT-TYPE
    SYNTAX      InterfaceIndex (0..65535)
    ACCESS      not-accessible
    STATUS      mandatory
    DESCRIPTION 
        "  On an interface having an  IP  Address,  zero.
         On  addressless  interfaces,  the corresponding
         value of ifIndex in the Internet Standard  MIB.
         On  row  creation, this can be derived from the
         instance.
         ALCATEL NOTE:
         ACCESS:      NA          USAGE:       NA
         PERSIST:     NO          INSRVMOD:    NA
         RANGE:       NA          DEFVALUE:    NA
         UNITS:       NA          SPARSE:      NO
         DESCR:       NA"
    ::= { fsMIOspfNbrEntry 2 }

fsMIOspfNbrDBSummaryQLen OBJECT-TYPE
    SYNTAX      Gauge
    ACCESS      read-only
    STATUS      mandatory
    DESCRIPTION 
        " This gives the Que Length of the Database summary List .
         ALCATEL NOTE:
           ACCESS:      NA          USAGE:       NA
           PERSIST:     NO          INSRVMOD:    NA
           RANGE:       NA          DEFVALUE:    0
           UNITS:       NA          SPARSE:      NO
           DESCR:       NA"
    ::= { fsMIOspfNbrEntry 3 }

fsMIOspfNbrLSReqQLen OBJECT-TYPE
    SYNTAX      Gauge
    ACCESS      read-only
    STATUS      mandatory
    DESCRIPTION 
        " This gives the Length of Link State Request Que .
         ALCATEL NOTE:
           ACCESS:      NA          USAGE:       NA
           PERSIST:     NO          INSRVMOD:    NA
           RANGE:       NA          DEFVALUE:    0
           UNITS:       NA          SPARSE:      NO
           DESCR:       NA"
    ::= { fsMIOspfNbrEntry 4 }

fsMIOspfRoutingTable OBJECT-TYPE
    SYNTAX      SEQUENCE OF FsMIOspfRoutingEntry
    ACCESS      not-accessible
    STATUS      mandatory
    DESCRIPTION 
        "A table of routing information.
         ALCATEL NOTE: 
         	TABLE SIZE:   DEP
         	DESCR:	 DEP(TABLESIZE):The size of the table is derived from the 
         			object fsVrfNoOfOspfRTSize in fsvrf.mib."
    ::= { fsMIOspf 8 }

fsMIOspfRoutingEntry OBJECT-TYPE
    SYNTAX      FsMIOspfRoutingEntry
    ACCESS      not-accessible
    STATUS      mandatory
    DESCRIPTION 
        "The information regarding a single route.
         Row creation : An entry shall be created when the system comes up.  
         Row deletion : An entry shall be deleted when the system shuts down.
         Index usage : the index is the Ip Address,Ip Address Mask,Route Ip Type Of Service,Route Ip Next Hop.
         Note that entries will be presented to the SNMP manager in full
         lexicographical order :  sorted on Ip Address,Ip Address Mask,Route Ip Type Of Service,Route Ip Next Hop."
    INDEX       { fsMIStdOspfContextId, fsMIOspfRouteIpAddr, 
                  fsMIOspfRouteIpAddrMask, fsMIOspfRouteIpTos, 
                  fsMIOspfRouteIpNextHop }
    ::= { fsMIOspfRoutingTable 1 }

FsMIOspfRoutingEntry ::= SEQUENCE {
    fsMIOspfRouteIpAddr             IpAddress,
    fsMIOspfRouteIpAddrMask         IpAddress,
    fsMIOspfRouteIpTos              TOSType,
    fsMIOspfRouteIpNextHop          IpAddress,
    fsMIOspfRouteType               INTEGER,
    fsMIOspfRouteAreaId             IpAddress,
    fsMIOspfRouteCost               BigMetric,
    fsMIOspfRouteType2Cost          BigMetric,
    fsMIOspfRouteInterfaceIndex     InterfaceIndex
}

fsMIOspfRouteIpAddr OBJECT-TYPE
    SYNTAX      IpAddress
    ACCESS      not-accessible
    STATUS      mandatory
    DESCRIPTION 
        " IP Address of the route
         ALCATEL NOTE:
           ACCESS:      NA          USAGE:       NA
           PERSIST:     NO          INSRVMOD:    NA
           RANGE:       NA          DEFVALUE:    NA
           UNITS:       NA          SPARSE:      NO
           DESCR:       NA"
    ::= { fsMIOspfRoutingEntry 1 }

fsMIOspfRouteIpAddrMask OBJECT-TYPE
    SYNTAX      IpAddress
    ACCESS      not-accessible
    STATUS      mandatory
    DESCRIPTION 
        " IP Address Mask of the route
         ALCATEL NOTE:
           ACCESS:      NA          USAGE:       NA
           PERSIST:     NO          INSRVMOD:    NA
           RANGE:       NA          DEFVALUE:    NA
           UNITS:       NA          SPARSE:      NO
           DESCR:       NA"
    ::= { fsMIOspfRoutingEntry 2 }

fsMIOspfRouteIpTos OBJECT-TYPE
    SYNTAX      TOSType
    ACCESS      not-accessible
    STATUS      mandatory
    DESCRIPTION 
        " IP TOS of the route
         ALCATEL NOTE:
           ACCESS:      NA                    USAGE:       NA
           PERSIST:     NO                    INSRVMOD:    NA
           RANGE:       1,2,3,5,7,9,11..31    DEFVALUE:    NA    
           UNITS:       NA                    SPARSE:      NO
           DESCR:       NA"
    ::= { fsMIOspfRoutingEntry 3 }

fsMIOspfRouteIpNextHop OBJECT-TYPE
    SYNTAX      IpAddress
    ACCESS      not-accessible
    STATUS      mandatory
    DESCRIPTION 
        " IP Next Hop of the route
         ALCATEL NOTE:
           ACCESS:      NA          USAGE:       NA
           PERSIST:     NO          INSRVMOD:    NA
           RANGE:       NA          DEFVALUE:    NA
           UNITS:       NA          SPARSE:      NO
           DESCR:       NA"
    ::= { fsMIOspfRoutingEntry 4 }

fsMIOspfRouteType OBJECT-TYPE
    SYNTAX      INTEGER { intraArea(1), interArea(2), type1External(3), 
                    type2External(4) }
    ACCESS      read-only
    STATUS      mandatory
    DESCRIPTION 
        "Type of the route
         ALCATEL NOTE:
           ACCESS:      NA          USAGE:       NA
           PERSIST:     NO          INSRVMOD:    NA
           RANGE:       NA          DEFVALUE:    1    
           UNITS:       NA          SPARSE:      NO
           DESCR:       NA"
    ::= { fsMIOspfRoutingEntry 5 }

fsMIOspfRouteAreaId OBJECT-TYPE
    SYNTAX      IpAddress
    ACCESS      read-only
    STATUS      mandatory
    DESCRIPTION 
        " Area ID associated with the route
         ALCATEL NOTE:
           ACCESS:      NA          USAGE:       NA
           PERSIST:     NO          INSRVMOD:    NA
           RANGE:       NA          DEFVALUE:    NA
           UNITS:       NA          SPARSE:      NO
           DESCR:       NA"
    ::= { fsMIOspfRoutingEntry 6 }

fsMIOspfRouteCost OBJECT-TYPE
    SYNTAX      BigMetric
    ACCESS      read-only
    STATUS      mandatory
    DESCRIPTION 
        " It is a Type 1 external metrics which is 
         expressed in the same units as OSPF interface
         cost ie. in terms of the OSPF link state metric. 
         If Type1 and Type2 cost are present, Type1 external
         metrics always take precedence
         ALCATEL NOTE:
         ACCESS:      NA           USAGE:       NA
         PERSIST:     NO           INSRVMOD:    NA
         RANGE:       0..16777215  DEFVALUE:    NA    
         UNITS:       NA           SPARSE:      NO
         DESCR:       NA"
    ::= { fsMIOspfRoutingEntry 7 }

fsMIOspfRouteType2Cost OBJECT-TYPE
    SYNTAX      BigMetric
    ACCESS      read-only
    STATUS      mandatory
    DESCRIPTION 
        " Type 2 external metrics are configured with  
         the cost greater than any path internal to the AS. 
         Use of Type 2 external metrics assumes that routing 
         between AS is the major cost of routing a packet, and
         eliminates the need for conversion of external costs to
         internal link state metrics
         ALCATEL NOTE:
         ACCESS:      NA           USAGE:       NA
         PERSIST:     NO           INSRVMOD:    NA
         RANGE:       0..16777215  DEFVALUE:    0    
         UNITS:       NA           SPARSE:      NO
         DESCR:       NA"
    ::= { fsMIOspfRoutingEntry 8 }

fsMIOspfRouteInterfaceIndex OBJECT-TYPE
    SYNTAX      InterfaceIndex
    ACCESS      read-only
    STATUS      mandatory
    DESCRIPTION 
        " Interface Index associated with the route
         ALCATEL NOTE:
           ACCESS:      NA           USAGE:       NA
            PERSIST:     NO           INSRVMOD:    NA
           RANGE:       DEP      DEFVALUE:    NA    
           UNITS:       NA           SPARSE:      NO
           DESCR:       DEP(RANGE): The range is from (maximum value of number of physical interfaces available in the system + 1) 
         			to (the total number of IP interfaces in the system  + 
         			maximum value of number of physical interfaces available in the system). 
         			The maximum number of physical interfaces is obtained from the object issSystemNumberOfPorts in fsiss.mib. 
         			The total number of IP interfaces in the system is obtained from the object fsVrfMaxIpInterfaces in fsvrf.mib"
    ::= { fsMIOspfRoutingEntry 9 }

fsMIOspfSecIfTable OBJECT-TYPE
    SYNTAX      SEQUENCE OF FsMIOspfSecIfEntry
    ACCESS      not-accessible
    STATUS      mandatory
    DESCRIPTION 
        "A table of Secondary IP Address information
         ALCATEL NOTE: 
         	TABLE SIZE:   36
         	DESCR:        NA"
    ::= { fsMIOspf 9 }

fsMIOspfSecIfEntry OBJECT-TYPE
    SYNTAX      FsMIOspfSecIfEntry
    ACCESS      not-accessible
    STATUS      mandatory
    DESCRIPTION 
        "The information regarding a single route.
         Row creation : An entry shall be created in one step by a 
          set-request with all necessary parameter values and  
           futOspfSecIfStatus set to createAndGo(4).
         Row deletion : An entry shall be deleted by setting
          the  futOspfSecIfStatus of the specific entry to destroy(6).
         Index usage : the index is the Ip Address,Address Less Interface,Secondary Ip Address,Secondary Ip Address Mask.
         Note that entries will be presented to the SNMP manager in full
         lexicographical order :  sorted on Ip Address,Address Less Interface,Secondary Ip Address,Secondary Ip Address Mask."
    INDEX       { fsMIStdOspfContextId, fsMIOspfPrimIpAddr, 
                  fsMIOspfPrimAddresslessIf, fsMIOspfSecIpAddr, 
                  fsMIOspfSecIpAddrMask }
    ::= { fsMIOspfSecIfTable 1 }

FsMIOspfSecIfEntry ::= SEQUENCE {
    fsMIOspfPrimIpAddr          IpAddress,
    fsMIOspfPrimAddresslessIf   InterfaceIndex,
    fsMIOspfSecIpAddr           IpAddress,
    fsMIOspfSecIpAddrMask       IpAddress,
    fsMIOspfSecIfStatus         RowStatus
}

fsMIOspfPrimIpAddr OBJECT-TYPE
    SYNTAX      IpAddress
    ACCESS      not-accessible
    STATUS      mandatory
    DESCRIPTION 
        " Primary Interface IP Address
         ALCATEL NOTE:
           ACCESS:      NA          USAGE:       NA
           PERSIST:     YES         INSRVMOD:    NA
           RANGE:       NA          DEFVALUE:    NA
           UNITS:       NA          SPARSE:      NO
           DESCR:       NA"
    ::= { fsMIOspfSecIfEntry 1 }

fsMIOspfPrimAddresslessIf OBJECT-TYPE
    SYNTAX      InterfaceIndex (0..65535)
    ACCESS      not-accessible
    STATUS      mandatory
    DESCRIPTION 
        " Primary Interface Addressless Index.
         ALCATEL NOTE:
           ACCESS:      NA          USAGE:       NA
           PERSIST:     YES         INSRVMOD:    NA
           RANGE:       NA          DEFVALUE:    NA
           UNITS:       NA          SPARSE:      NO
           DESCR:       NA"
    ::= { fsMIOspfSecIfEntry 2 }

fsMIOspfSecIpAddr OBJECT-TYPE
    SYNTAX      IpAddress
    ACCESS      not-accessible
    STATUS      mandatory
    DESCRIPTION 
        " Secondary Interface IP Address.
         ALCATEL NOTE:
           ACCESS:      NA          USAGE:       NA
           PERSIST:     YES         INSRVMOD:    NA
           RANGE:       NA          DEFVALUE:    NA
           UNITS:       NA          SPARSE:      NO
           DESCR:       NA"
    ::= { fsMIOspfSecIfEntry 3 }

fsMIOspfSecIpAddrMask OBJECT-TYPE
    SYNTAX      IpAddress
    ACCESS      not-accessible
    STATUS      mandatory
    DESCRIPTION 
        " Secondary Interface IP Address Mask.
         ALCATEL NOTE:
           ACCESS:      NA          USAGE:       NA
           PERSIST:     YES         INSRVMOD:    NA
           RANGE:       NA          DEFVALUE:    NA
           UNITS:       NA          SPARSE:      NO
           DESCR:       NA"
    ::= { fsMIOspfSecIfEntry 4 }

fsMIOspfSecIfStatus OBJECT-TYPE
    SYNTAX      RowStatus
    ACCESS      read-write
    STATUS      mandatory
    DESCRIPTION 
        " This variable displays the status of  the  entry.  
         Setting it to 'invalid' has the effect of
         rendering it inoperative.  The internal  effect
         (row removal) is implementation dependent.
         ALCATEL NOTE:
         ACCESS:      NA          USAGE:       MAND
         PERSIST:     YES         INSRVMOD:    YES
         RANGE:       1,4,5,6     DEFVALUE:    NA
         UNITS:       NA          SPARSE:      NO
         DESCR:       NA"
    ::= { fsMIOspfSecIfEntry 5 }

fsMIOspfAreaAggregateTable OBJECT-TYPE
    SYNTAX      SEQUENCE OF FsMIOspfAreaAggregateEntry
    ACCESS      not-accessible
    STATUS      mandatory
    DESCRIPTION 
        "Supports configuration of External Tag for
         Type-7 Address ranges configured.
         ALCATEL NOTE: 
         	TABLE SIZE:   DEP
         	DESCR:        The table size is derived from the mib object
         dimensioning parameter. The maximum value is 768"
    ::= { fsMIOspf 10 }

fsMIOspfAreaAggregateEntry OBJECT-TYPE
    SYNTAX      FsMIOspfAreaAggregateEntry
    ACCESS      not-accessible
    STATUS      mandatory
    DESCRIPTION 
        "Supports configuration of External Tag for
         Type-7 Address ranges configured.
         Row creation : An entry shall be created in one step by a 
         set-request with all necessary parameter values and  
         ospfAreaAggregateStatus (ospfAreaAggregateTable) set to createAndGo(4).
         Row deletion : An entry shall be deleted by setting
         the ospfAreaAggregateStatus (ospfAreaAggregateTable) of the specific entry to destroy(6).
         Index usage : the index is the Area Id,Link State type,Area Aggregate net,Area Aggregate Mask.
         Note that entries will be presented to the SNMP manager in full
         lexicographical order :  sorted on Area Id,Link State type,Area Aggregate net,Area Aggregate Mask."
    INDEX       { fsMIStdOspfContextId, fsMIOspfAreaAggregateAreaID, 
                  fsMIOspfAreaAggregateLsdbType, 
                  fsMIOspfAreaAggregateNet, fsMIOspfAreaAggregateMask }
    ::= { fsMIOspfAreaAggregateTable 1 }

FsMIOspfAreaAggregateEntry ::= SEQUENCE {
    fsMIOspfAreaAggregateAreaID         AreaID,
    fsMIOspfAreaAggregateLsdbType       INTEGER,
    fsMIOspfAreaAggregateNet            IpAddress,
    fsMIOspfAreaAggregateMask           IpAddress,
    fsMIOspfAreaAggregateExternalTag    INTEGER
}

fsMIOspfAreaAggregateAreaID OBJECT-TYPE
    SYNTAX      AreaID
    ACCESS      not-accessible
    STATUS      mandatory
    DESCRIPTION 
        "The Area the Address Aggregate is to be  found
         within
         ALCATEL NOTE:
         ACCESS:      NA          USAGE:       NA
         PERSIST:     YES         INSRVMOD:    NA
         RANGE:       NA          DEFVALUE:    NA
         UNITS:       NA          SPARSE:      NO
         DESCR:       NA"
--     REFERENCE   
--         "OSPF Version 2, Appendix C.2 Area parameters"
    ::= { fsMIOspfAreaAggregateEntry 1 }

fsMIOspfAreaAggregateLsdbType OBJECT-TYPE
    SYNTAX      INTEGER { summaryLink(3), nssaExternalLink(7) }
    ACCESS      not-accessible
    STATUS      mandatory
    DESCRIPTION 
        "The type of the Address Aggregate.  This field
         specifies  the  Lsdb type that this Address Ag-
         gregate applies to.
         ALCATEL NOTE:
         ACCESS:      NA          USAGE:       NA
         PERSIST:     YES         INSRVMOD:    NA
         RANGE:       NA          DEFVALUE:    3     
         UNITS:       NA          SPARSE:      NO
         DESCR:       NA"
--     REFERENCE   
--         "OSPF Version 2, Appendix A.4.1 The  Link  State
--          Advertisement header"
    ::= { fsMIOspfAreaAggregateEntry 2 }

fsMIOspfAreaAggregateNet OBJECT-TYPE
    SYNTAX      IpAddress
    ACCESS      not-accessible
    STATUS      mandatory
    DESCRIPTION 
        "The IP Address of the Net or Subnet  indicated
         by the range.
         ALCATEL NOTE:
         ACCESS:      NA          USAGE:       NA
         PERSIST:     YES         INSRVMOD:    NA
         RANGE:       NA          DEFVALUE:    NA
         UNITS:       NA          SPARSE:      NO
         DESCR:       NA"
--     REFERENCE   
--         "OSPF Version 2, Appendix C.2 Area parameters"
    ::= { fsMIOspfAreaAggregateEntry 3 }

fsMIOspfAreaAggregateMask OBJECT-TYPE
    SYNTAX      IpAddress
    ACCESS      not-accessible
    STATUS      mandatory
    DESCRIPTION 
        "The Subnet Mask that pertains to  the  Net  or
         Subnet.
         ALCATEL NOTE:
         ACCESS:      NA          USAGE:       NA
         PERSIST:     YES         INSRVMOD:    NA
         RANGE:       NA          DEFVALUE:    NA
         UNITS:       NA          SPARSE:      NO
         DESCR:       NA"
--     REFERENCE   
--         "OSPF Version 2, Appendix C.2 Area parameters"
    ::= { fsMIOspfAreaAggregateEntry 4 }

fsMIOspfAreaAggregateExternalTag OBJECT-TYPE
    SYNTAX      INTEGER
    ACCESS      read-write
    STATUS      mandatory
    DESCRIPTION 
        "A 32-bit field attached to each external route.
         This is not used by OSPF protocol itself. It may
         be used to communicate information between AS 
         boundary routers. The precise nature of this information
         is outside the scope of OSPF. 
         ALCATEL NOTE:
         ACCESS:      NA             USAGE:       NA
         PERSIST:     YES            INSRVMOD:    YES
         RANGE:       0..2147483647  DEFVALUE:    0    
         UNITS:       NA             SPARSE:      NO
         DESCR:       NA"
    ::= { fsMIOspfAreaAggregateEntry 5 }

fsMIOspfAsExternalAggregationTable OBJECT-TYPE
    SYNTAX      SEQUENCE OF FsMIOspfAsExternalAggregationEntry
    ACCESS      not-accessible
    STATUS      mandatory
    DESCRIPTION 
        "Indicates whether for the specified address range
         Type-7/Type-5 LSA will be aggregated or not generated. 
         ALCATEL NOTE: 
         	TABLE SIZE:   200
         	DESCR:        NA"
    ::= { fsMIOspf 11 }

fsMIOspfAsExternalAggregationEntry OBJECT-TYPE
    SYNTAX      FsMIOspfAsExternalAggregationEntry
    ACCESS      not-accessible
    STATUS      mandatory
    DESCRIPTION 
        "Supports configuration of Type-5,Type-7 Address Range specifying
         whether for the configured range, Type-5,Type-7 LSA will be 
         generated or not, and if generated whether aggregation is performed.
         Row creation : An entry shall be created in one step by a 
         set-request with all necessary parameter values and  
         futOspfAsExternalAggregationStatus set to createAndGo(4).
         Row deletion : An entry shall be deleted by setting
         the futOspfAsExternalAggregationStatus of the specific entry to destroy(6).
         Index usage : the index is the Area Id,Link State type,Area Aggregate net,Area Aggregate Mask.
         Note that entries will be presented to the SNMP manager in full
         lexicographical order :  sorted on Area Id,Link State type,Area Aggregate net,Area Aggregate Mask."
    INDEX       { fsMIStdOspfContextId, fsMIOspfAsExternalAggregationNet, 
                  fsMIOspfAsExternalAggregationMask, 
                  fsMIOspfAsExternalAggregationAreaId }
    ::= { fsMIOspfAsExternalAggregationTable 1 }

FsMIOspfAsExternalAggregationEntry ::= SEQUENCE {
    fsMIOspfAsExternalAggregationNet            IpAddress,
    fsMIOspfAsExternalAggregationMask           IpAddress,
    fsMIOspfAsExternalAggregationAreaId         AreaID,
    fsMIOspfAsExternalAggregationEffect         INTEGER,
    fsMIOspfAsExternalAggregationTranslation    INTEGER,
    fsMIOspfAsExternalAggregationStatus         RowStatus
}

fsMIOspfAsExternalAggregationNet OBJECT-TYPE
    SYNTAX      IpAddress
    ACCESS      not-accessible
    STATUS      mandatory
    DESCRIPTION 
        "The IP address of the Net indicated by 
         the range.
         ALCATEL NOTE:
         ACCESS:      NA          USAGE:       NA
         PERSIST:     YES         INSRVMOD:    NA
         RANGE:       NA          DEFVALUE:    NA
         UNITS:       NA          SPARSE:      NO
         DESCR:       NA"
    ::= { fsMIOspfAsExternalAggregationEntry 1 }

fsMIOspfAsExternalAggregationMask OBJECT-TYPE
    SYNTAX      IpAddress
    ACCESS      not-accessible
    STATUS      mandatory
    DESCRIPTION 
        "The subnet mask that pertains to the 
         range.
         ALCATEL NOTE:
         ACCESS:      NA          USAGE:       NA
         PERSIST:     YES         INSRVMOD:    NA
         RANGE:       NA          DEFVALUE:    NA
         UNITS:       NA          SPARSE:      NO
         DESCR:       NA"
    ::= { fsMIOspfAsExternalAggregationEntry 2 }

fsMIOspfAsExternalAggregationAreaId OBJECT-TYPE
    SYNTAX      AreaID
    ACCESS      not-accessible
    STATUS      mandatory
    DESCRIPTION 
        "Refer to description in fsMIOspfAsExternalAggregationEffect.
         ALCATEL NOTE:
              ACCESS:      NA          USAGE:       NA
              PERSIST:     YES         INSRVMOD:    NA
              RANGE:       NA          DEFVALUE:    NA
              UNITS:       NA          SPARSE:      NO
              DESCR:       NA"
    ::= { fsMIOspfAsExternalAggregationEntry 3 }

fsMIOspfAsExternalAggregationEffect OBJECT-TYPE
    SYNTAX      INTEGER { advertise(1), doNotAdvertise(2), allowAll(3), 
                    denyAll(4) }
    ACCESS      read-write
    STATUS      mandatory
    DESCRIPTION 
        "Indicates whether Type-5/Type-7 will be aggregated or not
         generated for the specified range. 
         When set to allowAll (3) and associated areaId is 0.0.0.0
         aggregated Type-5 are generated for the specified range. In
         addition aggregated Type-7 are generated in all attached NSSA
         areas, for the specified range.Value allowAll (3) is not valid
         for areaId other than 0.0.0.0 
         When set to denyAll (4) neither Type-5 nor Type-7 will be
         generated for the specified range. Value denyAll (4) is not
         valid for areaID other than 0.0.0.0
         When set to advertise (1) and associated areaId is 0.0.0.0,
         aggregated Type-5 are generated.Otherwise if associated areaId
         is x.x.x.x(other than 0.0.0.0) aggregated Type-7 is generated
         in NSSA area x.x.x.x
         When set to doNotAdvertise (2) and associated areaId is 0.0.0.0,
         Type-5 is not generated for the specified range, while aggregated
         Type-7 are generated in all attached NSSA areas.While if associated
         areaId is x.x.x.x(other than 0.0.0.0), Type-7 are not generated in
         NSSA area x.x.x.x for the specified range.
         ALCATEL NOTE:
         ACCESS:      NA          USAGE:       OPT
         PERSIST:     YES         INSRVMOD:    YES
         RANGE:       NA          DEFVALUE:    NA
         UNITS:       NA          SPARSE:      NO
         DESCR:       NA"
    DEFVAL      { advertise }
    ::= { fsMIOspfAsExternalAggregationEntry 4 }

fsMIOspfAsExternalAggregationTranslation OBJECT-TYPE
    SYNTAX      INTEGER { enabled(1), disabled(2) }
    ACCESS      read-write
    STATUS      mandatory
    DESCRIPTION 
        "This when set to enabled, P Bit is set in
         the generated Type-7 LSA. When set disabled
         P Bit is clear in the generated Type-7 LSA
         for the range.
         ALCATEL NOTE:
         ACCESS:      NA          USAGE:       OPT
         PERSIST:     YES         INSRVMOD:    YES
         RANGE:       NA          DEFVALUE:    NA
         UNITS:       NA          SPARSE:      NO
         DESCR:       NA"
    DEFVAL      { enabled }
    ::= { fsMIOspfAsExternalAggregationEntry 5 }

fsMIOspfAsExternalAggregationStatus OBJECT-TYPE
    SYNTAX      RowStatus
    ACCESS      read-write
    STATUS      mandatory
    DESCRIPTION 
        "This variable displays the status of  the  en-
         try.  Setting it to 'invalid' has the effect of
         rendering it inoperative.
         ALCATEL NOTE:
          ACCESS:      NA          USAGE:       MAND
          PERSIST:     YES         INSRVMOD:    YES
          RANGE:       1,2,4,5,6   DEFVALUE:    NA
          UNITS:       NA          SPARSE:      N0
          DESCR:       NA"
    ::= { fsMIOspfAsExternalAggregationEntry 6 }

fsMIOspfOpaqueLSAGroup OBJECT IDENTIFIER
    ::= { fsMIOspf 12 }

fsMIOspfOpaqueLSAGeneralGroup OBJECT IDENTIFIER
    ::= { fsMIOspfOpaqueLSAGroup 1 }

fsMIOspfOpaqueTable OBJECT-TYPE
    SYNTAX      SEQUENCE OF FsMIOspfOpaqueEntry
    ACCESS      not-accessible
    STATUS      mandatory
    DESCRIPTION 
        "Information describing the count and check the type 11LSAs. 
         ALCATEL NOTE:
         	TABLE SIZE:    64
         	DESCR:         NA"
    ::= { fsMIOspfOpaqueLSAGeneralGroup 1 }

fsMIOspfOpaqueEntry OBJECT-TYPE
    SYNTAX      FsMIOspfOpaqueEntry
    ACCESS      not-accessible
    STATUS      mandatory
    DESCRIPTION 
        " Information describing the type 11 LSAs Count and checksum .
         Row creation : An entry will be created by the system when an entry
             		is created in the fsMIStdOspfTable.
         Row deletion : An entry will be deleted by the system when an entry
             		is deleted in the fsMIStdOspfTable.
         Index usage : the index is fsMIStdOspfEntry.
           Note that entries will be presented to the SNMP manager in full
           lexicographical order :  sorted on fsMIStdOspfEntry."
    INDEX       { fsMIStdOspfContextId }
--     AUGMENTS    { fsMIStdOspfEntry }
    ::= { fsMIOspfOpaqueTable 1 }

FsMIOspfOpaqueEntry ::= SEQUENCE {
    fsMIOspfOpaqueOption        INTEGER,
    fsMIOspfType11LsaCount      Gauge,
    fsMIOspfType11LsaCksumSum   INTEGER,
    fsMIOspfAreaIDValid         TruthValue
}

fsMIOspfOpaqueOption OBJECT-TYPE
    SYNTAX      INTEGER { enabled(1), disabled(2) }
    ACCESS      read-write
    STATUS      mandatory
    DESCRIPTION 
        "Indicates whether router is Opaque-Capable or not
         ALCATEL NOTE:
           ACCESS:      NA          USAGE:       NA
           PERSIST:     NO          INSRVMOD:    YES
           RANGE:       NA          DEFVALUE:    NA
           UNITS:       NA          SPARSE:      NA
           DESCR:       NA"
--     REFERENCE   
--         "The Opaque LSA Option ,Section 5.0 Management Considerations"
    DEFVAL      { disabled }
    ::= { fsMIOspfOpaqueEntry 1 }

fsMIOspfType11LsaCount OBJECT-TYPE
    SYNTAX      Gauge
    ACCESS      read-only
    STATUS      mandatory
    DESCRIPTION 
        "The number of  LS type 11  link-state
         advertisements in the link-state database.
         ALCATEL NOTE:
          ACCESS:      NA          USAGE:       NA
          PERSIST:     NO          INSRVMOD:    NA
          RANGE:       NA          DEFVALUE:    0
          UNITS:       NA          SPARSE:      NA
          DESCR:       NA"
--     REFERENCE   
--         "The Opaque LSA Option, Section 5.0 Management Considerations"
    ::= { fsMIOspfOpaqueEntry 2 }

fsMIOspfType11LsaCksumSum OBJECT-TYPE
    SYNTAX      INTEGER
    ACCESS      read-only
    STATUS      mandatory
    DESCRIPTION 
        "The 32-bit unsigned sum of the LS checksums of
         the  Type 11  link-state  advertisements  con-
         tained in the link-state  database.   This  sum
         can  be  used  to determine if there has been a
         change in a router's link state  database,  and
         to  compare  the  link-state  database  of  two
         routers.
         ALCATEL NOTE:
         ACCESS:      NA          USAGE:       NA
         PERSIST:     NO          INSRVMOD:    NA
         RANGE:       NA          DEFVALUE:    0
         UNITS:       NA          SPARSE:      NA
         DESCR:       NA"
    ::= { fsMIOspfOpaqueEntry 3 }

fsMIOspfAreaIDValid OBJECT-TYPE
    SYNTAX      TruthValue
    ACCESS      read-write
    STATUS      mandatory
    DESCRIPTION 
        "Indicates whether an application is expected to provide 
         the AreaId, while generating a type-10 opaque LSA. This value
         will be true if an application can provide the AreaId otherwise
         false. In case of false the Opaque module will determine the
         associated area for a Type-10 LSA based on the interface to which
         the LSA is associated.
         ALCATEL NOTE:
         ACCESS:      NA          USAGE:       NA
         PERSIST:     NO          INSRVMOD:    NA
         RANGE:       1           DEFVALUE:    1
         UNITS:       NA          SPARSE:      NA
         DESCR:       NA"
    DEFVAL      { false }
    ::= { fsMIOspfOpaqueEntry 4 }

fsMIOspfOpaqueInterfaceTable OBJECT-TYPE
    SYNTAX      SEQUENCE OF FsMIOspfOpaqueInterfaceEntry
    ACCESS      not-accessible
    STATUS      mandatory
    DESCRIPTION 
        "Information describing the count and checksum of the Type9 LSAs.
         ALCATEL NOTE: 
         		TABLE SIZE:   18
         		DESCR:        NA"
--     REFERENCE   
--         "The Opaque LSA Option , Section 5.0 Management Considerations"
    ::= { fsMIOspfOpaqueLSAGroup 2 }

fsMIOspfOpaqueInterfaceEntry OBJECT-TYPE
    SYNTAX      FsMIOspfOpaqueInterfaceEntry
    ACCESS      not-accessible
    STATUS      mandatory
    DESCRIPTION 
        "Information describing the Type 9 LSAs Count and Checksums.
         Row creation : An entry shall be created in one step by a 
          set-request with all necessary parameter values and  
          ospfIfStatus (ospfIfTable) set to createAndGo(4).
         Row deletion : An entry shall be deleted by setting
          the ospfIfStatus (ospfIfTable) of the specific entry to destroy(6).
         Index usage : the index is the Ip Address,Address Less Interface.
         Note that entries will be presented to the SNMP manager in full
         lexicographical order :  sorted on Ip Address,Address Less Interface."
    INDEX       { fsMIStdOspfContextId, fsMIOspfIfIpAddress, 
                  fsMIOspfAddressLessIf }
--     AUGMENTS    { fsMIOspfIfEntry }
    ::= { fsMIOspfOpaqueInterfaceTable 1 }

FsMIOspfOpaqueInterfaceEntry ::= SEQUENCE {
    fsMIOspfOpaqueType9LsaCount     Gauge,
    fsMIOspfOpaqueType9LsaCksumSum  INTEGER
}

fsMIOspfOpaqueType9LsaCount OBJECT-TYPE
    SYNTAX      Gauge
    ACCESS      read-only
    STATUS      mandatory
    DESCRIPTION 
        "The total number of TYPE 9 Opaque link-state advertisements.
         ALCATEL NOTE:
           ACCESS:      NA          USAGE:       NA
           PERSIST:     NO          INSRVMOD:    NA
           RANGE:       NA          DEFVALUE:    0
           UNITS:       NA          SPARSE:      NO
           DESCR:       NA"
    ::= { fsMIOspfOpaqueInterfaceEntry 1 }

fsMIOspfOpaqueType9LsaCksumSum OBJECT-TYPE
    SYNTAX      INTEGER
    ACCESS      read-only
    STATUS      mandatory
    DESCRIPTION 
        "The 32-bit unsigned sum of the link-state ad-
         vertisements' TYPE9 Opaque LS checksums.The sum
         change in a router's link state data-base, and
         to compare the link-state database of the two
         routers.
         ALCATEL NOTE:
         ACCESS:      NA          USAGE:       NA
         PERSIST:     NO          INSRVMOD:    NA
         RANGE:       NA          DEFVALUE:    NA
         UNITS:       NA          SPARSE:      NO
         DESCR:       NA"
    DEFVAL      { 0 }
    ::= { fsMIOspfOpaqueInterfaceEntry 2 }

fsMIOspfType9LsdbTable OBJECT-TYPE
    SYNTAX      SEQUENCE OF FsMIOspfType9LsdbEntry
    ACCESS      not-accessible
    STATUS      mandatory
    DESCRIPTION 
        "The OSPF Process's TYPE9 Link State Database.
         ALCATEL NOTE: 
         	TABLE SIZE:   2200
         	DESCR:        NA"
--     REFERENCE   
--         "The Opaque LSA Option, Section 5.0 Management Considerations"
    ::= { fsMIOspfOpaqueLSAGroup 3 }

fsMIOspfType9LsdbEntry OBJECT-TYPE
    SYNTAX      FsMIOspfType9LsdbEntry
    ACCESS      not-accessible
    STATUS      mandatory
    DESCRIPTION 
        "A single Type 9 Link State Advertisement.
         Row creation : An entry shall be created dinamically.
         Row deletion : An entry shall be deleted dinamically.
         Index usage : the index is the Ip Address,Opaque Type,Link State Id,Router Id.
         Note that entries will be presented to the SNMP manager in full
         lexicographical order :  sorted on Ip Address,Opaque Type,Link State Id,Router Id."
    INDEX       { fsMIStdOspfContextId, fsMIOspfType9LsdbIfIpAddress, 
                  fsMIOspfType9LsdbOpaqueType, fsMIOspfType9LsdbLsid, 
                  fsMIOspfType9LsdbRouterId }
    ::= { fsMIOspfType9LsdbTable 1 }

FsMIOspfType9LsdbEntry ::= SEQUENCE {
    fsMIOspfType9LsdbIfIpAddress    IpAddress,
    fsMIOspfType9LsdbOpaqueType     INTEGER,
    fsMIOspfType9LsdbLsid           IpAddress,
    fsMIOspfType9LsdbRouterId       RouterID,
    fsMIOspfType9LsdbSequence       INTEGER,
    fsMIOspfType9LsdbAge            INTEGER,
    fsMIOspfType9LsdbChecksum       INTEGER,
    fsMIOspfType9LsdbAdvertisement  OCTET STRING
}

fsMIOspfType9LsdbIfIpAddress OBJECT-TYPE
    SYNTAX      IpAddress
    ACCESS      not-accessible
    STATUS      mandatory
    DESCRIPTION 
        "The IP address of this OSPF interface.
         ALCATEL NOTE:
           ACCESS:      NA          USAGE:       NA
           PERSIST:     NO          INSRVMOD:    NA
           RANGE:       NA          DEFVALUE:    NA
           UNITS:       NA          SPARSE:      NO
           DESCR:       NA"
    ::= { fsMIOspfType9LsdbEntry 1 }

fsMIOspfType9LsdbOpaqueType OBJECT-TYPE
    SYNTAX      INTEGER (1..11)
    ACCESS      not-accessible
    STATUS      mandatory
    DESCRIPTION 
        "The Opaque type  of  the  LSA.
         ALCATEL NOTE:
           ACCESS:      NA          USAGE:       NA
           PERSIST:     NO          INSRVMOD:    NA
           RANGE:       NA          DEFVALUE:    NA
           UNITS:       NA          SPARSE:      NO
           DESCR:       NA"
--     REFERENCE   
--         "The Opaque LSA Option ,Section A.3 The Opaque LSA"
    ::= { fsMIOspfType9LsdbEntry 2 }

fsMIOspfType9LsdbLsid OBJECT-TYPE
    SYNTAX      IpAddress
    ACCESS      not-accessible
    STATUS      mandatory
    DESCRIPTION 
        "The Link State ID is an LS Type Specific field
         containing the Opaque Type and Opaque ID.
         ALCATEL NOTE:
         ACCESS:      NA          USAGE:       NA
         PERSIST:     NO          INSRVMOD:    NA
         RANGE:       NA          DEFVALUE:    NA
         UNITS:       NA          SPARSE:      NO
         DESCR:       NA"
--     REFERENCE   
--         "The OpaqueLSA Option ,Appendix A.2 The Opaque LSA"
    ::= { fsMIOspfType9LsdbEntry 3 }

fsMIOspfType9LsdbRouterId OBJECT-TYPE
    SYNTAX      RouterID
    ACCESS      not-accessible
    STATUS      mandatory
    DESCRIPTION 
        "The 32 bit number that uniquely identifies the
         originating router in the Autonomous System.
         ALCATEL NOTE:
         ACCESS:      NA          USAGE:       NA
         PERSIST:     NO          INSRVMOD:    NA
         RANGE:       NA          DEFVALUE:    NA
         UNITS:       NA          SPARSE:      NO
         DESCR:       NA"
--     REFERENCE   
--         "The Opaque LSA Option ,Section 5.0 Management Considerations"
    ::= { fsMIOspfType9LsdbEntry 4 }

fsMIOspfType9LsdbSequence OBJECT-TYPE
    SYNTAX      INTEGER
    ACCESS      read-only
    STATUS      mandatory
    DESCRIPTION 
        "The sequence number field is a  signed  32-bit
         integer.   It  is used to detect old and dupli-
         cate link state advertisements.  The  space  of
         sequence  numbers  is  linearly  ordered.   The
         larger the sequence number the more recent  the
         advertisement.
         ALCATEL NOTE:
         ACCESS:      NA          USAGE:       NA
         PERSIST:     NO          INSRVMOD:    NA
         RANGE:       NA          DEFVALUE:    NA
         UNITS:       NA          SPARSE:      NO
         DESCR:       NA"
--     REFERENCE   
--         "The Opaque LSA Option ,Section 5.0 Management Considerations"
    ::= { fsMIOspfType9LsdbEntry 5 }

fsMIOspfType9LsdbAge OBJECT-TYPE
    SYNTAX      INTEGER
    ACCESS      read-only
    STATUS      mandatory
    DESCRIPTION 
        "This field is the age of the link state adver-
         tisement in seconds.
         ALCATEL NOTE:
         ACCESS:      NA          USAGE:       NA
         PERSIST:     NO          INSRVMOD:    NA
         RANGE:       0..3600     DEFVALUE:    0
         UNITS:       SECONDS     SPARSE:      NO
         DESCR:       NA"
--     REFERENCE   
--         "The Opaque LSA Option ,Section 5.0 Management Considerations"
    ::= { fsMIOspfType9LsdbEntry 6 }

fsMIOspfType9LsdbChecksum OBJECT-TYPE
    SYNTAX      INTEGER
    ACCESS      read-only
    STATUS      mandatory
    DESCRIPTION 
        "This field is the  checksum  of  the  complete
         contents  of  the  advertisement, excepting the
         age field.  The age field is excepted  so  that
         an   advertisement's  age  can  be  incremented
         without updating the  checksum.   The  checksum
         used  is  the same that is used for ISO connec-
         tionless datagrams; it is commonly referred  to
         as the Fletcher checksum.
         ALCATEL NOTE:
         ACCESS:      NA          USAGE:       NA
         PERSIST:     NO          INSRVMOD:    NA
         RANGE:       NA          DEFVALUE:    0
         UNITS:       NA          SPARSE:      NO
         DESCR:       NA"
--     REFERENCE   
--         "The Opaque LSA Option ,Section 5.0 Management Considerations"
    ::= { fsMIOspfType9LsdbEntry 7 }

fsMIOspfType9LsdbAdvertisement OBJECT-TYPE
    SYNTAX      OCTET STRING (SIZE(1..65535))
    ACCESS      read-only
    STATUS      mandatory
    DESCRIPTION 
        "The entire TYPE9 Opaque Link State Advertisement,
         including its header.
         ALCATEL NOTE:
         ACCESS:      NA          USAGE:       NA
         PERSIST:     NO          INSRVMOD:    NA
         RANGE:       NA          DEFVALUE:    '\0'
         UNITS:       NA          SPARSE:      NO
         DESCR:       NA"
--     REFERENCE   
--         "The Opaque LSA Option,Appendix A.2 The Opaque LSA"
    ::= { fsMIOspfType9LsdbEntry 8 }

fsMIOspfType11LsdbTable OBJECT-TYPE
    SYNTAX      SEQUENCE OF FsMIOspfType11LsdbEntry
    ACCESS      not-accessible
    STATUS      mandatory
    DESCRIPTION 
        "The OSPF Process's TYPE11 Links State Database.
         ALCATEL NOTE: 
         	TABLE SIZE:   2200
         	DESCR:        NA"
--     REFERENCE   
--         "The Opaque LSA Option ,Section 5.0 Management Considerations"
    ::= { fsMIOspfOpaqueLSAGroup 4 }

fsMIOspfType11LsdbEntry OBJECT-TYPE
    SYNTAX      FsMIOspfType11LsdbEntry
    ACCESS      not-accessible
    STATUS      mandatory
    DESCRIPTION 
        "A single TYPE11 Opaque Link State Advertisement.
         Row creation : An entry shall be created dynamically. 
         Row deletion : An entry shall be deleted dynamically.
         Index usage : the index is the Opaque Type,Link State Id,Router Id.
         Note that entries will be presented to the SNMP manager in full
         lexicographical order :  sorted on Opaque Type,Link State Id,Router Id."
    INDEX       { fsMIStdOspfContextId, fsMIOspfType11LsdbOpaqueType, 
                  fsMIOspfType11LsdbLsid, fsMIOspfType11LsdbRouterId }
    ::= { fsMIOspfType11LsdbTable 1 }

FsMIOspfType11LsdbEntry ::= SEQUENCE {
    fsMIOspfType11LsdbOpaqueType        INTEGER,
    fsMIOspfType11LsdbLsid              IpAddress,
    fsMIOspfType11LsdbRouterId          RouterID,
    fsMIOspfType11LsdbSequence          INTEGER,
    fsMIOspfType11LsdbAge               INTEGER,
    fsMIOspfType11LsdbChecksum          INTEGER,
    fsMIOspfType11LsdbAdvertisement     OCTET STRING
}

fsMIOspfType11LsdbOpaqueType OBJECT-TYPE
    SYNTAX      INTEGER (1..11)
    ACCESS      not-accessible
    STATUS      mandatory
    DESCRIPTION 
        "The Opaquetype  of  the  link  state  advertisement.
         ALCATEL NOTE:
           ACCESS:      NA          USAGE:       NA
           PERSIST:     NO          INSRVMOD:    NA
           RANGE:       NA          DEFVALUE:    NA    
           UNITS:       NA          SPARSE:      NO
           DESCR:       NA"
--     REFERENCE   
--         "The Opaque LSA Option ,Section 5.0 Management Considerations"
    ::= { fsMIOspfType11LsdbEntry 1 }

fsMIOspfType11LsdbLsid OBJECT-TYPE
    SYNTAX      IpAddress
    ACCESS      not-accessible
    STATUS      mandatory
    DESCRIPTION 
        "The Link State ID identifies the opaque type and
         the opaque ID of the received Opaque LSA for an application.
         ALCATEL NOTE:
         ACCESS:      NA          USAGE:       NA
         PERSIST:     NO          INSRVMOD:    NA
         RANGE:       NA          DEFVALUE:    NA
         UNITS:       NA          SPARSE:      NO
         DESCR:       NA"
--     REFERENCE   
--         "The Opaque LSA Option ,Section 5.0 Management Considerations"
    ::= { fsMIOspfType11LsdbEntry 2 }

fsMIOspfType11LsdbRouterId OBJECT-TYPE
    SYNTAX      RouterID
    ACCESS      not-accessible
    STATUS      mandatory
    DESCRIPTION 
        "The 32 bit number that uniquely identifies the
         originating router in the Autonomous System.
         ALCATEL NOTE:
          ACCESS:      NA          USAGE:       NA
          PERSIST:     NO          INSRVMOD:    NA
          RANGE:       NA          DEFVALUE:    NA
          UNITS:       NA          SPARSE:      NO
          DESCR:       NA"
--     REFERENCE   
--         "The Opaque LSA Option ,Section 5.0 Management Considerations"
    ::= { fsMIOspfType11LsdbEntry 3 }

fsMIOspfType11LsdbSequence OBJECT-TYPE
    SYNTAX      INTEGER
    ACCESS      read-only
    STATUS      mandatory
    DESCRIPTION 
        "The sequence number field is a  signed  32-bit
         integer.   It  is used to detect old and dupli-
         cate link state advertisements.  The  space  of
         sequence  numbers  is  linearly  ordered.   The
         larger the sequence number the more recent  the
         advertisement.
         ALCATEL NOTE:
         ACCESS:      NA          USAGE:       NA
         PERSIST:     NO          INSRVMOD:    NA
         RANGE:       NA          DEFVALUE:    NA
         UNITS:       NA          SPARSE:      NO
         DESCR:       NA"
--     REFERENCE   
--         "The Opaque LSA Option ,Section 5.0 Management Considerations"
    ::= { fsMIOspfType11LsdbEntry 4 }

fsMIOspfType11LsdbAge OBJECT-TYPE
    SYNTAX      INTEGER
    ACCESS      read-only
    STATUS      mandatory
    DESCRIPTION 
        "This field is the age of the link state adver-
         tisement in seconds.
         ALCATEL NOTE:
         ACCESS:      NA          USAGE:       NA
         PERSIST:     NO          INSRVMOD:    NA
         RANGE:       0..3600     DEFVALUE:    0
         UNITS:       SECONDS     SPARSE:      NO
         DESCR:       NA"
--     REFERENCE   
--         "The Opaque LSA Option ,Section 5.0 Management Considerations"
    ::= { fsMIOspfType11LsdbEntry 5 }

fsMIOspfType11LsdbChecksum OBJECT-TYPE
    SYNTAX      INTEGER
    ACCESS      read-only
    STATUS      mandatory
    DESCRIPTION 
        "This field is the  checksum  of  the  complete
         contents  of  the  advertisement, excepting the
         age field.  The age field is excepted  so  that
         an   advertisement's  age  can  be  incremented
         without updating the  checksum.   The  checksum
         used  is  the same that is used for ISO connec-
         tionless datagrams; it is commonly referred  to
         as the Fletcher checksum.
         ALCATEL NOTE:
         ACCESS:      NA          USAGE:       NA
         PERSIST:     NO          INSRVMOD:    NA
         RANGE:       NA          DEFVALUE:    0    
         UNITS:       NA          SPARSE:      NO
         DESCR:       NA"
--     REFERENCE   
--         "The Opaque LSA Option ,Section 5.0 Management Considerations"
    ::= { fsMIOspfType11LsdbEntry 6 }

fsMIOspfType11LsdbAdvertisement OBJECT-TYPE
    SYNTAX      OCTET STRING (SIZE(1..65535))
    ACCESS      read-only
    STATUS      mandatory
    DESCRIPTION 
        "The entire Link State Advertisement, including
         its header.
         ALCATEL NOTE:
         ACCESS:      NA          USAGE:       NA
         PERSIST:     NO          INSRVMOD:    NA
         RANGE:       NA          DEFVALUE:    '\0'
         UNITS:       NA          SPARSE:      NO
         DESCR:       NA"
--     REFERENCE   
--         "The Opaque LSA Option ,Section 5.0 Management Considerations"
    ::= { fsMIOspfType11LsdbEntry 7 }

fsMIOspfAppInfoDbTable OBJECT-TYPE
    SYNTAX      SEQUENCE OF FsMIOspfAppInfoDbEntry
    ACCESS      not-accessible
    STATUS      mandatory
    DESCRIPTION 
        "This table maintains information related to application statistics.       
         ALCATEL NOTE: 
         	TABLE SIZE:   255 
         	DESCR:        NA"
    ::= { fsMIOspfOpaqueLSAGroup 5 }

fsMIOspfAppInfoDbEntry OBJECT-TYPE
    SYNTAX      FsMIOspfAppInfoDbEntry
    ACCESS      not-accessible
    STATUS      mandatory
    DESCRIPTION 
        "A single Application's  statistical Information.
         Row creation : An entry shall be created dinamically. 
         Row deletion : An entry can be deleted when any dinamic infornmation lost.
         Index usage : the index is the Database Application Id.
         Note that entries will be presented to the SNMP manager in full
         lexicographical order :  sorted on Database Application Id."
    INDEX       { fsMIStdOspfContextId, fsMIOspfAppInfoDbAppid }
    ::= { fsMIOspfAppInfoDbTable 1 }

FsMIOspfAppInfoDbEntry ::= SEQUENCE {
    fsMIOspfAppInfoDbAppid              INTEGER,
    fsMIOspfAppInfoDbOpaqueType         INTEGER,
    fsMIOspfAppInfoDbLsaTypesSupported  INTEGER,
    fsMIOspfAppInfoDbType9Gen           Counter,
    fsMIOspfAppInfoDbType9Rcvd          Counter,
    fsMIOspfAppInfoDbType10Gen          Counter,
    fsMIOspfAppInfoDbType10Rcvd         Counter,
    fsMIOspfAppInfoDbType11Gen          Counter,
    fsMIOspfAppInfoDbType11Rcvd         Counter
}

fsMIOspfAppInfoDbAppid OBJECT-TYPE
    SYNTAX      INTEGER (1..65535)
    ACCESS      not-accessible
    STATUS      mandatory
    DESCRIPTION 
        "The Application's ID. Each Application has a
         unique Appid associated with it.
         ALCATEL NOTE:
         ACCESS:      NA          USAGE:       NA
         PERSIST:     NO          INSRVMOD:    NA
         RANGE:       NA          DEFVALUE:    NA    
         UNITS:       NA          SPARSE:      NO
         DESCR:       NA"
    ::= { fsMIOspfAppInfoDbEntry 1 }

fsMIOspfAppInfoDbOpaqueType OBJECT-TYPE
    SYNTAX      INTEGER (0..255)
    ACCESS      read-only
    STATUS      mandatory
    DESCRIPTION 
        "The OpaqueType of the LSA the application can
         generate or receive. Each Application can register
         only for a single OpaqueType.
         ALCATEL NOTE:
         ACCESS:      NA          USAGE:       NA
         PERSIST:     NO          INSRVMOD:    NA
         RANGE:       NA          DEFVALUE:    NA    
         UNITS:       NA          SPARSE:      NO
         DESCR:       NA"
    ::= { fsMIOspfAppInfoDbEntry 2 }

fsMIOspfAppInfoDbLsaTypesSupported OBJECT-TYPE
    SYNTAX      INTEGER (0..7)
    ACCESS      read-only
    STATUS      mandatory
    DESCRIPTION 
        "The LSA Types the application can generate is indicated
         by a BITMASK.The BITMASK and the interpretation of the
         types supported is given as below:-
         
          BitMask    TypesSupported
          0 0 0   ==>  No types
          0 0 1   ==>  Only Type9
          0 1 0   ==>  Only Type10
          0 1 1   ==>  Types 9,10
          1 0 0   ==>  Only Type11
          1 0 1   ==>  Types 9,11
          1 1 0   ==>  Types 10,11
          1 1 1   ==>  Types 9,10,11
         The remaining values are left for future definition.
         ALCATEL NOTE:
          ACCESS:      NA          USAGE:       NA
          PERSIST:     NO          INSRVMOD:    NA
          RANGE:       NA          DEFVALUE:    NA    
          UNITS:       NA          SPARSE:      NO
          DESCR:       NA"
    ::= { fsMIOspfAppInfoDbEntry 3 }

fsMIOspfAppInfoDbType9Gen OBJECT-TYPE
    SYNTAX      Counter
    ACCESS      read-only
    STATUS      mandatory
    DESCRIPTION 
        "The number of Type 9 LSAs generated by the application.
         This field is invalid if the application does not
         support the generation of Type9 LSAs.
         ALCATEL NOTE:
         ACCESS:      NA          USAGE:       NA
         PERSIST:     NO          INSRVMOD:    NA
         RANGE:       NA          DEFVALUE:    0
         UNITS:       LSA         SPARSE:      NO
         DESCR:       NA"
    ::= { fsMIOspfAppInfoDbEntry 4 }

fsMIOspfAppInfoDbType9Rcvd OBJECT-TYPE
    SYNTAX      Counter
    ACCESS      read-only
    STATUS      mandatory
    DESCRIPTION 
        "The number of Type 9 LSAs received by the application.
         ALCATEL NOTE:
           ACCESS:      NA          USAGE:       NA
           PERSIST:     NO          INSRVMOD:    NA
           RANGE:       NA          DEFVALUE:    0
           UNITS:       LSA         SPARSE:      NO
           DESCR:       NA"
    ::= { fsMIOspfAppInfoDbEntry 5 }

fsMIOspfAppInfoDbType10Gen OBJECT-TYPE
    SYNTAX      Counter
    ACCESS      read-only
    STATUS      mandatory
    DESCRIPTION 
        "The number of Type 10 LSAs generated by the application.
         This field is invalid if the application does not
         support the generation of Type10 LSAs.
         ALCATEL NOTE:
         ACCESS:      NA          USAGE:       NA
         PERSIST:     NO          INSRVMOD:    NA
         RANGE:       NA          DEFVALUE:    0
         UNITS:       LSA         SPARSE:      NO
         DESCR:       NA"
    ::= { fsMIOspfAppInfoDbEntry 6 }

fsMIOspfAppInfoDbType10Rcvd OBJECT-TYPE
    SYNTAX      Counter
    ACCESS      read-only
    STATUS      mandatory
    DESCRIPTION 
        "The number of Type 10 LSAs received by the application.
         ALCATEL NOTE:
           ACCESS:      NA          USAGE:       NA
           PERSIST:     NO          INSRVMOD:    NA
           RANGE:       NA          DEFVALUE:    0
           UNITS:       LSA         SPARSE:      NO
           DESCR:       NA"
    ::= { fsMIOspfAppInfoDbEntry 7 }

fsMIOspfAppInfoDbType11Gen OBJECT-TYPE
    SYNTAX      Counter
    ACCESS      read-only
    STATUS      mandatory
    DESCRIPTION 
        "The number of Type 11 LSAs generated by the application.
         This field is invalid if the application does not support
         the generation of Type11 LSAs.
         ALCATEL NOTE:
         ACCESS:      NA          USAGE:       NA
         PERSIST:     NO          INSRVMOD:    NA
         RANGE:       NA          DEFVALUE:    0
         UNITS:       LSA         SPARSE:      NO
         DESCR:       NA"
    ::= { fsMIOspfAppInfoDbEntry 8 }

fsMIOspfAppInfoDbType11Rcvd OBJECT-TYPE
    SYNTAX      Counter
    ACCESS      read-only
    STATUS      mandatory
    DESCRIPTION 
        "The number of Type 11 LSAs received by the application.
         ALCATEL NOTE:
           ACCESS:      NA          USAGE:       NA
           PERSIST:     NO          INSRVMOD:    NA
           RANGE:       NA          DEFVALUE:    0
           UNITS:       LSA         SPARSE:      NO
           DESCR:       NA"
    ::= { fsMIOspfAppInfoDbEntry 9 }

fsMIOspfRRDGroup OBJECT IDENTIFIER
    ::= { fsMIOspf 13 }

fsMIOspfRRDGeneralGroup OBJECT IDENTIFIER
    ::= { fsMIOspfRRDGroup 1 }

fsMIOspfRRDRouteTable OBJECT-TYPE
    SYNTAX      SEQUENCE OF FsMIOspfRRDRouteEntry
    ACCESS      not-accessible
    STATUS      mandatory
    DESCRIPTION 
        " Describes RRDRoute Entry 
         ALCATEL NOTE: 
         	TABLE SIZE:   64 
         	DESCR:        NA"
    ::= { fsMIOspfRRDGeneralGroup 1 }

fsMIOspfRRDRouteEntry OBJECT-TYPE
    SYNTAX      FsMIOspfRRDRouteEntry
    ACCESS      not-accessible
    STATUS      mandatory
    DESCRIPTION 
        " Information describing the RRDRoute 
         Row creation : An entry will be created by the system when an entry
             		is created in the fsMIStdOspfTable.
         Row deletion : An entry will be deleted by the system when an entry
             		is deleted in the fsMIStdOspfTable.
         Index usage : the index is fsMIStdOspfEntry.
           Note that entries will be presented to the SNMP manager in full
           lexicographical order :  sorted on fsMIStdOspfEntry."
    INDEX       { fsMIStdOspfContextId }
--     AUGMENTS    { fsMIStdOspfEntry }
    ::= { fsMIOspfRRDRouteTable 1 }

FsMIOspfRRDRouteEntry ::= SEQUENCE {
    fsMIOspfRRDStatus               Status,
    fsMIOspfRRDSrcProtoMaskEnable   INTEGER,
    fsMIOspfRRDSrcProtoMaskDisable  INTEGER
}

fsMIOspfRRDStatus OBJECT-TYPE
    SYNTAX      Status
    ACCESS      read-write
    STATUS      mandatory
    DESCRIPTION 
        "This MIB object enables/disables OSPF to participate in Route 
         Redistribution. If set to enabled, OSPF will start advertising 
         the routes learned by other protocols. If set to disabled, OSPF 
         will stop redisbution of routes. However, OSPF will continue  
         updating the Common Routing Table using the queue interface.
         ALCATEL NOTE:
         ACCESS:      NA          USAGE:       NA
         PERSIST:     YES         INSRVMOD:    YES
         RANGE:       1,2         DEFVALUE:    NA
         UNITS:       NA          SPARSE:      NO
         DESCR:       NA"
    DEFVAL      { disabled }
    ::= { fsMIOspfRRDRouteEntry 1 }

fsMIOspfRRDSrcProtoMaskEnable OBJECT-TYPE
    SYNTAX      INTEGER
    ACCESS      read-write
    STATUS      mandatory
    DESCRIPTION 
        "The bit mask of source protocols from which routes are 
         imported to OSPF.
         
         Bit 1, if set, indicates that local routes are
         redistributed into OSPF. (value = 2)
         
         Bit 2, if set, indicates that static routes are
         redistributed into OSPF. (value = 4)
         
         Bit 7, if set, indicates that routes from RIP are
         redistributed into OSPF. (value = 128)
         
         Bit 13, if set, indicates that routes from BGP are
         redistributed into OSPF. (value = 8192)
         
         Other bits are reserved for future use.
         ALCATEL NOTE:
         ACCESS:      NA          USAGE:       NA
         PERSIST:     YES         INSRVMOD:    YES
         RANGE:       NA          DEFVALUE:    NA
         UNITS:       NA          SPARSE:      NO
         DESCR:       NA"
    DEFVAL      { 0 }
    ::= { fsMIOspfRRDRouteEntry 2 }

fsMIOspfRRDSrcProtoMaskDisable OBJECT-TYPE
    SYNTAX      INTEGER
    ACCESS      read-write
    STATUS      mandatory
    DESCRIPTION 
        "The bit mask of source protocols from which redistribution 
         to OSPF is disabled.
         
         Bit 1, if set, indicates that local routes are not
         redistributed into OSPF. (value = 2)
         
         Bit 2, if set, indicates that static routes are not
         redistributed into OSPF. (value = 4)
         
         Bit 7, if set, indicates that routes from RIP are not
         redistributed into OSPF. (value = 128)
         
         Bit 13, if set, indicates that routes from BGP are not
         redistributed into OSPF. (value = 8192) 
         
         Other bits are reserved for future use.
         ALCATEL NOTE:
         ACCESS:      NA          USAGE:       NA
         PERSIST:     YES         INSRVMOD:    YES
         RANGE:       NA          DEFVALUE:    NA
         UNITS:       NA          SPARSE:      NO
         DESCR:       NA"
    DEFVAL      { 8326 }
    ::= { fsMIOspfRRDRouteEntry 3 }

fsMIOspfRRDRouteConfigTable OBJECT-TYPE
    SYNTAX      SEQUENCE OF FsMIOspfRRDRouteConfigEntry
    ACCESS      not-accessible
    STATUS      mandatory
    DESCRIPTION 
        "A table describing the configuration of Metric Cost and Route
         Type information to be applied to the routes learnt from the RTM.
         ALCATEL NOTE:
         	TABLE SIZE:   200
         	DESCR:        NA"
    ::= { fsMIOspfRRDGroup 2 }

fsMIOspfRRDRouteConfigEntry OBJECT-TYPE
    SYNTAX      FsMIOspfRRDRouteConfigEntry
    ACCESS      not-accessible
    STATUS      mandatory
    DESCRIPTION 
        "Information describing the configuration of single route entry.
         Row creation : An entry shall be created in one step by a 
          set-request with all necessary parameter values and  
          futOspfRRDRouteStatus set to createAndGo(4).
         Row deletion : An entry shall be deleted by setting
          the futOspfRRDRouteStatus of the specific entry to destroy(6).
         Index usage : the index is the Route Destination,Route Mask.
         Note that entries will be presented to the SNMP manager in full
         lexicographical order :  sorted on Route Destination,Route Mask."
    INDEX       { fsMIStdOspfContextId, fsMIOspfRRDRouteDest, 
                  fsMIOspfRRDRouteMask }
    ::= { fsMIOspfRRDRouteConfigTable 1 }

FsMIOspfRRDRouteConfigEntry ::= SEQUENCE {
    fsMIOspfRRDRouteDest        IpAddress,
    fsMIOspfRRDRouteMask        IpAddress,
    fsMIOspfRRDRouteMetric      BigMetric,
    fsMIOspfRRDRouteMetricType  INTEGER,
    fsMIOspfRRDRouteTagType     INTEGER,
    fsMIOspfRRDRouteTag         INTEGER,
    fsMIOspfRRDRouteStatus      RowStatus
}

fsMIOspfRRDRouteDest OBJECT-TYPE
    SYNTAX      IpAddress
    ACCESS      not-accessible
    STATUS      mandatory
    DESCRIPTION 
        "Ip Address of the Destination route.
         ALCATEL NOTE:
           ACCESS:      NA          USAGE:       NA
           PERSIST:     YES         INSRVMOD:    NA
           RANGE:       NA          DEFVALUE:    NA
           UNITS:       NA          SPARSE:      NO
           DESCR:       NA"
    ::= { fsMIOspfRRDRouteConfigEntry 1 }

fsMIOspfRRDRouteMask OBJECT-TYPE
    SYNTAX      IpAddress
    ACCESS      not-accessible
    STATUS      mandatory
    DESCRIPTION 
        "Mask of the Destination route.
         ALCATEL NOTE:
           ACCESS:      NA          USAGE:       NA
           PERSIST:     YES         INSRVMOD:    NA
           RANGE:       NA          DEFVALUE:    NA
           UNITS:       NA          SPARSE:      NO
           DESCR:       NA"
    ::= { fsMIOspfRRDRouteConfigEntry 2 }

fsMIOspfRRDRouteMetric OBJECT-TYPE
    SYNTAX      BigMetric
    ACCESS      read-write
    STATUS      mandatory
    DESCRIPTION 
        "The Metric value applied to the route before it is adv. into the
         OSPF Domain.
         ALCATEL NOTE:
         ACCESS:      NA          USAGE:       OPT
         PERSIST:     YES         INSRVMOD:    YES
         RANGE:       NA          DEFVALUE:    NA
         UNITS:       NA          SPARSE:      NO
         DESCR:       NA"
    DEFVAL      { 10 }
    ::= { fsMIOspfRRDRouteConfigEntry 3 }

fsMIOspfRRDRouteMetricType OBJECT-TYPE
    SYNTAX      INTEGER { asexttype1(1), asexttype2(2) }
    ACCESS      read-write
    STATUS      mandatory
    DESCRIPTION 
        "The Metric Type applied to the route before it is adv. into the
         OSPF Domain
         ALCATEL NOTE:
         ACCESS:      NA          USAGE:       OPT
         PERSIST:     YES         INSRVMOD:    YES
         RANGE:       NA          DEFVALUE:    NA
         UNITS:       NA          SPARSE:      NO
         DESCR:       NA"
    DEFVAL      { asexttype2 }
    ::= { fsMIOspfRRDRouteConfigEntry 4 }

fsMIOspfRRDRouteTagType OBJECT-TYPE
    SYNTAX      INTEGER { manual(1), automatic(2) }
    ACCESS      read-write
    STATUS      mandatory
    DESCRIPTION 
        "The Tag Type MIB object describes whether Tags will be 
         automatically generated or will be manually configured. 
         If tags are manually configured , the fsMIOspfRRDRouteTag 
         MIB has to be set with the Tag value needed. 
         ALCATEL NOTE:
         ACCESS:      NA          USAGE:       OPT
         PERSIST:     YES         INSRVMOD:    YES
         RANGE:       NA          DEFVALUE:    NA
         UNITS:       NA          SPARSE:      NO
         DESCR:       NA"
    DEFVAL      { manual }
    ::= { fsMIOspfRRDRouteConfigEntry 5 }

fsMIOspfRRDRouteTag OBJECT-TYPE
    SYNTAX      INTEGER
    ACCESS      read-write
    STATUS      mandatory
    DESCRIPTION 
        "The Route Tag in case the user configures a Manual option for 
         the tags. 
         ALCATEL NOTE:
         ACCESS:      NA          USAGE:       OPT
         PERSIST:     YES         INSRVMOD:    YES
         RANGE:       NA          DEFVALUE:    NA
         UNITS:       NA          SPARSE:      NO
         DESCR:       NA"
    DEFVAL      { 0 }
    ::= { fsMIOspfRRDRouteConfigEntry 6 }

fsMIOspfRRDRouteStatus OBJECT-TYPE
    SYNTAX      RowStatus
    ACCESS      read-write
    STATUS      mandatory
    DESCRIPTION 
        "The variable dispalys the status of the entry.Setting it to
         'invalid' has the effect of rendering it inoperative.
         ALCATEL NOTE:
         ACCESS:      NA          USAGE:       MAND
         PERSIST:     YES         INSRVMOD:    YES
         RANGE:       1,2,4,5,6   DEFVALUE:    NA
         UNITS:       NA          SPARSE:      NO
         DESCR:       NA"
    ::= { fsMIOspfRRDRouteConfigEntry 7 }

fsMIOspfTestGroup OBJECT IDENTIFIER
    ::= { fsMIOspf 100 }

END -- end of module ARICENT-OSPFMI-MIB.
