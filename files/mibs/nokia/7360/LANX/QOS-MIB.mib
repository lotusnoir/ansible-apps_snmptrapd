--
-- This SMIv1 module has been generated by smidump 0.4.8. Do not edit.
--

QOS-MIB DEFINITIONS ::= BEGIN

IMPORTS
    OBJECT-TYPE
        FROM RFC-1212
    Gauge, enterprises
        FROM RFC1155-SMI
    DisplayString, RowStatus
        FROM SNMPv2-TC;

lanxQOSMIB OBJECT IDENTIFIER
    ::= { enterprises futuresoftware(2076) 90 }

-- lanxQOSMIB MODULE-IDENTITY
--     LAST-UPDATED "200401031200Z"
--     ORGANIZATION 
--         "FUTURE SOFTWARE PVT. LIMITED"
--     CONTACT-INFO 
--         " FUTURE SOFTWARE PVT. LIMITED
--          481 Mount Road
--          Madras - 600 035
--          Phone : +91-44-2433 0550 
--               support@futsoft.com"
--     DESCRIPTION 
--         "The LANX QOS MIB "
--     REVISION    "200401031200Z"
--     DESCRIPTION 
--         "The initial revision of this MIB module was published as
--          RFC 1450."
--     ::= { enterprises futuresoftware(2076) 90 }


QosSchedulingMode ::=
    INTEGER { strict(1), wrr(2), wfq(3) }

-- QosSchedulingMode ::= TEXTUAL-CONVENTION
--     STATUS      mandatory
--     DESCRIPTION 
--         "Enumerated Integer data type"
--     SYNTAX      INTEGER
--                   { strict(1), wrr(2), wfq(3) }

QosFlowType ::=
    INTEGER { port(1), vlan(2), vlandot1P(3), vlandscp(4) }

-- QosFlowType ::= TEXTUAL-CONVENTION
--     STATUS      mandatory
--     DESCRIPTION 
--         "Enumerated Integer data type to indicate the flow type."
--     SYNTAX      INTEGER
--                   { port(1), vlan(2), vlandot1P(3), vlandscp(4) }

lanxQosSchedulingMode OBJECT-TYPE
    SYNTAX      QosSchedulingMode
    ACCESS      read-only
    STATUS      mandatory
    DESCRIPTION 
        "Gives the scheduling mode for Qos(strict, wrr, wfq).
         ALCATEL NOTE:
             ACCESS:      NA           USAGE:       NA
             PERSIST:     NO           INSRVMOD:    NA
             RANGE:       wrr          DEFVALUE:    NA
             UNITS:       NA           SPARSE:      NA
             DESCR:       NA"
    DEFVAL      { wrr }
    ::= { lanxQOSMIB 1 }

lanxQosPortConfigTable OBJECT-TYPE
    SYNTAX      SEQUENCE OF LanxQosPortConfigEntry
    ACCESS      not-accessible
    STATUS      mandatory
    DESCRIPTION 
        "LANX Qos port configuration table.
         ALCATEL NOTE:
             TABLESIZE:	DEP 
             DESCR:        DEP(TABLESIZE) The size of the table is the maximum number of physical interfaces
         			    in the system. This value can be got from the object issSystemNumberOfPorts
         			    in fsiss.mib."
    ::= { lanxQOSMIB 2 }

lanxQosPortConfigEntry OBJECT-TYPE
    SYNTAX      LanxQosPortConfigEntry
    ACCESS      not-accessible
    STATUS      mandatory
    DESCRIPTION 
        "Contains LANX Qos port parameters.
         Row creation : All the Entries are created by the system at the startup.
         Row deletion : All the Entries are deleted by the system when it shutdowns.
         Index usage : the index is the lanxInterfaceIndex.
         Note that entries will be presented to the SNMP manager in full
         lexicographical order :  sorted on lanxInterfaceIndex."
    INDEX       { lanxInterfaceIndex }
    ::= { lanxQosPortConfigTable 1 }

LanxQosPortConfigEntry ::= SEQUENCE {
    lanxInterfaceIndex          INTEGER,
    lanxQosWeightQ0             INTEGER,
    lanxQosWeightQ1             INTEGER,
    lanxQosWeightQ2             INTEGER,
    lanxQosWeightQ3             INTEGER,
    lanxQosPauseTx              INTEGER,
    lanxQosPauseRx              INTEGER,
    lanxQosPortRate             INTEGER,
    lanxQosDSCPtoPbitMapStatus  INTEGER
}

lanxInterfaceIndex OBJECT-TYPE
    SYNTAX      INTEGER (1..2147483647)
    ACCESS      not-accessible
    STATUS      mandatory
    DESCRIPTION 
        "LANX Qos port index.
         ALCATEL NOTE:
             ACCESS:      NA           USAGE:       NA
             PERSIST:     YES          INSRVMOD:    NA
             RANGE:       DEP           DEFVALUE:    NA
             UNITS:       NA           SPARSE:      NO
             DESCR:       DEP(RANGE) The range is the maximum number of physical ports in the system.
         			This value can be got from issSystemNumberOfPorts in fsiss.mib."
    ::= { lanxQosPortConfigEntry 1 }

lanxQosWeightQ0 OBJECT-TYPE
    SYNTAX      INTEGER (0..15)
    ACCESS      read-write
    STATUS      mandatory
    DESCRIPTION 
        "LANX Qos queue0 weight.
         ALCATEL NOTE:
             ACCESS:      NA           USAGE:       NA
             PERSIST:     YES          INSRVMOD:    YES
             RANGE:       1..15        DEFVALUE:    NA
             UNITS:       NA           SPARSE:      NO
             DESCR:       NA"
    DEFVAL      { 1 }
    ::= { lanxQosPortConfigEntry 2 }

lanxQosWeightQ1 OBJECT-TYPE
    SYNTAX      INTEGER (0..15)
    ACCESS      read-write
    STATUS      mandatory
    DESCRIPTION 
        "LANX Qos queue1 weight.
         ALCATEL NOTE:
             ACCESS:      NA           USAGE:       NA
             PERSIST:     YES          INSRVMOD:    YES
             RANGE:       1..15        DEFVALUE:    NA
             UNITS:       NA           SPARSE:      NO
             DESCR:       NA"
    DEFVAL      { 2 }
    ::= { lanxQosPortConfigEntry 3 }

lanxQosWeightQ2 OBJECT-TYPE
    SYNTAX      INTEGER (0..7)
    ACCESS      read-only
    STATUS      mandatory
    DESCRIPTION 
        "LANX Qos queue2 weight.
         ALCATEL NOTE:
             ACCESS:      NA           USAGE:       NA
             PERSIST:     NO           INSRVMOD:    NA 
             RANGE:       0            DEFVALUE:    NA
             UNITS:       NA           SPARSE:      NO
             DESCR:       NA"
    DEFVAL      { 0 }
    ::= { lanxQosPortConfigEntry 4 }

lanxQosWeightQ3 OBJECT-TYPE
    SYNTAX      INTEGER (0..7)
    ACCESS      read-only
    STATUS      mandatory
    DESCRIPTION 
        "LANX Qos queue3 weight.
         ALCATEL NOTE:
             ACCESS:      NA           USAGE:       NA
             PERSIST:     NO           INSRVMOD:    NA 
             RANGE:       0            DEFVALUE:    NA
             UNITS:       NA           SPARSE:      NO
             DESCR:       NA"
    DEFVAL      { 0 }
    ::= { lanxQosPortConfigEntry 5 }

lanxQosPauseTx OBJECT-TYPE
    SYNTAX      INTEGER { enable(1), disable(2) }
    ACCESS      read-write
    STATUS      mandatory
    DESCRIPTION 
        "LANX Qos pause transmit status.
         ALCATEL NOTE:
             ACCESS:      NA           USAGE:       NA
             PERSIST:     YES          INSRVMOD:    YES
             RANGE:       2            DEFVALUE:    NA
             UNITS:       NA           SPARSE:      NO
             DESCR:       NA"
    DEFVAL      { disable }
    ::= { lanxQosPortConfigEntry 6 }

lanxQosPauseRx OBJECT-TYPE
    SYNTAX      INTEGER { enable(1), disable(2) }
    ACCESS      read-write
    STATUS      mandatory
    DESCRIPTION 
        "LANX Qos pause recieve status.
         ALCATEL NOTE:
             ACCESS:      NA           USAGE:       NA
             PERSIST:     YES          INSRVMOD:    YES
             RANGE:       NA           DEFVALUE:    2
             UNITS:       NA           SPARSE:      NO
             DESCR:       NA"
    DEFVAL      { disable }
    ::= { lanxQosPortConfigEntry 7 }

lanxQosPortRate OBJECT-TYPE
    SYNTAX      INTEGER (0..163840)
    ACCESS      read-write
    STATUS      mandatory
    DESCRIPTION 
        "LANX Qos port Egress rate (in granularity of 64 Kbps ).
         For the 64 Kbps to the 1Gbps, there can be totally 16384 steps.
         ALCATEL NOTE:
         ACCESS:      NA           USAGE:       NA
         PERSIST:     YES          INSRVMOD:    YES
         RANGE:       1..163840    DEFVALUE:    16384(1Gbps) 163840 (10Gbps)
         UNITS:       64 Kbps      SPARSE:      NO
         DESCR:       NA"
    DEFVAL      { 16384 }
    ::= { lanxQosPortConfigEntry 8 }

lanxQosDSCPtoPbitMapStatus OBJECT-TYPE
    SYNTAX      INTEGER { enable(1), disable(2) }
    ACCESS      read-write
    STATUS      mandatory
    DESCRIPTION 
        "LANX Qos DSCP to P-bit allignment status.
         ALCATEL NOTE:
             ACCESS:      NA           USAGE:       NA
             PERSIST:     YES          INSRVMOD:    YES
             RANGE:       NA           DEFVALUE:    NA
             UNITS:       NA           SPARSE:      NO
             DESCR:       NA"
    DEFVAL      { disable }
    ::= { lanxQosPortConfigEntry 9 }

lanxQosDot1PTrafficClassTable OBJECT-TYPE
    SYNTAX      SEQUENCE OF LanxQosDot1PTrafficClassEntry
    ACCESS      not-accessible
    STATUS      mandatory
    DESCRIPTION 
        "A table mapping evaluated User Priority to Traffic
         Class, for forwarding by the bridge.  Traffic class is a
         number in the range (0..(dot1dPortNumTrafficClasses-1)).
         dot1dportNumTrafficClasses object will have value of 4 and
         read-only.
         ALCATEL NOTE:
             TABLESIZE:	 8
             DESCR:       NA"
--     REFERENCE   
--         "ISO/IEC 15802-3 Table 7-2"
    ::= { lanxQOSMIB 3 }

lanxQosDot1PTrafficClassEntry OBJECT-TYPE
    SYNTAX      LanxQosDot1PTrafficClassEntry
    ACCESS      not-accessible
    STATUS      mandatory
    DESCRIPTION 
        "User Priority to Traffic Class mapping.
         Row creation : All the Entries are created by the system at the startup.
         Row deletion : All the Entries are deleted by the system when it shutdowns.
         Index usage : the index is the lanxQosDot1PTrafficClassPriority.
         Note that entries will be presented to the SNMP manager in full
         lexicographical order :  sorted on lanxQosDot1PTrafficClassPriority."
    INDEX       { lanxQosDot1PTrafficClassPriority }
    ::= { lanxQosDot1PTrafficClassTable 1 }

LanxQosDot1PTrafficClassEntry ::= SEQUENCE {
    lanxQosDot1PTrafficClassPriority    INTEGER,
    lanxQosDot1PTrafficClass            INTEGER
}

lanxQosDot1PTrafficClassPriority OBJECT-TYPE
    SYNTAX      INTEGER (0..7)
    ACCESS      not-accessible
    STATUS      mandatory
    DESCRIPTION 
        "The Priority value determined for the received frame.
         This value is equivalent to the priority indicated in
         the tagged frame received, or one of the evaluated
         priorities, determined according to the media-type.
         
         For untagged frames received from Ethernet media, this
         value is equal to the dot1dPortDefaultUserPriority value
         for the ingress port.
         
         For untagged frames received from non-Ethernet media,
         this value is equal to the dot1dRegenUserPriority value
         for the ingress port and media-specific user priority.
         ALCATEL NOTE:
             ACCESS:      NA           USAGE:       NA
             PERSIST:     NO           INSRVMOD:    NA
             RANGE:       NA           DEFVALUE:    NA
             UNITS:       NA           SPARSE:      NO
             DESCR:       NA"
    ::= { lanxQosDot1PTrafficClassEntry 1 }

lanxQosDot1PTrafficClass OBJECT-TYPE
    SYNTAX      INTEGER
    ACCESS      read-write
    STATUS      mandatory
    DESCRIPTION 
        "The Traffic Class the received frame is mapped to.
         ALCATEL NOTE:
             ACCESS:      NA           USAGE:       NA
             PERSIST:     NO           INSRVMOD:    YES
             RANGE:       0..7         DEFVALUE:    NA
             UNITS:       NA           SPARSE:      NO
             DESCR:       NA"
    ::= { lanxQosDot1PTrafficClassEntry 2 }

lanxQosMeterTable OBJECT-TYPE
    SYNTAX      SEQUENCE OF LanxQosMeterEntry
    ACCESS      not-accessible
    STATUS      mandatory
    DESCRIPTION 
        "A table use to configure the various policing paramter information. The entry in this table can
         be associated with any flow on specific port.
         ALCATEL NOTE:
             TABLESIZE:	 64
             DESCR:       NA"
    ::= { lanxQOSMIB 5 }

lanxQosMeterEntry OBJECT-TYPE
    SYNTAX      LanxQosMeterEntry
    ACCESS      not-accessible
    STATUS      mandatory
    DESCRIPTION 
        "QoS Meter Prarmeters Configuation entry
         Row creation : A QOS-METER entry shall be created in one step by a
             		set-request with all necessary parameter values and
             		lanxQosMeterRowStatus set to createAndGo(4).
         			Two entries are created by the System at the startup.
         Row deletion : A QOS-METER entry shall be deleted by setting
             		the lanxQosMeterRowStatus of the specific entry to destroy(6).
         Index usage : the index is the lanxQosMeterIndex.
         Note that entries will be presented to the SNMP manager in full
         lexicographical order :  sorted on lanxQosMeterIndex."
    INDEX       { lanxQosMeterIndex }
    ::= { lanxQosMeterTable 1 }

LanxQosMeterEntry ::= SEQUENCE {
    lanxQosMeterIndex           INTEGER,
    lanxQosMeterIngressRate     INTEGER,
    lanxQosMeterBurstSize       INTEGER,
    lanxQosMeterRefCount        INTEGER,
    lanxQosMeterName            DisplayString,
    lanxQosMeterVersion         DisplayString,
    lanxQosMeterRowStatus       RowStatus
}

lanxQosMeterIndex OBJECT-TYPE
    SYNTAX      INTEGER (1..64)
    ACCESS      not-accessible
    STATUS      mandatory
    DESCRIPTION 
        "An index which is used to identify a unique entry.  
         ALCATEL NOTE:
             ACCESS:      NA           USAGE:       NA
             PERSIST:     YES          INSRVMOD:    NA
             RANGE:       NA           DEFVALUE:    NA
             UNITS:       NA           SPARSE:      NO
             DESCR:       NA"
    ::= { lanxQosMeterEntry 1 }

lanxQosMeterIngressRate OBJECT-TYPE
    SYNTAX      INTEGER (1..163840)
    ACCESS      read-write
    STATUS      mandatory
    DESCRIPTION 
        "The Ingress max policing Rate for the meter entry in steps of 64Kbps
         ALCATEL NOTE:
             ACCESS:      NA           USAGE:       OPT
             PERSIST:     YES          INSRVMOD:    YES
             RANGE:       1..163840    DEFVALUE:    16384(1 Gbps) 163840 (10 Gbps)
             UNITS:       64 Kbps      SPARSE:      NO
             DESCR:       NA"
    ::= { lanxQosMeterEntry 2 }

lanxQosMeterBurstSize OBJECT-TYPE
    SYNTAX      INTEGER (0..7)
    ACCESS      read-write
    STATUS      mandatory
    DESCRIPTION 
        "The Ingress Policer's Burst tolerance parameter.  The following mapping table will be  used to get the actual Burst Size tolerance from this parameter's value:
         Burst Size      Burst Tolerance (in KBytes)
                  0                     3
                  1                     8
                  2                     16
                  3                     28
                  4                     64
                  5                     128
                  6                     256
                  7                     512
             ALCATEL NOTE:
                 ACCESS:      NA           USAGE:       OPT
                 PERSIST:     YES          INSRVMOD:    YES
                 RANGE:       NA           DEFVALUE:    7
                 UNITS:       NA           SPARSE:      NO
                 DESCR:       NA"
    ::= { lanxQosMeterEntry 3 }

lanxQosMeterRefCount OBJECT-TYPE
    SYNTAX      INTEGER
    ACCESS      read-only
    STATUS      mandatory
    DESCRIPTION 
        "A counter to indicate the number of times the meter entry has actually been instantiated on any port.
         ALCATEL NOTE:
             ACCESS:      NA           USAGE:       NA
             PERSIST:     NO           INSRVMOD:    NA
             RANGE:       NA           DEFVALUE:    0
             UNITS:       NA           SPARSE:      NO
             DESCR:       NA"
    ::= { lanxQosMeterEntry 4 }

lanxQosMeterName OBJECT-TYPE
    SYNTAX      DisplayString (SIZE(1..15))
    ACCESS      read-write
    STATUS      mandatory
    DESCRIPTION 
        "A name for the Meter entry. This is an optional parameter. 
         ALCATEL NOTE:
             ACCESS:      NA           USAGE:       OPT
             PERSIST:     YES          INSRVMOD:    YES
             RANGE:       NA           DEFVALUE:    '\0'
             UNITS:       NA           SPARSE:      NO
             DESCR:       NA"
    ::= { lanxQosMeterEntry 5 }

lanxQosMeterVersion OBJECT-TYPE
    SYNTAX      DisplayString (SIZE(1..15))
    ACCESS      read-write
    STATUS      mandatory
    DESCRIPTION 
        "A version no for the Meter entry. This parameter is optional 
         ALCATEL NOTE:
             ACCESS:      NA           USAGE:       OPT
             PERSIST:     YES          INSRVMOD:    YES
             RANGE:       NA           DEFVALUE:    '\0'
             UNITS:       NA           SPARSE:      NO
             DESCR:       NA"
    ::= { lanxQosMeterEntry 6 }

lanxQosMeterRowStatus OBJECT-TYPE
    SYNTAX      RowStatus
    ACCESS      read-write
    STATUS      mandatory
    DESCRIPTION 
        "Status of the Meter Entry. 'Active' state implies that the entry is ready to use. Only 'Active' entries can be          associated with a policer table. The Row status will have only foll. Values:
         1  -  active To indicate entry is valid for use.
         4  - create and go To creat a entry and to set it to active
         6  - destroy - To delete a entry.  
         2  - Not_in_service - To indiacte that the entry is not used.
                ALCATEL NOTE:
                    ACCESS:      NA           USAGE:       MAND
                    PERSIST:     YES          INSRVMOD:    YES
                    RANGE:       1,2,4,5,6    DEFVALUE:    NA
                    UNITS:       NA           SPARSE:      NO
                    DESCR:       NA"
    ::= { lanxQosMeterEntry 7 }

lanxQosFlowTable OBJECT-TYPE
    SYNTAX      SEQUENCE OF LanxQosFlowEntry
    ACCESS      not-accessible
    STATUS      mandatory
    DESCRIPTION 
        "A table used to configure various flows to be policed.
         ALCATEL NOTE:
             TABLESIZE:	 64
             DESCR:       NA"
    ::= { lanxQOSMIB 6 }

lanxQosFlowEntry OBJECT-TYPE
    SYNTAX      LanxQosFlowEntry
    ACCESS      not-accessible
    STATUS      mandatory
    DESCRIPTION 
        "QoS Flow Configuration entry
         Row creation : A QOS-FLOW entry shall be created in one step by a
             		set-request with all necessary parameter values and
             		lanxQosFlowRowStatus set to createAndGo(4).
         			One entry will be created by the System at the startup.
         Row deletion : A QOS-FLOW entry shall be deleted by setting
             		the lanxQosFlowRowStatus of the specific entry to destroy(6).
         Index usage : the index is the lanxQosFlowIndex.
         Note that entries will be presented to the SNMP manager in full
         lexicographical order :  sorted on lanxQosFlowIndex."
    INDEX       { lanxQosFlowIndex }
    ::= { lanxQosFlowTable 1 }

LanxQosFlowEntry ::= SEQUENCE {
    lanxQosFlowIndex        INTEGER,
    lanxQosFlowType         QosFlowType,
    lanxQosFlowVlanId       INTEGER,
    lanxQosFlowPriority     INTEGER,
    lanxQosFlowDSCP         INTEGER,
    lanxQosFlowRefCount     INTEGER,
    lanxQosFlowName         DisplayString,
    lanxQosFlowVersion      DisplayString,
    lanxQosFlowRowStatus    RowStatus
}

lanxQosFlowIndex OBJECT-TYPE
    SYNTAX      INTEGER (1..64)
    ACCESS      not-accessible
    STATUS      mandatory
    DESCRIPTION 
        "An index which is used to identify a unique flow.  
         ALCATEL NOTE:
             ACCESS:      NA           USAGE:       NA
             PERSIST:     YES          INSRVMOD:    NA
             RANGE:       NA           DEFVALUE:    NA
             UNITS:       NA           SPARSE:      NO
             DESCR:       NA"
    ::= { lanxQosFlowEntry 1 }

lanxQosFlowType OBJECT-TYPE
    SYNTAX      QosFlowType
    ACCESS      read-write
    STATUS      mandatory
    DESCRIPTION 
        "This object defines the type of the logical flow that needs to be policed.
         Supported types are:
              1 - Port 
              2 - Port.VLAN 
              3 - Port.VLAN.Dot1P 
              4 - Port.VLAN.DSCP 
         If Port flow type is defined, then the  'lanxQosFlowVlanId',  'lanxQosFlowPriority' and 'lanxQosFlowDSCP' 
         parameters are ignored. A LANX port policer will rate limit all ingress traffic on a physical port.
         If Port.VLAN flow type is selected the 'lanxQosFlowVlanId' field is used to define the filter on the port,
         while 'lanxQosFlowPriority' and 'lanxQosFlowDSCP' are ignored. This flow type is useful to
          rate limit a VLAN on an ingress port.
          If Port.VLAN.Dot1P flow type is selected the 'lanxQosFlowVlanId' and 'lanxQosFlowPriority' fields are
          used to define the filter on the port, while 'lanxQosFlowDSCP' is ignored. This flow type is useful to
          rate limit a VLAN on a 802.1P-based traffic class criterion per ingress port.
          If Port.VLAN.DSCP flwo type is selected the 'lanxQosFlowVlanId' and 'lanxQosFlowDSCP' fields are
          used to define the filter on the port, while 'lanxQosFlowPriority' is ignored. This policer is useful to
          rate limit a VLAN on a DSCP-based traffic class criterion.
         ALCATEL NOTE:
         ACCESS:      NA           USAGE:       OPT
         PERSIST:     YES          INSRVMOD:    YES
         RANGE:       1..4         DEFVALUE:    1
         UNITS:       NA           SPARSE:      NO
         DESCR:       NA"
    ::= { lanxQosFlowEntry 2 }

lanxQosFlowVlanId OBJECT-TYPE
    SYNTAX      INTEGER (0..4096)
    ACCESS      read-write
    STATUS      mandatory
    DESCRIPTION 
        "The VLAN ID based on which the flow is detected. Default value of ZERO corresponds to 
         any VLAN ID based flow
            ALCATEL NOTE:
                ACCESS:      NA           USAGE:       OPT
                PERSIST:     YES          INSRVMOD:    YES
                RANGE:       0..4092      DEFVALUE:    NA
                UNITS:       NA           SPARSE:      NO
                DESCR:       NA"
    DEFVAL      { 0 }
    ::= { lanxQosFlowEntry 3 }

lanxQosFlowPriority OBJECT-TYPE
    SYNTAX      INTEGER (0..8)
    ACCESS      read-write
    STATUS      mandatory
    DESCRIPTION 
        "802.1 Priority is considered as one of the Flow detection parameter. When the value is set to EIGHT, 
         which implies any priority. For active Priority based flow configuration the valid range should be 
         from 0-7  which correspondingly maps to 0-7 in the packet
         ALCATEL NOTE:
             ACCESS:      NA           USAGE:       OPT
             PERSIST:     YES          INSRVMOD:    YES
             RANGE:       NA           DEFVALUE:    NA
             UNITS:       NA           SPARSE:      NO
             DESCR:       NA"
    DEFVAL      { 8 }
    ::= { lanxQosFlowEntry 4 }

lanxQosFlowDSCP OBJECT-TYPE
    SYNTAX      INTEGER (0..64)
    ACCESS      read-write
    STATUS      mandatory
    DESCRIPTION 
        "DSCP is considered as one of the Flow detection parameter. When the value is 
         set to SIXTYFOUR , which implies any code point. For active DSCP based flow configuration the 
         valid range should be from 0-63 which will correspondingly map to 0-63 in the packet 
         ALCATEL NOTE:
             ACCESS:      NA           USAGE:       OPT
             PERSIST:     YES          INSRVMOD:    YES
             RANGE:       NA           DEFVALUE:    NA
             UNITS:       NA           SPARSE:      NO
             DESCR:       NA"
    DEFVAL      { 64 }
    ::= { lanxQosFlowEntry 5 }

lanxQosFlowRefCount OBJECT-TYPE
    SYNTAX      INTEGER
    ACCESS      read-only
    STATUS      mandatory
    DESCRIPTION 
        "A counter to indicate the number of times the flow has been actually instantiated on any port. 
         ALCATEL NOTE:
             ACCESS:      NA           USAGE:       NA
             PERSIST:     NO           INSRVMOD:    NA
             RANGE:       NA           DEFVALUE:    0
             UNITS:       NA           SPARSE:      NO
             DESCR:       NA"
    ::= { lanxQosFlowEntry 6 }

lanxQosFlowName OBJECT-TYPE
    SYNTAX      DisplayString (SIZE(1..15))
    ACCESS      read-write
    STATUS      mandatory
    DESCRIPTION 
        "A name for the Flow entry. This is an optional parameter. 
         ALCATEL NOTE:
             ACCESS:      NA           USAGE:       OPT
             PERSIST:     YES          INSRVMOD:    YES
             RANGE:       NA           DEFVALUE:    '\0'
             UNITS:       NA           SPARSE:      NO
             DESCR:       NA"
    ::= { lanxQosFlowEntry 7 }

lanxQosFlowVersion OBJECT-TYPE
    SYNTAX      DisplayString (SIZE(1..15))
    ACCESS      read-write
    STATUS      mandatory
    DESCRIPTION 
        "A version no for the Flow entry. This parameter is optional 
         ALCATEL NOTE:
             ACCESS:      NA           USAGE:       OPT
             PERSIST:     YES          INSRVMOD:    YES
             RANGE:       NA           DEFVALUE:    '\0'
             UNITS:       NA           SPARSE:      NO
             DESCR:       NA"
    ::= { lanxQosFlowEntry 8 }

lanxQosFlowRowStatus OBJECT-TYPE
    SYNTAX      RowStatus
    ACCESS      read-write
    STATUS      mandatory
    DESCRIPTION 
        "Status of the Flow Entry. 'Active' state implies that the entry is ready to use. Only 'Active' entries can be          associated with a policer table. The Row status will have only foll. Values:
         1  -  active : To indicate entry is valid for use.
         4  - create and go : To create an entry and to set it to active
         6  - destroy : To delete a entry. 
         7  - Not_in service : To indicate that the entry is not used.
                ALCATEL NOTE:
                    ACCESS:      NA           USAGE:       MAND
                    PERSIST:     YES          INSRVMOD:    YES
                    RANGE:       1,2,4,5,6    DEFVALUE:    NA
                    UNITS:       NA           SPARSE:      NO
                    DESCR:       NA"
    ::= { lanxQosFlowEntry 9 }

lanxQosPolicerTable OBJECT-TYPE
    SYNTAX      SEQUENCE OF LanxQosPolicerEntry
    ACCESS      not-accessible
    STATUS      mandatory
    DESCRIPTION 
        "A table used to configure the policing association. It is indexed by the PortIndex as well as 
         the Flow Index. Multiple Ports can have same policer and same policer can be applied to 
         multiple ports. A list of Policers for each port is maintained as a part of Qos Port global database.
         ALCATEL NOTE:
             TABLESIZE:	 146
             DESCR:       NA"
    ::= { lanxQOSMIB 7 }

lanxQosPolicerEntry OBJECT-TYPE
    SYNTAX      LanxQosPolicerEntry
    ACCESS      not-accessible
    STATUS      mandatory
    DESCRIPTION 
        "QoS Policer Configuation entry
         Row creation : A QOS-POLICER entry shall be created in one step by a
         		      set-request with all necessary parameter values and
             		lanxQosPolicerRowStatus set to createAndGo(4).
         			One entry per port will be created by the System at the startup.
         Row deletion : A QOS-POLICER entry shall be deleted by setting
             		the lanxQosPolicerRowStatus of the specific entry to destroy(6).
         Index usage : the indexes are lanxQosPolicerPortIndex and lanxQosFlowIndex.
         Note that entries will be presented to the SNMP manager in full
         lexicographical order :  sorted on lanxQosPolicerPortIndex, then on lanxQosFlowIndex."
    INDEX       { lanxQosPolicerPortIndex, lanxQosFlowIndex }
    ::= { lanxQosPolicerTable 1 }

LanxQosPolicerEntry ::= SEQUENCE {
    lanxQosPolicerPortIndex     INTEGER,
    lanxQosPolicerMeterIndex    INTEGER,
    lanxQosPolicerRowStatus     RowStatus
}

lanxQosPolicerPortIndex OBJECT-TYPE
    SYNTAX      INTEGER (1..2147483647)
    ACCESS      not-accessible
    STATUS      mandatory
    DESCRIPTION 
        "LANX QoS port index
         ALCATEL NOTE:
             ACCESS:      NA           USAGE:       NA
             PERSIST:     YES          INSRVMOD:    NA
             RANGE:       DEP           DEFVALUE:    NA
             UNITS:       NA           SPARSE:      NO
             DESCR:       DEP(RANGE) The range is the maximum number of physical ports in the system.
         	    			    This value can be got from issSystemNumberOfPorts in fsiss.mib."
    ::= { lanxQosPolicerEntry 1 }

lanxQosPolicerMeterIndex OBJECT-TYPE
    SYNTAX      INTEGER (0..64)
    ACCESS      read-write
    STATUS      mandatory
    DESCRIPTION 
        "An index to an already created Meter Entry. Same meter entry could be used 
         shared by multiple policers if needed.
            ALCATEL NOTE:
                ACCESS:      NA          USAGE:       MAND
                PERSIST:     YES         INSRVMOD:    YES
                RANGE:       1..64       DEFVALUE:    NA
                UNITS:       NA          SPARSE:      NO
                DESCR:       NA"
    ::= { lanxQosPolicerEntry 2 }

lanxQosPolicerRowStatus OBJECT-TYPE
    SYNTAX      RowStatus
    ACCESS      read-write
    STATUS      mandatory
    DESCRIPTION 
        "Status of the Policer Entry. Only when the entry is made 'active' the corresponding 
         hardware resources are allocated.
         ALCATEL NOTE:
             ACCESS:      NA           USAGE:       MAND
             PERSIST:     YES          INSRVMOD:    YES
             RANGE:       1..6         DEFVALUE:    NA
             UNITS:       NA           SPARSE:      NO
             DESCR:       The Value 3 cannot be Set"
    ::= { lanxQosPolicerEntry 3 }

lanxQosMeterFreeIndex OBJECT-TYPE
    SYNTAX      INTEGER
    ACCESS      read-only
    STATUS      mandatory
    DESCRIPTION 
        "A index to indicate the next free entry in the MeterTable. Before performing a 'set' operation, a get is performed on this object and this value is used in the set  routine.
         ALCATEL NOTE:
             ACCESS:      NA           USAGE:       NA
             PERSIST:     NO           INSRVMOD:    NA
             RANGE:       1..64        DEFVALUE:    3
             UNITS:       NA           SPARSE:      NA
             DESCR:       NA"
    ::= { lanxQOSMIB 8 }

lanxQosFlowFreeIndex OBJECT-TYPE
    SYNTAX      INTEGER
    ACCESS      read-only
    STATUS      mandatory
    DESCRIPTION 
        "The next free index to the flow table. Before any set operation, a get is performed on this object and this value is used in the set routine.
         ALCATEL NOTE:
             ACCESS:      NA           USAGE:       NA
             PERSIST:     NO           INSRVMOD:    NA
             RANGE:       1..64        DEFVALUE:    2
             UNITS:       NA           SPARSE:      NA
             DESCR:       NA"
    ::= { lanxQOSMIB 9 }

lanxQosDSCPtoPbitMapTable OBJECT-TYPE
    SYNTAX      SEQUENCE OF LanxQosDSCPtoPbitMapEntry
    ACCESS      not-accessible
    STATUS      mandatory
    DESCRIPTION 
        "A table used to map DSCP values to Priority. Priority is a
         number in the range (0..(dot1dPortNumTrafficClasses-1)). There is only one
         DSCP to P-bits allignment table, common for all ports.
         ALCATEL NOTE:
             TABLESIZE:	 64
             DESCR:       NA"
    ::= { lanxQOSMIB 10 }

lanxQosDSCPtoPbitMapEntry OBJECT-TYPE
    SYNTAX      LanxQosDSCPtoPbitMapEntry
    ACCESS      not-accessible
    STATUS      mandatory
    DESCRIPTION 
        "DSCP to P-bit mapping.
         Row creation : All the Entries are created by the system at the startup.
         Row deletion : All the Entries are deleted by the system when it shutdowns.
         Index usage : the index is the lanxQosDSCPIndex.
         Note that entries will be presented to the SNMP manager in full
         lexicographical order :  sorted on lanxQosDSCPIndex."
    INDEX       { lanxQosDSCPIndex }
    ::= { lanxQosDSCPtoPbitMapTable 1 }

LanxQosDSCPtoPbitMapEntry ::= SEQUENCE {
    lanxQosDSCPIndex        INTEGER,
    lanxQosDSCPPriority     INTEGER
}

lanxQosDSCPIndex OBJECT-TYPE
    SYNTAX      INTEGER (0..63)
    ACCESS      not-accessible
    STATUS      mandatory
    DESCRIPTION 
        "The DSCP value in the IP frame. For all IP frames the 
         LANX looks up the DSCP field and alters the outgoing 
         P-bits as well as the internal priority based on the 
         DSCP_TABLE internal registers when DSCP to Pbit allignment 
         is enabled on the port.
         ALCATEL NOTE:
             ACCESS:      NA           USAGE:       NA
             PERSIST:     YES          INSRVMOD:    NA
             RANGE:       NA           DEFVALUE:    NA
             UNITS:       NA           SPARSE:      NO
             DESCR:       NA"
    ::= { lanxQosDSCPtoPbitMapEntry 1 }

lanxQosDSCPPriority OBJECT-TYPE
    SYNTAX      INTEGER (0..7)
    ACCESS      read-write
    STATUS      mandatory
    DESCRIPTION 
        "The Priority the received frame is mapped to.
         ALCATEL NOTE:
             ACCESS:      NA           		USAGE:       NA
             PERSIST:     YES          		INSRVMOD:    YES
             RANGE:       NA			DEFVALUE:    (lanxQosDSCPIndex/8)
             UNITS:       NA           		SPARSE:      NO
             DESCR:       NA"
    ::= { lanxQosDSCPtoPbitMapEntry 2 }

END -- end of module QOS-MIB.
