--
-- This SMIv1 module has been generated by smidump 0.4.8. Do not edit.
--

RSTP-MIB DEFINITIONS ::= BEGIN

IMPORTS
    dot1dBridge, dot1dStp
        FROM BRIDGE-MIB
    OBJECT-TYPE
        FROM RFC-1212
    Counter, Gauge, TimeTicks
        FROM RFC1155-SMI
    mib-2
        FROM RFC1213-MIB
    TruthValue
        FROM SNMPv2-TC;

rstpMIB OBJECT IDENTIFIER
    ::= { dot1dBridge 11 }

-- rstpMIB MODULE-IDENTITY
--     LAST-UPDATED "200111160000Z"
--     ORGANIZATION 
--         "IETF Bridge MIB Working Group"
--     CONTACT-INFO 
--         "Email: Bridge-mib@ietf.org"
--     DESCRIPTION 
--         "The Bridge MIB Extension module for managing devices
--          that support the Rapid Spanning Tree Protocol defined
--           by IEEE 802.1w."
--     REVISION    "200111160000Z"
--     DESCRIPTION 
--         "Draft 1"
--     ::= { dot1dBridge 11 }


BridgeId ::=
    OCTET STRING (SIZE(8))

-- BridgeId ::= TEXTUAL-CONVENTION
--     STATUS      mandatory
--     DESCRIPTION 
--         " Identifier of Bridge in 8 byte format"
--     SYNTAX      OCTET STRING (SIZE(8))

Timeout ::=
    INTEGER

-- Timeout ::= TEXTUAL-CONVENTION
--     DISPLAY-HINT "d4"
--     STATUS      mandatory
--     DESCRIPTION 
--         " Time out value in 4 byte"
--     SYNTAX      INTEGER

dot1dStpProtocolSpecification OBJECT-TYPE
    SYNTAX      INTEGER { unknown(1), decLb100(2), ieee8021d(3) }
    ACCESS      read-only
    STATUS      mandatory
    DESCRIPTION 
        "An indication of what version of the Spanning
         Tree Protocol is being run.  The value
         'ieee8021d (3)' indicates the IEEE 802.1d
         Spanning Tree protocol.
         ALCATEL NOTE:
         ACCESS:      NA            USAGE:       NA
         PERSIST:     NO            INSRVMOD:    NA
         RANGE:       NA            DEFVALUE:    ieee8021d(3)
         UNITS:       NA            SPARSE:      NA
         DESCR:       NA"
    ::= { dot1dStp 1 }

dot1dStpPriority OBJECT-TYPE
    SYNTAX      INTEGER (0..61440)
    ACCESS      read-write
    STATUS      mandatory
    DESCRIPTION 
        "The value of the write-able portion of the Bridge
         ID, i.e., the first two octets of the (8 octet
         long) Bridge ID.  The other (last) 6 octets of the
         Bridge ID are given by the value of
         dot1dBaseBridgeAddress.
         
         The values that are set for Bridge Priority must be 
         in steps of 4096.
         ALCATEL NOTE:
         ACCESS:      NA             USAGE:       NA
         PERSIST:     YES            INSRVMOD:    YES
         RANGE:       NA             DEFVALUE:    NA
         UNITS:       NA             SPARSE:      NA
         DESCR:       NA"
--     REFERENCE   
--         "P802.1d/D9, July 14, 1989: Section 4.5.3.7 - 
--          Modified description based on 802.1w-2001: Section 9.2.5"
    DEFVAL      { 32768 }
    ::= { dot1dStp 2 }

dot1dStpTimeSinceTopologyChange OBJECT-TYPE
    SYNTAX      TimeTicks
    ACCESS      read-only
    STATUS      mandatory
    DESCRIPTION 
        "The time (in hundredths of a second) since the
         TcWhile Timer for any port in this Bridge was 
         non-zero.
         ALCATEL NOTE:
         ACCESS:      NA            			USAGE:       NA
         PERSIST:     NO            			INSRVMOD:    NA
         RANGE:       NA           		                    DEFVALUE:    0 hours,0 minites,0 seconds            
         UNITS:       hundredths of a second                     SPARSE:      NA
         DESCR:       NA"
--     REFERENCE   
--         "P802.1d/D9, July 14, 1989: Section 6.8.1.1.3"
    ::= { dot1dStp 3 }

dot1dStpTopChanges OBJECT-TYPE
    SYNTAX      Counter
    ACCESS      read-only
    STATUS      mandatory
    DESCRIPTION 
        "The number of times that there have been atleast
         one non-zero TcWhile Timer on this Bridge.
         ALCATEL NOTE:
         ACCESS:      NA           USAGE:       NA
         PERSIST:     NO           INSRVMOD:    NA
         RANGE:       NA           DEFVALUE:    0
         UNITS:       NA           SPARSE:      NA
         DESCR:       NA"
--     REFERENCE   
--         "P802.1d/D9, July 14, 1989: Section 6.8.1.1.3"
    ::= { dot1dStp 4 }

dot1dStpDesignatedRoot OBJECT-TYPE
    SYNTAX      BridgeId
    ACCESS      read-only
    STATUS      mandatory
    DESCRIPTION 
        "The bridge identifier of the root of the spanning
         tree as determined by the Spanning Tree Protocol
         as executed by this node.  This value is used as
         the Root Identifier parameter in all Configuration
         Bridge PDUs originated by this node.
         ALCATEL NOTE:
         ACCESS:      NA            USAGE:       NA
         PERSIST:     NO            INSRVMOD:    NA
         RANGE:       NA            DEFVALUE:    0
         UNITS:       NA            SPARSE:      NA
         DESCR:       NA"
--     REFERENCE   
--         "P802.1d/D9, July 14, 1989: Section 4.5.3.1"
    ::= { dot1dStp 5 }

dot1dStpRootCost OBJECT-TYPE
    SYNTAX      INTEGER
    ACCESS      read-only
    STATUS      mandatory
    DESCRIPTION 
        "The cost of the path to the root as seen from
         this bridge.
         ALCATEL NOTE:
         ACCESS:      NA            USAGE:       NA
         PERSIST:     NO            INSRVMOD:    NA
         RANGE:       NA            DEFVALUE:    0
         UNITS:       NA            SPARSE:      NA
         DESCR:       NA"
--     REFERENCE   
--         "P802.1d/D9, July 14, 1989: Section 4.5.3.2"
    ::= { dot1dStp 6 }

dot1dStpRootPort OBJECT-TYPE
    SYNTAX      INTEGER
    ACCESS      read-only
    STATUS      mandatory
    DESCRIPTION 
        "The port number of the port which offers the
         lowest cost path from this bridge to the root
         bridge.
         ALCATEL NOTE:
         ACCESS:      NA            USAGE:       NA
         PERSIST:     NO            INSRVMOD:    NA
         RANGE:       NA            DEFVALUE:    0
         UNITS:       NA            SPARSE:      NA
         DESCR:       NA"
--     REFERENCE   
--         "P802.1d/D9, July 14, 1989: Section 4.5.3.3"
    ::= { dot1dStp 7 }

dot1dStpMaxAge OBJECT-TYPE
    SYNTAX      Timeout
    ACCESS      read-only
    STATUS      mandatory
    DESCRIPTION 
        "The maximum age of Spanning Tree Protocol
         information learned from the network on any port
         before it is discarded, in units of hundredths of
         a second.  This is the actual value that this
         bridge is currently using.
         ALCATEL NOTE:
         ACCESS:      NA           		 USAGE:       NA
         PERSIST:     NO            		 INSRVMOD:    NA
         RANGE:       NA            		 DEFVALUE:    2000                 
         UNITS:       hundredths of second       SPARSE:      NA
         DESCR:       NA"
--     REFERENCE   
--         "P802.1d/D9, July 14, 1989: Section 4.5.3.4"
    ::= { dot1dStp 8 }

dot1dStpHelloTime OBJECT-TYPE
    SYNTAX      Timeout
    ACCESS      read-only
    STATUS      mandatory
    DESCRIPTION 
        "The amount of time between the transmission of
         Configuration bridge PDUs by this node on any port
         when it is the root of the spanning tree or trying
         to become so, in units of hundredths of a second.
         This is the actual value that this bridge is
         currently using.
         ALCATEL NOTE:
         ACCESS:      NA           		 USAGE:       NA
         PERSIST:     NO           		 INSRVMOD:    NA
         RANGE:       NA        	   	 DEFVALUE:    200            
         UNITS:        hundredths of second     SPARSE:      NA
         DESCR:       NA"
--     REFERENCE   
--         "P802.1d/D9, July 14, 1989: Section 4.5.3.5"
    ::= { dot1dStp 9 }

dot1dStpHoldTime OBJECT-TYPE
    SYNTAX      INTEGER
    ACCESS      read-only
    STATUS      mandatory
    DESCRIPTION 
        "This time value determines the interval length
         during which no more than two Configuration bridge
         PDUs shall be transmitted by this node, in units
         of hundredths of a second.
         ALCATEL NOTE:
         ACCESS:      NA         			     USAGE:       NA
         PERSIST:     NO            			     INSRVMOD:    NA
         RANGE:       NA                                DEFVALUE:    100                    
         UNITS:       hundredths of a second            SPARSE:      NA
         DESCR:       NA"
--     REFERENCE   
--         "P802.1d/D9, July 14, 1989: Section 4.5.3.14"
    ::= { dot1dStp 10 }

dot1dStpForwardDelay OBJECT-TYPE
    SYNTAX      Timeout
    ACCESS      read-only
    STATUS      mandatory
    DESCRIPTION 
        "This time value, measured in units of hundredths
         of a second, controls how fast a port changes its
         spanning state when moving towards the Forwarding
         state.  The value determines how long the port
         stays in a particular state before moving to the
         next state.  For example, how long a port stays in
         the Listening state when moving from Blocking to
         Learning.  This value is also used, when a
         topology change has been detected and is underway,
         to age all dynamic entries in the Forwarding
         Database.  [Note that this value is the one that
         this bridge is currently using, in contrast to
         dot1dStpBridgeForwardDelay which is the value that
         this bridge and all others would start using
         if/when this bridge were to become the root.
         ALCATEL NOTE:
         ACCESS:      NA            			  USAGE:       NA
         PERSIST:     NO            			  INSRVMOD:    NA
         RANGE:       NA           			  DEFVALUE:    1500
         UNITS:       hundredths of a second         SPARSE:      NA                          
         DESCR:       NA"
--     REFERENCE   
--         "P802.1d/D9, July 14, 1989: Section 4.5.3.6"
    ::= { dot1dStp 11 }

dot1dStpBridgeMaxAge OBJECT-TYPE
    SYNTAX      Timeout (600..4000)
    ACCESS      read-write
    STATUS      mandatory
    DESCRIPTION 
        "The value that all bridges use for MaxAge when
         this bridge is acting as the root.  Note that
         802.1d/D9 specifies that the range for this
         parameter is related to the value of
         dot1dStpBridgeHelloTime. The granularity of this
         timer is specified by 802.1d/D9 to be 1 second.
         An agent may return a badValue error if a set is
         attempted to a value which is not a whole number
         of seconds.
         ALCATEL NOTE:
         ACCESS:      NA            USAGE:       NA
         PERSIST:     YES           INSRVMOD:    YES
         RANGE:       NA            DEFVALUE:    NA
         UNITS:       seconds       SPARSE:      NA                         
         DESCR:       NA"
--     REFERENCE   
--         "P802.1d/D9, July 14, 1989: Section 4.5.3.8"
    DEFVAL      { 2000 }
    ::= { dot1dStp 12 }

dot1dStpBridgeHelloTime OBJECT-TYPE
    SYNTAX      Timeout (100..1000)
    ACCESS      read-write
    STATUS      mandatory
    DESCRIPTION 
        "The value that all bridges use for HelloTime when
         this bridge is acting as the root.  The
         granularity of this timer is specified by
         802.1d/D9 to be 1 second.  An agent may return a
         badValue error if a set is attempted to a value
         which is not a whole number of seconds.
         ALCATEL NOTE:
         ACCESS:      NA            USAGE:       NA
         PERSIST:     YES           INSRVMOD:    YES
         RANGE:       NA            DEFVALUE:    NA
         UNITS:       seconds       SPARSE:      NA                  
         DESCR:       NA"
--     REFERENCE   
--         "P802.1d/D9, July 14, 1989: Section 4.5.3.9"
    DEFVAL      { 200 }
    ::= { dot1dStp 13 }

dot1dStpBridgeForwardDelay OBJECT-TYPE
    SYNTAX      Timeout (400..3000)
    ACCESS      read-write
    STATUS      mandatory
    DESCRIPTION 
        "The value that all bridges use for ForwardDelay
         when this bridge is acting as the root.  Note that
         802.1d/D9 specifies that the range for this
         parameter is related to the value of
         dot1dStpBridgeMaxAge.  The granularity of this
         timer is specified by 802.1d/D9 to be 1 second.
         An agent may return a badValue error if a set is
         attempted to a value which is not a whole number
         of seconds.
         ALCATEL NOTE:
         ACCESS:      NA            USAGE:       NA
         PERSIST:     YES           INSRVMOD:    YES
         RANGE:       NA            DEFVALUE:    NA
         UNITS:       seconds       SPARSE:      NA                    
         DESCR:       NA"
--     REFERENCE   
--         "P802.1d/D9, July 14, 1989: Section 4.5.3.10"
    DEFVAL      { 1500 }
    ::= { dot1dStp 14 }

dot1dStpPortTable OBJECT-TYPE
    SYNTAX      SEQUENCE OF Dot1dStpPortEntry
    ACCESS      not-accessible
    STATUS      mandatory
    DESCRIPTION 
        "A table that contains port-specific information
         for the Spanning Tree Protocol.
         ALCATEL NOTE:
         TABLESIZE: DEP
         DESCR:  DEP(TABLESIZE)The table size is the maximum number of ports in the system. This 
         		   value can be got from the object issSystemNumberOfPorts from fsiss.mib.  "
    ::= { dot1dStp 15 }

dot1dStpPortEntry OBJECT-TYPE
    SYNTAX      Dot1dStpPortEntry
    ACCESS      not-accessible
    STATUS      mandatory
    DESCRIPTION 
        "A list of information maintained by every port
         about the Spanning Tree Protocol state for that
         port.
         	 Row creation : All entries will be created when a RSTP module is
         		enabled.
         Row deletion : All entries will be deleted when a RSTP module is
            	   disabled.
         Index usage : The index is the Stp Port.
         lexicographical order :  Sorted on Stp Port"
    INDEX       { dot1dStpPort }
    ::= { dot1dStpPortTable 1 }

Dot1dStpPortEntry ::= SEQUENCE {
    dot1dStpPort                    INTEGER,
    dot1dStpPortPriority            INTEGER,
    dot1dStpPortState               INTEGER,
    dot1dStpPortEnable              INTEGER,
    dot1dStpPortPathCost            INTEGER,
    dot1dStpPortDesignatedRoot      BridgeId,
    dot1dStpPortDesignatedCost      INTEGER,
    dot1dStpPortDesignatedBridge    BridgeId,
    dot1dStpPortDesignatedPort      OCTET STRING,
    dot1dStpPortForwardTransitions  Counter
}

dot1dStpPort OBJECT-TYPE
    SYNTAX      INTEGER (1..65535)
    ACCESS      not-accessible
    STATUS      mandatory
    DESCRIPTION 
        "The port number of the port for which this entry contains 				
         Spanning Tree Protocol management information.
         ALCATEL NOTE:
              ACCESS:      NA           USAGE:       NA
              PERSIST:     YES          INSRVMOD:    NA
              RANGE:       DEP          DEFVALUE:    NA
              UNITS:       NA              SPARSE:      NO
         	    DESCR:       DEP(RANGE):The range of the index is from 1 to the maximum number of physical interfaces available in the system. 
         			 This is obtained from the object issSystemNumberOfPorts in fsiss.mib"
--     REFERENCE   
--         "IEEE 802.1D-1990: Section 6.8.2.1.2"
    ::= { dot1dStpPortEntry 1 }

dot1dStpPortPriority OBJECT-TYPE
    SYNTAX      INTEGER (0..240)
    ACCESS      read-write
    STATUS      mandatory
    DESCRIPTION 
        "The value of the priority field which is contained 
         in the first (in network byte order) octet of the 
         (2 octet long) Port ID.
         
         The values that are set for Port Priority must be 
         in steps of 16.
         ALCATEL NOTE:
         ACCESS:      NA           USAGE:       NA
         PERSIST:     YES          INSRVMOD:    YES
         RANGE:       NA           DEFVALUE:    NA
         UNITS:       NA           SPARSE:      NO
         DESCR:       NA"
--     REFERENCE   
--         "P802.1d/D9, July 14, 1989: Section 4.5.5.1 - 
--          Modified description based on 802.1w-2001: Section 9.2.7"
    DEFVAL      { 128 }
    ::= { dot1dStpPortEntry 2 }

dot1dStpPortState OBJECT-TYPE
    SYNTAX      INTEGER { disabled(1), blocking(2), listening(3), 
                    learning(4), forwarding(5), broken(6) }
    ACCESS      read-only
    STATUS      mandatory
    DESCRIPTION 
        "The port's current state as defined by
         application of the Spanning Tree Protocol.  This
         state controls what action a port takes on
         reception of a frame.  If the bridge has detected
         a port that is malfunctioning it will place that
         port into the broken(6) state.  
         
         For ports which are disabled (i.e 
         dot1dBasePortAdminStatus is set to down), this object
         will have a value of disabled(1).
         
         For Ports involved in RSTP, port states 'blocking' and
         'listening' have been merged to the 'Discarding' state.
         ALCATEL NOTE:
         ACCESS:      NA           USAGE:       NA
         PERSIST:     NO          INSRVMOD:    NA
         RANGE:       NA           DEFVALUE:    blocking(2)        
         UNITS:       NA           SPARSE:      NO
         DESCR:       NA"
--     REFERENCE   
--         "P802.1d/D9, July 14, 1989: Section 4.5.5.2"
    ::= { dot1dStpPortEntry 3 }

dot1dStpPortEnable OBJECT-TYPE
    SYNTAX      INTEGER { enabled(1), disabled(2) }
    ACCESS      read-write
    STATUS      mandatory
    DESCRIPTION 
        "The enabled/disabled status of the port.
         ALCATEL NOTE:
             ACCESS:      NA           USAGE:       NA
             PERSIST:     YES          INSRVMOD:    YES
             RANGE:       NA           DEFVALUE:    disabled(2)                     
             UNITS:       NA           SPARSE:      NO
             DESCR:       NA"
--     REFERENCE   
--         "IEEE 802.1D-1990: Section 4.5.5.2"
    ::= { dot1dStpPortEntry 4 }

dot1dStpPortPathCost OBJECT-TYPE
    SYNTAX      INTEGER (1..200000000)
    ACCESS      read-write
    STATUS      mandatory
    DESCRIPTION 
        "The contribution of this port to the path cost of
         paths towards the spanning tree root which include
         this port.
         ALCATEL NOTE:
         ACCESS:      NA           USAGE:       NA
         PERSIST:     YES          INSRVMOD:    YES
         RANGE:       NA           DEFVALUE:    20000
         UNITS:       NA           SPARSE:      NO
         DESCR:       NA"
--     REFERENCE   
--         "P802.1d/D9, July 14, 1989: Section 4.5.5.3 - 
--          Modified description based on 802.1w-2001: Section 17.28.2,
--          Table 17-7"
    ::= { dot1dStpPortEntry 5 }

dot1dStpPortDesignatedRoot OBJECT-TYPE
    SYNTAX      BridgeId
    ACCESS      read-only
    STATUS      mandatory
    DESCRIPTION 
        "The unique Bridge Identifier of the Bridge
         recorded as the Root in the Configuration BPDUs
         transmitted by the Designated Bridge for the
         segment to which the port is attached.
         ALCATEL NOTE:
         ACCESS:      NA           USAGE:       NA
         PERSIST:     NO          INSRVMOD:    NA
         RANGE:       NA           DEFVALUE:    0
         UNITS:       NA           SPARSE:      NO
         DESCR:       NA"
--     REFERENCE   
--         "P802.1d/D9, July 14, 1989: Section 4.5.5.4"
    ::= { dot1dStpPortEntry 6 }

dot1dStpPortDesignatedCost OBJECT-TYPE
    SYNTAX      INTEGER
    ACCESS      read-only
    STATUS      mandatory
    DESCRIPTION 
        "The path cost of the Designated Port of the
         segment connected to this port.  This value is
         compared to the Root Path Cost field in received
         bridge PDUs.
         ALCATEL NOTE:
         ACCESS:      NA           USAGE:       NA
         PERSIST:     NO          INSRVMOD:    NA
         RANGE:       NA           DEFVALUE:    0
         UNITS:       NA           SPARSE:      NO
         DESCR:       NA"
--     REFERENCE   
--         "P802.1d/D9, July 14, 1989: Section 4.5.5.5"
    ::= { dot1dStpPortEntry 7 }

dot1dStpPortDesignatedBridge OBJECT-TYPE
    SYNTAX      BridgeId
    ACCESS      read-only
    STATUS      mandatory
    DESCRIPTION 
        "The Bridge Identifier of the bridge which this
         port considers to be the Designated Bridge for
         this port's segment.
         ALCATEL NOTE:
         ACCESS:      NA           USAGE:       NA
         PERSIST:     NO          INSRVMOD:    NA
         RANGE:       NA           DEFVALUE:   0
         UNITS:       NA           SPARSE:      NO
         DESCR:       NA"
--     REFERENCE   
--         "P802.1d/D9, July 14, 1989: Section 4.5.5.6"
    ::= { dot1dStpPortEntry 8 }

dot1dStpPortDesignatedPort OBJECT-TYPE
    SYNTAX      OCTET STRING (SIZE(2))
    ACCESS      read-only
    STATUS      mandatory
    DESCRIPTION 
        "The Port Identifier of the port on the Designated
         Bridge for this port's segment.
         ALCATEL NOTE:
         ACCESS:      NA           USAGE:       NA
         PERSIST:     NO          INSRVMOD:    NA
         RANGE:       NA           DEFVALUE:    0
         UNITS:       NA           SPARSE:      NO
         DESCR:       NA"
--     REFERENCE   
--         "P802.1d/D9, July 14, 1989: Section 4.5.5.7"
    ::= { dot1dStpPortEntry 9 }

dot1dStpPortForwardTransitions OBJECT-TYPE
    SYNTAX      Counter
    ACCESS      read-only
    STATUS      mandatory
    DESCRIPTION 
        "The number of times this port has transitioned
         from the Learning state to the Forwarding state.
         ALCATEL NOTE:
         ACCESS:      NA                   USAGE:       NA
         PERSIST:     NO                   INSRVMOD:    NA                  
         RANGE:       NA                   DEFVALUE:    0
         UNITS:       NA                   SPARSE:      NO                   
         DESCR:       NA"
    ::= { dot1dStpPortEntry 10 }

dot1dStpVersion OBJECT-TYPE
    SYNTAX      INTEGER { stpCompatible(0), rstp(2) }
    ACCESS      read-write
    STATUS      mandatory
    DESCRIPTION 
        "The version of Spanning Tree Protocol the bridge is
         currently running.  The value 'stpCompatible(0)'
         indicates the Spanning Tree Protocol specified in
         IEEE 802.1D and 'rstp(2)' indicates the Rapid Spanning
         Tree Protocol specified in IEEE 802.1w.  New value may
         be defined as future versions of the protocol become
         available.
         ALCATEL NOTE:
            ACCESS:      NA            USAGE:       NA
            PERSIST:     YES           INSRVMOD:    YES
            RANGE:       NA            DEFVALUE:    NA          
            UNITS:       NA            SPARSE:      NA
            DESCR:       NA"
--     REFERENCE   
--         "IEEE 802.1w clause 14.8.1, 17.12, 17.16.1"
    DEFVAL      { rstp }
    ::= { dot1dStp 16 }

dot1dStpTxHoldCount OBJECT-TYPE
    SYNTAX      INTEGER (1..10)
    ACCESS      read-write
    STATUS      mandatory
    DESCRIPTION 
        "The value used by the Port Transmit state machine to limit
         the maximum transmission rate.
         ALCATEL NOTE:
            ACCESS:      NA            USAGE:       NA
            PERSIST:     YES           INSRVMOD:    YES
            RANGE:       NA            DEFVALUE:    NA
            UNITS:       NA            SPARSE:      NA
            DESCR:       NA"
--     REFERENCE   
--         "IEEE 802.1w clause 17.16.6"
    DEFVAL      { 3 }
    ::= { dot1dStp 17 }

dot1dStpPathCostDefault OBJECT-TYPE
    SYNTAX      INTEGER { stp8021d1998(1), stp8021t2001(2) }
    ACCESS      read-write
    STATUS      mandatory
    DESCRIPTION 
        "The version of the Spanning Tree default Path Costs that
         are to be used by this Bridge.  A value of 8021d1998(1)
         uses the 16-bit default Path Costs from IEEE Std. 802.1D-1998.
         A value of stp8021t2001(2) uses the 32-bit default Path
         Costs from IEEE Std. 802.1t.
         ALCATEL NOTE:
            ACCESS:      NA            USAGE:       NA
            PERSIST:     YES           INSRVMOD:    YES
            RANGE:       NA            DEFVALUE:   stp8021t2001 (2)
            UNITS:       NA            SPARSE:      NA
            DESCR:       NA"
--     REFERENCE   
--         "IEEE 802.1D & 802.1t Table 8-5"
    ::= { dot1dStp 18 }

dot1dStpExtPortTable OBJECT-TYPE
    SYNTAX      SEQUENCE OF Dot1dStpExtPortEntry
    ACCESS      not-accessible
    STATUS      mandatory
    DESCRIPTION 
        "A table that contains port-specific Rapid Spanning Tree
         information.
         ALCATEL NOTE:
             	TABLESIZE: NA 
            DESCR:	This object is not used by Alcatel"
    ::= { dot1dStp 19 }

dot1dStpExtPortEntry OBJECT-TYPE
    SYNTAX      Dot1dStpExtPortEntry
    ACCESS      not-accessible
    STATUS      mandatory
    DESCRIPTION 
        "A list of Rapid Spanning Tree information maintained by
         each port.
         Row creation : NA
         Row deletion : NA
         Index usage : NA
         lexicographical order :  NA
         This object is not used by Alcatel"
    INDEX       { dot1dStpPort }
    ::= { dot1dStpExtPortTable 1 }

Dot1dStpExtPortEntry ::= SEQUENCE {
    dot1dStpPortProtocolMigration   TruthValue,
    dot1dStpPortAdminEdgePort       TruthValue,
    dot1dStpPortOperEdgePort        TruthValue,
    dot1dStpPortAdminPointToPoint   INTEGER,
    dot1dStpPortOperPointToPoint    TruthValue
}

dot1dStpPortProtocolMigration OBJECT-TYPE
    SYNTAX      TruthValue
    ACCESS      read-write
    STATUS      mandatory
    DESCRIPTION 
        "When operating in RSTP (version 2) mode, writing TRUE(1)
         to this object forces this port to transmit RSTP BPDUs.
         Any other operation on this object has no effect and
         it always returns FALSE(2) when read.
         ALCATEL NOTE:
            ACCESS:      NA           USAGE:       NA
            PERSIST:     NA           INSRVMOD:    NA
            RANGE:       NA           DEFVALUE:    NA
            UNITS:       NA           SPARSE:      NA
            DESCR:       This object is not used by Alcatel"
--     REFERENCE   
--         "IEEE 802.1w clause 14.8.2.4, 17.18.10, 17.26"
    ::= { dot1dStpExtPortEntry 1 }

dot1dStpPortAdminEdgePort OBJECT-TYPE
    SYNTAX      TruthValue
    ACCESS      read-write
    STATUS      mandatory
    DESCRIPTION 
        "The administrative value of the Edge Port parameter.  A
         value of TRUE(1) indicates that this port should be
         assumed as an edge-port and a value of FALSE(2) indicates
         that this port should be assumed as a non-edge-port.
         ALCATEL NOTE:
            ACCESS:      NA           USAGE:       NA
            PERSIST:     NA           INSRVMOD:    NA
            RANGE:       NA           DEFVALUE:    NA
            UNITS:       NA           SPARSE:      NA
            DESCR:       This object is not used by Alcatel"
--     REFERENCE   
--         "IEEE 802.1t clause 14.8.2, 18.3.3"
    ::= { dot1dStpExtPortEntry 2 }

dot1dStpPortOperEdgePort OBJECT-TYPE
    SYNTAX      TruthValue
    ACCESS      read-only
    STATUS      mandatory
    DESCRIPTION 
        "The operational value of the Edge Port parameter.  The
         object is initialized to the value of
         dot1dStpPortAdminEdgePort and is set FALSE on reception of
         a BPDU.
         ALCATEL NOTE:
            ACCESS:      NA           USAGE:       NA
            PERSIST:     NA           INSRVMOD:    NA
            RANGE:       NA           DEFVALUE:    NA
            UNITS:       NA           SPARSE:      NA
            DESCR:       This object is not used by Alcatel"
--     REFERENCE   
--         "IEEE 802.1t clause 14.8.2, 18.3.4"
    ::= { dot1dStpExtPortEntry 3 }

dot1dStpPortAdminPointToPoint OBJECT-TYPE
    SYNTAX      INTEGER { forceTrue(0), forceFalse(1), auto(2) }
    ACCESS      read-write
    STATUS      mandatory
    DESCRIPTION 
        "The administrative point-to-point status of the LAN segment
         attached to this port.  A value of forceTrue(0) indicates that
         this port should always be treated as if it is connected to
         a point-to-point link.  A value of forceFalse(1) indicates
         that this port should be treated as having a shared media
         connection.  A value of auto(2) indicates that this port is
         considered to have a point-to-point link if it is an Aggregator
         and all of its members are aggregatable, or if the MAC entity
         is configured for full duplex operation, either through
         auto-negotiation or by management means.
         ALCATEL NOTE:
            ACCESS:      NA           USAGE:       NA
            PERSIST:     NA           INSRVMOD:    NA
            RANGE:       NA           DEFVALUE:    NA
            UNITS:       NA           SPARSE:      NA
            DESCR:       This object is not used by Alcatel"
--     REFERENCE   
--         "IEEE 802.1w clause 6.4.3, 6.5, 14.8.2"
    ::= { dot1dStpExtPortEntry 4 }

dot1dStpPortOperPointToPoint OBJECT-TYPE
    SYNTAX      TruthValue
    ACCESS      read-only
    STATUS      mandatory
    DESCRIPTION 
        "The operational point-to-point status of the LAN segment
         attached to this port.  It indicates whether a port is
         considered to have a point-to-point connection or not.
         The value is determined by management or by auto-detection,
         as described in the dot1dStpPortAdminPointToPoint object."
--     REFERENCE   
--         "IEEE 802.1w clause 6.4.3, 6.5, 14.8.2
--          ALCATEL NOTE:
--          ACCESS:      NA           USAGE:       NA
--          PERSIST:     NA           INSRVMOD:    NA
--          RANGE:       NA           DEFVALUE:    NA
--          UNITS:       NA           SPARSE:      NA
--          DESCR:       This object is not used by Alcatel"
    ::= { dot1dStpExtPortEntry 5 }

END -- end of module RSTP-MIB.
