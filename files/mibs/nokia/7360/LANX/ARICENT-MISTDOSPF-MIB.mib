--
-- This SMIv1 module has been generated by smidump 0.4.8. Do not edit.
--

ARICENT-MISTDOSPF-MIB DEFINITIONS ::= BEGIN

IMPORTS
    InterfaceIndex
        FROM IF-MIB
    OBJECT-TYPE
        FROM RFC-1212
    Counter, Gauge, IpAddress, enterprises
        FROM RFC1155-SMI
    RowStatus, TruthValue
        FROM SNMPv2-TC;

fsMIStdOspf OBJECT IDENTIFIER
    ::= { enterprises futuresoftware(2076) 146 }

-- fsMIStdOspf MODULE-IDENTITY
--     LAST-UPDATED "200702230000Z"
--     ORGANIZATION 
--         "ARICENT COMMUNICATIONS SOFTWARE"
--     CONTACT-INFO 
--         "ARICENT COMMUNICATIONS SOFTWARE
--          3460 Hillview Avenue,
--          Palo Alto, CA 94304-1388, USA,
--          Phone : +1-650-391-1088
--          E-mail:support@aricent.com"
--     DESCRIPTION 
--         "The enterprise ID 2076 was originally assigned to Future Software Pvt Limited.
--          Future Software is a part of Aricent."
--     REVISION    "200702230000Z"
--     DESCRIPTION 
--         "The Aricent Proprietary OSPFMI MIB modified from STDOSPF MIB"
--     ::= { enterprises futuresoftware(2076) 146 }


AreaID ::=
    IpAddress

-- AreaID ::= TEXTUAL-CONVENTION
--     STATUS      mandatory
--     DESCRIPTION 
--         "An OSPF Area Identifier."
--     SYNTAX      IpAddress

RouterID ::=
    IpAddress

-- RouterID ::= TEXTUAL-CONVENTION
--     STATUS      mandatory
--     DESCRIPTION 
--         "A OSPF Router Identifier."
--     SYNTAX      IpAddress

Metric ::=
    INTEGER (0..65535)

-- Metric ::= TEXTUAL-CONVENTION
--     DISPLAY-HINT "d"
--     STATUS      mandatory
--     DESCRIPTION 
--         "The OSPF Internal Metric."
--     SYNTAX      INTEGER (0..65535)

BigMetric ::=
    INTEGER (0..16777215)

-- BigMetric ::= TEXTUAL-CONVENTION
--     DISPLAY-HINT "d"
--     STATUS      mandatory
--     DESCRIPTION 
--         "The OSPF External Metric."
--     SYNTAX      INTEGER (0..16777215)

Status ::=
    INTEGER { enabled(1), disabled(2) }

-- Status ::= TEXTUAL-CONVENTION
--     STATUS      mandatory
--     DESCRIPTION 
--         "The status of an interface: 'enabled' indicates that
--          it is willing to communicate with other OSPF Routers,
--          while 'disabled' indicates that it is not."
--     SYNTAX      INTEGER
--                   { enabled(1), disabled(2) }

PositiveInteger ::=
    INTEGER (0..2147483647)

-- PositiveInteger ::= TEXTUAL-CONVENTION
--     DISPLAY-HINT "d"
--     STATUS      mandatory
--     DESCRIPTION 
--         "A positive integer. Values in excess are precluded as
--          unnecessary and prone to interoperability issues."
--     SYNTAX      INTEGER (0..2147483647)

HelloRange ::=
    INTEGER (1..65535)

-- HelloRange ::= TEXTUAL-CONVENTION
--     DISPLAY-HINT "d"
--     STATUS      mandatory
--     DESCRIPTION 
--         "The range of intervals on which hello messages are
--          exchanged."
--     SYNTAX      INTEGER (1..65535)

UpToMaxAge ::=
    INTEGER (0..3600)

-- UpToMaxAge ::= TEXTUAL-CONVENTION
--     DISPLAY-HINT "d"
--     STATUS      mandatory
--     DESCRIPTION 
--         "The values that one might find or configure for
--          variables bounded by the maximum age of an LSA."
--     SYNTAX      INTEGER (0..3600)

DesignatedRouterPriority ::=
    INTEGER (0..255)

-- DesignatedRouterPriority ::= TEXTUAL-CONVENTION
--     DISPLAY-HINT "d"
--     STATUS      mandatory
--     DESCRIPTION 
--         "The values defined for the priority of a system for
--          becoming the designated router."
--     SYNTAX      INTEGER (0..255)

TOSType ::=
    INTEGER (0..30)

-- TOSType ::= TEXTUAL-CONVENTION
--     DISPLAY-HINT "d"
--     STATUS      mandatory
--     DESCRIPTION 
--         "Type of Service is defined as a mapping to the IP Type of
--          Service Flags as defined in the IP Forwarding Table MIB
--          
--          +=====+=====+=====+=====+=====+=====+=====+=====+
--          |                 |                       |     |
--          |   PRECEDENCE    |    TYPE OF SERVICE    |  0  |
--          |                 |                       |     |
--          +=====+=====+=====+=====+=====+=====+=====+=====+
--          
--                   IP TOS                IP TOS
--              Field     Policy      Field     Policy
--          
--              Contents    Code      Contents    Code
--              0 0 0 0  ==>   0      0 0 0 1  ==>   2
--              0 0 1 0  ==>   4      0 0 1 1  ==>   6
--              0 1 0 0  ==>   8      0 1 0 1  ==>  10
--              0 1 1 0  ==>  12      0 1 1 1  ==>  14
--              1 0 0 0  ==>  16      1 0 0 1  ==>  18
--              1 0 1 0  ==>  20      1 0 1 1  ==>  22
--              1 1 0 0  ==>  24      1 1 0 1  ==>  26
--              1 1 1 0  ==>  28      1 1 1 1  ==>  30
--          
--          The remaining values are left for future definition."
--     SYNTAX      INTEGER (0..30)

fsMIStdOspfGeneralGroup OBJECT IDENTIFIER
    ::= { fsMIStdOspf 1 }

fsMIStdOspfTable OBJECT-TYPE
    SYNTAX      SEQUENCE OF FsMIStdOspfEntry
    ACCESS      not-accessible
    STATUS      mandatory
    DESCRIPTION 
        "Information describing the parameters 
         of router's instances
         TABLESIZE:  64
         DESCR: 	  NA"
    ::= { fsMIStdOspfGeneralGroup 1 }

fsMIStdOspfEntry OBJECT-TYPE
    SYNTAX      FsMIStdOspfEntry
    ACCESS      not-accessible
    STATUS      mandatory
    DESCRIPTION 
        "Information describing the parameters 
         of one of the router's instances
         Row creation : An entry shall be created in one step by a 
         set-request with all necessary parameter values and  
         fsMIStdOspfStatus is set to CreateAndGo. 
         Row deletion : An entry will be deleted when the object fsMIStdOspfStatus
                 is set to Destroy.     .
         Index usage : the index is fsMIStdOspfContextId.
         Note that entries will be presented to the SNMP manager in full
         lexicographical order :  sorted on fsMIStdOspfContextId."
    INDEX       { fsMIStdOspfContextId }
    ::= { fsMIStdOspfTable 1 }

FsMIStdOspfEntry ::= SEQUENCE {
    fsMIStdOspfContextId                INTEGER,
    fsMIStdOspfRouterId                 RouterID,
    fsMIStdOspfAdminStat                Status,
    fsMIStdOspfVersionNumber            INTEGER,
    fsMIStdOspfAreaBdrRtrStatus         TruthValue,
    fsMIStdOspfASBdrRtrStatus           TruthValue,
    fsMIStdOspfExternLsaCount           Gauge,
    fsMIStdOspfExternLsaCksumSum        INTEGER,
    fsMIStdOspfTOSSupport               TruthValue,
    fsMIStdOspfOriginateNewLsas         Counter,
    fsMIStdOspfRxNewLsas                Counter,
    fsMIStdOspfExtLsdbLimit             INTEGER,
    fsMIStdOspfMulticastExtensions      INTEGER,
    fsMIStdOspfExitOverflowInterval     PositiveInteger,
    fsMIStdOspfDemandExtensions         TruthValue,
    fsMIStdOspfStatus                   RowStatus
}

fsMIStdOspfContextId OBJECT-TYPE
    SYNTAX      INTEGER (0..255)
    ACCESS      not-accessible
    STATUS      mandatory
    DESCRIPTION 
        "A 32-bit unique context id for each entry
         ALCATEL NOTE:
                 ACCESS:      NA           USAGE:       NA
                 PERSIST:     YES          INSRVMOD:    YES
                 RANGE:       0..127       DEFVALUE:    NA      
                 UNITS:       NA           SPARSE:      NA
                 DESCR:       NA"
    ::= { fsMIStdOspfEntry 1 }

fsMIStdOspfRouterId OBJECT-TYPE
    SYNTAX      RouterID
    ACCESS      read-write
    STATUS      mandatory
    DESCRIPTION 
        "A  32-bit  integer  uniquely  identifying  the
         router in the Autonomous System.
         
         By  convention,  to  ensure  uniqueness,   this
         should  default  to  the  value  of  one of the
         router's IP interface addresses.
         ALCATEL NOTE:
          ACCESS:      NA           USAGE:       NA
          PERSIST:     YES          INSRVMOD:    YES
          RANGE:       NA           DEFVALUE:    0.0.0.0
          UNITS:       NA           SPARSE:      NA
          DESCR:       NA"
--     REFERENCE   
--         "OSPF Version 2, C.1 Global parameters"
    ::= { fsMIStdOspfEntry 2 }

fsMIStdOspfAdminStat OBJECT-TYPE
    SYNTAX      Status
    ACCESS      read-write
    STATUS      mandatory
    DESCRIPTION 
        "The  administrative  status  of  OSPF  in  the
         router.   The  value 'enabled' denotes that the
         OSPF Process is active on at least  one  inter-
         face;  'disabled'  disables  it  on  all inter-
         faces.
         ALCATEL NOTE:
          ACCESS:      NA           USAGE:       NA
          PERSIST:     YES          INSRVMOD:    YES
          RANGE:       1..4         DEFVALUE:    2
          UNITS:       NA           SPARSE:      NA
          DESCR:       NA"
    ::= { fsMIStdOspfEntry 3 }

fsMIStdOspfVersionNumber OBJECT-TYPE
    SYNTAX      INTEGER { version2(2) }
    ACCESS      read-only
    STATUS      mandatory
    DESCRIPTION 
        "The current version number of the OSPF  proto-
         col is 2
         ALCATEL NOTE:
          ACCESS:      NA           USAGE:       NA
          PERSIST:     NO           INSRVMOD:    NA
          RANGE:       2            DEFVALUE:    2
          UNITS:       NA           SPARSE:      NA
          DESCR:       NA"
--     REFERENCE   
--         "OSPF Version 2, Title"
    ::= { fsMIStdOspfEntry 4 }

fsMIStdOspfAreaBdrRtrStatus OBJECT-TYPE
    SYNTAX      TruthValue
    ACCESS      read-only
    STATUS      mandatory
    DESCRIPTION 
        "A flag to note whether this router is an  area
         border router.
         ALCATEL NOTE:
          ACCESS:      NA           USAGE:       NA
          PERSIST:     NO           INSRVMOD:    NA
          RANGE:       1,2          DEFVALUE:    2
          UNITS:       NA           SPARSE:      NA
          DESCR:       NA"
--     REFERENCE   
--         "OSPF Version 2, Section 3 Splitting the AS into
--          Areas"
    ::= { fsMIStdOspfEntry 5 }

fsMIStdOspfASBdrRtrStatus OBJECT-TYPE
    SYNTAX      TruthValue
    ACCESS      read-write
    STATUS      mandatory
    DESCRIPTION 
        "A flag to note whether this router is  config-
         ured as an Autonomous System border router.
         ALCATEL NOTE:
          ACCESS:      NA           USAGE:       NA
          PERSIST:     YES          INSRVMOD:    YES
          RANGE:       1,2          DEFVALUE:    2
          UNITS:       NA           SPARSE:      NA
          DESCR:       NA"
--     REFERENCE   
--         "OSPF Version 2, Section 3.3  Classification  of
--          routers"
    ::= { fsMIStdOspfEntry 6 }

fsMIStdOspfExternLsaCount OBJECT-TYPE
    SYNTAX      Gauge
    ACCESS      read-only
    STATUS      mandatory
    DESCRIPTION 
        "The number of external (LS type 5)  link-state
         advertisements in the link-state database.
         ALCATEL NOTE:
          ACCESS:      NA           USAGE:       NA
          PERSIST:     NO           INSRVMOD:    NA
          RANGE:       NA           DEFVALUE:    0               
          UNITS:       NA           SPARSE:      NA
          DESCR:       NA"
--     REFERENCE   
--         "OSPF Version 2, Appendix A.4.5 AS external link
--          advertisements"
    ::= { fsMIStdOspfEntry 7 }

fsMIStdOspfExternLsaCksumSum OBJECT-TYPE
    SYNTAX      INTEGER
    ACCESS      read-only
    STATUS      mandatory
    DESCRIPTION 
        "The 32-bit unsigned sum of the LS checksums of
         the  external  link-state  advertisements  con-
         tained in the link-state  database.   This  sum
         can  be  used  to determine if there has been a
         change in a router's link state  database,  and
         to  compare  the  link-state  database  of  two
         routers
         ALCATEL NOTE:
          ACCESS:      NA           USAGE:       NA
          PERSIST:     NO           INSRVMOD:    NA
          RANGE:       NA           DEFVALUE:    0
          UNITS:       NA           SPARSE:      NA
          DESCR:       NA"
    ::= { fsMIStdOspfEntry 8 }

fsMIStdOspfTOSSupport OBJECT-TYPE
    SYNTAX      TruthValue
    ACCESS      read-write
    STATUS      mandatory
    DESCRIPTION 
        "The router's support for type-of-service rout-
         ing.
         ALCATEL NOTE:
          ACCESS:      NA           USAGE:       NA
          PERSIST:     YES          INSRVMOD:    YES
          RANGE:       1,2          DEFVALUE:    1
          UNITS:       NA           SPARSE:      NA
          DESCR:       NA"
--     REFERENCE   
--         "OSPF Version 2,  Appendix  F.1.2  Optional  TOS
--          support"
    ::= { fsMIStdOspfEntry 9 }

fsMIStdOspfOriginateNewLsas OBJECT-TYPE
    SYNTAX      Counter
    ACCESS      read-only
    STATUS      mandatory
    DESCRIPTION 
        "The number of  new  link-state  advertisements
         that  have been originated.  This number is in-
         cremented each time the router originates a new
         LSA.
         ALCATEL NOTE:
          ACCESS:      NA           USAGE:       NA
          PERSIST:     NO           INSRVMOD:    NA
          RANGE:       NA           DEFVALUE:    0
          UNITS:       LSA          SPARSE:      NA
          DESCR:       NA"
    ::= { fsMIStdOspfEntry 10 }

fsMIStdOspfRxNewLsas OBJECT-TYPE
    SYNTAX      Counter
    ACCESS      read-only
    STATUS      mandatory
    DESCRIPTION 
        "The number of  link-state  advertisements  re-
         ceived  determined  to  be  new instantiations.
         This number does not include  newer  instantia-
         tions  of self-originated link-state advertise-
         ments.
         ALCATEL NOTE:
          ACCESS:      NA           USAGE:       NA
          PERSIST:     NO           INSRVMOD:    NA
          RANGE:       NA           DEFVALUE:    0
          UNITS:       LSA          SPARSE:      NA
          DESCR:       NA"
    ::= { fsMIStdOspfEntry 11 }

fsMIStdOspfExtLsdbLimit OBJECT-TYPE
    SYNTAX      INTEGER (-1..2147483647)
    ACCESS      read-write
    STATUS      mandatory
    DESCRIPTION 
        "The  maximum   number   of   non-default   AS-
         external-LSAs entries that can be stored in the
         link-state database.  If the value is -1,  then
         there is no limit.
         
         When the number of non-default AS-external-LSAs
         in   a  router's  link-state  database  reaches
         fsMIStdOspfExtLsdbLimit, the router  enters  Overflow-
         State.   The   router  never  holds  more  than
         fsMIStdOspfExtLsdbLimit  non-default  AS-external-LSAs
         in  its  database. fsMIStdOspfExtLsdbLimit MUST be set
         identically in all routers attached to the OSPF
         backbone  and/or  any regular OSPF area. (i.e.,
         OSPF stub areas and NSSAs are excluded).
         ALCATEL NOTE:
          ACCESS:      NA           USAGE:       NA
          PERSIST:     YES          INSRVMOD:    YES
          RANGE:       NA           DEFVALUE:    NA
          UNITS:       NA           SPARSE:      NA
          DESCR:       NA"
    DEFVAL      { -1 }
    ::= { fsMIStdOspfEntry 12 }

fsMIStdOspfMulticastExtensions OBJECT-TYPE
    SYNTAX      INTEGER
    ACCESS      read-write
    STATUS      mandatory
    DESCRIPTION 
        "A Bit Mask indicating whether  the  router  is
         forwarding  IP  multicast  (Class  D) datagrams
         based on the algorithms defined in  the  Multi-
         cast Extensions to OSPF.
         
         Bit 0, if set, indicates that  the  router  can
         forward  IP multicast datagrams in the router's
         directly attached areas (called intra-area mul-
         ticast routing).
         
         Bit 1, if set, indicates that  the  router  can
         forward  IP  multicast  datagrams  between OSPF
         areas (called inter-area multicast routing).
         
         Bit 2, if set, indicates that  the  router  can
         forward  IP  multicast  datagrams between Auto-
         nomous Systems (called inter-AS multicast rout-
         ing).
         
         Only certain combinations of bit  settings  are
         allowed,  namely: 0 (no multicast forwarding is
         enabled), 1 (intra-area multicasting  only),  3
         (intra-area  and  inter-area  multicasting),  5
         (intra-area and inter-AS  multicasting)  and  7
         (multicasting  everywhere). By default, no mul-
         ticast forwarding is enabled
         ALCATEL NOTE:
          ACCESS:      RO           USAGE:       NA
          PERSIST:     NO           INSRVMOD:    NA
          RANGE:       0            DEFVALUE:    NA
          UNITS:       NA           SPARSE:      NA
          DESCR:       NA"
    DEFVAL      { 0 }
    ::= { fsMIStdOspfEntry 13 }

fsMIStdOspfExitOverflowInterval OBJECT-TYPE
    SYNTAX      PositiveInteger
    ACCESS      read-write
    STATUS      mandatory
    DESCRIPTION 
        "The number of  seconds  that,  after  entering
         OverflowState,  a  router will attempt to leave
         OverflowState. This allows the router to  again
         originate  non-default  AS-external-LSAs.  When
         set to 0, the router will not  leave  Overflow-
         State until restarted.
         ALCATEL NOTE:
          ACCESS:      NA            USAGE:       NA
          PERSIST:     YES           INSRVMOD:    YES
          RANGE:       0..2147483647 DEFVALUE:    120
          UNITS:       SECONDS       SPARSE:      NA
          DESCR:       NA"
    DEFVAL      { 0 }
    ::= { fsMIStdOspfEntry 14 }

fsMIStdOspfDemandExtensions OBJECT-TYPE
    SYNTAX      TruthValue
    ACCESS      read-write
    STATUS      mandatory
    DESCRIPTION 
        "The router's support for demand routing.
         ALCATEL NOTE:
           ACCESS:      NA           USAGE:       NA
           PERSIST:     YES          INSRVMOD:    YES
           RANGE:       1,2          DEFVALUE:    1
           UNITS:       NA           SPARSE:      NA
           DESCR:       NA"
--     REFERENCE   
--         "OSPF Version 2, Appendix on Demand Routing"
    ::= { fsMIStdOspfEntry 15 }

fsMIStdOspfStatus OBJECT-TYPE
    SYNTAX      RowStatus
    ACCESS      read-write
    STATUS      mandatory
    DESCRIPTION 
        "This variable displays the status of  the  en-
         try.  Setting it to 'invalid' has the effect of
         rendering it inoperative.  The internal  effect
         (row removal) is implementation dependent.
         ALCATEL NOTE:
          ACCESS:      NA           USAGE:       NA
          PERSIST:     YES          INSRVMOD:    NA
          RANGE:       NA           DEFVALUE:    NA
          UNITS:       NA           SPARSE:      NA
          DESCR:       In ECNTA, Get of this object will always return 1 (Active), since this object is not supported in ECNTA"
    ::= { fsMIStdOspfEntry 16 }

fsMIStdOspfAreaTable OBJECT-TYPE
    SYNTAX      SEQUENCE OF FsMIStdOspfAreaEntry
    ACCESS      not-accessible
    STATUS      mandatory
    DESCRIPTION 
        "Information describing the configured  parame-
         ters  and cumulative statistics of the router's
         attached areas
         ALCATEL NOTE :
         	TABLE SIZE:  64                
         	DESCR:       NA"
--     REFERENCE   
--         "OSPF Version 2, Section 6  The Area Data Struc-
--          ture"
    ::= { fsMIStdOspf 2 }

fsMIStdOspfAreaEntry OBJECT-TYPE
    SYNTAX      FsMIStdOspfAreaEntry
    ACCESS      not-accessible
    STATUS      mandatory
    DESCRIPTION 
        "Information describing the configured  parame-
         ters  and  cumulative  statistics of one of the
         router's attached areas.
         Row creation : An entry shall be created in one step by a 
         set-request with all necessary parameter values and  
         ospfAreaStatus  set to createAndGo(4).
         Row deletion : An entry shall be deleted by setting
         the ospfAreaStatus  of the specific entry to destroy(6).
         Index usage : the index are context id and Area Id.
         Note that entries will be presented to the SNMP manager in full
         lexicographical order :  sorted on context id and then on Area Id"
    INDEX       { fsMIStdOspfContextId, fsMIStdOspfAreaId }
    ::= { fsMIStdOspfAreaTable 1 }

FsMIStdOspfAreaEntry ::= SEQUENCE {
    fsMIStdOspfAreaId           AreaID,
    fsMIStdOspfImportAsExtern   INTEGER,
    fsMIStdOspfSpfRuns          Counter,
    fsMIStdOspfAreaBdrRtrCount  Gauge,
    fsMIStdOspfAsBdrRtrCount    Gauge,
    fsMIStdOspfAreaLsaCount     Gauge,
    fsMIStdOspfAreaLsaCksumSum  INTEGER,
    fsMIStdOspfAreaSummary      INTEGER,
    fsMIStdOspfAreaStatus       RowStatus
}

fsMIStdOspfAreaId OBJECT-TYPE
    SYNTAX      AreaID
    ACCESS      not-accessible
    STATUS      mandatory
    DESCRIPTION 
        "A 32-bit integer uniquely identifying an area.
         Area ID 0.0.0.0 is used for the OSPF backbone.
         ALCATEL NOTE:
          ACCESS:      NA           USAGE:       NA
          PERSIST:     YES          INSRVMOD:    NA
          RANGE:       NA           DEFVALUE:    0
          UNITS:       NA           SPARSE:      NO
          DESCR:       NA"
--     REFERENCE   
--         "OSPF Version 2, Appendix C.2 Area parameters"
    ::= { fsMIStdOspfAreaEntry 1 }

fsMIStdOspfImportAsExtern OBJECT-TYPE
    SYNTAX      INTEGER { importExternal(1), importNoExternal(2), 
                    importNssa(3) }
    ACCESS      read-write
    STATUS      mandatory
    DESCRIPTION 
        "The area's support for importing  AS  external
         link- state advertisements.
         ALCATEL NOTE:
          ACCESS:      NA           USAGE:       OPT
          PERSIST:     YES          INSRVMOD:    YES
          RANGE:       NA           DEFVALUE:    NA
          UNITS:       NA           SPARSE:      NO
          DESCR:       NA"
--     REFERENCE   
--         "OSPF Version 2, Appendix C.2 Area parameters"
    DEFVAL      { importExternal }
    ::= { fsMIStdOspfAreaEntry 3 }

fsMIStdOspfSpfRuns OBJECT-TYPE
    SYNTAX      Counter
    ACCESS      read-only
    STATUS      mandatory
    DESCRIPTION 
        "The number of times that the intra-area  route
         table  has  been  calculated  using this area's
         link-state database.  This  is  typically  done
         using Dijkstra's algorithm.
         ALCATEL NOTE:
          ACCESS:      NA           USAGE:       NA
          PERSIST:     NO           INSRVMOD:    NA
          RANGE:       NA           DEFVALUE:    0
          UNITS:       NA           SPARSE:      NO
          DESCR:       NA"
    ::= { fsMIStdOspfAreaEntry 4 }

fsMIStdOspfAreaBdrRtrCount OBJECT-TYPE
    SYNTAX      Gauge
    ACCESS      read-only
    STATUS      mandatory
    DESCRIPTION 
        "The total number of area border routers reach-
         able within this area.  This is initially zero,
         and is calculated in each SPF Pass.
         ALCATEL NOTE:
          ACCESS:      NA           USAGE:       NA
          PERSIST:     NO           INSRVMOD:    NA
          RANGE:       NA           DEFVALUE:    0
          UNITS:       ROUTERS      SPARSE:      NO
          DESCR:       NA"
    ::= { fsMIStdOspfAreaEntry 5 }

fsMIStdOspfAsBdrRtrCount OBJECT-TYPE
    SYNTAX      Gauge
    ACCESS      read-only
    STATUS      mandatory
    DESCRIPTION 
        "The total number of Autonomous  System  border
         routers  reachable  within  this area.  This is
         initially zero, and is calculated in  each  SPF
         Pass.
         ALCATEL NOTE:
          ACCESS:      NA           USAGE:       NA
          PERSIST:     NO           INSRVMOD:    NA
          RANGE:       NA           DEFVALUE:    0
          UNITS:       ROUTERS      SPARSE:      NO
          DESCR:       NA"
    ::= { fsMIStdOspfAreaEntry 6 }

fsMIStdOspfAreaLsaCount OBJECT-TYPE
    SYNTAX      Gauge
    ACCESS      read-only
    STATUS      mandatory
    DESCRIPTION 
        "The total number of link-state  advertisements
         in  this  area's link-state database, excluding
         AS External LSA's.
         ALCATEL NOTE:
          ACCESS:      NA           USAGE:       NA
          PERSIST:     NO           INSRVMOD:    NA
          RANGE:       NA           DEFVALUE:    0
          UNITS:       LSA          SPARSE:      NO
          DESCR:       NA"
    ::= { fsMIStdOspfAreaEntry 7 }

fsMIStdOspfAreaLsaCksumSum OBJECT-TYPE
    SYNTAX      INTEGER
    ACCESS      read-only
    STATUS      mandatory
    DESCRIPTION 
        "The 32-bit unsigned sum of the link-state  ad-
         vertisements'  LS  checksums  contained in this
         area's link-state database.  This sum  excludes
         external (LS type 5) link-state advertisements.
         The sum can be used to determine if  there  has
         been  a  change  in a router's link state data-
         base, and to compare the link-state database of
         two routers.
         ALCATEL NOTE:
          ACCESS:      NA           USAGE:       NA
          PERSIST:     NO           INSRVMOD:    NA
          RANGE:       NA           DEFVALUE:    NA
          UNITS:       NA           SPARSE:      NO
          DESCR:       NA"
    DEFVAL      { 0 }
    ::= { fsMIStdOspfAreaEntry 8 }

fsMIStdOspfAreaSummary OBJECT-TYPE
    SYNTAX      INTEGER { noAreaSummary(1), sendAreaSummary(2) }
    ACCESS      read-write
    STATUS      mandatory
    DESCRIPTION 
        "The variable fsMIStdOspfAreaSummary controls the  im-
         port  of  summary LSAs into stub areas.  It has
         no effect on other areas.
         
         If it is noAreaSummary, the router will neither
         originate  nor  propagate summary LSAs into the
         stub area.  It will rely entirely  on  its  de-
         fault route.
         
         If it is sendAreaSummary, the router will  both
         summarize and propagate summary LSAs.
         ALCATEL NOTE:
          ACCESS:      NA           USAGE:       OPT
          PERSIST:     YES          INSRVMOD:    YES
          RANGE:       NA           DEFVALUE:    NA
          UNITS:       NA           SPARSE:      NO
          DESCR:       NA"
    DEFVAL      { noAreaSummary }
    ::= { fsMIStdOspfAreaEntry 9 }

fsMIStdOspfAreaStatus OBJECT-TYPE
    SYNTAX      RowStatus
    ACCESS      read-write
    STATUS      mandatory
    DESCRIPTION 
        "This variable displays the status of  the  en-
         try.  Setting it to 'invalid' has the effect of
         rendering it inoperative.  The internal  effect
         (row removal) is implementation dependent.
         ALCATEL NOTE:
          ACCESS:      NA           USAGE:       MAND
          PERSIST:     YES          INSRVMOD:    YES
          RANGE:       1,4,5,6      DEFVALUE:    NA
          UNITS:       NA           SPARSE:      NO
          DESCR:       NA"
    ::= { fsMIStdOspfAreaEntry 10 }

fsMIStdOspfStubAreaTable OBJECT-TYPE
    SYNTAX      SEQUENCE OF FsMIStdOspfStubAreaEntry
    ACCESS      not-accessible
    STATUS      mandatory
    DESCRIPTION 
        "The set of metrics that will be advertised  by
         a default Area Border Router into a stub area.
         ALCATEL NOTE:
         	TABLE SIZE:   160                     
         	DESCR:        NA"
--     REFERENCE   
--         "OSPF Version 2, Appendix C.2, Area Parameters"
    ::= { fsMIStdOspf 3 }

fsMIStdOspfStubAreaEntry OBJECT-TYPE
    SYNTAX      FsMIStdOspfStubAreaEntry
    ACCESS      not-accessible
    STATUS      mandatory
    DESCRIPTION 
        "The metric for a given Type  of  Service  that
         will  be  advertised  by  a default Area Border
         Router into a stub area.
         Row creation : An entry shall be created in one step by a 
         set-request with all necessary parameter values and  
         ospfStubStatus set to createAndGo(4).
         Row deletion : An entry shall be deleted by setting
         the ospfStubStatus of the specific entry to destroy(6).
         Index usage : the index are the context id, Stub Area Id,Stub Tos.
         Note that entries will be presented to the SNMP manager in full
         lexicographical order :  sorted on fsMIStdOspfContextId then on Stub Area Id,Stub Tos."
--     REFERENCE   
--         "OSPF Version 2, Appendix C.2, Area Parameters"
    INDEX       { fsMIStdOspfContextId, fsMIStdOspfStubAreaId, 
                  fsMIStdOspfStubTOS }
    ::= { fsMIStdOspfStubAreaTable 1 }

FsMIStdOspfStubAreaEntry ::= SEQUENCE {
    fsMIStdOspfStubAreaId       AreaID,
    fsMIStdOspfStubTOS          TOSType,
    fsMIStdOspfStubMetric       BigMetric,
    fsMIStdOspfStubStatus       RowStatus,
    fsMIStdOspfStubMetricType   INTEGER
}

fsMIStdOspfStubAreaId OBJECT-TYPE
    SYNTAX      AreaID
    ACCESS      not-accessible
    STATUS      mandatory
    DESCRIPTION 
        "The 32 bit identifier for the Stub  Area.   On
         creation,  this  can  be  derived  from the in-
         stance.
         ALCATEL NOTE:
          ACCESS:      NA           USAGE:       NA
          PERSIST:     YES          INSRVMOD:    NA
          RANGE:       NA           DEFVALUE:    NA
          UNITS:       NA           SPARSE:      NO
          DESCR:       NA"
    ::= { fsMIStdOspfStubAreaEntry 1 }

fsMIStdOspfStubTOS OBJECT-TYPE
    SYNTAX      TOSType
    ACCESS      not-accessible
    STATUS      mandatory
    DESCRIPTION 
        "The  Type  of  Service  associated  with   the
         metric.   On creation, this can be derived from
         the instance.
         ALCATEL NOTE:
          ACCESS:      NA           USAGE:       NA
          PERSIST:     YES          INSRVMOD:    NA
          RANGE:       NA           DEFVALUE:    NA
          UNITS:       NA           SPARSE:      NO
          DESCR:       NA"
    ::= { fsMIStdOspfStubAreaEntry 2 }

fsMIStdOspfStubMetric OBJECT-TYPE
    SYNTAX      BigMetric
    ACCESS      read-write
    STATUS      mandatory
    DESCRIPTION 
        "The metric value applied at the indicated type
         of  service.  By default, this equals the least
         metric at the type of service among the  inter-
         faces to other areas.
         ALCATEL NOTE:
          ACCESS:      NA           USAGE:       OPT
          PERSIST:     YES          INSRVMOD:    YES
          RANGE:       0..16777215   DEFVALUE:    10
          UNITS:       NA           SPARSE:      NO
          DESCR:       NA"
    ::= { fsMIStdOspfStubAreaEntry 3 }

fsMIStdOspfStubStatus OBJECT-TYPE
    SYNTAX      RowStatus
    ACCESS      read-write
    STATUS      mandatory
    DESCRIPTION 
        "This variable displays the status of  the  en-
         try.  Setting it to 'invalid' has the effect of
         rendering it inoperative.  The internal  effect
         (row removal) is implementation dependent.
         ALCATEL NOTE:
          ACCESS:      NA           USAGE:       MAND
          PERSIST:     YES          INSRVMOD:    YES
          RANGE:       1,4,5,6      DEFVALUE:    NA
          UNITS:       NA           SPARSE:      NO
          DESCR:       NA"
    ::= { fsMIStdOspfStubAreaEntry 4 }

fsMIStdOspfStubMetricType OBJECT-TYPE
    SYNTAX      INTEGER { ospfMetric(1), comparableCost(2), 
                    nonComparable(3) }
    ACCESS      read-write
    STATUS      mandatory
    DESCRIPTION 
        "This variable displays the type of metric  ad-
         vertised as a default route.
         ALCATEL NOTE:
          ACCESS:      NA           USAGE:       OPT
          PERSIST:     YES          INSRVMOD:    YES
          RANGE:       NA           DEFVALUE:    NA
          UNITS:       NA           SPARSE:      NO
          DESCR:       NA"
    DEFVAL      { ospfMetric }
    ::= { fsMIStdOspfStubAreaEntry 5 }

fsMIStdOspfLsdbTable OBJECT-TYPE
    SYNTAX      SEQUENCE OF FsMIStdOspfLsdbEntry
    ACCESS      not-accessible
    STATUS      mandatory
    DESCRIPTION 
        "The OSPF Process's Link State Database.
         ALCATEL NOTE:
         	TABLE SIZE:  2200   
         	DESCR:       NA"
--     REFERENCE   
--         "OSPF Version 2, Section 12  Link  State  Adver-
--          tisements"
    ::= { fsMIStdOspf 4 }

fsMIStdOspfLsdbEntry OBJECT-TYPE
    SYNTAX      FsMIStdOspfLsdbEntry
    ACCESS      not-accessible
    STATUS      mandatory
    DESCRIPTION 
        "A single Link State Advertisement.
         Row creation : An entry will be created when LSAs are received.
         Row deletion : An entry can not be deleted.
         Index usage : the index is the fsMIStdOspfContextId,  Link State Area Id,Link State Database Type,Link State Id,Link State Router Id.
         Note that entries will be presented to the SNMP manager in full
         lexicographical order :  sorted on fsMIStdOspfContextId then on Link State Area Id,Link State Database Type,Link State Id,Link State Router Id."
    INDEX       { fsMIStdOspfContextId, fsMIStdOspfLsdbAreaId, 
                  fsMIStdOspfLsdbType, fsMIStdOspfLsdbLsid, 
                  fsMIStdOspfLsdbRouterId }
    ::= { fsMIStdOspfLsdbTable 1 }

FsMIStdOspfLsdbEntry ::= SEQUENCE {
    fsMIStdOspfLsdbAreaId           AreaID,
    fsMIStdOspfLsdbType             INTEGER,
    fsMIStdOspfLsdbLsid             IpAddress,
    fsMIStdOspfLsdbRouterId         RouterID,
    fsMIStdOspfLsdbSequence         INTEGER,
    fsMIStdOspfLsdbAge              INTEGER,
    fsMIStdOspfLsdbChecksum         INTEGER,
    fsMIStdOspfLsdbAdvertisement    OCTET STRING
}

fsMIStdOspfLsdbAreaId OBJECT-TYPE
    SYNTAX      AreaID
    ACCESS      not-accessible
    STATUS      mandatory
    DESCRIPTION 
        "The 32 bit identifier of the Area  from  which
         the LSA was received.
         ALCATEL NOTE:
          ACCESS:      NA           USAGE:       NA
          PERSIST:     NO           INSRVMOD:    NA
          RANGE:       NA           DEFVALUE:    NA
          UNITS:       NA           SPARSE:      NO
          DESCR:       NA"
--     REFERENCE   
--         "OSPF Version 2, Appendix C.2 Area parameters"
    ::= { fsMIStdOspfLsdbEntry 1 }

fsMIStdOspfLsdbType OBJECT-TYPE
    SYNTAX      INTEGER { routerLink(1), networkLink(2), summaryLink(3), 
                    asSummaryLink(4), asExternalLink(5), 
                    multicastLink(6), nssaExternalLink(7) }
    ACCESS      not-accessible
    STATUS      mandatory
    DESCRIPTION 
        "The type  of  the  link  state  advertisement.
         Each  link state type has a separate advertise-
         ment format.
         ALCATEL NOTE:
          ACCESS:      NA           USAGE:       NA
          PERSIST:     NO           INSRVMOD:    NA
          RANGE:       NA           DEFVALUE:    NA
          UNITS:       NA           SPARSE:      NO
          DESCR:       NA"
--     REFERENCE   
--         "OSPF Version 2, Appendix A.4.1 The  Link  State
--          Advertisement header"
    ::= { fsMIStdOspfLsdbEntry 2 }

fsMIStdOspfLsdbLsid OBJECT-TYPE
    SYNTAX      IpAddress
    ACCESS      not-accessible
    STATUS      mandatory
    DESCRIPTION 
        "The Link State ID is an LS Type Specific field
         containing either a Router ID or an IP Address;
         it identifies the piece of the  routing  domain
         that is being described by the advertisement.
         ALCATEL NOTE:
          ACCESS:      NA           USAGE:       NA
          PERSIST:     NO           INSRVMOD:    NA
          RANGE:       NA           DEFVALUE:    NA
          UNITS:       NA           SPARSE:      NO
          DESCR:       NA"
--     REFERENCE   
--         "OSPF Version 2, Section 12.1.4 Link State ID"
    ::= { fsMIStdOspfLsdbEntry 3 }

fsMIStdOspfLsdbRouterId OBJECT-TYPE
    SYNTAX      RouterID
    ACCESS      not-accessible
    STATUS      mandatory
    DESCRIPTION 
        "The 32 bit number that uniquely identifies the
         originating router in the Autonomous System.
         ALCATEL NOTE:
          ACCESS:      NA           USAGE:       NA
          PERSIST:     NO           INSRVMOD:    NA
          RANGE:       NA           DEFVALUE:    NA
          UNITS:       NA           SPARSE:      NO
          DESCR:       NA"
--     REFERENCE   
--         "OSPF Version 2, Appendix C.1 Global parameters"
    ::= { fsMIStdOspfLsdbEntry 4 }

fsMIStdOspfLsdbSequence OBJECT-TYPE
    SYNTAX      INTEGER
    ACCESS      read-only
    STATUS      mandatory
    DESCRIPTION 
        "The sequence number field is a  signed  32-bit
         integer.   It  is used to detect old and dupli-
         cate link state advertisements.  The  space  of
         sequence  numbers  is  linearly  ordered.   The
         larger the sequence number the more recent  the
         advertisement.
         ALCATEL NOTE:
          ACCESS:      NA           USAGE:       NA
          PERSIST:     NO           INSRVMOD:    NA
          RANGE:       NA           DEFVALUE:    NA
          UNITS:       NA           SPARSE:      NO
          DESCR:       NA"
--     REFERENCE   
--         "OSPF Version  2,  Section  12.1.6  LS  sequence
--          number"
    ::= { fsMIStdOspfLsdbEntry 5 }

fsMIStdOspfLsdbAge OBJECT-TYPE
    SYNTAX      INTEGER
    ACCESS      read-only
    STATUS      mandatory
    DESCRIPTION 
        "This field is the age of the link state adver-
         tisement in seconds.
         ALCATEL NOTE:
          ACCESS:      NA           USAGE:       NA
          PERSIST:     NO           INSRVMOD:    NA
          RANGE:       0..3600      DEFVALUE:    0
          UNITS:       SECONDS      SPARSE:      NO
          DESCR:       NA"
--     REFERENCE   
--         "OSPF Version 2, Section 12.1.1 LS age"
    ::= { fsMIStdOspfLsdbEntry 6 }

fsMIStdOspfLsdbChecksum OBJECT-TYPE
    SYNTAX      INTEGER
    ACCESS      read-only
    STATUS      mandatory
    DESCRIPTION 
        "This field is the  checksum  of  the  complete
         contents  of  the  advertisement, excepting the
         age field.  The age field is excepted  so  that
         an   advertisement's  age  can  be  incremented
         without updating the  checksum.   The  checksum
         used  is  the same that is used for ISO connec-
         tionless datagrams; it is commonly referred  to
         as the Fletcher checksum.
         ALCATEL NOTE:
          ACCESS:      NA           USAGE:       NA
          PERSIST:     NO           INSRVMOD:    NA
          RANGE:       NA           DEFVALUE:    0
          UNITS:       NA           SPARSE:      NO
          DESCR:       NA"
--     REFERENCE   
--         "OSPF Version 2, Section 12.1.7 LS checksum"
    ::= { fsMIStdOspfLsdbEntry 7 }

fsMIStdOspfLsdbAdvertisement OBJECT-TYPE
    SYNTAX      OCTET STRING (SIZE(1..65535))
    ACCESS      read-only
    STATUS      mandatory
    DESCRIPTION 
        "The entire Link State Advertisement, including
         its header.
         ALCATEL NOTE:
          ACCESS:      NA           USAGE:       NA
          PERSIST:     NO           INSRVMOD:    NA
          RANGE:       NA           DEFVALUE:    '\0'
          UNITS:       NA           SPARSE:      NO
          DESCR:       NA"
--     REFERENCE   
--         "OSPF Version 2, Section 12  Link  State  Adver-
--          tisements"
    ::= { fsMIStdOspfLsdbEntry 8 }

fsMIStdOspfHostTable OBJECT-TYPE
    SYNTAX      SEQUENCE OF FsMIStdOspfHostEntry
    ACCESS      not-accessible
    STATUS      mandatory
    DESCRIPTION 
        "The list of Hosts, and their metrics, that the
         router will advertise as host routes.
         ALCATEL NOTE:
         	TABLE SIZE:     128                  
         	DESCR:          NA"
--     REFERENCE   
--         "OSPF Version 2, Appendix C.6  Host route param-
--          eters"
    ::= { fsMIStdOspf 5 }

fsMIStdOspfHostEntry OBJECT-TYPE
    SYNTAX      FsMIStdOspfHostEntry
    ACCESS      not-accessible
    STATUS      mandatory
    DESCRIPTION 
        "A metric to be advertised, for a given type of
         service, when a given host is reachable.
         Row creation : An entry shall be created in one step by a 
         set-request with all necessary parameter values and  
         ospfHostStatus set to createAndGo(4).
         Row deletion : An entry shall be deleted by setting
         the ospfHostStatus of the specific entry to destroy(6).
         Index usage : the index is the fsMIStdOspfContextId, Host Ip Address,Host Tos.
         Note that entries will be presented to the SNMP manager in full
         lexicographical order :  sorted on fsMIStdOspfContextId then on Host Ip Address,Host Tos."
    INDEX       { fsMIStdOspfContextId, fsMIStdOspfHostIpAddress, 
                  fsMIStdOspfHostTOS }
    ::= { fsMIStdOspfHostTable 1 }

FsMIStdOspfHostEntry ::= SEQUENCE {
    fsMIStdOspfHostIpAddress    IpAddress,
    fsMIStdOspfHostTOS          TOSType,
    fsMIStdOspfHostMetric       Metric,
    fsMIStdOspfHostStatus       RowStatus,
    fsMIStdOspfHostAreaID       AreaID
}

fsMIStdOspfHostIpAddress OBJECT-TYPE
    SYNTAX      IpAddress
    ACCESS      not-accessible
    STATUS      mandatory
    DESCRIPTION 
        "The IP Address of the Host.
         ALCATEL NOTE:
           ACCESS:      NA           USAGE:       NA
           PERSIST:     YES          INSRVMOD:    NA
           RANGE:       NA           DEFVALUE:    NA
           UNITS:       NA           SPARSE:      NO
           DESCR:       NA"
--     REFERENCE   
--         "OSPF Version 2, Appendix C.6 Host route parame-
--          ters"
    ::= { fsMIStdOspfHostEntry 1 }

fsMIStdOspfHostTOS OBJECT-TYPE
    SYNTAX      TOSType
    ACCESS      not-accessible
    STATUS      mandatory
    DESCRIPTION 
        "The Type of Service of the route being config-
         ured.
         ALCATEL NOTE:
          ACCESS:      NA           USAGE:       NA
          PERSIST:  	 YES          INSRVMOD:    NA
          RANGE:       NA           DEFVALUE:    NA
          UNITS:       NA           SPARSE:      NO
          DESCR:       NA"
--     REFERENCE   
--         "OSPF Version 2, Appendix C.6 Host route parame-
--          ters"
    ::= { fsMIStdOspfHostEntry 2 }

fsMIStdOspfHostMetric OBJECT-TYPE
    SYNTAX      Metric
    ACCESS      read-write
    STATUS      mandatory
    DESCRIPTION 
        "The Metric to be advertised.
         ALCATEL NOTE:
           ACCESS:      NA           USAGE:       OPT
           PERSIST:     YES          INSRVMOD:    YES
           RANGE:       0..65535     DEFVALUE:    NA     
           UNITS:       NA           SPARSE:      NO
           DESCR:       NA"
--     REFERENCE   
--         "OSPF Version 2, Appendix C.6 Host route parame-
--          ters"
    ::= { fsMIStdOspfHostEntry 3 }

fsMIStdOspfHostStatus OBJECT-TYPE
    SYNTAX      RowStatus
    ACCESS      read-write
    STATUS      mandatory
    DESCRIPTION 
        "This variable displays the status of  the  en-
         try.  Setting it to 'invalid' has the effect of
         rendering it inoperative.  The internal  effect
         (row removal) is implementation dependent.
         ALCATEL NOTE:
          ACCESS:      NA           USAGE:       MAND
          PERSIST:     YES          INSRVMOD:    YES
          RANGE:       1,4,5,6      DEFVALUE:    NA
          UNITS:       NA           SPARSE:      N0
          DESCR:       NA"
    ::= { fsMIStdOspfHostEntry 4 }

fsMIStdOspfHostAreaID OBJECT-TYPE
    SYNTAX      AreaID
    ACCESS      read-only
    STATUS      mandatory
    DESCRIPTION 
        "The Area the Host Entry is to be found within.
         By  default, the area that a subsuming OSPF in-
         terface is in, or 0.0.0.0
         ALCATEL NOTE:
          ACCESS:      NA           USAGE:       NA
          PERSIST:     NO           INSRVMOD:    NA
          RANGE:       NA           DEFVALUE:    0
          UNITS:       NA           SPARSE:      NO
          DESCR:       NA"
--     REFERENCE   
--         "OSPF Version 2, Appendix C.2 Area parameters"
    ::= { fsMIStdOspfHostEntry 5 }

fsMIStdOspfIfTable OBJECT-TYPE
    SYNTAX      SEQUENCE OF FsMIStdOspfIfEntry
    ACCESS      not-accessible
    STATUS      mandatory
    DESCRIPTION 
        "The OSPF Interface Table describes the  inter-
         faces from the viewpoint of OSPF.
         ALCATEL NOTE:
         	TABLE SIZE:    18
         	DESCR:         NA"
--     REFERENCE   
--         "OSPF Version 2, Appendix C.3  Router  interface
--          parameters"
    ::= { fsMIStdOspf 6 }

fsMIStdOspfIfEntry OBJECT-TYPE
    SYNTAX      FsMIStdOspfIfEntry
    ACCESS      not-accessible
    STATUS      mandatory
    DESCRIPTION 
        "The OSPF Interface Entry describes one  inter-
         face from the viewpoint of OSPF.
         Row creation : An entry shall be created in one step by a 
         set-request with all necessary parameter values and  
         ospfIfStatus set to createAndGo(4).
         Row deletion : An entry shall be deleted by setting
         the ospfIfStatus of the specific entry to destroy(6).
         Index usage : the index is fsMIStdOspfContextId,Ip Address,AddressLess Interfaces.
         Note that entries will be presented to the SNMP manager in full
         lexicographical order :  sorted on fsMIStdOspfContextId then on Ip Address,AddressLess Interfaces."
    INDEX       { fsMIStdOspfContextId, fsMIStdOspfIfIpAddress, 
                  fsMIStdOspfAddressLessIf }
    ::= { fsMIStdOspfIfTable 1 }

FsMIStdOspfIfEntry ::= SEQUENCE {
    fsMIStdOspfIfIpAddress                  IpAddress,
    fsMIStdOspfAddressLessIf                InterfaceIndex,
    fsMIStdOspfIfAreaId                     AreaID,
    fsMIStdOspfIfType                       INTEGER,
    fsMIStdOspfIfAdminStat                  Status,
    fsMIStdOspfIfRtrPriority                DesignatedRouterPriority,
    fsMIStdOspfIfTransitDelay               UpToMaxAge,
    fsMIStdOspfIfRetransInterval            UpToMaxAge,
    fsMIStdOspfIfHelloInterval              HelloRange,
    fsMIStdOspfIfRtrDeadInterval            PositiveInteger,
    fsMIStdOspfIfPollInterval               PositiveInteger,
    fsMIStdOspfIfState                      INTEGER,
    fsMIStdOspfIfDesignatedRouter           IpAddress,
    fsMIStdOspfIfBackupDesignatedRouter     IpAddress,
    fsMIStdOspfIfEvents                     Counter,
    fsMIStdOspfIfAuthKey                    OCTET STRING,
    fsMIStdOspfIfStatus                     RowStatus,
    fsMIStdOspfIfMulticastForwarding        INTEGER,
    fsMIStdOspfIfDemand                     TruthValue,
    fsMIStdOspfIfAuthType                   INTEGER
}

fsMIStdOspfIfIpAddress OBJECT-TYPE
    SYNTAX      IpAddress
    ACCESS      not-accessible
    STATUS      mandatory
    DESCRIPTION 
        "The IP address of this OSPF interface.
         ALCATEL NOTE:
           ACCESS:      NA           USAGE:       NA
           PERSIST:     YES          INSRVMOD:    NA
           RANGE:       NA           DEFVALUE:    NA 
           UNITS:       NA           SPARSE:      NO
           DESCR:       NA"
    ::= { fsMIStdOspfIfEntry 1 }

fsMIStdOspfAddressLessIf OBJECT-TYPE
    SYNTAX      InterfaceIndex
    ACCESS      not-accessible
    STATUS      mandatory
    DESCRIPTION 
        "For the purpose of easing  the  instancing  of
         addressed   and  addressless  interfaces;  This
         variable takes the value 0 on  interfaces  with
         IP  Addresses,  and  the corresponding value of
         ifIndex for interfaces having no IP Address.
         ALCATEL NOTE:
          ACCESS:      NA           USAGE:       NA
          PERSIST:     YES          INSRVMOD:    NA
          RANGE:       NA           DEFVALUE:    NA
          UNITS:       NA           SPARSE:      NO
          DESCR:       NA"
    ::= { fsMIStdOspfIfEntry 2 }

fsMIStdOspfIfAreaId OBJECT-TYPE
    SYNTAX      AreaID
    ACCESS      read-write
    STATUS      mandatory
    DESCRIPTION 
        "A 32-bit integer uniquely identifying the area
         to  which  the  interface  connects.   Area  ID
         0.0.0.0 is used for the OSPF backbone.
         ALCATEL NOTE:
          ACCESS:      NA           USAGE:       OPT
          PERSIST:     YES          INSRVMOD:    YES
          RANGE:       NA           DEFVALUE:    NA
          UNITS:       NA           SPARSE:      NO
          DESCR:       NA"
    DEFVAL      { '00000000'H }
    ::= { fsMIStdOspfIfEntry 3 }

fsMIStdOspfIfType OBJECT-TYPE
    SYNTAX      INTEGER { broadcast(1), nbma(2), pointToPoint(3), 
                    pointToMultipoint(5) }
    ACCESS      read-write
    STATUS      mandatory
    DESCRIPTION 
        "The OSPF interface type.
         
         By way of a default, this field may be intuited
         from the corresponding value of ifType.  Broad-
         cast LANs, such as  Ethernet  and  IEEE  802.5,
         take  the  value  'broadcast', X.25 and similar
         technologies take the value 'nbma',  and  links
         that  are  definitively point to point take the
         value 'pointToPoint'.
         ALCATEL NOTE:
          ACCESS:      NA           USAGE:       OPT
          PERSIST:     YES          INSRVMOD:    YES
          RANGE:       NA           DEFVALUE:    1
          UNITS:       NA	      SPARSE:      NO
          DESCR:       NA"
    ::= { fsMIStdOspfIfEntry 4 }

fsMIStdOspfIfAdminStat OBJECT-TYPE
    SYNTAX      Status
    ACCESS      read-write
    STATUS      mandatory
    DESCRIPTION 
        "The OSPF  interface's  administrative  status.
         The  value formed on the interface, and the in-
         terface will be advertised as an internal route
         to  some  area.   The  value 'disabled' denotes
         that the interface is external to OSPF.
         ALCATEL NOTE:
          ACCESS:      NA           USAGE:       OPT
          PERSIST:     YES          INSRVMOD:    YES
          RANGE:       1..4         DEFVALUE:    NA
          UNITS:       NA           SPARSE:      NO
          DESCR:       NA"
    DEFVAL      { enabled }
    ::= { fsMIStdOspfIfEntry 5 }

fsMIStdOspfIfRtrPriority OBJECT-TYPE
    SYNTAX      DesignatedRouterPriority
    ACCESS      read-write
    STATUS      mandatory
    DESCRIPTION 
        "The  priority  of  this  interface.   Used  in
         multi-access  networks,  this  field is used in
         the designated router election algorithm.   The
         value 0 signifies that the router is not eligi-
         ble to become the  designated  router  on  this
         particular  network.   In the event of a tie in
         this value, routers will use their Router ID as
         a tie breaker.
         ALCATEL NOTE:
          ACCESS:      NA           USAGE:       OPT
          PERSIST:     YES          INSRVMOD:    YES
          RANGE:       0..255       DEFVALUE:    NA
          UNITS:       NA           SPARSE:      NO
          DESCR:       NA"
    DEFVAL      { 1 }
    ::= { fsMIStdOspfIfEntry 6 }

fsMIStdOspfIfTransitDelay OBJECT-TYPE
    SYNTAX      UpToMaxAge
    ACCESS      read-write
    STATUS      mandatory
    DESCRIPTION 
        "The estimated number of seconds  it  takes  to
         transmit  a  link state update packet over this
         interface.
         ALCATEL NOTE:
          ACCESS:      NA           USAGE:       OPT
          PERSIST:     YES          INSRVMOD:    YES
          RANGE:       0..3600      DEFVALUE:    NA
          UNITS:       SECONDS      SPARSE:      NO
          DESCR:       NA"
    DEFVAL      { 1 }
    ::= { fsMIStdOspfIfEntry 7 }

fsMIStdOspfIfRetransInterval OBJECT-TYPE
    SYNTAX      UpToMaxAge
    ACCESS      read-write
    STATUS      mandatory
    DESCRIPTION 
        "The number of seconds between  link-state  ad-
         vertisement  retransmissions,  for  adjacencies
         belonging to this  interface.   This  value  is
         also used when retransmitting database descrip-
         tion and link-state request packets.
         ALCATEL NOTE:
          ACCESS:      NA           USAGE:       OPT
          PERSIST:     YES          INSRVMOD:    YES
          RANGE:       0..3600      DEFVALUE:    NA
          UNITS:       SECONDS      SPARSE:      NO
          DESCR:       NA"
    DEFVAL      { 5 }
    ::= { fsMIStdOspfIfEntry 8 }

fsMIStdOspfIfHelloInterval OBJECT-TYPE
    SYNTAX      HelloRange
    ACCESS      read-write
    STATUS      mandatory
    DESCRIPTION 
        "The length of time, in  seconds,  between  the
         Hello  packets that the router sends on the in-
         terface.  This value must be the same  for  all
         routers attached to a common network.
         ALCATEL NOTE:
          ACCESS:      NA           USAGE:       OPT
          PERSIST:     YES          INSRVMOD:    YES
          RANGE:       0..65535     DEFVALUE:    NA
          UNITS:       SECONDS      SPARSE:      NO
          DESCR:       NA"
    DEFVAL      { 10 }
    ::= { fsMIStdOspfIfEntry 9 }

fsMIStdOspfIfRtrDeadInterval OBJECT-TYPE
    SYNTAX      PositiveInteger
    ACCESS      read-write
    STATUS      mandatory
    DESCRIPTION 
        "The number of seconds that  a  router's  Hello
         packets  have  not been seen before it's neigh-
         bors declare the router down.  This  should  be
         some  multiple  of  the  Hello  interval.  This
         value must be the same for all routers attached
         to a common network.
         ALCATEL NOTE:
          ACCESS:      NA           USAGE:       OPT
          PERSIST:     YES          INSRVMOD:    YES
          RANGE:       0..65535     DEFVALUE:    NA
          UNITS:       SECONDS      SPARSE:      NO
          DESCR:       NA"
    DEFVAL      { 40 }
    ::= { fsMIStdOspfIfEntry 10 }

fsMIStdOspfIfPollInterval OBJECT-TYPE
    SYNTAX      PositiveInteger
    ACCESS      read-write
    STATUS      mandatory
    DESCRIPTION 
        "The larger time interval, in seconds,  between
         the  Hello  packets  sent  to  an inactive non-
         broadcast multi- access neighbor.
         ALCATEL NOTE:
          ACCESS:      NA           USAGE:       OPT
          PERSIST:     YES          INSRVMOD:    YES
          RANGE:       0..65535     DEFVALUE:    NA
          UNITS:       SECONDS      SPARSE:      NO
          DESCR:       NA"
    DEFVAL      { 120 }
    ::= { fsMIStdOspfIfEntry 11 }

fsMIStdOspfIfState OBJECT-TYPE
    SYNTAX      INTEGER { down(1), loopback(2), waiting(3), 
                    pointToPoint(4), designatedRouter(5), 
                    backupDesignatedRouter(6), otherDesignatedRouter(7) }
    ACCESS      read-only
    STATUS      mandatory
    DESCRIPTION 
        "The OSPF Interface State.
         ALCATEL NOTE:
           ACCESS:      NA           USAGE:       NA
           PERSIST:     NO           INSRVMOD:    NA
           RANGE:       NA           DEFVALUE:    NA   
           UNITS:       NA           SPARSE:      NO
           DESCR:       NA"
    DEFVAL      { down }
    ::= { fsMIStdOspfIfEntry 12 }

fsMIStdOspfIfDesignatedRouter OBJECT-TYPE
    SYNTAX      IpAddress
    ACCESS      read-only
    STATUS      mandatory
    DESCRIPTION 
        "The IP Address of the Designated Router.
         ALCATEL NOTE:
           ACCESS:      NA           USAGE:       NA
           PERSIST:     NO           INSRVMOD:    NA
           RANGE:       NA           DEFVALUE:    NA
           UNITS:       NA           SPARSE:      NO
           DESCR:       NA"
    DEFVAL      { '00000000'H }
    ::= { fsMIStdOspfIfEntry 13 }

fsMIStdOspfIfBackupDesignatedRouter OBJECT-TYPE
    SYNTAX      IpAddress
    ACCESS      read-only
    STATUS      mandatory
    DESCRIPTION 
        "The  IP  Address  of  the  Backup   Designated
         Router.
         ALCATEL NOTE:
          ACCESS:      NA           USAGE:       NA
          PERSIST:     NO           INSRVMOD:    NA
          RANGE:       NA           DEFVALUE:    NA
          UNITS:       NA           SPARSE:      NO
          DESCR:       NA"
    DEFVAL      { '00000000'H }
    ::= { fsMIStdOspfIfEntry 14 }

fsMIStdOspfIfEvents OBJECT-TYPE
    SYNTAX      Counter
    ACCESS      read-only
    STATUS      mandatory
    DESCRIPTION 
        "The number of times this  OSPF  interface  has
         changed its state, or an error has occurred.
         ALCATEL NOTE:
          ACCESS:      NA           USAGE:       NA
          PERSIST:     NO           INSRVMOD:    NA
          RANGE:       NA           DEFVALUE:    0
          UNITS:       NA           SPARSE:      NO
          DESCR:       NA"
    ::= { fsMIStdOspfIfEntry 15 }

fsMIStdOspfIfAuthKey OBJECT-TYPE
    SYNTAX      OCTET STRING (SIZE(0..256))
    ACCESS      read-write
    STATUS      mandatory
    DESCRIPTION 
        "The Authentication Key.  If the Area's Author-
         ization  Type  is  simplePassword,  and the key
         length is shorter than 8 octets, the agent will
         left adjust and zero fill to 8 octets.
         
         Note that unauthenticated  interfaces  need  no
         authentication key, and simple password authen-
         tication cannot use a key of more  than  8  oc-
         tets.  Larger keys are useful only with authen-
         tication mechanisms not specified in this docu-
         ment.
         
         When read, fsMIStdOspfIfAuthKey always returns the 
          encrypted key of length 16.
         
         Note: The operator can enter a maximum of 8 octets
         as a MD5 key
         ALCATEL NOTE:
          ACCESS:      NA           USAGE:       OPT
          PERSIST:     YES          INSRVMOD:    YES
          RANGE:       NA  	      DEFVALUE:    '\0'
          UNITS:       NA           SPARSE:      NO
          DESCR:       NA"
--     REFERENCE   
--         "OSPF Version 2, Section 9  The  Interface  Data
--          Structure"
    DEFVAL      { '0000000000000000'H }
    ::= { fsMIStdOspfIfEntry 16 }

fsMIStdOspfIfStatus OBJECT-TYPE
    SYNTAX      RowStatus
    ACCESS      read-write
    STATUS      mandatory
    DESCRIPTION 
        "This variable displays the status of  the  en-
         try.  Setting it to 'invalid' has the effect of
         rendering it inoperative.  The internal  effect
         (row removal) is implementation dependent.
         ALCATEL NOTE:
          ACCESS:      NA           USAGE:       MAND
          PERSIST:     YES          INSRVMOD:    YES
          RANGE:       1,4,5,6      DEFVALUE:    NA
          UNITS:       NA           SPARSE:      NO
          DESCR:       NA"
    ::= { fsMIStdOspfIfEntry 17 }

fsMIStdOspfIfMulticastForwarding OBJECT-TYPE
    SYNTAX      INTEGER { blocked(1), multicast(2), unicast(3) }
    ACCESS      read-write
    STATUS      mandatory
    DESCRIPTION 
        "The way multicasts should  forwarded  on  this
         interface;  not  forwarded,  forwarded  as data
         link multicasts, or forwarded as data link uni-
         casts.   Data link multicasting is not meaning-
         ful on point to point and NBMA interfaces,  and
         setting fsMIStdOspfMulticastForwarding to 0 effective-
         ly disables all multicast forwarding.
         ALCATEL NOTE:
          ACCESS:      RO           USAGE:       OPT
          PERSIST:     NO           INSRVMOD:    NA
          RANGE:       1            DEFVALUE:    NA
          UNITS:       NA           SPARSE:      NO
          DESCR:       NA"
    DEFVAL      { blocked }
    ::= { fsMIStdOspfIfEntry 18 }

fsMIStdOspfIfDemand OBJECT-TYPE
    SYNTAX      TruthValue
    ACCESS      read-write
    STATUS      mandatory
    DESCRIPTION 
        "Indicates whether Demand OSPF procedures (hel-
         lo supression to FULL neighbors and setting the
         DoNotAge flag on proogated LSAs) should be per-
         formed on this interface.
         ALCATEL NOTE:
          ACCESS:      NA           USAGE:       OPT
          PERSIST:     YES          INSRVMOD:    YES
          RANGE:       1,2          DEFVALUE:    NA
          UNITS:       NA           SPARSE:      NO
          DESCR:       NA"
    DEFVAL      { false }
    ::= { fsMIStdOspfIfEntry 19 }

fsMIStdOspfIfAuthType OBJECT-TYPE
    SYNTAX      INTEGER (0..255)
    ACCESS      read-write
    STATUS      mandatory
    DESCRIPTION 
        "The authentication type specified for  an  in-
         terface.   Additional  authentication types may
         be assigned locally.
         ALCATEL NOTE:
          ACCESS:      NA           USAGE:       OPT
          PERSIST:     YES          INSRVMOD:    YES
          RANGE:       0..2         DEFVALUE:    NA
          UNITS:       NA           SPARSE:      NO
          DESCR:       NA"
--     REFERENCE   
--         "OSPF Version 2, Appendix E Authentication"
    DEFVAL      { 0 }
    ::= { fsMIStdOspfIfEntry 20 }

fsMIStdOspfIfMetricTable OBJECT-TYPE
    SYNTAX      SEQUENCE OF FsMIStdOspfIfMetricEntry
    ACCESS      not-accessible
    STATUS      mandatory
    DESCRIPTION 
        "The TOS metrics for  a  non-virtual  interface
         identified by the interface index.
         ALCATEL NOTE:
         	TABLE SIZE:   288           
         	DESCR:        NA"
--     REFERENCE   
--         "OSPF Version 2, Appendix C.3  Router  interface
--          parameters"
    ::= { fsMIStdOspf 7 }

fsMIStdOspfIfMetricEntry OBJECT-TYPE
    SYNTAX      FsMIStdOspfIfMetricEntry
    ACCESS      not-accessible
    STATUS      mandatory
    DESCRIPTION 
        "A particular TOS metric for a non-virtual  in-
         terface identified by the interface index.
         Row creation : An entry shall be created in one step by a 
         set-request with all necessary parameter values and  
         ospfIfMetricStatus set to createAndGo(4).
         Row deletion : An entry shall be deleted by setting
         the ospfIfMetricStatus of the specific entry to destroy(6).
         Index usage : the index is the Context id ,Ip Address,Address Less Interface,TOS.
         Note that entries will be presented to the SNMP manager in full
         lexicographical order :  sorted on Context id then on Ip Address,Address Less Interface,TOS."
--     REFERENCE   
--         "OSPF Version 2, Appendix C.3  Router  interface
--          parameters"
    INDEX       { fsMIStdOspfContextId, fsMIStdOspfIfMetricIpAddress, 
                  fsMIStdOspfIfMetricAddressLessIf, 
                  fsMIStdOspfIfMetricTOS }
    ::= { fsMIStdOspfIfMetricTable 1 }

FsMIStdOspfIfMetricEntry ::= SEQUENCE {
    fsMIStdOspfIfMetricIpAddress        IpAddress,
    fsMIStdOspfIfMetricAddressLessIf    InterfaceIndex,
    fsMIStdOspfIfMetricTOS              TOSType,
    fsMIStdOspfIfMetricValue            Metric,
    fsMIStdOspfIfMetricStatus           RowStatus
}

fsMIStdOspfIfMetricIpAddress OBJECT-TYPE
    SYNTAX      IpAddress
    ACCESS      not-accessible
    STATUS      mandatory
    DESCRIPTION 
        "The IP address of this OSPF interface.  On row
         creation,  this  can  be  derived  from the in-
         stance.
         ALCATEL NOTE:
          ACCESS:      NA           USAGE:       NA
          PERSIST:     YES          INSRVMOD:    NA
          RANGE:       NA           DEFVALUE:    NA
          UNITS:       NA           SPARSE:      NO
          DESCR:       NA"
    ::= { fsMIStdOspfIfMetricEntry 1 }

fsMIStdOspfIfMetricAddressLessIf OBJECT-TYPE
    SYNTAX      InterfaceIndex
    ACCESS      not-accessible
    STATUS      mandatory
    DESCRIPTION 
        "For the purpose of easing  the  instancing  of
         addressed   and  addressless  interfaces;  This
         variable takes the value 0 on  interfaces  with
         IP  Addresses, and the value of ifIndex for in-
         terfaces having no IP Address.   On  row  crea-
         tion, this can be derived from the instance.
         ALCATEL NOTE:
          ACCESS:      NA           USAGE:       NA
          PERSIST:     YES          INSRVMOD:    NA
          RANGE:       NA           DEFVALUE:    0
          UNITS:       NA           SPARSE:      NO
          DESCR:       NA"
    ::= { fsMIStdOspfIfMetricEntry 2 }

fsMIStdOspfIfMetricTOS OBJECT-TYPE
    SYNTAX      TOSType
    ACCESS      not-accessible
    STATUS      mandatory
    DESCRIPTION 
        "The type of service metric  being  referenced.
         On  row  creation, this can be derived from the
         instance.
         ALCATEL NOTE:
          ACCESS:      NA           USAGE:       NA
          PERSIST:     YES          INSRVMOD:    NA
          RANGE:       0..30        DEFVALUE:    0
          UNITS:       NA           SPARSE:      NO
          DESCR:       NA"
    ::= { fsMIStdOspfIfMetricEntry 3 }

fsMIStdOspfIfMetricValue OBJECT-TYPE
    SYNTAX      Metric
    ACCESS      read-write
    STATUS      mandatory
    DESCRIPTION 
        "The metric of using this type  of  service  on
         this interface.  The default value of the TOS 0
         Metric is 10^8 / ifSpeed.
         ALCATEL NOTE:
          ACCESS:      NA           USAGE:       OPT
          PERSIST:     YES          INSRVMOD:    YES
          RANGE:       0..65535     DEFVALUE:    10
          UNITS:       NA           SPARSE:      NO
          DESCR:       NA"
    ::= { fsMIStdOspfIfMetricEntry 4 }

fsMIStdOspfIfMetricStatus OBJECT-TYPE
    SYNTAX      RowStatus
    ACCESS      read-write
    STATUS      mandatory
    DESCRIPTION 
        "This variable displays the status of  the  en-
         try.  Setting it to 'invalid' has the effect of
         rendering it inoperative.  The internal  effect
         (row removal) is implementation dependent.
         ALCATEL NOTE:
          ACCESS:      NA           USAGE:       MAND
          PERSIST:     YES          INSRVMOD:    YES
          RANGE:       1,4,5,6      DEFVALUE:    NA
          UNITS:       NA           SPARSE:      NO
          DESCR:       NA"
    ::= { fsMIStdOspfIfMetricEntry 5 }

fsMIStdOspfVirtIfTable OBJECT-TYPE
    SYNTAX      SEQUENCE OF FsMIStdOspfVirtIfEntry
    ACCESS      not-accessible
    STATUS      mandatory
    DESCRIPTION 
        "Information about this router's virtual inter-
         faces.
         ALCATEL NOTE:
         	TABLE SIZE:  NA   
         	DESCR:       THIS TABLE IS NOT SUPPORTED BY ALCATEL."
--     REFERENCE   
--         "OSPF Version  2,  Appendix  C.4   Virtual  link
--          parameters"
    ::= { fsMIStdOspf 8 }

fsMIStdOspfVirtIfEntry OBJECT-TYPE
    SYNTAX      FsMIStdOspfVirtIfEntry
    ACCESS      not-accessible
    STATUS      mandatory
    DESCRIPTION 
        "Information about a single Virtual Interface.
         Row creation :  NA.
         Row deletion :  NA.
         Index usage :   NA.
         lexicographical order :  NA.
         THIS IS NOT SUPPORTED BY ALCATEL."
    INDEX       { fsMIStdOspfContextId, fsMIStdOspfVirtIfAreaId, 
                  fsMIStdOspfVirtIfNeighbor }
    ::= { fsMIStdOspfVirtIfTable 1 }

FsMIStdOspfVirtIfEntry ::= SEQUENCE {
    fsMIStdOspfVirtIfAreaId             AreaID,
    fsMIStdOspfVirtIfNeighbor           RouterID,
    fsMIStdOspfVirtIfTransitDelay       UpToMaxAge,
    fsMIStdOspfVirtIfRetransInterval    UpToMaxAge,
    fsMIStdOspfVirtIfHelloInterval      HelloRange,
    fsMIStdOspfVirtIfRtrDeadInterval    PositiveInteger,
    fsMIStdOspfVirtIfState              INTEGER,
    fsMIStdOspfVirtIfEvents             Counter,
    fsMIStdOspfVirtIfAuthKey            OCTET STRING,
    fsMIStdOspfVirtIfStatus             RowStatus,
    fsMIStdOspfVirtIfAuthType           INTEGER
}

fsMIStdOspfVirtIfAreaId OBJECT-TYPE
    SYNTAX      AreaID
    ACCESS      not-accessible
    STATUS      mandatory
    DESCRIPTION 
        "The  Transit  Area  that  the   Virtual   Link
         traverses.  By definition, this is not 0.0.0.0
         ALCATEL NOTE:
          ACCESS:      NA           USAGE:       NA
          PERSIST:     NA           INSRVMOD:    NA
          RANGE:       NA           DEFVALUE:    NA
          UNITS:       NA           SPARSE:      NA
          DESCR:       THIS OBJECT IS NOT SUPPORTED BY ALCATEL."
    ::= { fsMIStdOspfVirtIfEntry 1 }

fsMIStdOspfVirtIfNeighbor OBJECT-TYPE
    SYNTAX      RouterID
    ACCESS      not-accessible
    STATUS      mandatory
    DESCRIPTION 
        "The Router ID of the Virtual Neighbor.
         ALCATEL NOTE:
           ACCESS:      NA           USAGE:       NA
           PERSIST:     NA           INSRVMOD:    NA
           RANGE:       NA           DEFVALUE:    NA
           UNITS:       NA           SPARSE:      NA
           DESCR:       THIS OBJECT IS NOT SUPPORTED BY ALCATEL."
    ::= { fsMIStdOspfVirtIfEntry 2 }

fsMIStdOspfVirtIfTransitDelay OBJECT-TYPE
    SYNTAX      UpToMaxAge
    ACCESS      read-write
    STATUS      mandatory
    DESCRIPTION 
        "The estimated number of seconds  it  takes  to
         transmit  a link- state update packet over this
         interface.
         ALCATEL NOTE:
          ACCESS:      NA           USAGE:       NA
          PERSIST:     NA           INSRVMOD:    NA
          RANGE:       NA           DEFVALUE:    NA
          UNITS:       NA           SPARSE:      NA
          DESCR:       THIS OBJECT IS NOT SUPPORTED BY ALCATEL."
    DEFVAL      { 1 }
    ::= { fsMIStdOspfVirtIfEntry 3 }

fsMIStdOspfVirtIfRetransInterval OBJECT-TYPE
    SYNTAX      UpToMaxAge
    ACCESS      read-write
    STATUS      mandatory
    DESCRIPTION 
        "The number of seconds between  link-state  ad-
         vertisement  retransmissions,  for  adjacencies
         belonging to this  interface.   This  value  is
         also used when retransmitting database descrip-
         tion  and  link-state  request  packets.   This
         value  should  be well over the expected round-
         trip time.
         ALCATEL NOTE:
          ACCESS:      NA           USAGE:       NA
          PERSIST:     NA           INSRVMOD:    NA
          RANGE:       NA           DEFVALUE:    NA
          UNITS:       NA           SPARSE:      NA
          DESCR:       THIS OBJECT IS NOT SUPPORTED BY ALCATEL."
    DEFVAL      { 5 }
    ::= { fsMIStdOspfVirtIfEntry 4 }

fsMIStdOspfVirtIfHelloInterval OBJECT-TYPE
    SYNTAX      HelloRange
    ACCESS      read-write
    STATUS      mandatory
    DESCRIPTION 
        "The length of time, in  seconds,  between  the
         Hello  packets that the router sends on the in-
         terface.  This value must be the same  for  the
         virtual neighbor.
         ALCATEL NOTE:
          ACCESS:      NA           USAGE:       NA
          PERSIST:     NA           INSRVMOD:    NA
          RANGE:       NA           DEFVALUE:    NA
          UNITS:       NA           SPARSE:      NA
          DESCR:       THIS OBJECT IS NOT SUPPORTED BY ALCATEL."
    DEFVAL      { 10 }
    ::= { fsMIStdOspfVirtIfEntry 5 }

fsMIStdOspfVirtIfRtrDeadInterval OBJECT-TYPE
    SYNTAX      PositiveInteger
    ACCESS      read-write
    STATUS      mandatory
    DESCRIPTION 
        "The number of seconds that  a  router's  Hello
         packets  have  not been seen before it's neigh-
         bors declare the router down.  This  should  be
         some  multiple  of  the  Hello  interval.  This
         value must be the same for the  virtual  neigh-
         bor
         ALCATEL NOTE:
          ACCESS:      NA           USAGE:       NA
          PERSIST:     NA           INSRVMOD:    NA
          RANGE:       NA           DEFVALUE:    NA
          UNITS:       NA           SPARSE:      NA
          DESCR:       THIS OBJECT IS NOT SUPPORTED BY ALCATEL."
    DEFVAL      { 60 }
    ::= { fsMIStdOspfVirtIfEntry 6 }

fsMIStdOspfVirtIfState OBJECT-TYPE
    SYNTAX      INTEGER { down(1), pointToPoint(4) }
    ACCESS      read-only
    STATUS      mandatory
    DESCRIPTION 
        "OSPF virtual interface states.
         ALCATEL NOTE:
           ACCESS:      NA           USAGE:       NA
           PERSIST:     NA           INSRVMOD:    NA
           RANGE:       NA           DEFVALUE:    NA
           UNITS:       NA           SPARSE:      NA
           DESCR:       THIS OBJECT IS NOT SUPPORTED BY ALCATEL."
    DEFVAL      { down }
    ::= { fsMIStdOspfVirtIfEntry 7 }

fsMIStdOspfVirtIfEvents OBJECT-TYPE
    SYNTAX      Counter
    ACCESS      read-only
    STATUS      mandatory
    DESCRIPTION 
        "The number of state changes or error events on
         this Virtual Link
         ALCATEL NOTE:
          ACCESS:      NA           USAGE:       NA
          PERSIST:     NA           INSRVMOD:    NA
          RANGE:       NA           DEFVALUE:    NA
          UNITS:       NA           SPARSE:      NA
          DESCR:       THIS OBJECT IS NOT SUPPORTED BY ALCATEL."
    ::= { fsMIStdOspfVirtIfEntry 8 }

fsMIStdOspfVirtIfAuthKey OBJECT-TYPE
    SYNTAX      OCTET STRING (SIZE(0..256))
    ACCESS      read-write
    STATUS      mandatory
    DESCRIPTION 
        "If Authentication Type is simplePassword,  the
         device  will left adjust and zero fill to 8 oc-
         tets.
         
         Note that unauthenticated  interfaces  need  no
         authentication key, and simple password authen-
         tication cannot use a key of more  than  8  oc-
         tets.  Larger keys are useful only with authen-
         tication mechanisms not specified in this docu-
         ment.
         
         When  read,  fsMIStdOspfVifAuthKey  always  returns  a
         string of length zero.
         ALCATEL NOTE:
          ACCESS:      NA           USAGE:       NA
          PERSIST:     NA           INSRVMOD:    NA
          RANGE:       NA           DEFVALUE:    NA
          UNITS:       NA           SPARSE:      NA
          DESCR:       THIS OBJECT IS NOT SUPPORTED BY ALCATEL."
--     REFERENCE   
--         "OSPF Version 2, Section 9  The  Interface  Data
--          Structure"
    DEFVAL      { '0000000000000000'H }
    ::= { fsMIStdOspfVirtIfEntry 9 }

fsMIStdOspfVirtIfStatus OBJECT-TYPE
    SYNTAX      RowStatus
    ACCESS      read-write
    STATUS      mandatory
    DESCRIPTION 
        "This variable displays the status of  the  en-
         try.  Setting it to 'invalid' has the effect of
         rendering it inoperative.  The internal  effect
         (row removal) is implementation dependent.
         ALCATEL NOTE:
          ACCESS:      NA           USAGE:       NA
          PERSIST:     NA           INSRVMOD:    NA
          RANGE:       NA           DEFVALUE:    NA
          UNITS:       NA           SPARSE:      NA
          DESCR:       THIS OBJECT IS NOT SUPPORTED BY ALCATEL."
    ::= { fsMIStdOspfVirtIfEntry 10 }

fsMIStdOspfVirtIfAuthType OBJECT-TYPE
    SYNTAX      INTEGER (0..255)
    ACCESS      read-write
    STATUS      mandatory
    DESCRIPTION 
        "The authentication type specified for a virtu-
         al  interface.  Additional authentication types
         may be assigned locally.
         ALCATEL NOTE:
          ACCESS:      NA           USAGE:       NA
          PERSIST:     NA           INSRVMOD:    NA
          RANGE:       NA           DEFVALUE:    NA
          UNITS:       NA           SPARSE:      NA
          DESCR:       THIS OBJECT IS NOT SUPPORTED BY ALCATEL."
--     REFERENCE   
--         "OSPF Version 2, Appendix E Authentication"
    DEFVAL      { 0 }
    ::= { fsMIStdOspfVirtIfEntry 11 }

fsMIStdOspfNbrTable OBJECT-TYPE
    SYNTAX      SEQUENCE OF FsMIStdOspfNbrEntry
    ACCESS      not-accessible
    STATUS      mandatory
    DESCRIPTION 
        "A table of non-virtual neighbor information.
         ALCATEL NOTE:
         	TABLE SIZE:   10
         	DESCR:        NA"
--     REFERENCE   
--         "OSPF Version 2, Section 10  The  Neighbor  Data
--          Structure"
    ::= { fsMIStdOspf 9 }

fsMIStdOspfNbrEntry OBJECT-TYPE
    SYNTAX      FsMIStdOspfNbrEntry
    ACCESS      not-accessible
    STATUS      mandatory
    DESCRIPTION 
        "The information regarding a single neighbor.
         Row creation : An entry shall be created in one step by a 
          set-request with all necessary parameter values and  
          ospfNbmaNbrStatus set to createAndGo(4).
         Row deletion : An entry shall be deleted by setting
          the ospfNbmaNbrStatus of the specific entry to destroy(6).
         Index usage : the index is the Context Id, Ip Address,Address Less Index.
         Note that entries will be presented to the SNMP manager in full
         lexicographical order :  sorted on Context id then on Ip Address,Address Less Index."
--     REFERENCE   
--         "OSPF Version 2, Section 10  The  Neighbor  Data
--          Structure"
    INDEX       { fsMIStdOspfContextId, fsMIStdOspfNbrIpAddr, 
                  fsMIStdOspfNbrAddressLessIndex }
    ::= { fsMIStdOspfNbrTable 1 }

FsMIStdOspfNbrEntry ::= SEQUENCE {
    fsMIStdOspfNbrIpAddr            IpAddress,
    fsMIStdOspfNbrAddressLessIndex  InterfaceIndex,
    fsMIStdOspfNbrRtrId             RouterID,
    fsMIStdOspfNbrOptions           INTEGER,
    fsMIStdOspfNbrPriority          DesignatedRouterPriority,
    fsMIStdOspfNbrState             INTEGER,
    fsMIStdOspfNbrEvents            Counter,
    fsMIStdOspfNbrLsRetransQLen     Gauge,
    fsMIStdOspfNbmaNbrStatus        RowStatus,
    fsMIStdOspfNbmaNbrPermanence    INTEGER,
    fsMIStdOspfNbrHelloSuppressed   TruthValue
}

fsMIStdOspfNbrIpAddr OBJECT-TYPE
    SYNTAX      IpAddress
    ACCESS      not-accessible
    STATUS      mandatory
    DESCRIPTION 
        "The IP address this neighbor is using  in  its
         IP  Source  Address.  Note that, on addressless
         links, this will not be 0.0.0.0,  but  the  ad-
         dress of another of the neighbor's interfaces.
         ALCATEL NOTE:
          ACCESS:      NA           USAGE:       NA
          PERSIST:     YES          INSRVMOD:    NA
          RANGE:       NA           DEFVALUE:    NA
          UNITS:       NA           SPARSE:      NO
          DESCR:       NA"
    ::= { fsMIStdOspfNbrEntry 1 }

fsMIStdOspfNbrAddressLessIndex OBJECT-TYPE
    SYNTAX      InterfaceIndex
    ACCESS      not-accessible
    STATUS      mandatory
    DESCRIPTION 
        "On an interface having an  IP  Address,  zero.
         On  addressless  interfaces,  the corresponding
         value of ifIndex in the Internet Standard  MIB.
         On  row  creation, this can be derived from the
         instance.
         ALCATEL NOTE:
          ACCESS:      NA           USAGE:       NA
          PERSIST:     YES          INSRVMOD:    NA
          RANGE:       NA           DEFVALUE:    NA
          UNITS:       NA           SPARSE:      NO
          DESCR:       NA"
    ::= { fsMIStdOspfNbrEntry 2 }

fsMIStdOspfNbrRtrId OBJECT-TYPE
    SYNTAX      RouterID
    ACCESS      read-only
    STATUS      mandatory
    DESCRIPTION 
        "A 32-bit integer (represented as a type  IpAd-
         dress)  uniquely  identifying  the  neighboring
         router in the Autonomous System.
         ALCATEL NOTE:
          ACCESS:      NA           USAGE:       NA
          PERSIST:     NO           INSRVMOD:    NA
          RANGE:       NA           DEFVALUE:    NA
          UNITS:       NA           SPARSE:      NO
          DESCR:       NA"
    DEFVAL      { '00000000'H }
    ::= { fsMIStdOspfNbrEntry 3 }

fsMIStdOspfNbrOptions OBJECT-TYPE
    SYNTAX      INTEGER
    ACCESS      read-only
    STATUS      mandatory
    DESCRIPTION 
        "A Bit Mask corresponding to the neighbor's op-
         tions field.
         
         Bit 0, if set, indicates that the  system  will
         operate  on  Type of Service metrics other than
         TOS 0.  If zero, the neighbor will  ignore  all
         metrics except the TOS 0 metric.
         
         Bit 1, if set, indicates  that  the  associated
         area  accepts and operates on external informa-
         tion; if zero, it is a stub area.
         
         Bit 2, if set, indicates that the system is ca-
         pable  of routing IP Multicast datagrams; i.e.,
         that it implements the Multicast Extensions  to
         OSPF.
         
         Bit 3, if set, indicates  that  the  associated
         area  is  an  NSSA.  These areas are capable of
         carrying type 7 external advertisements,  which
         are  translated into type 5 external advertise-
         ments at NSSA borders
         ALCATEL NOTE:
          ACCESS:      NA           USAGE:       NA
          PERSIST:     N0           INSRVMOD:    NA
          RANGE:       NA           DEFVALUE:    NA
          UNITS:       NA           SPARSE:      NO
          DESCR:       NA"
--     REFERENCE   
--         "OSPF Version 2, Section 12.1.2 Options"
    DEFVAL      { 0 }
    ::= { fsMIStdOspfNbrEntry 4 }

fsMIStdOspfNbrPriority OBJECT-TYPE
    SYNTAX      DesignatedRouterPriority
    ACCESS      read-write
    STATUS      mandatory
    DESCRIPTION 
        "The priority of this neighbor in the designat-
         ed router election algorithm.  The value 0 sig-
         nifies that the neighbor is not eligible to be-
         come  the  designated router on this particular
         network.
         ALCATEL NOTE:
          ACCESS:      NA           USAGE:       OPT
          PERSIST:     YES          INSRVMOD:    YES
          RANGE:       0..255       DEFVALUE:    NA
          UNITS:       NA           SPARSE:      NO
          DESCR:       NA"
    DEFVAL      { 1 }
    ::= { fsMIStdOspfNbrEntry 5 }

fsMIStdOspfNbrState OBJECT-TYPE
    SYNTAX      INTEGER { down(1), attempt(2), init(3), twoWay(4), 
                    exchangeStart(5), exchange(6), loading(7), full(8) }
    ACCESS      read-only
    STATUS      mandatory
    DESCRIPTION 
        "The State of the relationship with this Neigh-
         bor.
         ALCATEL NOTE:
          ACCESS:      NA           USAGE:       NA
          PERSIST:     NO           INSRVMOD:    NA
          RANGE:       NA           DEFVALUE:    NA
          UNITS:       NA           SPARSE:      NO
          DESCR:       NA"
--     REFERENCE   
--         "OSPF Version 2, Section 10.1 Neighbor States"
    DEFVAL      { down }
    ::= { fsMIStdOspfNbrEntry 6 }

fsMIStdOspfNbrEvents OBJECT-TYPE
    SYNTAX      Counter
    ACCESS      read-only
    STATUS      mandatory
    DESCRIPTION 
        "The number of times this neighbor relationship
         has changed state, or an error has occurred.
         ALCATEL NOTE:
          ACCESS:      NA           USAGE:       NA
          PERSIST:     NO           INSRVMOD:    NA
          RANGE:       NA           DEFVALUE:    0
          UNITS:       NA           SPARSE:      NO
          DESCR:       NA"
    ::= { fsMIStdOspfNbrEntry 7 }

fsMIStdOspfNbrLsRetransQLen OBJECT-TYPE
    SYNTAX      Gauge
    ACCESS      read-only
    STATUS      mandatory
    DESCRIPTION 
        "The  current  length  of  the   retransmission
         queue.
         ALCATEL NOTE:
          ACCESS:      NA           USAGE:       NA
          PERSIST:     NO           INSRVMOD:    NA
          RANGE:       NA           DEFVALUE:    0
          UNITS:       NA           SPARSE:      NO
          DESCR:       NA"
    ::= { fsMIStdOspfNbrEntry 8 }

fsMIStdOspfNbmaNbrStatus OBJECT-TYPE
    SYNTAX      RowStatus
    ACCESS      read-write
    STATUS      mandatory
    DESCRIPTION 
        "This variable displays the status of  the  en-
         try.  Setting it to 'invalid' has the effect of
         rendering it inoperative.  The internal  effect
         (row removal) is implementation dependent.
         ALCATEL NOTE:
          ACCESS:      NA           USAGE:       MAND
          PERSIST:     YES          INSRVMOD:    YES
          RANGE:       1,4,5,6      DEFVALUE:    NA
          UNITS:       NA           SPARSE:      NO
          DESCR:       NA"
    ::= { fsMIStdOspfNbrEntry 9 }

fsMIStdOspfNbmaNbrPermanence OBJECT-TYPE
    SYNTAX      INTEGER { dynamic(1), permanent(2) }
    ACCESS      read-only
    STATUS      mandatory
    DESCRIPTION 
        "This variable displays the status of  the  en-
         try.   'dynamic'  and  'permanent' refer to how
         the neighbor became known.
         ALCATEL NOTE:
          ACCESS:      NA           USAGE:       NA
          PERSIST:     NO           INSRVMOD:    NA
          RANGE:       NA           DEFVALUE:    NA
          UNITS:       NA           SPARSE:      NO
          DESCR:       NA"
    DEFVAL      { permanent }
    ::= { fsMIStdOspfNbrEntry 10 }

fsMIStdOspfNbrHelloSuppressed OBJECT-TYPE
    SYNTAX      TruthValue
    ACCESS      read-only
    STATUS      mandatory
    DESCRIPTION 
        "Indicates whether Hellos are being  suppressed
         to the neighbor
         ALCATEL NOTE:
          ACCESS:      NA           USAGE:       NA
          PERSIST:     NO           INSRVMOD:    NA
          RANGE:       1,2          DEFVALUE:    2 
          UNITS:       NA           SPARSE:      NO
          DESCR:       NA"
    ::= { fsMIStdOspfNbrEntry 11 }

fsMIStdOspfVirtNbrTable OBJECT-TYPE
    SYNTAX      SEQUENCE OF FsMIStdOspfVirtNbrEntry
    ACCESS      not-accessible
    STATUS      mandatory
    DESCRIPTION 
        "A table of virtual neighbor information.
         ALCATEL NOTE:
         	TABLE SIZE:   NA
         	 DESCR:       THIS TABLE IS NOT SUPPORTED BY ALCATEL."
--     REFERENCE   
--         "OSPF Version 2, Section 15  Virtual Links"
    ::= { fsMIStdOspf 10 }

fsMIStdOspfVirtNbrEntry OBJECT-TYPE
    SYNTAX      FsMIStdOspfVirtNbrEntry
    ACCESS      not-accessible
    STATUS      mandatory
    DESCRIPTION 
        "Virtual neighbor information.
         Row creation :  NA
         Row deletion :  NA
         Index usage :   NA
         lexicographical order :  NA
         	THIS TABLE IS NOT SUPPORTED BY ALCATEL."
    INDEX       { fsMIStdOspfContextId, fsMIStdOspfVirtNbrArea, 
                  fsMIStdOspfVirtNbrRtrId }
    ::= { fsMIStdOspfVirtNbrTable 1 }

FsMIStdOspfVirtNbrEntry ::= SEQUENCE {
    fsMIStdOspfVirtNbrArea              AreaID,
    fsMIStdOspfVirtNbrRtrId             RouterID,
    fsMIStdOspfVirtNbrIpAddr            IpAddress,
    fsMIStdOspfVirtNbrOptions           INTEGER,
    fsMIStdOspfVirtNbrState             INTEGER,
    fsMIStdOspfVirtNbrEvents            Counter,
    fsMIStdOspfVirtNbrLsRetransQLen     Gauge,
    fsMIStdOspfVirtNbrHelloSuppressed   TruthValue
}

fsMIStdOspfVirtNbrArea OBJECT-TYPE
    SYNTAX      AreaID
    ACCESS      not-accessible
    STATUS      mandatory
    DESCRIPTION 
        "The Transit Area Identifier.
         ALCATEL NOTE:
           ACCESS:      NA           USAGE:       NA
           PERSIST:     NA           INSRVMOD:    NA
           RANGE:       NA           DEFVALUE:    NA
           UNITS:       NA           SPARSE:      NA
           DESCR:       THIS TABLE IS NOT SUPPORTED BY ALCATEL."
    ::= { fsMIStdOspfVirtNbrEntry 1 }

fsMIStdOspfVirtNbrRtrId OBJECT-TYPE
    SYNTAX      RouterID
    ACCESS      not-accessible
    STATUS      mandatory
    DESCRIPTION 
        "A  32-bit  integer  uniquely  identifying  the
         neighboring router in the Autonomous System.
         ALCATEL NOTE:
          ACCESS:      NA           USAGE:       NA
          PERSIST:     NA           INSRVMOD:    NA
          RANGE:       NA           DEFVALUE:    NA
          UNITS:       NA           SPARSE:      NA
          DESCR:       THIS TABLE IS NOT SUPPORTED BY ALCATEL."
    ::= { fsMIStdOspfVirtNbrEntry 2 }

fsMIStdOspfVirtNbrIpAddr OBJECT-TYPE
    SYNTAX      IpAddress
    ACCESS      read-only
    STATUS      mandatory
    DESCRIPTION 
        "The IP address this Virtual  Neighbor  is  us-
         ing.
         ALCATEL NOTE:
          ACCESS:      NA           USAGE:       NA
          PERSIST:     NA           INSRVMOD:    NA
          RANGE:       NA           DEFVALUE:    NA
          UNITS:       NA           SPARSE:      NA
          DESCR:       THIS TABLE IS NOT SUPPORTED BY ALCATEL."
    ::= { fsMIStdOspfVirtNbrEntry 3 }

fsMIStdOspfVirtNbrOptions OBJECT-TYPE
    SYNTAX      INTEGER
    ACCESS      read-only
    STATUS      mandatory
    DESCRIPTION 
        "A Bit Mask corresponding to the neighbor's op-
         tions field.
         
         Bit 1, if set, indicates that the  system  will
         operate  on  Type of Service metrics other than
         TOS 0.  If zero, the neighbor will  ignore  all
         metrics except the TOS 0 metric.
         
         Bit 2, if set, indicates  that  the  system  is
         Network  Multicast  capable; ie, that it imple-
         ments OSPF Multicast Routing.
         ALCATEL NOTE:
          ACCESS:      NA           USAGE:       NA
          PERSIST:     NA           INSRVMOD:    NA
          RANGE:       NA           DEFVALUE:    NA
          UNITS:       NA           SPARSE:      NA
          DESCR:       THIS TABLE IS NOT SUPPORTED BY ALCATEL."
    ::= { fsMIStdOspfVirtNbrEntry 4 }

fsMIStdOspfVirtNbrState OBJECT-TYPE
    SYNTAX      INTEGER { down(1), attempt(2), init(3), twoWay(4), 
                    exchangeStart(5), exchange(6), loading(7), full(8) }
    ACCESS      read-only
    STATUS      mandatory
    DESCRIPTION 
        "The state of the  Virtual  Neighbor  Relation-
         ship.
         ALCATEL NOTE:
          ACCESS:      NA           USAGE:       NA
          PERSIST:     NA           INSRVMOD:    NA
          RANGE:       NA           DEFVALUE:    NA
          UNITS:       NA           SPARSE:      NA
          DESCR:       THIS TABLE IS NOT SUPPORTED BY ALCATEL."
    ::= { fsMIStdOspfVirtNbrEntry 5 }

fsMIStdOspfVirtNbrEvents OBJECT-TYPE
    SYNTAX      Counter
    ACCESS      read-only
    STATUS      mandatory
    DESCRIPTION 
        "The number of  times  this  virtual  link  has
         changed its state, or an error has occurred.
         ALCATEL NOTE:
          ACCESS:      NA           USAGE:       NA
          PERSIST:     NA           INSRVMOD:    NA
          RANGE:       NA           DEFVALUE:    NA
          UNITS:       NA           SPARSE:      NA
          DESCR:       THIS TABLE IS NOT SUPPORTED BY ALCATEL."
    ::= { fsMIStdOspfVirtNbrEntry 6 }

fsMIStdOspfVirtNbrLsRetransQLen OBJECT-TYPE
    SYNTAX      Gauge
    ACCESS      read-only
    STATUS      mandatory
    DESCRIPTION 
        "The  current  length  of  the   retransmission
         queue.
         ALCATEL NOTE:
          ACCESS:      NA           USAGE:       NA
          PERSIST:     NA           INSRVMOD:    NA
          RANGE:       NA           DEFVALUE:    NA
          UNITS:       NA           SPARSE:      NA
          DESCR:       THIS TABLE IS NOT SUPPORTED BY ALCATEL."
    ::= { fsMIStdOspfVirtNbrEntry 7 }

fsMIStdOspfVirtNbrHelloSuppressed OBJECT-TYPE
    SYNTAX      TruthValue
    ACCESS      read-only
    STATUS      mandatory
    DESCRIPTION 
        "Indicates whether Hellos are being  suppressed
         to the neighbor
         ALCATEL NOTE:
          ACCESS:      NA           USAGE:       NA
          PERSIST:     NA           INSRVMOD:    NA
          RANGE:       NA           DEFVALUE:    NA
          UNITS:       NA           SPARSE:      NA
          DESCR:       THIS TABLE IS NOT SUPPORTED BY ALCATEL."
    ::= { fsMIStdOspfVirtNbrEntry 8 }

fsMIStdOspfExtLsdbTable OBJECT-TYPE
    SYNTAX      SEQUENCE OF FsMIStdOspfExtLsdbEntry
    ACCESS      not-accessible
    STATUS      mandatory
    DESCRIPTION 
        "The OSPF Process's Links State Database.
         ALCATEL NOTE:
         	TABLE SIZE:  200                      
         	DESCR:       NA"
--     REFERENCE   
--         "OSPF Version 2, Section 12  Link  State  Adver-
--          tisements"
    ::= { fsMIStdOspf 11 }

fsMIStdOspfExtLsdbEntry OBJECT-TYPE
    SYNTAX      FsMIStdOspfExtLsdbEntry
    ACCESS      not-accessible
    STATUS      mandatory
    DESCRIPTION 
        "A single Link State Advertisement.
         Row creation : An entry will be created when LSAs are received.
         Row deletion : An entry can not be deleted.
         Index usage : the index is the Ospf Context Id, Link State Type,Link State Id,Link State Router Id.
         Note that entries will be presented to the SNMP manager in full
         lexicographical order :  sorted on Ospf Context Id then on Link State Type,Link State Id,Link State Router Id."
    INDEX       { fsMIStdOspfContextId, fsMIStdOspfExtLsdbType, 
                  fsMIStdOspfExtLsdbLsid, fsMIStdOspfExtLsdbRouterId }
    ::= { fsMIStdOspfExtLsdbTable 1 }

FsMIStdOspfExtLsdbEntry ::= SEQUENCE {
    fsMIStdOspfExtLsdbType              INTEGER,
    fsMIStdOspfExtLsdbLsid              IpAddress,
    fsMIStdOspfExtLsdbRouterId          RouterID,
    fsMIStdOspfExtLsdbSequence          INTEGER,
    fsMIStdOspfExtLsdbAge               INTEGER,
    fsMIStdOspfExtLsdbChecksum          INTEGER,
    fsMIStdOspfExtLsdbAdvertisement     OCTET STRING
}

fsMIStdOspfExtLsdbType OBJECT-TYPE
    SYNTAX      INTEGER { asExternalLink(5) }
    ACCESS      not-accessible
    STATUS      mandatory
    DESCRIPTION 
        "The type  of  the  link  state  advertisement.
         Each  link state type has a separate advertise-
         ment format.
         ALCATEL NOTE:
          ACCESS:      NA           USAGE:       NA
          PERSIST:     NO           INSRVMOD:    NA
          RANGE:       NA           DEFVALUE:    NA                          
          UNITS:       NA           SPARSE:      NO
          DESCR:       NA"
--     REFERENCE   
--         "OSPF Version 2, Appendix A.4.1 The  Link  State
--          Advertisement header"
    ::= { fsMIStdOspfExtLsdbEntry 1 }

fsMIStdOspfExtLsdbLsid OBJECT-TYPE
    SYNTAX      IpAddress
    ACCESS      not-accessible
    STATUS      mandatory
    DESCRIPTION 
        "The Link State ID is an LS Type Specific field
         containing either a Router ID or an IP Address;
         it identifies the piece of the  routing  domain
         that is being described by the advertisement.
         ALCATEL NOTE:
          ACCESS:      NA           USAGE:       NA
          PERSIST:     NO           INSRVMOD:    NA
          RANGE:       NA           DEFVALUE:    NA                       
          UNITS:       NA           SPARSE:      NO
          DESCR:       NA"
--     REFERENCE   
--         "OSPF Version 2, Section 12.1.4 Link State ID"
    ::= { fsMIStdOspfExtLsdbEntry 2 }

fsMIStdOspfExtLsdbRouterId OBJECT-TYPE
    SYNTAX      RouterID
    ACCESS      not-accessible
    STATUS      mandatory
    DESCRIPTION 
        "The 32 bit number that uniquely identifies the
         originating router in the Autonomous System.
         ALCATEL NOTE:
          ACCESS:      NA           USAGE:       NA
          PERSIST:     NO           INSRVMOD:    NA
          RANGE:       NA           DEFVALUE:    NA                         
          UNITS:       NA           SPARSE:      NO
          DESCR:       NA"
--     REFERENCE   
--         "OSPF Version 2, Appendix C.1 Global parameters"
    ::= { fsMIStdOspfExtLsdbEntry 3 }

fsMIStdOspfExtLsdbSequence OBJECT-TYPE
    SYNTAX      INTEGER
    ACCESS      read-only
    STATUS      mandatory
    DESCRIPTION 
        "The sequence number field is a  signed  32-bit
         integer.   It  is used to detect old and dupli-
         cate link state advertisements.  The  space  of
         sequence  numbers  is  linearly  ordered.   The
         larger the sequence number the more recent  the
         advertisement.
         ALCATEL NOTE:
          ACCESS:      NA           USAGE:       NA
          PERSIST:     NO           INSRVMOD:    NA
          RANGE:       NA           DEFVALUE:    NA
          UNITS:       NA           SPARSE:      NO
          DESCR:       NA"
--     REFERENCE   
--         "OSPF Version  2,  Section  12.1.6  LS  sequence
--          number"
    ::= { fsMIStdOspfExtLsdbEntry 4 }

fsMIStdOspfExtLsdbAge OBJECT-TYPE
    SYNTAX      INTEGER
    ACCESS      read-only
    STATUS      mandatory
    DESCRIPTION 
        "This field is the age of the link state adver-
         tisement in seconds.
         ALCATEL NOTE:
          ACCESS:      NA           USAGE:       NA
          PERSIST:     NO           INSRVMOD:    NA
          RANGE:       0..3600      DEFVALUE:    0
          UNITS:       SECONDS      SPARSE:      NO
          DESCR:       NA"
--     REFERENCE   
--         "OSPF Version 2, Section 12.1.1 LS age"
    ::= { fsMIStdOspfExtLsdbEntry 5 }

fsMIStdOspfExtLsdbChecksum OBJECT-TYPE
    SYNTAX      INTEGER
    ACCESS      read-only
    STATUS      mandatory
    DESCRIPTION 
        "This field is the  checksum  of  the  complete
         contents  of  the  advertisement, excepting the
         age field.  The age field is excepted  so  that
         an   advertisement's  age  can  be  incremented
         without updating the  checksum.   The  checksum
         used  is  the same that is used for ISO connec-
         tionless datagrams; it is commonly referred  to
         as the Fletcher checksum.
         ALCATEL NOTE:
          ACCESS:      NA           USAGE:       NA
          PERSIST:     NO           INSRVMOD:    NA
          RANGE:       NA           DEFVALUE:    0
          UNITS:       NA           SPARSE:      NO
          DESCR:       NA"
--     REFERENCE   
--         "OSPF Version 2, Section 12.1.7 LS checksum"
    ::= { fsMIStdOspfExtLsdbEntry 6 }

fsMIStdOspfExtLsdbAdvertisement OBJECT-TYPE
    SYNTAX      OCTET STRING (SIZE(36))
    ACCESS      read-only
    STATUS      mandatory
    DESCRIPTION 
        "The entire Link State Advertisement, including
         its header.
         ALCATEL NOTE:
          ACCESS:      NA           USAGE:       NA
          PERSIST:     NO           INSRVMOD:    NA
          RANGE:       NA           DEFVALUE:    '\0'
          UNITS:       NA           SPARSE:      NO
          DESCR:       NA"
--     REFERENCE   
--         "OSPF Version 2, Section 12  Link  State  Adver-
--          tisements"
    ::= { fsMIStdOspfExtLsdbEntry 7 }

fsMIStdOspfRouteGroup OBJECT IDENTIFIER
    ::= { fsMIStdOspf 12 }

fsMIStdOspfIntraArea OBJECT IDENTIFIER
    ::= { fsMIStdOspfRouteGroup 1 }

fsMIStdOspfInterArea OBJECT IDENTIFIER
    ::= { fsMIStdOspfRouteGroup 2 }

fsMIStdOspfExternalType1 OBJECT IDENTIFIER
    ::= { fsMIStdOspfRouteGroup 3 }

fsMIStdOspfExternalType2 OBJECT IDENTIFIER
    ::= { fsMIStdOspfRouteGroup 4 }

fsMIStdOspfAreaAggregateTable OBJECT-TYPE
    SYNTAX      SEQUENCE OF FsMIStdOspfAreaAggregateEntry
    ACCESS      not-accessible
    STATUS      mandatory
    DESCRIPTION 
        "A range of IP addresses  specified  by  an  IP
         address/IP  network  mask  pair.   For example,
         class B address range of X.X.X.X with a network
         mask  of  255.255.0.0 includes all IP addresses
         from X.X.0.0  to  X.X.255.255.   Note  that  if
         ranges  are configured such that one range sub-
         sumes  another  range  (e.g.,   10.0.0.0   mask
         255.0.0.0  and  10.1.0.0 mask 255.255.0.0), the 
          most specific match is the preferred one.
         
         ALCATEL NOTE:
         	TABLE SIZE:   30            
         	DESCR:        NA"
--     REFERENCE   
--         "OSPF Version 2, Appendix C.2  Area parameters"
    ::= { fsMIStdOspf 13 }

fsMIStdOspfAreaAggregateEntry OBJECT-TYPE
    SYNTAX      FsMIStdOspfAreaAggregateEntry
    ACCESS      not-accessible
    STATUS      mandatory
    DESCRIPTION 
        "A range of IP addresses  specified  by  an  IP
         address/IP  network  mask  pair.   For example,
         class B address range of X.X.X.X with a network
         mask  of  255.255.0.0 includes all IP addresses
         from X.X.0.0  to  X.X.255.255.   Note  that  if
         ranges are range configured such that one range
         subsumes another  range  (e.g.,  10.0.0.0  mask
         255.0.0.0  and  10.1.0.0 mask 255.255.0.0), the
         most specific match is the preferred one.
         Row creation : An entry shall be created in one step by a 
         set-request with all necessary parameter values and  
         ospfAreaAggregateStatus set to createAndGo(4).
         Row deletion : An entry shall be deleted by setting
         the ospfAreaAggregateStatus of the specific entry to destroy(6).
         Index usage : the index is the Ospf Context IdArea Id,Link State type,Area Aggregate net,Area Aggregate Mask.
         Note that entries will be presented to the SNMP manager in full
         lexicographical order :  sorted on Ospf Context Id then on Area Id,Link State type,Area Aggregate net,Area Aggregate Mask."
--     REFERENCE   
--         "OSPF Version 2, Appendix C.2  Area parameters"
    INDEX       { fsMIStdOspfContextId, fsMIStdOspfAreaAggregateAreaID, 
                  fsMIStdOspfAreaAggregateLsdbType, 
                  fsMIStdOspfAreaAggregateNet, 
                  fsMIStdOspfAreaAggregateMask }
    ::= { fsMIStdOspfAreaAggregateTable 1 }

FsMIStdOspfAreaAggregateEntry ::= SEQUENCE {
    fsMIStdOspfAreaAggregateAreaID      AreaID,
    fsMIStdOspfAreaAggregateLsdbType    INTEGER,
    fsMIStdOspfAreaAggregateNet         IpAddress,
    fsMIStdOspfAreaAggregateMask        IpAddress,
    fsMIStdOspfAreaAggregateStatus      RowStatus,
    fsMIStdOspfAreaAggregateEffect      INTEGER
}

fsMIStdOspfAreaAggregateAreaID OBJECT-TYPE
    SYNTAX      AreaID
    ACCESS      not-accessible
    STATUS      mandatory
    DESCRIPTION 
        "The Area the Address Aggregate is to be  found
         within.
         ALCATEL NOTE:
          ACCESS:      NA           USAGE:       NA
          PERSIST:     YES          INSRVMOD:    NA
          RANGE:       NA           DEFVALUE:    NA
          UNITS:       NA           SPARSE:      NO
          DESCR:       NA"
--     REFERENCE   
--         "OSPF Version 2, Appendix C.2 Area parameters"
    ::= { fsMIStdOspfAreaAggregateEntry 1 }

fsMIStdOspfAreaAggregateLsdbType OBJECT-TYPE
    SYNTAX      INTEGER { summaryLink(3), nssaExternalLink(7) }
    ACCESS      not-accessible
    STATUS      mandatory
    DESCRIPTION 
        "The type of the Address Aggregate.  This field
         specifies  the  Lsdb type that this Address Ag-
         gregate applies to.
         ALCATEL NOTE:
          ACCESS:      NA           USAGE:       NA
          PERSIST:     YES          INSRVMOD:    NA
          RANGE:       NA           DEFVALUE:    NA   
          UNITS:       NA           SPARSE:      NO
          DESCR:       NA"
--     REFERENCE   
--         "OSPF Version 2, Appendix A.4.1 The  Link  State
--          Advertisement header"
    ::= { fsMIStdOspfAreaAggregateEntry 2 }

fsMIStdOspfAreaAggregateNet OBJECT-TYPE
    SYNTAX      IpAddress
    ACCESS      not-accessible
    STATUS      mandatory
    DESCRIPTION 
        "The IP Address of the Net or Subnet  indicated
         by the range.
         ALCATEL NOTE:
          ACCESS:      NA           USAGE:       NA
          PERSIST:     YES          INSRVMOD:    NA
          RANGE:       NA           DEFVALUE:    NA
          UNITS:       NA           SPARSE:      NO
          DESCR:       NA"
--     REFERENCE   
--         "OSPF Version 2, Appendix C.2 Area parameters"
    ::= { fsMIStdOspfAreaAggregateEntry 3 }

fsMIStdOspfAreaAggregateMask OBJECT-TYPE
    SYNTAX      IpAddress
    ACCESS      not-accessible
    STATUS      mandatory
    DESCRIPTION 
        "The Subnet Mask that pertains to  the  Net  or
         Subnet.
         ALCATEL NOTE:
          ACCESS:      NA           USAGE:       NA
          PERSIST:     YES          INSRVMOD:    NA
          RANGE:       NA           DEFVALUE:    NA
          UNITS:       NA           SPARSE:      NO
          DESCR:       NA"
--     REFERENCE   
--         "OSPF Version 2, Appendix C.2 Area parameters"
    ::= { fsMIStdOspfAreaAggregateEntry 4 }

fsMIStdOspfAreaAggregateStatus OBJECT-TYPE
    SYNTAX      RowStatus
    ACCESS      read-write
    STATUS      mandatory
    DESCRIPTION 
        "This variable displays the status of  the  en-
         try.  Setting it to 'invalid' has the effect of
         rendering it inoperative.  The internal  effect
         (row removal) is implementation dependent.
         ALCATEL NOTE:
          ACCESS:      NA           USAGE:       MAND
          PERSIST:     YES          INSRVMOD:    YES
          RANGE:       1,4,5,6      DEFVALUE:    NA
          UNITS:       NA           SPARSE:      NO
          DESCR:       NA"
    ::= { fsMIStdOspfAreaAggregateEntry 5 }

fsMIStdOspfAreaAggregateEffect OBJECT-TYPE
    SYNTAX      INTEGER { advertiseMatching(1), 
                    doNotAdvertiseMatching(2) }
    ACCESS      read-write
    STATUS      mandatory
    DESCRIPTION 
        "Subnets subsumed by ranges either trigger  the
         advertisement  of  the indicated aggregate (ad-
         vertiseMatching), or result in the subnet's not
         being advertised at all outside the area.
         ALCATEL NOTE:
          ACCESS:      NA           USAGE:       OPT
          PERSIST:     YES          INSRVMOD:    YES
          RANGE:       NA           DEFVALUE:    NA
          UNITS:       NA           SPARSE:      NO
          DESCR:       NA"
    DEFVAL      { advertiseMatching }
    ::= { fsMIStdOspfAreaAggregateEntry 6 }

END -- end of module ARICENT-MISTDOSPF-MIB.
