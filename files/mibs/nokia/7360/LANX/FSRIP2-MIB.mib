--
-- This SMIv1 module has been generated by smidump 0.4.8. Do not edit.
--

FSRIP2-MIB DEFINITIONS ::= BEGIN

IMPORTS
    OBJECT-TYPE
        FROM RFC-1212
    Counter, Gauge, IpAddress, enterprises
        FROM RFC1155-SMI
    RowStatus
        FROM SNMPv2-TC;

fsrip OBJECT IDENTIFIER
    ::= { enterprises futuresoftware(2076) 75 }

-- fsrip MODULE-IDENTITY
--     LAST-UPDATED "200112191200Z"
--     ORGANIZATION 
--         "FUTURE SOFTWARE PVT. LIMITED"
--     CONTACT-INFO 
--         " FUTURE SOFTWARE PVT. LIMITED
--          481 Mount Road
--          Madras - 600 035
--          Phone : +91-44-433 055 0 
--          support@futsoft.com"
--     DESCRIPTION 
--         " ||||||"
--     REVISION    "200112191200Z"
--     DESCRIPTION 
--         "The initial revision of this MIB module was published as
--          RFC 1450."
--     ::= { enterprises futuresoftware(2076) 75 }


rip2GeneralGroup OBJECT IDENTIFIER
    ::= { fsrip 1 }

fsRip2Security OBJECT-TYPE
    SYNTAX      INTEGER { minimumSecurity(1), maximumSecurity(2) }
    ACCESS      read-write
    STATUS      mandatory
    DESCRIPTION 
        "A variable denotes the security level of RIP-2
         in the system. The value `minimumSecurity` denotes
         that the RIP1 packets will be accepted even when
         authentication is in use. The value `maximumSecurity`
         denotes that RIP1 packets will be ignored when
         authentication is in use
         ALCATEL NOTE:
         ACCESS:      NA           USAGE:       NA
         PERSIST:     YES          INSRVMOD:    YES
         RANGE:       NA           DEFVALUE:    NA      
         UNITS:       NA           SPARSE:      NA
         DESCR:       NA"
    DEFVAL      { maximumSecurity }
    ::= { rip2GeneralGroup 1 }

fsRip2Peers OBJECT-TYPE
    SYNTAX      INTEGER (1..65535)
    ACCESS      read-write
    STATUS      mandatory
    DESCRIPTION 
        "The maximum number of peers that can be in conversation
         with the RIP2 system simultaneously
         ALCATEL NOTE:
         ACCESS:      NA           USAGE:       NA
         PERSIST:     YES          INSRVMOD:    YES
         RANGE:       1..25        DEFVALUE:    25
         UNITS:       NA           SPARSE:      NA
         DESCR:       NA"
    ::= { rip2GeneralGroup 2 }

fsRip2TrustNBRListEnable OBJECT-TYPE
    SYNTAX      INTEGER { enabled(1), disabled(2) }
    ACCESS      read-write
    STATUS      mandatory
    DESCRIPTION 
        "The status of neighbor list in the router.
         The value 'enabled' denotes that a list of
         router's IP address can be configured and 
         RIP Packets from those router's will be processed 
         by RIP and packets from other Routers will be dropped.
         'Disabled' denotes that RIP Packet from all the
         router's will be processed.
         ALCATEL NOTE:
         ACCESS:      NA           USAGE:       NA
         PERSIST:     YES          INSRVMOD:    YES
         RANGE:       NA           DEFVALUE:    NA      
         UNITS:       NA           SPARSE:      NA
         DESCR:       NA"
    DEFVAL      { disabled }
    ::= { rip2GeneralGroup 3 }

fsRip2NumberOfDroppedPkts OBJECT-TYPE
    SYNTAX      Counter
    ACCESS      read-only
    STATUS      mandatory
    DESCRIPTION 
        "Number of RIP Packets dropped because of
         neighbor list check.
         ALCATEL NOTE:
         ACCESS:      NA           USAGE:       NA
         PERSIST:     NO           INSRVMOD:    NA
         RANGE:       NA           DEFVALUE:    0       
         UNITS:       RIP packets  SPARSE:      NA
         DESCR:       NA"
    ::= { rip2GeneralGroup 4 }

fsRip2SpacingEnable OBJECT-TYPE
    SYNTAX      INTEGER { enabled(1), disabled(2) }
    ACCESS      read-write
    STATUS      mandatory
    DESCRIPTION 
        "Whether spacing is enabled or not. If spacing 
         is enabled, generation of periodic update packet 
         will be split and send.
         ALCATEL NOTE:
         ACCESS:      NA           USAGE:       NA
         PERSIST:     YES          INSRVMOD:    YES
         RANGE:       NA           DEFVALUE:    NA      
         UNITS:       NA           SPARSE:      NA
         DESCR:       NA"
    DEFVAL      { disabled }
    ::= { rip2GeneralGroup 5 }

fsRip2RetransTimeoutInt OBJECT-TYPE
    SYNTAX      INTEGER (5..10)
    ACCESS      read-write
    STATUS      mandatory
    DESCRIPTION 
        "The timeout interval to be used to retransmit the Update 
         request packet or an unacknowledged update response packet.
         ALCATEL NOTE:
         ACCESS:      NA           USAGE:       NA
         PERSIST:     YES          INSRVMOD:    YES
         RANGE:       NA           DEFVALUE:    NA      
         UNITS:       seconds      SPARSE:      NA
         DESCR:       NA"
    DEFVAL      { 5 }
    ::= { rip2GeneralGroup 6 }

fsRip2MaxRetransmissions OBJECT-TYPE
    SYNTAX      INTEGER (10..40)
    ACCESS      read-write
    STATUS      mandatory
    DESCRIPTION 
        "The maximum number of retransmissions of the update request and update response packets. If no response is received then the routes via the next hop router are marked unreachable.
         ALCATEL NOTE:
             ACCESS:      NA           USAGE:       NA
             PERSIST:     YES          INSRVMOD:    YES
             RANGE:       NA           DEFVALUE:    NA      
             UNITS:       NA           SPARSE:      NA
             DESCR:       NA"
    DEFVAL      { 36 }
    ::= { rip2GeneralGroup 7 }

fsRip2OverSubscriptionTimeout OBJECT-TYPE
    SYNTAX      INTEGER (100..300)
    ACCESS      read-write
    STATUS      mandatory
    DESCRIPTION 
        "Over subscription timeout value as mentioned in RFC 2091.When a
         Circuit DOWN message is received from the circuit manager, this 
         timer will be started for the specified timeout value.
         ALCATEL NOTE:
         ACCESS:      NA           USAGE:       NA
         PERSIST:     YES          INSRVMOD:    YES
         RANGE:       NA           DEFVALUE:    NA      
         UNITS:       seconds      SPARSE:      NA
         DESCR:       NA"
    DEFVAL      { 180 }
    ::= { rip2GeneralGroup 8 }

fsRip2Propagate OBJECT-TYPE
    SYNTAX      INTEGER { enable(1), disable(2) }
    ACCESS      read-write
    STATUS      mandatory
    DESCRIPTION 
        "Is propagation of static route is enabled or not. If it
         is enabled then routing protocols (like RIP) are allowed
         to include static routes in the update messages.
         ALCATEL NOTE:
         ACCESS:      NA           USAGE:       NA
         PERSIST:     YES          INSRVMOD:    YES
         RANGE:       NA           DEFVALUE:    NA      
         UNITS:       NA	      SPARSE:      NA
         DESCR:       NA"
    DEFVAL      { disable }
    ::= { rip2GeneralGroup 9 }

fsRip2MaxRoutes OBJECT-TYPE
    SYNTAX      INTEGER
    ACCESS      read-only
    STATUS      mandatory
    DESCRIPTION 
        "This object represents the Maximum number of Rip 
         Routes that can be sent in RIP domain. Current value is 200
         ALCATEL NOTE:
         ACCESS:      NA           USAGE:       NA
         PERSIST:     NO	      INSRVMOD:    NA
         RANGE:       800   	      DEFVALUE:    800      
         UNITS:       routes       SPARSE:      NA
         DESCR:       NA"
    ::= { rip2GeneralGroup 10 }

fsRipTrcFlag OBJECT-TYPE
    SYNTAX      INTEGER (0..255)
    ACCESS      read-write
    STATUS      mandatory
    DESCRIPTION 
        "Enables the tracing in the RIP. A 32 bit integer
         is used to store the Tracing level in the specified module.
         Different Tracing Levels -
         BIT 0 - Initialisation and Shutdown Trace.
         BIT 1 - Management trace.
         BIT 2 - Data path trace.
         BIT 3 - Control Plane trace.
         BIT 4 - Packet Dump.
         BIT 5 - OS Resource trace.
         BIT 6 - All Failure trace (All failures including Packet Validation)
         BIT 7 - Buffer Trace.
         ALCATEL NOTE:
           ACCESS:      NA           USAGE:       NA
           PERSIST:     YES          INSRVMOD:    YES
           RANGE:       NA           DEFVALUE:    NA      
           UNITS:       NA	        SPARSE:      NA
           DESCR:       NA"
    DEFVAL      { 0 }
    ::= { rip2GeneralGroup 11 }

fsRip2NBRTrustListTable OBJECT-TYPE
    SYNTAX      SEQUENCE OF FsRip2NBRTrustListEntry
    ACCESS      not-accessible
    STATUS      mandatory
    DESCRIPTION 
        "This table contains a list of Router addresses 
         from which you can receive RIP Packets
         ALCATEL NOTE:
         TABLESIZE:	 10
         DESCR:       NA"
    ::= { rip2GeneralGroup 12 }

fsRip2NBRTrustListEntry OBJECT-TYPE
    SYNTAX      FsRip2NBRTrustListEntry
    ACCESS      not-accessible
    STATUS      mandatory
    DESCRIPTION 
        "An entry of fsRip2NBRTrustListTable.
         Row creation : A fsRip2NBRTrustList Entry shall be created in one step by a
             		set-request with all necessary parameter values and
             		fsRip2TrustNBRRowStatus set to createAndGo(4).
         Row deletion : A fsRip2NBRTrustList Entry shall be deleted by setting
             		the fsRip2TrustNBRRowStatus of the specific entry to destroy(6).
         Index usage : the index is the fsRip2TrustNBRIpAddr.
         Note that entries will be presented to the SNMP manager in full
         lexicographical order :  sorted on fsRip2TrustNBRIpAddr."
    INDEX       { fsRip2TrustNBRIpAddr }
    ::= { fsRip2NBRTrustListTable 1 }

FsRip2NBRTrustListEntry ::= SEQUENCE {
    fsRip2TrustNBRIpAddr        IpAddress,
    fsRip2TrustNBRRowStatus     RowStatus
}

fsRip2TrustNBRIpAddr OBJECT-TYPE
    SYNTAX      IpAddress
    ACCESS      read-only
    STATUS      mandatory
    DESCRIPTION 
        "Ipaddress of the Router from which this router 
         can accept RIP Packets
         ALCATEL NOTE:
         ACCESS:      NA           USAGE:       NA
         PERSIST:     YES          INSRVMOD:    NA
         RANGE:       NA           DEFVALUE:    NA
         UNITS:       NA	      SPARSE:      NO
         DESCR:       NA"
    ::= { fsRip2NBRTrustListEntry 1 }

fsRip2TrustNBRRowStatus OBJECT-TYPE
    SYNTAX      RowStatus
    ACCESS      read-write
    STATUS      mandatory
    DESCRIPTION 
        "The row status variable, used according to
         row installation and removal conventions.
         ALCATEL NOTE:
         ACCESS:      NA           USAGE:       MAND
         PERSIST:     YES          INSRVMOD:    YES
         RANGE:       1,2,4,5,6    DEFVALUE:    NA
         UNITS:       NA	      SPARSE:      NO
         DESCR:       NA"
    ::= { fsRip2NBRTrustListEntry 2 }

fsRip2IfConfTable OBJECT-TYPE
    SYNTAX      SEQUENCE OF FsRip2IfConfEntry
    ACCESS      not-accessible
    STATUS      mandatory
    DESCRIPTION 
        "A list of subnets which require separate
         configuration in RIP.
         ALCATEL NOTE:
         TABLESIZE:	 256
         DESCR:       NA"
    ::= { rip2GeneralGroup 13 }

fsRip2IfConfEntry OBJECT-TYPE
    SYNTAX      FsRip2IfConfEntry
    ACCESS      not-accessible
    STATUS      mandatory
    DESCRIPTION 
        "A Single Routing Domain in a single Subnet.
         Row creation : A fsRip2IfConf entry will be created by the system when an 
         			entry is created in the rip2IfConf Table.
         Row deletion : A fsRip2IfConf entry will be deleted by the system when an 
         			entry is deleted in the rip2IfConf Table.
         Index usage : the index is the fsRip2IfConfAddress.
         Note that entries will be presented to the SNMP manager in full
         lexicographical order :  sorted on fsRip2IfConfAddress."
    INDEX       { fsRip2IfConfAddress }
    ::= { fsRip2IfConfTable 1 }

FsRip2IfConfEntry ::= SEQUENCE {
    fsRip2IfConfAddress             IpAddress,
    fsRip2IfAdminStat               INTEGER,
    fsRip2IfConfOperState           INTEGER,
    fsRip2IfConfUpdateTmr           INTEGER,
    fsRip2IfConfGarbgCollectTmr     INTEGER,
    fsRip2IfConfRouteAgeTmr         INTEGER,
    fsRip2IfSplitHorizonStatus      INTEGER,
    fsRip2IfPeriodicUpdates         Counter,
    fsRip2IfReceptionStatus         INTEGER
}

fsRip2IfConfAddress OBJECT-TYPE
    SYNTAX      IpAddress
    ACCESS      read-only
    STATUS      mandatory
    DESCRIPTION 
        "The IP Address of this system on the indicated
         subnet.  For unnumbered interfaces, the value 0.0.0.N,
         where the least significant 24 bits (N) is the ifIndex
         for the IP Interface in network byte order.
         ALCATEL NOTE:
         ACCESS:      NA           USAGE:       NA
         PERSIST:     YES          INSRVMOD:    NA
         RANGE:       NA           DEFVALUE:    NA
         UNITS:       NA	      SPARSE:      NO
         DESCR:       NA"
    ::= { fsRip2IfConfEntry 1 }

fsRip2IfAdminStat OBJECT-TYPE
    SYNTAX      INTEGER { enabled(1), disabled(2), passive(3) }
    ACCESS      read-write
    STATUS      mandatory
    DESCRIPTION 
        "The  administrative  status  of  RIP-2  in  the
         router.   The  value 'enabled' denotes that the
         RIP2 Process is active throughout the system.
         'disabled'	 disables RIP2 Process in the system.
         --	  	     'passive'	denotes that the RIP2 Process runs as
         --	  	     a passive one
         ALCATEL NOTE:
         ACCESS:      NA           USAGE:       MAND
         PERSIST:     YES          INSRVMOD:    YES
         RANGE:       NA           DEFVALUE:    NA
         UNITS:       NA	      SPARSE:      NO
         DESCR:       NA"
    ::= { fsRip2IfConfEntry 2 }

fsRip2IfConfOperState OBJECT-TYPE
    SYNTAX      INTEGER { operup(1), operdown(2) }
    ACCESS      read-only
    STATUS      mandatory
    DESCRIPTION 
        " This gives the Operational Status of the Interface 
         ALCATEL NOTE:
             ACCESS:      NA           USAGE:       NA
             PERSIST:     NO           INSRVMOD:    NA
             RANGE:       NA           DEFVALUE:    2
             UNITS:       NA	      SPARSE:      NO
             DESCR:       NA"
    DEFVAL      { operdown }
    ::= { fsRip2IfConfEntry 3 }

fsRip2IfConfUpdateTmr OBJECT-TYPE
    SYNTAX      INTEGER (10..3600)
    ACCESS      read-write
    STATUS      mandatory
    DESCRIPTION 
        "Interval Time Between Updates
         ALCATEL NOTE:
             ACCESS:      NA           USAGE:       OPT
             PERSIST:     YES          INSRVMOD:    YES
             RANGE:       NA           DEFVALUE:    NA
             UNITS:       seconds      SPARSE:      NO
             DESCR:       NA"
    DEFVAL      { 30 }
    ::= { fsRip2IfConfEntry 4 }

fsRip2IfConfGarbgCollectTmr OBJECT-TYPE
    SYNTAX      INTEGER (120..180)
    ACCESS      read-write
    STATUS      mandatory
    DESCRIPTION 
        " Interval before deleting an entry after not hearing
         it. Also the advertisements of this entry is set to
         INFINITY while sending to others 
         ALCATEL NOTE:
         ACCESS:      NA           USAGE:       OPT
         PERSIST:     YES          INSRVMOD:    YES
         RANGE:       NA           DEFVALUE:    NA
         UNITS:       seconds      SPARSE:      NO
         DESCR:       NA"
    DEFVAL      { 120 }
    ::= { fsRip2IfConfEntry 5 }

fsRip2IfConfRouteAgeTmr OBJECT-TYPE
    SYNTAX      INTEGER (30..500)
    ACCESS      read-write
    STATUS      mandatory
    DESCRIPTION 
        " Time after which the entry is put into garbage collect
         interval 
         ALCATEL NOTE:
         ACCESS:      NA           USAGE:       OPT
         PERSIST:     YES          INSRVMOD:    YES
         RANGE:       NA           DEFVALUE:    NA
         UNITS:       seconds      SPARSE:      NO
         DESCR:       NA"
    DEFVAL      { 180 }
    ::= { fsRip2IfConfEntry 6 }

fsRip2IfSplitHorizonStatus OBJECT-TYPE
    SYNTAX      INTEGER { splitHorizon(1), splitHorizonWithPoisRev(2), 
                    disable(3) }
    ACCESS      read-write
    STATUS      mandatory
    DESCRIPTION 
        "A flag to denote the split horizon operational status
         in the system. The value `splitHorizon` denotes that
         splitHorizon should be applied in the response packets
         that are going out
         ALCATEL NOTE:
         ACCESS:      NA           USAGE:       OPT
         PERSIST:     YES          INSRVMOD:    YES
         RANGE:       NA           DEFVALUE:    NA
         UNITS:       NA	      SPARSE:      NO
         DESCR:       NA"
    DEFVAL      { splitHorizonWithPoisRev }
    ::= { fsRip2IfConfEntry 7 }

fsRip2IfPeriodicUpdates OBJECT-TYPE
    SYNTAX      Counter
    ACCESS      read-only
    STATUS      mandatory
    DESCRIPTION 
        "The total number of Periodic RIP updates actually 
         sent on this interface.
         ALCATEL NOTE:
            ACCESS:      NA           USAGE:       NA
            PERSIST:     NO           INSRVMOD:    NA
            RANGE:       NA           DEFVALUE:    0
            UNITS:       RIP packets  SPARSE:      NO
            DESCR:       NA"
    ::= { fsRip2IfConfEntry 8 }

fsRip2IfReceptionStatus OBJECT-TYPE
    SYNTAX      INTEGER { enable(1), disable(2) }
    ACCESS      read-write
    STATUS      mandatory
    DESCRIPTION 
        "The reception status of the RIP interface. When 
         it is enabled the RIP updates will be received 
         and processed. when the status is disabled the
         updates will not be processed.
         ALCATEL NOTE:
          ACCESS:      NA           USAGE:       MAND
          PERSIST:     YES          INSRVMOD:    YES
          RANGE:       NA           DEFVALUE:    NA
          UNITS:       NA           SPARSE:      NO
          DESCR:       NA"
    ::= { fsRip2IfConfEntry 9 }

fsRipMd5AuthTable OBJECT-TYPE
    SYNTAX      SEQUENCE OF FsRipMd5AuthEntry
    ACCESS      not-accessible
    STATUS      mandatory
    DESCRIPTION 
        "The MD5 Authentication table for RIP.
         ALCATEL NOTE:
         	    TABLESIZE:	 NA
             DESCR:       NA"
    ::= { rip2GeneralGroup 14 }

fsRipMd5AuthEntry OBJECT-TYPE
    SYNTAX      FsRipMd5AuthEntry
    ACCESS      not-accessible
    STATUS      mandatory
    DESCRIPTION 
        "An entry in to the MD5 Authentiaction table. More than one entry can be configured for an interface.
         Row creation : A fsRipMd5Auth entry shall be created in one step by a
             		set-request with all necessary parameter values and
             		fsRipMd5KeyRowStatus set to createAndGo(4).
         Row deletion : A fsRipMd5Auth entry shall be deleted by setting
             		the fsRipMd5KeyRowStatus of the specific entry to destroy(6).
         Index usage : the indexes are fsRipMd5AuthAddress and fsRipMd5AuthKeyId.
         Note that entries will be presented to the SNMP manager in full
         lexicographical order :  sorted on fsRipMd5AuthAddress,then on fsRipMd5AuthKeyId."
    INDEX       { fsRipMd5AuthAddress, fsRipMd5AuthKeyId }
    ::= { fsRipMd5AuthTable 1 }

FsRipMd5AuthEntry ::= SEQUENCE {
    fsRipMd5AuthAddress     IpAddress,
    fsRipMd5AuthKeyId       INTEGER,
    fsRipMd5AuthKey         OCTET STRING,
    fsRipMd5KeyStartTime    INTEGER,
    fsRipMd5KeyExpiryTime   INTEGER,
    fsRipMd5KeyRowStatus    RowStatus
}

fsRipMd5AuthAddress OBJECT-TYPE
    SYNTAX      IpAddress
    ACCESS      read-only
    STATUS      mandatory
    DESCRIPTION 
        "The IP Address of this system on the indicated
         subnet.  For unnumbered interfaces, the value 0.0.0.N,
         where the least significant 24 bits (N) is the ifIndex
         for the IP Interface in network byte order. RIP should
         have been enabled for this IP address and the rip2IfConfAuthType 
         should be MD5 for creating this entry.
         ALCATEL NOTE:
         ACCESS:      NA           USAGE:       NA
         PERSIST:     YES          INSRVMOD:    NA
         RANGE:       NA           DEFVALUE:    NA
         UNITS:       NA	      SPARSE:      NO
         DESCR:       NA"
    ::= { fsRipMd5AuthEntry 1 }

fsRipMd5AuthKeyId OBJECT-TYPE
    SYNTAX      INTEGER (0..255)
    ACCESS      read-only
    STATUS      mandatory
    DESCRIPTION 
        "The key ID for this key. This should be unique for the same 
         fsRipMd5AuthAddress. This enables the configuration of more than
         one key for an interface.
         ALCATEL NOTE:
         ACCESS:      NA           USAGE:       NA
         PERSIST:     YES          INSRVMOD:    NA
         RANGE:       NA           DEFVALUE:    NA
         UNITS:       NA	      SPARSE:      NO
         DESCR:       NA"
    ::= { fsRipMd5AuthEntry 2 }

fsRipMd5AuthKey OBJECT-TYPE
    SYNTAX      OCTET STRING (SIZE(1..16))
    ACCESS      read-write
    STATUS      mandatory
    DESCRIPTION 
        "The value to be used as the Authentication Key.
         If a string shorter than 16 octets is supplied, it will be 
         left- justified and padded to 16 octets, on the right,
         with nulls (0x00).authentication may not
         be bypassed by reading the MIB object.
         ALCATEL NOTE:
         ACCESS:      NA           	USAGE:       MAND
         PERSIST:     YES          	INSRVMOD:    YES
         RANGE:       NA		DEFVALUE:    NA
         UNITS:       NA		SPARSE:      NO
         DESCR:       NA"
    ::= { fsRipMd5AuthEntry 3 }

fsRipMd5KeyStartTime OBJECT-TYPE
    SYNTAX      INTEGER
    ACCESS      read-write
    STATUS      mandatory
    DESCRIPTION 
        "The time the router will start accepting or generating the 
         packets that have been created with this key. 
            The start time of the key should be less than the expiry time of
         the previous key.
         During the overlap interval, the next key will be used in the 
         generation of the authentication messages.The start time of the first           
         key should be zero.
         ALCATEL NOTE:
          ACCESS:      NA           	USAGE:       MAND
          PERSIST:     YES          	INSRVMOD:    YES
          RANGE:       -1..2147483647	DEFVALUE:    NA
          UNITS:       seconds	SPARSE:      NO
          DESCR:       The start time of the key should be greater than the start time  of the previous key"
    ::= { fsRipMd5AuthEntry 4 }

fsRipMd5KeyExpiryTime OBJECT-TYPE
    SYNTAX      INTEGER
    ACCESS      read-write
    STATUS      mandatory
    DESCRIPTION 
        "The time the router will stop accepting the packets that have
         been created with this key. This time will be indicated (in the 
         number of seconds) from the start time of the key. If the expiry time           
         of a key is zero, it means that, the key should be used for the                  
         infinite amount of time. If this key is the last key then that key
         will be used for the infinite amount of time or until the new key 
         is configured.
         ALCATEL NOTE:
          ACCESS:      NA           	USAGE:       MAND
          PERSIST:     YES          	INSRVMOD:    YES
          RANGE:       -1..2147483647	DEFVALUE:    NA
          UNITS:       seconds	SPARSE:      NO
          DESCR:       Expiry time should be set only after setting the start time and the
         		 expiry time of a key should be surely greater than the start time
         		 of the key"
    ::= { fsRipMd5AuthEntry 5 }

fsRipMd5KeyRowStatus OBJECT-TYPE
    SYNTAX      RowStatus
    ACCESS      read-write
    STATUS      mandatory
    DESCRIPTION 
        "The status of this row by which a new entry can be created or
         deleted by setting this object to the appropriate value as 
         mentioned in SMI-v2.If this entry is made active, then no other 
         entry in the table will be allowed to modify. The entry can be in                deleted from the table.
         ALCATEL NOTE:
         ACCESS:      NA           USAGE:       MAND
         PERSIST:     YES          INSRVMOD:    YES
         RANGE:       1,2,4,5,6    DEFVALUE:    NA
         UNITS:       NA	      SPARSE:      NO
         DESCR:       NA"
    ::= { fsRipMd5AuthEntry 6 }

fsRip2NBRUnicastListTable OBJECT-TYPE
    SYNTAX      SEQUENCE OF FsRip2NBRUnicastListEntry
    ACCESS      not-accessible
    STATUS      mandatory
    DESCRIPTION 
        "This table contains a list of Router addresses 
         from which you can receive RIP Packets
         ALCATEL NOTE:
         TABLESIZE:	 NA
         DESCR:       NA"
    ::= { rip2GeneralGroup 15 }

fsRip2NBRUnicastListEntry OBJECT-TYPE
    SYNTAX      FsRip2NBRUnicastListEntry
    ACCESS      not-accessible
    STATUS      mandatory
    DESCRIPTION 
        "An entry of fsRip2NBRUnicastListTable.
         Row creation : A fsRip2NBRUnicastList Entry shall be created in one step by a
             		set-request with all necessary parameter values and
             		fsRip2NBRUnicastNBRRowStatus set to createAndGo(4).
         Row deletion : A fsRip2NBRUnicastList Entry shall be deleted by setting
             		the fsRip2NBRUnicastNBRRowStatus of the specific entry to destroy(6).
         Index usage : the index is the fsRip2NBRUnicastIpAddr.
         Note that entries will be presented to the SNMP manager in full
         lexicographical order :  sorted on fsRip2NBRUnicastIpAddr."
    INDEX       { fsRip2NBRUnicastIpAddr }
    ::= { fsRip2NBRUnicastListTable 1 }

FsRip2NBRUnicastListEntry ::= SEQUENCE {
    fsRip2NBRUnicastIpAddr          IpAddress,
    fsRip2NBRUnicastNBRRowStatus    RowStatus
}

fsRip2NBRUnicastIpAddr OBJECT-TYPE
    SYNTAX      IpAddress
    ACCESS      read-only
    STATUS      mandatory
    DESCRIPTION 
        "Ipaddress of the neighbour Router to which unicast 
         update has to be sent
         ALCATEL NOTE:
         ACCESS:      NA           USAGE:       NA
         PERSIST:     YES          INSRVMOD:    NA
         RANGE:       NA           DEFVALUE:    NA
         UNITS:       NA	      SPARSE:      NO
         DESCR:       NA"
    ::= { fsRip2NBRUnicastListEntry 1 }

fsRip2NBRUnicastNBRRowStatus OBJECT-TYPE
    SYNTAX      RowStatus
    ACCESS      read-write
    STATUS      mandatory
    DESCRIPTION 
        "The row status variable, used according to
         row installation and removal conventions.
         ALCATEL NOTE:
         ACCESS:      NA           USAGE:       MAND
         PERSIST:     YES          INSRVMOD:    YES
         RANGE:       1,2,4,5,6    DEFVALUE:    NA
         UNITS:       NA	      SPARSE:      NO
         DESCR:       NA"
    ::= { fsRip2NBRUnicastListEntry 2 }

fsRip2LocalRoutingTable OBJECT-TYPE
    SYNTAX      SEQUENCE OF FsRip2LocalRouteEntry
    ACCESS      not-accessible
    STATUS      mandatory
    DESCRIPTION 
        "This table contain Local routing table entries 
         ALCATEL NOTE:
         	    TABLESIZE:	 800
             DESCR:       NA"
    ::= { rip2GeneralGroup 16 }

fsRip2LocalRouteEntry OBJECT-TYPE
    SYNTAX      FsRip2LocalRouteEntry
    ACCESS      not-accessible
    STATUS      mandatory
    DESCRIPTION 
        "A list of routes in local routing table
         Row creation : A fsRip2LocalRoute Entry will be created by the system
             		when an IP Interface is enabled,when it receives RIP Route Updates
             		and when an RIP static Entry is added.
         Row deletion : A fsRip2LocalRoute Entry will be deleted by the system
             		when an IP Interface is disabled/deleted,when the RIP route timer 
         			expires and when an RIP static Entry is deleted.
         Index usage : the indexes are fsRip2DestNet,fsRip2DestMask,fsRip2Tos and fsRip2NextHop.
         Note that entries will be presented to the SNMP manager in full
         lexicographical order :  sorted on fsRip2DestNet, then on fsRip2DestMask,
         					then on fsRip2Tos, then on fsRip2NextHop."
    INDEX       { fsRip2DestNet, fsRip2DestMask, fsRip2Tos, 
                  fsRip2NextHop }
    ::= { fsRip2LocalRoutingTable 1 }

FsRip2LocalRouteEntry ::= SEQUENCE {
    fsRip2DestNet       IpAddress,
    fsRip2DestMask      IpAddress,
    fsRip2Tos           INTEGER,
    fsRip2NextHop       IpAddress,
    fsRip2RtIfIndex     INTEGER,
    fsRip2RtType        INTEGER,
    fsRip2Proto         INTEGER,
    fsRip2ChgTime       INTEGER,
    fsRip2Metric        INTEGER,
    fsRip2RowStatus     INTEGER,
    fsRip2Gateway       IpAddress
}

fsRip2DestNet OBJECT-TYPE
    SYNTAX      IpAddress
    ACCESS      read-only
    STATUS      mandatory
    DESCRIPTION 
        "The IP Address of the destination network
         ALCATEL NOTE:
             ACCESS:      NA           USAGE:       NA
             PERSIST:     NO           INSRVMOD:    NA
             RANGE:       NA           DEFVALUE:    NA
             UNITS:       NA	      SPARSE:      NO
             DESCR:       NA"
    ::= { fsRip2LocalRouteEntry 1 }

fsRip2DestMask OBJECT-TYPE
    SYNTAX      IpAddress
    ACCESS      read-only
    STATUS      mandatory
    DESCRIPTION 
        "The Destination mask for the destination network
         ALCATEL NOTE:
             ACCESS:      NA           USAGE:       NA
             PERSIST:     NO           INSRVMOD:    NA
             RANGE:       NA           DEFVALUE:    NA
             UNITS:       NA	      SPARSE:      NO
             DESCR:       NA"
    ::= { fsRip2LocalRouteEntry 2 }

fsRip2Tos OBJECT-TYPE
    SYNTAX      INTEGER (0..2147483647)
    ACCESS      read-only
    STATUS      mandatory
    DESCRIPTION 
        "The  value for Rip is always zero
         ALCATEL NOTE:
             ACCESS:      NA           USAGE:       NA
             PERSIST:     NO           INSRVMOD:    NA
             RANGE:       NA           DEFVALUE:    NA
             UNITS:       NA	      SPARSE:      NO
             DESCR:       NA"
    ::= { fsRip2LocalRouteEntry 3 }

fsRip2NextHop OBJECT-TYPE
    SYNTAX      IpAddress
    ACCESS      read-only
    STATUS      mandatory
    DESCRIPTION 
        "The The nexthop address to which any datagrams 
         destined to the destination,to be 
         forwarded. (In some special cases)
         ALCATEL NOTE:
         ACCESS:      NA           USAGE:       NA
         PERSIST:     NO           INSRVMOD:    NA
         RANGE:       NA           DEFVALUE:    NA
         UNITS:       NA	      SPARSE:      NO
         DESCR:       NA"
    ::= { fsRip2LocalRouteEntry 4 }

fsRip2RtIfIndex OBJECT-TYPE
    SYNTAX      INTEGER
    ACCESS      read-only
    STATUS      mandatory
    DESCRIPTION 
        " The interface through which the route is learnt
         ALCATEL NOTE:
             ACCESS:      NA           USAGE:       NA
             PERSIST:     NO           INSRVMOD:    NA
             RANGE:       1..280       DEFVALUE:    NA
             UNITS:       NA           SPARSE:      NO
             DESCR:       NA"
    ::= { fsRip2LocalRouteEntry 5 }

fsRip2RtType OBJECT-TYPE
    SYNTAX      INTEGER
    ACCESS      read-only
    STATUS      mandatory
    DESCRIPTION 
        "The  value for Rip is always zero
         ALCATEL NOTE:
             ACCESS:      NA           USAGE:       NA
             PERSIST:     NO           INSRVMOD:    NA
             RANGE:       0..4	      DEFVALUE:    NA
             UNITS:       NA	      SPARSE:      NO
             DESCR:       NA"
    ::= { fsRip2LocalRouteEntry 6 }

fsRip2Proto OBJECT-TYPE
    SYNTAX      INTEGER
    ACCESS      read-only
    STATUS      mandatory
    DESCRIPTION 
        "The protocol id   == RIP (8 - 1)here
         ALCATEL NOTE:
             ACCESS:      NA           USAGE:       NA
             PERSIST:     NO           INSRVMOD:    NA
             RANGE:       1..3|8	      DEFVALUE:    NA
             UNITS:       NA	      SPARSE:      NO
             DESCR:       NA"
    ::= { fsRip2LocalRouteEntry 7 }

fsRip2ChgTime OBJECT-TYPE
    SYNTAX      INTEGER
    ACCESS      read-only
    STATUS      mandatory
    DESCRIPTION 
        "The time when the route is installed
         ALCATEL NOTE:
             ACCESS:      NA           USAGE:       NA
             PERSIST:     NO           INSRVMOD:    NA
             RANGE:       NA	      DEFVALUE:    0
             UNITS:       TimeTicks    SPARSE:      NO
             DESCR:       NA"
    ::= { fsRip2LocalRouteEntry 8 }

fsRip2Metric OBJECT-TYPE
    SYNTAX      INTEGER
    ACCESS      read-only
    STATUS      mandatory
    DESCRIPTION 
        "The reachability cost for the destination
         ALCATEL NOTE:
             ACCESS:      NA           USAGE:       NA
             PERSIST:     NO           INSRVMOD:    NA
             RANGE:       1..16        DEFVALUE:    NA
             UNITS:       NA	      SPARSE:      NO
             DESCR:       NA"
    ::= { fsRip2LocalRouteEntry 9 }

fsRip2RowStatus OBJECT-TYPE
    SYNTAX      INTEGER
    ACCESS      read-only
    STATUS      mandatory
    DESCRIPTION 
        "Row status for perticular route entry
         ALCATEL NOTE:
             ACCESS:      NA           USAGE:       NA
             PERSIST:     NO           INSRVMOD:    NA
             RANGE:       1,2	      DEFVALUE:    NA
             UNITS:       NA	      SPARSE:      NO
             DESCR:       NA"
    ::= { fsRip2LocalRouteEntry 10 }

fsRip2Gateway OBJECT-TYPE
    SYNTAX      IpAddress
    ACCESS      read-only
    STATUS      mandatory
    DESCRIPTION 
        "The gateway address to which any datagrams
         destined to the destination, to be 
         forwarded
         ALCATEL NOTE:
         ACCESS:      NA           USAGE:       NA
         PERSIST:     NO           INSRVMOD:    NA
         RANGE:       NA	      DEFVALUE:    NA
         UNITS:       NA	      SPARSE:      NO
         DESCR:       NA"
    ::= { fsRip2LocalRouteEntry 11 }

fsRipAggTable OBJECT-TYPE
    SYNTAX      SEQUENCE OF FsRipAggEntry
    ACCESS      not-accessible
    STATUS      mandatory
    DESCRIPTION 
        "The (conceptual) table listing the router's
         supernet routes.RIP advertises only supernet
         routes on the speicified interface. And it
         suppresses all routes which are subset of the supernet.
         ALCATEL NOTE:
         TABLESIZE:	 DEP
         DESCR:       The Default Table size is 12 and can be changed Dynamically using the object FsNoOfAggregatedRoutes"
    ::= { rip2GeneralGroup 17 }

fsRipAggEntry OBJECT-TYPE
    SYNTAX      FsRipAggEntry
    ACCESS      not-accessible
    STATUS      mandatory
    DESCRIPTION 
        "An entry (conceptual row) in the
         fsRipAggTable representing supertnet route for
         the domain.
         Row creation : A fsRipAgg Entry shall be created in one step by a
         	set-request with all necessary parameter values and
         	fsRipAggStatus set to Enabled(1).
         Row deletion : A fsRipAgg Entry shall be deleted by setting
         	the fsRipAggStatus of the specific entry to Disabled(2).
         Index usage : the indexes are fsRipAggAddress and fsRipAggAddressMask.
         Note that entries will be presented to the SNMP manager in full
         lexicographical order :  sorted on fsRipAggAddress, then on fsRipAggAddressMask"
    INDEX       { fsRipAggAddress, fsRipAggAddressMask }
    ::= { fsRipAggTable 1 }

FsRipAggEntry ::= SEQUENCE {
    fsRipAggAddress         IpAddress,
    fsRipAggAddressMask     IpAddress,
    fsRipAggStatus          INTEGER
}

fsRipAggAddress OBJECT-TYPE
    SYNTAX      IpAddress
    ACCESS      read-write
    STATUS      mandatory
    DESCRIPTION 
        "The aggregated address which when combined with the
         corresponding value of fsRipAggAddressMask
         identifies the supernet route for this domain.
         ALCATEL NOTE:
         ACCESS:      RO           USAGE:       NA
         PERSIST:     YES          INSRVMOD:    NA
         RANGE:       NA           DEFVALUE:    NA
         UNITS:       NA	      SPARSE:      NO
         DESCR:       NA"
    ::= { fsRipAggEntry 1 }

fsRipAggAddressMask OBJECT-TYPE
    SYNTAX      IpAddress
    ACCESS      read-write
    STATUS      mandatory
    DESCRIPTION 
        "The aggregated address mask which when combined with
         the corresponding value of fsRipAggAddress
         identifies the supernet route for the domain.
         ALCATEL NOTE:
         ACCESS:      RO           USAGE:       NA
         PERSIST:     YES          INSRVMOD:    NA
         RANGE:       NA           DEFVALUE:    NA
         UNITS:       NA	      SPARSE:      NO
         DESCR:       NA"
    ::= { fsRipAggEntry 2 }

fsRipAggStatus OBJECT-TYPE
    SYNTAX      INTEGER { enabled(1), disabled(2) }
    ACCESS      read-write
    STATUS      mandatory
    DESCRIPTION 
        "The object specifies the aggrigation status.
         ALCATEL NOTE:
             ACCESS:      NA           USAGE:       MAND
             PERSIST:     YES          INSRVMOD:    YES
             RANGE:       NA           DEFVALUE:    NA
             UNITS:       NA	      SPARSE:      NO
             DESCR:       NA"
    ::= { fsRipAggEntry 3 }

fsRip2GlobalPeriodicUpdates OBJECT-TYPE
    SYNTAX      Counter
    ACCESS      read-only
    STATUS      mandatory
    DESCRIPTION 
        "The total number of Periodic RIP updates actually 
         sent from this router.
         ALCATEL NOTE:
          ACCESS:      NA           USAGE:       NA
          PERSIST:     NO           INSRVMOD:    NA
          RANGE:       NA           DEFVALUE:    0      
          UNITS:       RIP packets  SPARSE:      NA
          DESCR:       NA"
    ::= { rip2GeneralGroup 18 }

fsRipRouteMapTable OBJECT-TYPE
    SYNTAX      SEQUENCE OF FsRipRouteMapEntry
    ACCESS      not-accessible
    STATUS      mandatory
    DESCRIPTION 
        "The route map table of RIP lists the filters applied on RIP route advertisements. 
         ALCATEL NOTE:
         	    TABLESIZE:	 128
             DESCR:       NA"
    ::= { rip2GeneralGroup 19 }

fsRipRouteMapEntry OBJECT-TYPE
    SYNTAX      FsRipRouteMapEntry
    ACCESS      not-accessible
    STATUS      mandatory
    DESCRIPTION 
        "An entry represents the route that can or cannot be propagated by RIP over an interface.
         Row creation : A fsRipRouteMap Entry shall be created in one step by a
             		set-request with all necessary parameter values and
             		fsRipRouteMapStatus set to createAndGo(4).
         Row deletion : A fsRipRouteMap Entry shall be deleted by setting
             		the fsRipRouteMapStatus of the specific entry to destroy(6).
         Index usage : the indexes are fsRipRouteMapIfIndex and fsRipRouteMapSubIndex.
         Note that entries will be presented to the SNMP manager in full
         lexicographical order :  sorted on fsRipRouteMapIfIndex,then on fsRipRouteMapSubIndex"
    INDEX       { fsRipRouteMapIfIndex, fsRipRouteMapSubIndex }
    ::= { fsRipRouteMapTable 1 }

FsRipRouteMapEntry ::= SEQUENCE {
    fsRipRouteMapIfIndex        INTEGER,
    fsRipRouteMapSubIndex       INTEGER,
    fsRipRouteMapIpAddress      IpAddress,
    fsRipRouteMapDirection      INTEGER,
    fsRipRouteMapAction         INTEGER,
    fsRipRouteMapSubnetMask     IpAddress,
    fsRipRouteMapStatus         RowStatus
}

fsRipRouteMapIfIndex OBJECT-TYPE
    SYNTAX      INTEGER (1..2147483647)
    ACCESS      read-only
    STATUS      mandatory
    DESCRIPTION 
        "The IP interface to which the route map filter is to be applied
         ALCATEL NOTE:
             ACCESS:      NA           USAGE:       NA
             PERSIST:     YES          INSRVMOD:    NA
             RANGE:       NA           DEFVALUE:    NA
             UNITS:       NA	      SPARSE:      NO
             DESCR:       NA"
    ::= { fsRipRouteMapEntry 1 }

fsRipRouteMapSubIndex OBJECT-TYPE
    SYNTAX      INTEGER (1..2147483647)
    ACCESS      read-only
    STATUS      mandatory
    DESCRIPTION 
        "The entry sub-index. Each route map entry may have rules for multiple IP addresses.
         This sub index identifies the rule for eacgh IP address.
         ALCATEL NOTE:
         ACCESS:      NA           USAGE:       NA
         PERSIST:     YES          INSRVMOD:    NA
         RANGE:       1..128       DEFVALUE:    NA
         UNITS:       NA	      SPARSE:      NO
         DESCR:       NA"
    ::= { fsRipRouteMapEntry 2 }

fsRipRouteMapIpAddress OBJECT-TYPE
    SYNTAX      IpAddress
    ACCESS      read-write
    STATUS      mandatory
    DESCRIPTION 
        "The IpAddress of the subnet that can be allowed or disallowed to be propagated by RIP over the interface
         ALCATEL NOTE:
             ACCESS:      NA           USAGE:       MAND
             PERSIST:     YES          INSRVMOD:    YES
             RANGE:       NA           DEFVALUE:    NA
             UNITS:       NA	      SPARSE:      NO
             DESCR:       NA"
    ::= { fsRipRouteMapEntry 3 }

fsRipRouteMapDirection OBJECT-TYPE
    SYNTAX      INTEGER { transmit(1), receive(2) }
    ACCESS      read-write
    STATUS      mandatory
    DESCRIPTION 
        "This MIB object specifes the direction in which the RIP routes are advertised over an IP interface. Only direction TRANSMIT is supported. Direction receive is not supported.
         ALCATEL NOTE:
             ACCESS:      NA           USAGE:       OPT
             PERSIST:     YES          INSRVMOD:    YES
             RANGE:       1            DEFVALUE:    NA
             UNITS:       NA	      SPARSE:      NO
             DESCR:       NA"
    DEFVAL      { transmit }
    ::= { fsRipRouteMapEntry 4 }

fsRipRouteMapAction OBJECT-TYPE
    SYNTAX      INTEGER { permit(1), deny(2) }
    ACCESS      read-write
    STATUS      mandatory
    DESCRIPTION 
        "This MIB object specifes the action to be allowed.
         Permit - The route will be advertised by RIP over the interface in transmit direction. In direction receive this route will be accepted by RIP for advertisement.
         Deny - The route will not be advertised by RIP over the interface in transmit direction. In the direction receive this route will not be accepted by RIP for advertisement 
         ALCATEL NOTE:
         ACCESS:      NA           USAGE:       OPT
         PERSIST:     YES          INSRVMOD:    YES
         RANGE:       NA           DEFVALUE:    NA
         UNITS:       NA	      SPARSE:      NO
         DESCR:       NA"
    DEFVAL      { permit }
    ::= { fsRipRouteMapEntry 5 }

fsRipRouteMapSubnetMask OBJECT-TYPE
    SYNTAX      IpAddress
    ACCESS      read-write
    STATUS      mandatory
    DESCRIPTION 
        "The SubnetMask of the subnet that can be allowed or disallowed to be propagated by RIP over the interface
         ALCATEL NOTE:
             ACCESS:      NA           USAGE:       MAND
             PERSIST:     YES          INSRVMOD:    YES
             RANGE:       NA           DEFVALUE:    NA
             UNITS:       NA	      SPARSE:      NO
             DESCR:       NA"
    ::= { fsRipRouteMapEntry 6 }

fsRipRouteMapStatus OBJECT-TYPE
    SYNTAX      RowStatus
    ACCESS      read-write
    STATUS      mandatory
    DESCRIPTION 
        "The row status variable, used according to
         row installation and removal conventions.
         ALCATEL NOTE:
         ACCESS:      NA           USAGE:       MAND
         PERSIST:     YES          INSRVMOD:    YES
         RANGE:       1,4,5,6      DEFVALUE:    NA
         UNITS:       NA	      SPARSE:      NO
         DESCR:       NA"
    ::= { fsRipRouteMapEntry 7 }

fsRipRouteMapAvailableSubIndex OBJECT-TYPE
    SYNTAX      INTEGER
    ACCESS      read-only
    STATUS      mandatory
    DESCRIPTION 
        "Shows the next available free sub index for  creating the route map.
         ALCATEL NOTE:
             ACCESS:      NA           USAGE:       NA
             PERSIST:     NO           INSRVMOD:    NA
             RANGE:       1..128       DEFVALUE:    NA      
             UNITS:       NA	      SPARSE:      NA
             DESCR:       NA"
    ::= { rip2GeneralGroup 20 }

fsRipRRDGeneralGroup OBJECT IDENTIFIER
    ::= { fsrip 2 }

fsRipRRDGlobalStatus OBJECT-TYPE
    SYNTAX      INTEGER { enabled(1), disabled(2) }
    ACCESS      read-write
    STATUS      mandatory
    DESCRIPTION 
        "This MIB object enables / disables RIP to participate
         in Route Redistribution. If set to enabled then RIP will start 
         advertising the routes learned by other protocols. If set to
         disabled then RIP will stop redistribution of routes
         but will continue to send updates to the RTM.
         ALCATEL NOTE:
            ACCESS:      NA           USAGE:       NA
            PERSIST:     YES          INSRVMOD:    YES
            RANGE:       NA	      DEFVALUE:    NA
            UNITS:       NA	      SPARSE:      NA
            DESCR:       NA"
    DEFVAL      { disabled }
    ::= { fsRipRRDGeneralGroup 1 }

fsRipRRDSrcProtoMaskEnable OBJECT-TYPE
    SYNTAX      INTEGER (0..65535)
    ACCESS      read-write
    STATUS      mandatory
    DESCRIPTION 
        "This object determines the protocols from which the routes have to be imported to RIP
         
         Bit 1, if set indicates the routes have to be imported from the local interface.
         Bit 2, if set indicates the routes have to be imported from static route.
         Bit 12, if set indicates the routes have to be imported from OSPF.
         Bit 13, if set indicates the routes have to be imported from BGP.
         ALCATEL NOTE:
             ACCESS:      NA           USAGE:       NA
             PERSIST:     YES          INSRVMOD:    YES
             RANGE:       NA	      DEFVALUE:    NA
             UNITS:       NA	      SPARSE:      NA
             DESCR:       NA"
    DEFVAL      { 0 }
    ::= { fsRipRRDGeneralGroup 2 }

fsRipRRDSrcProtoMaskDisable OBJECT-TYPE
    SYNTAX      INTEGER (0..65535)
    ACCESS      read-write
    STATUS      mandatory
    DESCRIPTION 
        "This object determines the protocols from which the importing of 
         routes should be stopped to RIP
         
         Bit 1, if set indicates the routes have to be imported from the local interface.
         Bit 2, if set indicates the routes have to be imported from static route.
         Bit 12, if set indicates the routes have to be imported from OSPF.
         Bit 13, if set indicates the routes have to be imported from BGP.
           ALCATEL NOTE:
               ACCESS:      NA           USAGE:       NA
               PERSIST:     YES          INSRVMOD:    YES
               RANGE:       NA	      DEFVALUE:    NA
               UNITS:       NA	      SPARSE:      NA
               DESCR:       NA"
    DEFVAL      { 0 }
    ::= { fsRipRRDGeneralGroup 3 }

fsRipRRDRouteTagType OBJECT-TYPE
    SYNTAX      INTEGER { manual(1), automatic(2) }
    ACCESS      read-write
    STATUS      mandatory
    DESCRIPTION 
        "The Tag Type MIB object describes whether Tags
         will be automatically generated or will be manually 
         configured. If tags are manually configured , the 
         fsripRRDRouteTag MIB has to be set with the Tag
         value needed.
          ALCATEL NOTE:
              ACCESS:      NA           USAGE:       NA
              PERSIST:     YES          INSRVMOD:    YES
              RANGE:       NA	      DEFVALUE:    NA
              UNITS:       NA	      SPARSE:      NA
              DESCR:       NA"
    DEFVAL      { manual }
    ::= { fsRipRRDGeneralGroup 4 }

fsRipRRDRouteTag OBJECT-TYPE
    SYNTAX      INTEGER (0..65535)
    ACCESS      read-write
    STATUS      mandatory
    DESCRIPTION 
        " The Route Tag in case the user configures a Manual option for
         the tags .
               ALCATEL NOTE:
                   ACCESS:      NA           USAGE:       NA
                   PERSIST:     YES          INSRVMOD:    YES
                   RANGE:       NA	      DEFVALUE:    NA
                   UNITS:       NA	      SPARSE:      NA
                   DESCR:       NA"
    DEFVAL      { 0 }
    ::= { fsRipRRDGeneralGroup 5 }

fsRipRRDRouteDefMetric OBJECT-TYPE
    SYNTAX      INTEGER (1..16)
    ACCESS      read-write
    STATUS      mandatory
    DESCRIPTION 
        "The default metric to be used for the imported routes from RTM.
         ALCATEL NOTE:
             ACCESS:      NA           USAGE:       NA
             PERSIST:     YES          INSRVMOD:    YES
             RANGE:       NA	      DEFVALUE:    NA
             UNITS:       NA	      SPARSE:      NA
             DESCR:       NA"
    DEFVAL      { 3 }
    ::= { fsRipRRDGeneralGroup 6 }

END -- end of module FSRIP2-MIB.
