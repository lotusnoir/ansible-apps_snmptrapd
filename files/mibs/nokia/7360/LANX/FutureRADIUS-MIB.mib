--
-- This SMIv1 module has been generated by smidump 0.4.8. Do not edit.
--

FutureRADIUS-MIB DEFINITIONS ::= BEGIN

IMPORTS
    InterfaceIndex
        FROM IF-MIB
    OBJECT-TYPE
        FROM RFC-1212
    Gauge, IpAddress, enterprises
        FROM RFC1155-SMI
    DisplayString, RowStatus
        FROM SNMPv2-TC;

futureRADIUSMIB OBJECT IDENTIFIER
    ::= { enterprises futuresoftware(2076) 25 }

-- futureRADIUSMIB MODULE-IDENTITY
--     LAST-UPDATED "200203150530Z"
--     ORGANIZATION 
--         "FUTURE SOFTWARE PVT. LIMITED"
--     CONTACT-INFO 
--         "Shijith C
--          FUTURE SOFTWARE PVT. LIMITED
--          481 Mount Road
--          Madras - 600 035
--          Phone : +91-44-433 055 0
--          E-mail: shijithc@future.futsoft.com"
--     DESCRIPTION 
--         " The RADIUS ext. MIB is placed under futuresoftware MIB branch."
--     REVISION    "200203150530Z"
--     DESCRIPTION 
--         "The initial revision of this MIB module was published as
--          RFC 1450."
--     ::= { enterprises futuresoftware(2076) 25 }


radiusExtClient OBJECT IDENTIFIER
    ::= { futureRADIUSMIB 1 }

radiusExtDebugMask OBJECT-TYPE
    SYNTAX      INTEGER { disableall(0), enableall(1), error(2), 
                    event(3), packet(4), response(5), timer(6) }
    ACCESS      read-write
    STATUS      mandatory
    DESCRIPTION 
        "Mask for enabling or disabling the Debug/Trace
         prints in the radius module."
    ::= { radiusExtClient 1 }

radiusMaxNoOfUserEntries OBJECT-TYPE
    SYNTAX      INTEGER (1..100)
    ACCESS      read-write
    STATUS      mandatory
    DESCRIPTION 
        "  Max of No of User entries stored.For value of this
         object will be stored for the MemPool Initialization."
    ::= { radiusExtClient 2 }

radiusExtServerTable OBJECT-TYPE
    SYNTAX      SEQUENCE OF RadiusExtServerEntry
    ACCESS      not-accessible
    STATUS      mandatory
    DESCRIPTION 
        "The (conceptual) table listing the RADIUS servers with
         which the client shares a secret."
    ::= { radiusExtClient 3 }

radiusExtServerEntry OBJECT-TYPE
    SYNTAX      RadiusExtServerEntry
    ACCESS      not-accessible
    STATUS      mandatory
    DESCRIPTION 
        "An entry (conceptual row) representing a RADIUS server
         with which the client shares a secret."
    INDEX       { radiusExtServerIndex }
    ::= { radiusExtServerTable 1 }

RadiusExtServerEntry ::= SEQUENCE {
    radiusExtServerIndex                    InterfaceIndex,
    radiusExtServerAddress                  IpAddress,
    radiusExtServerType                     INTEGER,
    radiusExtServerSharedSecret             DisplayString,
    radiusExtServerEnabled                  INTEGER,
    radiusExtServerResponseTime             INTEGER,
    radiusExtServerMaximumRetransmission    INTEGER,
    radiusExtServerEntryStatus              RowStatus
}

radiusExtServerIndex OBJECT-TYPE
    SYNTAX      InterfaceIndex
    ACCESS      read-only
    STATUS      mandatory
    DESCRIPTION 
        "The RADIUS server with whom the client interacts."
    ::= { radiusExtServerEntry 1 }

radiusExtServerAddress OBJECT-TYPE
    SYNTAX      IpAddress
    ACCESS      read-write
    STATUS      mandatory
    DESCRIPTION 
        "The IP address of the RADIUS server
         referred to in this table entry."
    ::= { radiusExtServerEntry 2 }

radiusExtServerType OBJECT-TYPE
    SYNTAX      INTEGER { auth(1), acct(2), both(3) }
    ACCESS      read-write
    STATUS      mandatory
    DESCRIPTION 
        "The RADIUS server type (Authentication or Accounting or Both).
         For creating a server entry Server Type should be set"
    ::= { radiusExtServerEntry 3 }

radiusExtServerSharedSecret OBJECT-TYPE
    SYNTAX      DisplayString
    ACCESS      read-write
    STATUS      mandatory
    DESCRIPTION 
        "The secret string which is shared between Server and Client"
    ::= { radiusExtServerEntry 4 }

radiusExtServerEnabled OBJECT-TYPE
    SYNTAX      INTEGER { enabled(1), disabled(2), destroy(3) }
    ACCESS      read-write
    STATUS      mandatory
    DESCRIPTION 
        "Flag to tell whether the server is active or Inactive"
    DEFVAL      { enabled }
    ::= { radiusExtServerEntry 5 }

radiusExtServerResponseTime OBJECT-TYPE
    SYNTAX      INTEGER (1..120)
    ACCESS      read-write
    STATUS      mandatory
    DESCRIPTION 
        "The maximum time within which the server has to respond for a
         request from the client"
    ::= { radiusExtServerEntry 6 }

radiusExtServerMaximumRetransmission OBJECT-TYPE
    SYNTAX      INTEGER (1..254)
    ACCESS      read-write
    STATUS      mandatory
    DESCRIPTION 
        "The allowed maximum no. of trials to be tried by a client to get
         response from the server for a request"
    ::= { radiusExtServerEntry 7 }

radiusExtServerEntryStatus OBJECT-TYPE
    SYNTAX      RowStatus
    ACCESS      read-write
    STATUS      mandatory
    DESCRIPTION 
        "The status of the entry can be used as specified in the SNMP V2
         standard. "
    ::= { radiusExtServerEntry 8 }

END -- end of module FutureRADIUS-MIB.
