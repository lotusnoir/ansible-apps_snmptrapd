--
-- This SMIv1 module has been generated by smidump 0.4.8. Do not edit.
--

STDRIP2-MIB DEFINITIONS ::= BEGIN

IMPORTS
    OBJECT-TYPE
        FROM RFC-1212
    Counter, Gauge, IpAddress, TimeTicks
        FROM RFC1155-SMI
    mib-2
        FROM RFC1213-MIB
    RowStatus
        FROM SNMPv2-TC;

rip2 OBJECT IDENTIFIER
    ::= { mib-2 23 }

-- rip2 MODULE-IDENTITY
--     LAST-UPDATED "200112190600Z"
--     ORGANIZATION 
--         "IETF RIP-II Working Group"
--     CONTACT-INFO 
--         "       Fred Baker 
--          Postal: Cisco Systems 
--                  519 Lado Drive 
--                  Santa Barbara, California 93111 
--          Tel:    +1 805 681 0115 
--          E-Mail: fbaker@cisco.com 
--          Postal: Gary Malkin 
--                  Xylogics, Inc. 
--                  53 Third Avenue 
--                  Burlington, MA  01803 
--          Phone:  (617) 272-8140 
--          EMail:  gmalkin@Xylogics.COM"
--     DESCRIPTION 
--         "The MIB module to describe the RIP2 Version 2 Protocol"
--     REVISION    "200112190600Z"
--     DESCRIPTION 
--         "The initial revision of this MIB module was published as
--          RFC 1450."
--     ::= { mib-2 23 }


RouteTag ::=
    OCTET STRING (SIZE(2))

-- RouteTag ::= TEXTUAL-CONVENTION
--     STATUS      mandatory
--     DESCRIPTION 
--         "the RouteTag type represents the contents of the Route Domain 
--          field in the packet header or route entry"
--     SYNTAX      OCTET STRING (SIZE(2))

rip2Globals OBJECT IDENTIFIER
    ::= { rip2 1 }

rip2GlobalRouteChanges OBJECT-TYPE
    SYNTAX      Counter
    ACCESS      read-only
    STATUS      mandatory
    DESCRIPTION 
        "The number of route changes made to the IP Route 
         Database by RIP.  This does not include the refresh 
         of a route's age.
         ALCATEL NOTE:
          ACCESS:      NA           USAGE:       NA
          PERSIST:     NO           INSRVMOD:    NA
          RANGE:       NA           DEFVALUE:    0
          UNITS:       NA           SPARSE:      NA
          DESCR:       NA"
    ::= { rip2Globals 1 }

rip2GlobalQueries OBJECT-TYPE
    SYNTAX      Counter
    ACCESS      read-only
    STATUS      mandatory
    DESCRIPTION 
        "The number of responses sent to RIP queries 
         from other systems.
         ALCATEL NOTE:
          ACCESS:      NA           USAGE:       NA
          PERSIST:     NO           INSRVMOD:    NA
          RANGE:       NA           DEFVALUE:    0
          UNITS:       RIP Msgs     SPARSE:      NA
          DESCR:       NA"
    ::= { rip2Globals 2 }

rip2IfStatTable OBJECT-TYPE
    SYNTAX      SEQUENCE OF Rip2IfStatEntry
    ACCESS      not-accessible
    STATUS      mandatory
    DESCRIPTION 
        "A list of subnets which require separate 
         status monitoring in RIP.
         ALCATEL NOTE:
          TABLESIZE: 	256
         	DESCR: 	NA"
    ::= { rip2 2 }

rip2IfStatEntry OBJECT-TYPE
    SYNTAX      Rip2IfStatEntry
    ACCESS      not-accessible
    STATUS      mandatory
    DESCRIPTION 
        "A Single Routing Domain in a single Subnet.
         Row creation : A rip2IfStat entry shall be created in one step by a
             		set-request with all necessary parameter values and
             		rip2IfStatStatus set to createAndGo(4).
         Row deletion : A rip2IfStat entry shall be deleted by setting
             		the rip2IfStatStatus of the specific entry to destroy(6).
         Index usage : the index is the rip2IfStatAddress.
         Note that entries will be presented to the SNMP manager in full
         lexicographical order :  sorted on rip2IfStatAddress."
    INDEX       { rip2IfStatAddress }
    ::= { rip2IfStatTable 1 }

Rip2IfStatEntry ::= SEQUENCE {
    rip2IfStatAddress           IpAddress,
    rip2IfStatRcvBadPackets     Counter,
    rip2IfStatRcvBadRoutes      Counter,
    rip2IfStatSentUpdates       Counter,
    rip2IfStatStatus            RowStatus
}

rip2IfStatAddress OBJECT-TYPE
    SYNTAX      IpAddress
    ACCESS      read-only
    STATUS      mandatory
    DESCRIPTION 
        "The IP Address of this system on the indicated 
         subnet. For unnumbered interfaces, the value 0.0.0.N, 
         where the least significant 24 bits (N) is the ifIndex 
         for the IP Interface in network byte order.
         ALCATEL NOTE:
          ACCESS:      NA           USAGE:       NA
          PERSIST:     NO           INSRVMOD:    NA 
          RANGE:       NA           DEFVALUE:    NA       
          UNITS:       NA           SPARSE:      NO
          DESCR:       NA"
    ::= { rip2IfStatEntry 1 }

rip2IfStatRcvBadPackets OBJECT-TYPE
    SYNTAX      Counter
    ACCESS      read-only
    STATUS      mandatory
    DESCRIPTION 
        "The number of RIP response packets received by 
         the RIP process which were subsequently discarded 
         for any reason (e.g. a version 0 packet, or an 
         unknown command type).
         ALCATEL NOTE:
          ACCESS:      NA           USAGE:       NA 
          PERSIST:     NO           INSRVMOD:    NA  
          RANGE:       NA           DEFVALUE:    0
          UNITS:       RIP Msgs     SPARSE:      NO
          DESCR:       NA"
    ::= { rip2IfStatEntry 2 }

rip2IfStatRcvBadRoutes OBJECT-TYPE
    SYNTAX      Counter
    ACCESS      read-only
    STATUS      mandatory
    DESCRIPTION 
        "The number of routes, in valid RIP packets, 
         which were ignored for any reason (e.g. unknown 
         address family, or invalid metric).
         ALCATEL NOTE:
          ACCESS:      NA           USAGE:       NA 
          PERSIST:     NO           INSRVMOD:    NA  
          RANGE:       NA           DEFVALUE:    0
          UNITS:       routes       SPARSE:      NO
          DESCR:       NA"
    ::= { rip2IfStatEntry 3 }

rip2IfStatSentUpdates OBJECT-TYPE
    SYNTAX      Counter
    ACCESS      read-only
    STATUS      mandatory
    DESCRIPTION 
        "The number of triggered RIP updates actually 
         sent on this interface.  This explicitly does 
         NOT include full updates sent containing new 
         information.
         ALCATEL NOTE:
          ACCESS:      NA           USAGE:       NA 
          PERSIST:     NO           INSRVMOD:    NA  
          RANGE:       NA           DEFVALUE:    0
          UNITS:       RIP Msgs     SPARSE:      NO
          DESCR:       NA"
    ::= { rip2IfStatEntry 4 }

rip2IfStatStatus OBJECT-TYPE
    SYNTAX      RowStatus
    ACCESS      read-write
    STATUS      mandatory
    DESCRIPTION 
        "Writing invalid has the effect of deleting 
         this interface.
         ALCATEL NOTE:
          ACCESS:      NA           USAGE:       MAND
          PERSIST:     NO           INSRVMOD:    YES  
          RANGE:       1,2,4,5,6    DEFVALUE:    NA
          UNITS:       NA           SPARSE:      NO
          DESCR:       NA"
    ::= { rip2IfStatEntry 5 }

rip2IfConfTable OBJECT-TYPE
    SYNTAX      SEQUENCE OF Rip2IfConfEntry
    ACCESS      not-accessible
    STATUS      mandatory
    DESCRIPTION 
        "A list of subnets which require separate 
         configuration in RIP.
         ALCATEL NOTE:
          TABLESIZE:  256
         	DESCR: 	NA"
    ::= { rip2 3 }

rip2IfConfEntry OBJECT-TYPE
    SYNTAX      Rip2IfConfEntry
    ACCESS      not-accessible
    STATUS      mandatory
    DESCRIPTION 
        "A Single Routing Domain in a single Subnet.
         Row creation : A rip2IfConf entry shall be created in one step by a
             		set-request with all necessary parameter values and
             		rip2IfConfStatus set to createAndGo(4).
         Row deletion : A rip2IfConf entry shall be deleted by setting
             		the rip2IfConfStatus of the specific entry to destroy(6).
         Index usage : the index is the rip2IfConfAddress.
         Note that entries will be presented to the SNMP manager in full
         lexicographical order :  sorted on rip2IfConfAddress."
    INDEX       { rip2IfConfAddress }
    ::= { rip2IfConfTable 1 }

Rip2IfConfEntry ::= SEQUENCE {
    rip2IfConfAddress           IpAddress,
    rip2IfConfDomain            RouteTag,
    rip2IfConfAuthType          INTEGER,
    rip2IfConfAuthKey           OCTET STRING,
    rip2IfConfSend              INTEGER,
    rip2IfConfReceive           INTEGER,
    rip2IfConfDefaultMetric     INTEGER,
    rip2IfConfStatus            RowStatus,
    rip2IfConfSrcAddress        IpAddress
}

rip2IfConfAddress OBJECT-TYPE
    SYNTAX      IpAddress
    ACCESS      read-only
    STATUS      mandatory
    DESCRIPTION 
        "The IP Address of this system on the indicated 
         subnet.  For unnumbered interfaces, the value 0.0.0.N, 
         where the least significant 24 bits (N) is the ifIndex 
         for the IP Interface in network byte order.
         ALCATEL NOTE:
          ACCESS:      NA           USAGE:       NA
          PERSIST:     YES          INSRVMOD:    NA
          RANGE:       NA           DEFVALUE:    NA       
          UNITS:       NA           SPARSE:      NO
          DESCR:       NA"
    ::= { rip2IfConfEntry 1 }

rip2IfConfDomain OBJECT-TYPE
    SYNTAX      RouteTag
    ACCESS      read-write
    STATUS      obsolete
    DESCRIPTION 
        "Value inserted into the Routing Domain field 
         of all RIP packets sent on this interface.
         ALCATEL NOTE:
          ACCESS:      NA           USAGE:       OPT
          PERSIST:     YES          INSRVMOD:    YES
          RANGE:       NA           DEFVALUE:    NA       
          UNITS:       NA           SPARSE:      NO
          DESCR:       NA"
    DEFVAL      { '0000'H }
    ::= { rip2IfConfEntry 2 }

rip2IfConfAuthType OBJECT-TYPE
    SYNTAX      INTEGER { noAuthentication(1), simplePassword(2), md5(3) }
    ACCESS      read-write
    STATUS      mandatory
    DESCRIPTION 
        "The type of Authentication used on this 
         interface.
         ALCATEL NOTE:
          ACCESS:      NA           USAGE:       OPT
          PERSIST:     YES          INSRVMOD:    YES
          RANGE:       NA           DEFVALUE:    NA       
          UNITS:       NA           SPARSE:      NO
          DESCR:       NA"
    DEFVAL      { noAuthentication }
    ::= { rip2IfConfEntry 3 }

rip2IfConfAuthKey OBJECT-TYPE
    SYNTAX      OCTET STRING (SIZE(0..16))
    ACCESS      read-write
    STATUS      mandatory
    DESCRIPTION 
        "The value to be used as the Authentication Key 
         whenever the corresponding instance of 
         rip2IfConfAuthType has a value other than 
         noAuthentication.  A modification of the corresponding 
         instance of rip2IfConfAuthType does not modify 
         the rip2IfConfAuthKey value.  If a string shorter 
         than 16 octets is supplied, it will be left- 
         justified and padded to 16 octets, on the right, 
         with nulls (0x00). 
         
         Reading this object always results in an  OCTET 
         STRING of length zero; authentication may not 
         be bypassed by reading the MIB object.
         ALCATEL NOTE:
          ACCESS:      NA           USAGE:       OPT
          PERSIST:     YES          INSRVMOD:    YES
          RANGE:       NA           DEFVALUE:    NA       
          UNITS:       NA           SPARSE:      NO
          DESCR:       NA"
    DEFVAL      { "" }
    ::= { rip2IfConfEntry 4 }

rip2IfConfSend OBJECT-TYPE
    SYNTAX      INTEGER { doNotSend(1), ripVersion1(2), 
                    rip1Compatible(3), ripVersion2(4), ripV1Demand(5), 
                    ripV2Demand(6) }
    ACCESS      read-write
    STATUS      mandatory
    DESCRIPTION 
        "What the router sends on this interface. 
         ripVersion1 implies sending RIP updates compliant 
         with  RFC  1058.   rip1Compatible implies 
         broadcasting RIP-2 updates using RFC 1058 route 
         subsumption rules.  ripVersion2 implies 
         multicasting RIP-2 updates.  ripV1Demand indicates 
         the use of Demand RIP on a WAN interface under RIP 
         Version 1 rules.  ripV2Demand indicates the use of 
         Demand RIP on a WAN interface under Version 2 rules.
         ALCATEL NOTE:
          ACCESS:      NA           USAGE:       OPT
          PERSIST:     YES          INSRVMOD:    YES
          RANGE:       NA           DEFVALUE:    NA       
          UNITS:       NA           SPARSE:      NO
          DESCR:       NA"
    DEFVAL      { rip1Compatible }
    ::= { rip2IfConfEntry 5 }

rip2IfConfReceive OBJECT-TYPE
    SYNTAX      INTEGER { rip1(1), rip2(2), rip1OrRip2(3), 
                    doNotRecieve(4) }
    ACCESS      read-write
    STATUS      mandatory
    DESCRIPTION 
        "This indicates which version of RIP updates 
         are to be accepted.  Note that rip2 and 
         rip1OrRip2 implies reception of multicast 
         packets.
         ALCATEL NOTE:
          ACCESS:      NA           USAGE:       OPT
          PERSIST:     YES          INSRVMOD:    YES
          RANGE:       NA           DEFVALUE:    NA       
          UNITS:       NA           SPARSE:      NO
          DESCR:       NA"
    DEFVAL      { rip1OrRip2 }
    ::= { rip2IfConfEntry 6 }

rip2IfConfDefaultMetric OBJECT-TYPE
    SYNTAX      INTEGER (0..15)
    ACCESS      read-write
    STATUS      mandatory
    DESCRIPTION 
        "This variable indicates the metric that is to 
         be used for the default route entry in RIP updates 
         originated on this interface.  A value of zero 
         indicates that no default route should be 
         originated; in this case, a default route via 
         another router may be propagated.
         ALCATEL NOTE:
          ACCESS:      NA           USAGE:       MAND
          PERSIST:     YES          INSRVMOD:    YES
          RANGE:       NA           DEFVALUE:    NA       
          UNITS:       NA           SPARSE:      NO
          DESCR:       NA"
    ::= { rip2IfConfEntry 7 }

rip2IfConfStatus OBJECT-TYPE
    SYNTAX      RowStatus
    ACCESS      read-write
    STATUS      mandatory
    DESCRIPTION 
        "Writing invalid has  the  effect  of  deleting 
         this interface.
         ALCATEL NOTE:
          ACCESS:      NA           USAGE:       MAND
          PERSIST:     YES          INSRVMOD:    YES
          RANGE:       1,2,4,5,6    DEFVALUE:    NA
          UNITS:       NA           SPARSE:      NO
          DESCR:       NA"
    ::= { rip2IfConfEntry 8 }

rip2IfConfSrcAddress OBJECT-TYPE
    SYNTAX      IpAddress
    ACCESS      read-write
    STATUS      mandatory
    DESCRIPTION 
        "The IP Address this system will use as a source 
         address on this interface.  If it is a numbered 
         interface, this MUST be the same value as 
         rip2IfConfAddress.  On unnumbered interfaces, 
         it must be the value of rip2IfConfAddress for 
         some interface on the system.
         ALCATEL NOTE:
         ACCESS:      NA           USAGE:       MAND
         PERSIST:     YES          INSRVMOD:    YES
         RANGE:       NA           DEFVALUE:    NA     
         UNITS:       NA           SPARSE:      NO
         DESCR:       NA"
    ::= { rip2IfConfEntry 9 }

rip2PeerTable OBJECT-TYPE
    SYNTAX      SEQUENCE OF Rip2PeerEntry
    ACCESS      not-accessible
    STATUS      mandatory
    DESCRIPTION 
        "A list of RIP Peers.
         ALCATEL NOTE:
             TABLESIZE: 	DEP
         	  	DESCR: 	The Default Table size is 25 and it can be changed Dynamically using the object fsRip2Peers"
    ::= { rip2 4 }

rip2PeerEntry OBJECT-TYPE
    SYNTAX      Rip2PeerEntry
    ACCESS      not-accessible
    STATUS      mandatory
    DESCRIPTION 
        "Information regarding a single routing peer.
         Row creation : A entry will be created by the System when it receives a RIP Packet from the PEER.
         Row deletion : A entry will be deleted when then RIP Interface is deleted/disabled.
         Index usage : the indexes are rip2PeerAddress and rip2PeerDomain
         Note that entries will be presented to the SNMP manager in full
         lexicographical order :  sorted on rip2PeerAddress,then on rip2PeerDomain."
    INDEX       { rip2PeerAddress, rip2PeerDomain }
    ::= { rip2PeerTable 1 }

Rip2PeerEntry ::= SEQUENCE {
    rip2PeerAddress         IpAddress,
    rip2PeerDomain          RouteTag,
    rip2PeerLastUpdate      TimeTicks,
    rip2PeerVersion         INTEGER,
    rip2PeerRcvBadPackets   Counter,
    rip2PeerRcvBadRoutes    Counter
}

rip2PeerAddress OBJECT-TYPE
    SYNTAX      IpAddress
    ACCESS      read-only
    STATUS      mandatory
    DESCRIPTION 
        "The IP Address that the peer is using as its source 
         address.  Note that on an unnumbered link, this may 
         not be a member of any subnet on the system.
         ALCATEL NOTE:
         ACCESS:      NA           USAGE:       NA
         PERSIST:     NO           INSRVMOD:    NA 
         RANGE:       NA           DEFVALUE:    NA       
         UNITS:       NA           SPARSE:      NO
         DESCR:       NA"
    ::= { rip2PeerEntry 1 }

rip2PeerDomain OBJECT-TYPE
    SYNTAX      RouteTag
    ACCESS      read-only
    STATUS      mandatory
    DESCRIPTION 
        "The value in the Routing Domain field  in  RIP 
         packets received from the peer.  As domain suuport 
         is deprecated, this must be zero.
         ALCATEL NOTE:
          ACCESS:      NA           USAGE:       NA
          PERSIST:     NO           INSRVMOD:    NA 
          RANGE:       NA           DEFVALUE:    NA       
          UNITS:       NA           SPARSE:      NO
          DESCR:       NA"
    ::= { rip2PeerEntry 2 }

rip2PeerLastUpdate OBJECT-TYPE
    SYNTAX      TimeTicks
    ACCESS      read-only
    STATUS      mandatory
    DESCRIPTION 
        "The value of sysUpTime when the most recent 
         RIP update was received from this system.
         ALCATEL NOTE:
          ACCESS:      NA           USAGE:       NA
          PERSIST:     NO           INSRVMOD:    NA 
          RANGE:       NA           DEFVALUE:    0
          UNITS:       NA           SPARSE:      NO
          DESCR:       NA"
    ::= { rip2PeerEntry 3 }

rip2PeerVersion OBJECT-TYPE
    SYNTAX      INTEGER (0..255)
    ACCESS      read-only
    STATUS      mandatory
    DESCRIPTION 
        "The RIP version number in the header of the 
         last RIP packet received.
         ALCATEL NOTE:
          ACCESS:      NA           USAGE:       NA
          PERSIST:     NO           INSRVMOD:    NA 
          RANGE:       NA           DEFVALUE:    NA
          UNITS:       NA           SPARSE:      NO
          DESCR:       NA"
    ::= { rip2PeerEntry 4 }

rip2PeerRcvBadPackets OBJECT-TYPE
    SYNTAX      Counter
    ACCESS      read-only
    STATUS      mandatory
    DESCRIPTION 
        "The number of RIP response packets from this 
         peer discarded as invalid.
         ALCATEL NOTE:
          ACCESS:      NA           USAGE:       NA 
          PERSIST:     NO           INSRVMOD:    NA  
          RANGE:       NA           DEFVALUE:    0
          UNITS:       packets      SPARSE:      NO
          DESCR:       NA"
    ::= { rip2PeerEntry 5 }

rip2PeerRcvBadRoutes OBJECT-TYPE
    SYNTAX      Counter
    ACCESS      read-only
    STATUS      mandatory
    DESCRIPTION 
        "The number of routes from this peer that were 
         ignored because the entry format was invalid.
         ALCATEL NOTE:
          ACCESS:      NA           USAGE:       NA 
          PERSIST:     NO           INSRVMOD:    NA  
          RANGE:       NA           DEFVALUE:    0
          UNITS:       routes       SPARSE:      NO
          DESCR:       NA"
    ::= { rip2PeerEntry 6 }

rip2Conformance OBJECT IDENTIFIER
    ::= { rip2 5 }

rip2Groups OBJECT IDENTIFIER
    ::= { rip2Conformance 1 }

rip2GlobalGroup OBJECT IDENTIFIER
    ::= { rip2Groups 1 }

rip2IfStatGroup OBJECT IDENTIFIER
    ::= { rip2Groups 2 }

rip2IfConfGroup OBJECT IDENTIFIER
    ::= { rip2Groups 3 }

rip2PeerGroup OBJECT IDENTIFIER
    ::= { rip2Groups 4 }

rip2Compliances OBJECT IDENTIFIER
    ::= { rip2Conformance 2 }

rip2Compliance OBJECT IDENTIFIER
    ::= { rip2Compliances 1 }

END -- end of module STDRIP2-MIB.
