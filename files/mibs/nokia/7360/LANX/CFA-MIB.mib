--
-- This SMIv1 module has been generated by smidump 0.4.8. Do not edit.
--

CFA-MIB DEFINITIONS ::= BEGIN

IMPORTS
    OBJECT-TYPE
        FROM RFC-1212
    TRAP-TYPE
        FROM RFC-1215
    Counter, Gauge, IpAddress, enterprises
        FROM RFC1155-SMI
    RowStatus, TimeStamp, TruthValue
        FROM SNMPv2-TC;

fscfa OBJECT IDENTIFIER
    ::= { enterprises futuresoftware(2076) 27 }

-- fscfa MODULE-IDENTITY
--     LAST-UPDATED "200005290830Z"
--     ORGANIZATION 
--         "Future Software Private Limited"
--     CONTACT-INFO 
--         " Ketan Talaulikar
--          Postal:  Future Software Pvt. Ltd.,
--                   480-481, Anna Salai,
--                   Nandanam,
--                   Chennai,
--                   India  600 035  
--          Tel: +91-44-4330550
--          E-Mail: ketant@future.futsoft.com "
--     DESCRIPTION 
--         " The MIB module for FutureCFA. "
--     REVISION    "200005290830Z"
--     DESCRIPTION 
--         "The revised version of the MIB for FutureCFA
--          release 1.1.0.0. "
--     ::= { enterprises futuresoftware(2076) 27 }


InterfaceIndex ::=
    INTEGER (1..2147483647)

-- InterfaceIndex ::= TEXTUAL-CONVENTION
--     DISPLAY-HINT "d"
--     STATUS      mandatory
--     DESCRIPTION 
--         "A unique value, greater than zero, for each interface
--          or interface sub-layer in the managed system.  It is
--          recommended that values are assigned contiguously
--          starting from 1.  The value for each interface sub-
--          layer must remain constant at least from one re-
--          initialization of the entity's network management
--          system to the next re-initialization."
--     SYNTAX      INTEGER (1..2147483647)

if OBJECT IDENTIFIER
    ::= { fscfa 1 }

ifMaxInterfaces OBJECT-TYPE
    SYNTAX      InterfaceIndex
    ACCESS      read-write
    STATUS      mandatory
    DESCRIPTION 
        "Specifies the maximum number of interfaces that can
         be present in the system.
         	ALCATEL NOTE:
            	ACCESS:      RO           USAGE:       NA
         	PERSIST:     NO           INSRVMOD:    NA
         	RANGE:       NA           DEFVALUE:    DEP
         	UNITS:       interfaces   SPARSE:      NA
         	DESCR:       DEP(DEFVALUE):The Default Value is the maximum number of physical interfaces
         			    	   available in the system + the total number of IP interfaces in the system. 
         				   The maximum number of physical interfaces is obtained from the object issSystemNumberOfPorts in fsiss.mib.
         				   The total number of IP interfaces in the system is obtained from the object fsVrfMaxIpInterfaces
         				   in fsvrf.mib"
    ::= { if 1 }

ifMaxPhysInterfaces OBJECT-TYPE
    SYNTAX      InterfaceIndex
    ACCESS      read-write
    STATUS      mandatory
    DESCRIPTION 
        "Specifies the maximum number of physical interfaces 
         that can be present in the system.
         	ALCATEL NOTE:
            	ACCESS:      RO           USAGE:       NA
         	PERSIST:     NO           INSRVMOD:    NA
         	RANGE:       NA           DEFVALUE:    DEP 
         	UNITS:       interfaces   SPARSE:      NA
         	DESCR:       DEP(DEFVALUE):The Default Value is the maximum number of physical interfaces
         			    	   available in the system. This is obtained from the object 
         			   	   issSystemNumberOfPorts in fsiss.mib"
    ::= { if 2 }

ifAvailableIndex OBJECT-TYPE
    SYNTAX      InterfaceIndex
    ACCESS      read-only
    STATUS      mandatory
    DESCRIPTION 
        "Shows an ifIndex which is available for creation of
         any new virtual (non-physical) interface in the system.
         This ifIndex value can be used for creation of interfaces
         in the ifMainTable or any media-specif MIB. For creation
         of physical interfaces, any free ifIndex between 1 and
         ifMaxPhysInterfaces can be used.
         	ALCATEL NOTE:
            	ACCESS:      NA           USAGE:       NA
         	PERSIST:     NO           INSRVMOD:    NA
         	RANGE:       NA           DEFVALUE:    NA
         	UNITS:       NA           SPARSE:      NA
         	DESCR:       NA"
    ::= { if 3 }

ifMainTable OBJECT-TYPE
    SYNTAX      SEQUENCE OF IfMainEntry
    ACCESS      not-accessible
    STATUS      mandatory
    DESCRIPTION 
        "A list of all the interface entries in the system. 
         This table contains objects which are applicable to all
         types of interfaces in the system. This table is a 
         proprietary extension to the standard ifTable and 
         ifXTable. The index to this table has the semantics of
         the MIB-2 ifIndex.
         	ALCATEL NOTE:
              TABLESIZE: DEP
         DESCR:	 DEP(TABLESIZE):The size of the table is derived from the 
         		       max number of physical interfaces + 
         		       total number of IP interfaces in the system.
         		       The max number of physical interfaces can be got from the object issSystemNumberOfPorts
         		       in fsiss.mib.
         		       The total number of IP interfaces in the system is obtained from
         		       the object fsVrfMaxIpInterfaces in fsvrf.mib"
    ::= { if 4 }

ifMainEntry OBJECT-TYPE
    SYNTAX      IfMainEntry
    ACCESS      not-accessible
    STATUS      mandatory
    DESCRIPTION 
        "An entry containing management information applicable
         to a particular interface.
         Row creation : Entries for Maximum number of physical interfaces (obtained from issSystemNumberOfPorts in fsiss.mib) and 2 logical interfaces 
         	       (vlan 4093 & 4094) will be created during system startup. Other entries shall be created in one step by a
         		set-request with all necessary parameter values and  ifMainRowStatus 
         		set to createAndGo(4).
         Row deletion : The default entries for Maximum number of physical interfaces (obtained from issSystemNumberOfPorts in fsiss.mib) 
         	       and 2 logical interfaces (vlan 4093 & 4094) cannot be deleted. Other entries shall be deleted by setting the ifMainRowStatus 
         	       of the specific entry to destroy(6)
         Index usage : the index is the if index.
         Note that entries will be presented to the SNMP manager in full
         lexicographical order :  sorted on if index."
    INDEX       { ifMainIndex }
    ::= { ifMainTable 1 }

IfMainEntry ::= SEQUENCE {
    ifMainIndex         InterfaceIndex,
    ifMainType          INTEGER,
    ifMainMtu           INTEGER,
    ifMainAdminStatus   INTEGER,
    ifMainOperStatus    INTEGER,
    ifMainEncapType     INTEGER,
    ifMainRowStatus     RowStatus
}

ifMainIndex OBJECT-TYPE
    SYNTAX      InterfaceIndex
    ACCESS      not-accessible
    STATUS      mandatory
    DESCRIPTION 
        "A unique value, greater than zero, for each
         interface. This object is identical to the ifIndex
         of the standard MIB-2 ifTable.
         	ALCATEL NOTE:
            	ACCESS:      NA           USAGE:       NA
         	PERSIST:     YES          INSRVMOD:    NA
         	RANGE:       DEP	  DEFVALUE:    NA
         	UNITS:       NA           SPARSE:      NO
         	DESCR:       DEP :The IP interfaces will start from 65536 to the 
         			  total number of IP interfaces in the system is obtained from 
              		  the object fsVrfMaxIpInterfaces in fsvrf.mib.  
         			  The indices 81920 & 81921 are reserved for vlan 4094 & 4093.  
         			  respectively."
    ::= { ifMainEntry 1 }

ifMainType OBJECT-TYPE
    SYNTAX      INTEGER { rfc877x25(5), ethernetCsmacd(6), 
                    iso88025TokenRing(9), ppp(23), softwareLoopback(24), 
                    frameRelay(32), miox25(38), aal5(49), async(84), 
                    frameRelayMPI(92), pppMultilinkBundle(108), 
                    ipOverAtm(114), hdlc(118), atmSubInterface(134), 
                    l3ipvlan(136) }
    ACCESS      read-write
    STATUS      mandatory
    DESCRIPTION 
        "The type/protocol of interface. Specification of
         the object is mandatory for all interfaces. This
         value should be specified after the row creation
         in the ifMainTable and before setting any other
         object in this table. Once the type is specified,
         it cannot be changed - the interface should be
         deleted for changing the type of the interface.
         
         The ethernetCsmacd(6), iso88025TokenRing(9), aal5(49),
         async(84) and hdlc(118) are physical interfaces while
         all other types are virtual or logical interfaces.
         
         For creation of physical interface types, it is mandatory to
         specify the handle to the device driver using the ifAlias
         object of the standard ifXTable before specifying the type.
         This handle could be something like eth1 or /dev/abcd.
         	ALCATEL NOTE:
            	ACCESS:      NA           USAGE:       MAND
         	PERSIST:     YES          INSRVMOD:    NO
         	RANGE:       NA           DEFVALUE:    NA
         	UNITS:       NA           SPARSE:      NO
         	DESCR:       NA"
    ::= { ifMainEntry 2 }

ifMainMtu OBJECT-TYPE
    SYNTAX      INTEGER (90..2026)
    ACCESS      read-write
    STATUS      mandatory
    DESCRIPTION 
        "The MTU for the interface as shown to the higher
         interface sub-layer (this value should not include
         the encapsulation or header added by the interface).
         If IP is operating over the interface, then this 
         value indicates the IP MTU over this interface.
         
         For changing the MTU of any interface, the interface
         must be brought down first - changing MTU while the
         interface is administratively up is not permitted.
         
         If not specified during interface creation, a default
         value is assigned based on the ifMainType given to
         the particular interface.
         
         MTU size of the physical interfaces shall not be taken 
         into account by LANX system and all ethernet packets 
         received with length above 2048 bytes shall be 
         discarded. For L3, MTU size includes the IP header +
         payload.
         	ALCATEL NOTE:
            	ACCESS:      NA           USAGE:       OPT
         	PERSIST:     YES          INSRVMOD:    NO
         	RANGE:       NA           DEFVALUE:    1500
         	UNITS:       bytes        SPARSE:      NO
         	DESCR:       NA"
    ::= { ifMainEntry 3 }

ifMainAdminStatus OBJECT-TYPE
    SYNTAX      INTEGER { up(1), down(2), testing(3), autoup(4) }
    ACCESS      read-write
    STATUS      mandatory
    DESCRIPTION 
        "The desired state of the interface. This object
         can be set only when the ifMainRowStatus of the
         interface is active. This object has the semantics
         of the ifAdminStatus of the standard ifTable.
         
         The testing(3) state indicates that no operational 
         packets can be passed - this state is not currently
         supported. 
         
         When a managed system initializes, all 
         interfaces start with ifMainAdminStatus in the
         autoup(4) state, it's a default state also. As a result
         of either explicit management action or per 
         configuration information retained by the managed
         system, ifMainAdminStatus can be then changed to
         the up (1) state or down (2) state (or remains in the
         autoup(4) state).
         	ALCATEL NOTE:
            	ACCESS:      NA           USAGE:       OPT
         	PERSIST:     YES          INSRVMOD:    YES
         	RANGE:       NA           DEFVALUE:    NA
         	UNITS:       NA           SPARSE:      NO
         	DESCR:       NA"
    DEFVAL      { autoup }
    ::= { ifMainEntry 4 }

ifMainOperStatus OBJECT-TYPE
    SYNTAX      INTEGER { up(1), down(2), testing(3), unknown(4), 
                    dormant(5), notPresent(6), lowerLayerDown(7) }
    ACCESS      read-only
    STATUS      mandatory
    DESCRIPTION 
        "The current operational state of the interface.
         The testing (3) state indicates that no operational
         packets can be passed - this state is not supported
         currently. 
         
         If ifMainAdminStatus is down (2)
         then ifMainOperStatus would be down (2). If
         ifMainAdminStatus is changed to up (1) then
         ifMainOperStatus should change to up (1) if the
         interface is ready to transmit and receive
         work traffic; it should change to dormant (5)
         the interface is waiting for external actions
         (such as a serial line waiting for an incoming
         connection); it should change to lowerLayerDown(7)
         state if it cannot be made up as the interface sub-layer
         below it is down; it should remain in the down (2) state
         if and only if there is a fault that prevents it
         from going to the up (1) state; it should remain in
         the notPresent (6) state if the interface has
         missing (typically, hardware) components.
         
         The status unknown(4) is shown when it is not possible
         to determine the exact status of the interface - e.g.
         the interface sub-layer is performing negotiations - 
         during this period the interface is not up but at the
         same time, it is not a fault condition and hence it
         cannot be shown as down - in such periods the status
         is shown as unknown.
         
         This object has the semantics of the ifOperStatus of the
         standard ifTable.
         	ALCATEL NOTE:
            	ACCESS:      NA           USAGE:       NA
         	PERSIST:     NO           INSRVMOD:    NA
         	RANGE:       NA           DEFVALUE:    NA
         	UNITS:       NA           SPARSE:      NO
         	DESCR:       NA"
    ::= { ifMainEntry 5 }

ifMainEncapType OBJECT-TYPE
    SYNTAX      INTEGER { other(1), nlpid(2), nlpidSnap(3), cudNlpid(4), 
                    cudNlpidSnap(5), llcSnap(6), vcMultiplexed(7), 
                    ethernetV2(8) }
    ACCESS      read-write
    STATUS      mandatory
    DESCRIPTION 
        "The encapsulation type to be used over the interface.
         
         For Ethernet interfaces, the default encapsulation
         type is ethernetV2(8). The other possible encapsulation
         is llcSnap(6). If other(1) is specified then an
         automatic encapsulation type learning method is used
         in ARP for determining the encapsulation for unicast
         destinations while the multicast and broadcast destinations
         use ethernetV2(8).
         
         For PPP and MLPPP interfaces, the encapsulation type can
         only be other(1) and this is the default value.
         
         For FR VCs, the value can be nlpid(2) (for carrying protocols
         which have NLPID) or nlpidSnap(3) (for other protocols). The
         default is nlpid(2) and the types of protocols supported are
         inferred from the stack-layering implemented over the
         interface.
         
         For X.25 VCs, the value can be nlpid(2) or nlpidSnap(3) 
         (where the VC can carry multiplexed protocol traffic with
         each data packet containing the NLPID or SNAP header) or
         cudNlpid(4) or cudNlpidSnap(5) (where the CUD specifies
         the NLPID of the protocol or SNAP and the data packets do
         not contain these headers - for dedicated VCs). The default 
         is cudNlpid(4).
         
         For ATM VCs, the default is llcSnap(6) but the 
         vcMultiplexed(7) encapsulation is also supported.
         			
         This object is not applicable to other interfaces.
         	ALCATEL NOTE:
            	ACCESS:      NA           USAGE:       OPT
         	PERSIST:     YES          INSRVMOD:    NO
         	RANGE:       NA           DEFVALUE:    8
         	UNITS:       NA           SPARSE:      NO
         	DESCR:       NA"
    ::= { ifMainEntry 6 }

ifMainRowStatus OBJECT-TYPE
    SYNTAX      RowStatus
    ACCESS      read-write
    STATUS      mandatory
    DESCRIPTION 
        "A RowStatus variable for addition, deletion and in-activation
         of the interfaces. Specification of the object is mandatory
         for all interfaces.
         
         When the status is active, the interface is created and
         ready to use in the respective protocol modules.
         
         When the status is notInService, the interface has not been
         registered with the respective protocol modules and as such
         those modules are not aware of the existence of the interface
         - creation is hence, incomplete. Setting an active interface
         to notInService results in de-registration/deletion of the
         interface from the respective protocol modules and all the
         configurations associated with that interface in those modules
         may be lost.
         
         Deletion of an interface, may affect the status of other
         interfaces which are layered above or below it in the Interface
         Stack (ifStackTable) and may result in other interfaces being
         made notReady or notInService.
         	ALCATEL NOTE:
            	ACCESS:      NA           USAGE:       MAND
         	PERSIST:     YES          INSRVMOD:    YES
         	RANGE:       1,4,5,6      DEFVALUE:    NA
         	UNITS:       NA           SPARSE:      NO
         	DESCR:       NA"
    ::= { ifMainEntry 7 }

ifIpTable OBJECT-TYPE
    SYNTAX      SEQUENCE OF IfIpEntry
    ACCESS      not-accessible
    STATUS      mandatory
    DESCRIPTION 
        "A list of all the interface entries in the system which
         are registered with IP.
               
         This table contains objects which are applicable for the
         management of IP over the network interfaces
         in the system. 
            
         This table is a extension to the ifMainTable. 
         The index to this table has the semantics of
         the ifMainIndex of the ifMainTable.
               
         Entries are created automatically in this table for
         any interface sub-layer which is layer below IP using
         the ifStackTable. Similarly, entries are deleted from
         this table when the interface's layering below IP is
         removed.
         	ALCATEL NOTE:
         	TABLESIZE: DEP
         DESCR:	 DEP(TABLESIZE):The size of the table is derived from the 
         		       max number of physical interfaces + 
         		       total number of IP interfaces in the system.
         		       The max number of physical interfaces can be got from the object issSystemNumberOfPorts
         		       in fsiss.mib.
         		       The total number of IP interfaces in the system is obtained from 
         		       the object fsVrfMaxIpInterfaces in fsvrf.mib"
    ::= { if 5 }

ifIpEntry OBJECT-TYPE
    SYNTAX      IfIpEntry
    ACCESS      not-accessible
    STATUS      mandatory
    DESCRIPTION 
        "An entry containing management information applicable
         to a particular interface over which IP is operating.
         Row creation : Entries for Maximum number of physical interfaces (obtained from issSystemNumberOfPorts in fsiss.mib)
         		and 2 logical interfaces (vlan 4093 & 4094) will be created during system startup. Other entries shall be created in one step by a
         		set-request with all necessary parameter values and  ifMainRowStatus (ifMainTable) 
         		set to createAndGo(4).
         Row deletion : The default entries for Maximum number of physical interfaces (obtained from issSystemNumberOfPorts in fsiss.mib) 
         		and 2 logical interfaces (vlan 4093 & 4094) cannot be deleted. Other entries shall be deleted by setting the
         		ifMainRowStatus (ifMainTable) of the specific entry to destroy(6)
         Index usage : the index is the if index.
         Note that entries will be presented to the SNMP manager in full
         lexicographical order :  sorted on if index."
    INDEX       { ifMainIndex }
    ::= { ifIpTable 1 }

IfIpEntry ::= SEQUENCE {
    ifIpAddrAllocMethod         INTEGER,
    ifIpForwardingEnable        TruthValue,
    ifIpVrfId                   INTEGER,
    ifIpUserGatewayInterface    TruthValue
}

ifIpAddrAllocMethod OBJECT-TYPE
    SYNTAX      INTEGER { manual(1), negotiation(2), localAddressPool(3) }
    ACCESS      read-write
    STATUS      mandatory
    DESCRIPTION 
        "The mechanism to be used for allocation of IP
         address for this interface. 
         
         The value negotiation can be used only for PPP
         and MLPPP interfaces which support obtaining of
         IP addresses through negotiation.
         
         The localAddressPool(3) option takes an IP 
         address dynamically from the IP address pool
         of the system.
         
         If the method specified is manual and the IP 
         address is not provided (then the interface   
         would be treated as a un-numbered interface.
         	ALCATEL NOTE:
            	ACCESS:      NA           USAGE:       OPT
         	PERSIST:     YES          INSRVMOD:    NO
         	RANGE:       NA           DEFVALUE:    NA
         	UNITS:       NA           SPARSE:      NO
         	DESCR:       NA"
    DEFVAL      { manual }
    ::= { ifIpEntry 1 }

ifIpForwardingEnable OBJECT-TYPE
    SYNTAX      TruthValue
    ACCESS      read-write
    STATUS      mandatory
    DESCRIPTION 
        "Specifies whether IP forwarding is enable on
         this interface. Disabling IP forwarding on an
         interface will result in packets which are to
         be forwarded on that interface being dropped
         and ICMP error messages being generated for the
         packets.
         	ALCATEL NOTE:
            	ACCESS:      NA           USAGE:       OPT
         	PERSIST:     YES          INSRVMOD:    YES
         	RANGE:       1,2          DEFVALUE:    NA
         	UNITS:       NA           SPARSE:      NO
         	DESCR:       NA"
    DEFVAL      { true }
    ::= { ifIpEntry 5 }

ifIpVrfId OBJECT-TYPE
    SYNTAX      INTEGER
    ACCESS      read-write
    STATUS      mandatory
    DESCRIPTION 
        "Specifies the VRF instance to which this interface is associated. 
         Setting this object to a new value removes the IP address of this
         interface. The IP address of the interface should be reconfigured.
         The default for an interface is 1, which is the default VRF 
         instance.
         	ALCATEL NOTE:
           	ACCESS:      NA           USAGE:       OPT
         	PERSIST:     YES          INSRVMOD:    NO
         	RANGE:       0..127       DEFVALUE:    0
         	UNITS:       NA           SPARSE:      NO
         	DESCR:       NA"
    DEFVAL      { 1 }
    ::= { ifIpEntry 6 }

ifIpUserGatewayInterface OBJECT-TYPE
    SYNTAX      TruthValue
    ACCESS      read-only
    STATUS      mandatory
    DESCRIPTION 
        "The IP interface configured on the V-VLAN in Fast Path VRF is User Gate way Interface.
         If the VLAN for which the IP interface is created is V-VLAN then this object gets set
         as True. Otherwise, false
         	ALCATEL NOTE:
          	ACCESS:      NA           USAGE:       NA
         	PERSIST:     NA           INSRVMOD:    NA
         	RANGE:       1,2          DEFVALUE:    NA
         	UNITS:       NA           SPARSE:      NO
         	DESCR:       NA"
    ::= { ifIpEntry 7 }

ifWanTable OBJECT-TYPE
    SYNTAX      SEQUENCE OF IfWanEntry
    ACCESS      not-accessible
    STATUS      mandatory
    DESCRIPTION 
        "A list of all the WAN interfaces in the system.
         
         This table contains objects which are applicable for the
         management of WAN interfaces like PPP, MP bundle and
         FR/X.25/ATM VCs in the system.
            
         This table is a extension to the ifMainTable. 
         The index to this table has the semantics of
         the ifMainIndex of the ifMainTable.
               
         Entries are created automatically in this table when
         any WAN interface is created in the ifMainTable. The 
         ppp(23), miox25(38), frameRelayMPI(92), 
         pppMultilinkBundle(108) and atmSubInterface(134)
         interfaces have entries in this table. The entries
         in this table are deleted when the interfaces are
         deleted from the ifMainTable.
         ALCATEL NOTE:
          	TABLESIZE: NA 
         	DESCR:	This object is not used by Alcatel"
    ::= { if 6 }

ifWanEntry OBJECT-TYPE
    SYNTAX      IfWanEntry
    ACCESS      not-accessible
    STATUS      mandatory
    DESCRIPTION 
        "An entry containing management information applicable
         to a WAN interface.
         Row creation : NA
         Row deletion : NA
         Index usage : NA
         lexicographical order :  NA
         This object is not used by Alcatel"
    INDEX       { ifMainIndex }
    ::= { ifWanTable 1 }

IfWanEntry ::= SEQUENCE {
    ifWanInterfaceType      INTEGER,
    ifWanConnectionType     INTEGER,
    ifWanVirtualPathId      INTEGER,
    ifWanVirtualCircuitId   INTEGER,
    ifWanPeerMediaAddress   OCTET STRING,
    ifWanSustainedSpeed     INTEGER,
    ifWanPeakSpeed          INTEGER,
    ifWanMaxBurstSize       INTEGER,
    ifWanIpQosProfileIndex  INTEGER,
    ifWanIdleTimeout        INTEGER,
    ifWanPeerIpAddr         IpAddress,
    ifWanRtpHdrComprEnable  TruthValue,
    ifWanPersistence        INTEGER
}

ifWanInterfaceType OBJECT-TYPE
    SYNTAX      INTEGER { ppp(23), miox25(38), frameRelayMPI(92), 
                    pppMultilinkBundle(108), atmSubInterface(134) }
    ACCESS      read-only
    STATUS      mandatory
    DESCRIPTION 
        "The type of the WAN interface. This is
         same as if MIB-2 ifType and ifMainType.
         ALCATEL NOTE:
         ACCESS:      NA           USAGE:       NA
         PERSIST:     NA           INSRVMOD:    NA
         RANGE:       NA           DEFVALUE:    NA
         UNITS:       NA           SPARSE:      NA
         DESCR:       This object is not used by Alcatel"
    ::= { ifWanEntry 1 }

ifWanConnectionType OBJECT-TYPE
    SYNTAX      INTEGER { other(0), permanent(1), switched(2) }
    ACCESS      read-write
    STATUS      mandatory
    DESCRIPTION 
        "The type of WAN connection. This object
         will not be applicable to PPP and MLPPP
         interfaces and will have the value other(0).
         For all other interfaces the default value
         is permanent(1). 
         
         It is possible to pre-configure a SVC through
         this table. The actual SVC establishment may
         take place when there is data to be sent or
         through some other system policy.
         ALCATEL NOTE:
         ACCESS:      NA           USAGE:       NA
         PERSIST:     NA           INSRVMOD:    NA
         RANGE:       NA           DEFVALUE:    NA
         UNITS:       NA           SPARSE:      NA
         DESCR:       This object is not used by Alcatel"
    ::= { ifWanEntry 2 }

ifWanVirtualPathId OBJECT-TYPE
    SYNTAX      INTEGER
    ACCESS      read-write
    STATUS      mandatory
    DESCRIPTION 
        "The VPI for ATM VCs. This object
         will not be applicable to other
         interfaces and will have the value 0.
         ALCATEL NOTE:
         ACCESS:      NA           USAGE:       NA
         PERSIST:     NA           INSRVMOD:    NA
         RANGE:       NA           DEFVALUE:    NA
         UNITS:       NA           SPARSE:      NA
         DESCR:       This object is not used by Alcatel"
    DEFVAL      { 0 }
    ::= { ifWanEntry 3 }

ifWanVirtualCircuitId OBJECT-TYPE
    SYNTAX      INTEGER
    ACCESS      read-write
    STATUS      mandatory
    DESCRIPTION 
        "The VCI for ATM VCs, DLCI for Frame Relay VCs and
         the channel identifier for X.25 VCs.
         
         For SVCs this object is read-only, the value will be 
         assigned after the SVC establishment.
         
         This object will not be applicable to PPP and
         MLPPP interfaces and will have the value 0.
         ALCATEL NOTE:
         ACCESS:      NA           USAGE:       NA
         PERSIST:     NA           INSRVMOD:    NA
         RANGE:       NA           DEFVALUE:    NA
         UNITS:       NA           SPARSE:      NA
         DESCR:       This object is not used by Alcatel"
    DEFVAL      { 0 }
    ::= { ifWanEntry 4 }

ifWanPeerMediaAddress OBJECT-TYPE
    SYNTAX      OCTET STRING (SIZE(0..40))
    ACCESS      read-write
    STATUS      mandatory
    DESCRIPTION 
        "The Media Address of the peer to whom this 
         connection is to be established.
         
         For ATM VCs this can be in E.164, NSAP or either of these along
         with the subaddress. For Frame Relay VCs this is in
         E.164 and for X.25 VCs it is in X.121 format.
         
         For SVCs this object is mandatory, for PVCs it is
         optional.
         
         This object will not be applicable to PPP and
         MLPPP interfaces and will have the value 0.
         ALCATEL NOTE:
         ACCESS:      NA           USAGE:       NA
         PERSIST:     NA           INSRVMOD:    NA
         RANGE:       NA           DEFVALUE:    NA
         UNITS:       NA           SPARSE:      NA
         DESCR:       This object is not used by Alcatel"
    ::= { ifWanEntry 5 }

ifWanSustainedSpeed OBJECT-TYPE
    SYNTAX      INTEGER
    ACCESS      read-write
    STATUS      mandatory
    DESCRIPTION 
        "The sustained or minimum gauranteed speed of
         the interface. This is semantically similar to
         the CIR for FR and SCR for ATM. The value to be
         assigned is the CIR or SCR as the case may be.
         This value is used by IP-QoS.
         
         For PPP links this object should be given the value
         of the speed of the lower link. For MP this value
         is the sum of the speed of all the lower PPP links.
         
         If the value is not specified then the system default 
         values are taken based on the type of the interface.
         ALCATEL NOTE:
         ACCESS:      NA           USAGE:       NA
         PERSIST:     NA           INSRVMOD:    NA
         RANGE:       NA           DEFVALUE:    NA
         UNITS:       NA           SPARSE:      NA
         DESCR:       This object is not used by Alcatel"
    ::= { ifWanEntry 6 }

ifWanPeakSpeed OBJECT-TYPE
    SYNTAX      INTEGER
    ACCESS      read-write
    STATUS      mandatory
    DESCRIPTION 
        "The maximum speed available on the interface. 
         This is semantically similar to the CIR+EIR for FR
         and PCR for ATM. This value is used by IP-QoS.
         
         For PPP links this object should be given the value
         of the speed of the lower link. For MP this value
         is the sum of the speed of all the lower PPP links.
         
         If the value is not specified then the ifWanSustatinedSpeed
         values are taken as the peak speed values.
         ALCATEL NOTE:
         ACCESS:      NA           USAGE:       NA
         PERSIST:     NA           INSRVMOD:    NA
         RANGE:       NA           DEFVALUE:    NA
         UNITS:       NA           SPARSE:      NA
         DESCR:       This object is not used by Alcatel"
    ::= { ifWanEntry 7 }

ifWanMaxBurstSize OBJECT-TYPE
    SYNTAX      INTEGER
    ACCESS      read-write
    STATUS      mandatory
    DESCRIPTION 
        "The maximum burst size in bytes that the interface
         can sustain. This is semantically similar to the Bc for FR
         and MBS for ATM. This value is used by IP-QoS.
         
         For PPP links this object should be given the value
         of the speed of the lower link. For MP this value
         is the sum of the speed of all the lower PPP links.
         
         If the value is not specified then the system default
         values are taken based on the type of interface.
         ALCATEL NOTE:
         ACCESS:      NA           USAGE:       NA
         PERSIST:     NA           INSRVMOD:    NA
         RANGE:       NA           DEFVALUE:    NA
         UNITS:       NA           SPARSE:      NA
         DESCR:       This object is not used by Alcatel"
    ::= { ifWanEntry 8 }

ifWanIpQosProfileIndex OBJECT-TYPE
    SYNTAX      INTEGER
    ACCESS      read-write
    STATUS      mandatory
    DESCRIPTION 
        "The index of an IP-QoS profile which is configured
         in the IP-QoS MIB. Assigning the index of the profile
         results in instantiation of that profile for the
         interface. 
         
         This object is optional and may be specified only for
         assigning an IP-QoS profile - if not specified then no
         profile is applied to this interface - default value
         is then the invalid index 0.
         ALCATEL NOTE:
         ACCESS:      NA           USAGE:       NA
         PERSIST:     NA           INSRVMOD:    NA
         RANGE:       NA           DEFVALUE:    NA
         UNITS:       NA           SPARSE:      NA
         DESCR:       This object is not used by Alcatel"
    DEFVAL      { 0 }
    ::= { ifWanEntry 9 }

ifWanIdleTimeout OBJECT-TYPE
    SYNTAX      INTEGER
    ACCESS      read-write
    STATUS      mandatory
    DESCRIPTION 
        "The minimum duration (in seconds) to wait before
         disconnecting an idle established circuit/interface. (a
         default value of 0 where not required) Specification
         of the object is optional for all interfaces; if not
         specified the system default value is assumed on the basis
         of the IfType specified.
         ALCATEL NOTE:
         ACCESS:      NA           USAGE:       NA
         PERSIST:     NA           INSRVMOD:    NA
         RANGE:       NA           DEFVALUE:    NA
         UNITS:       NA           SPARSE:      NA
         DESCR:       This object is not used by Alcatel"
    DEFVAL      { 0 }
    ::= { ifWanEntry 10 }

ifWanPeerIpAddr OBJECT-TYPE
    SYNTAX      IpAddress
    ACCESS      read-write
    STATUS      mandatory
    DESCRIPTION 
        "The IP address of the peer to whom this interface is
         established with. Specification of this value is optional
         for all interfaces.
         
         For PPP and MLPPP interfaces, this value if specified
         is used during IPCP negotiation for assigning IP address
         to the peer. This object stores the configured peer IP
         address and this object is not updated with the actual
         IP address of the peer.
         
         For other interfaces, this value is either configured
         for peers who do not have InARP support or this object
         is instantiated after the peer IP address is obtained 
         after InARP.
         ALCATEL NOTE:
         ACCESS:      NA           USAGE:       NA
         PERSIST:     NA           INSRVMOD:    NA
         RANGE:       NA           DEFVALUE:    NA
         UNITS:       NA           SPARSE:      NA
         DESCR:       This object is not used by Alcatel"
    DEFVAL      { '00000000'H }
    ::= { ifWanEntry 11 }

ifWanRtpHdrComprEnable OBJECT-TYPE
    SYNTAX      TruthValue
    ACCESS      read-write
    STATUS      mandatory
    DESCRIPTION 
        "Enable or disable the RTP header compression on the
         WAN interface. This object is writable for only those
         interface which are registered with IP. If the RTP
         header compression negotiation with the peer fails then
         this object is reset to false.
         ALCATEL NOTE:
         ACCESS:      NA           USAGE:       NA
         PERSIST:     NA           INSRVMOD:    NA
         RANGE:       NA           DEFVALUE:    NA
         UNITS:       NA           SPARSE:      NA
         DESCR:       This object is not used by Alcatel"
    DEFVAL      { false }
    ::= { ifWanEntry 12 }

ifWanPersistence OBJECT-TYPE
    SYNTAX      INTEGER { other(1), demand(2) }
    ACCESS      read-write
    STATUS      mandatory
    DESCRIPTION 
        "The persistence of the WAN interface in the system.
         
         Demand(2) circuits are pre-configured but are opened only 
         when there is some data to be sent (these interfaces are 
         administratively UP, but operationally DORMANT and they are 
         made UP dynamically whenever there is any data to be sent 
         over the interface). The demand circuit configuration 
         continues to persist in the system.
         
         Alll other WAN interface which do not fall under the above
         categories are to be configured as other(1) which is the
         default value.
         ALCATEL NOTE:
         ACCESS:      NA           USAGE:       NA
         PERSIST:     NA           INSRVMOD:    NA
         RANGE:       NA           DEFVALUE:    NA
         UNITS:       NA           SPARSE:      NA
         DESCR:       This object is not used by Alcatel"
    DEFVAL      { other }
    ::= { ifWanEntry 13 }

ifAutoCktProfileTable OBJECT-TYPE
    SYNTAX      SEQUENCE OF IfAutoProfileEntry
    ACCESS      not-accessible
    STATUS      mandatory
    DESCRIPTION 
        "A list of all the automatic circuit profiles in the system. 
         This table contains objects which are useful for configuration
         of an automatic circuit profile for a given interface.
         The profile specified here is used for the configuration of
         all the incoming calls on the specified interface. The new
         interfaces are assigned MIB-2 ifIndex upon creation. The
         interface is deleted once the circuit is closed.
         ALCATEL NOTE:
          	TABLESIZE: NA 
         	DESCR:	This object is not used by Alcatel"
    ::= { if 7 }

ifAutoProfileEntry OBJECT-TYPE
    SYNTAX      IfAutoProfileEntry
    ACCESS      not-accessible
    STATUS      mandatory
    DESCRIPTION 
        "An entry containing information applicable
         to an automatic circuit profile for an interface.
         Row creation : NA
         Row deletion : NA
         Index usage : NA
         lexicographical order :  NA
         This object is not used by Alcatel"
    INDEX       { ifAutoProfileIfIndex }
    ::= { ifAutoCktProfileTable 1 }

IfAutoProfileEntry ::= SEQUENCE {
    ifAutoProfileIfIndex                InterfaceIndex,
    ifAutoProfileIfType                 INTEGER,
    ifAutoProfileIpAddrAllocMethod      INTEGER,
    ifAutoProfileDefIpSubnetMask        IpAddress,
    ifAutoProfileDefIpBroadcastAddr     IpAddress,
    ifAutoProfileIdleTimeout            INTEGER,
    ifAutoProfileEncapType              INTEGER,
    ifAutoProfileIpQosProfileIndex      INTEGER,
    ifAutoProfileRowStatus              RowStatus
}

ifAutoProfileIfIndex OBJECT-TYPE
    SYNTAX      InterfaceIndex
    ACCESS      not-accessible
    STATUS      mandatory
    DESCRIPTION 
        "The MIB-2 ifIndex of the interface for which
         this automatic circuit profile is applicable.
         All incoming calls on this interface will be
         handled/configured according to this profile.
         ALCATEL NOTE:
         ACCESS:      NA           USAGE:       NA
         PERSIST:     NA           INSRVMOD:    NA
         RANGE:       NA           DEFVALUE:    NA
         UNITS:       NA           SPARSE:      NA
         DESCR:       This object is not used by Alcatel"
    ::= { ifAutoProfileEntry 1 }

ifAutoProfileIfType OBJECT-TYPE
    SYNTAX      INTEGER { rfc877x25(5), frameRelay(32), aal5(49), 
                    ipOverAtm(114) }
    ACCESS      read-only
    STATUS      mandatory
    DESCRIPTION 
        "The type of the WAN interface. This is
         same as if MIB-2 ifType and ifMainType.
         ALCATEL NOTE:
         ACCESS:      NA           USAGE:       NA
         PERSIST:     NA           INSRVMOD:    NA
         RANGE:       NA           DEFVALUE:    NA
         UNITS:       NA           SPARSE:      NA
         DESCR:       This object is not used by Alcatel"
    ::= { ifAutoProfileEntry 2 }

ifAutoProfileIpAddrAllocMethod OBJECT-TYPE
    SYNTAX      INTEGER { other(1), negotiation(2), localAddressPool(3) }
    ACCESS      read-write
    STATUS      mandatory
    DESCRIPTION 
        "The mechanism to be used for allocation of IP
         address for this interface. 
         
         The value negotiation can be used only if PPP
         or MLPPP interfaces are to run over the automatic
         circuits.
         
         The localAddressPool(3) option takes an IP 
         address dynamically from the IP address pool
         specified by the ifAutoProfileIpAddrPoolIndex.
         
         If the method specified is other(1) then either
         the IP address is not required or is obtained 
         by some other method.
         ALCATEL NOTE:
         ACCESS:      NA           USAGE:       NA
         PERSIST:     NA           INSRVMOD:    NA
         RANGE:       NA           DEFVALUE:    NA
         UNITS:       NA           SPARSE:      NA
         DESCR:       This object is not used by Alcatel"
    DEFVAL      { other }
    ::= { ifAutoProfileEntry 3 }

ifAutoProfileDefIpSubnetMask OBJECT-TYPE
    SYNTAX      IpAddress
    ACCESS      read-write
    STATUS      mandatory
    DESCRIPTION 
        "Specifies the default IP Subnet Mask for this
         profile. The value should be specified only
         for network interfaces and any valid VLSM is
         accepted. 
         
         If not specified, this object takes the default
         subnet mask value based on the class of the IP
         address configured for the interface.
         ALCATEL NOTE:
         ACCESS:      NA           USAGE:       NA
         PERSIST:     NA           INSRVMOD:    NA
         RANGE:       NA           DEFVALUE:    NA
         UNITS:       NA           SPARSE:      NA
         DESCR:       This object is not used by Alcatel"
    ::= { ifAutoProfileEntry 4 }

ifAutoProfileDefIpBroadcastAddr OBJECT-TYPE
    SYNTAX      IpAddress
    ACCESS      read-write
    STATUS      mandatory
    DESCRIPTION 
        "Specifies the default IP broadcast address for this
         interface. Any valid broadcast
         address based on a valid VLSM is accepted. 
         
         If not specified, this object takes the default
         value based on the class of the IP
         address configured for the interface.
         ALCATEL NOTE:
         ACCESS:      NA           USAGE:       NA
         PERSIST:     NA           INSRVMOD:    NA
         RANGE:       NA           DEFVALUE:    NA
         UNITS:       NA           SPARSE:      NA
         DESCR:       This object is not used by Alcatel"
    ::= { ifAutoProfileEntry 5 }

ifAutoProfileIdleTimeout OBJECT-TYPE
    SYNTAX      INTEGER
    ACCESS      read-write
    STATUS      mandatory
    DESCRIPTION 
        "The minimum duration (in seconds) to wait before
         disconnecting an idle automatic circuit. Specification
         of the object is mandatory.
         ALCATEL NOTE:
         ACCESS:      NA           USAGE:       NA
         PERSIST:     NA           INSRVMOD:    NA
         RANGE:       NA           DEFVALUE:    NA
         UNITS:       NA           SPARSE:      NA
         DESCR:       This object is not used by Alcatel"
    ::= { ifAutoProfileEntry 6 }

ifAutoProfileEncapType OBJECT-TYPE
    SYNTAX      INTEGER { other(1), nlpid(2), nlpidSnap(3), cudNlpid(4), 
                    cudNlpidSnap(5), llcSnap(6), vcMultiplexed(7) }
    ACCESS      read-write
    STATUS      mandatory
    DESCRIPTION 
        "The encapsulation type to be used over the automatic 
         circuit.
         
         For FR interface, the value can be nlpid(2) (for carrying protocols
         which have NLPID) or nlpidSnap(3) (for other protocols). The
         default is nlpid(2) and the types of protocols supported are
         inferred from the stack-layering implemented over the
         interface.
         
         For X.25 interface, the value can be nlpid(2) or nlpidSnap(3) 
         (where the VC can carry multiplexed protocol traffic with
         each data packet containing the NLPID or SNAP header) or
         cudNlpid(4) or cudNlpidSnap(5) (where the CUD specifies
         the NLPID of the protocol or SNAP and the data packets do
         not contain these headers - for dedicated VCs). The default 
         is cudNlpid(4).
         
         For ATM interface, the default is llcSnap(6) but the 
         vcMultiplexed(7) encapsulation is also supported.
         ALCATEL NOTE:
         ACCESS:      NA           USAGE:       NA
         PERSIST:     NA           INSRVMOD:    NA
         RANGE:       NA           DEFVALUE:    NA
         UNITS:       NA           SPARSE:      NA
         DESCR:       This object is not used by Alcatel"
    ::= { ifAutoProfileEntry 7 }

ifAutoProfileIpQosProfileIndex OBJECT-TYPE
    SYNTAX      INTEGER
    ACCESS      read-write
    STATUS      mandatory
    DESCRIPTION 
        "The index of an IP-QoS profile which is configured
         in the IP-QoS MIB. Assigning the index of the profile
         results in instantiation of that profile for any
         automatic circuit which is instantiated based on this
         profile (and a corresponding profile is instantiated
         in the IP-QoS table also).
         
         This object is optional and may be specified only for
         assigning an IP-QoS profile - if not specified then no
         profile is applied to this interface - default value
         is then the invalid index 0.
         ALCATEL NOTE:
         ACCESS:      NA           USAGE:       NA
         PERSIST:     NA           INSRVMOD:    NA
         RANGE:       NA           DEFVALUE:    NA
         UNITS:       NA           SPARSE:      NA
         DESCR:       This object is not used by Alcatel"
    DEFVAL      { 0 }
    ::= { ifAutoProfileEntry 8 }

ifAutoProfileRowStatus OBJECT-TYPE
    SYNTAX      RowStatus
    ACCESS      read-write
    STATUS      mandatory
    DESCRIPTION 
        "A RowStatus object for creation of automatic circuit
         profile on a per interface basis.
         
         It is necessary to create the parent FR,X.25 or ATM/IPoA
         interface before creating the automatic circuit profile
         for that interface.
         
         The profile is deleted once the parent interface is 
         deleted from the system.
         
         Setting this object to notInService for an active profile
         will result in the profile being not applied to any new
         automatic circuit, but the existing circuits would not
         be affected. Similarly, deleting a profile would not affect
         existing circuits which have used that profile.
         ALCATEL NOTE:
         ACCESS:      NA           USAGE:       NA
         PERSIST:     NA           INSRVMOD:    NA
         RANGE:       NA           DEFVALUE:    NA
         UNITS:       NA           SPARSE:      NA
         DESCR:       This object is not used by Alcatel"
    ::= { ifAutoProfileEntry 9 }

ifIvrTable OBJECT-TYPE
    SYNTAX      SEQUENCE OF IfIvrEntry
    ACCESS      not-accessible
    STATUS      mandatory
    DESCRIPTION 
        "A list of all the interfaces in the system with IVR related
         configurations.
         
         This table is an extension to the ifMainTable. The index to 
         this table has the semantics of the ifMainIndex of the 
         ifMainTable.
         	ALCATEL NOTE:
         	TABLESIZE: DEP
         DESCR:	 DEP(TABLESIZE):The size of the table is derived from the 
         		       max number of physical interfaces + 
         		       total number of IP interfaces in the system.
         		       The max number of physical interfaces can be got from the object issSystemNumberOfPorts
         		       in fsiss.mib.
         		       The total number of IP interfaces in the system is obtained from 
         		       the object fsVrfMaxIpInterfaces in fsvrf.mib"
    ::= { if 8 }

ifIvrEntry OBJECT-TYPE
    SYNTAX      IfIvrEntry
    ACCESS      not-accessible
    STATUS      mandatory
    DESCRIPTION 
        "An entry containing IVR-related information applicable
         to a interface.
         Row creation : Entries for Maximum number of physical interfaces (obtained from issSystemNumberOfPorts in fsiss.mib)
         		and 2 logical interfaces (vlan 4093 & 4094) will be created during system startup. Other entries shall be created in one step by a
         		set-request with all necessary parameter values and  ifMainRowStatus (ifMainTable) 
         		set to createAndGo(4).
         Row deletion : The default entries for Maximum number of physical interfaces (obtained from issSystemNumberOfPorts in fsiss.mib)
         		and 2 logical interfaces (vlan 4093 & 4094) cannot be deleted. Other entries shall be deleted by setting the 
         		ifMainRowStatus (ifMainTable) of the specific entry to destroy(6)
         Index usage : the index is the if index.
         Note that entries will be presented to the SNMP manager in full
         lexicographical order :  sorted on if index."
    INDEX       { ifMainIndex }
    ::= { ifIvrTable 1 }

IfIvrEntry ::= SEQUENCE {
    ifIvrBridgedIface   TruthValue
}

ifIvrBridgedIface OBJECT-TYPE
    SYNTAX      TruthValue
    ACCESS      read-write
    STATUS      mandatory
    DESCRIPTION 
        "Indicates if this interface is a Bridged interface
         or not. 
         A value of 'TRUE' indicates that this interface is 
         a Bridged interface and is capable of performing 
         bridging of packets through this interface.
         A value of 'FALSE' indicates that this 
         interface is a Routed interface and is capable of
         performing routing of packets through this interface.
         	ALCATEL NOTE:
            	ACCESS:      NA           USAGE:       MAND
         	PERSIST:     YES          INSRVMOD:    YES
         	RANGE:       1,2          DEFVALUE:    NA
         	UNITS:       NA           SPARSE:      NO
         	DESCR:       NA"
    ::= { ifIvrEntry 1 }

ifSetMgmtVlanList OBJECT-TYPE
    SYNTAX      OCTET STRING (SIZE(0..512))
    ACCESS      read-write
    STATUS      mandatory
    DESCRIPTION 
        "A string of octets containing one bit per VLAN. The
         first octet corresponds to VLANs with VlanId values
         1 through 8; the second octet to VLANs 9 through
         16 etc.  The most significant bit of each octet
         corresponds to the lowest VlanId value in that octet.
         This is the set of vlans configured by management to associate 
         with the management interface.
         	ALCATEL NOTE:
             	ACCESS:      RO           USAGE:       NA
          	PERSIST:     NO           INSRVMOD:    NA
          	RANGE:       NA           DEFVALUE:    NA
          	UNITS:       NA           SPARSE:      NA
          	DESCR:       NA"
    ::= { if 9 }

ifResetMgmtVlanList OBJECT-TYPE
    SYNTAX      OCTET STRING (SIZE(0..512))
    ACCESS      read-write
    STATUS      mandatory
    DESCRIPTION 
        "A string of octets containing one bit per VLAN. The
         first octet corresponds to VLANs with VlanId values
         1 through 8; the second octet to VLANs 9 through
         16 etc.  The most significant bit of each octet
         corresponds to the lowest VlanId value in that octet.
         This is the set of vlans configured by management to dis-associate 
         from the management interface.
         Get operation is not allowed for this object.
         	ALCATEL NOTE:
             	ACCESS:      RO           USAGE:       NA
          	PERSIST:     NO           INSRVMOD:    NA
          	RANGE:       NA           DEFVALUE:    NA
          	UNITS:       NA           SPARSE:      NA
          	DESCR:       NA"
    ::= { if 10 }

ifMultiNetIpTable OBJECT-TYPE
    SYNTAX      SEQUENCE OF IfMultiNetIpEntry
    ACCESS      not-accessible
    STATUS      mandatory
    DESCRIPTION 
        "A list of all the interface entries in the system which
         are registered with IP and their corresponding set of
          IP addresses.
         	ALCATEL NOTE:
         	TABLESIZE: DEP
         DESCR:	 DEP(TABLESIZE):The size of the table is derived from the 
         		       max number of physical interfaces + 
         		       total number of IP interfaces in the system.
         		       The max number of physical interfaces can be got from the object issSystemNumberOfPorts
         		       in fsiss.mib.
         		       The total number of IP interfaces in the system is obtained from
         		       the object fsVrfMaxIpInterfaces in fsvrf.mib"
    ::= { if 11 }

ifMultiNetIpEntry OBJECT-TYPE
    SYNTAX      IfMultiNetIpEntry
    ACCESS      not-accessible
    STATUS      mandatory
    DESCRIPTION 
        "An entry containing management information applicable
         to a particular interface over which IP is operating.
         Row creation : Entries shall be created in one step by a set-request with all necessary 
         		parameter values and  ifMultiNetIpRowStatus set to createAndGo(4).
         Row deletion : Entries shall be deleted by setting the ifMultiNetIpRowStatus  
         		of the specific entry to destroy(6)
         Index usage : the index is the if index and IP address.
         Note that entries will be presented to the SNMP manager in full
         lexicographical order :  sorted on if index, the on IP address."
    INDEX       { ifMainIndex, ifMultiNetIpAddr }
    ::= { ifMultiNetIpTable 1 }

IfMultiNetIpEntry ::= SEQUENCE {
    ifMultiNetIpAddr            IpAddress,
    ifMultiNetIpSubnetMask      IpAddress,
    ifMultiNetIpBroadcastAddr   IpAddress,
    ifMultiNetIpRowStatus       RowStatus
}

ifMultiNetIpAddr OBJECT-TYPE
    SYNTAX      IpAddress
    ACCESS      read-only
    STATUS      mandatory
    DESCRIPTION 
        "Specifies the IP address given to this
         interface. The specification of this object is
         mandatory for all interfaces. If the IP address is
         not specified for the interface then the default value
         of 0.0.0.0 is assigned and the interface is
         treated as a un-numbered interface by IP.	
         	ALCATEL NOTE:
            	ACCESS:      NA           USAGE:       NA
         	PERSIST:     YES          INSRVMOD:    NA
         	RANGE:       NA           DEFVALUE:    NA
         	UNITS:       NA           SPARSE:      NO
         	DESCR:       NA"
    ::= { ifMultiNetIpEntry 1 }

ifMultiNetIpSubnetMask OBJECT-TYPE
    SYNTAX      IpAddress
    ACCESS      read-write
    STATUS      mandatory
    DESCRIPTION 
        "Specifies the IP Subnet Mask for this
         interface.The specification of this object is
         mandatory for all interfaces. 
         	ALCATEL NOTE:
            	ACCESS:      NA           USAGE:       OPT
         	PERSIST:     YES          INSRVMOD:    YES
         	RANGE:       NA           DEFVALUE:    NA
         	UNITS:       NA           SPARSE:      NO
         	DESCR:       NA"
    ::= { ifMultiNetIpEntry 2 }

ifMultiNetIpBroadcastAddr OBJECT-TYPE
    SYNTAX      IpAddress
    ACCESS      read-only
    STATUS      mandatory
    DESCRIPTION 
        "Specifies the IP Broadcast address for this
         interface.
         	ALCATEL NOTE:
            	ACCESS:      NA           USAGE:       OPT
         	PERSIST:     YES          INSRVMOD:    YES
         	RANGE:       NA           DEFVALUE:    NA
         	UNITS:       NA           SPARSE:      NO
         	DESCR:       NA"
    ::= { ifMultiNetIpEntry 3 }

ifMultiNetIpRowStatus OBJECT-TYPE
    SYNTAX      RowStatus
    ACCESS      read-write
    STATUS      mandatory
    DESCRIPTION 
        "Specifies the Row Status of the IP entry for the interface. 
         To create a new entry this has to be created with one of the following options
         
         - `active(1)', which indicates that the entry  is available for use 
         
         -  'NotinService(2)', which indicates status is not in service
         
         - `createAndGo(4)', which is used to create a new instance and to 
           have its status automatically set to active
         
         - 'CreateAndWait(5)', which is used to create an new instance and wait for the status to 
             be set to active by the user 
         
         - `destroy(6)', which is used to delete that row
         	ALCATEL NOTE:
           	ACCESS:      NA           USAGE:       MAND
         	PERSIST:     YES          INSRVMOD:    YES
         	RANGE:       1,2,4,5,6    DEFVALUE:    NA
         	UNITS:       NA           SPARSE:      NO
         	DESCR:       NA"
    ::= { ifMultiNetIpEntry 4 }

ifUnnumberedTable OBJECT-TYPE
    SYNTAX      SEQUENCE OF IfUnnumberedEntry
    ACCESS      not-accessible
    STATUS      mandatory
    DESCRIPTION 
        "A list of Unnumbered interfaces in the system.
         This table is an extension to the ifMainTable. The index to 
         this table has the semantics of the ifMainIndex of the 
          ifMainTable.
         	ALCATEL NOTE:
          	TABLESIZE: 1 
         	DESCR:	NA"
    ::= { if 12 }

ifUnnumberedEntry OBJECT-TYPE
    SYNTAX      IfUnnumberedEntry
    ACCESS      not-accessible
    STATUS      mandatory
    DESCRIPTION 
        "An entry containing Associated Interface Index applicable
         to a Unnumbered L3IP VLAN interface.
         Entries shall be created by directly configuring ifBorrowedIndex object.
         Entries shall be deleted by setting the ifMainRowStatus (present in 
         	ifMainTable) of the specific entry to destroy(6).
         Note that entries will be presented to the SNMP manager in full
         lexicographical order :  sorted on if index"
    INDEX       { ifMainIndex }
    ::= { ifUnnumberedTable 1 }

IfUnnumberedEntry ::= SEQUENCE {
    ifBorrowedIndex     InterfaceIndex
}

ifBorrowedIndex OBJECT-TYPE
    SYNTAX      InterfaceIndex
    ACCESS      read-write
    STATUS      mandatory
    DESCRIPTION 
        "A value, greater than zero, for each unnumbered
         interface denoting the Interface Index of the interface
         to which it is assosiated.This object is identical 
         to the ifIndex of the standard MIB-2 ifTable.
         	ALCATEL NOTE:
            ACCESS:      NA		  USAGE:       MAND 
         	PERSIST:     NO           INSRVMOD:    YES
         	RANGE:       DEP        DEFVALUE:    0 
         	UNITS:       NA           SPARSE:      NO
         DESCR:       DEP(RANGE): The range is from (maximum value of number of physical interfaces available in the system + 1) 
         			to (the total number of IP interfaces in the system  + 
         			maximum value of number of physical interfaces available in the system). 
         			The maximum number of physical interfaces is obtained from the object issSystemNumberOfPorts in fsiss.mib. 
         			The total number of IP interfaces in the system is obtained from the object fsVrfMaxIpInterfaces in fsvrf.mib.
                            The IP interfaces will start from 65536 to the total number of IP interfaces in the system. 
                            The indices 81920 & 81921 are reserved for vlan 4094 & 4093 respectively."
    ::= { ifUnnumberedEntry 1 }

ff OBJECT IDENTIFIER
    ::= { fscfa 2 }

ffFastForwardingEnable OBJECT-TYPE
    SYNTAX      TruthValue
    ACCESS      read-write
    STATUS      mandatory
    DESCRIPTION 
        "This object permits the enabling and disabling of 
         the Fast Forwarding feature in the router. Setting of 
         this variable to TRUE(1) enables fast-forwarding and 
         setting it to FALSE(2) disables it.
         	ALCATEL NOTE:
            	ACCESS:      NA           USAGE:       NA
         	PERSIST:     YES          INSRVMOD:    YES
         	RANGE:       1,2          DEFVALUE:    NA
         	UNITS:       NA           SPARSE:      NA
         	DESCR:       NA"
    DEFVAL      { false }
    ::= { ff 1 }

ffCacheSize OBJECT-TYPE
    SYNTAX      INTEGER (10..65535)
    ACCESS      read-write
    STATUS      mandatory
    DESCRIPTION 
        "This object permits the resizing of the Host
         Cache. This object can be changed only when
         the Fast Forwarding Mechanism is disabled.
         For changing the Cache Size, The Fast-Forwarding
         Mechanism should be disabled first (this will
         result in loss of all current entries in the 
         cache) and then enabled again after specifying
         the new size.
         	ALCATEL NOTE:
            	ACCESS:      RO           USAGE:       NA
         	PERSIST:     NO           INSRVMOD:    NO
         	RANGE:       NA           DEFVALUE:    1000
         	UNITS:       NA           SPARSE:      NA
         	DESCR:       NA"
    ::= { ff 2 }

ffIpChecksumValidationEnable OBJECT-TYPE
    SYNTAX      TruthValue
    ACCESS      read-write
    STATUS      mandatory
    DESCRIPTION 
        "This object permits the enabling and disabling of
         the validation of the IP Checksum for incoming 
         IP packets. Setting of this variable to TRUE(1) enables 
         the checksum validation and setting it to FALSE(2) 
         disables it.
         	ALCATEL NOTE:
            	ACCESS:      NA           USAGE:       NA
         	PERSIST:     YES          INSRVMOD:    YES
         	RANGE:       1,2          DEFVALUE:    NA
         	UNITS:       NA           SPARSE:      NA
         	DESCR:       NA"
    DEFVAL      { true }
    ::= { ff 3 }

ffCachePurgeCount OBJECT-TYPE
    SYNTAX      Counter
    ACCESS      read-only
    STATUS      mandatory
    DESCRIPTION 
        "A counter which indicates the number of times the
         entries in the Host Cache Table were purged due 
         to cache overflow.
         	ALCATEL NOTE:
            	ACCESS:      NA           USAGE:       NA
         	PERSIST:     NO           INSRVMOD:    NA
         	RANGE:       NA           DEFVALUE:    0
         	UNITS:       NA           SPARSE:      NO
         	DESCR:       NA"
    ::= { ff 4 }

ffCacheLastPurgeTime OBJECT-TYPE
    SYNTAX      TimeStamp
    ACCESS      read-only
    STATUS      mandatory
    DESCRIPTION 
        "Indicates the SysUpTime when the last purging of
         entries in the Host Cache Table took place.
         	ALCATEL NOTE:
            	ACCESS:      NA           USAGE:       NA
         	PERSIST:     NO           INSRVMOD:    NA
         	RANGE:       NA           DEFVALUE:    0
         	UNITS:       TimeTicks    SPARSE:      NA
         	DESCR:       NA"
    ::= { ff 5 }

ffStaticEntryInvalidTrapEnable OBJECT-TYPE
    SYNTAX      TruthValue
    ACCESS      read-write
    STATUS      mandatory
    DESCRIPTION 
        "Permits enabling and disabling of the generation of 
         ffStaticEntryInvalid SNMP Enterprise Trap when a static
         entry becomes invalid. When its value is TRUE(1), the 
         trap is generated when a static entry become invalid.
         	ALCATEL NOTE:
            	ACCESS:      NA           USAGE:       NA
         	PERSIST:     NO           INSRVMOD:    YES
         	RANGE:       1,2          DEFVALUE:    NA
         	UNITS:       NA           SPARSE:      NA
         	DESCR:       NA"
    DEFVAL      { true }
    ::= { ff 6 }

ffCurrentStaticEntryInvalidCount OBJECT-TYPE
    SYNTAX      Counter
    ACCESS      read-only
    STATUS      mandatory
    DESCRIPTION 
        "A counter which indicates the number of static
         entries in the Host Cache Table that are 
         currently invalid.
         	ALCATEL NOTE:
            	ACCESS:      NA           USAGE:       NA
         	PERSIST:     NO           INSRVMOD:    NA
         	RANGE:       NA           DEFVALUE:    0
         	UNITS:       NA           SPARSE:      NA
         	DESCR:       NA"
    ::= { ff 7 }

ffTotalEntryCount OBJECT-TYPE
    SYNTAX      Counter
    ACCESS      read-only
    STATUS      mandatory
    DESCRIPTION 
        "A counter which indicates the total number of
         entries in the Host Cache Table.
         	ALCATEL NOTE:
            	ACCESS:      NA           USAGE:       NA
         	PERSIST:     NO           INSRVMOD:    NA
         	RANGE:       NA           DEFVALUE:    0
         	UNITS:       NA           SPARSE:      NA
         	DESCR:       NA"
    ::= { ff 8 }

ffStaticEntryCount OBJECT-TYPE
    SYNTAX      Counter
    ACCESS      read-only
    STATUS      mandatory
    DESCRIPTION 
        "A counter which indicates the number of static
         entries in the Host Cache Table.
         	ALCATEL NOTE:
            	ACCESS:      NA           USAGE:       NA
         	PERSIST:     NO           INSRVMOD:    NA
         	RANGE:       NA           DEFVALUE:    0
         	UNITS:       NA           SPARSE:      NA
         	DESCR:       NA"
    ::= { ff 9 }

ffTotalPktsFastForwarded OBJECT-TYPE
    SYNTAX      Counter
    ACCESS      read-only
    STATUS      mandatory
    DESCRIPTION 
        "A counter which indicates the number of packets
         that were successfully fast-forwarded by the
         host cache mechanism.
         	ALCATEL NOTE:
            	ACCESS:      NA           USAGE:       NA
         	PERSIST:     NO           INSRVMOD:    NA
         	RANGE:       NA           DEFVALUE:    0
         	UNITS:       packets      SPARSE:      NA
         	DESCR:       NA"
    ::= { ff 10 }

ffHostCacheTable OBJECT-TYPE
    SYNTAX      SEQUENCE OF FfHostCacheEntry
    ACCESS      not-accessible
    STATUS      mandatory
    DESCRIPTION 
        "This table has entries corresponding to the current 
         entries in the Host Cache. The entries in this table
         can be added, deleted or modified.
         	ALCATEL NOTE:
          	TABLESIZE: 1000
         	DESCR:	NA"
    ::= { ff 11 }

ffHostCacheEntry OBJECT-TYPE
    SYNTAX      FfHostCacheEntry
    ACCESS      not-accessible
    STATUS      mandatory
    DESCRIPTION 
        "An Entry consisting of all the information 
         about an entry in the Host Cache.
         Row creation : Entries shall be created in one step by a set-request with all necessary 
         		parameter values and  ffHostCacheRowStatus set to createAndGo(4).
         Row deletion : Entries shall be deleted by setting the ffHostCacheRowStatus
         		of the specific entry to destroy(6)
         Index usage : the index is the dest address.
         Note that entries will be presented to the SNMP manager in full
         lexicographical order :  sorted on dest address."
    INDEX       { ffHostCacheDestAddr }
    ::= { ffHostCacheTable 1 }

FfHostCacheEntry ::= SEQUENCE {
    ffHostCacheDestAddr             IpAddress,
    ffHostCacheNextHopAddr          IpAddress,
    ffHostCacheIfIndex              InterfaceIndex,
    ffHostCacheNextHopMediaAddr     OCTET STRING,
    ffHostCacheHits                 Counter,
    ffHostCacheLastHitTime          TimeStamp,
    ffHostCacheEntryType            INTEGER,
    ffHostCacheRowStatus            RowStatus
}

ffHostCacheDestAddr OBJECT-TYPE
    SYNTAX      IpAddress
    ACCESS      not-accessible
    STATUS      mandatory
    DESCRIPTION 
        "The IP address of the destination host. 
         ALCATEL NOTE:
         ACCESS:      NA           USAGE:       NA
         PERSIST:     NO           INSRVMOD:    NA
         RANGE:       NA           DEFVALUE:    NA
         UNITS:       NA           SPARSE:      NO
         DESCR:       NA"
    ::= { ffHostCacheEntry 1 }

ffHostCacheNextHopAddr OBJECT-TYPE
    SYNTAX      IpAddress
    ACCESS      read-write
    STATUS      mandatory
    DESCRIPTION 
        "The IP address of the next-hop to which a packet 
         for this host are forwarded. This could be same as 
         ffHostCacheDestAddr if the next-hop is the end-host 
         as well. 
            
         When creating a static entry, this object 
         should be set with the IP address of the next-hop 
         (router) for a host which is not directly connected 
         to our system and with the IP address of the host 
         itself for a host which is directly connected to us.
            
         A set on this object for an entry whose 
         ffHostCacheEntryType is dynamic is not permitted.
         	ALCATEL NOTE:
            	ACCESS:      NA           USAGE:       OPT
         	PERSIST:     NO           INSRVMOD:    YES
         	RANGE:       NA           DEFVALUE:    NA
         	UNITS:       NA           SPARSE:      NO
         	DESCR:       NA"
    ::= { ffHostCacheEntry 2 }

ffHostCacheIfIndex OBJECT-TYPE
    SYNTAX      InterfaceIndex
    ACCESS      read-write
    STATUS      mandatory
    DESCRIPTION 
        "Identifies the MIB-2 ifIndex of the outgoing
         interface over which packets to this host are sent.
         When creating a static entry, this object should be
         set with the ifIndex of our network interface 
         for reaching the specified next-hop. 
            
         It is mandatory to specify the next-hop IP address
         using the ffHostCacheNextHopAddr before setting this
         value. The specified ifIndex should be that of an
         interface which is registered with IP.
            
         A set on this object for an entry
         whose ffHostCacheEntryType is dynamic is not 
         permitted.
         	ALCATEL NOTE:
            	ACCESS:      NA           USAGE:       OPT
         	PERSIST:     NO           INSRVMOD:    YES
         	RANGE:       DEP          DEFVALUE:    NA
         	UNITS:       NA           SPARSE:      NO
         	DESCR:	 DEP(RANGE):The range is from 1 to the (max number of physical interfaces  +  
         		 total number of IP interfaces in the system).
         		 The max number of physical interfaces is obtained from the object issSystemNumberOfPorts in fsiss.mib.
         		 The total number of IP interfaces in the system  is obtained from the object fsVrfMaxIpInterfaces in fsvrf.mib."
    ::= { ffHostCacheEntry 3 }

ffHostCacheNextHopMediaAddr OBJECT-TYPE
    SYNTAX      OCTET STRING (SIZE(0..6))
    ACCESS      read-write
    STATUS      mandatory
    DESCRIPTION 
        "Provides the media address of the next-hop
         to which the packet for this host is to be sent to.
         
         It is mandatory to specify the next-hop IP address
         and the outgoing ifIndex using the 
         ffHostCacheNextHopAddr and ffHostCacheIfIndex
         respectively before setting this value.
         
         This object must be specified for hosts, which are
         reached through the interfaces of ethernetCsmacd(6) 
         and iso88025TokenRing(9) type. The value for such 
         interfaces would be the MAC address as per the
         representation used for the particular media.
            
         For interfaces of type ppp(23) and 
         pppMultilinkBundle(108), this object must have the
         default value 0. 
               
         For virtual circuit interfaces (type miox25(38) and 
         frameRelayMPI(92)), this object must have the MIB-2
         ifIndex assigned to the respective virtual circuit.
                  
         For virtual interfaces (type ipOverAtm(114) and
         frameRelay(32)), this object MAY be used to (optionally)
         specify the MIB-2 ifIndex assigned to the outgoing
         virtual circuit. If not specified the value would be
         obtained automatically from the respective modules.
         
         A set on this object for an entry whose 
         ffHostCacheEntryType is dynamic is not permitted.
         	ALCATEL NOTE:
            	ACCESS:      NA           USAGE:       OPT
         	PERSIST:     NO           INSRVMOD:    YES
         	RANGE:       NA           DEFVALUE:    NA
         	UNITS:       NA           SPARSE:      NO
         	DESCR:       NA"
    ::= { ffHostCacheEntry 4 }

ffHostCacheHits OBJECT-TYPE
    SYNTAX      Counter
    ACCESS      read-only
    STATUS      mandatory
    DESCRIPTION 
        "Indicates the total number of packets fast-
         forwarded to this host.
         	ALCATEL NOTE:
            	ACCESS:      NA           USAGE:       NA
         	PERSIST:     NO           INSRVMOD:    NA
         	RANGE:       NA           DEFVALUE:    0
         	UNITS:       packets      SPARSE:      NO
         	DESCR:       NA"
    ::= { ffHostCacheEntry 5 }

ffHostCacheLastHitTime OBJECT-TYPE
    SYNTAX      TimeStamp
    ACCESS      read-only
    STATUS      mandatory
    DESCRIPTION 
        "Indicates the SysUpTime when the last packet
         was fast-forwarded to this host.
         	ALCATEL NOTE:
            	ACCESS:      NA           USAGE:       NA
         	PERSIST:     NO           INSRVMOD:    NA
         	RANGE:       NA           DEFVALUE:    0
         	UNITS:       TimeTicks    SPARSE:      NO
         	DESCR:       NA"
    ::= { ffHostCacheEntry 6 }

ffHostCacheEntryType OBJECT-TYPE
    SYNTAX      INTEGER { static(1), dynamic(2) }
    ACCESS      read-write
    STATUS      mandatory
    DESCRIPTION 
        "An object, which indicates the type of this Host Cache 
         entry. 
            
         A static entry is an entry created by the Network 
         Manager and is not purged by the system. Such entries
         would be invalidated due to route or other changes
         but will continue to remain in the Host Cache.
            
         Dynamic entries are those entries which have been learnt by 
         the system and which can be purged in the event of 
         a cache overflow or invalidation due to route or other
         changes. 
            
         All entries created through SNMP must set this object to 
         static otherwise.
         	ALCATEL NOTE:
            	ACCESS:      NA           USAGE:       OPT
         	PERSIST:     NO           INSRVMOD:    YES
         	RANGE:       NA           DEFVALUE:    NA
         	UNITS:       NA           SPARSE:      NO
         	DESCR:       NA"
    DEFVAL      { static }
    ::= { ffHostCacheEntry 7 }

ffHostCacheRowStatus OBJECT-TYPE
    SYNTAX      RowStatus
    ACCESS      read-write
    STATUS      mandatory
    DESCRIPTION 
        "A RowStatus object for addition/deletion of Host
         Cache entries. It also indicates the status of the
         entry. 
            
         Set action is not allowed for notInService(2). An entry,
         which has become invalid due to a route failure or 
         address resolution failure, would have the status 
         'notInService'. 
            
         An entry for a host for which the link layer 
         information can be cached but the information is 
         not currently available would have the status 'notReady'.
            
         All active entries with all possible information 
         complete would have the value 'active'.
         	ALCATEL NOTE:
            	ACCESS:      NA           USAGE:       MAND 
         	PERSIST:     NO           INSRVMOD:    YES
         	RANGE:       1,2,4,5,6    DEFVALUE:    NA
         	UNITS:       NA           SPARSE:      NO
         	DESCR:       NA"
    ::= { ffHostCacheEntry 8 }

fm OBJECT IDENTIFIER
    ::= { fscfa 3 }

fmMemoryResourceTrapEnable OBJECT-TYPE
    SYNTAX      TruthValue
    ACCESS      read-write
    STATUS      mandatory
    DESCRIPTION 
        "Permits the enabling and disabling of 
         fmLowMemoryResource Trap when a memory 
         allocation failure is encountered in the 
         module.
         	ALCATEL NOTE:
            	ACCESS:      NA           USAGE:       NA
         	PERSIST:     NO           INSRVMOD:    YES
         	RANGE:       1,2          DEFVALUE:    NA
         	UNITS:       NA           SPARSE:      NO
         	DESCR:       NA"
    DEFVAL      { true }
    ::= { fm 1 }

fmTimersResourceTrapEnable OBJECT-TYPE
    SYNTAX      TruthValue
    ACCESS      read-write
    STATUS      mandatory
    DESCRIPTION 
        "Permits the enabling and disabling of 
         fmLowTimerResource Trap when a request 
         for a timer fails in the module.
         	ALCATEL NOTE:
            	ACCESS:      NA           USAGE:       NA
         	PERSIST:     NO           INSRVMOD:    YES
         	RANGE:       1,2          DEFVALUE:    NA
         	UNITS:       NA           SPARSE:      NO
         	DESCR:       NA"
    DEFVAL      { true }
    ::= { fm 2 }

fmTracingEnable OBJECT-TYPE
    SYNTAX      INTEGER
    ACCESS      read-write
    STATUS      mandatory
    DESCRIPTION 
        "Permits the enabling and disabling of 
         the generation of the log/trace messages
         throughout the module. This object acts
         as a Tracing Level Flag and specifies
         the level of trace or log to be enabled in 
         the module.
         	ALCATEL NOTE:
            	ACCESS:      NA           USAGE:       NA
         	PERSIST:     NO           INSRVMOD:    YES 
         	RANGE:       NA           DEFVALUE:    NA
         	UNITS:       NA           SPARSE:      NO
         	DESCR:       NA"
    DEFVAL      { 0 }
    ::= { fm 3 }

fmMemAllocFailCount OBJECT-TYPE
    SYNTAX      Counter
    ACCESS      read-only
    STATUS      mandatory
    DESCRIPTION 
        "Maintains a count of the number of times
         when a failure was encountered while memory
         allocation operation in the module.
         	ALCATEL NOTE:
            	ACCESS:      NA           USAGE:       NA
         	PERSIST:     NO           INSRVMOD:    NA
         	RANGE:       NA           DEFVALUE:    0
         	UNITS:       NA           SPARSE:      NO
         	DESCR:       NA"
    ::= { fm 4 }

fmTimerReqFailCount OBJECT-TYPE
    SYNTAX      Counter
    ACCESS      read-only
    STATUS      mandatory
    DESCRIPTION 
        "Maintains a count of the number of times
         when a failure was encountered while requesting
         a timer in the module.
         	ALCATEL NOTE:
            	ACCESS:      NA           USAGE:       NA
         	PERSIST:     NO           INSRVMOD:    NA
         	RANGE:       NA           DEFVALUE:    0
         	UNITS:       NA           SPARSE:      NO
         	DESCR:       NA"
    ::= { fm 5 }

traps OBJECT IDENTIFIER
    ::= { fscfa 4 }

trapPrefix OBJECT IDENTIFIER
    ::= { traps 0 }

fmLowTimerResource TRAP-TYPE
    ENTERPRISE  traps
    VARIABLES   { fmTimerReqFailCount }
--     STATUS      mandatory
    DESCRIPTION 
        "This trap is generated whenever there is a failure in
         a timer related operation in the module.
            
         This trap is generated only when the value of the 
         fmTimersResouceTrapEnable object is TRUE(1)."
    ::= 1

fmLowBufferResource TRAP-TYPE
    ENTERPRISE  traps
    VARIABLES   { fmMemAllocFailCount }
--     STATUS      mandatory
    DESCRIPTION 
        "This trap is generated when a memory allocation 
         failure occurs in the module. This 
         trap is generated only when the value of the 
         fmMemoryResourceTrapEnable object is TRUE(1)."
    ::= 2

ffStaticEntryInvalid TRAP-TYPE
    ENTERPRISE  traps
    VARIABLES   { ffHostCacheIfIndex, ffHostCacheEntryType }
--     STATUS      mandatory
    DESCRIPTION 
        "This trap is generated when a static entry
         in the ffHostCacheTable becomes invalid
         due to a route deletion or address resolution failure. This 
         trap is generated only when the value of the 
         ffStaticEntryInvalidTrapEnable object is TRUE (1)."
    ::= 3

END -- end of module CFA-MIB.
