--
-- This SMIv1 module has been generated by smidump 0.4.8. Do not edit.
--

SNTP-MIB DEFINITIONS ::= BEGIN

IMPORTS
    OBJECT-TYPE
        FROM RFC-1212
    Gauge, IpAddress, enterprises
        FROM RFC1155-SMI;

asam OBJECT IDENTIFIER
    ::= { enterprises alcatel(637) asd(61) 1 }

-- asam MODULE-IDENTITY
--     LAST-UPDATED "200401031200Z"
--     ORGANIZATION 
--         "FUTURE SOFTWARE PVT. LIMITED"
--     CONTACT-INFO 
--         " FUTURE SOFTWARE PVT. LIMITED
--          481 Mount Road
--          Madras - 600 035
--          Phone : +91-44-433 055 0 
--          support@futsoft.com"
--     DESCRIPTION 
--         "The LANX SNTP client MIB "
--     REVISION    "200401031200Z"
--     DESCRIPTION 
--         "The LANX SNTP client MIB "
--     ::= { enterprises alcatel(637) asd(61) 1 }


SNTPOperatingMode ::=
    INTEGER { unicast(1), anycast(2), multicast(3) }

-- SNTPOperatingMode ::= TEXTUAL-CONVENTION
--     STATUS      mandatory
--     DESCRIPTION 
--         "Enumerated integer datatype"
--     SYNTAX      INTEGER
--                   { unicast(1), anycast(2), multicast(3) }

SNTPEnableDisable ::=
    INTEGER { enable(1), disable(2) }

-- SNTPEnableDisable ::= TEXTUAL-CONVENTION
--     STATUS      mandatory
--     DESCRIPTION 
--         "Enumerated integer datatype"
--     SYNTAX      INTEGER
--                   { enable(1), disable(2) }

asamSNTPMIB OBJECT IDENTIFIER
    ::= { asam 13 }

asamSNTPServerIpAddress OBJECT-TYPE
    SYNTAX      IpAddress
    ACCESS      read-write
    STATUS      mandatory
    DESCRIPTION 
        "IpAddress for the SNTP Server 
         of the SNMP agent.
         ALCATEL NOTE:
         ACCESS:	 NA		USAGE:	  NA
         PERSIST: YES		INSRVMOD: YES
         RANGE:	 NA		DEFVALUE: 0.0.0.0      
         UNITS:	 NA		SPARSE:	  NA
         DESCR:	 NA"
    ::= { asamSNTPMIB 1 }

asamSNTPServerPort OBJECT-TYPE
    SYNTAX      INTEGER (0..65535)
    ACCESS      read-write
    STATUS      mandatory
    DESCRIPTION 
        "Port number for the SNTP Server 
         of the SNMP agent.
         ALCATEL NOTE:
         ACCESS:	 NA		USAGE:	  NA
         PERSIST: YES		INSRVMOD: YES
         RANGE:	 NA		DEFVALUE: NA
         UNITS:	 NA		SPARSE:	  NA
         DESCR:	 NA"
    DEFVAL      { 123 }
    ::= { asamSNTPMIB 2 }

asamSNTPPollingRate OBJECT-TYPE
    SYNTAX      INTEGER (60..4294967)
    ACCESS      read-write
    STATUS      mandatory
    DESCRIPTION 
        "The polling for the SNMP agent. 
         Unit of the object is Seconds.
         ALCATEL NOTE:
         ACCESS:	 NA		USAGE:	  NA
         PERSIST: YES		INSRVMOD: YES
         RANGE:	 1..4294967	DEFVALUE: NA
         UNITS:	 Seconds	SPARSE:	  NA
         DESCR:	 NA"
    DEFVAL      { 3600 }
    ::= { asamSNTPMIB 3 }

asamSNTPEnableDisable OBJECT-TYPE
    SYNTAX      SNTPEnableDisable
    ACCESS      read-write
    STATUS      mandatory
    DESCRIPTION 
        "This object manages the functionality
         of the SNTP application. If it is set to 
         enable, SNTP application works. If it is
         set to Disable, Network Time is not polled.
         ALCATEL NOTE:
         ACCESS:	 NA		USAGE:	  NA
         PERSIST: YES		INSRVMOD: YES
         RANGE:	 1,2		DEFVALUE: NA
         UNITS:	 NA		SPARSE:	  NA
         DESCR:	 NA"
    DEFVAL      { disable }
    ::= { asamSNTPMIB 4 }

asamSNTPTimeSeconds OBJECT-TYPE
    SYNTAX      Gauge (0..4294967295)
    ACCESS      read-write
    STATUS      mandatory
    DESCRIPTION 
        "This object gives the network time in 
         seconds. This object is read-write. 
         Network time can be managed by the 
         Operator by means of this object.
         ALCATEL NOTE:
         ACCESS:	 NA		USAGE:	  NA
         PERSIST: YES		INSRVMOD: YES
         RANGE:	 NA		DEFVALUE: NA     
         UNITS:	 seconds	SPARSE:	  NA
         DESCR:	 NA"
    ::= { asamSNTPMIB 5 }

asamSNTPTimeFractionOfSeconds OBJECT-TYPE
    SYNTAX      INTEGER (1..2147483647)
    ACCESS      read-write
    STATUS      mandatory
    DESCRIPTION 
        "This object gives the network time in 
         mili seconds. The number of miliseconds
         elapsed in a second is given by this object.
         This object is read-write. Network time 
         can be managed by the Operator by means 
         of this object.
         ALCATEL NOTE:
         ACCESS:	 NA		USAGE:	  NA
         PERSIST: YES		INSRVMOD: YES
         RANGE:	 NA		DEFVALUE: NA      
         UNITS:	 Miliseconds	SPARSE:	  NA
         DESCR:	 NA"
    ::= { asamSNTPMIB 6 }

asamSNTPOperatingMode OBJECT-TYPE
    SYNTAX      SNTPOperatingMode
    ACCESS      read-only
    STATUS      mandatory
    DESCRIPTION 
        "This object gives the operating mode
         for the SNTP application at the SNMP
         agent.
         ALCATEL NOTE:
         ACCESS:	 NA		USAGE:	  NA
         PERSIST: NO		INSRVMOD: NA
         RANGE:	 1		DEFVALUE: NA
         UNITS:	 NA		SPARSE:	  NA
         DESCR:	 NA"
    DEFVAL      { unicast }
    ::= { asamSNTPMIB 7 }

END -- end of module SNTP-MIB.
