--       TIMETRA SAS MPOINT (MultiPoint Management) 
--       Management Information Base

TIMETRA-SAS-MPOINT-MGMT-MIB DEFINITIONS ::= BEGIN

IMPORTS
    MODULE-IDENTITY, OBJECT-TYPE, Unsigned32, Integer32,
    Counter64
        FROM SNMPv2-SMI

    MODULE-COMPLIANCE, OBJECT-GROUP
        FROM SNMPv2-CONF

    RowStatus, TimeStamp,
    TEXTUAL-CONVENTION
        FROM SNMPv2-TC

    TNamedItem, TItemDescription FROM TIMETRA-TC-MIB

    timetraSASObjs, timetraSASNotifyPrefix, 
    timetraSASConfs, timetraSASModules               
        FROM TIMETRA-SAS-GLOBAL-MIB

    TAdaptationRule, TBurstSize FROM TIMETRA-SAS-QOS-MIB

    ;

timetraSASMpointMgmtMIBModule   MODULE-IDENTITY
        LAST-UPDATED    "1005100000Z"
        ORGANIZATION    "Nokia"
        CONTACT-INFO    
            "Nokia 7xx0 Support
             Web: http://www.nokia.com"
        DESCRIPTION
        "This is the SNMP MIB module for ingress multipoint management
         policy on Nokia 7xx0 equipment.

         Copyright 2008-2011 Nokia. All rights reserved.
         Reproduction of this document is authorized on the condition that
         the foregoing copyright notice is included.

         This SNMP MIB module (Specification) embodies Nokia's
         proprietary intellectual property.  Nokia retains 
         all title and ownership in the Specification, including any 
         revisions.

         Nokia grants all interested parties a non-exclusive 
         license to use and distribute an unmodified copy of this 
         Specification in connection with management of Nokia
         products, and without fee, provided this copyright notice and 
         license appear on all copies.

         This Specification is supplied 'as is', and Nokia 
         makes no warranty, either express or implied, as to the use, 
         operation, condition, or performance of the Specification."

--
--  Revision History
--

        REVISION        "1005100000Z"
        DESCRIPTION     "Rev 1.0                10 May 2010 00:00
                         1.0 release of the TIMETRA-SAS-MPOINT-MGMT-MIB."


        ::= { timetraSASModules 54 }

--%%%%%%%%%%%%%%%%%%%%%%%%%%%%%%%%%%%%%%%%%%%%%%%%%%%%%%%%%%%%%%%%%%%%%%
--
--  Nokia 7xx0 SR series multipoint management policy objects
--

tSASMpObjects         OBJECT IDENTIFIER ::= { timetraSASObjs 54 }
    tSASMpGlobalObjs     OBJECT IDENTIFIER ::= { tSASMpObjects 1 }
    tSASMpNotifyObjs     OBJECT IDENTIFIER ::= { tSASMpObjects 2 }

tSASMpConformance  OBJECT IDENTIFIER ::= { timetraSASConfs 54 }
   tSASMpCompliances   OBJECT IDENTIFIER ::= { tSASMpConformance 1 }
   tSASMpGroups        OBJECT IDENTIFIER ::= { tSASMpConformance 2 }

tSASMpNotifyPrefix OBJECT IDENTIFIER ::= { timetraSASNotifyPrefix 54 }
    tSASMpNotifications OBJECT IDENTIFIER ::= { tSASMpNotifyPrefix 0 }
    
 --
 -- Textual Conventions
 --

TSASMpQueueIdTc ::= TEXTUAL-CONVENTION 
     STATUS      current 
     DESCRIPTION 
         "The value TSASMpQueueIdTc data type is an enumerated integer 
          that describes  the values used to identify the id of ingress queue of 
          fabric multipoint path." 
     SYNTAX      INTEGER { 
                     none (0),
                     queue1 (1),
                     queue2 (2),
                     queue3 (3),
                     queue4 (4),
                     queue5 (5),
                     queue6 (6),
                     queue7 (7),
                     queue8 (8)
                 } 

-- ------------------------------------------------
-- mib objects
-- ------------------------------------------------

-- ------------------------------------------------
-- multipoint bandwidth policy table
-- ------------------------------------------------

tSASMpBwPlcyTable OBJECT-TYPE
    SYNTAX      SEQUENCE OF TSASMpBwPlcyEntry
    MAX-ACCESS  not-accessible
    STATUS      current
    DESCRIPTION
        "The tSASMpBwPlcyTable has an entry for each multipoint bandwidth
         policy configured on this system."
    ::= { tSASMpGlobalObjs 1 }

tSASMpBwPlcyEntry    OBJECT-TYPE
    SYNTAX      TSASMpBwPlcyEntry
    MAX-ACCESS  not-accessible
    STATUS      current
    DESCRIPTION
        "Each row entry represents a particular multipoint bandwidth policy.
         Entries are created/deleted by the user."
    INDEX { tSASMpBwPlcyName }
    ::= { tSASMpBwPlcyTable 1}

TSASMpBwPlcyEntry ::= SEQUENCE
   {
       tSASMpBwPlcyName               TNamedItem,
       tSASMpBwPlcyRowStatus          RowStatus,
       tSASMpBwPlcyLastChanged        TimeStamp,
       tSASMpBwPlcyDescription        TItemDescription,
       tSASMpBwPlcyIngrAggrRate       Integer32
   }

tSASMpBwPlcyName              OBJECT-TYPE
    SYNTAX      TNamedItem
    MAX-ACCESS  not-accessible
    STATUS      current
    DESCRIPTION
        "The value of tSASMpBwPlcyName indicates the name of the multicast 
         bandwidth policy."
    ::= { tSASMpBwPlcyEntry 1 }

tSASMpBwPlcyRowStatus       OBJECT-TYPE
    SYNTAX      RowStatus
    MAX-ACCESS  read-create
    STATUS      current
    DESCRIPTION
        "The value of tSASMpBwPlcyRowStatus is used for creation/deletion of
         multicast bandwidth policies."
    ::= { tSASMpBwPlcyEntry 2 }

tSASMpBwPlcyLastChanged  OBJECT-TYPE
    SYNTAX      TimeStamp
    MAX-ACCESS  read-only
    STATUS      current
    DESCRIPTION
        "The value of tSASMpBwPlcyLastChanged indicates the timestamp of 
         last change to this row in tSASMpBwPlcyTable."
    ::= { tSASMpBwPlcyEntry 3 }

tSASMpBwPlcyDescription    OBJECT-TYPE
    SYNTAX      TItemDescription
    MAX-ACCESS  read-create
    STATUS      current
    DESCRIPTION
        "The value of tSASMpBwPlcyDescription specifies the textual 
         description of this multicast bandwidth policy."
    DEFVAL      { "" } 
    ::= { tSASMpBwPlcyEntry 4 }    

tSASMpBwPlcyIngrAggrRate    OBJECT-TYPE
    SYNTAX      Integer32 (-1|1..10000)
    UNITS       "mega-bits-per-second"
    MAX-ACCESS  read-create
    STATUS      current
    DESCRIPTION
        "The value of tSASMpBwPlcyIngrAggrRate specifies the aggregate rate 
         of multipoint traffic that will be admitted in the ingress that 
         will be replicated."
    DEFVAL { -1 } 
    ::= { tSASMpBwPlcyEntry 5 }    

-- ------------------------------------------------
-- multipoint bandwidth policy queue params table
-- ------------------------------------------------

tSASMpBwPlcyQueueTable OBJECT-TYPE
    SYNTAX      SEQUENCE OF TSASMpBwPlcyQueueEntry
    MAX-ACCESS  not-accessible
    STATUS      current
    DESCRIPTION
        "Bandwidth Queue Params Table"
    ::= { tSASMpGlobalObjs 2 }

tSASMpBwPlcyQueueEntry    OBJECT-TYPE
    SYNTAX      TSASMpBwPlcyQueueEntry
    MAX-ACCESS  not-accessible
    STATUS      current
    DESCRIPTION
        "Bandwidth Queue Params for SAS platform."
    INDEX { tSASMpBwPlcyName, tSASMpBwPlcyQueueId }
    ::= { tSASMpBwPlcyQueueTable 1}

TSASMpBwPlcyQueueEntry ::= SEQUENCE
   {
       tSASMpBwPlcyQueueId               TSASMpQueueIdTc,
       tSASMpBwPlcyCbs                   TBurstSize,
       tSASMpBwPlcyMbs                   INTEGER,
       tSASMpBwPlcyCir                   Unsigned32,
       tSASMpBwPlcyPir                   Unsigned32,
       tSASMpBwPlcyCirAdaptation         TAdaptationRule,
       tSASMpBwPlcyPirAdaptation         TAdaptationRule,
       tSASMpBwPlcyQueMgmtPlcy           TNamedItem,
       tSASMpBwPlcyQueStatsFwdPkts       Counter64,
       tSASMpBwPlcyQueStatsFwdOcts       Counter64,
       tSASMpBwPlcyQueStatsDroPkts       Counter64,
       tSASMpBwPlcyQueStatsDroOcts       Counter64       
   }

tSASMpBwPlcyQueueId  OBJECT-TYPE
    SYNTAX      TSASMpQueueIdTc
    MAX-ACCESS  not-accessible
    STATUS      current
    DESCRIPTION
        "The value of tSASMpBwPlcyQueueId specifies the queue number."
    ::= { tSASMpBwPlcyQueueEntry 1 }    

tSASMpBwPlcyCbs      OBJECT-TYPE
    SYNTAX      TBurstSize
    MAX-ACCESS  read-create
    STATUS      current
    DESCRIPTION
        "The amount of reserved buffer space (in kilo bytes) for the queue."
    DEFVAL { -1 } 
    ::= { tSASMpBwPlcyQueueEntry 2 }     

tSASMpBwPlcyMbs      OBJECT-TYPE
    SYNTAX      INTEGER (-1 | 1..131072)
    MAX-ACCESS  read-create
    STATUS      current
    DESCRIPTION
        "The maximum amount of buffer space (in kilo bytes) allowed for the
        queue."
    DEFVAL { -1 } 
    ::= { tSASMpBwPlcyQueueEntry 3 }     

tSASMpBwPlcyCir      OBJECT-TYPE
    SYNTAX      Unsigned32 (0..100)
    UNITS       "percent"
    MAX-ACCESS  read-create
    STATUS      current
    DESCRIPTION
        "The value of tSASMpBwPlcyCir overrides the default CIR for each
         individual queue."
    DEFVAL { 100 } 
    ::= { tSASMpBwPlcyQueueEntry 4 }     

tSASMpBwPlcyPir      OBJECT-TYPE
    SYNTAX      Unsigned32 (1..100)
    UNITS       "percent"
    MAX-ACCESS  read-create
    STATUS      current
    DESCRIPTION
        "The value of tSASMpBwPlcyPir overrides the default PIR for each
         individual queue."
    DEFVAL { 100 } 
    ::= { tSASMpBwPlcyQueueEntry 5 }     

tSASMpBwPlcyCirAdaptation      OBJECT-TYPE
    SYNTAX      TAdaptationRule
    MAX-ACCESS  read-create
    STATUS      current
    DESCRIPTION
        "The adaptation rule to be used while computing the operational CIR
         value. The adaptation rule specifies the rules to compute the
         operational values while maintaining minimum offset."
    DEFVAL { closest } 
    ::= { tSASMpBwPlcyQueueEntry 6 }     

tSASMpBwPlcyPirAdaptation      OBJECT-TYPE
    SYNTAX      TAdaptationRule
    MAX-ACCESS  read-create
    STATUS      current
    DESCRIPTION
        "The adaptation rule to be used while computing the operational PIR
         value. The adaptation rule specifies the rules to compute the
         operational values while maintaining minimum offset."
    DEFVAL { closest } 
    ::= { tSASMpBwPlcyQueueEntry 7 }     

tSASMpBwPlcyQueMgmtPlcy  OBJECT-TYPE
    SYNTAX       TNamedItem 
    MAX-ACCESS   read-create
    STATUS       current
    DESCRIPTION
        "Queue Management Policy to be attached."
    DEFVAL { "default" }
    ::= { tSASMpBwPlcyQueueEntry 8 }

tSASMpBwPlcyQueStatsFwdPkts  OBJECT-TYPE
    SYNTAX       Counter64 
    MAX-ACCESS   read-only
    STATUS       current
    DESCRIPTION
        "The number of forwarded packets
         on this Queue"
    ::= { tSASMpBwPlcyQueueEntry 9 }

tSASMpBwPlcyQueStatsFwdOcts  OBJECT-TYPE
    SYNTAX       Counter64 
    MAX-ACCESS   read-only
    STATUS       current
    DESCRIPTION
        "The number of forwarded bytes
         on this Queue"
    ::= { tSASMpBwPlcyQueueEntry 10 }
    
tSASMpBwPlcyQueStatsDroPkts  OBJECT-TYPE
    SYNTAX       Counter64 
    MAX-ACCESS   read-only
    STATUS       current
    DESCRIPTION
        "The number of dropped packets
         on this Queue"
    ::= { tSASMpBwPlcyQueueEntry 11 }

tSASMpBwPlcyQueStatsDroOcts  OBJECT-TYPE
    SYNTAX       Counter64 
    MAX-ACCESS   read-only
    STATUS       current
    DESCRIPTION
        "The number of dropped bytes
         on this Queue"
    ::= { tSASMpBwPlcyQueueEntry 12 }
    
-- ----------------------------------------------
-- Compliance Statements
-- ----------------------------------------------

tSASMp7210V1v0Compliance   MODULE-COMPLIANCE
    STATUS      current
    DESCRIPTION
        "The compliance statement for revision 1.0 of TIMETRA-SAS-MPOINT-MGMT-MIB."
    MODULE      --this module
        MANDATORY-GROUPS {
            tSASMpGlobalGroup
        }
    ::= { tSASMpCompliances 1 }

-- ----------------------------------------------
-- Units of Conformance
-- ----------------------------------------------

tSASMpGlobalGroup   OBJECT-GROUP
    OBJECTS {   
                 tSASMpBwPlcyRowStatus,
                 tSASMpBwPlcyLastChanged,
                 tSASMpBwPlcyDescription,
                 tSASMpBwPlcyIngrAggrRate,
                 tSASMpBwPlcyCbs,
                 tSASMpBwPlcyMbs,
                 tSASMpBwPlcyCir,
                 tSASMpBwPlcyPir,
                 tSASMpBwPlcyCirAdaptation,
                 tSASMpBwPlcyPirAdaptation,
                 tSASMpBwPlcyQueMgmtPlcy
            }
    STATUS      current
    DESCRIPTION
        "SAS group obkects definition."
    ::= { tSASMpGroups 1 }

END
