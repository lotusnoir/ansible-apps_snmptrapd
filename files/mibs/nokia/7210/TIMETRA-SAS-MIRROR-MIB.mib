TIMETRA-SAS-MIRROR-MIB DEFINITIONS ::= BEGIN

IMPORTS
    MODULE-IDENTITY, OBJECT-TYPE, NOTIFICATION-TYPE,
    Unsigned32, IpAddress, Integer32
        FROM SNMPv2-SMI

    MODULE-COMPLIANCE, OBJECT-GROUP, NOTIFICATION-GROUP
        FROM SNMPv2-CONF

    TEXTUAL-CONVENTION, RowStatus, TruthValue,
    MacAddress, TimeStamp, DisplayString
        FROM SNMPv2-TC

    timetraSRMIBModules, tmnxSRObjs, tmnxSRNotifyPrefix,
    tmnxSRConfs
        FROM TIMETRA-GLOBAL-MIB

    timetraSASObjs, timetraSASNotifyPrefix, 
    timetraSASConfs, timetraSASModules      FROM TIMETRA-SAS-GLOBAL-MIB        

    TItemDescription, TFCName, ServiceAdminStatus, ServiceOperStatus,
    TmnxPortID, TmnxEncapVal, TmnxServId, TNamedItem, TFCSet, TNamedItemOrEmpty,
    TPolicyID, SdpBindId, TProfileOrNone
        FROM TIMETRA-TC-MIB

    SdpId 
        FROM TIMETRA-SERV-MIB

   tMirrorSourcePortEntry, tMirrorDestinationEntry      FROM TIMETRA-MIRROR-MIB

    TIPFilterID, TMACFilterID, TEntryId, TFilterType, TFilterID, TEntryIdOrZero
        FROM TIMETRA-FILTER-MIB

    InetAddressType, InetAddress
        FROM INET-ADDRESS-MIB

    InterfaceIndexOrZero
        FROM IF-MIB
    ;

    
    timetraSASMirrorMIBModule   MODULE-IDENTITY
        LAST-UPDATED    "1105010000Z"
        ORGANIZATION    "Nokia"
        CONTACT-INFO    
            "Nokia 7x50 Support
             Web: http://www.nokia.com"
        DESCRIPTION
        "This document is the SNMP MIB module to manage and provision 
         traffic mirroring on Nokia 7x50 systems.

         Copyright 2003-2013 Nokia. All rights reserved.
         Reproduction of this document is authorized on the condition that
         the foregoing copyright notice is included.

         This SNMP MIB module (Specification) embodies Nokia's
         proprietary intellectual property.  Nokia retains 
         all title and ownership in the Specification, including any 
         revisions.

         Nokia grants all interested parties a non-exclusive 
         license to use and distribute an unmodified copy of this 
         Specification in connection with management of Nokia
         products, and without fee, provided this copyright notice and 
         license appear on all copies.

         This Specification is supplied 'as is', and Nokia 
         makes no warranty, either express or implied, as to the use, 
         operation, condition, or performance of the Specification."

--
--  Revision History
--
        REVISION        "1105010000Z"
        DESCRIPTION     "Rev 1.0                01 Jan 2009 00:00
                         1.0 release of the TIMETRA-SAS-MIRROR-MIB."

        ::= { timetraSASModules 13 }

tSASMirrorObjects                  OBJECT IDENTIFIER ::= { timetraSASObjs 13 }        

tMirrorSourcePortExtnTable OBJECT-TYPE
    SYNTAX       SEQUENCE OF TMirrorSourcePortExtnEntry
    MAX-ACCESS   not-accessible
    STATUS       current
    DESCRIPTION  
        ""
    ::= { tSASMirrorObjects 1 }

tMirrorSourcePortExtnEntry OBJECT-TYPE
    SYNTAX       TMirrorSourcePortExtnEntry
    MAX-ACCESS   not-accessible
    STATUS       current
    DESCRIPTION 
        ""
    AUGMENTS {tMirrorSourcePortEntry}    
    ::= { tMirrorSourcePortExtnTable 1 }

TMirrorSourcePortExtnEntry ::=
    SEQUENCE {
      tMirrorSourcePortEgressMirroringType         INTEGER
    }    

tMirrorSourcePortEgressMirroringType OBJECT-TYPE
    SYNTAX          INTEGER {          
                        true-egress-mirroring (1),
                        normal-egress-mirroring (2)
                    }
    MAX-ACCESS      read-create
    STATUS          current
    DESCRIPTION     
      "With no-true-egress specified and when egress port mirroring is enabled,
        the mirrored copy of the packets will not be an exact replica of the forwarded
        copy. Some ofthe modifications applied to the forwarded packet in the egress
        processing path will no be available in the mirrored copy"
    DEFVAL { true-egress-mirroring }        
    ::= { tMirrorSourcePortExtnEntry 1 }

tMirrorDestinationExtnTable OBJECT-TYPE
    SYNTAX       SEQUENCE OF TMirrorDestinationExtnEntry
    MAX-ACCESS   not-accessible
    STATUS       current
    DESCRIPTION  
        ""
    ::= { tSASMirrorObjects 2 }

tMirrorDestinationExtnEntry OBJECT-TYPE
    SYNTAX       TMirrorDestinationExtnEntry
    MAX-ACCESS   not-accessible
    STATUS       current
    DESCRIPTION 
        ""
    AUGMENTS {tMirrorDestinationEntry}    
    ::= { tMirrorDestinationExtnTable 1 }

TMirrorDestinationExtnEntry ::=
    SEQUENCE {
      tMirrorDestinationFCProfile                TProfileOrNone,
      tMirrorDestinationMirrorSourceType   INTEGER
    }    

tMirrorDestinationFCProfile OBJECT-TYPE
    SYNTAX          TProfileOrNone
    MAX-ACCESS      read-create
    STATUS          current
    DESCRIPTION     
      "Specifies the profile of the packet associated with the forwarding class 
       tMirrorDestinationFC"
    DEFVAL { out }        
    ::= { tMirrorDestinationExtnEntry 1 }

tMirrorDestinationMirrorSourceType OBJECT-TYPE
    SYNTAX          INTEGER {          
                        local (1),
                        remote (2),
                        both (3)
                    }
    MAX-ACCESS      read-create
    STATUS          current
    DESCRIPTION     
      "User can specify if the mirror services needs to support local mirror sources, 
      remote mirror sources or both"
    DEFVAL { local }        
    ::= { tMirrorDestinationExtnEntry 2 }
    
tmnxSASMirrorGroups      OBJECT IDENTIFIER ::= { timetraSASConfs 8 }

tmnxSASMirrorV1v0Group       OBJECT-GROUP
    OBJECTS {
                    tMirrorSourcePortEgressMirroringType,
                    tMirrorDestinationFCProfile,
                    tMirrorDestinationMirrorSourceType
                    }                                   
    STATUS        current
    DESCRIPTION
        "The group of objects supporting management of transport and
         virtual routers on version 1.0 Nokia 7210 SAS series systems."
    ::= { tmnxSASMirrorGroups 1 }

END
