TIMETRA-SUBSCRIBER-MGMT-MIB DEFINITIONS ::= BEGIN

IMPORTS
       MODULE-IDENTITY,
       OBJECT-TYPE, Unsigned32, Counter32,
       Counter64, NOTIFICATION-TYPE,
       Integer32, Gauge32, IpAddress,
       TimeTicks
                                                FROM SNMPv2-SMI

       OBJECT-GROUP, MODULE-COMPLIANCE,
       NOTIFICATION-GROUP                       FROM SNMPv2-CONF

       RowStatus,
       TEXTUAL-CONVENTION,
       TruthValue, DisplayString, DateAndTime,
       TimeStamp, TimeInterval, MacAddress      FROM SNMPv2-TC

       timetraSRMIBModules, tmnxSRObjs,
       tmnxSRConfs, tmnxSRNotifyPrefix          FROM TIMETRA-GLOBAL-MIB

       TPolicyStatementNameOrEmpty,
       TIngressPolicerId,
       TEgressPolicerId,
       TmnxIngPolicerStatMode,
       TmnxEgrPolicerStatMode,
       TNamedItem, TNamedItemOrEmpty, TXLNamedItem,
       TItemDescription, TPolicyID,
       TIngressQueueId, TEgressQueueId,
       TPortSchedulerPIR, TmnxPortID,
       TmnxServId, TmnxVRtrIDOrZero,
       TmnxAdminState, 
       TmnxOperState, TPIRRate, TCIRRate,
       TmnxSubIdentStringOrEmpty,
       TIngHsmdaPerPacketOffsetOvr,
       TEgrHsmdaPerPacketOffsetOvr,
       TEgressPerPacketOffsetOvr,
       THsmdaPIRKRateOverride,
       THsmdaCIRKRateOverride, TEgrRateModType,
       TIngressHsmdaQueueId, TEgressHsmdaQueueId,
       TIngressHsmdaCounterId, TEgressHsmdaCounterId,
       TSapIngressPolicyID, TSapEgressPolicyID,
       TmnxPppoeSessionId,
       TQueueId, THsmdaCounterIdOrZero, TQueueIdOrAll,
       TmnxAccPlcyQICounters, TmnxAccPlcyQECounters,
       TmnxAccPlcyOICounters,
       THsmdaCounterIdOrZeroOrAll,
       TmnxActionType, TIpProtocol,
       TmnxAccPlcyOECounters,
       TDSCPNameOrEmpty,
       TTcpUdpPort,
       TTcpUdpPortOperator, TIpOption,
       TmnxCustId,
       TPIRRateOverride,
       TCIRRateOverride,
       TBurstSizeBytesOverride, TBurstSizeBytesOvr,
       THSMDABurstSizeBytesOverride,
       TPerPacketOffsetOvr,
       THPolPIRRateOverride,
       THPolCIRRateOverride,
       TmnxBinarySpecification,
       TPlcrBurstSizeBytesOverride,
       TDirectionIngEgr,
       TQosOverrideType,
       TQueueStatModeFormat,
       THsmdaWeightOverride, THsmdaWrrWeightOverride,
       TmnxPppoeSessionInfoOrigin,
       TmnxPppoeUserName,
       TmnxPppoeUserNameOrEmpty,
       TmnxSubProfileStringOrEmpty,
       TmnxSlaProfileStringOrEmpty,
       TmnxAncpStringOrZero,
       TmnxSubMgtIntDestIdOrEmpty,
       TmnxAppProfileStringOrEmpty,
       TmnxSubNasPortSuffixType,
       TmnxSubNasPortPrefixType,
       TmnxSubNasPortTypeType,
       TmnxSubRadiusAttrType, 
       TmnxSubRadiusVendorId,
       TmnxSubRadServAlgorithm,
       TmnxRadiusServerOperState,
       TmnxRadiusPendingReqLimit,
       TmnxManagedRouteStatus,
       TmnxAccessLoopEncapDataLink, 
       TmnxAccessLoopEncaps1,
       TmnxAccessLoopEncaps2,
       TmnxSubAleOffsetMode,
       TmnxSubAleOffset,
       BgpPeeringStatus,
       TmnxMacSpecification,
       TmnxEncapVal,
       TmnxMdaQos, THPolVirtualSchePIRRate,
       THPolVirtualScheCIRRate,
       TmnxSubAcctSessionId,
       TmnxHttpRedirectUrl,
       TPortSchedulerAggRateLimitPIR,
       TmnxDisplayStringURL,
       TmnxSubCallingStationIdType,
       TmnxAuthPassword,
       TmnxIgmpVersion,
       TmnxMldVersion,
       TmnxSubAuthPlcyUserNameOp,
       TmnxLagPerLinkHashClass,
       TmnxLagPerLinkHashWeight,
       TmnxRipListenerStatus,
       TQosQueuePIRRateOverride,
       TQosQueueCIRRateOverride,
       TmnxRadiusFramedRouteMetric,
       TmnxRadiusFramedRoutePreference,
       TmnxRadiusFramedRouteTag,
       TmnxSubShcvAction,
       TmnxSubShcvInterval,
       TmnxSubShcvRetryCount,
       TmnxSubShcvRetryTimeout,
       TmnxSubShcvSrcIpOrigin,
       TmnxSubTerminationType,
       TFCType,
       TAnyQosPolicyIDorZero,
       TmnxEnabledDisabled
                                                FROM TIMETRA-TC-MIB

       vRtrID                                   FROM TIMETRA-VRTR-MIB
        
       CounterBasedGauge64                      FROM HCNUM-TC

       VRtrIgmpHostMcRDstStatType               FROM TIMETRA-IGMP-MIB

       TIPFilterID, TEntryId, TFilterAction,
       TItemMatch                               FROM TIMETRA-FILTER-MIB

       tSchedulerPolicyName,
       tVirtualSchedulerName,
       tSapIngressIndex, tSapEgressIndex,
       tSapIngressQueue, tSapEgressQueueIndex,
       tSapIngressHsmdaQueue,
       tSapEgressHsmdaQueue,
       tSapIngPolicerId, tSapEgrPolicerId,
       tQosPolicerCtrlPolName,
       tQosPolicerLevel                         FROM TIMETRA-QOS-MIB

       svcId, iesIfIndex, ServShcvOperState,
       DhcpLseStateInfoOrigin,
       svcDhcpLeaseCiAddrMaskLen                FROM TIMETRA-SERV-MIB
       sapPortId, sapEncapValue,
       sapHostLockoutPolicy
                                                FROM TIMETRA-SAP-MIB
       sdpBindId                                FROM TIMETRA-SDP-MIB

       InetAddressType, InetAddress,
       InetAddressIPv4,
       InetAddressIPv6,
       InetAddressPrefixLength,
       InetAutonomousSystemNumber,
       InetPortNumber
                                                FROM INET-ADDRESS-MIB

       InterfaceIndexOrZero                     FROM IF-MIB
       TmnxPppCpState                           FROM TIMETRA-PPP-MIB
       
       tmnxChassisIndex, tmnxCardSlotNum,
       tmnxMDASlotNum                           FROM TIMETRA-CHASSIS-MIB
       
       tmnxPwPortId                             FROM TIMETRA-PORT-MIB
       
       TmnxRipNgAuthType,
       TmnxRipNgAuthKey                         FROM TIMETRA-RIP-NG-MIB
       ;

tmnxSubMgmtMIBModule MODULE-IDENTITY
        LAST-UPDATED "201402200000Z"
        ORGANIZATION "Nokia"
        CONTACT-INFO
            "Nokia SROS Support
             Web: http://www.nokia.com"
    DESCRIPTION
        "This document contains the SNMP MIB module for handling subscriber
         management for the Nokia SROS series systems.

         Copyright 2005-2015 Nokia. All rights reserved.
         Reproduction of this document is authorized on the condition that
         the foregoing copyright notice is included.

         This SNMP MIB module (Specification) embodies Nokia's
         proprietary intellectual property.  Nokia retains
         all title and ownership in the Specification, including any
         revisions.

         Nokia grants all interested parties a non-exclusive
         license to use and distribute an unmodified copy of this
         Specification in connection with management of Nokia
         products, and without fee, provided this copyright notice and
         license appear on all copies.

         This Specification is supplied 'as is', and Nokia
         makes no warranty, either express or implied, as to the use,
         operation, condition, or performance of the Specification."
--
--  Revision History
--
    REVISION      "201402200000Z"
    DESCRIPTION   "Rev 13.0               20 Feb 2014 00:00
                   13.0 release of the TIMETRA-SUBSCRIBER-MGMT-MIB."
                   
    REVISION      "201401010000Z"
    DESCRIPTION   "Rev 12.0                1 Jan 2014 00:00
                   12.0 release of the TIMETRA-SUBSCRIBER-MGMT-MIB."

    REVISION      "201108010000Z"
    DESCRIPTION   "Rev 10.0                1 Aug 2011 00:00
                   10.0 release of the TIMETRA-SUBSCRIBER-MGMT-MIB."

    REVISION      "201102010000Z"
    DESCRIPTION   "Rev 9.0                 1 Feb 2011 00:00
                   9.0 release of the TIMETRA-SUBSCRIBER-MGMT-MIB."

    REVISION      "200902280000Z"
    DESCRIPTION   "Rev 7.0                28 Feb 2009 00:00
                   7.0 release of the TIMETRA-SUBSCRIBER-MGMT-MIB."

    REVISION      "200807010000Z"
    DESCRIPTION   "Rev 6.1                01 Jul 2008 00:00
                   6.1 release of the TIMETRA-SUBSCRIBER-MGMT-MIB."

    REVISION      "200801010000Z"
    DESCRIPTION   "Rev 6.0                01 Jan 2008 00:00
                   6.0 release of the TIMETRA-SUBSCRIBER-MGMT-MIB."

    REVISION      "200701010000Z"
    DESCRIPTION   "Rev 5.0                01 Jan 2007 00:00
                   5.0 release of the TIMETRA-SUBSCRIBER-MGMT-MIB."

    REVISION      "200602280000Z"
    DESCRIPTION   "Rev 4.0                28 Feb 2006 00:00
                   4.0 release of the TIMETRA-SUBSCRIBER-MGMT-MIB."

    REVISION      "200508310000Z"
    DESCRIPTION   "Rev 3.0                31 Aug 2005 00:00
                   3.0 release of the TIMETRA-SUBSCRIBER-MGMT-MIB."

    REVISION      "200503010000Z"
    DESCRIPTION   "Rev 1.0                01 Mar 2005 00:00
                   1.0 release of the TIMETRA-SUBSCRIBER-MGMT-MIB."

    ::= { timetraSRMIBModules 33 }

----------------------------------------------------------------------------
--  Nokia SROS series TIMETRA-SUBSCRIBER-MGMT
--  MIB structure
----------------------------------------------------------------------------
tmnxSubMgmt                      OBJECT IDENTIFIER ::= { tmnxSRObjs 33 }
    tmnxSubMgmtObjects           OBJECT IDENTIFIER ::= { tmnxSubMgmt 1 }
    tmnxSubscriberNotifyObjects  OBJECT IDENTIFIER ::= { tmnxSubMgmt 2 }
    tmnxSubRadNotifyStatsObjects OBJECT IDENTIFIER ::= { tmnxSubMgmt 3 }
    tmnxSubIgmpHostObjs          OBJECT IDENTIFIER ::= { tmnxSubMgmt 4 }
    tmnxSubPppObjs               OBJECT IDENTIFIER ::= { tmnxSubMgmt 5 }
    tmnxSubHsmda2Objs            OBJECT IDENTIFIER ::= { tmnxSubMgmt 6 }
    tmnxSubIpoeObjs              OBJECT IDENTIFIER ::= { tmnxSubMgmt 7 }
    tmnxSubRipObjs               OBJECT IDENTIFIER ::= { tmnxSubMgmt 8 }
    tmnxSubPimObjs               OBJECT IDENTIFIER ::= { tmnxSubMgmt 9 }
    tmnxSubShcvObjs              OBJECT IDENTIFIER ::= { tmnxSubMgmt 10 }

tmnxSubscriberNotifyPrefix       OBJECT IDENTIFIER ::= { tmnxSRNotifyPrefix 33 }
    tmnxSubscriberNotifications  OBJECT IDENTIFIER ::= { tmnxSubscriberNotifyPrefix 0 }

tmnxSubMgmtConformance           OBJECT IDENTIFIER ::= { tmnxSRConfs 33 }
    tmnxSubMgmtCompliances       OBJECT IDENTIFIER ::= { tmnxSubMgmtConformance 1 }
    tmnxSubMgmtGroups            OBJECT IDENTIFIER ::= { tmnxSubMgmtConformance 2 }
    tmnxSubMgmtNotifGroup        OBJECT IDENTIFIER ::= { tmnxSubMgmtConformance 3 }

--
-- Subtrees
--
    tmnxSubHttpRedirectObjs      OBJECT IDENTIFIER ::= { tmnxSubMgmtObjects 1000 }
    tmnxSubSysObjs               OBJECT IDENTIFIER ::= { tmnxSubMgmtObjects 1001 }

----------------------------------------------------------------------------
--  Textual Conventions   (alphabetical)
----------------------------------------------------------------------------
TmnxSubAcctPlcySessionIdFormat ::= TEXTUAL-CONVENTION
    STATUS      current
    DESCRIPTION
        "The TmnxSubAcctPlcySessionIdFormat data type is an enumerated integer
         that indicates the format for the acct-session-id attribute used in
         RADIUS accounting requests."
    SYNTAX INTEGER {
        description (1),
        number      (2)
    }

TmnxSubAcctPlcyAccountingType ::= TEXTUAL-CONVENTION
    STATUS      current
    DESCRIPTION
        "The TmnxSubAcctPlcyAccountingType data type is an enumerated integer
         that indicates which accounting messages are sent."
    SYNTAX INTEGER { 
        enabled     (1), -- start/stop accounting messages
        disabled    (2), -- no accounting messages 
        interim     (3), -- start/interim/stop messages
        host        (4), -- start/host updates/stop messages
        interimHost (5)  -- start/interim and host updates/stop messages
    }

TmnxSubAdminStatus ::= TEXTUAL-CONVENTION
    STATUS      current
    DESCRIPTION
        "The TmnxSubAdminStatus data type is an enumerated integer that
         describes the values used to identify the administrative state."
    SYNTAX INTEGER {
        enabled  (1),
        disabled (2)
    }

TmnxSubAuthPlcyUserNameAppend ::= TEXTUAL-CONVENTION
    STATUS      current
    DESCRIPTION
        "The TmnxSubAuthPlcyUserNameAppend data type is an enumerated integer
         that indicates what needs to be appended to the user-name sent to the
         RADIUS server."
    SYNTAX INTEGER {
        nothing    (1),
        domainName (2)
    }

TmnxSubAuthPlcyUserNameFormat ::= TEXTUAL-CONVENTION
    STATUS      current
    DESCRIPTION
        "The TmnxSubAuthPlcyUserNameFormat data type is an enumerated integer
         that indicates the format used to identify the user towards the RADIUS
         server."
    SYNTAX INTEGER {
        macAddress              (1),
        circuitId               (2),
        both                    (3),
        asciiConvertedCircuitId (4),
        asciiConvertedBoth      (5),
        dhcpClientVendorOpts    (6),
        macGiaddr               (7),
        pppUserName             (8)
    }

TmnxSubAuthPppoeAccessMethod ::= TEXTUAL-CONVENTION
    STATUS      current
    DESCRIPTION
        "The TmnxSubAuthPppoeAccessMethod data type is an enumerated integer
         that indicates the authentication method used towards the RADIUS
         server in case the policy is used for PPPoE:
         - none     (1) : indicates that no PPPoE authentication is done
         - padi     (2) : indicates that authentication is done based on the
                          received PADI packet
         - pap-chap (3) : indicates that PAP/CHAP authentication is done."
    SYNTAX INTEGER {
        none     (1),
        padi     (2),
        pap-chap (3)
    }

TmnxSubCcAccountedResource ::= TEXTUAL-CONVENTION
    STATUS      current
    DESCRIPTION
        "The TmnxSubCcAccountedResource data type is an enumerated integer that
         specifies what action property is used for accounting and credit
         control."
    SYNTAX      INTEGER {
                    volume (1),
                    time   (2)
                }

TmnxSubCcAccountedResourceOrNone ::= TEXTUAL-CONVENTION
    STATUS      current
    DESCRIPTION
        "The TmnxSubCcAccountedResource data type is an enumerated integer that
         specifies what action property is used for accounting and credit
         control."
    SYNTAX      INTEGER {
                    none   (0),
                    volume (1),
                    time   (2)
                }

TmnxSubCcErrorAction ::= TEXTUAL-CONVENTION
    STATUS      current
    DESCRIPTION
        "The TmnxSubCcErrorAction data type is an enumerated integer that
         specifies what action is to be taken when an error condition is met."
    SYNTAX INTEGER {
        continue  (1),
        block     (2)
    }

TmnxSubCcOutOfCreditAction ::= TEXTUAL-CONVENTION
    STATUS      current
    DESCRIPTION
        "The TmnxSubCcOutOfCreditAction data type is an enumerated integer that
         specifies what action is to be taken when running out of credit."
    SYNTAX INTEGER {
        none               (0),
        continue           (1),
        disconnectHost     (2),
        blockCategory      (3),
        changeServiceLevel (4)
    }

TmnxSubDirection ::= TEXTUAL-CONVENTION
    STATUS      current
    DESCRIPTION
        "The TmnxSubDirection data type is an enumerated integer that indicates
         whether the data applies to ingress or egress direction."
    SYNTAX INTEGER {
        ingress (1),
        egress  (2)
    }

TmnxSubHostOrigin ::= TEXTUAL-CONVENTION
    STATUS      current
    DESCRIPTION
        "The TmnxSubHostOrigin data type is a bitfield that indicates the
         origin of the specific subscriber host:
         - staticHost    (0): created as result of a static host
                              (TIMETRA-SAP-MIB::sapStaticHostTable)
         - dhcpLease     (1): created as result of a DHCP lease state
                              (TIMETRA-SERV-MIB::svcDhcpLeaseStateTable)
         - nonSubTraffic (2): created as result of non-sub-traffic parameters
                              (TIMETRA-SAP-MIB::sapSubMgmtNonSubTraffic)
         - pppoeSession  (3): created as result of a PPPoE session
                              (TIMETRA-PPPOE-MIB::tmnxPppoeSessionTable)
         - arpHost       (4): created as result of an ARP host
                              (TIMETRA-SERV-MIB::svcArpHostTable)
         - ipcpSession   (5): created as result of a PPPoE or L2TP (LNS)
                              IPCP session
         - l2tpSession   (6): created as result of a PPPoE or L2TP (LNS)
                              LAC session
         - pppSLAAC      (7): created as result of a PPPoE or L2TP (LNS)
                              IPV6CP (IPv6 Control Protocol) session
         - pppDhcp6      (8): created as result of a PPPoE or L2TP (LNS)
                              DHCP6 lease state
         - ipoeDhcp6     (9): created as result of an DHCP6 lease state
                              (TIMETRA-SERV-MIB::svcDhcpLeaseStateTable)
         - ipoeSLAAC    (10): created as result of an IPoE slaac host
         - wpp          (11): created as result of a Web Portal request.
         - staticHost6  (12): created as result of a static host
                              (TIMETRA-SAP-MIB::sapStatHost6Table)"
    SYNTAX BITS {
        staticHost    (0),
        dhcpLease     (1),
        nonSubTraffic (2),
        pppoeSession  (3),
        arpHost       (4),
        ipcpSession   (5),
        l2tpSession   (6),
        pppSLAAC      (7),
        pppDhcp6      (8),
        ipoeDhcp6     (9),
        ipoeSLAAC    (10),
        wpp          (11),
        staticHost6  (12)
    }

TmnxSubHostTrkStatsType ::= TEXTUAL-CONVENTION
    STATUS      current
    DESCRIPTION
        "The TmnxSubHostTrkStatsType data type is an enumerated integer
         that indicates a type of host tracking statistics."
    SYNTAX INTEGER {
        rxIgmp2Reports   (1),
        rxIgmp2Leaves    (2),
        rxIgmp3Reports   (3),
        rxIgmpDrops      (4),
        rxGroupJoins     (5),
        rxGroupLeaves    (6),
        groupExpiries    (7),
        policyDrops      (8),
        groupLimitDrops  (9),
        sourceLimitDrops (10)
    }

TmnxSubProfEgrEncapOffset ::= TEXTUAL-CONVENTION
    STATUS      current
    DESCRIPTION
        "The TmnxSubProfEgrEncapOffset data type is an enumerated integer that
         specifies what offset will be used for in the calculation of the 
         packet encapsulation overhead."
    SYNTAX INTEGER {
        none       (0),
        auto       (1)
    }

TmnxSubOperStatus ::= TEXTUAL-CONVENTION
    STATUS      current
    DESCRIPTION
        "The TmnxSubOperStatus data type is an enumerated integer that
         describes the values used to identify the operational state."
    SYNTAX INTEGER {
        up   (1),
        down (2)
    }

TmnxSubOvrBurstPercent ::= TEXTUAL-CONVENTION
    STATUS      current
    DESCRIPTION
        "The TmnxSubOvrBurstPercent data type is an integer that indicates the
         override percentage of buffer space assigned to a queue that is
         reserved for some purpose.
         The value -1 means that the actual value is derived from the
         corresponding buffer policy's default value. The value -2 indicates
         that the value is not overridden."
    SYNTAX INTEGER (-2|-1|0..100)

TmnxSubOvrBurstSize ::= TEXTUAL-CONVENTION
    STATUS      current
    DESCRIPTION
        "The TmnxSubOvrBurstSize data type is an integer that indicates the
         override amount of buffer space (in kbytes) assigned to a queue.
         The value -1 means that the actual value is derived from the
         corresponding buffer policy's default value. The value -2 indicates
         that the value is not overridden."
    SYNTAX INTEGER (-2|-1|0..1048576)

TmnxSubPppType ::= TEXTUAL-CONVENTION
    STATUS      current
    DESCRIPTION
        "The TmnxSubPppType data type is an enumerated integer that
         describes the values used to identify the type of subscriber PPP
         session."
    SYNTAX INTEGER {
        oE    (1), -- over Ethernet
        oEoA  (2), -- over Ethernet over ATM
        oA    (3), -- over ATM
        oL2tp (4)  -- over L2TP (LNS)
    }

TmnxSubPppTerminationType ::= TEXTUAL-CONVENTION
    STATUS      current
    DESCRIPTION
        "The TmnxSubPppTerminationType indicates how the subscriber PPP
         session is terminated."
    SYNTAX INTEGER {
        local          (1), -- Locally terminated session.
        localWholesale (2), -- Wholesale/retail session terminating in the
                            -- wholesale service.
        localRetail    (3), -- Wholesale/retail session terminating in the 
                            -- retail service.
        lac            (4)  -- Session is tunneled to an LNS via L2TP.
    }

TmnxSubReportRateType ::= TEXTUAL-CONVENTION 
    STATUS      current
    DESCRIPTION
        "The TmnxSubReportRateType data type is an enumerated integer that
         indicates what rate will be reported when creating an L2TP
         session:
         - maximum         (0): Take the port rate.
         - aggRateLimit    (1): Take the aggregate rate as received from the
                                RADIUS Access-Accept message in
                                VSA 'Alc-Subscriber-QoS-Override'. When this
                                RADIUS VSA is not present in the Access-Accept
                                or when RADIUS is not used then take the 
                                configured aggregate rate limit; in case none
                                is configured then take the port rate.
         - namedScheduler  (2): Take the rate of the specified scheduler, in 
                                case the scheduler is not linked with the
                                scheduler-policy from the subscriber-profile 
                                then take the port rate.
         - pppoeActualRate (3): Take the rate from the DSL-Forum 
                                Vendor-Specific PPPoE Tag when available,
                                otherwise take the port rate.
         - rfc5515ActualRate (4):
                                Put the same value as the transmitted Actual-Data-Rate-Upstream AVP
                                in the Rx-Connect-Speed AVP,
                                and the same value as the  transmitted Actual-Data-Rate-Downstream AVP
                                in the Tx-Connect-Speed AVP."
    SYNTAX INTEGER {
        maximum         (0),
        aggRateLimit    (1),
        namedScheduler  (2),
        pppoeActualRate (3),
        rfc5515ActualRate (4)
    }

TmnxSubSLAProfHostLimit ::= TEXTUAL-CONVENTION
    STATUS      current
    DESCRIPTION
        "The TmnxSubSLAProfHostLimit data type is an integer that indicates the
         maximum number of hosts using a given SLA (Service Level Agreement)
         profile.
         The value -1 indicates that there is no limit. 0 is not allowed"
    SYNTAX INTEGER (-1|1..131071)

TmnxSubSLAProfHostLimit2 ::= TEXTUAL-CONVENTION
    STATUS      current
    DESCRIPTION
        "The TmnxSubSLAProfHostLimit2 data type is an integer that indicates the
         maximum number of hosts using a given SLA (Service Level Agreement)
         profile.
         The value -1 indicates that there is no limit."
    SYNTAX INTEGER (-1..131071)

TmnxSubQueuesEgress ::= TEXTUAL-CONVENTION
    STATUS      current
    DESCRIPTION
        "The TmnxSubQueuesEgress data type is a bitfield that indicates
         a set of egress queues"
    SYNTAX BITS {
        queue1    (0),
        queue2    (1),
        queue3    (2),
        queue4    (3),
        queue5    (4),
        queue6    (5),
        queue7    (6),
        queue8    (7)
    }

TmnxSubQueuesIngress ::= TEXTUAL-CONVENTION
    STATUS      current
    DESCRIPTION
        "The TmnxSubQueuesIngress data type is a bitfield that indicates
         a set of ingress queues"
    SYNTAX BITS {
        queue1    (0),
        queue2    (1),
        queue3    (2),
        queue4    (3),
        queue5    (4),
        queue6    (5),
        queue7    (6),
        queue8    (7),
        queue9    (8),
        queue10   (9),
        queue11   (10),
        queue12   (11),
        queue13   (12),
        queue14   (13),
        queue15   (14),
        queue16   (15),
        queue17   (16),
        queue18   (17),
        queue19   (18),
        queue20   (19),
        queue21   (20),
        queue22   (21),
        queue23   (22),
        queue24   (23),
        queue25   (24),
        queue26   (25),
        queue27   (26),
        queue28   (27),
        queue29   (28),
        queue30   (29),
        queue31   (30),
        queue32   (31)
    }
    
TmnxSubApCategoryDfltCrdtVolUnit ::= TEXTUAL-CONVENTION 
    STATUS      current
    DESCRIPTION
        "The TmnxSubApCategoryDfltCrdtVolUnit data type is an enumerated integer
         that specifies the unit in which the default-credit is expressed."
    SYNTAX      INTEGER {
                    bytes     (0),
                    kilobytes (1),
                    megabytes (2),
                    gigabytes (3)
                }

TmnxSubPolicersEgress ::= TEXTUAL-CONVENTION
    STATUS      current
    DESCRIPTION
        "The TmnxSubPolicersEgress data type is a bitfield that indicates
         a set of egress policers"
    SYNTAX BITS {
        policer1    (0),
        policer2    (1),
        policer3    (2),
        policer4    (3),
        policer5    (4),
        policer6    (5),
        policer7    (6),
        policer8    (7),
        policer9    (8),
        policer10   (9),
        policer11   (10),
        policer12   (11),
        policer13   (12),
        policer14   (13),
        policer15   (14),
        policer16   (15),
        policer17   (16),
        policer18   (17),
        policer19   (18),
        policer20   (19),
        policer21   (20),
        policer22   (21),
        policer23   (22),
        policer24   (23),
        policer25   (24),
        policer26   (25),
        policer27   (26),
        policer28   (27),
        policer29   (28),
        policer30   (29),
        policer31   (30),
        policer32   (31),
        policer33   (32),
        policer34   (33),
        policer35   (34),
        policer36   (35),
        policer37   (36),
        policer38   (37),
        policer39   (38),
        policer40   (39),
        policer41   (40),
        policer42   (41),
        policer43   (42),
        policer44   (43),
        policer45   (44),
        policer46   (45),
        policer47   (46),
        policer48   (47),
        policer49   (48),
        policer50   (49),
        policer51   (50),
        policer52   (51),
        policer53   (52),
        policer54   (53),
        policer55   (54),
        policer56   (55),
        policer57   (56),
        policer58   (57),
        policer59   (58),
        policer60   (59),
        policer61   (60),
        policer62   (61),
        policer63   (62)
    }

TmnxSubPolicersIngress ::= TEXTUAL-CONVENTION
    STATUS      current
    DESCRIPTION
        "The TmnxSubPolicersIngress data type is a bitfield that indicates
         a set of ingress policers"
    SYNTAX BITS {
        policer1    (0),
        policer2    (1),
        policer3    (2),
        policer4    (3),
        policer5    (4),
        policer6    (5),
        policer7    (6),
        policer8    (7),
        policer9    (8),
        policer10   (9),
        policer11   (10),
        policer12   (11),
        policer13   (12),
        policer14   (13),
        policer15   (14),
        policer16   (15),
        policer17   (16),
        policer18   (17),
        policer19   (18),
        policer20   (19),
        policer21   (20),
        policer22   (21),
        policer23   (22),
        policer24   (23),
        policer25   (24),
        policer26   (25),
        policer27   (26),
        policer28   (27),
        policer29   (28),
        policer30   (29),
        policer31   (30),
        policer32   (31),
        policer33   (32),
        policer34   (33),
        policer35   (34),
        policer36   (35),
        policer37   (36),
        policer38   (37),
        policer39   (38),
        policer40   (39),
        policer41   (40),
        policer42   (41),
        policer43   (42),
        policer44   (43),
        policer45   (44),
        policer46   (45),
        policer47   (46),
        policer48   (47),
        policer49   (48),
        policer50   (49),
        policer51   (50),
        policer52   (51),
        policer53   (52),
        policer54   (53),
        policer55   (54),
        policer56   (55),
        policer57   (56),
        policer58   (57),
        policer59   (58),
        policer60   (59),
        policer61   (60),
        policer62   (61),
        policer63   (62)
    }

TOverruleFilterId ::= TEXTUAL-CONVENTION
    STATUS      current
    DESCRIPTION
        "The TOverruleFilterId data type represents filter Id info that is
         used to override the filter-id info specified in the sla-profile.
         
         The value '0' indicates that no filter overrule is requested,
        
         THe value 'FFFFFFFF'H indicates a request
         to apply no filter (i.e. an overrule request with no filter).
         
         Any other value can be interpreted using the description which
         can be found in TIMETRA-FILTER-MIB::TAnyFilterID."
    SYNTAX Unsigned32

TmnxSubAutoSubIdKey ::= TEXTUAL-CONVENTION
    STATUS      current
    DESCRIPTION
        "The TmnxSubAutoSubIdKey data type is an enumerated integer that
         specifies which string is used as base for the auto-generated
         subscriber identification"
    SYNTAX INTEGER {
        none              (0),
        mac               (1),
        sapId             (2),
        circuitId         (3),
        remoteId          (4),
        sessionId         (5),
        dualStackRemoteId (6)
    }

TmnxSubSlaacInfoOrigin ::= TEXTUAL-CONVENTION
    STATUS          current
    DESCRIPTION
        "Indicates the originator of the provided information."
    SYNTAX INTEGER {
        none        (0),
        dhcp        (1),
        radius      (2),
        default     (3),
        localUserDb (4),
        localPool   (5),
        dtc         (6),
        diameterNasreq (7)
    }

TmnxSubLcktPlcyHostKey ::= TEXTUAL-CONVENTION
    STATUS          current
    DESCRIPTION
        "Indicates the method for host matching."
    SYNTAX INTEGER {
        all        (0),
        mac        (1)
    }

TmnxPccRuleName ::= TEXTUAL-CONVENTION
    STATUS  current
    DESCRIPTION
        "The TmnxPccRuleName data type defines the name of a PCC rule."
    SYNTAX DisplayString (SIZE (1..100))

TmnxPccRuleMonitorKey ::= TEXTUAL-CONVENTION
    STATUS  current
    DESCRIPTION
        "The TmnxPccRuleMonitorKey data type defines the monitor key name
         that can be received in a PCC rule.
         An empty string (length 0) indicates that no monitor key is defined
         in the PCC rule."
    SYNTAX DisplayString (SIZE (0..80))

TmnxPccRuleStatus ::= TEXTUAL-CONVENTION
    STATUS      current
    DESCRIPTION
        "The TmnxPccRuleStatus data type is an enumerated integer that
         describes the possible states of a PCC-rule."
    SYNTAX INTEGER {
        up   (1),
        down (2)
    }

-- --------------------------------------------------------
-- tmnxSubAuthPlcyTable
-- --------------------------------------------------------
tmnxSubAuthPlcyTable OBJECT-TYPE
    SYNTAX      SEQUENCE OF TmnxSubAuthPlcyEntry
    MAX-ACCESS  not-accessible
    STATUS      current
    DESCRIPTION
        "The tmnxSubAuthPlcyTable allows configuration of subscriber Radius
         authentication policy parameters."
    ::= { tmnxSubMgmtObjects 1 }

tmnxSubAuthPlcyEntry OBJECT-TYPE
    SYNTAX      TmnxSubAuthPlcyEntry
    MAX-ACCESS  not-accessible
    STATUS      current
    DESCRIPTION
        "tmnxSubAuthPlcyEntry is an entry (conceptual row) in the
         tmnxSubAuthPlcyTable. Each entry represents the configuration for a
         RADIUS policy. Entries in this table can be created and deleted via
         SNMP SET operations to tmnxSubAuthPlcyRowStatus. Entries have a
         presumed StorageType of nonVolatile."
    INDEX { tmnxSubAuthPlcyName }
    ::= { tmnxSubAuthPlcyTable 1 }

TmnxSubAuthPlcyEntry ::= SEQUENCE {
    tmnxSubAuthPlcyName              TNamedItem,
    tmnxSubAuthPlcyRowStatus         RowStatus,
    tmnxSubAuthPlcyLastMgmtChange    TimeStamp,
    tmnxSubAuthPlcyDescription       TItemDescription,
    tmnxSubAuthPlcyPassword          TmnxAuthPassword,
    tmnxSubAuthPlcyRadAuthRetries    Unsigned32,
    tmnxSubAuthPlcyRadAuthSrceAddr   InetAddress,
    tmnxSubAuthPlcyRadAuthSrceAddrTp InetAddressType,
    tmnxSubAuthPlcyRadAuthTimeout    Unsigned32,
    tmnxSubAuthPlcyReAuthenticate    TruthValue,
    tmnxSubAuthPlcyUserNameFormat    TmnxSubAuthPlcyUserNameFormat,
    tmnxSubAuthPlcyRadAuthVRtrID     TmnxVRtrIDOrZero,
    tmnxSubAuthPlcyAcceptAuthChange  TruthValue,
    tmnxSubAuthPlcyInclAttributes    BITS,
    tmnxSubAuthPlcyRadAuthAlgorithm  TmnxSubRadServAlgorithm,
    tmnxSubAuthPlcyPppoeAccessMethod TmnxSubAuthPppoeAccessMethod,
    tmnxSubAuthPlcyNasPortPfixType   TmnxSubNasPortPrefixType,
    tmnxSubAuthPlcyNasPortPfixString DisplayString,
    tmnxSubAuthPlcyNasPortSfixType   TmnxSubNasPortSuffixType,
    tmnxSubAuthPlcyUserNameAppend    TmnxSubAuthPlcyUserNameAppend,
    tmnxSubAuthPlcyFallbackAction    INTEGER,
    tmnxSubAuthPlcyFallbackUserDb    TNamedItemOrEmpty,
    tmnxSubAuthPlcyClngStationIdType TmnxSubCallingStationIdType,
    tmnxSubAuthPlcyNasPortTypeType   TmnxSubNasPortTypeType,
    tmnxSubAuthPlcyNasPortTypeValue  Unsigned32,
    tmnxSubAuthPlcyPppUserNameOp     TmnxSubAuthPlcyUserNameOp,
    tmnxSubAuthPlcyPppDomain         DisplayString,
    tmnxSubAuthPlcyRadAuthDownTime   Unsigned32,
    tmnxSubAuthPlcyUserNameOp        TmnxSubAuthPlcyUserNameOp,
    tmnxSubAuthPlcyDomain            DisplayString,
    tmnxSubAuthPlcyUserNameMacFormat TmnxMacSpecification,
    tmnxSubAuthPlcyRadRespAttrSelect TruthValue,
    tmnxSubAuthPlcyRequestScriptPlcy TNamedItemOrEmpty,
    tmnxSubAuthPlcyAcceptScriptPlcy  TNamedItemOrEmpty,
    tmnxSubAuthPlcyCoAScriptPlcy     TNamedItemOrEmpty,
    tmnxSubAuthPlcyAcctSessionIdType INTEGER,
    tmnxSubAuthPlcyNasPortBitspec    TmnxBinarySpecification,
    tmnxSubAuthPlcyRadiusServerPlcy  TNamedItemOrEmpty,
    tmnxSubAuthPlcyAcctStopOnFail    BITS
}

tmnxSubAuthPlcyName OBJECT-TYPE
    SYNTAX      TNamedItem
    MAX-ACCESS  not-accessible
    STATUS      current
    DESCRIPTION
        "The value of tmnxSubAuthPlcyName specifies a specific subscriber
         authentication policy."
    ::= { tmnxSubAuthPlcyEntry 1 }

tmnxSubAuthPlcyRowStatus OBJECT-TYPE
    SYNTAX      RowStatus
    MAX-ACCESS  read-create
    STATUS      current
    DESCRIPTION
        "The value of tmnxSubAuthPlcyRowStatus controls the creation and
         deletion of rows in the table. An attempt to delete a row that is
         referred to in vRtrIfDHCPAuthPolicy will fail with an
         inconsistentValue error."
    ::= { tmnxSubAuthPlcyEntry 2 }

tmnxSubAuthPlcyLastMgmtChange OBJECT-TYPE
    SYNTAX      TimeStamp
    MAX-ACCESS  read-only
    STATUS      current
    DESCRIPTION
        "The value of tmnxSubAuthPlcyLastMgmtChange indicates the sysUpTime at
         the time of the most recent management-initiated change to this
         Policy."
    ::= { tmnxSubAuthPlcyEntry 3 }

tmnxSubAuthPlcyDescription OBJECT-TYPE
    SYNTAX      TItemDescription
    MAX-ACCESS  read-create
    STATUS      current
    DESCRIPTION
        "The value of tmnxSubAuthPlcyDescription specifies the user provided
         description of this subscriber authentication policy."
    DEFVAL { "" }
    ::= { tmnxSubAuthPlcyEntry 4 }

tmnxSubAuthPlcyPassword OBJECT-TYPE
    SYNTAX      TmnxAuthPassword
    MAX-ACCESS  read-create
    STATUS      current
    DESCRIPTION
        "The value of tmnxSubAuthPlcyPassword specifies the password associated
         with the user for going to the RADIUS server. An empty string is
         returned on SNMP GET requests."
    DEFVAL { "" }
    ::= { tmnxSubAuthPlcyEntry 5 }

tmnxSubAuthPlcyRadAuthRetries OBJECT-TYPE
    SYNTAX      Unsigned32 (1..256)
    MAX-ACCESS  read-create
    STATUS      current
    DESCRIPTION
        "The value of tmnxSubAuthPlcyRadAuthRetries specifies the number of
         RADIUS requests towards the same RADIUS server."
    DEFVAL { 3 }
    ::= { tmnxSubAuthPlcyEntry 6 }

tmnxSubAuthPlcyRadAuthSrceAddr OBJECT-TYPE
    SYNTAX      InetAddress (SIZE (4))
    MAX-ACCESS  read-create
    STATUS      current
    DESCRIPTION
        "The value of tmnxSubAuthPlcyRadAuthSrceAddr specifies the source
         address of a radius packet for subscriber authentication. It must be
         a valid unicast address (otherwise a wrongValue error is returned).

         If this object is configured with the address of the router interface
         (ref TIMETRA-VRTR-MIB::vRiaIpAddress) the Radius client uses it while
         making a request to the server.

         If the address is not configured or is not the address of one of the
         interfaces, the source address is based on the address of the Radius
         server. If the server address is in-band, the client uses the system
         ip address. If it is out-of-band, the source address is the address of
         the management interface (The addresses can be found in
         TIMETRA-VRTR-MIB::vRiaIpAddress)."
    DEFVAL { '00000000'H }  -- 0.0.0.0
    ::= { tmnxSubAuthPlcyEntry 7 }

tmnxSubAuthPlcyRadAuthSrceAddrTp OBJECT-TYPE
    SYNTAX      InetAddressType
    MAX-ACCESS  read-create
    STATUS      current
    DESCRIPTION
        "The value of tmnxSubAuthPlcyRadAuthSrceAddrTp specifies the type of
         host address stored in tmnxSubAuthPlcyRadAuthSrceAddr."
    DEFVAL { ipv4 }
    ::= { tmnxSubAuthPlcyEntry 8 }

tmnxSubAuthPlcyRadAuthTimeout OBJECT-TYPE
    SYNTAX      Unsigned32 (1..340)
    UNITS       "seconds"
    MAX-ACCESS  read-create
    STATUS      current
    DESCRIPTION
        "The value of tmnxSubAuthPlcyRadAuthTimeout specifies, in seconds,
         between authentication request retries towards the same RADIUS
         server."
    DEFVAL { 5 }
    ::= { tmnxSubAuthPlcyEntry 9 }

tmnxSubAuthPlcyReAuthenticate OBJECT-TYPE
    SYNTAX      TruthValue
    MAX-ACCESS  read-create
    STATUS      current
    DESCRIPTION
        "The value of tmnxSubAuthPlcyReAuthenticate specifies whether
         authentication must be re-issued when the DHCP lease timer expires.

         This field is only applicable for DHCP authentication."
    DEFVAL { false }
    ::= { tmnxSubAuthPlcyEntry 10 }

tmnxSubAuthPlcyUserNameFormat OBJECT-TYPE
    SYNTAX      TmnxSubAuthPlcyUserNameFormat
    MAX-ACCESS  read-create
    STATUS      current
    DESCRIPTION
        "The value of tmnxSubAuthPlcyUserNameFormat specifies how the user is
         represented when contacting RADIUS server."
    DEFVAL { macAddress }
    ::= { tmnxSubAuthPlcyEntry 11 }

tmnxSubAuthPlcyRadAuthVRtrID OBJECT-TYPE
    SYNTAX      TmnxVRtrIDOrZero
    MAX-ACCESS  read-create
    STATUS      current
    DESCRIPTION
        "The value of tmnxSubAuthPlcyRadAuthVRtrID specifies the virtual router
         instance applicable for the set of configured RADIUS servers
         (tmnxSubAuthPlcyRadServTable). The value of this object cannot be
         changed once an RADIUS server is configured for this policy.
         When the value is '0', both base and management router instances are
         matched."
    DEFVAL { 0 }
    ::= { tmnxSubAuthPlcyEntry 12 }

tmnxSubAuthPlcyAcceptAuthChange OBJECT-TYPE
    SYNTAX      TruthValue
    MAX-ACCESS  read-create
    STATUS      current
    DESCRIPTION
        "The value of tmnxSubAuthPlcyAcceptAuthChange specifies whether or not
         the system should handle the CoA messages initiated by the RADIUS
         server, and provide for mid-session interval changes of policies
         applicable to subscriber hosts."
    DEFVAL { false }
    ::= { tmnxSubAuthPlcyEntry 13 }

tmnxSubAuthPlcyInclAttributes OBJECT-TYPE
    SYNTAX      BITS {
                    circuitId         (0),
                    remoteId          (1),
                    nasPortId         (2),
                    nasIdentifier     (3),
                    pppoeServiceName  (4),
                    dhcpVendorClassId (5),
                    accessLoopOptions (6),
                    macAddress        (7),
                    callingStationId  (8),
                    calledStationId   (9),
                    tunnelServerAttrs (10),
                    dhcpOptions       (11),
                    nasPortType       (12),
                    acctSessionId     (13),
                    nasPort           (14),
                    sapSessionIndex   (15),
                    dhcp6Options      (16),
                    wifiSsidVlan      (17)
                }
    MAX-ACCESS  read-create
    STATUS      current
    DESCRIPTION
        "The value of tmnxSubAuthPlcyInclAttributes specifies what RADIUS
         attributes the system should include into RADIUS
         authentication-request messages."
    DEFVAL { { } }
    ::= { tmnxSubAuthPlcyEntry 14 }

tmnxSubAuthPlcyRadAuthAlgorithm OBJECT-TYPE
    SYNTAX      TmnxSubRadServAlgorithm {
                    direct     (1),
                    roundRobin (2)
                }
    MAX-ACCESS  read-create
    STATUS      current
    DESCRIPTION
        "The value of tmnxSubAuthPlcyRadAuthAlgorithm specifies the algorithm
         used to select a RADIUS server from the list of configured servers
         (tmnxSubAuthPlcyRadServTable)."
    DEFVAL { direct }
    ::= { tmnxSubAuthPlcyEntry 15 }

tmnxSubAuthPlcyPppoeAccessMethod OBJECT-TYPE
    SYNTAX      TmnxSubAuthPppoeAccessMethod
    MAX-ACCESS  read-create
    STATUS      current
    DESCRIPTION
        "The value of tmnxSubAuthPlcyPppoeAccessMethod specifies the
         authentication method used to authenticate PPPoE towards the RADIUS
         server."
    DEFVAL { padi }
    ::= { tmnxSubAuthPlcyEntry 16 }

tmnxSubAuthPlcyNasPortPfixType OBJECT-TYPE
    SYNTAX      TmnxSubNasPortPrefixType
    MAX-ACCESS  read-create
    STATUS      current
    DESCRIPTION
        "The value of tmnxSubAuthPlcyNasPortPfixType specifies what type of
         prefix will be added to the NAS-Port attribute if included in RADIUS
         authentication-request messages.
         This field is only applicable if the 'nasPortId' bit is set in
         tmnxSubAuthPlcyInclAttributes."
    DEFVAL { none }
    ::= { tmnxSubAuthPlcyEntry 17 }

tmnxSubAuthPlcyNasPortPfixString OBJECT-TYPE
    SYNTAX      DisplayString (SIZE (0..8))
    MAX-ACCESS  read-create
    STATUS      current
    DESCRIPTION
        "The value of tmnxSubAuthPlcyNasPortPfixString specifies the user
         configurable string to be added as prefix to the NAS-Port attribute if
         included in RADIUS authentication-request messages.
         This field is only applicable if the 'nasPortId' bit is set in
         tmnxSubAuthPlcyInclAttributes and tmnxSubAuthPlcyNasPortPfixType
         is set to 'userString'."
    DEFVAL { "" }
    ::= { tmnxSubAuthPlcyEntry 18 }

tmnxSubAuthPlcyNasPortSfixType OBJECT-TYPE
    SYNTAX      TmnxSubNasPortSuffixType
    MAX-ACCESS  read-create
    STATUS      current
    DESCRIPTION
        "The value of tmnxSubAuthPlcyNasPortSfixType specifies what type of
         suffix will be added to the NAS-Port attribute if included in RADIUS
         authentication-request messages.
         This field is only applicable if the 'nasPortId' bit is set in
         tmnxSubAuthPlcyInclAttributes."
    DEFVAL { none }
    ::= { tmnxSubAuthPlcyEntry 19 }

tmnxSubAuthPlcyUserNameAppend OBJECT-TYPE
    SYNTAX      TmnxSubAuthPlcyUserNameAppend
    MAX-ACCESS  read-create
    STATUS      current
    DESCRIPTION
        "The value of tmnxSubAuthPlcyUserNameAppend specifies what will be
         appended to the user-name sent to the RADIUS server.

         When the value is 'nothing', the user-name will be created as
         indicated by tmnxSubAuthPlcyUserNameFormat.
         When the value is 'domainName', the user-name will be created as
         indicated by tmnxSubAuthPlcyUserNameFormat, appended by '@' and a
         domain-name if returned via a lookup in the local-user-database
         (TIMETRA-LOCAL-USER-DB-MIB::tmnxLocUsrDbDhcpDomainName).
         
         From release 8.0R4 onwards, use 'tmnxSubAuthPlcyUserNameOp' instead;
         the value of this object is ignored if the value of 
         'tmnxSubAuthPlcyUserNameOp' is different from 'noOperation'."
    DEFVAL { nothing }
    ::= { tmnxSubAuthPlcyEntry 20 }

tmnxSubAuthPlcyFallbackAction OBJECT-TYPE
    SYNTAX      INTEGER {
                          deny   (0),
                          accept (1),
                          userDb (2)
                }
    MAX-ACCESS  read-create
    STATUS      current
    DESCRIPTION
        "The value of tmnxSubAuthPlcyFallbackAction specifies the 
         authentication action in case no RADIUS server is available.

         When the value is 'deny', all hosts are denied access.

         When the value is 'accept', all hosts are granted access.

         When the value is 'userDb', the local user database identified by the 
         value of the object tmnxSubAuthPlcyFallbackUserDb' is used for
         authentication.
         
         The value of this object must be set together with the value of 
         the object tmnxSubAuthPlcyFallbackUserDb."
    DEFVAL { deny }
    ::= { tmnxSubAuthPlcyEntry 21 }

tmnxSubAuthPlcyFallbackUserDb OBJECT-TYPE
    SYNTAX      TNamedItemOrEmpty
    MAX-ACCESS  read-create
    STATUS      current
    DESCRIPTION
        "The value of tmnxSubAuthPlcyFallbackUserDb specifies the local user
         database to use for authentication while no RADIUS server is availabe.

         This object is only relevant while the value of the object 
         'tmnxSubAuthPlcyFallbackAction' is equal to 'userDb'.
         
         The value of this object must be set together with the value of 
         the object tmnxSubAuthPlcyFallbackAction."
    DEFVAL { "" }
    ::= { tmnxSubAuthPlcyEntry 22 }

tmnxSubAuthPlcyClngStationIdType OBJECT-TYPE
    SYNTAX      TmnxSubCallingStationIdType
    MAX-ACCESS  read-create
    STATUS      current
    DESCRIPTION
        "The value of tmnxSubAuthPlcyClngStationIdType specifies 
         what string will be put in the RADIUS Calling-Station-Id 
         attribute if included in RADIUS authentication-request messages.

         This field is only applicable if the 'callingStationId' bit is set in
         tmnxSubAuthPlcyInclAttributes."
    DEFVAL { sapString }
    ::= { tmnxSubAuthPlcyEntry 23 }

tmnxSubAuthPlcyNasPortTypeType OBJECT-TYPE
    SYNTAX      TmnxSubNasPortTypeType
    MAX-ACCESS  read-create
    STATUS      current
    DESCRIPTION
        "The value of tmnxSubAuthPlcyNasPortTypeType specifies 
         what kind of value will be put in the RADIUS NAS-Port-Type attribute 
         if included in RADIUS authentication-request messages.

         This field is only applicable if the 'nasPortType' bit 
         is set in tmnxSubAuthPlcyInclAttributes."
    DEFVAL { standard }
    ::= { tmnxSubAuthPlcyEntry 24 }

tmnxSubAuthPlcyNasPortTypeValue OBJECT-TYPE
    SYNTAX      Unsigned32 (0..255)
    MAX-ACCESS  read-create
    STATUS      current
    DESCRIPTION
        "The value of tmnxSubAuthPlcyNasPortTypeValue specifies 
         what value will be put in the RADIUS NAS-Port-Type attribute 
         if included in RADIUS authentication-request messages.

         This field is only applicable if the 'nasPortType' bit 
         is set in  tmnxSubAuthPlcyInclAttributes 
         and the value of the object tmnxSubAuthPlcyNasPortTypeType is equal to
         'config'."
    DEFVAL { 0 }
    ::= { tmnxSubAuthPlcyEntry 25 }

tmnxSubAuthPlcyPppUserNameOp OBJECT-TYPE
    SYNTAX      TmnxSubAuthPlcyUserNameOp
    MAX-ACCESS  read-create
    STATUS      current
    DESCRIPTION
        "The value of tmnxSubAuthPlcyPppUserNameOp specifies the 
         operation to perform on the PAP/CHAP user name.

         When the value is 'appendDomain', the string specified by 
         'tmnxSubAuthPlcyPppDomain', preceded with a '@', is appended to
         the PAP/CHAP user name.

         When the value is 'stripDomain', any '@' character and all subsequent
         characters are removed from the PAP/CHAP user name.

         When the value is 'replaceDomain', all characters after a '@' delimiter
         are replaced with the string specified by 'tmnxSubAuthPlcyPppDomain'.

         When the value is 'defaultDomain', the same action is performed as with
         'appendDomain', but only if the PAP/CHAP user name does not contain
         a domain name already."
    DEFVAL { noOperation }
    ::= { tmnxSubAuthPlcyEntry 26 }

tmnxSubAuthPlcyPppDomain OBJECT-TYPE
    SYNTAX      DisplayString (SIZE (0..128))
    MAX-ACCESS  read-create
    STATUS      current
    DESCRIPTION
        "The value of tmnxSubAuthPlcyPppDomain specifies the domain name
         to use with PAP/CHAP user name operations.

         This object is only relevant while the value of the object 
         'tmnxSubAuthPlcyPppUserNameOp' is equal to 'appendDomain',
         'replaceDomain' or 'defaultDomain'."
    DEFVAL { "" }
    ::= { tmnxSubAuthPlcyEntry 27 }

tmnxSubAuthPlcyRadAuthDownTime OBJECT-TYPE
    SYNTAX      Unsigned32 (30..900)
    UNITS       "seconds"
    MAX-ACCESS  read-create
    STATUS      current
    DESCRIPTION
        "The value of tmnxSubAuthPlcyRadAuthDownTime specifies the hold down 
         time.

         If a RADIUS authentication server that was considered 'down' becomes
         responsive again, the system waits for this amount of time before
         it starts to address that server again."
    DEFVAL { 30 }
    ::= { tmnxSubAuthPlcyEntry 30 }

tmnxSubAuthPlcyUserNameOp OBJECT-TYPE
    SYNTAX      TmnxSubAuthPlcyUserNameOp
    MAX-ACCESS  read-create
    STATUS      current
    DESCRIPTION
        "The value of tmnxSubAuthPlcyUserNameOp specifies the 
         operation to perform on the user name of DHCP hosts before
         transmitting it to the RADIUS server.

         When the value is 'appendDomain', the string specified by 
         'tmnxSubAuthPlcyDomain', preceded with a '@', is appended to
         the user name; if the value of 'tmnxSubAuthPlcyDomain' is empty, 
         the domain-name string is retrieved from the local-user-database
         (TIMETRA-LOCAL-USER-DB-MIB::tmnxLocUsrDbDhcpDomainName)

         When the value is 'stripDomain', any '@' character and all subsequent
         characters are removed from the user name.

         When the value is 'replaceDomain', all characters after a '@' delimiter
         are replaced with the string specified by 'tmnxSubAuthPlcyDomain'.

         When the value is 'defaultDomain', the same action is performed as with
         'appendDomain', but only if the user name does not contain
         a domain name already.
         
         When the value is 'noOperation', the value of 
         'tmnxSubAuthPlcyUserNameAppend' is considered, for backwards  
         compatibility with release 8.0R1, 8.0R2 and 8.0R3."
    DEFVAL { noOperation }
    ::= { tmnxSubAuthPlcyEntry 31 }

tmnxSubAuthPlcyDomain OBJECT-TYPE
    SYNTAX      DisplayString (SIZE (0..128))
    MAX-ACCESS  read-create
    STATUS      current
    DESCRIPTION
        "The value of tmnxSubAuthPlcyDomain specifies the domain name
         to use with user name operations.

         This object is only relevant while the value of the object 
         'tmnxSubAuthPlcyUserNameOp' is equal to 'appendDomain',
         'replaceDomain' or 'defaultDomain'."
    DEFVAL { "" }
    ::= { tmnxSubAuthPlcyEntry 32 }

tmnxSubAuthPlcyUserNameMacFormat OBJECT-TYPE
    SYNTAX      TmnxMacSpecification (SIZE (2..7))
    MAX-ACCESS  read-create
    STATUS      current
    DESCRIPTION
        "The value of tmnxSubAuthPlcyUserNameMacFormat specifies how a MAC
         address is represented when contacting a RADIUS server.         
             
         This is only used while the value of tmnxSubAuthPlcyUserNameFormat is
         equal to 'dhcpClientVendorOpts' and if the MAC address is used 
         by default of DHCP client vendor options.
         
         Examples:
         
         'ab:'               00:0c:f1:99:85:b8  Nokia SROS style
         'XY-'               00-0C-F1-99-85-B8  IEEE canonical style 
         'mmmm.'             0002.03aa.abff     Cisco style."
    DEFVAL { "aa:" }
    ::= { tmnxSubAuthPlcyEntry 33 }
    
tmnxSubAuthPlcyRadRespAttrSelect OBJECT-TYPE
    SYNTAX      TruthValue
    MAX-ACCESS  read-create
    STATUS      obsolete
    DESCRIPTION
        "The value of tmnxSubAuthPlcyRadRespAttrSelect specifies
         if the rows in the tmnxSubRadiusAcceptTable are considered 
         to selectively accept attributes in the authentication response
         messages.

         While the value of tmnxSubAuthPlcyRadRespAttrSelect is equal to 'false',
         the rows in the tmnxSubRadiusAcceptTable associated with this 
         authentication policy are ignored, and all attributes are accepted."
    DEFVAL { false }
    ::= { tmnxSubAuthPlcyEntry 34 }

tmnxSubAuthPlcyRequestScriptPlcy OBJECT-TYPE
    SYNTAX      TNamedItemOrEmpty
    MAX-ACCESS  read-create
    STATUS      current
    DESCRIPTION
       "The value of tmnxSubAuthPlcyRequestScriptPlcy specifies
        the RADIUS script policy used to change the RADIUS attributes of the
        outgoing Access-Request messages."
    DEFVAL    { "" }
    ::= { tmnxSubAuthPlcyEntry 35 }
    
tmnxSubAuthPlcyAcceptScriptPlcy OBJECT-TYPE
    SYNTAX      TNamedItemOrEmpty
    MAX-ACCESS  read-create
    STATUS      current
    DESCRIPTION
       "The value of tmnxSubAuthPlcyAcceptScriptPlcy specifies
        the RADIUS script policy used to change the RADIUS attributes of the
        incoming Access-Accept messages."
    DEFVAL    { "" }
    ::= { tmnxSubAuthPlcyEntry 36 }
    
tmnxSubAuthPlcyCoAScriptPlcy OBJECT-TYPE
    SYNTAX      TNamedItemOrEmpty
    MAX-ACCESS  read-create
    STATUS      current
    DESCRIPTION
       "The value of tmnxSubAuthPlcyCoAScriptPlcy specifies
        the RADIUS script policy used to change the RADIUS attributes of the
        incoming Change-of-Authorization messages."
    DEFVAL    { "" }
    ::= { tmnxSubAuthPlcyEntry 37 }

tmnxSubAuthPlcyAcctSessionIdType OBJECT-TYPE
    SYNTAX      INTEGER {
                    host (1),
                    session (2)
                }
    MAX-ACCESS  read-create
    STATUS      current
    DESCRIPTION
        "The value of tmnxSubAuthPlcyAcctSessionIdType specifies
         the accounting session ID type if included in RADIUS
         authentication-request messages.
         This field is only applicable if the 'acctSessionId' bit is set in
         tmnxSubAuthPlcyInclAttributes."
    DEFVAL { host }
    ::= { tmnxSubAuthPlcyEntry 38 }

tmnxSubAuthPlcyNasPortBitspec OBJECT-TYPE
    SYNTAX      TmnxBinarySpecification
    MAX-ACCESS  read-create
    STATUS      current
    DESCRIPTION
        "The value of tmnxSubAuthPlcyNasPortBitspec specifies
         what number will be put in the RADIUS NAS-Port 
         attribute if included in RADIUS authentication-request messages.

         This field is only applicable if the 'nasPort' bit is set in
         tmnxSubAuthPlcyInclAttributes.
             
         <origin>               ::= 'o' | 'i' | 's' | 'm' | 'p' | 'v' | 'c'

         'c' - ATM VCI (Virtual Channel Identifier)
         'i' - inner VLAN ID
         'm' - MDA number
         'o' - outer VLAN ID
         'p' - port number
         's' - slot number
         'v' - ATM VPI (Virtual Path Identifier)

         Maximum 32 bits can be specified.
             
         If less than 32 bits are specified, the least significant bits are
         used and the omitted higher bits are set to zero.
             
         Example:  *12o*12i*2s01 means 'the 12 least significant bits of the
         outer VLAN ID, followed by the 12 least significant bits of the inner
         VLAN ID, followed by the two least significant bits of the slot number,
         followed by a zero and a one-bit', stored in network order in the least
         significant bits: 0000ooooooooooooiiiiiiiiiiiiss01."
    DEFVAL { "" }
    ::= { tmnxSubAuthPlcyEntry 39 }

tmnxSubAuthPlcyRadiusServerPlcy OBJECT-TYPE
    SYNTAX      TNamedItemOrEmpty
    MAX-ACCESS  read-create
    STATUS      current
    DESCRIPTION
        "The value of tmnxSubAuthPlcyRadiusServerPlcy specifies
         the RADIUS server policy as defined in 
         TIMETRA-RADIUS-MIB::tmnxRadSrvPlcyTable to be applied
         in this subscriber authentication policy."
    DEFVAL { "" }
    ::= { tmnxSubAuthPlcyEntry 40 }

tmnxSubAuthPlcyAcctStopOnFail OBJECT-TYPE
    SYNTAX      BITS {
                    onRequestFailure (0),
                    onReject         (1),
                    onAcceptFailure  (2)
                }
    MAX-ACCESS  read-create
    STATUS      current
    DESCRIPTION
        "The value of tmnxSubAuthPlcyAcctStopOnFail specifies if and in
         what failure condition a RADIUS accounting-stop message indicating
         the failure has to be sent.
         
         - onRequestFailure: RADIUS Access-Request message could not be sent 
                             (e.g. no server configured, or timeout).
         - onReject:         Reception of a RADIUS Access-Reject message.
         - onAcceptFailure:  A failure occured after the reception of a RADIUS 
                             Access-Accept message (e.g. duplicate IP 
                             address)."
    DEFVAL { { } }
    ::= { tmnxSubAuthPlcyEntry 41 }

-- --------------------------------------------------------
-- tmnxSubAuthPlcyRadServTable
-- --------------------------------------------------------
tmnxSubAuthPlcyRadServTable OBJECT-TYPE
    SYNTAX      SEQUENCE OF TmnxSubAuthPlcyRadServEntry
    MAX-ACCESS  not-accessible
    STATUS      current
    DESCRIPTION
        "The tmnxSubAuthPlcyRadServTable has an entry for each RADIUS server
         used for subscriber authentication."
    ::= { tmnxSubMgmtObjects 2 }

tmnxSubAuthPlcyRadServEntry OBJECT-TYPE
    SYNTAX      TmnxSubAuthPlcyRadServEntry
    MAX-ACCESS  not-accessible
    STATUS      current
    DESCRIPTION
        "tmnxSubAuthPlcyRadServEntry is an entry (conceptual row) in the
         tmnxSubAuthPlcyRadServTable. Each entry represents the configuration
         for a RADIUS server. Entries in this table can be created and deleted
         via SNMP SET operations to tmnxSubAuthPlcyRadServRowStatus. Entries
         have a presumed StorageType of nonVolatile."
    INDEX {tmnxSubAuthPlcyRadServPlcyName,
           tmnxSubAuthPlcyRadServIndex}
    ::= { tmnxSubAuthPlcyRadServTable 1 }

TmnxSubAuthPlcyRadServEntry ::=
    SEQUENCE {
        tmnxSubAuthPlcyRadServPlcyName   TNamedItem,
        tmnxSubAuthPlcyRadServIndex      Unsigned32,
        tmnxSubAuthPlcyRadServRowStatus  RowStatus,
        tmnxSubAuthPlcyRadLastMgmtChange TimeStamp,
        tmnxSubAuthPlcyRadServAddress    InetAddress,
        tmnxSubAuthPlcyRadServAddrType   InetAddressType,
        tmnxSubAuthPlcyRadServSecret     DisplayString,
        tmnxSubAuthPlcyRadServAuthPort   Unsigned32,
        tmnxSubAuthPlcyRadServOperState  TmnxRadiusServerOperState,
        tmnxSubAuthPlcyRadServCoAOnly    TruthValue,
        tmnxSubAuthPlcyRadServPndRqLimit TmnxRadiusPendingReqLimit,
        tmnxSubAuthPlcyRadServOutTime    Counter32,
        tmnxSubAuthPlcyRadServOvrldTime  Counter32
    }

tmnxSubAuthPlcyRadServPlcyName OBJECT-TYPE
    SYNTAX      TNamedItem
    MAX-ACCESS  not-accessible
    STATUS      current
    DESCRIPTION
        "The value of tmnxSubAuthPlcyRadServPlcyName specifies a specific
         subscriber authentication policy in tmnxSubAuthPlcyTable to which this
         radius server is connected. Row creation will be denied if no policy
         with the same name occurs in the tmnxSubAuthPlcyTable."
    ::= { tmnxSubAuthPlcyRadServEntry 1 }

tmnxSubAuthPlcyRadServIndex OBJECT-TYPE
    SYNTAX      Unsigned32 (1..16)
    MAX-ACCESS  not-accessible
    STATUS      current
    DESCRIPTION
        "The value of tmnxSubAuthPlcyRadServIndex specifies a specific radius
         server in the policy."
   ::= { tmnxSubAuthPlcyRadServEntry 2 }

tmnxSubAuthPlcyRadServRowStatus OBJECT-TYPE
    SYNTAX      RowStatus
    MAX-ACCESS  read-create
    STATUS      current
    DESCRIPTION
        "The value of tmnxSubAuthPlcyRadServRowStatus controls the creation and
         deletion of rows in the table."
    ::= { tmnxSubAuthPlcyRadServEntry 3 }

tmnxSubAuthPlcyRadLastMgmtChange OBJECT-TYPE
    SYNTAX      TimeStamp
    MAX-ACCESS  read-only
    STATUS      current
    DESCRIPTION
        "The value of tmnxSubAuthPlcyRadLastMgmtChange indicates the sysUpTime
         at the time of the most recent management-initiated change to this
         policy server."
    ::= { tmnxSubAuthPlcyRadServEntry 4 }

tmnxSubAuthPlcyRadServAddress OBJECT-TYPE
    SYNTAX      InetAddress
    MAX-ACCESS  read-create
    STATUS      current
    DESCRIPTION
        "The value of tmnxSubAuthPlcyRadServAddress specifies the IP address of
         the RADIUS server. A valid unicast IP address must be specified for row
         creation to succeed."
    ::= { tmnxSubAuthPlcyRadServEntry 5 }

tmnxSubAuthPlcyRadServAddrType OBJECT-TYPE
    SYNTAX      InetAddressType
    MAX-ACCESS  read-create
    STATUS      current
    DESCRIPTION
        "The value of tmnxSubAuthPlcyRadServAddrType specifies the type of
         address stored in tmnxSubAuthPlcyRadServAddress."
    DEFVAL { ipv4 }
    ::= { tmnxSubAuthPlcyRadServEntry 6 }

tmnxSubAuthPlcyRadServSecret OBJECT-TYPE
    SYNTAX      DisplayString (SIZE (0|1..20))
    MAX-ACCESS  read-create
    STATUS      current
    DESCRIPTION
        "The value of tmnxSubAuthPlcyRadServSecret specifies the secret key
         associated with the RADIUS server. An empty key is not accepted on
         input. An empty string is however returned by the system on any GET
         request."
    ::= { tmnxSubAuthPlcyRadServEntry 7 }

tmnxSubAuthPlcyRadServAuthPort OBJECT-TYPE
    SYNTAX      Unsigned32 (1..65535)
    MAX-ACCESS  read-create
    STATUS      current
    DESCRIPTION
        "The value of tmnxSubAuthPlcyRadServAuthPort specifies the UDP port
         number on which to contact the RADIUS server for authentication."
    DEFVAL { 1812 }
    ::= { tmnxSubAuthPlcyRadServEntry 8 }

tmnxSubAuthPlcyRadServOperState OBJECT-TYPE
    SYNTAX      TmnxRadiusServerOperState
    MAX-ACCESS  read-only
    STATUS      current
    DESCRIPTION
        "The value of tmnxSubAuthPlcyRadServOperState indicates the operational
         state of the RADIUS server."
    ::= { tmnxSubAuthPlcyRadServEntry 9 }

tmnxSubAuthPlcyRadServCoAOnly OBJECT-TYPE
    SYNTAX      TruthValue
    MAX-ACCESS  read-create
    STATUS      current
    DESCRIPTION
        "The value of tmnxSubAuthPlcyRadServCoAOnly specifies
         if this RADIUS server is restricted to sending Change-of-Authorization
         messages only (not authentication requests).
         
         There can be maximum 16 of these CoA-only servers associated with
         a single authentication policy.
         
         If the value of tmnxSubAuthPlcyRadServCoAOnly is equal to 'true', the
         value of tmnxSubAuthPlcyAcceptAuthChange is not considered anymore
         for this RADIUS server."
    REFERENCE
       "RFC 3576 Dynamic Authorization Extensions to RADIUS
        section 2.2 Change-of-Authorization Messages (CoA)."
    DEFVAL { false }
    ::= { tmnxSubAuthPlcyRadServEntry 10 }

tmnxSubAuthPlcyRadServPndRqLimit OBJECT-TYPE
    SYNTAX      TmnxRadiusPendingReqLimit
    MAX-ACCESS  read-create
    STATUS      current
    DESCRIPTION
        "The value of tmnxSubAuthPlcyRadServPndRqLimit specifies
         the limit of the number of pending RADIUS authentication
         requests for this RADIUS server."
    DEFVAL { 4096 }
    ::= { tmnxSubAuthPlcyRadServEntry 11 }

tmnxSubAuthPlcyRadServOutTime OBJECT-TYPE
    SYNTAX      Counter32
    UNITS       "seconds"
    MAX-ACCESS  read-only
    STATUS      current
    DESCRIPTION
        "The value of tmnxSubAuthPlcyRadServOutTime indicates
         the accumulated time that the value of the 
         object tmnxSubAuthPlcyRadServOperState has been equal to 'outOfService'
         since this row was created."
    ::= { tmnxSubAuthPlcyRadServEntry 12 }

tmnxSubAuthPlcyRadServOvrldTime OBJECT-TYPE
    SYNTAX      Counter32
    UNITS       "seconds"
    MAX-ACCESS  read-only
    STATUS      current
    DESCRIPTION
        "The value of tmnxSubAuthPlcyRadServOvrldTime indicates
         the accumulated time that the value of the 
         object tmnxSubAuthPlcyRadServOperState has been equal to 'overloaded'
         since this row was created."
    ::= { tmnxSubAuthPlcyRadServEntry 13 }  
    
-- --------------------------------------------------------
-- tmnxSubAuthPlcyStatsTable
-- --------------------------------------------------------
tmnxSubAuthPlcyStatsTable OBJECT-TYPE
    SYNTAX      SEQUENCE OF TmnxSubAuthPlcyStatsEntry
    MAX-ACCESS  not-accessible
    STATUS      current
    DESCRIPTION
        "The tmnxSubAuthPlcyStatsTable has an entry for each subscriber
         authentication policy configured in the system."
    ::= { tmnxSubMgmtObjects 3 }

tmnxSubAuthPlcyStatsEntry OBJECT-TYPE
    SYNTAX      TmnxSubAuthPlcyStatsEntry
    MAX-ACCESS  not-accessible
    STATUS      current
    DESCRIPTION
        "Each row entry represents a collection of statistics for a subscriber
         authentication policy in the system.

         Entries cannot be created and deleted via SNMP SET operations."
    INDEX { tmnxSubAuthPlcyName }
    ::= { tmnxSubAuthPlcyStatsTable 1 }

TmnxSubAuthPlcyStatsEntry ::=
        SEQUENCE {
            tmnxSubAuthPlcySuccess          Counter32,
            tmnxSubAuthPlcyReject           Counter32,
            tmnxSubAuthPlcyFallbackSuccess  Counter32,
            tmnxSubAuthPlcyFallbackReject   Counter32,
            tmnxSubAuthPlcySendFail         Counter32
        }

tmnxSubAuthPlcySuccess OBJECT-TYPE
    SYNTAX      Counter32
    MAX-ACCESS  read-only
    STATUS      current
    DESCRIPTION
        "The value of tmnxSubAuthPlcySuccess indicates how many subscriber
         messages (e.g. DHCP, PPPoE, ...) were authenticated successfully.
         Note that not all requests are therefore forwarded to radius. If
         several requests are sent in a short timeframe, only the first one is
         sent to radius."
    ::= { tmnxSubAuthPlcyStatsEntry 1 }

tmnxSubAuthPlcyReject OBJECT-TYPE
    SYNTAX      Counter32
    MAX-ACCESS  read-only
    STATUS      current
    DESCRIPTION
        "The value of tmnxSubAuthPlcyReject indicates how many subscriber
         messages (e.g. DHCP, PPPoE, ...) were rejected by the authentication.
         Note that not all requests are therefore forwarded to radius. If
         several requests are sent in a short timeframe, only the first one is
         sent to radius."
    ::= { tmnxSubAuthPlcyStatsEntry 2 }

tmnxSubAuthPlcyFallbackSuccess OBJECT-TYPE
    SYNTAX      Counter32
    MAX-ACCESS  read-only
    STATUS      current
    DESCRIPTION
        "The value of tmnxSubAuthPlcySuccess indicates how many subscriber
         messages (e.g. DHCP, PPPoE, ...) were authenticated successfully
         by the fallback mechanism."
    ::= { tmnxSubAuthPlcyStatsEntry 3 }

tmnxSubAuthPlcyFallbackReject OBJECT-TYPE
    SYNTAX      Counter32
    MAX-ACCESS  read-only
    STATUS      current
    DESCRIPTION
        "The value of tmnxSubAuthPlcyReject indicates how many subscriber
         messages (e.g. DHCP, PPPoE, ...) were rejected by the fallback
         mechanism."
    ::= { tmnxSubAuthPlcyStatsEntry 4 }

tmnxSubAuthPlcySendFail OBJECT-TYPE
    SYNTAX      Counter32
    MAX-ACCESS  read-only
    STATUS      current
    DESCRIPTION
        "The value of tmnxSubAuthPlcySendFail indicates how many subscriber
         messages (e.g. DHCP, PPPoE, ...) failed to be sent."
    ::= { tmnxSubAuthPlcyStatsEntry 5 }

-- --------------------------------------------------------
-- tmnxSubAuthPlcyRadStatsTable
-- --------------------------------------------------------
tmnxSubAuthPlcyRadStatsTable OBJECT-TYPE
    SYNTAX      SEQUENCE OF TmnxSubAuthPlcyRadStatsEntry
    MAX-ACCESS  not-accessible
    STATUS      current
    DESCRIPTION
        "The tmnxSubAuthPlcyStatsTable has an entry for each subscriber
         authentication policy configured in the system."
    ::= { tmnxSubMgmtObjects 4 }

tmnxSubAuthPlcyRadStatsEntry OBJECT-TYPE
    SYNTAX      TmnxSubAuthPlcyRadStatsEntry
    MAX-ACCESS  not-accessible
    STATUS      current
    DESCRIPTION
        "Each row entry represents a collection of statistics for a specific
         radius server in a subscriber authentication policy in the system.
         Entries cannot be created and deleted via SNMP SET operations."
    INDEX { tmnxSubAuthPlcyRadServPlcyName,
            tmnxSubAuthPlcyRadServIndex }
    ::= { tmnxSubAuthPlcyRadStatsTable 1 }

TmnxSubAuthPlcyRadStatsEntry ::=
    SEQUENCE {
        tmnxSubAuthPlcyRadSuccess   Counter32,
        tmnxSubAuthPlcyRadReject    Counter32,
        tmnxSubAuthPlcyRadTimeout   Counter32,
        tmnxSubAuthPlcyRadMd5Fail   Counter32,
        tmnxSubAuthPlcyRadPending   Counter32,
        tmnxSubAuthPlcyRadSendFail  Counter32,
        tmnxSubAuthPlcyRadOvrldSendFail Counter32
    }

tmnxSubAuthPlcyRadSuccess OBJECT-TYPE
    SYNTAX      Counter32
    MAX-ACCESS  read-only
    STATUS      current
    DESCRIPTION
        "The value of tmnxSubAuthPlcyRadSuccess indicates how many
         authentication requests were accepted by this radius server."
    ::= { tmnxSubAuthPlcyRadStatsEntry 1 }

tmnxSubAuthPlcyRadReject OBJECT-TYPE
    SYNTAX      Counter32
    MAX-ACCESS  read-only
    STATUS      current
    DESCRIPTION
        "The value of tmnxSubAuthPlcyRadReject indicates how many
         authentication requests were rejected by this radius server."
    ::= { tmnxSubAuthPlcyRadStatsEntry 2 }

tmnxSubAuthPlcyRadTimeout OBJECT-TYPE
    SYNTAX      Counter32
    MAX-ACCESS  read-only
    STATUS      current
    DESCRIPTION
        "The value of tmnxSubAuthPlcyRadTimeout indicates how many times this
         radius did not reply to an authentication request within the timeout."
    ::= { tmnxSubAuthPlcyRadStatsEntry 3 }

tmnxSubAuthPlcyRadMd5Fail OBJECT-TYPE
    SYNTAX      Counter32
    MAX-ACCESS  read-only
    STATUS      current
    DESCRIPTION
        "The value of tmnxSubAuthPlcyRadMd5Fail indicates how many times the
         MD5 verification failed on a msg from this radius server."
    ::= { tmnxSubAuthPlcyRadStatsEntry 4 }

tmnxSubAuthPlcyRadPending OBJECT-TYPE
    SYNTAX      Counter32
    MAX-ACCESS  read-only
    STATUS      current
    DESCRIPTION
        "The value of tmnxSubAuthPlcyRadPending indicates how many
         authentication requests are currently pending."
    ::= { tmnxSubAuthPlcyRadStatsEntry 5 }

tmnxSubAuthPlcyRadSendFail OBJECT-TYPE
    SYNTAX      Counter32
    MAX-ACCESS  read-only
    STATUS      current
    DESCRIPTION
        "The value of tmnxSubAuthPlcyRadSendFail indicates how many
         authentication requests failed because the packet could not be
         sent out."
    ::= { tmnxSubAuthPlcyRadStatsEntry 6 }

tmnxSubAuthPlcyRadOvrldSendFail OBJECT-TYPE
    SYNTAX      Counter32
    MAX-ACCESS  read-only
    STATUS      current
    DESCRIPTION
        "The value of tmnxSubAuthPlcyRadOvrldSendFail indicates how many
         authentication requests failed because the packet could not be
         sent out while the RADIUS server was in overload."
    ::= { tmnxSubAuthPlcyRadStatsEntry 7 }
-- --------------------------------------------------------
-- tmnxSubProfileTable
-- --------------------------------------------------------
tmnxSubProfileTable OBJECT-TYPE
    SYNTAX      SEQUENCE OF TmnxSubProfileEntry
    MAX-ACCESS  not-accessible
    STATUS      current
    DESCRIPTION
        "The tmnxSubProfileTable has an entry for each subscriber profile
         configured in the system."
    ::= { tmnxSubMgmtObjects 5 }

tmnxSubProfileEntry OBJECT-TYPE
    SYNTAX      TmnxSubProfileEntry
    MAX-ACCESS  not-accessible
    STATUS      current
    DESCRIPTION
        "Each row entry represents a subscriber profile configured in the
         system. Entries can be created and deleted via SNMP SET operations on
         the object tmnxSubProfRowStatus."
    INDEX { IMPLIED tmnxSubProfName }
    ::= { tmnxSubProfileTable 1 }

TmnxSubProfileEntry ::=
    SEQUENCE {
        tmnxSubProfName                  TNamedItem,
        tmnxSubProfRowStatus             RowStatus,
        tmnxSubProfLastMgmtChange        TimeStamp,
        tmnxSubProfDescription           TItemDescription,
        tmnxSubProfIngQosSchedPolicy     TNamedItemOrEmpty,
        tmnxSubProfEgrQosSchedPolicy     TNamedItemOrEmpty,
        tmnxSubProfCollectAcctStats      TruthValue,
        tmnxSubProfAccountingPolicyId    Unsigned32,
        tmnxSubProfEgrAggRateLimit       TPortSchedulerAggRateLimitPIR,
        tmnxSubProfRadiusAcctPolicy      TNamedItemOrEmpty,
        tmnxSubProfDuplRadiusAcctPolicy  TNamedItemOrEmpty,
        tmnxSubProfUseDirectSLAMapAsDef  TruthValue,
        tmnxSubProfFrameBasedAccounting  TruthValue,
        tmnxSubProfIngQosPolId           TSapIngressPolicyID,
        tmnxSubProfEgrQosPolId           TSapEgressPolicyID,
        tmnxSubProfHsmdaIngAggRateLimit  TPortSchedulerPIR,
        tmnxSubProfHsmdaEgrAggRateLimit  TPortSchedulerPIR,
        tmnxSubProfHsmdaIngPackByteOff   TIngHsmdaPerPacketOffsetOvr,
        tmnxSubProfHsmdaEgrPackByteOff   TEgrHsmdaPerPacketOffsetOvr,
        tmnxSubProfHostTrackingPolicy    TNamedItemOrEmpty,
        tmnxSubProfUseSubscriberMss      TruthValue,
        tmnxSubProfIngPolicerPolicy      TNamedItemOrEmpty,
        tmnxSubProfEgrPolicerPolicy      TNamedItemOrEmpty,
        tmnxSubProfNatPolicy             TNamedItemOrEmpty,
        tmnxSubProfIgmpPolicy            TNamedItemOrEmpty,
        tmnxSubProfEgrAvgFrameSize       INTEGER,
        tmnxSubProfEgrEncapOffsetMode    TmnxSubAleOffsetMode,  
        tmnxSubProfEgrEncapOffset        TmnxSubAleOffset,  
        tmnxSubProfSubMcacPolicy         TNamedItemOrEmpty,
        tmnxSubProfPreference            Unsigned32,
        tmnxSubProfUseDirectFltrMapAsDef TruthValue,
        tmnxSubProfHsmda2IngQosPolId     TSapIngressPolicyID,
        tmnxSubProfHsmda2EgrQosPolId     TSapEgressPolicyID,
        tmnxSubProfHsmda2EgrAggRateLimit TPortSchedulerPIR,
        tmnxSubProfHsmda2EgrQosWrrPolicy TNamedItemOrEmpty,
        tmnxSubProfHsmda2EgrPackByteOff  TEgrHsmdaPerPacketOffsetOvr,
        tmnxSubProfMldPolicy             TNamedItemOrEmpty,
        tmnxSubProfVolumeStatsType       INTEGER,
        tmnxSubProfPimPolicy             TNamedItemOrEmpty
    }

tmnxSubProfName OBJECT-TYPE
    SYNTAX      TNamedItem
    MAX-ACCESS  not-accessible
    STATUS      current
    DESCRIPTION
        "The value of tmnxSubProfName specifies the name of the subscriber
         profile."
    ::= { tmnxSubProfileEntry 1 }

tmnxSubProfRowStatus OBJECT-TYPE
    SYNTAX      RowStatus
    MAX-ACCESS  read-create
    STATUS      current
    DESCRIPTION
        "The value of tmnxSubProfRowStatus controls the creation and deletion
         of rows in this table."
    ::= { tmnxSubProfileEntry 2 }

tmnxSubProfLastMgmtChange OBJECT-TYPE
    SYNTAX      TimeStamp
    MAX-ACCESS  read-only
    STATUS      current
    DESCRIPTION
        "The value of tmnxSubProfLastMgmtChange indicates the sysUpTime at the
         time of the most recent management-initiated change to this table row."
    ::= { tmnxSubProfileEntry 3 }

tmnxSubProfDescription OBJECT-TYPE
    SYNTAX      TItemDescription
    MAX-ACCESS  read-create
    STATUS      current
    DESCRIPTION
        "The value of tmnxSubProfDescription specifies the user provided
         description of this subscriber profile."
    DEFVAL { ''H }
    ::= { tmnxSubProfileEntry 4 }

tmnxSubProfIngQosSchedPolicy OBJECT-TYPE
    SYNTAX      TNamedItemOrEmpty
    MAX-ACCESS  read-create
    STATUS      current
    DESCRIPTION
        "The value of tmnxSubProfIngQosSchedPolicy specifies the QoS ingress
         scheduler policy (from TIMETRA-QOS-MIB::tSchedulerPolicyTable)
         applicable to this subscriber profile."
    DEFVAL { ''H }
    ::= { tmnxSubProfileEntry 5 }

tmnxSubProfEgrQosSchedPolicy OBJECT-TYPE
    SYNTAX      TNamedItemOrEmpty
    MAX-ACCESS  read-create
    STATUS      current
    DESCRIPTION
        "The value of tmnxSubProfEgrQosSchedPolicy specifies the QoS egress
         scheduler policy (from TIMETRA-QOS-MIB::tSchedulerPolicyTable)
         applicable to this subscriber profile."
    DEFVAL { ''H }
    ::= { tmnxSubProfileEntry 6 }

tmnxSubProfCollectAcctStats OBJECT-TYPE
    SYNTAX      TruthValue
    MAX-ACCESS  read-create
    STATUS      current
    DESCRIPTION
        "When the value of the object tmnxSubProfCollectAcctStats is true(1)
         the agent collects accounting statistics on this subscriber profile."
    DEFVAL { false }
    ::= { tmnxSubProfileEntry 7 }

tmnxSubProfAccountingPolicyId OBJECT-TYPE
    SYNTAX      Unsigned32
    MAX-ACCESS  read-create
    STATUS      current
    DESCRIPTION
        "The value of the object tmnxSubProfAccountingPolicyId specifies the
         policy to use to collect accounting statistics on this subscriber
         profile. The value zero indicates that the agent should use the
         default accounting policy, if one exists."
    DEFVAL { 0 }
    ::= { tmnxSubProfileEntry 8 }

tmnxSubProfEgrAggRateLimit OBJECT-TYPE
    SYNTAX      TPortSchedulerAggRateLimitPIR
    UNITS       "kbps"
    MAX-ACCESS  read-create
    STATUS      current
    DESCRIPTION
        "The value of the object tmnxSubProfEgrAggRateLimit specifies the
         maximum total rate of all egress queues for this subscriber. The
         value '-1' means that there is no limit."
    DEFVAL { -1 }
    ::= { tmnxSubProfileEntry 9 }

tmnxSubProfRadiusAcctPolicy OBJECT-TYPE
    SYNTAX      TNamedItemOrEmpty
    MAX-ACCESS  read-create
    STATUS      current
    DESCRIPTION
        "The value of tmnxSubProfRadiusAcctPolicy specifies the RADIUS
         accounting policy (tmnxSubAcctPlcyTable) applicable to this
         subscriber profile."
    DEFVAL { ''H }
    ::= { tmnxSubProfileEntry 10 }

tmnxSubProfDuplRadiusAcctPolicy OBJECT-TYPE
    SYNTAX      TNamedItemOrEmpty
    MAX-ACCESS  read-create
    STATUS      current
    DESCRIPTION
        "The value of tmnxSubProfDuplRadiusAcctPolicy specifies the RADIUS
         accounting policy (tmnxSubAcctPlcyTable) to be used for generating
         duplicate accounting information."
    DEFVAL { ''H }
    ::= { tmnxSubProfileEntry 11 }

tmnxSubProfUseDirectSLAMapAsDef OBJECT-TYPE
    SYNTAX      TruthValue
    MAX-ACCESS  read-create
    STATUS      current
    DESCRIPTION
        "The value of tmnxSubProfUseDirectSLAMapAsDef specifies whether
         the provided SLA profile string is directly mapped to the SLA profile
         by default.

         If the value of this object is set to 'true(1)', the SLA profile string
         is used as the SLA profile name, when no matching
         tmnxSubProfSLAProfMapSLAString is found."
    DEFVAL { false }
    ::= { tmnxSubProfileEntry 12 }

tmnxSubProfFrameBasedAccounting OBJECT-TYPE
    SYNTAX       TruthValue
    MAX-ACCESS   read-create
    STATUS       current
    DESCRIPTION
        "The value of tmnxSubProfFrameBasedAccounting specifies whether
         to use frame-based accounting when evaluating
         tmnxSubProfEgrAggRateLimit for subscriber queues.

         If the value is 'false', the default packet-based accounting
         method will be used."
    DEFVAL { false }
    ::= { tmnxSubProfileEntry 13 }

tmnxSubProfIngQosPolId OBJECT-TYPE
    SYNTAX      TSapIngressPolicyID
    MAX-ACCESS  read-create
    STATUS      obsolete
    DESCRIPTION
        "The value of the object tmnxSubProfIngQosPolId specifies the
         SAP ingress QOS policy, where the value corresponds to
         TIMETRA-QOS-MIB::tSapIngressIndex.

         The value 1 specifies the index of the default SAP ingress
         qos policy.

         This object is obsoleted in 10.0 Release."
    DEFVAL { 1 }
    ::= { tmnxSubProfileEntry 14 }

tmnxSubProfEgrQosPolId OBJECT-TYPE
    SYNTAX      TSapEgressPolicyID
    MAX-ACCESS  read-create
    STATUS      obsolete
    DESCRIPTION
        "The value of the object tmnxSubProfEgrQosPolId specifies the
         SAP egress QOS policy, where the value corresponds to
         TIMETRA-QOS-MIB::tSapEgressIndex.

         The value 1 specifies the index of the default sap-egress
         qos policy.

         This object is obsoleted in 10.0 Release."   
    DEFVAL { 1 }
    ::= { tmnxSubProfileEntry 15 }

tmnxSubProfHsmdaIngAggRateLimit OBJECT-TYPE
    SYNTAX      TPortSchedulerPIR
    UNITS       "kbps"
    MAX-ACCESS  read-create
    STATUS      obsolete
    DESCRIPTION
        "The value of the object tmnxSubProfHsmdaIngAggRateLimit specifies the
         maximum total rate of all ingress HSMDA queues for this subscriber. The
         value '-1' means that there is no limit.

         This object is obsoleted in 10.0 Release."       
    DEFVAL { -1 }
    ::= { tmnxSubProfileEntry 16 }

tmnxSubProfHsmdaEgrAggRateLimit OBJECT-TYPE
    SYNTAX      TPortSchedulerPIR
    UNITS       "kbps"
    MAX-ACCESS  read-create
    STATUS      obsolete
    DESCRIPTION
        "The value of the object tmnxSubProfHsmdaEgrAggRateLimit specifies the
         maximum total rate of all egress HSMDA queues for this subscriber. The
         value '-1' means that there is no limit.

         This object is obsoleted in 10.0 Release."
    DEFVAL { -1 }
    ::= { tmnxSubProfileEntry 17 }

tmnxSubProfHsmdaIngPackByteOff        OBJECT-TYPE
    SYNTAX      TIngHsmdaPerPacketOffsetOvr
    UNITS       "bytes"
    MAX-ACCESS  read-create
    STATUS      obsolete
    DESCRIPTION
        "The value of tmnxSubProfHsmdaIngPackByteOff specifies the value,
         In bytes, of the adjustment for accounting to make to the size
         of each HSMDA packet on ingress. The specified value overrides
         the the value of tSapIngressHsmdaPacketOffset specified in the
         tSapIngressEntry indexed by tmnxSubProfIngQosPolId.

         A value of -128 indicates no override.

         This object is obsoleted in 10.0 Release."
    DEFVAL { -128 }
    ::= { tmnxSubProfileEntry 18 }

tmnxSubProfHsmdaEgrPackByteOff        OBJECT-TYPE
    SYNTAX      TEgrHsmdaPerPacketOffsetOvr
    UNITS       "bytes"
    MAX-ACCESS  read-create
    STATUS      obsolete
    DESCRIPTION
        "The value of tmnxSubProfHsmdaEgrPackByteOff specifies the value,
         in bytes, of the adjustment for accounting to make to the size
         of each HSMDA packet on egress. The specified value overrides
         the the value of tSapEgressHsmdaPacketOffset specified in the
         tSapEgressEntry indexed by tmnxSubProfEgrQosPolId.

         A value of -128 indicates no override.

         This object is obsoleted in 10.0 Release."
    DEFVAL { -128 }
    ::= { tmnxSubProfileEntry 19 }

tmnxSubProfHostTrackingPolicy OBJECT-TYPE
    SYNTAX      TNamedItemOrEmpty
    MAX-ACCESS  read-create
    STATUS      current
    DESCRIPTION
        "The value of tmnxSubProfHostTrackingPolicy specifies the IGMP
         host tracking policy applicable to this subscriber profile."
    DEFVAL { ''H }
    ::= { tmnxSubProfileEntry 20 }

tmnxSubProfUseSubscriberMss OBJECT-TYPE
    SYNTAX       TruthValue
   MAX-ACCESS   read-create
   STATUS       current
   DESCRIPTION
       "The value of tmnxSubProfHostTrackingPolicy specifies whether
        the subscribers will use the default multi-service site of the customer
        associated with the port on which the subscriber is applied."
   DEFVAL { false }
   ::= { tmnxSubProfileEntry 21 }

tmnxSubProfIngPolicerPolicy OBJECT-TYPE
    SYNTAX      TNamedItemOrEmpty
    MAX-ACCESS  read-create
    STATUS      current
    DESCRIPTION
        "The value of tmnxSubProfIngPolicerPolicy specifies the ingress
         policer control policy applicable to this subscriber profile."
    DEFVAL { ''H }
    ::= { tmnxSubProfileEntry 22 }

tmnxSubProfEgrPolicerPolicy OBJECT-TYPE
    SYNTAX      TNamedItemOrEmpty
    MAX-ACCESS  read-create
    STATUS      current
    DESCRIPTION
        "The value of tmnxSubProfEgrPolicerPolicy specifies the egress
         policer control policy applicable to this subscriber profile."
    DEFVAL { ''H }
    ::= { tmnxSubProfileEntry 23 }

tmnxSubProfNatPolicy OBJECT-TYPE
    SYNTAX      TNamedItemOrEmpty
    MAX-ACCESS  read-create
    STATUS      current
    DESCRIPTION
        "The value of tmnxSubProfNatPolicy specifies 
         the NAT (Network Address Translation) policy of this subscriber profile
         ."
    DEFVAL { ''H }
    ::= { tmnxSubProfileEntry 24 }

tmnxSubProfIgmpPolicy OBJECT-TYPE
    SYNTAX      TNamedItemOrEmpty
    MAX-ACCESS  read-create
    STATUS      current
    DESCRIPTION
        "The value of tmnxSubProfIgmpPolicy specifies 
         the IGMP policy of this subscriber profile
         ."
    DEFVAL { ''H }
    ::= { tmnxSubProfileEntry 25 }

tmnxSubProfEgrAvgFrameSize OBJECT-TYPE
    SYNTAX      INTEGER (0 | 64..4096)
    MAX-ACCESS  read-create
    STATUS      current
    DESCRIPTION
        "The value of tmnxSubProfEgrAvgFrameSize specifies the 
         average frame size value to be used in the adjustment of the subscriber
         aggregate rate to account for the per packet variable expansion of the
         last mile for the specific session used by the subscriber host.
         
         The value 0 will disable the adjustments and cause the value of 
         tmnxSubProfEgrEncapOffsetMode to be ignored.
         
         The value of tmnxSubProfEgrAvgFrameSize is only used for subscribers
         serviced by specific HSMDA and ignored otherwise."
    DEFVAL { 0 }
    ::= { tmnxSubProfileEntry 26 }

tmnxSubProfEgrEncapOffsetMode OBJECT-TYPE
    SYNTAX      TmnxSubAleOffsetMode
    MAX-ACCESS  read-create
    STATUS      current
    DESCRIPTION
        "The value of tmnxSubProfEgrEncapOffset specifies how 
         the fixed packet offset will be derived.
         
         This fixed packet offset will be used in the adjustment of the 
         subscriber aggregate rate, to account for the fixed offset and per 
         packet variable expansion of the last mile for the specific session 
         used by the subscriber host.
         
         The value 'none (0)' will disable the adjustments.
         
         The value 'auto (1)' will derive the fixed packet offset from the 
         encapsulation type value signaled in the Access-loop-encapsulation 
         sub-TLV in the Vendor-Specific PPPoE Tags or DHCP Relay Options 
         [rfc4679]."
    DEFVAL { none }
    ::= { tmnxSubProfileEntry 27 }

tmnxSubProfEgrEncapOffset OBJECT-TYPE
    SYNTAX      TmnxSubAleOffset
    MAX-ACCESS  read-create
    STATUS      current
    DESCRIPTION
        "The value of tmnxSubProfEgrEncapOffset specifies 
         the fixed packet offset.
         
         This fixed packet offset will be used in the adjustment of the 
         subscriber aggregate rate, to account for the fixed offset and per 
         packet variable expansion of the last mile for the specific session 
         used by the subscriber host.
         
         If the value of the object tmnxSubProfEgrEncapOffsetMode is equal to 
         'none', the offset is ignored.
         
         If the value of the object tmnxSubProfEgrEncapOffsetMode is equal to 
         'auto', the offset is used as a default value for automatic learning."
    DEFVAL { none }
    ::= { tmnxSubProfileEntry 28 }

tmnxSubProfSubMcacPolicy OBJECT-TYPE
    SYNTAX      TNamedItemOrEmpty
    MAX-ACCESS  read-create
    STATUS      current
    DESCRIPTION
        "The value of tmnxSubProfSubMcacPolicy specifies the name 
         of the multicast CAC policy.

         The multicast CAC policy applies the subscriber CAC algorithm if 
         the channel(group) of this subscriber is part of the policy as specified
         in vRtrIgmpIfMcacPolicyName."
    DEFVAL { ''H }
    ::= { tmnxSubProfileEntry 29 }

tmnxSubProfPreference OBJECT-TYPE
    SYNTAX      Unsigned32 (1..10)
    MAX-ACCESS  read-create
    STATUS      current
    DESCRIPTION
        "The value of the object tmnxSubProfPreference specifies 
         its preference with respect to other subscriber profiles.
         
         The number '1' corresponds to the lowest preference.
         
         For a given subscriber, it is possible that the current subscriber 
         profile is replaced with another one that has a higher or equal 
         preference; the current subscriber profile will never be replaced
         with another one that has a lower preference."
    DEFVAL { 5 }
    ::= { tmnxSubProfileEntry 40 }

tmnxSubProfUseDirectFltrMapAsDef OBJECT-TYPE
    SYNTAX      TruthValue
    MAX-ACCESS  read-create
    STATUS      current
    DESCRIPTION
        "The value of tmnxSubProfUseDirectFltrMapAsDef specifies whether
         the provided filter profile string is directly mapped to the
         filter profile by default.

         If the value of this object is set to 'true(1)', the filter profile
         string is used as the filter profile name, when no matching
         tmnxSPFltrProfMapFltrString is found."
    DEFVAL { false }
    ::= { tmnxSubProfileEntry 41 }

tmnxSubProfHsmda2IngQosPolId OBJECT-TYPE
    SYNTAX      TSapIngressPolicyID (1..65535)
    MAX-ACCESS  read-create
    STATUS      current
    DESCRIPTION
        "The value of the object tmnxSubProfHsmda2IngQosPolId specifies 
         the identifier of the SAP ingress QOS policy for HSMDA-2 subscribers.

         The value 1 specifies the index of the default SAP ingress
         qos policy."
    DEFVAL { 1 }
    ::= { tmnxSubProfileEntry 101 }

tmnxSubProfHsmda2EgrQosPolId OBJECT-TYPE
    SYNTAX      TSapEgressPolicyID (1..65535)
    MAX-ACCESS  read-create
    STATUS      current
    DESCRIPTION
        "The value of the object tmnxSubProfHsmda2EgrQosPolId specifies
         the identifier of the SAP egress QOS policy for HSMDA-2 subscribers.

         The value 1 specifies the index of the default sap-egress
         qos policy."
    DEFVAL { 1 }
    ::= { tmnxSubProfileEntry 102 }

tmnxSubProfHsmda2EgrAggRateLimit OBJECT-TYPE
    SYNTAX      TPortSchedulerPIR
    UNITS       "kbps"
    MAX-ACCESS  read-create
    STATUS      current
    DESCRIPTION
        "The value of the object tmnxSubProfHsmda2EgrAggRateLimit specifies the
         maximum total rate of all egress HSMDA-2 queues for this subscriber. 
         
         The value '-1' means that there is no limit."
    DEFVAL { -1 }
    ::= { tmnxSubProfileEntry 103 }

tmnxSubProfHsmda2EgrQosWrrPolicy  OBJECT-TYPE
    SYNTAX       TNamedItemOrEmpty
    MAX-ACCESS   read-create
    STATUS       current
    DESCRIPTION
        "The value of tmnxSubProfHsmda2EgrQosWrrPolicy specifies
         the HSMDA Weighted Round Robin (WRR) scheduling policy."
    DEFVAL { "" }
    ::= { tmnxSubProfileEntry 104 }

tmnxSubProfHsmda2EgrPackByteOff OBJECT-TYPE
    SYNTAX      TEgrHsmdaPerPacketOffsetOvr
    MAX-ACCESS  read-create
    STATUS      current
    DESCRIPTION
        "The value of tmnxSubProfHsmda2EgrPackByteOff specifies the packet byte
         offset for addition of policing information for the policer."
    DEFVAL { -128 }
    ::= { tmnxSubProfileEntry 105 }

tmnxSubProfMldPolicy OBJECT-TYPE
    SYNTAX      TNamedItemOrEmpty
    MAX-ACCESS  read-create
    STATUS      current
    DESCRIPTION
        "The value of tmnxSubProfMldPolicy specifies 
         the MLD policy of this subscriber profile."
    DEFVAL { ''H }
    ::= { tmnxSubProfileEntry 106 }
    
tmnxSubProfVolumeStatsType OBJECT-TYPE
    SYNTAX      INTEGER {
                    default (0),
                    ip      (1)
                }
    MAX-ACCESS  read-create
    STATUS      current
    DESCRIPTION
        "The value of tmnxSubProfVolumeStatsType specifies what volume 
         statistics are used for accounting in this subscriber profile."
    DEFVAL { default }
    ::= { tmnxSubProfileEntry 107 }
    
tmnxSubProfPimPolicy OBJECT-TYPE
    SYNTAX      TNamedItemOrEmpty
    MAX-ACCESS  read-create
    STATUS      current
    DESCRIPTION
        "The value of tmnxSubProfPimPolicy specifies
         the PIM (Protocol Independent Multicast) policy
         associated with this subscriber profile.
         
         A non-empty value must correspond to a row in the
         tmnxSubPimPlcyTable, and implicitly enables
         PIM for the subscriber hosts associated with
         this profile."
    DEFVAL { ''H }
    ::= { tmnxSubProfileEntry 108 }

-- --------------------------------------------------------
-- tmnxSubProfSchedOverrideTable
-- --------------------------------------------------------
tmnxSubProfSchedOverrideTable OBJECT-TYPE
    SYNTAX      SEQUENCE OF TmnxSubProfSchedOverrideEntry
    MAX-ACCESS  not-accessible
    STATUS      current
    DESCRIPTION
        "The tmnxSubProfSchedOverrideTable allows overriding of ingress/egress
         scheduler rates on a per subscriber profile basis."
    ::= { tmnxSubMgmtObjects 6 }

tmnxSubProfSchedOverrideEntry OBJECT-TYPE
    SYNTAX      TmnxSubProfSchedOverrideEntry
    MAX-ACCESS  not-accessible
    STATUS      current
    DESCRIPTION
        "Each entry of the tmnxSubProfSchedOverrideTable describes
         ingress/egress scheduler rates which are overridden for the subscriber
         profile indicated by tmnxSubProfName. Rows can be created and deleted
         by the operator (tmnxSubProfSchedOvrRowStatus). Rows can only be
         created for existing schedulers defined in
         TIMETRA-QOS-MIB::tVirtualSchedulerTable."
    INDEX { tmnxSubProfName,
            tmnxSubProfSchedOvrDirection,
            tSchedulerPolicyName,
            IMPLIED tVirtualSchedulerName }
    ::= { tmnxSubProfSchedOverrideTable 1 }

TmnxSubProfSchedOverrideEntry ::=
    SEQUENCE {
        tmnxSubProfSchedOvrDirection      TmnxSubDirection,
        tmnxSubProfSchedOvrRowStatus      RowStatus,
        tmnxSubProfSchedOvrLastMgmtChange TimeStamp,
        tmnxSubProfSchedOvrPIR            THPolVirtualSchePIRRate,
        tmnxSubProfSchedOvrCIR            THPolVirtualScheCIRRate,
        tmnxSubProfSchedOvrSummedCIR      TruthValue,
        tmnxSubProfSchedOvrPIRHi          Unsigned32,
        tmnxSubProfSchedOvrPIRLo          Unsigned32,
        tmnxSubProfSchedOvrCIRHi          Unsigned32,
        tmnxSubProfSchedOvrCIRLo          Unsigned32
    }

tmnxSubProfSchedOvrDirection OBJECT-TYPE
    SYNTAX      TmnxSubDirection
    MAX-ACCESS  not-accessible
    STATUS      current
    DESCRIPTION
        "The value of tmnxSubProfSchedOvrDirection indicates whether this row
         specifies ingress or egress scheduler override parameters."
    ::= { tmnxSubProfSchedOverrideEntry 1 }

tmnxSubProfSchedOvrRowStatus OBJECT-TYPE
    SYNTAX      RowStatus
    MAX-ACCESS  read-create
    STATUS      current
    DESCRIPTION
        "The value of tmnxSubProfSchedOvrRowStatus controls the creation and
         deletion of rows in this table."
    ::= { tmnxSubProfSchedOverrideEntry 2 }

tmnxSubProfSchedOvrLastMgmtChange OBJECT-TYPE
    SYNTAX      TimeStamp
    MAX-ACCESS  read-only
    STATUS      current
    DESCRIPTION
        "The value of tmnxSubProfSchedOvrLastMgmtChange indicates the sysUpTime
         at the time of the most recent management-initiated change to this
         table row."
    ::= { tmnxSubProfSchedOverrideEntry 3 }

tmnxSubProfSchedOvrPIR OBJECT-TYPE
    SYNTAX      THPolVirtualSchePIRRate
    UNITS       "kbps"
    MAX-ACCESS  read-create
    STATUS      obsolete
    DESCRIPTION
        "The value of tmnxSubProfSchedOvrPIR specifies the PIR rate in kbps
         allowed for this scheduler. This object is mandatory at creation time.

         This object is obsoleted in 11.0 Release. It is replaced by 
         tmnxSubProfSchedOvrPIRHi and tmnxSubProfSchedOvrPIRLo."
    ::= { tmnxSubProfSchedOverrideEntry 4 }

tmnxSubProfSchedOvrCIR OBJECT-TYPE
    SYNTAX      THPolVirtualScheCIRRate
    UNITS       "kbps"
    MAX-ACCESS  read-create
    STATUS      obsolete
    DESCRIPTION
        "The value of tmnxSubProfSchedOvrCIR specifies the CIR rate in kbps
         allowed for this scheduler.
         
         This object is obsoleted in 11.0 Release. It is replaced by 
         tmnxSubProfSchedOvrCIRHi and tmnxSubProfSchedOvrCIRLo."
    DEFVAL { 0 }
    ::= { tmnxSubProfSchedOverrideEntry 5 }

tmnxSubProfSchedOvrSummedCIR OBJECT-TYPE
    SYNTAX      TruthValue
    MAX-ACCESS  read-create
    STATUS      current
    DESCRIPTION
        "The value of tmnxSubProfSchedOvrSummedCIR specifies if the CIR should
         be used as the summed CIR values of the children schedulers or queues.
         If set to 'true', the applicable scheduler CIR (tmnxSubProfSchedOvrCIR)
         loses its meaning."
    DEFVAL { true }
    ::= { tmnxSubProfSchedOverrideEntry 6 }

tmnxSubProfSchedOvrPIRHi OBJECT-TYPE
    SYNTAX      Unsigned32 (0 | 4294967295)
    UNITS       "kbps"
    MAX-ACCESS  read-create
    STATUS      current
    DESCRIPTION 
        "The value of tmnxSubProfSchedOvrPIRHi indicates upper 32 bits of the
         pir-rate allowed for this scheduler.    

         This value should always be set along with tmnxSubProfSchedOvrPIRLo,
         otherwise an 'inconsistentValue' error is returned. This object is
         mandatory at creation time.

         When the value of tmnxSubProfSchedOvrPIRHi along with the value of
         tmnxSubProfSchedOvrPIRLo is set to 4294967295 (0xFFFFFFFF), rate for 
         this scheduler indicates maximum rate."
    DEFVAL { 4294967295 }
    ::= { tmnxSubProfSchedOverrideEntry 7 }

tmnxSubProfSchedOvrPIRLo OBJECT-TYPE
    SYNTAX       Unsigned32 (1..3200000000 | 4294967295)
    UNITS        "kbps"
    MAX-ACCESS   read-create
    STATUS      current
    DESCRIPTION 
        "The value of tmnxSubProfSchedOvrPIRLo indicates lower 32 bits of the
         pir-rate allowed for this scheduler.    

         This value should always be set along with tmnxSubProfSchedOvrPIRHi,
         otherwise an 'inconsistentValue' error is returned. This object is
         mandatory at creation time.

         When the value of tmnxSubProfSchedOvrPIRHi along with the value of
         tmnxSubProfSchedOvrPIRLo is set to 4294967295 (0xFFFFFFFF), rate for 
         this scheduler indicates maximum rate."
    DEFVAL { 4294967295 }
    ::= { tmnxSubProfSchedOverrideEntry 8 }

tmnxSubProfSchedOvrCIRHi OBJECT-TYPE
    SYNTAX       Unsigned32 (0 | 4294967295)
    UNITS        "kbps"
    MAX-ACCESS   read-create
    STATUS      current
    DESCRIPTION 
        "The value of tmnxSubProfSchedOvrCIRHi indicates upper 32 bits of the
         cir-rate allowed for this scheduler.    

         This value should always be set along with tmnxSubProfSchedOvrCIRLo,
         otherwise an 'inconsistentValue' error is returned. This object is
         mandatory at creation time.

         When the value of tmnxSubProfSchedOvrCIRHi along with the value of
         tmnxSubProfSchedOvrCIRLo is set to 4294967295 (0xFFFFFFFF), rate for 
         this scheduler indicates maximum rate."
    DEFVAL { 4294967295 }
    ::= { tmnxSubProfSchedOverrideEntry 9 }

tmnxSubProfSchedOvrCIRLo OBJECT-TYPE
    SYNTAX       Unsigned32 (0..3200000000 | 4294967295)
    UNITS        "kbps"
    MAX-ACCESS   read-create
    STATUS      current
    DESCRIPTION 
        "The value of tmnxSubProfSchedOvrCIRLo indicates lower 32 bits of the
         cir-rate allowed for this scheduler.    

         This value should always be set along with tmnxSubProfSchedOvrPIRHi,
         otherwise an 'inconsistentValue' error is returned. This object is
         mandatory at creation time.

         When the value of tmnxSubProfSchedOvrCIRHi along with the value of
         tmnxSubProfSchedOvrCIRLo is set to 4294967295 (0xFFFFFFFF), rate for 
         this scheduler indicates maximum rate."
    DEFVAL { 4294967295 }
    ::= { tmnxSubProfSchedOverrideEntry 10 }

-- --------------------------------------------------------
-- tmnxSubProfSLAProfileMapTable
-- --------------------------------------------------------
tmnxSubProfSLAProfileMapTable OBJECT-TYPE
    SYNTAX      SEQUENCE OF TmnxSubProfSLAProfileMapEntry
    MAX-ACCESS  not-accessible
    STATUS      current
    DESCRIPTION
        "The tmnxSubProfSLAProfileMapTable has an entry for each SLA profile
         string to SLA profile name mapping defined under a subscriber
         profile configured in the system."
    ::= { tmnxSubMgmtObjects 7 }

tmnxSubProfSLAProfileMapEntry OBJECT-TYPE
    SYNTAX      TmnxSubProfSLAProfileMapEntry
    MAX-ACCESS  not-accessible
    STATUS      current
    DESCRIPTION
        "Each row entry represents an SLA profile string to SLA profile name
         mapping defined under a subscriber profile configured in the system.
         Entries can be created and deleted via SNMP SET operations on the
         object tmnxSubProfSLAProfMapRowStatus."
    INDEX { tmnxSubProfName,
            IMPLIED tmnxSubProfSLAProfMapSLAString }
    ::= { tmnxSubProfSLAProfileMapTable 1 }

TmnxSubProfSLAProfileMapEntry ::=
    SEQUENCE {
        tmnxSubProfSLAProfMapSLAString      DisplayString,
        tmnxSubProfSLAProfMapRowStatus      RowStatus,
        tmnxSubProfSLAProfMapLastMgmtChange TimeStamp,
        tmnxSubProfSLAProfMapSLAProfile     TNamedItem
    }

tmnxSubProfSLAProfMapSLAString OBJECT-TYPE
    SYNTAX      DisplayString (SIZE (1..16))
    MAX-ACCESS  not-accessible
    STATUS      current
    DESCRIPTION
        "The value of tmnxSubProfSLAProfMapSLAString specifies the SLA
         profile string for this row."
    ::= { tmnxSubProfSLAProfileMapEntry 1 }

tmnxSubProfSLAProfMapRowStatus OBJECT-TYPE
    SYNTAX      RowStatus
    MAX-ACCESS  read-create
    STATUS      current
    DESCRIPTION
        "The value of tmnxSubProfSLAProfMapRowStatus controls the creation and
         deletion of rows in this table."
    ::= { tmnxSubProfSLAProfileMapEntry 2 }

tmnxSubProfSLAProfMapLastMgmtChange OBJECT-TYPE
    SYNTAX      TimeStamp
    MAX-ACCESS  read-only
    STATUS      current
    DESCRIPTION
        "The value of tmnxSubProfSLAProfMapLastMgmtChange indicates the
         sysUpTime at the time of the most recent management-initiated change to
         this table row."
    ::= { tmnxSubProfSLAProfileMapEntry 3 }

tmnxSubProfSLAProfMapSLAProfile OBJECT-TYPE
    SYNTAX      TNamedItem
    MAX-ACCESS  read-create
    STATUS      current
    DESCRIPTION
        "The value of tmnxSubProfSLAProfMapSLAProfile specifies the SLA
         profile name corresponding to this row."
    ::= { tmnxSubProfSLAProfileMapEntry 4 }

-- --------------------------------------------------------
-- tmnxSLAProfileTable
-- --------------------------------------------------------
tmnxSLAProfileTable OBJECT-TYPE
    SYNTAX      SEQUENCE OF TmnxSLAProfileEntry
    MAX-ACCESS  not-accessible
    STATUS      current
    DESCRIPTION
        "The tmnxSLAProfileTable has an entry for each SLA (Service Level
         Agreement) profile defined in the system."
    ::= { tmnxSubMgmtObjects 8 }

tmnxSLAProfileEntry OBJECT-TYPE
    SYNTAX      TmnxSLAProfileEntry
    MAX-ACCESS  not-accessible
    STATUS      current
    DESCRIPTION
        "Each row entry represents an SLA profile configured in the system.
         Entries can be created and deleted via SNMP SET operations on the
         object tmnxSLAProfRowStatus."
    INDEX { IMPLIED tmnxSLAProfName }
    ::= { tmnxSLAProfileTable 1 }

TmnxSLAProfileEntry ::=
    SEQUENCE {
        tmnxSLAProfName                  TNamedItem,
        tmnxSLAProfRowStatus             RowStatus,
        tmnxSLAProfLastMgmtChange        TimeStamp,
        tmnxSLAProfDescription           TItemDescription,
        tmnxSLAProfHostLimit             TmnxSubSLAProfHostLimit,
        tmnxSLAProfRemoveOldest          TruthValue,
        tmnxSLAProfIngQosPolId           TPolicyID,
        tmnxSLAProfIngSharedQPolicy      TNamedItemOrEmpty,
        tmnxSLAProfIngUseMpointShared    TruthValue,
        tmnxSLAProfIngIPFilterId         TIPFilterID,
        tmnxSLAProfEgrQosPolId           TPolicyID,
        tmnxSLAProfEgrIPFilterId         TIPFilterID,
        tmnxSLAProfCreditControlPlcy     TNamedItemOrEmpty,
        tmnxSLAProfReportIngRateType     TmnxSubReportRateType,
        tmnxSLAProfReportIngRateSched    TNamedItemOrEmpty,
        tmnxSLAProfReportEgrRateType     TmnxSubReportRateType,
        tmnxSLAProfReportEgrRateSched    TNamedItemOrEmpty,
        tmnxSLAProfEgrQosMarkingFromSap  TruthValue,
        tmnxSLAProfIngIPv6FilterId       TIPFilterID,
        tmnxSLAProfEgrIPv6FilterId       TIPFilterID,
        tmnxSLAProfEgrSchedulerType      INTEGER,
        tmnxSLAProfOTHttpRdrIpv4FltrId   TIPFilterID,
        tmnxSLAProfEgrUseIngL2tpDscp     TruthValue,
        tmnxSLAProfEgrQosSchedPolicy     TNamedItemOrEmpty,

        tmnxSLAProfHostLimV4             TmnxSubSLAProfHostLimit2,
        tmnxSLAProfHostLimV4Ppp          TmnxSubSLAProfHostLimit2,
        tmnxSLAProfHostLimV4Dhcp         TmnxSubSLAProfHostLimit2,
        tmnxSLAProfHostLimV4Arp          TmnxSubSLAProfHostLimit2,
        tmnxSLAProfHostLimV6             TmnxSubSLAProfHostLimit2,
        tmnxSLAProfHostLimV6Wan          TmnxSubSLAProfHostLimit2,
        tmnxSLAProfHostLimV6WanPppSlaac  TmnxSubSLAProfHostLimit2,
        tmnxSLAProfHostLimV6WanPppDhcp   TmnxSubSLAProfHostLimit2,
        tmnxSLAProfHostLimV6WanIpoeSlaac TmnxSubSLAProfHostLimit2,
        tmnxSLAProfHostLimV6WanIpoeDhcp  TmnxSubSLAProfHostLimit2,
        tmnxSLAProfHostLimV6Pd           TmnxSubSLAProfHostLimit2,
        tmnxSLAProfHostLimV6PdPppDhcp    TmnxSubSLAProfHostLimit2,
        tmnxSLAProfHostLimV6PdIpoeDhcp   TmnxSubSLAProfHostLimit2,
        tmnxSLAProfHostLimLac            TmnxSubSLAProfHostLimit2
    }

tmnxSLAProfName OBJECT-TYPE
    SYNTAX      TNamedItem
    MAX-ACCESS  not-accessible
    STATUS      current
    DESCRIPTION
        "The value of tmnxSLAProfName specifies the name of the SLA profile."
    ::= { tmnxSLAProfileEntry 1 }

tmnxSLAProfRowStatus OBJECT-TYPE
    SYNTAX      RowStatus
    MAX-ACCESS  read-create
    STATUS      current
    DESCRIPTION
        "The value of tmnxSLAProfRowStatus controls the creation and deletion
         of rows in this table."
    ::= { tmnxSLAProfileEntry 2 }

tmnxSLAProfLastMgmtChange OBJECT-TYPE
    SYNTAX      TimeStamp
    MAX-ACCESS  read-only
    STATUS      current
    DESCRIPTION
        "The value of tmnxSLAProfLastMgmtChange indicates the sysUpTime at
         the time of the most recent management-initiated change to this table
         row."
    ::= { tmnxSLAProfileEntry 3 }

tmnxSLAProfDescription OBJECT-TYPE
    SYNTAX      TItemDescription
    MAX-ACCESS  read-create
    STATUS      current
    DESCRIPTION
        "The value of tmnxSLAProfDescription specifies the user provided
         description of this SLA profile."
    DEFVAL { ''H }
    ::= { tmnxSLAProfileEntry 4 }

tmnxSLAProfHostLimit OBJECT-TYPE
    SYNTAX      TmnxSubSLAProfHostLimit
    MAX-ACCESS  read-create
    STATUS      current
    DESCRIPTION
        "The value of tmnxSLAProfHostLimit specifies the maximum number of
         hosts using this SLA profile."
    DEFVAL { -1 }
    ::= { tmnxSLAProfileEntry 5 }

tmnxSLAProfRemoveOldest OBJECT-TYPE
    SYNTAX      TruthValue
    MAX-ACCESS  read-create
    STATUS      current
    DESCRIPTION
        "The value of tmnxSLAProfRemoveOldest specifies whether the oldest
         subscriber host should be removed when the tmnxSLAProfHostLimit is
         hit."
    DEFVAL { false }
    ::= { tmnxSLAProfileEntry 6 }

tmnxSLAProfIngQosPolId OBJECT-TYPE
    SYNTAX      TPolicyID (1..65535)
    MAX-ACCESS  read-create
    STATUS      current
    DESCRIPTION
        "The value of tmnxSLAProfIngQosPolId specifies the ingress QoS policy
         applicable to this SLA profile. The corresponding policy is defined in
         the TIMETRA-QOS-MIB::tSapIngressTable."
    DEFVAL { 1 }
    ::= { tmnxSLAProfileEntry 7 }

tmnxSLAProfIngSharedQPolicy OBJECT-TYPE
    SYNTAX      TNamedItemOrEmpty
    MAX-ACCESS  read-create
    STATUS      current
    DESCRIPTION
        "The value of tmnxSLAProfIngSharedQPolicy specifies the ingress shared
         queue policy (found in TIMETRA-QOS-MIB::tSharedQueuePolicyTable)
         applicable to this SLA profile. When the value of this object is an
         empty string it means that the SLA profile will use individual ingress
         QoS queues, instead of the shared ones."
    DEFVAL { ''H }
    ::= { tmnxSLAProfileEntry 8 }

tmnxSLAProfIngUseMpointShared OBJECT-TYPE
    SYNTAX      TruthValue
    MAX-ACCESS  read-create
    STATUS      current
    DESCRIPTION
        "The value of tmnxSLAProfIngUseMpointShared specifies whether the
         multipoint-shared queues of the shared queue policy specified by
         tmnxSLAProfIngSharedQPolicy are used. If no shared queue policy is
         specified, this object has no meaning."
    DEFVAL { false }
    ::= { tmnxSLAProfileEntry 9 }

tmnxSLAProfIngIPFilterId OBJECT-TYPE
    SYNTAX      TIPFilterID
    MAX-ACCESS  read-create
    STATUS      current
    DESCRIPTION
        "The value of tmnxSLAProfIngIPFilterId specifies the ingress IP filter
         (from TIMETRA-FILTER-MIB::tIPFilterTable) applicable to this SLA
         profile."
    DEFVAL { 0 }
    ::= { tmnxSLAProfileEntry 10 }

tmnxSLAProfEgrQosPolId OBJECT-TYPE
    SYNTAX      TPolicyID (1..65535)
    MAX-ACCESS  read-create
    STATUS      current
    DESCRIPTION
        "The value of tmnxSLAProfEgrQosPolId specifies the egress QoS policy
         applicable to this SLA profile. The corresponding policy is defined in
         the TIMETRA-QOS-MIB::tSapEgressTable."
    DEFVAL { 1 }
    ::= { tmnxSLAProfileEntry 11 }

tmnxSLAProfEgrIPFilterId OBJECT-TYPE
    SYNTAX      TIPFilterID
    MAX-ACCESS  read-create
    STATUS      current
    DESCRIPTION
        "The value of tmnxSLAProfEgrIPFilterId specifies the egress IP filter
         (from TIMETRA-FILTER-MIB::tIPFilterTable) applicable to this SLA
         profile."
    DEFVAL { 0 }
    ::= { tmnxSLAProfileEntry 12 }

tmnxSLAProfCreditControlPlcy OBJECT-TYPE
    SYNTAX      TNamedItemOrEmpty
    MAX-ACCESS  read-create
    STATUS      current
    DESCRIPTION
        "The value of tmnxSLAProfCreditControlPlcy specifies the Credit Control
         Policy used by this SLA profile. The value specified must be defined
         in tmnxSubApCreditControlPlcyTable"
    DEFVAL { ''H }
    ::= { tmnxSLAProfileEntry 13 }

tmnxSLAProfReportIngRateType OBJECT-TYPE
    SYNTAX      TmnxSubReportRateType
    MAX-ACCESS  read-create
    STATUS      current
    DESCRIPTION
        "The value of tmnxSLAProfReportIngRateType specifies what rate will
         be reported in the L2TP RX-connect-speed attribute (AVP 38) when
         creating an L2TP LAC session."
    DEFVAL { maximum }
    ::= { tmnxSLAProfileEntry 14 }

tmnxSLAProfReportIngRateSched OBJECT-TYPE
    SYNTAX      TNamedItemOrEmpty
    MAX-ACCESS  read-create
    STATUS      current
    DESCRIPTION
        "The value of tmnxSLAProfReportIngRateSched specifies the scheduler to
         take the rate from. This object can only be set to a non-empty string
         if tmnxSLAProfReportIngRateType is set to 'namedScheduler'."
    DEFVAL { ''H }
    ::= { tmnxSLAProfileEntry 15 }

tmnxSLAProfReportEgrRateType OBJECT-TYPE
    SYNTAX      TmnxSubReportRateType
    MAX-ACCESS  read-create
    STATUS      current
    DESCRIPTION
        "The value of tmnxSLAProfReportEgrRateType specifies what rate will
         be reported in the L2TP TX-connect-speed attribute (AVP 24) when
         creating an L2TP LAC session."
    DEFVAL { maximum }
    ::= { tmnxSLAProfileEntry 16 }

tmnxSLAProfReportEgrRateSched OBJECT-TYPE
    SYNTAX      TNamedItemOrEmpty
    MAX-ACCESS  read-create
    STATUS      current
    DESCRIPTION
        "The value of tmnxSLAProfReportEgrRateSched specifies the scheduler to
         take the rate from. This object can only be set to a non-empty string
         if tmnxSLAProfReportEgrRateType is set to 'namedScheduler'."
    DEFVAL { ''H }
    ::= { tmnxSLAProfileEntry 17 }

tmnxSLAProfEgrQosMarkingFromSap OBJECT-TYPE
    SYNTAX      TruthValue
    MAX-ACCESS  read-create
    STATUS      current
    DESCRIPTION
        "The value of tmnxSLAProfEgrQosMarkingFromSap specifies which
         egress QoS marking rules are applied.
         If set to 'false', the egress Qos marking is defined in the
         sap-egress policy defined at SLA-profile level. 
         If set to 'true', QoS marking rules defined in the sap-egress
         policy associated with the given SAP are applied."
    DEFVAL { true }
    ::= { tmnxSLAProfileEntry 18 }

tmnxSLAProfIngIPv6FilterId OBJECT-TYPE
    SYNTAX      TIPFilterID
    MAX-ACCESS  read-create
    STATUS      current
    DESCRIPTION
        "The value of tmnxSLAProfIngIPv6FilterId specifies the ingress IPv6 filter
         (from TIMETRA-FILTER-MIB::tIPv6FilterTable) applicable to this SLA
         profile."
    DEFVAL { 0 }
    ::= { tmnxSLAProfileEntry 19 }

tmnxSLAProfEgrIPv6FilterId OBJECT-TYPE
    SYNTAX      TIPFilterID
    MAX-ACCESS  read-create
    STATUS      current
    DESCRIPTION
        "The value of tmnxSLAProfEgrIPv6FilterId specifies the egress IPv6 filter
         (from TIMETRA-FILTER-MIB::tIPv6FilterTable) applicable to this SLA
         profile."
    DEFVAL { 0 }
    ::= { tmnxSLAProfileEntry 20 }

tmnxSLAProfEgrSchedulerType OBJECT-TYPE
    SYNTAX      INTEGER {
        portScheduler  (1),
        vportScheduler (2)
    }
    MAX-ACCESS  read-create
    STATUS      current
    DESCRIPTION
        "The value of tmnxSLAProfEgrSchedulerType specifies the type of 
         scheduling for queued traffic.
         
         If set to 'portScheduler (1)' the subscriber host queues will be 
         parented to the port scheduler.
         
         If set to 'vportScheduler (2)' the subscriber host queues will be 
         parented to a virtual port, which  will be derived by performing
         a lookup with the subscriber host's intermediate destination id
         and organization string in the
         TIMETRA-PORT-MIB::tPortEgrVPortHostMatchTable."
    DEFVAL { portScheduler }
    ::= { tmnxSLAProfileEntry 21 }

tmnxSLAProfOTHttpRdrIpv4FltrId OBJECT-TYPE
    SYNTAX      TIPFilterID
    MAX-ACCESS  read-create
    STATUS      current
    DESCRIPTION
        "The value of tmnxSLAProfOTHttpRdrIpv4FltrId specifies the one-time
         HTTP redirection IP filter (from TIMETRA-FILTER-MIB::tIPFilterTable)
         applicable to this SLA profile."
    DEFVAL { 0 }
    ::= { tmnxSLAProfileEntry 22 }

tmnxSLAProfEgrUseIngL2tpDscp OBJECT-TYPE
    SYNTAX      TruthValue
    MAX-ACCESS  read-create
    STATUS      current
    DESCRIPTION
        "The value of tmnxSLAProfEgrUseIngL2tpDscp specifies
         if the DSCP value found in the L2TP header of ingress traffic
         of PPP subscribers must be used to get the Forwarding Class
         for egress reclassification."
    DEFVAL { false }
    ::= { tmnxSLAProfileEntry 26 }

tmnxSLAProfEgrQosSchedPolicy OBJECT-TYPE
    SYNTAX      TNamedItemOrEmpty
    MAX-ACCESS  read-create
    STATUS      current
    DESCRIPTION
        "The value of tmnxSLAProfEgrQosSchedPolicy specifies the QoS egress
         scheduler policy (from TIMETRA-QOS-MIB::tSchedulerPolicyTable)
         applicable to this SLA profile."
    DEFVAL { ''H }
    ::= { tmnxSLAProfileEntry 27 }
    
tmnxSLAProfHostLimV4 OBJECT-TYPE
    SYNTAX      TmnxSubSLAProfHostLimit2
    MAX-ACCESS  read-create
    STATUS      current
    DESCRIPTION
        "The value of tmnxSLAProfHostLimV4 specifies the maximum  
         number of IPv4 hosts overall."
    DEFVAL { -1 }
    ::= { tmnxSLAProfileEntry 28 }

tmnxSLAProfHostLimV4Ppp OBJECT-TYPE
    SYNTAX      TmnxSubSLAProfHostLimit2
    MAX-ACCESS  read-create
    STATUS      current
    DESCRIPTION
        "The value of tmnxSLAProfHostLimV4Ppp specifies the maximum 
         number of IPv4 PPP hosts."
    DEFVAL { -1 }
    ::= { tmnxSLAProfileEntry 29 }

tmnxSLAProfHostLimV4Dhcp OBJECT-TYPE
    SYNTAX      TmnxSubSLAProfHostLimit2
    MAX-ACCESS  read-create
    STATUS      current
    DESCRIPTION
        "The value of tmnxSLAProfHostLimV4Dhcp specifies the maximum 
         number of IPv4 DHCP hosts."
    DEFVAL { -1 }
    ::= { tmnxSLAProfileEntry 30 }

tmnxSLAProfHostLimV4Arp OBJECT-TYPE
    SYNTAX      TmnxSubSLAProfHostLimit2
    MAX-ACCESS  read-create
    STATUS      current
    DESCRIPTION
        "The value of tmnxSLAProfHostLimV4Arp specifies the maximum 
         number of IPv4 ARP hosts."
    DEFVAL { -1 }
    ::= { tmnxSLAProfileEntry 31 }

tmnxSLAProfHostLimV6 OBJECT-TYPE
    SYNTAX      TmnxSubSLAProfHostLimit2
    MAX-ACCESS  read-create
    STATUS      current
    DESCRIPTION
        "The value of tmnxSLAProfHostLimV6 specifies the maximum
         number of IPv6 hosts overall."
    DEFVAL { -1 }
    ::= { tmnxSLAProfileEntry 32 }

tmnxSLAProfHostLimV6Wan OBJECT-TYPE
    SYNTAX      TmnxSubSLAProfHostLimit2
    MAX-ACCESS  read-create
    STATUS      current
    DESCRIPTION
        "The value of tmnxSLAProfHostLimV6Wan specifies the maximum
         number of IPv6-WAN hosts overall."
    DEFVAL { -1 }
    ::= { tmnxSLAProfileEntry 33 }

tmnxSLAProfHostLimV6WanPppSlaac OBJECT-TYPE
    SYNTAX      TmnxSubSLAProfHostLimit2
    MAX-ACCESS  read-create
    STATUS      current
    DESCRIPTION
        "The value of tmnxSLAProfHostLimV6WanPppSlaac specifies the maximum
         number of IPv6-WAN PPP SLAAC hosts."
    DEFVAL { -1 }
    ::= { tmnxSLAProfileEntry 34 }

tmnxSLAProfHostLimV6WanPppDhcp OBJECT-TYPE
    SYNTAX      TmnxSubSLAProfHostLimit2
    MAX-ACCESS  read-create
    STATUS      current
    DESCRIPTION
        "The value of tmnxSLAProfHostLimV6WanPppDhcp specifies the maximum
         number of IPv6-WAN PPP DHCP hosts."
    DEFVAL { -1 }
    ::= { tmnxSLAProfileEntry 35 }

tmnxSLAProfHostLimV6WanIpoeSlaac OBJECT-TYPE
    SYNTAX      TmnxSubSLAProfHostLimit2
    MAX-ACCESS  read-create
    STATUS      current
    DESCRIPTION
        "The value of tmnxSLAProfHostLimV6WanIpoeSlaac specifies the maximum
         number of IPv6-WAN IPOE SLAAC hosts."
    DEFVAL { -1 }
    ::= { tmnxSLAProfileEntry 36 }

tmnxSLAProfHostLimV6WanIpoeDhcp OBJECT-TYPE
    SYNTAX      TmnxSubSLAProfHostLimit2
    MAX-ACCESS  read-create
    STATUS      current
    DESCRIPTION
        "The value of tmnxSLAProfHostLimV6WanIpoeDhcp specifies the maximum
         number of IPv6-WAN IPOE DHCP hosts."
    DEFVAL { -1 }
    ::= { tmnxSLAProfileEntry 37 }

tmnxSLAProfHostLimV6Pd OBJECT-TYPE
    SYNTAX      TmnxSubSLAProfHostLimit2
    MAX-ACCESS  read-create
    STATUS      current
    DESCRIPTION
        "The value of tmnxSLAProfHostLimV6Pd specifies the maximum
         number of IPv6-PD hosts overall."
    DEFVAL { -1 }
    ::= { tmnxSLAProfileEntry 38 }

tmnxSLAProfHostLimV6PdPppDhcp OBJECT-TYPE
    SYNTAX      TmnxSubSLAProfHostLimit2
    MAX-ACCESS  read-create
    STATUS      current
    DESCRIPTION
        "The value of tmnxSLAProfHostLimV6PdPppDhcp specifies the maximum
         number of IPv6-PD PPP DHCP hosts."
    DEFVAL { -1 }
    ::= { tmnxSLAProfileEntry 39 }

tmnxSLAProfHostLimV6PdIpoeDhcp OBJECT-TYPE
    SYNTAX      TmnxSubSLAProfHostLimit2
    MAX-ACCESS  read-create
    STATUS      current
    DESCRIPTION
        "The value of tmnxSLAProfHostLimV6PdIpoeDhcp specifies the maximum
         number of IPv6-PD IPOE DHCP hosts."
    DEFVAL { -1 }
    ::= { tmnxSLAProfileEntry 40 }

tmnxSLAProfHostLimLac OBJECT-TYPE
    SYNTAX      TmnxSubSLAProfHostLimit2
    MAX-ACCESS  read-create
    STATUS      current
    DESCRIPTION
        "The value of tmnxSLAProfHostLimLac specifies the maximum
         number of L2TP LAC hosts."
    DEFVAL { -1 }
    ::= { tmnxSLAProfileEntry 41 }


-- --------------------------------------------------------
-- tmnxSLAIngQueueOverrideTable
-- --------------------------------------------------------
tmnxSLAIngQueueOverrideTable OBJECT-TYPE
    SYNTAX      SEQUENCE OF TmnxSLAIngQueueOverrideEntry
    MAX-ACCESS  not-accessible
    STATUS      current
    DESCRIPTION
        "The tmnxSLAIngQueueOverrideTable allows overriding of ingress QoS
         policy queue parameters on a per SLA profile basis."
    ::= { tmnxSubMgmtObjects 9 }

tmnxSLAIngQueueOverrideEntry OBJECT-TYPE
    SYNTAX      TmnxSLAIngQueueOverrideEntry
    MAX-ACCESS  not-accessible
    STATUS      current
    DESCRIPTION
        "Each entry of the tmnxSLAIngQueueOverrideTable describes queue
         parameters which override the corresponding template queue parameters
         from the specified ingress QoS policy. Rows can be created and deleted
         by the operator (tmnxSLAIngQueueOvrRowStatus). Rows can only be created
         for queues that exist in table TIMETRA-QOS-MIB::tSapIngressQueueTable."
    INDEX { tmnxSLAProfName,
            tSapIngressIndex,
            tSapIngressQueue }
    ::= { tmnxSLAIngQueueOverrideTable 1 }

TmnxSLAIngQueueOverrideEntry ::=
    SEQUENCE {
        tmnxSLAIngQueueOvrRowStatus      RowStatus,
        tmnxSLAIngQueueOvrLastMgmtChange TimeStamp,
        tmnxSLAIngQueueOvrPIR            TQosQueuePIRRateOverride,
        tmnxSLAIngQueueOvrCIR            TQosQueueCIRRateOverride,
        tmnxSLAIngQueueOvrMBS            TmnxSubOvrBurstSize,
        tmnxSLAIngQueueOvrCBS            TmnxSubOvrBurstSize,
        tmnxSLAIngQueueOvrHiPrioOnly     TmnxSubOvrBurstPercent,
        tmnxSLAIngQueueOvrMBSBytes       TBurstSizeBytesOvr,
        tmnxSLAIngQueueOvrStatMode       INTEGER
    }

tmnxSLAIngQueueOvrRowStatus OBJECT-TYPE
    SYNTAX      RowStatus
    MAX-ACCESS  read-create
    STATUS      current
    DESCRIPTION
        "The value of tmnxSLAIngQueueOvrRowStatus controls the creation and
         deletion of rows in this table."
    ::= { tmnxSLAIngQueueOverrideEntry 1 }

tmnxSLAIngQueueOvrLastMgmtChange OBJECT-TYPE
    SYNTAX      TimeStamp
    MAX-ACCESS  read-only
    STATUS      current
    DESCRIPTION
        "The value of tmnxSLAIngQueueOvrLastMgmtChange indicates the sysUpTime
         at the time of the most recent management-initiated change to this
         table row."
    ::= { tmnxSLAIngQueueOverrideEntry 2 }

tmnxSLAIngQueueOvrPIR OBJECT-TYPE
    SYNTAX       TQosQueuePIRRateOverride
    UNITS       "kbps"
    MAX-ACCESS  read-create
    STATUS      current
    DESCRIPTION
        "The value of tmnxSLAIngQueueOvrPIR specifies the PIR rate in kbps
         allowed for this queue."
    DEFVAL { -2 }
    ::= { tmnxSLAIngQueueOverrideEntry 3 }

tmnxSLAIngQueueOvrCIR OBJECT-TYPE
    SYNTAX       TQosQueueCIRRateOverride
    UNITS       "kbps"
    MAX-ACCESS  read-create
    STATUS      current
    DESCRIPTION
        "The value of tmnxSLAIngQueueOvrCIR specifies the CIR rate in kbps
         allowed for this queue."
    DEFVAL { -2 }
    ::= { tmnxSLAIngQueueOverrideEntry 4 }

tmnxSLAIngQueueOvrMBS OBJECT-TYPE
    SYNTAX      TmnxSubOvrBurstSize
    UNITS       "kbytes"
    MAX-ACCESS  read-create
    STATUS      obsolete
    DESCRIPTION
        "The value of tmnxSLAIngQueueOvrMBS specifies the maximum amount of
         buffer space (in kbytes) allowed for the queue."
    DEFVAL { -2 }
    ::= { tmnxSLAIngQueueOverrideEntry 5 }

tmnxSLAIngQueueOvrCBS OBJECT-TYPE
    SYNTAX      TmnxSubOvrBurstSize
    UNITS       "kbytes"
    MAX-ACCESS  read-create
    STATUS      current
    DESCRIPTION
        "The value of tmnxSLAIngQueueOvrCBS specifies the amount of reserved
         buffer space (in kbytes) for the queue."
    DEFVAL { -2 }
    ::= { tmnxSLAIngQueueOverrideEntry 6 }

tmnxSLAIngQueueOvrHiPrioOnly OBJECT-TYPE
    SYNTAX      TmnxSubOvrBurstPercent
    UNITS       "percent"
    MAX-ACCESS  read-create
    STATUS      current
    DESCRIPTION
        "The value of tmnxSLAIngQueueOvrHiPrioOnly specifies the percentage of
         buffer space for the queue, used exclusively by high priority packets."
    DEFVAL { -2 }
    ::= { tmnxSLAIngQueueOverrideEntry 7 }

tmnxSLAIngQueueOvrMBSBytes OBJECT-TYPE
    SYNTAX      TBurstSizeBytesOvr
    UNITS       "bytes"
    MAX-ACCESS  read-create
    STATUS      current
    DESCRIPTION
        "The value of tmnxSLAIngQueueOvrMBSBytes specifies the maximum amount of
         buffer space (bytes) allowed for the queue."
    DEFVAL { -2 }
    ::= { tmnxSLAIngQueueOverrideEntry 8 }

tmnxSLAIngQueueOvrStatMode  OBJECT-TYPE
    SYNTAX      INTEGER {
                    noOverride              (-1),
                    v4V6                    (0)
                 }
    MAX-ACCESS  read-create
    STATUS      current
    DESCRIPTION
        "The value of tmnxSLAIngQueueOvrStatMode specifies the mode of
         statistics collected for the queue.
         
         A value of 'v4V6(0)' indicates seperate counters are collected
         for IPv4 and IPv6 instead of the normal queue statistics."
    DEFVAL { noOverride }
    ::= { tmnxSLAIngQueueOverrideEntry 9 }
        
-- --------------------------------------------------------
-- tmnxSLAEgrQueueOverrideTable
-- --------------------------------------------------------
tmnxSLAEgrQueueOverrideTable OBJECT-TYPE
    SYNTAX      SEQUENCE OF TmnxSLAEgrQueueOverrideEntry
    MAX-ACCESS  not-accessible
    STATUS      current
    DESCRIPTION
        "The tmnxSLAEgrQueueOverrideTable allows overriding of egress QoS
         policy queue parameters on a per SLA profile basis."
    ::= { tmnxSubMgmtObjects 10 }

tmnxSLAEgrQueueOverrideEntry OBJECT-TYPE
    SYNTAX      TmnxSLAEgrQueueOverrideEntry
    MAX-ACCESS  not-accessible
    STATUS      current
    DESCRIPTION
        "Each entry of the tmnxSLAEgrQueueOverrideEntry describes queue
         parameters which override the corresponding template queue parameters
         from the specified egress QoS policy. Rows can be created and deleted
         by the operator (tmnxSLAEgrQueueOvrRowStatus). Rows can only be created
         for queues that exist in table TIMETRA-QOS-MIB::tSapEgressQueueTable."
    INDEX { tmnxSLAProfName,
            tSapEgressIndex,
            tSapEgressQueueIndex }
    ::= { tmnxSLAEgrQueueOverrideTable 1 }

TmnxSLAEgrQueueOverrideEntry ::=
    SEQUENCE {
        tmnxSLAEgrQueueOvrRowStatus      RowStatus,
        tmnxSLAEgrQueueOvrLastMgmtChange TimeStamp,
        tmnxSLAEgrQueueOvrPIR            TQosQueuePIRRateOverride,
        tmnxSLAEgrQueueOvrCIR            TQosQueueCIRRateOverride,
        tmnxSLAEgrQueueOvrMBS            TmnxSubOvrBurstSize,
        tmnxSLAEgrQueueOvrCBS            TmnxSubOvrBurstSize,
        tmnxSLAEgrQueueOvrHiPrioOnly     TmnxSubOvrBurstPercent,
        tmnxSLAEgrQueueOvrAvgOverhead    Integer32,
        tmnxSLAEgrQueueOvrMBSBytes       TBurstSizeBytesOvr,
        tmnxSLAEgrQueueOvrStatMode       INTEGER
    }

tmnxSLAEgrQueueOvrRowStatus OBJECT-TYPE
    SYNTAX      RowStatus
    MAX-ACCESS  read-create
    STATUS      current
    DESCRIPTION
        "The value of tmnxSLAEgrQueueOvrRowStatus controls the creation and
         deletion of rows in this table."
    ::= { tmnxSLAEgrQueueOverrideEntry 1 }

tmnxSLAEgrQueueOvrLastMgmtChange OBJECT-TYPE
    SYNTAX      TimeStamp
    MAX-ACCESS  read-only
    STATUS      current
    DESCRIPTION
        "The value of tmnxSLAEgrQueueOvrLastMgmtChange indicates the sysUpTime
         at the time of the most recent management-initiated change to this
         table row."
    ::= { tmnxSLAEgrQueueOverrideEntry 2 }

tmnxSLAEgrQueueOvrPIR OBJECT-TYPE
    SYNTAX       TQosQueuePIRRateOverride
    UNITS       "kbps"
    MAX-ACCESS  read-create
    STATUS      current
    DESCRIPTION
        "The value of tmnxSLAEgrQueueOvrPIR specifies the PIR rate in kbps
         allowed for this queue."
    DEFVAL { -2 }
    ::= { tmnxSLAEgrQueueOverrideEntry 3 }

tmnxSLAEgrQueueOvrCIR OBJECT-TYPE
    SYNTAX       TQosQueueCIRRateOverride
    UNITS       "kbps"
    MAX-ACCESS  read-create
    STATUS      current
    DESCRIPTION
        "The value of tmnxSLAEgrQueueOvrCIR specifies the CIR rate in kbps
         allowed for this queue."
    DEFVAL { -2 }
    ::= { tmnxSLAEgrQueueOverrideEntry 4 }

tmnxSLAEgrQueueOvrMBS OBJECT-TYPE
    SYNTAX      TmnxSubOvrBurstSize
    UNITS       "kbytes"
    MAX-ACCESS  read-create
    STATUS      obsolete
    DESCRIPTION
        "The value of tmnxSLAEgrQueueOvrMBS specifies the maximum amount of
         buffer space (in kbytes) allowed for the queue."
    DEFVAL { -2 }
    ::= { tmnxSLAEgrQueueOverrideEntry 5 }

tmnxSLAEgrQueueOvrCBS OBJECT-TYPE
    SYNTAX      TmnxSubOvrBurstSize
    UNITS       "kbytes"
    MAX-ACCESS  read-create
    STATUS      current
    DESCRIPTION
        "The value of tmnxSLAEgrQueueOvrCBS specifies the amount of reserved
         buffer space (in kbytes) for the queue."
    DEFVAL { -2 }
    ::= { tmnxSLAEgrQueueOverrideEntry 6 }

tmnxSLAEgrQueueOvrHiPrioOnly OBJECT-TYPE
    SYNTAX      TmnxSubOvrBurstPercent
    UNITS       "percent"
    MAX-ACCESS  read-create
    STATUS      current
    DESCRIPTION
        "The value of tmnxSLAEgrQueueOvrHiPrioOnly specifies the percentage of
         buffer space for the queue, used exclusively by high priority packets."
    DEFVAL { -2 }
    ::= { tmnxSLAEgrQueueOverrideEntry 7 }

tmnxSLAEgrQueueOvrAvgOverhead      OBJECT-TYPE
    SYNTAX      Integer32 (-2|0..10000)
    MAX-ACCESS  read-create
    STATUS      current
    DESCRIPTION
        "The value of tmnxSLAEgrQueueOvrAvgOverhead specifies the
         encapsulation overhead, in hundredths of a percent,  used to
         translate packet-based rate to frame-based rate and vice versa.
         The value '-2' indicates that the value is not overridden."
    DEFVAL      { -2 }
    ::= { tmnxSLAEgrQueueOverrideEntry 8 }

tmnxSLAEgrQueueOvrMBSBytes OBJECT-TYPE
    SYNTAX      TBurstSizeBytesOvr
    UNITS       "bytes"
    MAX-ACCESS  read-create
    STATUS      current
    DESCRIPTION
        "The value of tmnxSLAEgrQueueOvrMBSBytes specifies the maximum amount of
         buffer space (in bytes) allowed for the queue."
    DEFVAL { -2 }
    ::= { tmnxSLAEgrQueueOverrideEntry 9 }

tmnxSLAEgrQueueOvrStatMode  OBJECT-TYPE
    SYNTAX       INTEGER {
                    noOverride              (-1),
                    v4V6                    (0)
                 }
    MAX-ACCESS  read-create
    STATUS      current
    DESCRIPTION
        "The value of tmnxSLAEgrQueueOvrStatMode specifies the mode of
         statistics collected for the queue.
         
         A value of 'v4V6(0)' indicates seperate counters are collected
         for IPv4 and IPv6 instead of the normal queue statistics."
    DEFVAL { noOverride }
    ::= { tmnxSLAEgrQueueOverrideEntry 10 }
        
-- --------------------------------------------------------
-- tmnxSubExplicitMapTable
-- --------------------------------------------------------
tmnxSubExplicitMapTable OBJECT-TYPE
    SYNTAX      SEQUENCE OF TmnxSubExplicitMapEntry
    MAX-ACCESS  not-accessible
    STATUS      current
    DESCRIPTION
        "The tmnxSubExplicitMapTable has an entry for each subscriber
         identification string mapping configured in the system."
    ::= { tmnxSubMgmtObjects 13 }

tmnxSubExplicitMapEntry OBJECT-TYPE
    SYNTAX      TmnxSubExplicitMapEntry
    MAX-ACCESS  not-accessible
    STATUS      current
    DESCRIPTION
        "Each row entry represents a subscriber identification string mapping
         configured in the system. Entries can be created and deleted via SNMP
         SET operations on the object tmnxSubExplicitMapRowStatus."
    INDEX { IMPLIED tmnxSubExplicitMapSubIdent }
    ::= { tmnxSubExplicitMapTable 1 }

TmnxSubExplicitMapEntry ::=
    SEQUENCE {
        tmnxSubExplicitMapSubIdent       DisplayString,
        tmnxSubExplicitMapRowStatus      RowStatus,
        tmnxSubExplicitMapLastMgmtChange TimeStamp,
        tmnxSubExplicitMapSubProfile     TNamedItemOrEmpty,
        tmnxSubExplicitMapSLAProfile     TNamedItemOrEmpty,
        tmnxSubExplicitMapAlias          DisplayString,
        tmnxSubExplicitMapAppProfile     TNamedItemOrEmpty
    }

tmnxSubExplicitMapSubIdent OBJECT-TYPE
    SYNTAX      DisplayString (SIZE (1..32))
    MAX-ACCESS  not-accessible
    STATUS      current
    DESCRIPTION
        "The value of tmnxSubExplicitMapSubIdent specifies the subscriber
         identification string for this row."
    ::= { tmnxSubExplicitMapEntry 1 }

tmnxSubExplicitMapRowStatus OBJECT-TYPE
    SYNTAX      RowStatus
    MAX-ACCESS  read-create
    STATUS      current
    DESCRIPTION
        "The value of tmnxSubExplicitMapRowStatus controls the creation and
         deletion of rows in this table."
    ::= { tmnxSubExplicitMapEntry 2 }

tmnxSubExplicitMapLastMgmtChange OBJECT-TYPE
    SYNTAX      TimeStamp
    MAX-ACCESS  read-only
    STATUS      current
    DESCRIPTION
        "The value of tmnxSubExplicitMapLastMgmtChange indicates the sysUpTime
         at the time of the most recent management-initiated change to this
         table row."
    ::= { tmnxSubExplicitMapEntry 3 }

tmnxSubExplicitMapSubProfile OBJECT-TYPE
    SYNTAX      TNamedItemOrEmpty
    MAX-ACCESS  read-create
    STATUS      current
    DESCRIPTION
        "The value of tmnxSubExplicitMapSubProfile specifies the subscriber
         profile corresponding to this row."
    DEFVAL { ''H }
    ::= { tmnxSubExplicitMapEntry 4 }

tmnxSubExplicitMapSLAProfile OBJECT-TYPE
    SYNTAX      TNamedItemOrEmpty
    MAX-ACCESS  read-create
    STATUS      current
    DESCRIPTION
        "The value of tmnxSubExplicitMapSLAProfile specifies the SLA
         profile corresponding to this row."
    DEFVAL { ''H }
    ::= { tmnxSubExplicitMapEntry 5 }

tmnxSubExplicitMapAlias OBJECT-TYPE
    SYNTAX      DisplayString (SIZE (0..64))
    MAX-ACCESS  read-create
    STATUS      current
    DESCRIPTION
        "The value of tmnxSubExplicitMapAlias specifies an alias for the
         subscriber identification string."
    DEFVAL { ''H }
    ::= { tmnxSubExplicitMapEntry 6 }

tmnxSubExplicitMapAppProfile OBJECT-TYPE
    SYNTAX      TNamedItemOrEmpty
    MAX-ACCESS  read-create
    STATUS      current
    DESCRIPTION
        "The value of tmnxSubExplicitMapAppProfile specifies the
         application profile corresponding to this row.

         The application profile is configured in
         TIMETRA-BSX-NG-MIB.mib::tmnxBsxAppProfTable."
    DEFVAL { ''H }
    ::= { tmnxSubExplicitMapEntry 7 }

-- --------------------------------------------------------
-- tmnxSubIdentPolicyTable
-- --------------------------------------------------------
tmnxSubIdentPolicyTable OBJECT-TYPE
    SYNTAX      SEQUENCE OF TmnxSubIdentPolicyEntry
    MAX-ACCESS  not-accessible
    STATUS      current
    DESCRIPTION
        "The tmnxSubIdentPolicyTable has an entry for each subscriber
         identification policy configured in the system."
    ::= { tmnxSubMgmtObjects 14 }

tmnxSubIdentPolicyEntry OBJECT-TYPE
    SYNTAX      TmnxSubIdentPolicyEntry
    MAX-ACCESS  not-accessible
    STATUS      current
    DESCRIPTION
        "Each row entry represents a subscriber identification policy
         configured in the system. Entries can be created and deleted via SNMP
         SET operations on the object tmnxSubIPolRowStatus."
    INDEX { IMPLIED tmnxSubIPolName }
    ::= { tmnxSubIdentPolicyTable 1 }

TmnxSubIdentPolicyEntry ::=
    SEQUENCE {
        tmnxSubIPolName                 TNamedItem,
        tmnxSubIPolRowStatus            RowStatus,
        tmnxSubIPolLastMgmtChange       TimeStamp,
        tmnxSubIPolDescription          TItemDescription,
        tmnxSubIPolScript1URL           TmnxDisplayStringURL,
        tmnxSubIPolScript1AdminState    TmnxSubAdminStatus,
        tmnxSubIPolScript1OperState     TmnxSubOperStatus,
        tmnxSubIPolScript2URL           TmnxDisplayStringURL,
        tmnxSubIPolScript2AdminState    TmnxSubAdminStatus,
        tmnxSubIPolScript2OperState     TmnxSubOperStatus,
        tmnxSubIPolScript3URL           TmnxDisplayStringURL,
        tmnxSubIPolScript3AdminState    TmnxSubAdminStatus,
        tmnxSubIPolScript3OperState     TmnxSubOperStatus,
        tmnxSubIPolUseDirectSubMapAsDef TruthValue,
        tmnxSubIPolUseDirectSLAMapAsDef TruthValue,
        tmnxSubIPolUseDirectAppMapAsDef TruthValue,
        tmnxSubIPolStringsFromOption    Unsigned32,
        tmnxSubIPolUseDirectFltrMapAsDef TruthValue,
        tmnxSubIPolRejectUnknownStrings TruthValue
    }

tmnxSubIPolName OBJECT-TYPE
    SYNTAX      TNamedItem
    MAX-ACCESS  not-accessible
    STATUS      current
    DESCRIPTION
        "The value of tmnxSubIPolName specifies the name of the subscriber
         identification policy."
    ::= { tmnxSubIdentPolicyEntry 1 }

tmnxSubIPolRowStatus OBJECT-TYPE
    SYNTAX      RowStatus
    MAX-ACCESS  read-create
    STATUS      current
    DESCRIPTION
        "The value of tmnxSubIPolRowStatus controls the creation and deletion
         of rows in this table."
    ::= { tmnxSubIdentPolicyEntry 2 }

tmnxSubIPolLastMgmtChange OBJECT-TYPE
    SYNTAX      TimeStamp
    MAX-ACCESS  read-only
    STATUS      current
    DESCRIPTION
        "The value of tmnxSubIPolLastMgmtChange indicates the sysUpTime at the
         time of the most recent management-initiated change to this table row."
    ::= { tmnxSubIdentPolicyEntry 3 }

tmnxSubIPolDescription OBJECT-TYPE
    SYNTAX      TItemDescription
    MAX-ACCESS  read-create
    STATUS      current
    DESCRIPTION
        "The value of tmnxSubIPolDescription specifies the user provided
         description of this subscriber identification policy."
    DEFVAL { ''H }
    ::= { tmnxSubIdentPolicyEntry 4 }

tmnxSubIPolScript1URL OBJECT-TYPE
    SYNTAX      TmnxDisplayStringURL
    MAX-ACCESS  read-create
    STATUS      current
    DESCRIPTION
        "The value of tmnxSubIPolScript1URL specifies the URL of the primary
         identification script."
    DEFVAL { ''H }
    ::= { tmnxSubIdentPolicyEntry 5 }

tmnxSubIPolScript1AdminState OBJECT-TYPE
    SYNTAX      TmnxSubAdminStatus
    MAX-ACCESS  read-create
    STATUS      current
    DESCRIPTION
        "The value of tmnxSubIPolScript1AdminState specifies the administrative
         state of the primary identification script."
    DEFVAL { disabled }
    ::= { tmnxSubIdentPolicyEntry 6 }

tmnxSubIPolScript1OperState OBJECT-TYPE
    SYNTAX      TmnxSubOperStatus
    MAX-ACCESS  read-only
    STATUS      current
    DESCRIPTION
        "The value of tmnxSubIPolScript1OperState indicates the operational
         state of the primary identification script."
    ::= { tmnxSubIdentPolicyEntry 7 }

tmnxSubIPolScript2URL OBJECT-TYPE
    SYNTAX      TmnxDisplayStringURL
    MAX-ACCESS  read-create
    STATUS      current
    DESCRIPTION
        "The value of tmnxSubIPolScript2URL specifies the URL of the secondary
         identification script."
    DEFVAL { ''H }
    ::= { tmnxSubIdentPolicyEntry 8 }

tmnxSubIPolScript2AdminState OBJECT-TYPE
    SYNTAX      TmnxSubAdminStatus
    MAX-ACCESS  read-create
    STATUS      current
    DESCRIPTION
        "The value of tmnxSubIPolScript2AdminState specifies the administrative
         state of the secondary identification script."
    DEFVAL { disabled }
    ::= { tmnxSubIdentPolicyEntry 9 }

tmnxSubIPolScript2OperState OBJECT-TYPE
    SYNTAX      TmnxSubOperStatus
    MAX-ACCESS  read-only
    STATUS      current
    DESCRIPTION
        "The value of tmnxSubIPolScript2OperState indicates the operational
         state of the secondary identification script."
    ::= { tmnxSubIdentPolicyEntry 10 }

tmnxSubIPolScript3URL OBJECT-TYPE
    SYNTAX      TmnxDisplayStringURL
    MAX-ACCESS  read-create
    STATUS      current
    DESCRIPTION
        "The value of tmnxSubIPolScript3URL specifies the URL of the tertiary
         identification script."
    DEFVAL { ''H }
    ::= { tmnxSubIdentPolicyEntry 11 }

tmnxSubIPolScript3AdminState OBJECT-TYPE
    SYNTAX      TmnxSubAdminStatus
    MAX-ACCESS  read-create
    STATUS      current
    DESCRIPTION
        "The value of tmnxSubIPolScript3AdminState specifies the administrative
         state of the tertiary identification script."
    DEFVAL { disabled }
    ::= { tmnxSubIdentPolicyEntry 12 }

tmnxSubIPolScript3OperState OBJECT-TYPE
    SYNTAX      TmnxSubOperStatus
    MAX-ACCESS  read-only
    STATUS      current
    DESCRIPTION
        "The value of tmnxSubIPolScript3OperState indicates the operational
         state of the tertiary identification script."
    ::= { tmnxSubIdentPolicyEntry 13 }

tmnxSubIPolUseDirectSubMapAsDef OBJECT-TYPE
    SYNTAX      TruthValue
    MAX-ACCESS  read-create
    STATUS      current
    DESCRIPTION
        "The value of tmnxSubIPolUseDirectSubMapAsDef specifies whether
         the provided subscriber profile string is directly mapped to the
         subscriber profile name by default.

         If the value of this object is set to 'true(1)', the subscriber profile
         string is used as the subscriber profile name, when no matching
         tmnxSubIPolSubProfMapSubString is found."
    DEFVAL { false }
    ::= { tmnxSubIdentPolicyEntry 14 }

tmnxSubIPolUseDirectSLAMapAsDef OBJECT-TYPE
    SYNTAX      TruthValue
    MAX-ACCESS  read-create
    STATUS      current
    DESCRIPTION
        "The value of tmnxSubIPolUseDirectSLAMapAsDef specifies whether
         the provided SLA profile string is directly mapped to the SLA profile
         by default.

         If the value of this object is set to 'true(1)', the SLA profile string
         is used as the SLA profile name, when no matching
         tmnxSubIPolSLAProfMapSLAString is found."
    DEFVAL { false }
    ::= { tmnxSubIdentPolicyEntry 15 }

tmnxSubIPolUseDirectAppMapAsDef OBJECT-TYPE
    SYNTAX      TruthValue
    MAX-ACCESS  read-create
    STATUS      current
    DESCRIPTION
        "The value of tmnxSubIPolUseDirectAppMapAsDef specifies whether
         the provided application profile string is directly mapped to
         the application profile by default.

         If the value of this object is set to 'true(1)', the application
         profile string is used as the application profile name, when no
         matching tmnxSubIPolAppProfMapAppString is found."
    DEFVAL { false }
    ::= { tmnxSubIdentPolicyEntry 16 }

tmnxSubIPolStringsFromOption OBJECT-TYPE
    SYNTAX      Unsigned32 (0|1..254)
    MAX-ACCESS  read-create
    STATUS      current
    DESCRIPTION
        "The value of tmnxSubIPolStringsFromOption specifies the option
         number in the DHCP acknowledgement packet where to take the
         identification strings from.

         If the value of this object is set to 0, the identification strings
         are derived using the identification scripts. If the value is set
         to non-0, the strings are taken directly from the specified option
         without using the identification scripts."
    DEFVAL { 0 }
    ::= { tmnxSubIdentPolicyEntry 17 }

tmnxSubIPolUseDirectFltrMapAsDef OBJECT-TYPE
    SYNTAX      TruthValue
    MAX-ACCESS  read-create
    STATUS      current
    DESCRIPTION
        "The value of tmnxSubIPolUseDirectFltrMapAsDef specifies whether
         the provided filter profile string is directly mapped to the filter
         profile by default.

         If the value of this object is set to 'true(1)', the filter profile
         string is used as the filter profile name, when no matching
         tmnxSubIPolFltrProfMapFltrString is found."
    DEFVAL { false }
    ::= { tmnxSubIdentPolicyEntry 18 }

tmnxSubIPolRejectUnknownStrings OBJECT-TYPE
    SYNTAX      TruthValue
    MAX-ACCESS  read-create
    STATUS      current
    DESCRIPTION
        "The value of tmnxSubIPolRejectUnknownStrings specifies 
         if unknown subscriber strings are explicitly rejected by the system.
         
         If the value of tmnxSubIPolRejectUnknownStrings is equal to 'false',
         the system silently recovers using a known string that may be different
         from the current string used by the subscriber.
         
         If the value of tmnxSubIPolRejectUnknownStrings is equal to 'true',
         unknown strings are refused with an error message, and the subscriber
         strings are not modified."
    DEFVAL { false }
    ::= { tmnxSubIdentPolicyEntry 22 }

-- --------------------------------------------------------
-- tmnxSubIPolSubProfileMapTable
-- --------------------------------------------------------
tmnxSubIPolSubProfileMapTable OBJECT-TYPE
    SYNTAX      SEQUENCE OF TmnxSubIPolSubProfileMapEntry
    MAX-ACCESS  not-accessible
    STATUS      current
    DESCRIPTION
        "The tmnxSubIPolSubProfileMapTable has an entry for each subscriber
         profile string to subscriber profile name mapping defined under a
         subscriber identification policy configured in the system."
    ::= { tmnxSubMgmtObjects 15 }

tmnxSubIPolSubProfileMapEntry OBJECT-TYPE
    SYNTAX      TmnxSubIPolSubProfileMapEntry
    MAX-ACCESS  not-accessible
    STATUS      current
    DESCRIPTION
        "Each row entry represents a subscriber profile string to subscriber
         profile name mapping defined under a subscriber identification policy
         configured in the system. Entries can be created and deleted via SNMP
         SET operations on the object tmnxSubIPolSubProfMapRowStatus."
    INDEX { tmnxSubIPolName,
            IMPLIED tmnxSubIPolSubProfMapSubString }
    ::= { tmnxSubIPolSubProfileMapTable 1 }

TmnxSubIPolSubProfileMapEntry ::=
    SEQUENCE {
        tmnxSubIPolSubProfMapSubString      DisplayString,
        tmnxSubIPolSubProfMapRowStatus      RowStatus,
        tmnxSubIPolSubProfMapLastMgmtChange TimeStamp,
        tmnxSubIPolSubProfMapSubProfile     TNamedItem
    }

tmnxSubIPolSubProfMapSubString OBJECT-TYPE
    SYNTAX      DisplayString (SIZE (1..16))
    MAX-ACCESS  not-accessible
    STATUS      current
    DESCRIPTION
        "The value of tmnxSubIPolSubProfMapSubString specifies the subscriber
         profile string for this row."
    ::= { tmnxSubIPolSubProfileMapEntry 1 }

tmnxSubIPolSubProfMapRowStatus OBJECT-TYPE
    SYNTAX      RowStatus
    MAX-ACCESS  read-create
    STATUS      current
    DESCRIPTION
        "The value of tmnxSubIPolSubProfMapRowStatus controls the creation and
         deletion of rows in this table."
    ::= { tmnxSubIPolSubProfileMapEntry 2 }

tmnxSubIPolSubProfMapLastMgmtChange OBJECT-TYPE
    SYNTAX      TimeStamp
    MAX-ACCESS  read-only
    STATUS      current
    DESCRIPTION
        "The value of tmnxSubIPolSubProfMapLastMgmtChange indicates the
         sysUpTime at the time of the most recent management-initiated change to
         this table row."
    ::= { tmnxSubIPolSubProfileMapEntry 3 }

tmnxSubIPolSubProfMapSubProfile OBJECT-TYPE
    SYNTAX      TNamedItem
    MAX-ACCESS  read-create
    STATUS      current
    DESCRIPTION
        "The value of tmnxSubIPolSubProfMapSubProfile specifies the subscriber
         profile name corresponding to this row."
    ::= { tmnxSubIPolSubProfileMapEntry 4 }

-- --------------------------------------------------------
-- tmnxSubIPolSLAProfileMapTable
-- --------------------------------------------------------
tmnxSubIPolSLAProfileMapTable OBJECT-TYPE
    SYNTAX      SEQUENCE OF TmnxSubIPolSLAProfileMapEntry
    MAX-ACCESS  not-accessible
    STATUS      current
    DESCRIPTION
        "The tmnxSubIPolSLAProfileMapTable has an entry for each SLA profile
         string to SLA profile name mapping defined under a subscriber
         identification policy configured in the system."
    ::= { tmnxSubMgmtObjects 16 }

tmnxSubIPolSLAProfileMapEntry OBJECT-TYPE
    SYNTAX      TmnxSubIPolSLAProfileMapEntry
    MAX-ACCESS  not-accessible
    STATUS      current
    DESCRIPTION
        "Each row entry represents an SLA profile string to SLA profile name
         mapping defined under a subscriber identification policy configured in
         the system. Entries can be created and deleted via SNMP SET operations
         on the object tmnxSubIPolSLAProfMapRowStatus."
    INDEX { tmnxSubIPolName,
            IMPLIED tmnxSubIPolSLAProfMapSLAString }
    ::= { tmnxSubIPolSLAProfileMapTable 1 }

TmnxSubIPolSLAProfileMapEntry ::=
    SEQUENCE {
        tmnxSubIPolSLAProfMapSLAString      DisplayString,
        tmnxSubIPolSLAProfMapRowStatus      RowStatus,
        tmnxSubIPolSLAProfMapLastMgmtChange TimeStamp,
        tmnxSubIPolSLAProfMapSLAProfile     TNamedItem
    }

tmnxSubIPolSLAProfMapSLAString OBJECT-TYPE
    SYNTAX      DisplayString (SIZE (1..16))
    MAX-ACCESS  not-accessible
    STATUS      current
    DESCRIPTION
        "The value of tmnxSubIPolSLAProfMapSLAString specifies the SLA
         profile string for this row."
    ::= { tmnxSubIPolSLAProfileMapEntry 1 }

tmnxSubIPolSLAProfMapRowStatus OBJECT-TYPE
    SYNTAX      RowStatus
    MAX-ACCESS  read-create
    STATUS      current
    DESCRIPTION
        "The value of tmnxSubIPolSLAProfMapRowStatus controls the creation and
         deletion of rows in this table."
    ::= { tmnxSubIPolSLAProfileMapEntry 2 }

tmnxSubIPolSLAProfMapLastMgmtChange OBJECT-TYPE
    SYNTAX      TimeStamp
    MAX-ACCESS  read-only
    STATUS      current
    DESCRIPTION
        "The value of tmnxSubIPolSLAProfMapLastMgmtChange indicates the
         sysUpTime at the time of the most recent management-initiated change to
         this table row."
    ::= { tmnxSubIPolSLAProfileMapEntry 3 }

tmnxSubIPolSLAProfMapSLAProfile OBJECT-TYPE
    SYNTAX      TNamedItem
    MAX-ACCESS  read-create
    STATUS      current
    DESCRIPTION
        "The value of tmnxSubIPolSLAProfMapSLAProfile specifies the SLA
         profile name corresponding to this row."
    ::= { tmnxSubIPolSLAProfileMapEntry 4 }

-- --------------------------------------------------------
-- tmnxSubIPolAppProfileMapTable
-- --------------------------------------------------------
tmnxSubIPolAppProfileMapTable OBJECT-TYPE
    SYNTAX      SEQUENCE OF TmnxSubIPolAppProfileMapEntry
    MAX-ACCESS  not-accessible
    STATUS      current
    DESCRIPTION
        "The tmnxSubIPolAppProfileMapTable has an entry for each application
         profile string to application profile name mapping defined under a
         subscriber identification policy configured in the system."
    ::= { tmnxSubMgmtObjects 31 }

tmnxSubIPolAppProfileMapEntry OBJECT-TYPE
    SYNTAX      TmnxSubIPolAppProfileMapEntry
    MAX-ACCESS  not-accessible
    STATUS      current
    DESCRIPTION
        "Each row entry represents an application profile string to
         application profile name mapping defined under a subscriber
         identification policy configured in the system. Entries can
         be created and deleted via SNMP SET operations on the object
         tmnxSubIPolAppProfMapRowStatus."
    INDEX { tmnxSubIPolName,
            IMPLIED tmnxSubIPolAppProfMapAppString }
    ::= { tmnxSubIPolAppProfileMapTable 1 }

TmnxSubIPolAppProfileMapEntry ::=
    SEQUENCE {
        tmnxSubIPolAppProfMapAppString      DisplayString,
        tmnxSubIPolAppProfMapRowStatus      RowStatus,
        tmnxSubIPolAppProfMapLastMgmtChange TimeStamp,
        tmnxSubIPolAppProfMapAppProfile     TNamedItem
    }

tmnxSubIPolAppProfMapAppString OBJECT-TYPE
    SYNTAX      DisplayString (SIZE (1..16))
    MAX-ACCESS  not-accessible
    STATUS      current
    DESCRIPTION
        "The value of tmnxSubIPolAppProfMapAppString specifies the
         application profile string for this row."
    ::= { tmnxSubIPolAppProfileMapEntry 1 }

tmnxSubIPolAppProfMapRowStatus OBJECT-TYPE
    SYNTAX      RowStatus
    MAX-ACCESS  read-create
    STATUS      current
    DESCRIPTION
        "The value of tmnxSubIPolAppProfMapRowStatus controls the creation and
         deletion of rows in this table."
    ::= { tmnxSubIPolAppProfileMapEntry 2 }

tmnxSubIPolAppProfMapLastMgmtChange OBJECT-TYPE
    SYNTAX      TimeStamp
    MAX-ACCESS  read-only
    STATUS      current
    DESCRIPTION
        "The value of tmnxSubIPolAppProfMapLastMgmtChange indicates the
         sysUpTime at the time of the most recent management-initiated
         change to this table row."
    ::= { tmnxSubIPolAppProfileMapEntry 3 }

tmnxSubIPolAppProfMapAppProfile OBJECT-TYPE
    SYNTAX      TNamedItem
    MAX-ACCESS  read-create
    STATUS      current
    DESCRIPTION
        "The value of tmnxSubIPolAppProfMapAppProfile specifies the
         application profile name corresponding to this row.  Application
         profiles are configured in TIMETRA-BSX-NG-MIB::tmnxBsxAppProfTable"
    ::= { tmnxSubIPolAppProfileMapEntry 4 }

-- ----------------------------------------
-- tmnxSubscriberInfoTable
-- ----------------------------------------
tmnxSubscriberInfoTable OBJECT-TYPE
    SYNTAX      SEQUENCE OF TmnxSubscriberInfoEntry
    MAX-ACCESS  not-accessible
    STATUS      current
    DESCRIPTION
        "The tmnxSubscriberInfoTable has an entry for each subscriber found in
         the system."
    ::= { tmnxSubMgmtObjects 17 }

tmnxSubscriberInfoEntry OBJECT-TYPE
    SYNTAX      TmnxSubscriberInfoEntry
    MAX-ACCESS  not-accessible
    STATUS      current
    DESCRIPTION
        "Each row entry contains information about a particular subscriber
         available in the system."
    INDEX { IMPLIED tmnxSubInfoSubIdent }
    ::= { tmnxSubscriberInfoTable 1 }

TmnxSubscriberInfoEntry ::=
    SEQUENCE {
        tmnxSubInfoSubIdent             DisplayString,
        tmnxSubInfoSubProfile           TNamedItem,
        tmnxSubInfoSubAncpString        TmnxAncpStringOrZero,
        tmnxSubInfoNumSubProfileChanges Unsigned32,
        tmnxSubInfoIntermediateDestId   DisplayString,
        tmnxSubInfoAppProfile           TNamedItemOrEmpty,
        tmnxSubInfoEgrSecShaper         INTEGER,
        tmnxSubInfoMssCustId            TmnxCustId,
        tmnxSubInfoMssName              TNamedItemOrEmpty,
        tmnxSubInfoRadEgrAggRateLimit   TPIRRateOverride,
        tmnxSubInfoEgrAggRateLimit      TPIRRateOverride,
        tmnxSubInfoQos                  TmnxMdaQos
    }

tmnxSubInfoSubIdent OBJECT-TYPE
    SYNTAX      DisplayString (SIZE (1..32))
    MAX-ACCESS  not-accessible
    STATUS      current
    DESCRIPTION
        "The value of tmnxSubInfoSubIdent specifies the subscriber
         identification of this subscriber."
    ::= { tmnxSubscriberInfoEntry 1 }

tmnxSubInfoSubProfile OBJECT-TYPE
    SYNTAX      TNamedItem
    MAX-ACCESS  read-only
    STATUS      current
    DESCRIPTION
        "The value of tmnxSubInfoSubProfile indicates the subscriber
         profile (found in tmnxSubProfileTable) used by this subscriber."
    ::= { tmnxSubscriberInfoEntry 2 }

tmnxSubInfoSubAncpString OBJECT-TYPE
    SYNTAX      TmnxAncpStringOrZero
    MAX-ACCESS  read-only
    STATUS      current
    DESCRIPTION
        "The value of tmnxSubInfoSubAncpString indicates the ancp string
         corresponding to this subscriber id."
    ::= { tmnxSubscriberInfoEntry 3 }

tmnxSubInfoNumSubProfileChanges OBJECT-TYPE
    SYNTAX      Unsigned32
    MAX-ACCESS  read-only
    STATUS      current
    DESCRIPTION
        "The value of tmnxSubInfoNumSubProfileChanges indicates the number of
         times tmnxSubInfoSubProfile has changed.

         A high value of this object could indicate a problem with the
         subscriber identification policy (e.g. when two or more lease states
         belonging to the same subscriber evaluate to a different subscriber
         profile name)."
    ::= { tmnxSubscriberInfoEntry 4 }

tmnxSubInfoIntermediateDestId OBJECT-TYPE
    SYNTAX      DisplayString (SIZE (0..32))
    MAX-ACCESS  read-only
    STATUS      current
    DESCRIPTION
        "The value of tmnxSubInfoIntermediateDestId indicates the intermediate
         destination identifier corresponding to this subscriber id."
    ::= { tmnxSubscriberInfoEntry 5 }

tmnxSubInfoAppProfile OBJECT-TYPE
    SYNTAX      TNamedItemOrEmpty
    MAX-ACCESS  read-only
    STATUS      current
    DESCRIPTION
        "The value of tmnxSubInfoAppProfile indicates the application
         profile used by this subscriber.  Application profiles are in
         TIMETRA-BSX-NG-MIB::tmnxBsxAppProfTable"
    ::= { tmnxSubscriberInfoEntry 6 }

tmnxSubInfoEgrSecShaper OBJECT-TYPE
    SYNTAX      INTEGER {
                          unused    (0),
                          default   (1),
                          intDestId (2)
                }
    MAX-ACCESS  read-only
    STATUS      current
    DESCRIPTION
        "The value of tmnxSubInfoEgrSecShaper indicates the interpretation
         of the tmnxSubInfoIntermediateDestId object. A value 'unused',
         indicates that this subscriber is on a non-HSMDA MDA and the value
         of tmnxSubInfoIntermediateDestId is unused. A value of 'default'
         indicates that the default secondary shaper will be used for the
         subscriber. A value of 'intDestId' indicates that the value of
         tmnxSubInfoIntermediateDestId indicates the secondary shaper that
         will be used for this subscriber."
    ::= { tmnxSubscriberInfoEntry 7 }

tmnxSubInfoMssCustId OBJECT-TYPE
    SYNTAX      TmnxCustId
    MAX-ACCESS  read-only
    STATUS      current
    DESCRIPTION
        "The value of tmnxSubInfoMssCustId indicates the customer-id of the
         customer in which the multi-service-site specified in 
         tmnxSubInfoMssName is defined."
    ::= { tmnxSubscriberInfoEntry 8 }

tmnxSubInfoMssName OBJECT-TYPE
    SYNTAX      TNamedItemOrEmpty
    MAX-ACCESS  read-only
    STATUS      current
    DESCRIPTION
        "The value of tmnxSubInfoMssName indicates the name of the
         multi-service-site used by this subscriber."
    ::= { tmnxSubscriberInfoEntry 9 }
    
tmnxSubInfoRadEgrAggRateLimit OBJECT-TYPE
    SYNTAX      TPIRRateOverride
    MAX-ACCESS  read-only
    STATUS      current
    DESCRIPTION
        "The value of tmnxSubInfoRadEgrAggRateLimit indicates the egress aggregate
         rate limit override received by RADIUS."
    ::= { tmnxSubscriberInfoEntry 10 }

tmnxSubInfoEgrAggRateLimit OBJECT-TYPE
    SYNTAX      TPIRRateOverride
    MAX-ACCESS  read-only
    STATUS      current
    DESCRIPTION
        "The value of tmnxSubInfoEgrAggRateLimit indicates 
         the intended egress aggregate rate limit, regardless of its origin."
    ::= { tmnxSubscriberInfoEntry 11 }

tmnxSubInfoQos OBJECT-TYPE
    SYNTAX      TmnxMdaQos
    MAX-ACCESS  read-only
    STATUS      current
    DESCRIPTION
        "The value of tmnxSubInfoQos indicates the Quality of Service model
         associated with this subscriber.
         
         It is determined by the MDA (Media Dependent Adapter) of the
         subscriber hosts."
    ::= { tmnxSubscriberInfoEntry 12 }

-- ----------------------------------------
-- tmnxSubHostInfoTable
-- ----------------------------------------
tmnxSubHostInfoTable OBJECT-TYPE
    SYNTAX      SEQUENCE OF TmnxSubHostInfoEntry
    MAX-ACCESS  not-accessible
    STATUS      obsolete
    DESCRIPTION
        "The tmnxSubHostInfoTable has an entry for each subscriber host found in
         the system."
    ::= { tmnxSubMgmtObjects 18 }

tmnxSubHostInfoEntry OBJECT-TYPE
    SYNTAX      TmnxSubHostInfoEntry
    MAX-ACCESS  not-accessible
    STATUS      obsolete
    DESCRIPTION
        "Each row entry contains information about a particular subscriber host
         available in the system."
    INDEX { svcId,
            sapPortId,
            sapEncapValue,
            tmnxSubHostInfoIpAddressType,
            tmnxSubHostInfoIpAddress,
            tmnxSubHostInfoMacAddress }
    ::= { tmnxSubHostInfoTable 1 }

TmnxSubHostInfoEntry ::=
    SEQUENCE {
        tmnxSubHostInfoIpAddressType InetAddressType,
        tmnxSubHostInfoIpAddress     InetAddress,
        tmnxSubHostInfoMacAddress    MacAddress,
        tmnxSubHostInfoSubIdent      DisplayString,
        tmnxSubHostInfoSubProfile    TNamedItemOrEmpty,
        tmnxSubHostInfoSLAProfile    TNamedItemOrEmpty,
        tmnxSubHostInfoOrigin        TmnxSubHostOrigin,
        tmnxSubHostInfoRetailerSvcId TmnxServId,
        tmnxSubHostInfoRetailerIf    InterfaceIndexOrZero,
        tmnxSubHostInfoFwdingState   TmnxOperState,
        tmnxSubHostInfoAppProfile    TNamedItemOrEmpty
    }

tmnxSubHostInfoIpAddressType OBJECT-TYPE
    SYNTAX      InetAddressType
    MAX-ACCESS  not-accessible
    STATUS      obsolete
    DESCRIPTION
        "The value of tmnxSubHostInfoIpAddressType specifies the type of address
         stored in tmnxSubHostInfoIpAddress."
    ::= { tmnxSubHostInfoEntry 1 }

tmnxSubHostInfoIpAddress OBJECT-TYPE
    SYNTAX      InetAddress
    MAX-ACCESS  not-accessible
    STATUS      obsolete
    DESCRIPTION
        "The value of tmnxSubHostInfoIpAddress specifies the IP address of this
         subscriber host."
    ::= { tmnxSubHostInfoEntry 2 }

tmnxSubHostInfoMacAddress OBJECT-TYPE
    SYNTAX      MacAddress
    MAX-ACCESS  not-accessible
    STATUS      obsolete
    DESCRIPTION
        "The value of tmnxSubHostInfoMacAddress specifies the MAC address of
         this subscriber host."
    ::= { tmnxSubHostInfoEntry 3 }

tmnxSubHostInfoSubIdent OBJECT-TYPE
    SYNTAX      DisplayString
    MAX-ACCESS  read-only
    STATUS      obsolete
    DESCRIPTION
        "The value of tmnxSubHostInfoSubIdent indicates the subscriber
         identification applicable for this subscriber host. If subscriber
         management is disabled for the corresponding SAP (see
         TIMETRA-SAP-MIB::sapSubMgmtAdminStatus), this object may contain an
         empty string."
    ::= { tmnxSubHostInfoEntry 4 }

tmnxSubHostInfoSubProfile OBJECT-TYPE
    SYNTAX      TNamedItemOrEmpty
    MAX-ACCESS  read-only
    STATUS      obsolete
    DESCRIPTION
        "The value of tmnxSubHostInfoSubProfile indicates the subscriber profile
         (found in tmnxSubProfileTable) used by this subscriber host. If
         subscriber management is disabled for the corresponding SAP (see
         TIMETRA-SAP-MIB::sapSubMgmtAdminStatus), this object will contain an
         empty string."
    ::= { tmnxSubHostInfoEntry 5 }

tmnxSubHostInfoSLAProfile OBJECT-TYPE
    SYNTAX      TNamedItemOrEmpty
    MAX-ACCESS  read-only
    STATUS      obsolete
    DESCRIPTION
        "The value of tmnxSubHostInfoSLAProfile indicates the SLA profile (found
         in tmnxSLAProfileTable) used by this subscriber host. If
         subscriber management is disabled for the corresponding SAP (see
         TIMETRA-SAP-MIB::sapSubMgmtAdminStatus), this object will contain an
         empty string."
    ::= { tmnxSubHostInfoEntry 6 }

tmnxSubHostInfoOrigin OBJECT-TYPE
    SYNTAX      TmnxSubHostOrigin
    MAX-ACCESS  read-only
    STATUS      obsolete
    DESCRIPTION
        "The value of tmnxSubHostInfoOrigin indicates the origin of this
         subscriber host."
    ::= { tmnxSubHostInfoEntry 7 }

tmnxSubHostInfoRetailerSvcId OBJECT-TYPE
    SYNTAX          TmnxServId
    MAX-ACCESS      read-only
    STATUS          obsolete
    DESCRIPTION
        "The value of tmnxSubHostInfoRetailerSvcId indicates the service ID of
         the retailer VPRN service to which this subscriber host belongs. When
         this object is non zero, the subscriber host belongs to a
         retailer VPRN."
    ::= { tmnxSubHostInfoEntry 8 }

tmnxSubHostInfoRetailerIf       OBJECT-TYPE
    SYNTAX          InterfaceIndexOrZero
    MAX-ACCESS      read-only
    STATUS          obsolete
    DESCRIPTION
        "The value of tmnxSubHostInfoRetailerIf indicates the interface index
         of the retailer VPRN interface to which this subscriber host belongs.
         When this object is non zero, the subscriber host belongs to a retailer
         VPRN."
    ::= { tmnxSubHostInfoEntry 9 }

tmnxSubHostInfoFwdingState      OBJECT-TYPE
    SYNTAX          TmnxOperState
    MAX-ACCESS      read-only
    STATUS          obsolete
    DESCRIPTION
        "The value of tmnxSubHostInfoFwdingState indicates the forwarding state
         of this subscriber host. When the value is 'outOfService', host traffic
         is not forwarded. When it is 'inService', host traffic is forwarded."
    ::= { tmnxSubHostInfoEntry 10 }

tmnxSubHostInfoAppProfile OBJECT-TYPE
    SYNTAX      TNamedItemOrEmpty
    MAX-ACCESS  read-only
    STATUS      obsolete
    DESCRIPTION
        "The value of tmnxSubHostInfoAppProfile indicates the application
         profile (found in TIMETRA-BSX-NG-MIB::tmnxBsxAppProfTable) used by
         this subscriber host. If subscriber management is disabled for the
         corresponding SAP (see TIMETRA-SAP-MIB::sapSubMgmtAdminStatus),
         this object will contain an empty string."
    ::= { tmnxSubHostInfoEntry 11 }

-- ----------------------------------------
-- tmnxSubIngQosSchedStatsTable
-- ----------------------------------------
tmnxSubIngQosSchedStatsTable OBJECT-TYPE
    SYNTAX      SEQUENCE OF TmnxSubIngQosSchedStatsEntry
    MAX-ACCESS  not-accessible
    STATUS      current
    DESCRIPTION
        "The tmnxSubIngQosSchedStatsTable contains ingress QoS scheduler
         statistics about subscribers.

         In the descriptions below 'Pchip' refers to the Nokia SROS 
         series Packet Processing chip, while 'Qchip' refers to the 
         Nokia SROS series QoS Queueing Engine chip."
    ::= { tmnxSubMgmtObjects 19 }

tmnxSubIngQosSchedStatsEntry OBJECT-TYPE
    SYNTAX      TmnxSubIngQosSchedStatsEntry
    MAX-ACCESS  not-accessible
    STATUS      current
    DESCRIPTION
        "Each row entry contains ingress statistics about a particular
         subscriber QoS scheduler."
    INDEX { tmnxSubInfoSubIdent,
            IMPLIED tmnxSubIngQosSchedStatsName }
    ::= { tmnxSubIngQosSchedStatsTable 1 }

TmnxSubIngQosSchedStatsEntry ::=
    SEQUENCE {
        tmnxSubIngQosSchedStatsName      TNamedItem,
        tmnxSubIngQosSchedStatsFwdPkts   Counter64,
        tmnxSubIngQosSchedStatsFwdOctets Counter64
    }

tmnxSubIngQosSchedStatsName OBJECT-TYPE
    SYNTAX      TNamedItem
    MAX-ACCESS  not-accessible
    STATUS      current
    DESCRIPTION
        "The value of tmnxSubIngQosSchedStatsName specifies the ingress QoS
         scheduler of this subscriber."
    ::= { tmnxSubIngQosSchedStatsEntry 1 }

tmnxSubIngQosSchedStatsFwdPkts OBJECT-TYPE
    SYNTAX      Counter64
    MAX-ACCESS  read-only
    STATUS      current
    DESCRIPTION
        "The value of tmnxSubIngQosSchedStatsFwdPkts indicates the number of
         forwarded packets, as determined by the subscriber ingress scheduler
         policy, offered by the Pchip to the Qchip."
    ::= { tmnxSubIngQosSchedStatsEntry 2 }

tmnxSubIngQosSchedStatsFwdOctets OBJECT-TYPE
    SYNTAX      Counter64
    MAX-ACCESS  read-only
    STATUS      current
    DESCRIPTION
        "The value of tmnxSubIngQosSchedStatsFwdOctets indicates the number of
         forwarded octets, as determined by the subscriber ingress scheduler
         policy, offered by the Pchip to the Qchip."
    ::= { tmnxSubIngQosSchedStatsEntry 3 }

-- ----------------------------------------
-- tmnxSubEgrQosSchedStatsTable
-- ----------------------------------------
tmnxSubEgrQosSchedStatsTable OBJECT-TYPE
    SYNTAX      SEQUENCE OF TmnxSubEgrQosSchedStatsEntry
    MAX-ACCESS  not-accessible
    STATUS      current
    DESCRIPTION
        "The tmnxSubEgrQosSchedStatsTable contains egress QoS scheduler
         statistics about subscribers.

         In the descriptions below 'Pchip' refers to the Nokia SROS 
         series Packet Processing chip, while 'Qchip' refers to the 
         Nokia SROS series QoS Queueing Engine chip."
    ::= { tmnxSubMgmtObjects 20 }

tmnxSubEgrQosSchedStatsEntry OBJECT-TYPE
    SYNTAX      TmnxSubEgrQosSchedStatsEntry
    MAX-ACCESS  not-accessible
    STATUS      current
    DESCRIPTION
        "Each row entry contains egress statistics about a particular
         subscriber QoS scheduler."
    INDEX { tmnxSubInfoSubIdent,
            IMPLIED tmnxSubEgrQosSchedStatsName }
    ::= { tmnxSubEgrQosSchedStatsTable 1 }

TmnxSubEgrQosSchedStatsEntry ::=
    SEQUENCE {
        tmnxSubEgrQosSchedStatsName      TNamedItem,
        tmnxSubEgrQosSchedStatsFwdPkts   Counter64,
        tmnxSubEgrQosSchedStatsFwdOctets Counter64
    }

tmnxSubEgrQosSchedStatsName OBJECT-TYPE
    SYNTAX      TNamedItem
    MAX-ACCESS  not-accessible
    STATUS      current
    DESCRIPTION
        "The value of tmnxSubEgrQosSchedStatsName specifies the egress QoS
         scheduler of this subscriber."
    ::= { tmnxSubEgrQosSchedStatsEntry 1 }

tmnxSubEgrQosSchedStatsFwdPkts OBJECT-TYPE
    SYNTAX      Counter64
    MAX-ACCESS  read-only
    STATUS      current
    DESCRIPTION
        "The value of tmnxSubEgrQosSchedStatsFwdPkts indicates the number of
         forwarded packets by the egress Qchip, as determined by the subscriber
         egress scheduler policy."
    ::= { tmnxSubEgrQosSchedStatsEntry 2 }

tmnxSubEgrQosSchedStatsFwdOctets OBJECT-TYPE
    SYNTAX      Counter64
    MAX-ACCESS  read-only
    STATUS      current
    DESCRIPTION
        "The value of tmnxSubEgrQosSchedStatsFwdOctets indicates the number of
         forwarded octets by the egress Qchip, as determined by the subscriber
         egress scheduler policy."
    ::= { tmnxSubEgrQosSchedStatsEntry 3 }

-- ----------------------------------------
-- tmnxSLAProfInstSubHostTable
-- ----------------------------------------
tmnxSLAProfInstSubHostTable OBJECT-TYPE
    SYNTAX      SEQUENCE OF TmnxSLAProfInstSubHostEntry
    MAX-ACCESS  not-accessible
    STATUS      obsolete
    DESCRIPTION
        "The tmnxSLAProfInstSubHostTable has an entry for each subscriber host
         found in the system, sorted by SLA profile instance."
    ::= { tmnxSubMgmtObjects 21 }

tmnxSLAProfInstSubHostEntry OBJECT-TYPE
    SYNTAX      TmnxSLAProfInstSubHostEntry
    MAX-ACCESS  not-accessible
    STATUS      obsolete
    DESCRIPTION
        "Each row entry indicates a particular subscriber host available in the
         system."
    INDEX { tmnxSubInfoSubIdent,
            sapPortId,
            sapEncapValue,
            tmnxSLAProfName,
            tmnxSPISubHostIpAddressType,
            tmnxSPISubHostIpAddress }
    ::= { tmnxSLAProfInstSubHostTable 1 }

TmnxSLAProfInstSubHostEntry ::=
    SEQUENCE {
        tmnxSPISubHostIpAddressType InetAddressType,
        tmnxSPISubHostIpAddress     InetAddress,
        tmnxSPISubHostMacAddress    MacAddress,
        tmnxSPISubHostOrigin        TmnxSubHostOrigin
    }

tmnxSPISubHostIpAddressType OBJECT-TYPE
    SYNTAX      InetAddressType
    MAX-ACCESS  not-accessible
    STATUS      obsolete
    DESCRIPTION
        "The value of tmnxSPISubHostIpAddressType specifies the type of address
         stored in tmnxSPISubHostIpAddress."
    ::= { tmnxSLAProfInstSubHostEntry 1 }

tmnxSPISubHostIpAddress OBJECT-TYPE
    SYNTAX      InetAddress
    MAX-ACCESS  not-accessible
    STATUS      obsolete
    DESCRIPTION
        "The value of tmnxSPISubHostIpAddress specifies the IP address of this
         subscriber host."
    ::= { tmnxSLAProfInstSubHostEntry 2 }

tmnxSPISubHostMacAddress OBJECT-TYPE
    SYNTAX      MacAddress
    MAX-ACCESS  read-only
    STATUS      obsolete
    DESCRIPTION
        "The value of tmnxSPISubHostMacAddress indicates the MAC address of
         this subscriber host."
    ::= { tmnxSLAProfInstSubHostEntry 3 }

tmnxSPISubHostOrigin OBJECT-TYPE
    SYNTAX      TmnxSubHostOrigin
    MAX-ACCESS  read-only
    STATUS      obsolete
    DESCRIPTION
        "The value of tmnxSPISubHostOrigin indicates the origin of this
         subscriber host."
    ::= { tmnxSLAProfInstSubHostEntry 4 }

-- ----------------------------------------
-- tmnxSLAProfInstStatsTable
-- ----------------------------------------
tmnxSLAProfInstStatsTable OBJECT-TYPE
    SYNTAX      SEQUENCE OF TmnxSLAProfInstStatsEntry
    MAX-ACCESS  not-accessible
    STATUS      current
    DESCRIPTION
        "The tmnxSLAProfInstStatsTable contains basic statistics about SLA
         profile instances.
         In the descriptions below 'Pchip' refers to the Nokia SROS 
         series Packet Processing chip, while 'Qchip' refers to the 
         Nokia SROS series QoS Queueing Engine chip."
    ::= { tmnxSubMgmtObjects 22 }

tmnxSLAProfInstStatsEntry OBJECT-TYPE
    SYNTAX      TmnxSLAProfInstStatsEntry
    MAX-ACCESS  not-accessible
    STATUS      current
    DESCRIPTION
        "Each row entry contains basic statistics about a particular SLA
         profile instance."
    INDEX { tmnxSubInfoSubIdent,
            sapPortId,
            sapEncapValue,
            tmnxSLAProfName }
    ::= { tmnxSLAProfInstStatsTable 1 }

TmnxSLAProfInstStatsEntry ::=
    SEQUENCE {
        tmnxSPIStatsIngPchipOffHiPrioPkts     Counter64,
        tmnxSPIStatsIngPchipOffHiPrioOctets   Counter64,
        tmnxSPIStatsIngPchipOffLoPrioPkts     Counter64,
        tmnxSPIStatsIngPchipOffLoPrioOctets   Counter64,
        tmnxSPIStatsIngPchipOffUncolPkts      Counter64,
        tmnxSPIStatsIngPchipOffUncolOctets    Counter64,
        tmnxSPIStatsIngQchipDropHiPrioPkts    Counter64,
        tmnxSPIStatsIngQchipDropHiPrioOctets  Counter64,
        tmnxSPIStatsIngQchipDropLoPrioPkts    Counter64,
        tmnxSPIStatsIngQchipDropLoPrioOctets  Counter64,
        tmnxSPIStatsIngQchipFwdInProfPkts     Counter64,
        tmnxSPIStatsIngQchipFwdInProfOctets   Counter64,
        tmnxSPIStatsIngQchipFwdOutProfPkts    Counter64,
        tmnxSPIStatsIngQchipFwdOutProfOctets  Counter64,
        tmnxSPIStatsEgrQchipDropInProfPkts    Counter64,
        tmnxSPIStatsEgrQchipDropInProfOctets  Counter64,
        tmnxSPIStatsEgrQchipDropOutProfPkts   Counter64,
        tmnxSPIStatsEgrQchipDropOutProfOctets Counter64,
        tmnxSPIStatsEgrQchipFwdInProfPkts     Counter64,
        tmnxSPIStatsEgrQchipFwdInProfOctets   Counter64,
        tmnxSPIStatsEgrQchipFwdOutProfPkts    Counter64,
        tmnxSPIStatsEgrQchipFwdOutProfOctets  Counter64,
        tmnxSPIStatsIngPchipOffV4Pkts         Counter64,
        tmnxSPIStatsIngPchipOffV4Octets       Counter64,
        tmnxSPIStatsIngPchipOffV6Pkts         Counter64,
        tmnxSPIStatsIngPchipOffV6Octets       Counter64,
        tmnxSPIStatsIngQchipDropV4Pkts        Counter64,
        tmnxSPIStatsIngQchipDropV4Octets      Counter64,
        tmnxSPIStatsIngQchipDropV6Pkts        Counter64,
        tmnxSPIStatsIngQchipDropV6Octets      Counter64,
        tmnxSPIStatsIngQchipFwdV4Pkts         Counter64,
        tmnxSPIStatsIngQchipFwdV4Octets       Counter64,
        tmnxSPIStatsIngQchipFwdV6Pkts         Counter64,
        tmnxSPIStatsIngQchipFwdV6Octets       Counter64,
        tmnxSPIStatsEgrQchipDropV4Pkts        Counter64,
        tmnxSPIStatsEgrQchipDropV4Octets      Counter64,
        tmnxSPIStatsEgrQchipDropV6Pkts        Counter64,
        tmnxSPIStatsEgrQchipDropV6Octets      Counter64,
        tmnxSPIStatsEgrQchipFwdV4Pkts         Counter64,
        tmnxSPIStatsEgrQchipFwdV4Octets       Counter64,
        tmnxSPIStatsEgrQchipFwdV6Pkts         Counter64,
        tmnxSPIStatsEgrQchipFwdV6Octets       Counter64
    }

tmnxSPIStatsIngPchipOffHiPrioPkts OBJECT-TYPE
    SYNTAX      Counter64
    MAX-ACCESS  read-only
    STATUS      current
    DESCRIPTION
        "The value of tmnxSPIStatsIngPchipOffHiPrioPkts indicates the number
         of high priority packets as determined by the SLA profile ingress QoS
         policy, offered by the Pchip to the Qchip."
    ::= { tmnxSLAProfInstStatsEntry 1 }

tmnxSPIStatsIngPchipOffHiPrioOctets OBJECT-TYPE
    SYNTAX      Counter64
    MAX-ACCESS  read-only
    STATUS      current
    DESCRIPTION
        "The value of tmnxSPIStatsIngPchipOffHiPrioOctets indicates the number
         of high priority octets as determined by the SLA profile ingress QoS
         policy, offered by the Pchip to the Qchip."
    ::= { tmnxSLAProfInstStatsEntry 2 }

tmnxSPIStatsIngPchipOffLoPrioPkts OBJECT-TYPE
    SYNTAX      Counter64
    MAX-ACCESS  read-only
    STATUS      current
    DESCRIPTION
        "The value of tmnxSPIStatsIngPchipOffLoPrioPkts indicates the number
         of low priority packets as determined by the SLA profile ingress QoS
         policy, offered by the Pchip to the Qchip."
    ::= { tmnxSLAProfInstStatsEntry 3 }

tmnxSPIStatsIngPchipOffLoPrioOctets OBJECT-TYPE
    SYNTAX      Counter64
    MAX-ACCESS  read-only
    STATUS      current
    DESCRIPTION
        "The value of tmnxSPIStatsIngPchipOffLoPrioOctets indicates the number
         of low priority octets as determined by the SLA profile ingress QoS
         policy, offered by the Pchip to the Qchip."
    ::= { tmnxSLAProfInstStatsEntry 4 }

tmnxSPIStatsIngPchipOffUncolPkts OBJECT-TYPE
    SYNTAX      Counter64
    MAX-ACCESS  read-only
    STATUS      current
    DESCRIPTION
        "The value of tmnxSPIStatsIngPchipOffUncolPkts indicates the number
         of uncolored packets as determined by the SLA profile ingress QoS
         policy, offered by the Pchip to the Qchip."
    ::= { tmnxSLAProfInstStatsEntry 5 }

tmnxSPIStatsIngPchipOffUncolOctets OBJECT-TYPE
    SYNTAX      Counter64
    MAX-ACCESS  read-only
    STATUS      current
    DESCRIPTION
        "The value of tmnxSPIStatsIngPchipOffUncolOctets indicates the number
         of uncolored octets as determined by the SLA profile ingress QoS
         policy, offered by the Pchip to the Qchip."
    ::= { tmnxSLAProfInstStatsEntry 6 }

tmnxSPIStatsIngQchipDropHiPrioPkts OBJECT-TYPE
    SYNTAX      Counter64
    MAX-ACCESS  read-only
    STATUS      current
    DESCRIPTION
        "The value of tmnxSPIStatsIngQchipDropHiPrioPkts indicates the number
         of high priority packets as determined by the SLA profile ingress QoS
         policy, dropped by the Qchip."
    ::= { tmnxSLAProfInstStatsEntry 7 }

tmnxSPIStatsIngQchipDropHiPrioOctets OBJECT-TYPE
    SYNTAX      Counter64
    MAX-ACCESS  read-only
    STATUS      current
    DESCRIPTION
        "The value of tmnxSPIStatsIngQchipDropHiPrioOctets indicates the number
         of high priority octets as determined by the SLA profile ingress QoS
         policy, dropped by the Qchip."
    ::= { tmnxSLAProfInstStatsEntry 8 }

tmnxSPIStatsIngQchipDropLoPrioPkts OBJECT-TYPE
    SYNTAX      Counter64
    MAX-ACCESS  read-only
    STATUS      current
    DESCRIPTION
        "The value of tmnxSPIStatsIngQchipDropLoPrioPkts indicates the number
         of low priority packets as determined by the SLA profile ingress QoS
         policy, dropped by the Qchip."
    ::= { tmnxSLAProfInstStatsEntry 9 }

tmnxSPIStatsIngQchipDropLoPrioOctets OBJECT-TYPE
    SYNTAX      Counter64
    MAX-ACCESS  read-only
    STATUS      current
    DESCRIPTION
        "The value of tmnxSPIStatsIngQchipDropLoPrioOctets indicates the number
         of low priority octets as determined by the SLA profile ingress QoS
         policy, dropped by the Qchip."
    ::= { tmnxSLAProfInstStatsEntry 10 }

tmnxSPIStatsIngQchipFwdInProfPkts OBJECT-TYPE
    SYNTAX      Counter64
    MAX-ACCESS  read-only
    STATUS      current
    DESCRIPTION
        "The value of tmnxSPIStatsIngQchipFwdInProfPkts indicates the number
         of in-profile packets (rate below CIR) forwarded by the ingress Qchip."
    ::= { tmnxSLAProfInstStatsEntry 11 }

tmnxSPIStatsIngQchipFwdInProfOctets OBJECT-TYPE
    SYNTAX      Counter64
    MAX-ACCESS  read-only
    STATUS      current
    DESCRIPTION
        "The value of tmnxSPIStatsIngQchipFwdInProfOctets indicates the number
         of in-profile octets (rate below CIR) forwarded by the ingress Qchip."
    ::= { tmnxSLAProfInstStatsEntry 12 }

tmnxSPIStatsIngQchipFwdOutProfPkts OBJECT-TYPE
    SYNTAX      Counter64
    MAX-ACCESS  read-only
    STATUS      current
    DESCRIPTION
        "The value of tmnxSPIStatsIngQchipFwdOutProfPkts indicates the number
         of out-of-profile packets (rate above CIR) forwarded by the ingress
         Qchip."
    ::= { tmnxSLAProfInstStatsEntry 13 }

tmnxSPIStatsIngQchipFwdOutProfOctets OBJECT-TYPE
    SYNTAX      Counter64
    MAX-ACCESS  read-only
    STATUS      current
    DESCRIPTION
        "The value of tmnxSPIStatsIngQchipFwdOutProfOctets indicates the number
         of out-of-profile octets (rate above CIR) forwarded by the ingress
         Qchip."
    ::= { tmnxSLAProfInstStatsEntry 14 }

tmnxSPIStatsEgrQchipDropInProfPkts OBJECT-TYPE
    SYNTAX      Counter64
    MAX-ACCESS  read-only
    STATUS      current
    DESCRIPTION
        "The value of tmnxSPIStatsEgrQchipDropInProfPkts indicates the number
         of in-profile packets dropped by the egress Qchip."
    ::= { tmnxSLAProfInstStatsEntry 15 }

tmnxSPIStatsEgrQchipDropInProfOctets OBJECT-TYPE
    SYNTAX      Counter64
    MAX-ACCESS  read-only
    STATUS      current
    DESCRIPTION
        "The value of tmnxSPIStatsEgrQchipDropInProfOctets indicates the number
         of in-profile octets dropped by the egress Qchip."
    ::= { tmnxSLAProfInstStatsEntry 16 }

tmnxSPIStatsEgrQchipDropOutProfPkts OBJECT-TYPE
    SYNTAX      Counter64
    MAX-ACCESS  read-only
    STATUS      current
    DESCRIPTION
        "The value of tmnxSPIStatsEgrQchipDropOutProfPkts indicates the number
         of out-of-profile packets dropped by the egress Qchip."
    ::= { tmnxSLAProfInstStatsEntry 17 }

tmnxSPIStatsEgrQchipDropOutProfOctets OBJECT-TYPE
    SYNTAX      Counter64
    MAX-ACCESS  read-only
    STATUS      current
    DESCRIPTION
        "The value of tmnxSPIStatsEgrQchipDropOutProfOctets indicates the
         number of out-of-profile octets dropped by the egress Qchip."
    ::= { tmnxSLAProfInstStatsEntry 18 }

tmnxSPIStatsEgrQchipFwdInProfPkts OBJECT-TYPE
    SYNTAX      Counter64
    MAX-ACCESS  read-only
    STATUS      current
    DESCRIPTION
        "The value of tmnxSPIStatsEgrQchipFwdInProfPkts indicates the number
         of in-profile packets (rate below CIR) forwarded by the egress Qchip."
    ::= { tmnxSLAProfInstStatsEntry 19 }

tmnxSPIStatsEgrQchipFwdInProfOctets OBJECT-TYPE
    SYNTAX      Counter64
    MAX-ACCESS  read-only
    STATUS      current
    DESCRIPTION
        "The value of tmnxSPIStatsEgrQchipFwdInProfOctets indicates the number
         of in-profile octets (rate below CIR) forwarded by the egress Qchip."
    ::= { tmnxSLAProfInstStatsEntry 20 }

tmnxSPIStatsEgrQchipFwdOutProfPkts OBJECT-TYPE
    SYNTAX      Counter64
    MAX-ACCESS  read-only
    STATUS      current
    DESCRIPTION
        "The value of tmnxSPIStatsEgrQchipFwdOutProfPkts indicates the number
         of out-of-profile packets (rate above CIR) forwarded by the egress
         Qchip."
    ::= { tmnxSLAProfInstStatsEntry 21 }

tmnxSPIStatsEgrQchipFwdOutProfOctets OBJECT-TYPE
    SYNTAX      Counter64
    MAX-ACCESS  read-only
    STATUS      current
    DESCRIPTION
        "The value of tmnxSPIStatsEgrQchipFwdOutProfOctets indicates the number
         of out-of-profile octets (rate above CIR) forwarded by the egress
         Qchip."
    ::= { tmnxSLAProfInstStatsEntry 22 }

tmnxSPIStatsIngPchipOffV4Pkts OBJECT-TYPE
    SYNTAX      Counter64
    MAX-ACCESS  read-only
    STATUS      current
    DESCRIPTION
        "The value of tmnxSPIStatsIngPchipOffV4Pkts indicates the number
         of V4 packets offered by the Pchip to the Qchip."
    ::= { tmnxSLAProfInstStatsEntry 23 }

tmnxSPIStatsIngPchipOffV4Octets OBJECT-TYPE
    SYNTAX      Counter64
    MAX-ACCESS  read-only
    STATUS      current
    DESCRIPTION
        "The value of tmnxSPIStatsIngPchipOffV4Octets indicates the number
         of V4 octets offered by the Pchip to the Qchip."
    ::= { tmnxSLAProfInstStatsEntry 24 }

tmnxSPIStatsIngPchipOffV6Pkts OBJECT-TYPE
    SYNTAX      Counter64
    MAX-ACCESS  read-only
    STATUS      current
    DESCRIPTION
        "The value of tmnxSPIStatsIngPchipOffV6Pkts indicates the number
         of V6 packets offered by the Pchip to the Qchip."
    ::= { tmnxSLAProfInstStatsEntry 25 }

tmnxSPIStatsIngPchipOffV6Octets OBJECT-TYPE
    SYNTAX      Counter64
    MAX-ACCESS  read-only
    STATUS      current
    DESCRIPTION
        "The value of tmnxSPIStatsIngPchipOffV6Octets indicates the number
         of V6 octets offered by the Pchip to the Qchip."
    ::= { tmnxSLAProfInstStatsEntry 26 }

tmnxSPIStatsIngQchipDropV4Pkts OBJECT-TYPE
    SYNTAX      Counter64
    MAX-ACCESS  read-only
    STATUS      current
    DESCRIPTION
        "The value of tmnxSPIStatsIngQchipDropV4Pkts indicates the
         number of V4 packets dropped by the ingress Qchip."
    ::= { tmnxSLAProfInstStatsEntry 27 }

tmnxSPIStatsIngQchipDropV4Octets OBJECT-TYPE
    SYNTAX      Counter64
    MAX-ACCESS  read-only
    STATUS      current
    DESCRIPTION
        "The value of tmnxSPIStatsIngQchipDropV4Octets indicates the
         number of V4 octets dropped by the ingress Qchip."
    ::= { tmnxSLAProfInstStatsEntry 28 }

tmnxSPIStatsIngQchipDropV6Pkts OBJECT-TYPE
    SYNTAX      Counter64
    MAX-ACCESS  read-only
    STATUS      current
    DESCRIPTION
        "The value of tmnxSPIStatsIngQchipDropV6Pkts indicates the
         number of V6 packets dropped by the ingress Qchip."
    ::= { tmnxSLAProfInstStatsEntry 29 }

tmnxSPIStatsIngQchipDropV6Octets OBJECT-TYPE
    SYNTAX      Counter64
    MAX-ACCESS  read-only
    STATUS      current
    DESCRIPTION
        "The value of tmnxSPIStatsIngQchipDropV6Octets indicates the
         number of V6 octets dropped by the ingress Qchip."
    ::= { tmnxSLAProfInstStatsEntry 30 }

tmnxSPIStatsIngQchipFwdV4Pkts OBJECT-TYPE
    SYNTAX      Counter64
    MAX-ACCESS  read-only
    STATUS      current
    DESCRIPTION
        "The value of tmnxSPIStatsIngQchipFwdV4Pkts indicates the
         number of V4 packets forwarded by the ingress Qchip."
    ::= { tmnxSLAProfInstStatsEntry 31 }

tmnxSPIStatsIngQchipFwdV4Octets OBJECT-TYPE
    SYNTAX      Counter64
    MAX-ACCESS  read-only
    STATUS      current
    DESCRIPTION
        "The value of tmnxSPIStatsIngQchipFwdV4Octets indicates the
         number of V4 octets forwarded by the ingress Qchip."
    ::= { tmnxSLAProfInstStatsEntry 32 }

tmnxSPIStatsIngQchipFwdV6Pkts OBJECT-TYPE
    SYNTAX      Counter64
    MAX-ACCESS  read-only
    STATUS      current
    DESCRIPTION
        "The value of tmnxSPIStatsIngQchipFwdV6Pkts indicates the
         number of V6 packets forwarded by the ingress Qchip."
    ::= { tmnxSLAProfInstStatsEntry 33 }

tmnxSPIStatsIngQchipFwdV6Octets OBJECT-TYPE
    SYNTAX      Counter64
    MAX-ACCESS  read-only
    STATUS      current
    DESCRIPTION
        "The value of tmnxSPIStatsIngQchipFwdV6Octets indicates the
         number of V6 octets forwarded by the ingress Qchip."
    ::= { tmnxSLAProfInstStatsEntry 34 }

tmnxSPIStatsEgrQchipDropV4Pkts OBJECT-TYPE
    SYNTAX      Counter64
    MAX-ACCESS  read-only
    STATUS      current
    DESCRIPTION
        "The value of tmnxSPIStatsEgrQchipDropV4Pkts indicates the
         number of V4 packets dropped by the egress Qchip."
    ::= { tmnxSLAProfInstStatsEntry 35 }

tmnxSPIStatsEgrQchipDropV4Octets OBJECT-TYPE
    SYNTAX      Counter64
    MAX-ACCESS  read-only
    STATUS      current
    DESCRIPTION
        "The value of tmnxSPIStatsEgrQchipDropV4Octets indicates the
         number of V4 octets dropped by the egress Qchip."
    ::= { tmnxSLAProfInstStatsEntry 36 }

tmnxSPIStatsEgrQchipDropV6Pkts OBJECT-TYPE
    SYNTAX      Counter64
    MAX-ACCESS  read-only
    STATUS      current
    DESCRIPTION
        "The value of tmnxSPIStatsEgrQchipDropV6Pkts indicates the
         number of V6 packets dropped by the egress Qchip."
    ::= { tmnxSLAProfInstStatsEntry 37 }

tmnxSPIStatsEgrQchipDropV6Octets OBJECT-TYPE
    SYNTAX      Counter64
    MAX-ACCESS  read-only
    STATUS      current
    DESCRIPTION
        "The value of tmnxSPIStatsEgrQchipDropV6Octets indicates the
         number of V6 octets dropped by the egress Qchip."
    ::= { tmnxSLAProfInstStatsEntry 38 }

tmnxSPIStatsEgrQchipFwdV4Pkts OBJECT-TYPE
    SYNTAX      Counter64
    MAX-ACCESS  read-only
    STATUS      current
    DESCRIPTION
        "The value of tmnxSPIStatsEgrQchipFwdV4Pkts indicates the
         number of V4 packets forwarded by the egress Qchip."
    ::= { tmnxSLAProfInstStatsEntry 39 }

tmnxSPIStatsEgrQchipFwdV4Octets OBJECT-TYPE
    SYNTAX      Counter64
    MAX-ACCESS  read-only
    STATUS      current
    DESCRIPTION
        "The value of tmnxSPIStatsEgrQchipFwdV4Octets indicates the
         number of V4 octets forwarded by the egress Qchip."
    ::= { tmnxSLAProfInstStatsEntry 40 }

tmnxSPIStatsEgrQchipFwdV6Pkts OBJECT-TYPE
    SYNTAX      Counter64
    MAX-ACCESS  read-only
    STATUS      current
    DESCRIPTION
        "The value of tmnxSPIStatsEgrQchipFwdV6Pkts indicates the
         number of V6 packets forwarded by the egress Qchip."
    ::= { tmnxSLAProfInstStatsEntry 41 }

tmnxSPIStatsEgrQchipFwdV6Octets OBJECT-TYPE
    SYNTAX      Counter64
    MAX-ACCESS  read-only
    STATUS      current
    DESCRIPTION
        "The value of tmnxSPIStatsEgrQchipFwdV6Octets indicates the
         number of V6 octets forwarded by the egress Qchip."
    ::= { tmnxSLAProfInstStatsEntry 42 }

-- ----------------------------------------
-- tmnxSLAProfInstIngQStatsTable
-- ----------------------------------------
tmnxSLAProfInstIngQStatsTable OBJECT-TYPE
    SYNTAX      SEQUENCE OF TmnxSLAProfInstIngQStatsEntry
    MAX-ACCESS  not-accessible
    STATUS      current
    DESCRIPTION
        "The tmnxSLAProfInstIngQStatsTable contains ingress QoS queue
         statistics about SLA profile instances.

         In the descriptions below 'Pchip' refers to the Nokia SROS 
         series Packet Processing chip, while 'Qchip' refers to the 
         Nokia SROS series QoS Queueing Engine chip."
    ::= { tmnxSubMgmtObjects 23 }

tmnxSLAProfInstIngQStatsEntry OBJECT-TYPE
    SYNTAX      TmnxSLAProfInstIngQStatsEntry
    MAX-ACCESS  not-accessible
    STATUS      current
    DESCRIPTION
        "Each row entry contains ingress statistics about a particular SLA
         profile instance QoS queue."
    INDEX { tmnxSubInfoSubIdent,
            sapPortId,
            sapEncapValue,
            tmnxSLAProfName,
            tmnxSPIIngQStatsQueueId }
    ::= { tmnxSLAProfInstIngQStatsTable 1 }

TmnxSLAProfInstIngQStatsEntry ::=
    SEQUENCE {
        tmnxSPIIngQStatsQueueId          TIngressQueueId,
        tmnxSPIIngQStatsOffHiPrioPkts    Counter64,
        tmnxSPIIngQStatsDropHiPrioPkts   Counter64,
        tmnxSPIIngQStatsOffLoPrioPkts    Counter64,
        tmnxSPIIngQStatsDropLoPrioPkts   Counter64,
        tmnxSPIIngQStatsOffHiPrioOctets  Counter64,
        tmnxSPIIngQStatsDropHiPrioOctets Counter64,
        tmnxSPIIngQStatsOffLoPrioOctets  Counter64,
        tmnxSPIIngQStatsDropLoPrioOctets Counter64,
        tmnxSPIIngQStatsOffUncolPkts     Counter64,
        tmnxSPIIngQStatsOffUncolOctets   Counter64,
        tmnxSPIIngQStatsFwdInProfPkts    Counter64,
        tmnxSPIIngQStatsFwdOutProfPkts   Counter64,
        tmnxSPIIngQStatsFwdInProfOctets  Counter64,
        tmnxSPIIngQStatsFwdOutProfOctets Counter64,
        tmnxSPIIngQStatModeFormat        TQueueStatModeFormat
    }

tmnxSPIIngQStatsQueueId OBJECT-TYPE
    SYNTAX      TIngressQueueId
    MAX-ACCESS  not-accessible
    STATUS      current
    DESCRIPTION
        "The value of tmnxSPIIngQStatsQueueId specifies the index of the
         ingress QoS queue of this SLA profile instance."
    ::= { tmnxSLAProfInstIngQStatsEntry 1 }

tmnxSPIIngQStatsOffHiPrioPkts OBJECT-TYPE
    SYNTAX      Counter64
    MAX-ACCESS  read-only
    STATUS      current
    DESCRIPTION
        "The value of tmnxSPIIngQStatsOffHiPrioPkts indicates the number of
         high priority packets, as determined by the SLA profile ingress QoS
         policy, offered by the Pchip to the Qchip."
    ::= { tmnxSLAProfInstIngQStatsEntry 2 }

tmnxSPIIngQStatsDropHiPrioPkts OBJECT-TYPE
    SYNTAX      Counter64
    MAX-ACCESS  read-only
    STATUS      current
    DESCRIPTION
        "The value of tmnxSPIIngQStatsDropHiPrioPkts indicates the number of
         high priority packets, as determined by the SLA profile ingress QoS
         policy, dropped by the Qchip."
    ::= { tmnxSLAProfInstIngQStatsEntry 3 }

tmnxSPIIngQStatsOffLoPrioPkts OBJECT-TYPE
    SYNTAX      Counter64
    MAX-ACCESS  read-only
    STATUS      current
    DESCRIPTION
        "The value of tmnxSPIIngQStatsOffLoPrioPkts indicates the number of low
         priority packets, as determined by the SLA profile ingress QoS policy,
         offered by the Pchip to the Qchip."
    ::= { tmnxSLAProfInstIngQStatsEntry 4 }

tmnxSPIIngQStatsDropLoPrioPkts OBJECT-TYPE
    SYNTAX      Counter64
    MAX-ACCESS  read-only
    STATUS      current
    DESCRIPTION
        "The value of tmnxSPIIngQStatsDropLoPrioPkts indicates the number of
         low priority packets, as determined by the SLA profile ingress QoS
         policy, dropped by the Qchip."
    ::= { tmnxSLAProfInstIngQStatsEntry 5 }

tmnxSPIIngQStatsOffHiPrioOctets OBJECT-TYPE
    SYNTAX      Counter64
    MAX-ACCESS  read-only
    STATUS      current
    DESCRIPTION
        "The value of tmnxSPIIngQStatsOffHiPrioOctets indicates the number
         of high priority octets, as determined by the SLA profile ingress QoS
         policy, offered by the Pchip to the Qchip."
    ::= { tmnxSLAProfInstIngQStatsEntry 6 }

tmnxSPIIngQStatsDropHiPrioOctets OBJECT-TYPE
    SYNTAX      Counter64
    MAX-ACCESS  read-only
    STATUS      current
    DESCRIPTION
        "The value of tmnxSPIIngQStatsDropHiPrioOctets indicates the number of
         high priority octets, as determined by the SLA profile ingress QoS
         policy, dropped by the Qchip."
    ::= { tmnxSLAProfInstIngQStatsEntry 7 }

tmnxSPIIngQStatsOffLoPrioOctets OBJECT-TYPE
    SYNTAX      Counter64
    MAX-ACCESS  read-only
    STATUS      current
    DESCRIPTION
        "The value of tmnxSPIIngQStatsOffLoPrioOctets indicates the number of
         low priority octets, as determined by the SLA profile ingress QoS
         policy, offered by the Pchip to the Qchip."
    ::= { tmnxSLAProfInstIngQStatsEntry 8 }

tmnxSPIIngQStatsDropLoPrioOctets OBJECT-TYPE
    SYNTAX      Counter64
    MAX-ACCESS  read-only
    STATUS      current
    DESCRIPTION
        "The value of tmnxSPIIngQStatsDropLoPrioOctets indicates the number of
         low priority octets, as determined by the SLA profile ingress QoS
         policy, dropped by the Qchip."
    ::= { tmnxSLAProfInstIngQStatsEntry 9 }

tmnxSPIIngQStatsOffUncolPkts OBJECT-TYPE
    SYNTAX      Counter64
    MAX-ACCESS  read-only
    STATUS      current
    DESCRIPTION
        "The value of tmnxSPIIngQStatsOffUncolPkts indicates the number of
         uncolored packets offered to the ingress Qchip."
    ::= { tmnxSLAProfInstIngQStatsEntry 10 }

tmnxSPIIngQStatsOffUncolOctets OBJECT-TYPE
    SYNTAX      Counter64
    MAX-ACCESS  read-only
    STATUS      current
    DESCRIPTION
        "The value of tmnxSPIIngQStatsOffUncolOctets indicates the number of
         uncolored octets offered to the ingress Qchip."
    ::= { tmnxSLAProfInstIngQStatsEntry 11 }

tmnxSPIIngQStatsFwdInProfPkts OBJECT-TYPE
    SYNTAX      Counter64
    MAX-ACCESS  read-only
    STATUS      current
    DESCRIPTION
        "The value of tmnxSPIIngQStatsFwdInProfPkts indicates the number of
         in-profile packets (rate below CIR) forwarded by the ingress Qchip."
    ::= { tmnxSLAProfInstIngQStatsEntry 12 }

tmnxSPIIngQStatsFwdOutProfPkts OBJECT-TYPE
    SYNTAX      Counter64
    MAX-ACCESS  read-only
    STATUS      current
    DESCRIPTION
        "The value of tmnxSPIIngQStatsFwdOutProfPkts indicates the number of
         out-of-profile packets (rate above CIR) forwarded by the ingress
         Qchip."
    ::= { tmnxSLAProfInstIngQStatsEntry 13 }

tmnxSPIIngQStatsFwdInProfOctets OBJECT-TYPE
    SYNTAX      Counter64
    MAX-ACCESS  read-only
    STATUS      current
    DESCRIPTION
        "The value of tmnxSPIIngQStatsFwdInProfOctets indicates the number of
         in-profile octets (rate below CIR) forwarded by the ingress Qchip."
    ::= { tmnxSLAProfInstIngQStatsEntry 14 }

tmnxSPIIngQStatsFwdOutProfOctets OBJECT-TYPE
    SYNTAX      Counter64
    MAX-ACCESS  read-only
    STATUS      current
    DESCRIPTION
        "The value of tmnxSPIIngQStatsFwdOutProfOctets indicates the number of
         out-of-profile octets (rate above CIR) forwarded by the ingress Qchip."
    ::= { tmnxSLAProfInstIngQStatsEntry 15 }

tmnxSPIIngQStatModeFormat OBJECT-TYPE
    SYNTAX      TQueueStatModeFormat
    MAX-ACCESS  read-only
    STATUS      current
    DESCRIPTION
        "The value of tmnxSPIIngQStatModeFormat specifies the stat mode format
         of this ingress QoS queue of this SLA profile instance."
    ::= { tmnxSLAProfInstIngQStatsEntry 16 }

-- ----------------------------------------
-- tmnxSLAProfInstEgrQStatsTable
-- ----------------------------------------
tmnxSLAProfInstEgrQStatsTable OBJECT-TYPE
    SYNTAX      SEQUENCE OF TmnxSLAProfInstEgrQStatsEntry
    MAX-ACCESS  not-accessible
    STATUS      current
    DESCRIPTION
        "The tmnxSLAProfInstEgrQStatsTable contains egress QoS queue
         statistics about SLA profile instances.

         In the descriptions below 'Pchip' refers to the Nokia SROS 
         series Packet Processing chip, while 'Qchip' refers to the 
         Nokia SROS series QoS Queueing Engine chip."
    ::= { tmnxSubMgmtObjects 24 }

tmnxSLAProfInstEgrQStatsEntry OBJECT-TYPE
    SYNTAX      TmnxSLAProfInstEgrQStatsEntry
    MAX-ACCESS  not-accessible
    STATUS      current
    DESCRIPTION
        "Each row entry contains egress statistics about a particular SLA
         profile instance QoS queue."
    INDEX { tmnxSubInfoSubIdent,
            sapPortId,
            sapEncapValue,
            tmnxSLAProfName,
            tmnxSPIEgrQStatsQueueId }
    ::= { tmnxSLAProfInstEgrQStatsTable 1 }

TmnxSLAProfInstEgrQStatsEntry ::=
    SEQUENCE {
        tmnxSPIEgrQStatsQueueId           TEgressQueueId,
        tmnxSPIEgrQStatsFwdInProfPkts     Counter64,
        tmnxSPIEgrQStatsDropInProfPkts    Counter64,
        tmnxSPIEgrQStatsFwdOutProfPkts    Counter64,
        tmnxSPIEgrQStatsDropOutProfPkts   Counter64,
        tmnxSPIEgrQStatsFwdInProfOctets   Counter64,
        tmnxSPIEgrQStatsDropInProfOctets  Counter64,
        tmnxSPIEgrQStatsFwdOutProfOctets  Counter64,
        tmnxSPIEgrQStatsDropOutProfOctets Counter64,
        tmnxSPIEgrQStatModeFormat         TQueueStatModeFormat
    }

tmnxSPIEgrQStatsQueueId OBJECT-TYPE
    SYNTAX      TEgressQueueId
    MAX-ACCESS  not-accessible
    STATUS      current
    DESCRIPTION
        "The value of tmnxSPIEgrQStatsQueueId specifies the index of the egress
         QoS queue of this SLA profile instance."
    ::= { tmnxSLAProfInstEgrQStatsEntry 1 }

tmnxSPIEgrQStatsFwdInProfPkts OBJECT-TYPE
    SYNTAX      Counter64
    MAX-ACCESS  read-only
    STATUS      current
    DESCRIPTION
        "The value of tmnxSPIEgrQStatsFwdInProfPkts indicates the number of
         in-profile packets (rate below CIR) forwarded by the egress Qchip."
    ::= { tmnxSLAProfInstEgrQStatsEntry 2 }

tmnxSPIEgrQStatsDropInProfPkts OBJECT-TYPE
    SYNTAX      Counter64
    MAX-ACCESS  read-only
    STATUS      current
    DESCRIPTION
        "The value of tmnxSPIEgrQStatsDropInProfPkts indicates the number of
         in-profile packets discarded by the egress Qchip."
    ::= { tmnxSLAProfInstEgrQStatsEntry 3 }

tmnxSPIEgrQStatsFwdOutProfPkts OBJECT-TYPE
    SYNTAX      Counter64
    MAX-ACCESS  read-only
    STATUS      current
    DESCRIPTION
        "The value of tmnxSPIEgrQStatsFwdOutProfPkts indicates the number of
         out-of-profile packets (rate above CIR) forwarded by the egress Qchip."
    ::= { tmnxSLAProfInstEgrQStatsEntry 4 }

tmnxSPIEgrQStatsDropOutProfPkts OBJECT-TYPE
    SYNTAX      Counter64
    MAX-ACCESS  read-only
    STATUS      current
    DESCRIPTION
        "The value of tmnxSPIEgrQStatsDropOutProfPkts indicates the number of
         out-of-profile packets discarded by the egress Qchip."
    ::= { tmnxSLAProfInstEgrQStatsEntry 5 }

tmnxSPIEgrQStatsFwdInProfOctets OBJECT-TYPE
    SYNTAX      Counter64
    MAX-ACCESS  read-only
    STATUS      current
    DESCRIPTION
        "The value of tmnxSPIEgrQStatsFwdInProfOctets indicates the number of
         in-profile octets (rate below CIR) forwarded by the egress Qchip."
    ::= { tmnxSLAProfInstEgrQStatsEntry 6 }

tmnxSPIEgrQStatsDropInProfOctets OBJECT-TYPE
    SYNTAX      Counter64
    MAX-ACCESS  read-only
    STATUS      current
    DESCRIPTION
        "The value of tmnxSPIEgrQStatsDropInProfOctets indicates the number of
         in-profile octets discarded by the egress Qchip."
    ::= { tmnxSLAProfInstEgrQStatsEntry 7 }

tmnxSPIEgrQStatsFwdOutProfOctets OBJECT-TYPE
    SYNTAX      Counter64
    MAX-ACCESS  read-only
    STATUS      current
    DESCRIPTION
        "The value of tmnxSPIEgrQStatsFwdOutProfOctets indicates the number of
         out-of-profile octets (rate above CIR) forwarded by the egress Qchip."
    ::= { tmnxSLAProfInstEgrQStatsEntry 8 }

tmnxSPIEgrQStatsDropOutProfOctets OBJECT-TYPE
    SYNTAX      Counter64
    MAX-ACCESS  read-only
    STATUS      current
    DESCRIPTION
        "The value of tmnxSPIEgrQStatsDropOutProfOctets indicates the number of
         out-of-profile octets discarded by the egress Qchip."
    ::= { tmnxSLAProfInstEgrQStatsEntry 9 }

tmnxSPIEgrQStatModeFormat OBJECT-TYPE
    SYNTAX      TQueueStatModeFormat
    MAX-ACCESS  read-only
    STATUS      current
    DESCRIPTION
        "The value of tmnxSPIEgrQStatModeFormat specifies the stat mode format
         of this egress QoS queue of this SLA profile instance."
    ::= { tmnxSLAProfInstEgrQStatsEntry 10 }

-- ----------------------------------------
-- tmnxSubscriberInfoModifyTable
-- ----------------------------------------
tmnxSubscriberInfoModifyTable OBJECT-TYPE
    SYNTAX      SEQUENCE OF TmnxSubscriberInfoModifyEntry
    MAX-ACCESS  not-accessible
    STATUS      current
    DESCRIPTION
        "The tmnxSubscriberInfoModifyTable augments the tmnxSubscriberInfoTable.
         The table allows the operator to modify subscriber attributes
         including the subscriber identification name."
    ::= { tmnxSubMgmtObjects 25 }

tmnxSubscriberInfoModifyEntry OBJECT-TYPE
    SYNTAX      TmnxSubscriberInfoModifyEntry
    MAX-ACCESS  not-accessible
    STATUS      current
    DESCRIPTION
        "Each row entry contains parameters that allow to modify a subscriber
         attribute"
    AUGMENTS { tmnxSubscriberInfoEntry }
    ::= { tmnxSubscriberInfoModifyTable 1 }

TmnxSubscriberInfoModifyEntry ::=
    SEQUENCE {
        tmnxSubInfoModifySubIdent DisplayString
    }

tmnxSubInfoModifySubIdent OBJECT-TYPE
    SYNTAX      DisplayString (SIZE (0..32))
    MAX-ACCESS  read-write
    STATUS      current
    DESCRIPTION
        "The value of tmnxSubInfoModifySubIdent allows to specify a new
         name for this subscriber.

         When a SET of this object is done, with a non empty string, the
         system will attempt to rename the subscriber referred to by this row.
         If this action is successful, this row will be automatically removed
         by the system, and a new row will be created for the renamed
         subscriber.

         GETs and GETNEXTs on this variable return an empty string."
    DEFVAL { ''H }   -- the empty string
    ::= { tmnxSubscriberInfoModifyEntry 1 }

-- --------------------------------------------------------
-- tmnxSubAcctPlcyTable
-- --------------------------------------------------------
tmnxSubAcctPlcyTable OBJECT-TYPE
    SYNTAX      SEQUENCE OF TmnxSubAcctPlcyEntry
    MAX-ACCESS  not-accessible
    STATUS      current
    DESCRIPTION
        "The tmnxSubAcctPlcyTable allows configuration of RADIUS based
         accounting policies."
    ::= { tmnxSubMgmtObjects 27 }

tmnxSubAcctPlcyEntry OBJECT-TYPE
    SYNTAX      TmnxSubAcctPlcyEntry
    MAX-ACCESS  not-accessible
    STATUS      current
    DESCRIPTION
        "tmnxSubAcctPlcyEntry is an entry (conceptual row) in the
         tmnxSubAcctPlcyTable.
         Each entry represents the configuration for a RADIUS accounting policy.
         Entries in this table can be created and deleted via SNMP SET
         operations to tmnxSubAcctPlcyRowStatus. Entries have a presumed
         StorageType of nonVolatile."
    INDEX { tmnxSubAcctPlcyName }
    ::= { tmnxSubAcctPlcyTable 1 }

TmnxSubAcctPlcyEntry ::=
    SEQUENCE {
        tmnxSubAcctPlcyName              TNamedItem,
        tmnxSubAcctPlcyRowStatus         RowStatus,
        tmnxSubAcctPlcyLastMgmtChange    TimeStamp,
        tmnxSubAcctPlcyDescription       TItemDescription,
        tmnxSubAcctPlcySessionIdFormat   TmnxSubAcctPlcySessionIdFormat,
        tmnxSubAcctPlcyInclAttributes    BITS,
        tmnxSubAcctPlcyUpdateIvl         Unsigned32,
        tmnxSubAcctPlcyServVRtrID        TmnxVRtrIDOrZero,
        tmnxSubAcctPlcyServRetry         Unsigned32,
        tmnxSubAcctPlcyServSrcAddrTp     InetAddressType,
        tmnxSubAcctPlcyServSrcAddr       InetAddress,
        tmnxSubAcctPlcyServTimeout       Unsigned32,
        tmnxSubAcctPlcyServAlgorithm     TmnxSubRadServAlgorithm,
        tmnxSubAcctPlcyUseStdAcctAttrib  TruthValue,
        tmnxSubAcctPlcyNasPortPfixType   TmnxSubNasPortPrefixType,
        tmnxSubAcctPlcyNasPortPfixString DisplayString,
        tmnxSubAcctPlcyNasPortSfixType   TmnxSubNasPortSuffixType,
        tmnxSubAcctPlcyNasPortTypeType   TmnxSubNasPortTypeType,
        tmnxSubAcctPlcyNasPortTypeValue  Unsigned32,
        tmnxSubAcctPlcyHostAccounting    TmnxSubAcctPlcyAccountingType,
        tmnxSubAcctPlcyClngStationIdType TmnxSubCallingStationIdType,
        tmnxSubAcctPlcyNasPortBitspec    TmnxBinarySpecification,
        tmnxSubAcctPlcyRequestScriptPlcy TNamedItemOrEmpty,
        tmnxSubAcctPlcyQueueInstAcct     TmnxSubAcctPlcyAccountingType,
        tmnxSubAcctPlcySessionAcct       TmnxSubAcctPlcyAccountingType,
        tmnxSubAcctPlcyRadiusServerPlcy  TNamedItemOrEmpty,
        tmnxSubAcctPlcyUpdateIvlJitter   INTEGER
    }

tmnxSubAcctPlcyName OBJECT-TYPE
    SYNTAX      TNamedItem
    MAX-ACCESS  accessible-for-notify
    STATUS      current
    DESCRIPTION
        "The value of tmnxSubAcctPlcyName specifies a specific subscriber
         RADIUS based accounting policy."
    ::= { tmnxSubAcctPlcyEntry 1 }

tmnxSubAcctPlcyRowStatus OBJECT-TYPE
    SYNTAX      RowStatus
    MAX-ACCESS  read-create
    STATUS      current
    DESCRIPTION
        "The value of tmnxSubAcctPlcyRowStatus controls the creation and
         deletion of rows in the table. An attempt to delete a row that is
         referred to will fail with an inconsistentValue error."
    ::= { tmnxSubAcctPlcyEntry 2 }

tmnxSubAcctPlcyLastMgmtChange OBJECT-TYPE
    SYNTAX      TimeStamp
    MAX-ACCESS  read-only
    STATUS      current
    DESCRIPTION
        "The value of tmnxSubAcctPlcyLastMgmtChange indicates the sysUpTime at
         the time of the most recent management-initiated change to this
         policy."
    ::= { tmnxSubAcctPlcyEntry 3 }

tmnxSubAcctPlcyDescription OBJECT-TYPE
    SYNTAX      TItemDescription
    MAX-ACCESS  read-create
    STATUS      current
    DESCRIPTION
        "The value of tmnxSubAcctPlcyDescription specifies the user provided
         description of this subscriber RADIUS based accounting policy."
    DEFVAL { "" }
    ::= { tmnxSubAcctPlcyEntry 4 }

tmnxSubAcctPlcySessionIdFormat OBJECT-TYPE
    SYNTAX      TmnxSubAcctPlcySessionIdFormat
    MAX-ACCESS  read-create
    STATUS      current
    DESCRIPTION
        "The value of tmnxSubAcctPlcySessionIdFormat specifies the format
         for the acct-session-id attribute used in RADIUS accounting requests."
    DEFVAL { description }
    ::= { tmnxSubAcctPlcyEntry 5 }

tmnxSubAcctPlcyInclAttributes OBJECT-TYPE
    SYNTAX      BITS {
                    framedIpAddr                   (0),
                    framedIpNetMask                (1),
                    subscriberId                   (2),
                    circuitId                      (3),
                    remoteId                       (4),
                    nasPortId                      (5),
                    nasIdentifier                  (6),
                    subProfile                     (7),
                    slaProfile                     (8),
                    callingStationId               (9),
                    userName                      (10),
                    calledStationId               (11),
                    framedIfId                    (12),
                    ipv6Address                   (13),
                    framedIpv6Prefix              (14),
                    delegatedIpv6Prefix           (15),
                    tunnelServerAttrs             (16),
                    macAddress                    (17),
                    nasPortType                   (18),
                    natPortRange                  (19),
                    acctDelayTime                 (20),
                    acctAuthentic                 (21),
                    nasPort                       (22),
                    filterProfile                 (23),
                    dhcpVendorClassId             (24),
                    wifiRssi                      (25),
                    alcAcctTriggeredReason        (26),
                    framedRoute                   (27),
                    framedIpv6Route               (28),
                    allAuthorizedSessionAddresses (29),
                    accessLoopOptions             (30),
                    detailedAcctAttributes        (31),
                    stdAcctAttributes             (32),
                    v6AggregateStats              (33),
                    wifiSsidVlan                  (34)
                }
    MAX-ACCESS  read-create
    STATUS      current
    DESCRIPTION
        "The value of tmnxSubAcctPlcyInclAttributes specifies what RADIUS
         attributes the system should include into RADIUS accounting messages.
         
         Note: the 'filterProfile' attribute is not supported for now."
    DEFVAL { {detailedAcctAttributes} }
    ::= { tmnxSubAcctPlcyEntry 6 }

tmnxSubAcctPlcyUpdateIvl OBJECT-TYPE
    SYNTAX      Unsigned32 (0|5..259200)
    MAX-ACCESS  read-create
    STATUS      current
    DESCRIPTION
        "The value of tmnxSubAcctPlcyUpdateIvl specifies the interval at which
         accounting data of subscriber hosts will be updated. If set to 0, no
         intermediate updates will be sent."
    DEFVAL { 0 }
    ::= { tmnxSubAcctPlcyEntry 7 }

tmnxSubAcctPlcyServVRtrID OBJECT-TYPE
    SYNTAX      TmnxVRtrIDOrZero
    MAX-ACCESS  read-create
    STATUS      current
    DESCRIPTION
        "The value of tmnxSubAcctPlcyServVRtrID specifies the virtual router
         instance applicable for the set of configured RADIUS servers
         (tmnxSubAcctPlcyRadServTable). The value of this object cannot be
         changed once an RADIUS server is configured for this policy.
         When the value is '0', both base and management router instances are
         matched."
    DEFVAL { 0 }
    ::= { tmnxSubAcctPlcyEntry 8 }

tmnxSubAcctPlcyServRetry OBJECT-TYPE
    SYNTAX      Unsigned32 (1..256)
    MAX-ACCESS  read-create
    STATUS      current
    DESCRIPTION
        "The value of tmnxSubAcctPlcyServRetry specifies the number of RADIUS
         requests towards the same RADIUS server."
    DEFVAL { 3 }
    ::= { tmnxSubAcctPlcyEntry 9 }

tmnxSubAcctPlcyServSrcAddrTp OBJECT-TYPE
    SYNTAX      InetAddressType
    MAX-ACCESS  read-create
    STATUS      current
    DESCRIPTION
        "The value of tmnxSubAcctPlcyServSrcAddrTp specifies the type of
         address stored in tmnxSubAcctPlcyServSrcAddr."
    DEFVAL { ipv4 }
    ::= { tmnxSubAcctPlcyEntry 10 }

tmnxSubAcctPlcyServSrcAddr OBJECT-TYPE
    SYNTAX      InetAddress (SIZE(4))
    MAX-ACCESS  read-create
    STATUS      current
    DESCRIPTION
        "The value of tmnxSubAcctPlcyServSrcAddr specifies the source address
         of a RADIUS packet for subscriber accounting. It must be a valid
         unicast address (otherwise a wrongValue error is returned).

         If this object is configured with the address of the router interface
         (ref TIMETRA-VRTR-MIB::vRiaIpAddress) the RADIUS client uses it while
         making a request to the server.

         If the address is not configured or is not the address of one of the
         interfaces, the source address is based on the address of the RADIUS
         server. If the server address is in-band, the client uses the system
         ip address. If it is out-of-band, the source address is the address of
         the management interface (the addresses can be found in
         TIMETRA-VRTR-MIB::vRiaIpAddress)."
    DEFVAL { '00000000'H }
    ::= { tmnxSubAcctPlcyEntry 11 }

tmnxSubAcctPlcyServTimeout OBJECT-TYPE
    SYNTAX      Unsigned32 (1..340)
    UNITS       "seconds"
    MAX-ACCESS  read-create
    STATUS      current
    DESCRIPTION
        "The value of tmnxSubAcctPlcyServTimeout specifies, in seconds, the
         timeout between retries towards the same RADIUS server."
    DEFVAL { 5 }
    ::= { tmnxSubAcctPlcyEntry 12 }

tmnxSubAcctPlcyServAlgorithm OBJECT-TYPE
    SYNTAX      TmnxSubRadServAlgorithm {
                    direct     (1),
                    roundRobin (2)
                }
    MAX-ACCESS  read-create
    STATUS      current
    DESCRIPTION
        "The value of tmnxSubAcctPlcyServAlgorithm specifies the algorithm
         used to select a RADIUS server from the list of configured servers
         (tmnxSubAcctPlcyRadServTable)."
    DEFVAL { direct }
    ::= { tmnxSubAcctPlcyEntry 13 }

tmnxSubAcctPlcyUseStdAcctAttrib OBJECT-TYPE
    SYNTAX      TruthValue
    MAX-ACCESS  read-create
    STATUS      deprecated
    DESCRIPTION
        "The value of tmnxSubAcctPlcyUseStdAcctAttrib specifies
         whether or not the standard accounting attributes are used.

         If set to 'true (1)', the standard accounting attributes are used
         for accounting information, instead of the vendor specific attributes.

         This field has been deprecated in the 12.0 release, and is replaced by 
         the 'perQueueStats(31)' and 'stdAcctAttributes(32)' bit-values in 
         tmnxSubAcctPlcyInclAttributes."
    DEFVAL { false }
    ::= { tmnxSubAcctPlcyEntry 14 }

tmnxSubAcctPlcyNasPortPfixType OBJECT-TYPE
    SYNTAX      TmnxSubNasPortPrefixType
    MAX-ACCESS  read-create
    STATUS      current
    DESCRIPTION
        "The value of tmnxSubAcctPlcyNasPortPfixType specifies what type of
         prefix will be added to the NAS-Port-Id attribute if included in RADIUS
         accounting-request messages.
         This field is only applicable if the 'nasPortId' bit is set in
         tmnxSubAcctPlcyInclAttributes."
    DEFVAL { none }
    ::= { tmnxSubAcctPlcyEntry 15 }

tmnxSubAcctPlcyNasPortPfixString OBJECT-TYPE
    SYNTAX      DisplayString (SIZE (0..8))
    MAX-ACCESS  read-create
    STATUS      current
    DESCRIPTION
        "The value of tmnxSubAcctPlcyNasPortPfixString specifies the user
         configurable string to be added as prefix to the NAS-Port attribute if
         included in RADIUS accounting-request messages.
         This field is only applicable if the 'nasPortId' bit is set in
         tmnxSubAcctPlcyInclAttributes and tmnxSubAcctPlcyNasPortPfixType
         is set to 'userString'."
    DEFVAL { "" }
    ::= { tmnxSubAcctPlcyEntry 16 }

tmnxSubAcctPlcyNasPortSfixType OBJECT-TYPE
    SYNTAX      TmnxSubNasPortSuffixType
    MAX-ACCESS  read-create
    STATUS      current
    DESCRIPTION
        "The value of tmnxSubAcctPlcyNasPortSfixType specifies what type of
         suffix will be added to the NAS-Port-Id attribute if included in RADIUS
         accounting-request messages.
         This field is only applicable if the 'nasPortId' bit is set in
         tmnxSubAcctPlcyInclAttributes."
    DEFVAL { none }
    ::= { tmnxSubAcctPlcyEntry 17 }

tmnxSubAcctPlcyNasPortTypeType OBJECT-TYPE
    SYNTAX      TmnxSubNasPortTypeType
    MAX-ACCESS  read-create
    STATUS      current
    DESCRIPTION
        "The value of tmnxSubAcctPlcyNasPortTypeType specifies 
         what kind of value will be put in the RADIUS NAS-Port-Type attribute 
         if included in RADIUS accounting-request messages.

         This field is only applicable if the 'nasPortType'
         bit is set in tmnxSubAcctPlcyInclAttributes."
    DEFVAL { standard }
    ::= { tmnxSubAcctPlcyEntry 18 }

tmnxSubAcctPlcyNasPortTypeValue OBJECT-TYPE
    SYNTAX      Unsigned32 (0..255)
    MAX-ACCESS  read-create
    STATUS      current
    DESCRIPTION
        "The value of tmnxSubAcctPlcyNasPortTypeValue specifies
         what value will be put in the RADIUS NAS-Port-Type attribute 
         if included in RADIUS accounting-request messages.

         This field is only applicable if the 'nasPortType' 
         bit is set in tmnxSubAcctPlcyInclAttributes and the value of the object 
         tmnxSubAcctPlcyNasPortTypeType is equal to 'config'."
    DEFVAL { 0 }
    ::= { tmnxSubAcctPlcyEntry 19 }

tmnxSubAcctPlcyHostAccounting OBJECT-TYPE
    SYNTAX      TmnxSubAcctPlcyAccountingType
    MAX-ACCESS  read-create
    STATUS      current
    DESCRIPTION
        "The value of tmnxSubAcctPlcyHostAccounting specifies 
         whether accounting messages are sent for the host."
    DEFVAL { disabled }
    ::= { tmnxSubAcctPlcyEntry 20 }

tmnxSubAcctPlcyClngStationIdType OBJECT-TYPE
    SYNTAX      TmnxSubCallingStationIdType
    MAX-ACCESS  read-create
    STATUS      current
    DESCRIPTION
        "The value of tmnxSubAcctPlcyClngStationIdType specifies
         what string will be put in the RADIUS Calling-Station-Id 
         attribute if included in RADIUS accounting-request messages.

         This field is only applicable if the 'callingStationId' bit is set in
         tmnxSubAcctPlcyInclAttributes."
    DEFVAL { sapString }
    ::= { tmnxSubAcctPlcyEntry 21 }

tmnxSubAcctPlcyNasPortBitspec OBJECT-TYPE
    SYNTAX      TmnxBinarySpecification
    MAX-ACCESS  read-create
    STATUS      current
    DESCRIPTION
        "The value of tmnxSubAcctPlcyNasPortBitspec specifies
         what number will be put in the RADIUS NAS-Port 
         attribute if included in RADIUS accounting-request messages.

         This field is only applicable if the 'nasPort' bit is set in
         tmnxSubAcctPlcyInclAttributes.
         
         <origin>               ::= 'o' | 'i' | 's' | 'm' | 'p' | 'v' | 'c'

         'c' - ATM VCI (Virtual Channel Identifier)
         'i' - inner VLAN ID
         'm' - MDA number
         'o' - outer VLAN ID
         'p' - port number
         's' - slot number
         'v' - ATM VPI (Virtual Path Identifier)

         Maximum 32 bits can be specified.
         
         If less than 32 bits are specified, the least significant bits are
         used and the omitted higher bits are set to zero.
         
         Example:  *12o*12i*2s01 means 'the 12 least significant bits of the
         outer VLAN ID, followed by the 12 least significant bits of the inner
         VLAN ID, followed by the two least significant bits of the slot number,
         followed by a zero and a one-bit', stored in network order in the least
         significant bits: 0000ooooooooooooiiiiiiiiiiiiss01."
    DEFVAL { "" }
    ::= { tmnxSubAcctPlcyEntry 22 }

tmnxSubAcctPlcyRequestScriptPlcy OBJECT-TYPE
    SYNTAX      TNamedItemOrEmpty
    MAX-ACCESS  read-create
    STATUS      current
    DESCRIPTION
        "The value of tmnxSubAcctPlcyRequestScriptPlcy specifies
        the RADIUS script policy used to change the RADIUS attributes of the
        outgoing Accounting-Request messages."
    DEFVAL { "" }
    ::= { tmnxSubAcctPlcyEntry 23 }

tmnxSubAcctPlcyQueueInstAcct OBJECT-TYPE
    SYNTAX      TmnxSubAcctPlcyAccountingType
    MAX-ACCESS  read-create
    STATUS      current
    DESCRIPTION
        "The value of tmnxSubAcctPlcyQueueInstAcct specifies
         whether accounting messages are sent for the queue-instance.
         The queue-instance is the subscriber on High Scale MDA (HSMDA),
         or the SLA profile instance otherwise."
    DEFVAL { interim }
    ::= { tmnxSubAcctPlcyEntry 24 }

tmnxSubAcctPlcySessionAcct OBJECT-TYPE
    SYNTAX      TmnxSubAcctPlcyAccountingType
    MAX-ACCESS  read-create
    STATUS      current
    DESCRIPTION
        "The value of tmnxSubAcctPlcySessionAcct specifies
         whether accounting messages are sent for the session."
    DEFVAL { disabled }
    ::= { tmnxSubAcctPlcyEntry 25 }
    
tmnxSubAcctPlcyRadiusServerPlcy OBJECT-TYPE
    SYNTAX      TNamedItemOrEmpty
    MAX-ACCESS  read-create
    STATUS      current
    DESCRIPTION
        "The value of tmnxSubAcctPlcyRadiusServerPlcy specifies
         the RADIUS server policy as defined in 
         TIMETRA-RADIUS-MIB::tmnxRadSrvPlcyTable to be applied
         in this RADIUS accounting policy."
    DEFVAL { "" }
    ::= { tmnxSubAcctPlcyEntry 26 }

tmnxSubAcctPlcyUpdateIvlJitter OBJECT-TYPE
    SYNTAX      INTEGER( -10 | 0..3600 )
    MAX-ACCESS  read-create
    STATUS      current
    DESCRIPTION
        "The value of tmnxSubAcctPlcyUpdateIvlJitter specifies the amount of
         jitter to be applied on the update interval which is 
         configured in tmnxSubAcctPlcyUpdateIvl and can be overrruled by RADIUS.
         
         A value between 0..3600 specifies the amount of jitter in seconds.

         The (default) value -10 corresponds to a jitter value of 10% of 
         the update interval.
         
         The operational value used by the system will never be bigger then 
         10% of the update interval."
    DEFVAL { -10 }
    ::= { tmnxSubAcctPlcyEntry 27 }

    -- --------------------------------------------------------
-- tmnxSubAcctPlcyRadServTable
-- --------------------------------------------------------
tmnxSubAcctPlcyRadServTable OBJECT-TYPE
    SYNTAX      SEQUENCE OF TmnxSubAcctPlcyRadServEntry
    MAX-ACCESS  not-accessible
    STATUS      current
    DESCRIPTION
        "The tmnxSubAcctPlcyRadServTable has an entry for each RADIUS server
         used for subscriber accounting."
    ::= { tmnxSubMgmtObjects 28 }

tmnxSubAcctPlcyRadServEntry OBJECT-TYPE
    SYNTAX      TmnxSubAcctPlcyRadServEntry
    MAX-ACCESS  not-accessible
    STATUS      current
    DESCRIPTION
        "tmnxSubAcctPlcyRadServEntry is an entry (conceptual row) in the
         tmnxSubAcctPlcyRadServTable. Each entry represents the configuration
         for a RADIUS server. Entries in this table can be created and deleted
         via SNMP SET operations to tmnxSubAcctPlcyRadServRowStatus. Entries
         have a presumed StorageType of nonVolatile."
    INDEX { tmnxSubAcctPlcyRadServPlcyName,
            tmnxSubAcctPlcyRadServIndex }
    ::= { tmnxSubAcctPlcyRadServTable 1 }

TmnxSubAcctPlcyRadServEntry ::=
    SEQUENCE {
        tmnxSubAcctPlcyRadServPlcyName  TNamedItem,
        tmnxSubAcctPlcyRadServIndex     Unsigned32,
        tmnxSubAcctPlcyRadServRowStatus RowStatus,
        tmnxSubAcctPlcyRadServLstMgtChg TimeStamp,
        tmnxSubAcctPlcyRadServAddrType  InetAddressType,
        tmnxSubAcctPlcyRadServAddr      InetAddress,
        tmnxSubAcctPlcyRadServSecret    DisplayString,
        tmnxSubAcctPlcyRadServAcctPort  Unsigned32,
        tmnxSubAcctPlcyRadServOperState TmnxRadiusServerOperState
    }

tmnxSubAcctPlcyRadServPlcyName OBJECT-TYPE
    SYNTAX      TNamedItem
    MAX-ACCESS  not-accessible
    STATUS      current
    DESCRIPTION
        "The value of tmnxSubAcctPlcyRadServPlcyName specifies a specific
         subscriber accounting policy in the tmnxSubAcctPlcyTable to which this
         RADIUS server is connected. Row creation will be denied if no policy
         with the same name occurs in the tmnxSubAcctPlcyTable."
    ::= { tmnxSubAcctPlcyRadServEntry 1 }

tmnxSubAcctPlcyRadServIndex OBJECT-TYPE
    SYNTAX      Unsigned32 (1..5)
    MAX-ACCESS  not-accessible
    STATUS      current
    DESCRIPTION
        "The value of tmnxSubAcctPlcyRadServIndex specifies a specific RADIUS
         server in the policy."
   ::= { tmnxSubAcctPlcyRadServEntry 2 }

tmnxSubAcctPlcyRadServRowStatus OBJECT-TYPE
    SYNTAX      RowStatus
    MAX-ACCESS  read-create
    STATUS      current
    DESCRIPTION
        "The value of tmnxSubAcctPlcyRadServRowStatus controls the creation and
         deletion of rows in the table."
    ::= { tmnxSubAcctPlcyRadServEntry 3 }

tmnxSubAcctPlcyRadServLstMgtChg OBJECT-TYPE
    SYNTAX      TimeStamp
    MAX-ACCESS  read-only
    STATUS      current
    DESCRIPTION
        "The value tmnxSubAcctPlcyRadServLstMgtChg indicates the sysUpTime at
         the time of the most recent management-initiated change to this
         policy server."
    ::= { tmnxSubAcctPlcyRadServEntry 4 }

tmnxSubAcctPlcyRadServAddrType OBJECT-TYPE
    SYNTAX      InetAddressType
    MAX-ACCESS  read-create
    STATUS      current
    DESCRIPTION
        "The value of tmnxSubAcctPlcyRadServAddrType specifies the type of
         address stored in tmnxSubAcctPlcyRadServAddr."
    DEFVAL { ipv4 }
    ::= { tmnxSubAcctPlcyRadServEntry 5 }

tmnxSubAcctPlcyRadServAddr OBJECT-TYPE
    SYNTAX      InetAddress
    MAX-ACCESS  read-create
    STATUS      current
    DESCRIPTION
        "The value of tmnxSubAcctPlcyRadServAddr specifies the IP address of
         the RADIUS server. A valid unicast IP address must be specified for
         row creation to succeed."
    ::= { tmnxSubAcctPlcyRadServEntry 6 }

tmnxSubAcctPlcyRadServSecret OBJECT-TYPE
    SYNTAX      DisplayString (SIZE (0|1..20))
    MAX-ACCESS  read-create
    STATUS      current
    DESCRIPTION
        "The value of tmnxSubAcctPlcyRadServSecret specifies the secret key
         associated with the RADIUS server. An empty key is not accepted
         as input. However If this object is read an empty string is
         returned."
    ::= { tmnxSubAcctPlcyRadServEntry 7 }

tmnxSubAcctPlcyRadServAcctPort OBJECT-TYPE
    SYNTAX      Unsigned32 (1..65535)
    MAX-ACCESS  read-create
    STATUS      current
    DESCRIPTION
        "The value of tmnxSubAcctPlcyRadServAcctPort specifies the UDP port
         number on which to contact the RADIUS server for accounting."
    DEFVAL { 1813 }
    ::= { tmnxSubAcctPlcyRadServEntry 8 }

tmnxSubAcctPlcyRadServOperState OBJECT-TYPE
    SYNTAX      TmnxRadiusServerOperState
    MAX-ACCESS  read-only
    STATUS      current
    DESCRIPTION
        "The value of tmnxSubAcctPlcyRadServOperState indicates the operational
         state of the RADIUS server."
    ::= { tmnxSubAcctPlcyRadServEntry 9 }

-- --------------------------------------------------------
-- tmnxSubAcctPlcyStatsTable
-- --------------------------------------------------------
tmnxSubAcctPlcyStatsTable OBJECT-TYPE
    SYNTAX      SEQUENCE OF TmnxSubAcctPlcyStatsEntry
    MAX-ACCESS  not-accessible
    STATUS      current
    DESCRIPTION
        "The tmnxSubAcctPlcyStatsTable has an entry for each subscriber RADIUS
         accounting policy configured in the system."
    ::= { tmnxSubMgmtObjects 29 }

tmnxSubAcctPlcyStatsEntry OBJECT-TYPE
    SYNTAX      TmnxSubAcctPlcyStatsEntry
    MAX-ACCESS  not-accessible
    STATUS      current
    DESCRIPTION
        "Each row entry represents a collection of statistics for a subscriber
         RADIUS accounting policy in the system.

         Entries cannot be created and deleted via SNMP SET operations."
    INDEX { tmnxSubAcctPlcyName }
    ::= { tmnxSubAcctPlcyStatsTable 1 }

TmnxSubAcctPlcyStatsEntry ::=
    SEQUENCE {
        tmnxSubAcctPlcyTxRequests  Counter32,
        tmnxSubAcctPlcyRxResponses Counter32,
        tmnxSubAcctPlcyReqTimeouts Counter32,
        tmnxSubAcctPlcySendRetries Counter32,
        tmnxSubAcctPlcySendFail    Counter32
    }

tmnxSubAcctPlcyTxRequests OBJECT-TYPE
    SYNTAX      Counter32
    MAX-ACCESS  read-only
    STATUS      current
    DESCRIPTION
        "The value of tmnxSubAcctPlcyTxRequests indicates the number of
         accounting requests transmitted for this policy."
    ::= { tmnxSubAcctPlcyStatsEntry 1 }

tmnxSubAcctPlcyRxResponses OBJECT-TYPE
    SYNTAX      Counter32
    MAX-ACCESS  read-only
    STATUS      current
    DESCRIPTION
        "The value of tmnxSubAcctPlcyRxResponses indicates the number of
         accounting responses received for this policy."
    ::= { tmnxSubAcctPlcyStatsEntry 2 }

tmnxSubAcctPlcyReqTimeouts OBJECT-TYPE
    SYNTAX      Counter32
    MAX-ACCESS  read-only
    STATUS      current
    DESCRIPTION
        "The value of tmnxSubAcctPlcyReqTimeouts indicates the number of
         accounting requests which have timed out for this policy."
    ::= { tmnxSubAcctPlcyStatsEntry 3 }

tmnxSubAcctPlcySendRetries OBJECT-TYPE
    SYNTAX      Counter32
    MAX-ACCESS  read-only
    STATUS      current
    DESCRIPTION
        "The value of tmnxSubAcctPlcySendRetries indicates the number of
         retries to a different server for a single accounting request for this
         policy."
    ::= { tmnxSubAcctPlcyStatsEntry 4 }

tmnxSubAcctPlcySendFail OBJECT-TYPE
    SYNTAX      Counter32
    MAX-ACCESS  read-only
    STATUS      current
    DESCRIPTION
        "The value of tmnxSubAcctPlcySendFail indicates how many
         accounting requests failed because the packet could not be
         sent out."
    ::= { tmnxSubAcctPlcyStatsEntry 5 }

-- --------------------------------------------------------
-- tmnxSubAcctPlcyRadStatsTable
-- --------------------------------------------------------
tmnxSubAcctPlcyRadStatsTable OBJECT-TYPE
    SYNTAX      SEQUENCE OF TmnxSubAcctPlcyRadStatsEntry
    MAX-ACCESS  not-accessible
    STATUS      current
    DESCRIPTION
        "The tmnxSubAcctPlcyRadStatsTable has an entry for each RADIUS
         accounting server configured in the system."
    ::= { tmnxSubMgmtObjects 30 }

tmnxSubAcctPlcyRadStatsEntry OBJECT-TYPE
    SYNTAX      TmnxSubAcctPlcyRadStatsEntry
    MAX-ACCESS  not-accessible
    STATUS      current
    DESCRIPTION
        "Each row entry represents a collection of statistics for a specific
         RADIUS server in a subscriber accounting policy in the system.

         Entries cannot be created and deleted via SNMP SET operations."
    INDEX { tmnxSubAcctPlcyRadServPlcyName,
            tmnxSubAcctPlcyRadServIndex }
    ::= { tmnxSubAcctPlcyRadStatsTable 1 }

TmnxSubAcctPlcyRadStatsEntry ::=
    SEQUENCE {
        tmnxSubAcctPlcyRadTxRequests  Counter32,
        tmnxSubAcctPlcyRadRxResponses Counter32,
        tmnxSubAcctPlcyRadReqTimeouts Counter32,
        tmnxSubAcctPlcyRadReqSendFail Counter32
    }

tmnxSubAcctPlcyRadTxRequests OBJECT-TYPE
    SYNTAX      Counter32
    MAX-ACCESS  read-only
    STATUS      current
    DESCRIPTION
        "The value of tmnxSubAcctPlcyRadTxRequests indicates the number of
         accounting requests transmitted for this server."
    ::= { tmnxSubAcctPlcyRadStatsEntry 1 }

tmnxSubAcctPlcyRadRxResponses OBJECT-TYPE
    SYNTAX      Counter32
    MAX-ACCESS  read-only
    STATUS      current
    DESCRIPTION
        "The value of tmnxSubAcctPlcyRadRxResponses indicates the number of
         accounting responses received for this server."
    ::= { tmnxSubAcctPlcyRadStatsEntry 2 }

tmnxSubAcctPlcyRadReqTimeouts OBJECT-TYPE
    SYNTAX      Counter32
    MAX-ACCESS  read-only
    STATUS      current
    DESCRIPTION
        "The value of tmnxSubAcctPlcyRadReqTimeouts indicates the number of
         accounting requests which have timed out for this server."
    ::= { tmnxSubAcctPlcyRadStatsEntry 3 }

tmnxSubAcctPlcyRadReqSendFail OBJECT-TYPE
    SYNTAX      Counter32
    MAX-ACCESS  read-only
    STATUS      current
    DESCRIPTION
        "The value of tmnxSubAcctPlcyRadReqSendFail indicates the number of
         accounting requests failed because the packet could not be
         sent out."
    ::= { tmnxSubAcctPlcyRadStatsEntry 4 }

-- --------------------------------------------------------
-- tmnxSubHsmdaIngQueueOvrTable
-- --------------------------------------------------------
tmnxSubHsmdaIngQueueOvrTableLC  OBJECT-TYPE
    SYNTAX          TimeStamp
    MAX-ACCESS      read-only
    STATUS          obsolete
    DESCRIPTION
        "The value of tmnxSubHsmdaIngQueueOvrTableLC indicates the
         sysUpTime at the time of the last modification
         of tmnxSubHsmdaIngQueueOvrTable.

         If no changes were made to the entry since the last
         re-initialization of the local network management subsystem,
         then this object contains a zero value.

         This object is obsoleted in 10.0 Release."
    ::= { tmnxSubMgmtObjects 32 }

tmnxSubHsmdaIngQueueOvrTable OBJECT-TYPE
    SYNTAX      SEQUENCE OF TmnxSubHsmdaIngQueueOvrEntry
    MAX-ACCESS  not-accessible
    STATUS      obsolete
    DESCRIPTION
        "The tmnxSubHsmdaIngQueueOvrTable has an entry for each Hsmda
         ingress queue override configured on the system.

         This table is obsoleted in 10.0 Release."    
    ::= { tmnxSubMgmtObjects 33 }

tmnxSubHsmdaIngQueueOvrEntry     OBJECT-TYPE
    SYNTAX      TmnxSubHsmdaIngQueueOvrEntry
    MAX-ACCESS  not-accessible
    STATUS      obsolete
    DESCRIPTION
        "Each row entry represents a Hsmda ingress queue override record.

         Entries are created and deleted via SNMP SET operations on
         tmnxSubHsmdaIngQueueOvrRowStat."
    INDEX { tmnxSubProfName,
            tSapIngressIndex,
            tSapIngressHsmdaQueue }
    ::= { tmnxSubHsmdaIngQueueOvrTable 1}

TmnxSubHsmdaIngQueueOvrEntry ::= SEQUENCE
    {
        tmnxSubHsmdaIngQueueOvrRowStat        RowStatus,
        tmnxSubHsmdaIngQueueOvrLastChgd       TimeStamp,
        tmnxSubHsmdaIngQueueOvrPIR            THsmdaPIRKRateOverride,
        tmnxSubHsmdaIngQueueOvrCIR            THsmdaCIRKRateOverride,
        tmnxSubHsmdaIngQueueOvrSlpPlcy        TNamedItemOrEmpty
    }

tmnxSubHsmdaIngQueueOvrRowStat        OBJECT-TYPE
    SYNTAX      RowStatus
    MAX-ACCESS  read-create
    STATUS      obsolete
    DESCRIPTION
        "The value of tmnxSubHsmdaIngQueueOvrRowStat controls the creation
         and deletion of rows in this table."
    ::= { tmnxSubHsmdaIngQueueOvrEntry  1 }

tmnxSubHsmdaIngQueueOvrLastChgd  OBJECT-TYPE
    SYNTAX      TimeStamp
    MAX-ACCESS  read-only
    STATUS      obsolete
    DESCRIPTION
        "The value of tmnxSubHsmdaIngQueueOvrLastChgd indicates the sysUpTime
         at the time of the most recent management-initiated change to this
         table row."
    ::= { tmnxSubHsmdaIngQueueOvrEntry  2 }

tmnxSubHsmdaIngQueueOvrPIR        OBJECT-TYPE
    SYNTAX      THsmdaPIRKRateOverride
    UNITS       "kbps"
    MAX-ACCESS  read-create
    STATUS      obsolete
    DESCRIPTION
        "The value of tmnxSubHsmdaIngQueueOvrPIR specifies the PIR rate in kbps
         allowed for this Hsmda ingress queue."
    DEFVAL { -2 }
    ::= { tmnxSubHsmdaIngQueueOvrEntry  3 }

tmnxSubHsmdaIngQueueOvrCIR        OBJECT-TYPE
    SYNTAX      THsmdaCIRKRateOverride
    UNITS       "kbps"
    MAX-ACCESS  read-create
    STATUS      obsolete
    DESCRIPTION
        "The value of tmnxSubHsmdaIngQueueOvrCIR specifies the CIR rate in kbps
         allowed for this Hsmda ingress queue."
    DEFVAL { -2 }
    ::= { tmnxSubHsmdaIngQueueOvrEntry  4 }

tmnxSubHsmdaIngQueueOvrSlpPlcy        OBJECT-TYPE
    SYNTAX      TNamedItemOrEmpty
    MAX-ACCESS  read-create
    STATUS      obsolete
    DESCRIPTION
        "The value of tmnxSubHsmdaIngQueueOvrSlpPlcy specifies the slope
         policy that defines the RED slopes for this Hsmda ingress queue."
    DEFVAL { "" }
    ::= { tmnxSubHsmdaIngQueueOvrEntry  5 }

-- --------------------------------------------------------
-- tmnxSubHsmdaEgrQueueOvrTable
-- --------------------------------------------------------
tmnxSubHsmdaEgrQueueOvrTblLC  OBJECT-TYPE
    SYNTAX          TimeStamp
    MAX-ACCESS      read-only
    STATUS          obsolete
    DESCRIPTION
        "The value of tmnxSubHsmdaEgrQueueOvrTblLC indicates the
         sysUpTime at the time of the last modification
         of tmnxSubHsmdaEgrQueueOvrTable.

         If no changes were made to the entry since the last
         re-initialization of the local network management subsystem,
         then this object contains a zero value.

         This object is obsoleted in 10.0 Release."
    ::= { tmnxSubMgmtObjects 34 }

tmnxSubHsmdaEgrQueueOvrTable OBJECT-TYPE
    SYNTAX      SEQUENCE OF TmnxSubHsmdaEgrQueueOvrEntry
    MAX-ACCESS  not-accessible
    STATUS      obsolete
    DESCRIPTION
        "The tmnxSubHsmdaEgrQueueOvrTable has an entry for each Hsmda egress
         queue override configured on the system.

         This table is obsoleted in 10.0 Release."
    ::= { tmnxSubMgmtObjects 35 }

tmnxSubHsmdaEgrQueueOvrEntry     OBJECT-TYPE
    SYNTAX      TmnxSubHsmdaEgrQueueOvrEntry
    MAX-ACCESS  not-accessible
    STATUS      obsolete
    DESCRIPTION
        "Each row entry represents a Hsmda egress queue override record.

         Entries are created and deleted via SNMP SET operations on
         tmnxSubHsmdaEgrQueueOvrRowStat."
    INDEX { tmnxSubProfName,
            tSapEgressIndex,
            tSapEgressHsmdaQueue }
    ::= { tmnxSubHsmdaEgrQueueOvrTable 1}

TmnxSubHsmdaEgrQueueOvrEntry ::= SEQUENCE
    {
        tmnxSubHsmdaEgrQueueOvrRowStat        RowStatus,
        tmnxSubHsmdaEgrQueueOvrLastChgd       TimeStamp,
        tmnxSubHsmdaEgrQueueOvrPIR            THsmdaPIRKRateOverride,
        tmnxSubHsmdaEgrQueueOvrCIR            THsmdaCIRKRateOverride,
        tmnxSubHsmdaEgrQueueOvrSlpPlcy        TNamedItemOrEmpty
    }

tmnxSubHsmdaEgrQueueOvrRowStat        OBJECT-TYPE
    SYNTAX      RowStatus
    MAX-ACCESS  read-create
    STATUS      obsolete
    DESCRIPTION
        "The value of tmnxSubHsmdaEgrQueueOvrRowStat controls the creation
         and deletion of rows in this table."
    ::= { tmnxSubHsmdaEgrQueueOvrEntry  1 }

tmnxSubHsmdaEgrQueueOvrLastChgd        OBJECT-TYPE
    SYNTAX      TimeStamp
    MAX-ACCESS  read-only
    STATUS      obsolete
    DESCRIPTION
        "The value of tmnxSubHsmdaEgrQueueOvrLastChgd indicates the sysUpTime
         at the time of the most recent management-initiated change to this
         table row."
    ::= { tmnxSubHsmdaEgrQueueOvrEntry  2 }

tmnxSubHsmdaEgrQueueOvrPIR        OBJECT-TYPE
    SYNTAX      THsmdaPIRKRateOverride
    UNITS       "kbps"
    MAX-ACCESS  read-create
    STATUS      obsolete
    DESCRIPTION
        "The value of tmnxSubHsmdaEgrQueueOvrPIR specifies the PIR rate in kbps
         allowed for this Hsmda egress queue."
    DEFVAL { -2 }
    ::= { tmnxSubHsmdaEgrQueueOvrEntry  3 }

tmnxSubHsmdaEgrQueueOvrCIR        OBJECT-TYPE
    SYNTAX      THsmdaCIRKRateOverride
    UNITS       "kbps"
    MAX-ACCESS  read-create
    STATUS      obsolete
    DESCRIPTION
        "The value of tmnxSubHsmdaEgrQueueOvrCIR specifies the CIR rate in kbps
         allowed for this Hsmda egress queue."
    DEFVAL { -2 }
    ::= { tmnxSubHsmdaEgrQueueOvrEntry  4 }

tmnxSubHsmdaEgrQueueOvrSlpPlcy        OBJECT-TYPE
    SYNTAX      TNamedItemOrEmpty
    MAX-ACCESS  read-create
    STATUS      obsolete
    DESCRIPTION
        "The value of tmnxSubHsmdaEgrQueueOvrSlpPlcy specifies the slope
         policy that defines the RED slopes for this Hsmda egress queue."
    DEFVAL { "" }
    ::= { tmnxSubHsmdaEgrQueueOvrEntry  5 }

-- --------------------------------------------------------
-- tmnxSubscriberHsmdaStatsTable
-- --------------------------------------------------------
tmnxSubscriberHsmdaStatsTable OBJECT-TYPE
    SYNTAX      SEQUENCE OF TmnxSubscriberHsmdaStatsEntry
    MAX-ACCESS  not-accessible
    STATUS      current
    DESCRIPTION
        "A table that contains HSMDA subscriber statistics."
    ::= { tmnxSubMgmtObjects 36 }

tmnxSubscriberHsmdaStatsEntry    OBJECT-TYPE
    SYNTAX      TmnxSubscriberHsmdaStatsEntry
    MAX-ACCESS  not-accessible
    STATUS      current
    DESCRIPTION
        "HSMDA statistics for a specific subscriber."
    INDEX { tmnxSubInfoSubIdent }
    ::= { tmnxSubscriberHsmdaStatsTable 1 }

TmnxSubscriberHsmdaStatsEntry ::= SEQUENCE {
        tmnxSubHsmdaStSubPortId          TmnxPortID,
        tmnxSubHsmdaStIngOffTotalPkt     Counter64,
        tmnxSubHsmdaStIngOffTotalOct     Counter64,
        tmnxSubHsmdaStIngFwdInProfPkt    Counter64,
        tmnxSubHsmdaStIngFwdOutProfPkt   Counter64,
        tmnxSubHsmdaStIngFwdInProfOct    Counter64,
        tmnxSubHsmdaStIngFwdOutProfOct   Counter64,
        tmnxSubHsmdaStIngDropHiPrioPkt   Counter64,
        tmnxSubHsmdaStIngDropLoPrioPkt   Counter64,
        tmnxSubHsmdaStIngDropHiPrioOct   Counter64,
        tmnxSubHsmdaStIngDropLoPrioOct   Counter64,
        tmnxSubHsmdaStEgrFwdInProfPkt    Counter64,
        tmnxSubHsmdaStEgrFwdOutProfPkt   Counter64,
        tmnxSubHsmdaStEgrFwdInProfOct    Counter64,
        tmnxSubHsmdaStEgrFwdOutProfOct   Counter64,
        tmnxSubHsmdaStEgrDropInProfPkt   Counter64,
        tmnxSubHsmdaStEgrDropOutProfPkt  Counter64,
        tmnxSubHsmdaStEgrDropInProfOct   Counter64,
        tmnxSubHsmdaStEgrDropOutProfOct  Counter64,
        tmnxSubHsmdaStIngOffHiPrioPkt    Counter64,
        tmnxSubHsmdaStIngOffHiPrioPktLw  Counter32,
        tmnxSubHsmdaStIngOffHiPrioPktHw  Counter32,
        tmnxSubHsmdaStIngOffHiPrioOct    Counter64,
        tmnxSubHsmdaStIngOffHiPrioOctLw  Counter32,
        tmnxSubHsmdaStIngOffHiPrioOctHw  Counter32,
        tmnxSubHsmdaStIngOffLoPrioPkt    Counter64,
        tmnxSubHsmdaStIngOffLoPrioPktLw  Counter32,
        tmnxSubHsmdaStIngOffLoPrioPktHw  Counter32,
        tmnxSubHsmdaStIngOffLoPrioOct    Counter64,
        tmnxSubHsmdaStIngOffLoPrioOctLw  Counter32,
        tmnxSubHsmdaStIngOffLoPrioOctHw  Counter32,
        tmnxSubHsmdaStIngOffUncolPkt     Counter64,
        tmnxSubHsmdaStIngOffUncolPktLw   Counter32,
        tmnxSubHsmdaStIngOffUncolPktHw   Counter32,
        tmnxSubHsmdaStIngOffUncolOct     Counter64,
        tmnxSubHsmdaStIngOffUncolOctLw   Counter32,
        tmnxSubHsmdaStIngOffUncolOctHw   Counter32,
        tmnxSubHsmdaStIngOffV4Packets    Counter64,
        tmnxSubHsmdaStIngOffV4Octets     Counter64,
        tmnxSubHsmdaStIngOffV6Packets    Counter64,
        tmnxSubHsmdaStIngOffV6Octets     Counter64,
        tmnxSubHsmdaStIngDropV4Packets   Counter64,
        tmnxSubHsmdaStIngDropV4Octets    Counter64,
        tmnxSubHsmdaStIngDropV6Packets   Counter64,
        tmnxSubHsmdaStIngDropV6Octets    Counter64,
        tmnxSubHsmdaStIngFwdV4Packets    Counter64,
        tmnxSubHsmdaStIngFwdV4Octets     Counter64,
        tmnxSubHsmdaStIngFwdV6Packets    Counter64,
        tmnxSubHsmdaStIngFwdV6Octets     Counter64,
        tmnxSubHsmdaStEgrDropV4Packets   Counter64,
        tmnxSubHsmdaStEgrDropV4Octets    Counter64,
        tmnxSubHsmdaStEgrDropV6Packets   Counter64,
        tmnxSubHsmdaStEgrDropV6Octets    Counter64,
        tmnxSubHsmdaStEgrFwdV4Packets    Counter64,
        tmnxSubHsmdaStEgrFwdV4Octets     Counter64,
        tmnxSubHsmdaStEgrFwdV6Packets    Counter64,
        tmnxSubHsmdaStEgrFwdV6Octets     Counter64
    }

tmnxSubHsmdaStSubPortId        OBJECT-TYPE
    SYNTAX      TmnxPortID
    MAX-ACCESS  read-only
    STATUS      current
    DESCRIPTION
        "The value of tmnxSubHsmdaStSubPortId indicates the access port
         for this entry."
    ::= { tmnxSubscriberHsmdaStatsEntry 1 }

tmnxSubHsmdaStIngOffTotalPkt        OBJECT-TYPE
    SYNTAX      Counter64
    MAX-ACCESS  read-only
    STATUS      current
    DESCRIPTION
        "The value of tmnxSubHsmdaStIngOffTotalPkt indicates the
         total number of packets offered on ingress for
         this subscriber."
    ::= { tmnxSubscriberHsmdaStatsEntry 2 }

tmnxSubHsmdaStIngOffTotalOct        OBJECT-TYPE
    SYNTAX      Counter64
    MAX-ACCESS  read-only
    STATUS      current
    DESCRIPTION
        "The value of tmnxSubHsmdaStIngOffTotalOct indicates the
         total number of octets offered on ingress for
         this subscriber."
    ::= { tmnxSubscriberHsmdaStatsEntry 3 }

tmnxSubHsmdaStIngFwdInProfPkt        OBJECT-TYPE
    SYNTAX      Counter64
    MAX-ACCESS  read-only
    STATUS      current
    DESCRIPTION
        "The value of tmnxSubHsmdaStIngFwdInProfPkt indicates the
         number of in-profile packets forwarded by the ingress
         Qchip for this subscriber."
    ::= { tmnxSubscriberHsmdaStatsEntry 4 }

tmnxSubHsmdaStIngFwdOutProfPkt        OBJECT-TYPE
    SYNTAX      Counter64
    MAX-ACCESS  read-only
    STATUS      current
    DESCRIPTION
        "The value of tmnxSubHsmdaStIngFwdOutProfPkt indicates the
         number of out-of-profile packets forwarded by the ingress
         Qchip for this subscriber."
    ::= { tmnxSubscriberHsmdaStatsEntry 5 }

tmnxSubHsmdaStIngFwdInProfOct        OBJECT-TYPE
    SYNTAX      Counter64
    MAX-ACCESS  read-only
    STATUS      current
    DESCRIPTION
        "The value of tmnxSubHsmdaStIngFwdInProfOct indicates the
         number of out-of-profile octets forwarded by the ingress
         Qchip for this subscriber."
    ::= { tmnxSubscriberHsmdaStatsEntry 6 }

tmnxSubHsmdaStIngFwdOutProfOct        OBJECT-TYPE
    SYNTAX      Counter64
    MAX-ACCESS  read-only
    STATUS      current
    DESCRIPTION
        "The value of tmnxSubHsmdaStIngFwdOutProfOct indicates the
         number of out-of-profile octets forwarded by the ingress
         Qchip for this subscriber."
    ::= { tmnxSubscriberHsmdaStatsEntry 7 }

tmnxSubHsmdaStIngDropHiPrioPkt        OBJECT-TYPE
    SYNTAX      Counter64
    MAX-ACCESS  read-only
    STATUS      current
    DESCRIPTION
        "The value of tmnxSubHsmdaStIngDropHiPrioPkt indicates the
         number of high-priority packets discarded by the ingress
         Qchip for this subscriber."
    ::= { tmnxSubscriberHsmdaStatsEntry 8 }

tmnxSubHsmdaStIngDropLoPrioPkt        OBJECT-TYPE
    SYNTAX      Counter64
    MAX-ACCESS  read-only
    STATUS      current
    DESCRIPTION
        "The value of tmnxSubHsmdaStIngDropLoPrioPkt indicates the
         number of low-priority packets discarded by the ingress
         Qchip for this subscriber."
    ::= { tmnxSubscriberHsmdaStatsEntry 9 }

tmnxSubHsmdaStIngDropHiPrioOct        OBJECT-TYPE
    SYNTAX      Counter64
    MAX-ACCESS  read-only
    STATUS      current
    DESCRIPTION
        "The value of tmnxSubHsmdaStIngDropHiPrioOct indicates the
         number of high-priority octets discarded by the ingress
         Qchip for this subscriber."
    ::= { tmnxSubscriberHsmdaStatsEntry 10 }

tmnxSubHsmdaStIngDropLoPrioOct        OBJECT-TYPE
    SYNTAX      Counter64
    MAX-ACCESS  read-only
    STATUS      current
    DESCRIPTION
        "The value of tmnxSubHsmdaStIngDropLoPrioOct indicates the
         number of low-priority octets discarded by the ingress
         Qchip for this subscriber."
    ::= { tmnxSubscriberHsmdaStatsEntry 11 }

tmnxSubHsmdaStEgrFwdInProfPkt        OBJECT-TYPE
    SYNTAX      Counter64
    MAX-ACCESS  read-only
    STATUS      current
    DESCRIPTION
        "The value of tmnxSubHsmdaStEgrFwdInProfPkt indicates the
         number of in-profile packets forwarded by the egress
         Qchip for this subscriber."
    ::= { tmnxSubscriberHsmdaStatsEntry 12 }

tmnxSubHsmdaStEgrFwdOutProfPkt        OBJECT-TYPE
    SYNTAX      Counter64
    MAX-ACCESS  read-only
    STATUS      current
    DESCRIPTION
        "The value of tmnxSubHsmdaStEgrFwdOutProfPkt indicates the
         number of out-of-profile packets forwarded by the egress
         Qchip for this subscriber."
    ::= { tmnxSubscriberHsmdaStatsEntry 13 }

tmnxSubHsmdaStEgrFwdInProfOct        OBJECT-TYPE
    SYNTAX      Counter64
    MAX-ACCESS  read-only
    STATUS      current
    DESCRIPTION
        "The value of tmnxSubHsmdaStEgrFwdInProfOct indicates the
         number of out-of-profile octets forwarded by the egress
         Qchip for this subscriber."
    ::= { tmnxSubscriberHsmdaStatsEntry 14 }

tmnxSubHsmdaStEgrFwdOutProfOct        OBJECT-TYPE
    SYNTAX      Counter64
    MAX-ACCESS  read-only
    STATUS      current
    DESCRIPTION
        "The value of tmnxSubHsmdaStEgrFwdOutProfOct indicates the
         number of out-of-profile octets forwarded by the egress
         Qchip for this subscriber."
    ::= { tmnxSubscriberHsmdaStatsEntry 15 }

tmnxSubHsmdaStEgrDropInProfPkt        OBJECT-TYPE
    SYNTAX      Counter64
    MAX-ACCESS  read-only
    STATUS      current
    DESCRIPTION
        "The value of tmnxSubHsmdaStEgrDropInProfPkt indicates the
         number of high-priority packets discarded by the egress
         Qchip for this subscriber."
    ::= { tmnxSubscriberHsmdaStatsEntry 16 }

tmnxSubHsmdaStEgrDropOutProfPkt        OBJECT-TYPE
    SYNTAX      Counter64
    MAX-ACCESS  read-only
    STATUS      current
    DESCRIPTION
        "The value of tmnxSubHsmdaStEgrDropOutProfPkt indicates the
         number of low-priority packets discarded by the egress
         Qchip for this subscriber."
    ::= { tmnxSubscriberHsmdaStatsEntry 17 }

tmnxSubHsmdaStEgrDropInProfOct        OBJECT-TYPE
    SYNTAX      Counter64
    MAX-ACCESS  read-only
    STATUS      current
    DESCRIPTION
        "The value of tmnxSubHsmdaStEgrDropInProfOct indicates the
         number of high-priority octets discarded by the egress
         Qchip for this subscriber."
    ::= { tmnxSubscriberHsmdaStatsEntry 18 }

tmnxSubHsmdaStEgrDropOutProfOct        OBJECT-TYPE
    SYNTAX      Counter64
    MAX-ACCESS  read-only
    STATUS      current
    DESCRIPTION
        "The value of tmnxSubHsmdaStEgrDropOutProfOct indicates the
         number of low-priority octets discarded by the egress
         Qchip for this subscriber."
    ::= { tmnxSubscriberHsmdaStatsEntry 19 }

tmnxSubHsmdaStIngOffHiPrioPkt        OBJECT-TYPE
    SYNTAX      Counter64
    MAX-ACCESS  read-only
    STATUS      current
    DESCRIPTION
        "The value of tmnxSubHsmdaStIngOffHiPrioPkt indicates 
         the number of high priority packets offered by the Pchip to the Qchip 
         for this subscriber.
         
         This is only supported for subscribers on an HSMDA-2."
    ::= { tmnxSubscriberHsmdaStatsEntry 30 }

tmnxSubHsmdaStIngOffHiPrioPktLw        OBJECT-TYPE
    SYNTAX      Counter32
    MAX-ACCESS  read-only
    STATUS      current
    DESCRIPTION
        "The value of tmnxSubHsmdaStIngOffHiPrioPktLw indicates 
         the lower 32-bits word of the value of tmnxSubHsmdaStIngOffHiPrioPkt."
    ::= { tmnxSubscriberHsmdaStatsEntry 31 }

tmnxSubHsmdaStIngOffHiPrioPktHw        OBJECT-TYPE
    SYNTAX      Counter32
    MAX-ACCESS  read-only
    STATUS      current
    DESCRIPTION
        "The value of tmnxSubHsmdaStIngOffHiPrioPktHw indicates 
         the higher 32-bits word of the value of tmnxSubHsmdaStIngOffHiPrioPkt."
    ::= { tmnxSubscriberHsmdaStatsEntry 32 }

tmnxSubHsmdaStIngOffHiPrioOct        OBJECT-TYPE
    SYNTAX      Counter64
    MAX-ACCESS  read-only
    STATUS      current
    DESCRIPTION
        "The value of tmnxSubHsmdaStIngOffHiPrioOct indicates 
         the number of high priority octets offered by the Pchip to the Qchip 
         for this subscriber.
         
         This is only supported for subscribers on an HSMDA-2."
    ::= { tmnxSubscriberHsmdaStatsEntry 33 }

tmnxSubHsmdaStIngOffHiPrioOctLw        OBJECT-TYPE
    SYNTAX      Counter32
    MAX-ACCESS  read-only
    STATUS      current
    DESCRIPTION
        "The value of tmnxSubHsmdaStIngOffHiPrioPktLw indicates 
         the lower 32-bits word of the value of tmnxSubHsmdaStIngOffHiPrioOct."
    ::= { tmnxSubscriberHsmdaStatsEntry 34 }

tmnxSubHsmdaStIngOffHiPrioOctHw        OBJECT-TYPE
    SYNTAX      Counter32
    MAX-ACCESS  read-only
    STATUS      current
    DESCRIPTION
        "The value of tmnxSubHsmdaStIngOffHiPrioPktHw indicates 
         the higher 32-bits word of the value of tmnxSubHsmdaStIngOffHiPrioOct."
    ::= { tmnxSubscriberHsmdaStatsEntry 35 }

tmnxSubHsmdaStIngOffLoPrioPkt        OBJECT-TYPE
    SYNTAX      Counter64
    MAX-ACCESS  read-only
    STATUS      current
    DESCRIPTION
        "The value of tmnxSubHsmdaStIngOffLoPrioPkt indicates 
         the number of low priority packets offered by the Pchip to the Qchip 
         for this subscriber.
         
         This is only supported for subscribers on an HSMDA-2."
    ::= { tmnxSubscriberHsmdaStatsEntry 36 }

tmnxSubHsmdaStIngOffLoPrioPktLw        OBJECT-TYPE
    SYNTAX      Counter32
    MAX-ACCESS  read-only
    STATUS      current
    DESCRIPTION
        "The value of tmnxSubHsmdaStIngOffHiPrioPktLw indicates 
         the lower 32-bits word of the value of tmnxSubHsmdaStIngOffLoPrioPkt."
    ::= { tmnxSubscriberHsmdaStatsEntry 37 }

tmnxSubHsmdaStIngOffLoPrioPktHw        OBJECT-TYPE
    SYNTAX      Counter32
    MAX-ACCESS  read-only
    STATUS      current
    DESCRIPTION
        "The value of tmnxSubHsmdaStIngOffLoPrioPktHw indicates 
         the higher 32-bits word of the value of tmnxSubHsmdaStIngOffLoPrioPkt."
    ::= { tmnxSubscriberHsmdaStatsEntry 38 }

tmnxSubHsmdaStIngOffLoPrioOct        OBJECT-TYPE
    SYNTAX      Counter64
    MAX-ACCESS  read-only
    STATUS      current
    DESCRIPTION
        "The value of tmnxSubHsmdaStIngOffLoPrioOct indicates 
         the number of low priority octets offered by the Pchip to the Qchip 
         for this subscriber.
         
         This is only supported for subscribers on an HSMDA-2."
    ::= { tmnxSubscriberHsmdaStatsEntry 39 }

tmnxSubHsmdaStIngOffLoPrioOctLw        OBJECT-TYPE
    SYNTAX      Counter32
    MAX-ACCESS  read-only
    STATUS      current
    DESCRIPTION
        "The value of tmnxSubHsmdaStIngOffHiPrioPktLw indicates 
         the lower 32-bits word of the value of tmnxSubHsmdaStIngOffLoPrioOct."
    ::= { tmnxSubscriberHsmdaStatsEntry 40 }

tmnxSubHsmdaStIngOffLoPrioOctHw        OBJECT-TYPE
    SYNTAX      Counter32
    MAX-ACCESS  read-only
    STATUS      current
    DESCRIPTION
        "The value of tmnxSubHsmdaStIngOffLoPrioOctHw indicates 
         the higher 32-bits word of the value of tmnxSubHsmdaStIngOffLoPrioOct."
    ::= { tmnxSubscriberHsmdaStatsEntry 41 }

tmnxSubHsmdaStIngOffUncolPkt        OBJECT-TYPE
    SYNTAX      Counter64
    MAX-ACCESS  read-only
    STATUS      current
    DESCRIPTION
        "The value of tmnxSubHsmdaStIngOffUncolPkt indicates 
         the number of uncolored packets offered by the Pchip to the Qchip 
         for this subscriber.
         
         This is only supported for subscribers on an HSMDA-2."
    ::= { tmnxSubscriberHsmdaStatsEntry 42 }

tmnxSubHsmdaStIngOffUncolPktLw        OBJECT-TYPE
    SYNTAX      Counter32
    MAX-ACCESS  read-only
    STATUS      current
    DESCRIPTION
        "The value of tmnxSubHsmdaStIngOffUncolPktLw indicates 
         the lower 32-bits word of the value of tmnxSubHsmdaStIngOffUncolPkt."
    ::= { tmnxSubscriberHsmdaStatsEntry 43 }

tmnxSubHsmdaStIngOffUncolPktHw        OBJECT-TYPE
    SYNTAX      Counter32
    MAX-ACCESS  read-only
    STATUS      current
    DESCRIPTION
        "The value of tmnxSubHsmdaStIngOffUncolPktHw indicates 
         the higher 32-bits word of the value of tmnxSubHsmdaStIngOffUncolPkt."
    ::= { tmnxSubscriberHsmdaStatsEntry 44 }

tmnxSubHsmdaStIngOffUncolOct        OBJECT-TYPE
    SYNTAX      Counter64
    MAX-ACCESS  read-only
    STATUS      current
    DESCRIPTION
    "The value of tmnxSubHsmdaStIngOffUncolOct indicates 
     the number of uncolored octets offered by the Pchip to the Qchip 
     for this subscriber.
     
     This is only supported for subscribers on an HSMDA-2."
    ::= { tmnxSubscriberHsmdaStatsEntry 45 }

tmnxSubHsmdaStIngOffUncolOctLw        OBJECT-TYPE
    SYNTAX      Counter32
    MAX-ACCESS  read-only
    STATUS      current
    DESCRIPTION
        "The value of tmnxSubHsmdaStIngOffUncolOctLw indicates 
         the lower 32-bits word of the value of tmnxSubHsmdaStIngOffUncolOct."
    ::= { tmnxSubscriberHsmdaStatsEntry 46 }

tmnxSubHsmdaStIngOffUncolOctHw        OBJECT-TYPE
    SYNTAX      Counter32
    MAX-ACCESS  read-only
    STATUS      current
    DESCRIPTION
        "The value of tmnxSubHsmdaStIngOffUncolOctHw indicates 
         the higher 32-bits word of the value of tmnxSubHsmdaStIngOffUncolOct."
    ::= { tmnxSubscriberHsmdaStatsEntry 47 }

tmnxSubHsmdaStIngOffV4Packets         OBJECT-TYPE
    SYNTAX      Counter64
    MAX-ACCESS  read-only
    STATUS      current
    DESCRIPTION
        "The value of tmnxSubHsmdaStIngOffV4Packets indicates
         the number of IPv4 packets offered on ingress 
         for this subscriber."
    ::= { tmnxSubscriberHsmdaStatsEntry 48 }

tmnxSubHsmdaStIngOffV4Octets          OBJECT-TYPE
    SYNTAX      Counter64
    MAX-ACCESS  read-only
    STATUS      current
    DESCRIPTION
        "The value of tmnxSubHsmdaStIngOffV4Octets indicates
         the number of IPv4 octets offered on ingress 
         for this subscriber."
    ::= { tmnxSubscriberHsmdaStatsEntry 49 }

tmnxSubHsmdaStIngOffV6Packets         OBJECT-TYPE
    SYNTAX      Counter64
    MAX-ACCESS  read-only
    STATUS      current
    DESCRIPTION
        "The value of tmnxSubHsmdaStIngOffV6Packets indicates
         the number of IPv6 packets offered on ingress 
         for this subscriber."
    ::= { tmnxSubscriberHsmdaStatsEntry 50 }

tmnxSubHsmdaStIngOffV6Octets          OBJECT-TYPE
    SYNTAX      Counter64
    MAX-ACCESS  read-only
    STATUS      current
    DESCRIPTION
        "The value of tmnxSubHsmdaStIngOffV6Octets indicates
         the number of IPv6 octets offered on ingress 
         for this subscriber."
    ::= { tmnxSubscriberHsmdaStatsEntry 51 }

tmnxSubHsmdaStIngDropV4Packets        OBJECT-TYPE
    SYNTAX      Counter64
    MAX-ACCESS  read-only
    STATUS      current
    DESCRIPTION
        "The value of tmnxSubHsmdaStIngDropV4Packets indicates
         the number of IPv4 packets discarded by the ingress Qchip
         for this subscriber."
    ::= { tmnxSubscriberHsmdaStatsEntry 52 }

tmnxSubHsmdaStIngDropV4Octets         OBJECT-TYPE
    SYNTAX      Counter64
    MAX-ACCESS  read-only
    STATUS      current
    DESCRIPTION
        "The value of tmnxSubHsmdaStIngDropV4Octets indicates
         the number of IPv4 octets discarded by the ingress Qchip
         for this subscriber."
    ::= { tmnxSubscriberHsmdaStatsEntry 53 }

tmnxSubHsmdaStIngDropV6Packets        OBJECT-TYPE
    SYNTAX      Counter64
    MAX-ACCESS  read-only
    STATUS      current
    DESCRIPTION
        "The value of tmnxSubHsmdaStIngDropV6Packets indicates
         the number of IPv6 packets discarded by the ingress Qchip
         for this subscriber."
    ::= { tmnxSubscriberHsmdaStatsEntry 54 }

tmnxSubHsmdaStIngDropV6Octets         OBJECT-TYPE
    SYNTAX      Counter64
    MAX-ACCESS  read-only
    STATUS      current
    DESCRIPTION
        "The value of tmnxSubHsmdaStIngDropV6Octets indicates
         the number of IPv6 octets discarded by the ingress Qchip
         for this subscriber."
    ::= { tmnxSubscriberHsmdaStatsEntry 55 }

tmnxSubHsmdaStIngFwdV4Packets         OBJECT-TYPE
    SYNTAX      Counter64
    MAX-ACCESS  read-only
    STATUS      current
    DESCRIPTION
        "The value of tmnxSubHsmdaStIngFwdV4Packets indicates
         the number of IPv4 packets forwarded by the ingress Qchip
         for this subscriber."
    ::= { tmnxSubscriberHsmdaStatsEntry 56 }

tmnxSubHsmdaStIngFwdV4Octets          OBJECT-TYPE
    SYNTAX      Counter64
    MAX-ACCESS  read-only
    STATUS      current
    DESCRIPTION
        "The value of tmnxSubHsmdaStIngFwdV4Octets indicates
         the number of IPv4 octets forwarded by the ingress Qchip
         for this subscriber."
    ::= { tmnxSubscriberHsmdaStatsEntry 57 }

tmnxSubHsmdaStIngFwdV6Packets         OBJECT-TYPE
    SYNTAX      Counter64
    MAX-ACCESS  read-only
    STATUS      current
    DESCRIPTION
        "The value of tmnxSubHsmdaStIngFwdV6Packets indicates
         the number of IPv6 packets forwarded by the ingress Qchip
         for this subscriber."
    ::= { tmnxSubscriberHsmdaStatsEntry 58 }

tmnxSubHsmdaStIngFwdV6Octets          OBJECT-TYPE
    SYNTAX      Counter64
    MAX-ACCESS  read-only
    STATUS      current
    DESCRIPTION
        "The value of tmnxSubHsmdaStIngFwdV6Octets indicates
         the number of IPv6 octets forwarded by the ingress Qchip
         for this subscriber."
    ::= { tmnxSubscriberHsmdaStatsEntry 59 }

tmnxSubHsmdaStEgrDropV4Packets        OBJECT-TYPE
    SYNTAX      Counter64
    MAX-ACCESS  read-only
    STATUS      current
    DESCRIPTION
        "The value of tmnxSubHsmdaStEgrDropV4Packets indicates
         the number of IPv4 packets discarded by the egress Qchip
         for this subscriber."
    ::= { tmnxSubscriberHsmdaStatsEntry 60 }

tmnxSubHsmdaStEgrDropV4Octets         OBJECT-TYPE
    SYNTAX      Counter64
    MAX-ACCESS  read-only
    STATUS      current
    DESCRIPTION
        "The value of tmnxSubHsmdaStEgrDropV4Octets indicates
         the number of IPv4 octets discarded by the egress Qchip
         for this subscriber."
    ::= { tmnxSubscriberHsmdaStatsEntry 61 }

tmnxSubHsmdaStEgrDropV6Packets        OBJECT-TYPE
    SYNTAX      Counter64
    MAX-ACCESS  read-only
    STATUS      current
    DESCRIPTION
        "The value of tmnxSubHsmdaStEgrDropV6Packets indicates
         the number of IPv6 packets discarded by the egress Qchip
         for this subscriber."
    ::= { tmnxSubscriberHsmdaStatsEntry 62 }

tmnxSubHsmdaStEgrDropV6Octets         OBJECT-TYPE
    SYNTAX      Counter64
    MAX-ACCESS  read-only
    STATUS      current
    DESCRIPTION
        "The value of tmnxSubHsmdaStEgrDropV6Octets indicates
         the number of IPv6 octets discarded by the egress Qchip
         for this subscriber."
    ::= { tmnxSubscriberHsmdaStatsEntry 63 }

tmnxSubHsmdaStEgrFwdV4Packets         OBJECT-TYPE
    SYNTAX      Counter64
    MAX-ACCESS  read-only
    STATUS      current
    DESCRIPTION
        "The value of tmnxSubHsmdaStEgrFwdV4Packets indicates
         the number of IPv4 packets forwarded by the egress Qchip
         for this subscriber."
    ::= { tmnxSubscriberHsmdaStatsEntry 64 }

tmnxSubHsmdaStEgrFwdV4Octets          OBJECT-TYPE
    SYNTAX      Counter64
    MAX-ACCESS  read-only
    STATUS      current
    DESCRIPTION
        "The value of tmnxSubHsmdaStEgrFwdV4Octets indicates
         the number of IPv4 octets forwarded by the egress Qchip
         for this subscriber."
    ::= { tmnxSubscriberHsmdaStatsEntry 65 }

tmnxSubHsmdaStEgrFwdV6Packets         OBJECT-TYPE
    SYNTAX      Counter64
    MAX-ACCESS  read-only
    STATUS      current
    DESCRIPTION
        "The value of tmnxSubHsmdaStEgrFwdV6Packets indicates
         the number of IPv6 packets forwarded by the egress Qchip
         for this subscriber."
    ::= { tmnxSubscriberHsmdaStatsEntry 66 }

tmnxSubHsmdaStEgrFwdV6Octets          OBJECT-TYPE
    SYNTAX      Counter64
    MAX-ACCESS  read-only
    STATUS      current
    DESCRIPTION
        "The value of tmnxSubHsmdaStEgrFwdV6Octets indicates
         the number of IPv6 octets forwarded by the egress Qchip
         for this subscriber."

    ::= { tmnxSubscriberHsmdaStatsEntry 67 }

-- --------------------------------------------------------
-- tmnxSubscriberIngQStatsTable
-- --------------------------------------------------------
tmnxSubscriberIngQStatsTable OBJECT-TYPE
    SYNTAX      SEQUENCE OF TmnxSubscriberIngQStatsEntry
    MAX-ACCESS  not-accessible
    STATUS      current
    DESCRIPTION
        "A table that contains subscriber ingress HSMDA queue statistics."
    ::= { tmnxSubMgmtObjects 37 }

tmnxSubscriberIngQStatsEntry    OBJECT-TYPE
    SYNTAX      TmnxSubscriberIngQStatsEntry
    MAX-ACCESS  not-accessible
    STATUS      current
    DESCRIPTION
        "Ingress statistics about a specific subscriber's HSMDA queue."
    INDEX { tmnxSubInfoSubIdent, tmnxSubIngQStatsQueueId }
    ::= { tmnxSubscriberIngQStatsTable 1 }

TmnxSubscriberIngQStatsEntry ::= SEQUENCE {
        tmnxSubIngQStatsQueueId          TIngressQueueId,
        tmnxSubIngQStatsSubPortId        TmnxPortID,
        tmnxSubIngQStatsOffTotalPkts     Counter64,
        tmnxSubIngQStatsOffTotalOcts     Counter64,
        tmnxSubIngQStatsFwdInProfPkts    Counter64,
        tmnxSubIngQStatsFwdOutProfPkts   Counter64,
        tmnxSubIngQStatsFwdInProfOcts    Counter64,
        tmnxSubIngQStatsFwdOutProfOcts   Counter64,
        tmnxSubIngQStatsDropHiPrioPkts   Counter64,
        tmnxSubIngQStatsDropLoPrioPkts   Counter64,
        tmnxSubIngQStatsDropHiPrioOcts   Counter64,
        tmnxSubIngQStatsDropLoPrioOcts   Counter64,
        tmnxSubIngQStatsOffHiPrioPkts    Counter64,
        tmnxSubIngQStatsOffHiPrioPktsLw  Counter32,
        tmnxSubIngQStatsOffHiPrioPktsHw  Counter32,
        tmnxSubIngQStatsOffLoPrioPkts    Counter64,
        tmnxSubIngQStatsOffLoPrioPktsLw  Counter32,
        tmnxSubIngQStatsOffLoPrioPktsHw  Counter32,
        tmnxSubIngQStatsOffHiPrioOcts    Counter64,
        tmnxSubIngQStatsOffHiPrioOctsLw  Counter32,
        tmnxSubIngQStatsOffHiPrioOctsHw  Counter32,
        tmnxSubIngQStatsOffLoPrioOcts    Counter64,
        tmnxSubIngQStatsOffLoPrioOctsLw  Counter32,
        tmnxSubIngQStatsOffLoPrioOctsHw  Counter32,
        tmnxSubIngQStatsOffUncolPkts     Counter64,
        tmnxSubIngQStatsOffUncolPktsLw   Counter32,
        tmnxSubIngQStatsOffUncolPktsHw   Counter32,
        tmnxSubIngQStatsOffUncolOcts     Counter64,
        tmnxSubIngQStatsOffUncolOctsLw   Counter32,
        tmnxSubIngQStatsOffUncolOctsHw   Counter32,
        tmnxSubIngQStatModeFormat        TQueueStatModeFormat
    }

tmnxSubIngQStatsQueueId        OBJECT-TYPE
    SYNTAX      TIngressQueueId
    MAX-ACCESS  not-accessible
    STATUS      current
    DESCRIPTION
        "The value of tmnxSubIngQStatsQueueId index specifies the Hsmda
         ingress queue for this entry."
    ::= { tmnxSubscriberIngQStatsEntry 1 }

tmnxSubIngQStatsSubPortId        OBJECT-TYPE
    SYNTAX      TmnxPortID
    MAX-ACCESS  read-only
    STATUS      current
    DESCRIPTION
        "The value of tmnxSubIngQStatsSubPortId indicates the access port
         for this entry."
    ::= { tmnxSubscriberIngQStatsEntry 2 }

tmnxSubIngQStatsOffTotalPkts        OBJECT-TYPE
    SYNTAX      Counter64
    MAX-ACCESS  read-only
    STATUS      current
    DESCRIPTION
        "The value of tmnxSubIngQStatsOffTotalPkts indicates the
         total number of packets offered for this subscriber."
    ::= { tmnxSubscriberIngQStatsEntry 3 }

tmnxSubIngQStatsOffTotalOcts        OBJECT-TYPE
    SYNTAX      Counter64
    MAX-ACCESS  read-only
    STATUS      current
    DESCRIPTION
        "The value of tmnxSubIngQStatsOffTotalOcts indicates the
         total number of octets offered on ingress on this subscriber."
    ::= { tmnxSubscriberIngQStatsEntry 4 }

tmnxSubIngQStatsFwdInProfPkts        OBJECT-TYPE
    SYNTAX      Counter64
    MAX-ACCESS  read-only
    STATUS      current
    DESCRIPTION
        "The value of tmnxSubIngQStatsFwdInProfPkts indicates the
         number of in-profile packets forwarded on ingress on
         this subscriber."
    ::= { tmnxSubscriberIngQStatsEntry 5 }

tmnxSubIngQStatsFwdOutProfPkts        OBJECT-TYPE
    SYNTAX      Counter64
    MAX-ACCESS  read-only
    STATUS      current
    DESCRIPTION
        "The value of tmnxSubIngQStatsFwdOutProfPkts indicates the
         number of out-of-profile packets forwarded on ingress on
         this subscriber."
    ::= { tmnxSubscriberIngQStatsEntry 6 }

tmnxSubIngQStatsFwdInProfOcts        OBJECT-TYPE
    SYNTAX      Counter64
    MAX-ACCESS  read-only
    STATUS      current
    DESCRIPTION
        "The value of tmnxSubIngQStatsFwdInProfOcts indicates the
         number of out-of-profile octets forwarded on ingress on
         this subscriber."
    ::= { tmnxSubscriberIngQStatsEntry 7 }

tmnxSubIngQStatsFwdOutProfOcts        OBJECT-TYPE
    SYNTAX      Counter64
    MAX-ACCESS  read-only
    STATUS      current
    DESCRIPTION
        "The value of tmnxSubIngQStatsFwdOutProfOcts indicates the
         number of out-of-profile octets forwarded on ingress on
         this subscriber."
    ::= { tmnxSubscriberIngQStatsEntry 8 }

tmnxSubIngQStatsDropHiPrioPkts        OBJECT-TYPE
    SYNTAX      Counter64
    MAX-ACCESS  read-only
    STATUS      current
    DESCRIPTION
        "The value of tmnxSubIngQStatsDropHiPrioPkts indicates the
         number of high-priority packets dropped on ingress on
         this subscriber."
    ::= { tmnxSubscriberIngQStatsEntry 9 }

tmnxSubIngQStatsDropLoPrioPkts        OBJECT-TYPE
    SYNTAX      Counter64
    MAX-ACCESS  read-only
    STATUS      current
    DESCRIPTION
        "The value of tmnxSubIngQStatsDropLoPrioPkts indicates the
         number of low-priority packets dropped on ingress on
         this subscriber."
    ::= { tmnxSubscriberIngQStatsEntry 10 }

tmnxSubIngQStatsDropHiPrioOcts        OBJECT-TYPE
    SYNTAX      Counter64
    MAX-ACCESS  read-only
    STATUS      current
    DESCRIPTION
        "The value of tmnxSubIngQStatsDropHiPrioOcts indicates the
         number of high-priority octets dropped on ingress on
         this subscriber."
    ::= { tmnxSubscriberIngQStatsEntry 11 }

tmnxSubIngQStatsDropLoPrioOcts        OBJECT-TYPE
    SYNTAX      Counter64
    MAX-ACCESS  read-only
    STATUS      current
    DESCRIPTION
        "The value of tmnxSubIngQStatsDropLoPrioOcts indicates the
         number of low-priority octets dropped on ingress on
         this subscriber."
    ::= { tmnxSubscriberIngQStatsEntry 12 }

tmnxSubIngQStatsOffHiPrioPkts          OBJECT-TYPE
    SYNTAX      Counter64
    MAX-ACCESS  read-only
    STATUS      current
    DESCRIPTION
        "The value of tmnxSubIngQStatsOffHiPrioPkts indicates the
         number of high-priority packets offered by the Pchip to the Qchip 
         for this subscriber and this HSMDA-2 queue."
    ::= { tmnxSubscriberIngQStatsEntry 20 }

tmnxSubIngQStatsOffHiPrioPktsLw        OBJECT-TYPE
    SYNTAX      Counter32
    MAX-ACCESS  read-only
    STATUS      current
    DESCRIPTION
        "The value of tmnxSubIngQStatsOffHiPrioPktsLw indicates
         the lower 32-bits word of the value of tmnxSubIngQStatsOffHiPrioPkts."
    ::= { tmnxSubscriberIngQStatsEntry 21 }

tmnxSubIngQStatsOffHiPrioPktsHw        OBJECT-TYPE
    SYNTAX      Counter32
    MAX-ACCESS  read-only
    STATUS      current
    DESCRIPTION
        "The value of tmnxSubIngQStatsOffHiPrioPkts indicates
         the higher 32-bits word of the value of tmnxSubIngQStatsOffHiPrioPkts."
    ::= { tmnxSubscriberIngQStatsEntry 22 }

tmnxSubIngQStatsOffLoPrioPkts          OBJECT-TYPE
    SYNTAX      Counter64
    MAX-ACCESS  read-only
    STATUS      current
    DESCRIPTION
        "The value of tmnxSubIngQStatsOffLoPrioPkts indicates the
         number of low-priority packets offered by the Pchip to the Qchip 
         for this subscriber and this HSMDA-2 queue."
    ::= { tmnxSubscriberIngQStatsEntry 23 }

tmnxSubIngQStatsOffLoPrioPktsLw        OBJECT-TYPE
    SYNTAX      Counter32
    MAX-ACCESS  read-only
    STATUS      current
    DESCRIPTION
        "The value of tmnxSubIngQStatsOffLoPrioPktsLw indicates
         the lower 32-bits word of the value of tmnxSubIngQStatsOffLoPrioPkts."
    ::= { tmnxSubscriberIngQStatsEntry 24 }

tmnxSubIngQStatsOffLoPrioPktsHw        OBJECT-TYPE
    SYNTAX      Counter32
    MAX-ACCESS  read-only
    STATUS      current
    DESCRIPTION
        "The value of tmnxSubIngQStatsOffLoPrioPktsHw indicates
         the higher 32-bits word of the value of tmnxSubIngQStatsOffLoPrioPkts."
    ::= { tmnxSubscriberIngQStatsEntry 25 }

tmnxSubIngQStatsOffHiPrioOcts          OBJECT-TYPE
    SYNTAX      Counter64
    MAX-ACCESS  read-only
    STATUS      current
    DESCRIPTION
        "The value of tmnxSubIngQStatsOffHiPrioOcts indicates the
         number of high-priority octets offered by the Pchip to the Qchip 
         for this subscriber and this HSMDA-2 queue."
    ::= { tmnxSubscriberIngQStatsEntry 26 }

tmnxSubIngQStatsOffHiPrioOctsLw        OBJECT-TYPE
    SYNTAX      Counter32
    MAX-ACCESS  read-only
    STATUS      current
    DESCRIPTION
        "The value of tmnxSubIngQStatsOffHiPrioOctsLw indicates
         the lower 32-bits word of the value of tmnxSubIngQStatsOffHiPrioOcts."
    ::= { tmnxSubscriberIngQStatsEntry 27 }

tmnxSubIngQStatsOffHiPrioOctsHw        OBJECT-TYPE
    SYNTAX      Counter32
    MAX-ACCESS  read-only
    STATUS      current
    DESCRIPTION
        "The value of tmnxSubIngQStatsOffHiPrioOctsHw indicates
         the higher 32-bits word of the value of tmnxSubIngQStatsOffHiPrioOcts."
    ::= { tmnxSubscriberIngQStatsEntry 28 }

tmnxSubIngQStatsOffLoPrioOcts          OBJECT-TYPE
    SYNTAX      Counter64
    MAX-ACCESS  read-only
    STATUS      current
    DESCRIPTION
        "The value of tmnxSubIngQStatsOffLoPrioOcts indicates the
         number of low-priority octets offered by the Pchip to the Qchip 
         for this subscriber and this HSMDA-2 queue."
    ::= { tmnxSubscriberIngQStatsEntry 29 }

tmnxSubIngQStatsOffLoPrioOctsLw        OBJECT-TYPE
    SYNTAX      Counter32
    MAX-ACCESS  read-only
    STATUS      current
    DESCRIPTION
        "The value of tmnxSubIngQStatsOffLoPrioOctsLw indicates 
         the lower 32-bits word of the value of tmnxSubIngQStatsOffLoPrioOcts."
    ::= { tmnxSubscriberIngQStatsEntry 30 }

tmnxSubIngQStatsOffLoPrioOctsHw        OBJECT-TYPE
    SYNTAX      Counter32
    MAX-ACCESS  read-only
    STATUS      current
    DESCRIPTION
        "The value of tmnxSubIngQStatsOffLoPrioOctsHw indicates
         the higher 32-bits word of the value of tmnxSubIngQStatsOffLoPrioOcts."
    ::= { tmnxSubscriberIngQStatsEntry 31 }

tmnxSubIngQStatsOffUncolPkts           OBJECT-TYPE
    SYNTAX      Counter64
    MAX-ACCESS  read-only
    STATUS      current
    DESCRIPTION
        "The value of tmnxSubIngQStatsOffUncolPkts indicates the
         number of uncolored packets offered by the Pchip to the Qchip 
         for this subscriber and this HSMDA-2 queue."
    ::= { tmnxSubscriberIngQStatsEntry 32 }

tmnxSubIngQStatsOffUncolPktsLw         OBJECT-TYPE
    SYNTAX      Counter32
    MAX-ACCESS  read-only
    STATUS      current
    DESCRIPTION
        "The value of tmnxSubIngQStatsOffUncolPktsLw indicates
         the lower 32-bits word of the value of tmnxSubIngQStatsOffUncolPkts."
    ::= { tmnxSubscriberIngQStatsEntry 33 }

tmnxSubIngQStatsOffUncolPktsHw         OBJECT-TYPE
    SYNTAX      Counter32
    MAX-ACCESS  read-only
    STATUS      current
    DESCRIPTION
        "The value of tmnxSubIngQStatsOffUncolPktsHw indicates
         the higher 32-bits word of the value of tmnxSubIngQStatsOffUncolPkts."
    ::= { tmnxSubscriberIngQStatsEntry 34 }

tmnxSubIngQStatsOffUncolOcts           OBJECT-TYPE
    SYNTAX      Counter64
    MAX-ACCESS  read-only
    STATUS      current
    DESCRIPTION
        "The value of tmnxSubIngQStatsOffUncolOcts indicates the
         number of uncolored octets offered by the Pchip to the Qchip 
         for this subscriber and this HSMDA-2 queue."
    ::= { tmnxSubscriberIngQStatsEntry 35 }

tmnxSubIngQStatsOffUncolOctsLw         OBJECT-TYPE
    SYNTAX      Counter32
    MAX-ACCESS  read-only
    STATUS      current
    DESCRIPTION
        "The value of tmnxSubIngQStatsOffUncolOctsLw indicates
         the lower 32-bits word of the value of tmnxSubIngQStatsOffUncolOcts."
    ::= { tmnxSubscriberIngQStatsEntry 36 }

tmnxSubIngQStatsOffUncolOctsHw         OBJECT-TYPE
    SYNTAX      Counter32
    MAX-ACCESS  read-only
    STATUS      current
    DESCRIPTION
        "The value of tmnxSubIngQStatsOffUncolOctsHw indicates
         the higher 32-bits word of the value of tmnxSubIngQStatsOffUncolOcts."
    ::= { tmnxSubscriberIngQStatsEntry 37 }

tmnxSubIngQStatModeFormat              OBJECT-TYPE
    SYNTAX      TQueueStatModeFormat
    MAX-ACCESS  read-only
    STATUS      current
    DESCRIPTION
        "The value of tmnxSubIngQStatModeFormat specifies the stat mode format
         of this ingress QoS queue of this subscriber."
    ::= { tmnxSubscriberIngQStatsEntry 38 }

-- --------------------------------------------------------
-- tmnxSubscriberEgrQStatsTable
-- --------------------------------------------------------
tmnxSubscriberEgrQStatsTable OBJECT-TYPE
    SYNTAX      SEQUENCE OF TmnxSubscriberEgrQStatsEntry
    MAX-ACCESS  not-accessible
    STATUS      current
    DESCRIPTION
        "A table that contains subscriber egress HSMDA queue statistics."
    ::= { tmnxSubMgmtObjects 38 }

tmnxSubscriberEgrQStatsEntry    OBJECT-TYPE
    SYNTAX      TmnxSubscriberEgrQStatsEntry
    MAX-ACCESS  not-accessible
    STATUS      current
    DESCRIPTION
        "Egress statistics about a specific subscriber's HSMDA queue."
    INDEX { tmnxSubInfoSubIdent, tmnxSubEgrQStatsQueueId }
    ::= { tmnxSubscriberEgrQStatsTable 1 }

TmnxSubscriberEgrQStatsEntry ::= SEQUENCE {
        tmnxSubEgrQStatsQueueId            TEgressHsmdaQueueId,
        tmnxSubEgrQStatsSubPortId          TmnxPortID,
        tmnxSubEgrQStatsFwdInProfPkts      Counter64,
        tmnxSubEgrQStatsFwdOutProfPkts     Counter64,
        tmnxSubEgrQStatsFwdInProfOcts      Counter64,
        tmnxSubEgrQStatsFwdOutProfOcts     Counter64,
        tmnxSubEgrQStatsDropInProfPkts     Counter64,
        tmnxSubEgrQStatsDropOutProfPkts     Counter64,
        tmnxSubEgrQStatsDropInProfOcts     Counter64,
        tmnxSubEgrQStatsDropOutProfOcts     Counter64,
        tmnxSubEgrQStatModeFormat          TQueueStatModeFormat
    }

tmnxSubEgrQStatsQueueId        OBJECT-TYPE
    SYNTAX      TEgressHsmdaQueueId
    MAX-ACCESS  not-accessible
    STATUS      current
    DESCRIPTION
        "The value of tmnxSubEgrQStatsQueueId index specifies the Hsmda
         egress queue for this entry."
    ::= { tmnxSubscriberEgrQStatsEntry 1 }

tmnxSubEgrQStatsSubPortId        OBJECT-TYPE
    SYNTAX      TmnxPortID
    MAX-ACCESS  read-only
    STATUS      current
    DESCRIPTION
        "The value of tmnxSubEgrQStatsSubPortId indicates the access port
         for this entry."
    ::= { tmnxSubscriberEgrQStatsEntry 2 }

tmnxSubEgrQStatsFwdInProfPkts        OBJECT-TYPE
    SYNTAX      Counter64
    MAX-ACCESS  read-only
    STATUS      current
    DESCRIPTION
        "The value of tmnxSubEgrQStatsFwdInProfPkts indicates the
         number of in-profile packets forwarded on egress on
         this subscriber."
    ::= { tmnxSubscriberEgrQStatsEntry 3 }

tmnxSubEgrQStatsFwdOutProfPkts        OBJECT-TYPE
    SYNTAX      Counter64
    MAX-ACCESS  read-only
    STATUS      current
    DESCRIPTION
        "The value of tmnxSubEgrQStatsFwdOutProfPkts indicates the
         number of out-of-profile packets forwarded on egress on
         this subscriber."
    ::= { tmnxSubscriberEgrQStatsEntry 4 }

tmnxSubEgrQStatsFwdInProfOcts        OBJECT-TYPE
    SYNTAX      Counter64
    MAX-ACCESS  read-only
    STATUS      current
    DESCRIPTION
        "The value of tmnxSubEgrQStatsFwdInProfOcts indicates the
         number of out-of-profile octets forwarded on egress on
         this subscriber."
    ::= { tmnxSubscriberEgrQStatsEntry 5 }

tmnxSubEgrQStatsFwdOutProfOcts        OBJECT-TYPE
    SYNTAX      Counter64
    MAX-ACCESS  read-only
    STATUS      current
    DESCRIPTION
        "The value of tmnxSubEgrQStatsFwdOutProfOcts indicates the
         number of out-of-profile octets forwarded on egress on
         this subscriber."
    ::= { tmnxSubscriberEgrQStatsEntry 6 }

tmnxSubEgrQStatsDropInProfPkts        OBJECT-TYPE
    SYNTAX      Counter64
    MAX-ACCESS  read-only
    STATUS      current
    DESCRIPTION
        "The value of tmnxSubEgrQStatsDropInProfPkts indicates the
         number of high-priority packets dropped on egress on
         this subscriber."
    ::= { tmnxSubscriberEgrQStatsEntry 7 }

tmnxSubEgrQStatsDropOutProfPkts        OBJECT-TYPE
    SYNTAX      Counter64
    MAX-ACCESS  read-only
    STATUS      current
    DESCRIPTION
        "The value of tmnxSubEgrQStatsDropOutProfPkts indicates the
         number of low-priority packets dropped on egress on
         this subscriber."
    ::= { tmnxSubscriberEgrQStatsEntry 8 }

tmnxSubEgrQStatsDropInProfOcts        OBJECT-TYPE
    SYNTAX      Counter64
    MAX-ACCESS  read-only
    STATUS      current
    DESCRIPTION
        "The value of tmnxSubEgrQStatsDropInProfOcts indicates the
         number of high-priority octets dropped on egress on
         this subscriber."
    ::= { tmnxSubscriberEgrQStatsEntry 9 }

tmnxSubEgrQStatsDropOutProfOcts        OBJECT-TYPE
    SYNTAX      Counter64
    MAX-ACCESS  read-only
    STATUS      current
    DESCRIPTION
        "The value of tmnxSubEgrQStatsDropOutProfOcts indicates the
         number of low-priority octets dropped on egress on
         this subscriber."
    ::= { tmnxSubscriberEgrQStatsEntry 10 }

tmnxSubEgrQStatModeFormat              OBJECT-TYPE
    SYNTAX      TQueueStatModeFormat
    MAX-ACCESS  read-only
    STATUS      current
    DESCRIPTION
        "The value of tmnxSubEgrQStatModeFormat specifies the stat mode format
         of this egress QoS queue of this subscriber."
    ::= { tmnxSubscriberEgrQStatsEntry 11 }

-- --------------------------------------------------------
-- tmnxSubIngOverrideCounterTable
-- --------------------------------------------------------
tmnxSubIngOverrideCounterTable OBJECT-TYPE
    SYNTAX      SEQUENCE OF TmnxSubIngOverrideCounterEntry
    MAX-ACCESS  not-accessible
    STATUS      obsolete
    DESCRIPTION
        "A table that contains ingress HSMDA counter subscriber statistics.

         This table is obsoleted in 10.0 release."
    ::= { tmnxSubMgmtObjects 39 }

tmnxSubIngOverrideCounterEntry    OBJECT-TYPE
    SYNTAX      TmnxSubIngOverrideCounterEntry
    MAX-ACCESS  not-accessible
    STATUS      obsolete
    DESCRIPTION
        "Ingress statistics about a specific subscriber's HSMDA counter."
    INDEX { tmnxSubInfoSubIdent, tmnxSubIngOvrCntrId }
    ::= { tmnxSubIngOverrideCounterTable 1}

TmnxSubIngOverrideCounterEntry ::= SEQUENCE {
        tmnxSubIngOvrCntrId                TIngressHsmdaCounterId,
        tmnxSubIngOvrCntrSubPortId         TmnxPortID,
        tmnxSubIngOvrCntrOffTotalPkts      Counter64,
        tmnxSubIngOvrCntrOffTotalOcts      Counter64,
        tmnxSubIngOvrCntrFwdInProfPkts     Counter64,
        tmnxSubIngOvrCntrFwdOutProfPkts    Counter64,
        tmnxSubIngOvrCntrFwdInProfOcts     Counter64,
        tmnxSubIngOvrCntrFwdOutProfOcts    Counter64,
        tmnxSubIngOvrCntrDropHiPrioPkts    Counter64,
        tmnxSubIngOvrCntrDropLoPrioPkts    Counter64,
        tmnxSubIngOvrCntrDropHiPrioOcts    Counter64,
        tmnxSubIngOvrCntrDropLoPrioOcts    Counter64
    }

tmnxSubIngOvrCntrId        OBJECT-TYPE
    SYNTAX      TIngressHsmdaCounterId
    MAX-ACCESS  not-accessible
    STATUS      obsolete
    DESCRIPTION
        "The value of tmnxSubIngOvrCntrId indicates the counter ID
         for the statistics."
    ::= { tmnxSubIngOverrideCounterEntry 1 }

tmnxSubIngOvrCntrSubPortId        OBJECT-TYPE
    SYNTAX      TmnxPortID
    MAX-ACCESS  read-only
    STATUS      obsolete
    DESCRIPTION
        "The value of tmnxSubIngOvrCntrSubPortId indicates the access port
         for this entry."
    ::= { tmnxSubIngOverrideCounterEntry 2 }

tmnxSubIngOvrCntrOffTotalPkts        OBJECT-TYPE
    SYNTAX      Counter64
    MAX-ACCESS  read-only
    STATUS      obsolete
    DESCRIPTION
        "The value of tmnxSubIngOvrCntrOffTotalPkts indicates the
         total number of packets offered on ingress on this subscriber."
    ::= { tmnxSubIngOverrideCounterEntry 3 }

tmnxSubIngOvrCntrOffTotalOcts        OBJECT-TYPE
    SYNTAX      Counter64
    MAX-ACCESS  read-only
    STATUS      obsolete
    DESCRIPTION
        "The value of tmnxSubIngOvrCntrOffTotalOcts indicates the
         total number of octets offered on ingress on this subscriber."
    ::= { tmnxSubIngOverrideCounterEntry 4 }

tmnxSubIngOvrCntrFwdInProfPkts        OBJECT-TYPE
    SYNTAX      Counter64
    MAX-ACCESS  read-only
    STATUS      obsolete
    DESCRIPTION
        "The value of tmnxSubIngOvrCntrFwdInProfPkts indicates the
         number of in-profile packets forwarded for the ingress
         counter, specified by the index tmnxSubIngOvrCntrId,
         on this subscriber."
    ::= { tmnxSubIngOverrideCounterEntry 5 }

tmnxSubIngOvrCntrFwdOutProfPkts        OBJECT-TYPE
    SYNTAX      Counter64
    MAX-ACCESS  read-only
    STATUS      obsolete
    DESCRIPTION
        "The value of tmnxSubIngOvrCntrFwdOutProfPkts indicates the
         number of out-of-profile packets forwarded for the ingress
         counter, specified by the index tmnxSubIngOvrCntrId,
         on this subscriber."
    ::= { tmnxSubIngOverrideCounterEntry 6 }

tmnxSubIngOvrCntrFwdInProfOcts        OBJECT-TYPE
    SYNTAX      Counter64
    MAX-ACCESS  read-only
    STATUS      obsolete
    DESCRIPTION
        "The value of tmnxSubIngOvrCntrFwdInProfOcts indicates the
         number of in-profile octets forwarded for the ingress
         counter, specified by the index tmnxSubIngOvrCntrId,
         on this subscriber."
    ::= { tmnxSubIngOverrideCounterEntry 7 }

tmnxSubIngOvrCntrFwdOutProfOcts        OBJECT-TYPE
    SYNTAX      Counter64
    MAX-ACCESS  read-only
    STATUS      obsolete
    DESCRIPTION
        "The value of tmnxSubIngOvrCntrFwdOutProfOcts indicates the
         number of out-of-profile octets forwarded for the ingress
         counter, specified by the index tmnxSubIngOvrCntrId,
         on this subscriber."
    ::= { tmnxSubIngOverrideCounterEntry 8 }

tmnxSubIngOvrCntrDropHiPrioPkts        OBJECT-TYPE
    SYNTAX      Counter64
    MAX-ACCESS  read-only
    STATUS      obsolete
    DESCRIPTION
        "The value of tmnxSubIngOvrCntrDropHiPrioPkts indicates the
         number of high-priority packets dropped for the ingress
         counter, specified by the index tmnxSubIngOvrCntrId,
         on this subscriber."
    ::= { tmnxSubIngOverrideCounterEntry 9 }

tmnxSubIngOvrCntrDropLoPrioPkts        OBJECT-TYPE
    SYNTAX      Counter64
    MAX-ACCESS  read-only
    STATUS      obsolete
    DESCRIPTION
        "The value of tmnxSubIngOvrCntrDropLoPrioPkts indicates the
         number of low-priority packets dropped for the ingress
         counter, specified by the index tmnxSubIngOvrCntrId,
         on this subscriber."
    ::= { tmnxSubIngOverrideCounterEntry 10 }

tmnxSubIngOvrCntrDropHiPrioOcts        OBJECT-TYPE
    SYNTAX      Counter64
    MAX-ACCESS  read-only
    STATUS      obsolete
    DESCRIPTION
        "The value of tmnxSubIngOvrCntrDropHiPrioOcts indicates the
         number of high-priority octets dropped for the ingress
         counter, specified by the index tmnxSubIngOvrCntrId,
         on this subscriber."
    ::= { tmnxSubIngOverrideCounterEntry 11 }

tmnxSubIngOvrCntrDropLoPrioOcts        OBJECT-TYPE
    SYNTAX      Counter64
    MAX-ACCESS  read-only
    STATUS      obsolete
    DESCRIPTION
        "The value of tmnxSubIngOvrCntrDropLoPrioOcts indicates the
         number of low-priority octets dropped for the ingress
         counter, specified by the index tmnxSubIngOvrCntrId,
         on this subscriber."
    ::= { tmnxSubIngOverrideCounterEntry 12 }

-- --------------------------------------------------------
-- tmnxSubEgrOverrideCounterTable
-- --------------------------------------------------------
tmnxSubEgrOverrideCounterTable OBJECT-TYPE
    SYNTAX      SEQUENCE OF TmnxSubEgrOverrideCounterEntry
    MAX-ACCESS  not-accessible
    STATUS      current
    DESCRIPTION
        "A table that contains egress HSMDA counter subscriber statistics."
    ::= { tmnxSubMgmtObjects 40 }

tmnxSubEgrOverrideCounterEntry    OBJECT-TYPE
    SYNTAX      TmnxSubEgrOverrideCounterEntry
    MAX-ACCESS  not-accessible
    STATUS      current
    DESCRIPTION
        "Egress statistics about a specific subscriber's HSMDA counter."
    INDEX { tmnxSubInfoSubIdent, tmnxSubEgrOvrCntrId }
    ::= { tmnxSubEgrOverrideCounterTable 1}

TmnxSubEgrOverrideCounterEntry ::= SEQUENCE {
        tmnxSubEgrOvrCntrId                TEgressHsmdaCounterId,
        tmnxSubEgrOvrCntrSubPortId         TmnxPortID,
        tmnxSubEgrOvrCntrFwdInProfPkts     Counter64,
        tmnxSubEgrOvrCntrFwdOutProfPkts    Counter64,
        tmnxSubEgrOvrCntrFwdInProfOcts     Counter64,
        tmnxSubEgrOvrCntrFwdOutProfOcts    Counter64,
        tmnxSubEgrOvrCntrDropInProfPkts    Counter64,
        tmnxSubEgrOvrCntrDropOutProfPkts   Counter64,
        tmnxSubEgrOvrCntrDropInProfOcts    Counter64,
        tmnxSubEgrOvrCntrDropOutProfOcts   Counter64,
        tmnxSubEgrOvrCntrStatModeFormat    TQueueStatModeFormat
    }

tmnxSubEgrOvrCntrId        OBJECT-TYPE
    SYNTAX      TEgressHsmdaCounterId
    MAX-ACCESS  not-accessible
    STATUS      current
    DESCRIPTION
        "The value of tmnxSubEgrOvrCntrId indicates the counter ID
         for the statistics."
    ::= { tmnxSubEgrOverrideCounterEntry 1 }

tmnxSubEgrOvrCntrSubPortId        OBJECT-TYPE
    SYNTAX      TmnxPortID
    MAX-ACCESS  read-only
    STATUS      current
    DESCRIPTION
        "The value of tmnxSubEgrOvrCntrSubPortId indicates the access port
         for this entry."
    ::= { tmnxSubEgrOverrideCounterEntry 2 }

tmnxSubEgrOvrCntrFwdInProfPkts        OBJECT-TYPE
    SYNTAX      Counter64
    MAX-ACCESS  read-only
    STATUS      current
    DESCRIPTION
        "The value of tmnxSubEgrOvrCntrFwdInProfPkts indicates the
         number of in-profile packets forwarded for the egress
         counter, specified by the index tmnxSubEgrOvrCntrId,
         on this subscriber."
    ::= { tmnxSubEgrOverrideCounterEntry 3 }

tmnxSubEgrOvrCntrFwdOutProfPkts        OBJECT-TYPE
    SYNTAX      Counter64
    MAX-ACCESS  read-only
    STATUS      current
    DESCRIPTION
        "The value of tmnxSubEgrOvrCntrFwdOutProfPkts indicates the
         number of out-of-profile packets forwarded for the egress
         counter, specified by the index tmnxSubEgrOvrCntrId,
         on this subscriber."
    ::= { tmnxSubEgrOverrideCounterEntry 4 }

tmnxSubEgrOvrCntrFwdInProfOcts        OBJECT-TYPE
    SYNTAX      Counter64
    MAX-ACCESS  read-only
    STATUS      current
    DESCRIPTION
        "The value of tmnxSubEgrOvrCntrFwdInProfOcts indicates the
         number of in-profile octets forwarded for the egress
         counter, specified by the index tmnxSubEgrOvrCntrId,
         on this subscriber."
    ::= { tmnxSubEgrOverrideCounterEntry 5 }

tmnxSubEgrOvrCntrFwdOutProfOcts        OBJECT-TYPE
    SYNTAX      Counter64
    MAX-ACCESS  read-only
    STATUS      current
    DESCRIPTION
        "The value of tmnxSubEgrOvrCntrFwdOutProfOcts indicates the
         number of out-of-profile octets forwarded for the egress
         counter, specified by the index tmnxSubEgrOvrCntrId,
         on this subscriber."
    ::= { tmnxSubEgrOverrideCounterEntry 6 }

tmnxSubEgrOvrCntrDropInProfPkts        OBJECT-TYPE
    SYNTAX      Counter64
    MAX-ACCESS  read-only
    STATUS      current
    DESCRIPTION
        "The value of tmnxSubEgrOvrCntrDropInProfPkts indicates the
         number of high-priority packets dropped for the egress
         counter, specified by the index tmnxSubEgrOvrCntrId,
         on this subscriber."
    ::= { tmnxSubEgrOverrideCounterEntry 7 }

tmnxSubEgrOvrCntrDropOutProfPkts        OBJECT-TYPE
    SYNTAX      Counter64
    MAX-ACCESS  read-only
    STATUS      current
    DESCRIPTION
        "The value of tmnxSubEgrOvrCntrDropOutProfPkts indicates the
         number of low-priority packets dropped for the egress
         counter, specified by the index tmnxSubEgrOvrCntrId,
         on this subscriber."
    ::= { tmnxSubEgrOverrideCounterEntry 8 }

tmnxSubEgrOvrCntrDropInProfOcts        OBJECT-TYPE
    SYNTAX      Counter64
    MAX-ACCESS  read-only
    STATUS      current
    DESCRIPTION
        "The value of tmnxSubEgrOvrCntrDropInProfOcts indicates the
         number of high-priority octets dropped for the egress
         counter, specified by the index tmnxSubEgrOvrCntrId,
         on this subscriber."
    ::= { tmnxSubEgrOverrideCounterEntry 9 }

tmnxSubEgrOvrCntrDropOutProfOcts        OBJECT-TYPE
    SYNTAX      Counter64
    MAX-ACCESS  read-only
    STATUS      current
    DESCRIPTION
        "The value of tmnxSubEgrOvrCntrDropOutProfOcts indicates the
         number of low-priority octets dropped for the egress
         counter, specified by the index tmnxSubEgrOvrCntrId,
         on this subscriber."
    ::= { tmnxSubEgrOverrideCounterEntry 10 }
        
tmnxSubEgrOvrCntrStatModeFormat OBJECT-TYPE
    SYNTAX      TQueueStatModeFormat
    MAX-ACCESS  read-only
    STATUS      current
    DESCRIPTION
        "The value of tmnxSubEgrOvrCntrStatModeFormat specifies the
         stat mode format of this egress override counter of this subscriber."
    ::= { tmnxSubEgrOverrideCounterEntry 11 }

-- ----------------------------------------
-- tmnxSubHostInfoV2Table
-- ----------------------------------------
tmnxSubHostInfoV2Table OBJECT-TYPE
    SYNTAX      SEQUENCE OF TmnxSubHostInfoV2Entry
    MAX-ACCESS  not-accessible
    STATUS      current
    DESCRIPTION
        "The tmnxSubHostInfoV2Table has an entry for each subscriber host found
         in the system."
    ::= { tmnxSubMgmtObjects 41 }

tmnxSubHostInfoV2Entry OBJECT-TYPE
    SYNTAX      TmnxSubHostInfoV2Entry
    MAX-ACCESS  not-accessible
    STATUS      current
    DESCRIPTION
        "Each row entry contains information about a particular subscriber host
         available in the system."
    INDEX { svcId,
            sapPortId,
            sapEncapValue,
            tmnxSubHostInfoV2IpAddressType,
            tmnxSubHostInfoV2IpAddress,
            tmnxSubHostInfoV2MacAddress,
            tmnxSubHostInfoV2PppoeSessionId }
    ::= { tmnxSubHostInfoV2Table 1 }

TmnxSubHostInfoV2Entry ::=
    SEQUENCE {
        tmnxSubHostInfoV2IpAddressType   InetAddressType,
        tmnxSubHostInfoV2IpAddress       InetAddress,
        tmnxSubHostInfoV2MacAddress      MacAddress,
        tmnxSubHostInfoV2PppoeSessionId  TmnxPppoeSessionId,
        tmnxSubHostInfoV2FwdingState     TmnxOperState,
        tmnxSubHostInfoV2Origin          TmnxSubHostOrigin,
        tmnxSubHostInfoV2SubIdent        DisplayString,
        tmnxSubHostInfoV2SubProfile      TNamedItemOrEmpty,
        tmnxSubHostInfoV2SLAProfile      TNamedItemOrEmpty,
        tmnxSubHostInfoV2AppProfile      TNamedItemOrEmpty,
        tmnxSubHostInfoV2RetailerSvcId   TmnxServId,
        tmnxSubHostInfoV2RetailerIf      InterfaceIndexOrZero,
        tmnxSubHostInfoV2PfxLen          InetAddressPrefixLength,
        tmnxSubHostInfoV2EgrQGrpName     TNamedItemOrEmpty,
        tmnxSubHostInfoV2EgrVPortName    TNamedItemOrEmpty,
        tmnxSubHostInfoV2AcctSessionId   TmnxSubAcctSessionId,
        tmnxSubHostInfoV2AddressOrigin   INTEGER,
        tmnxSubHostInfoV2PppIndex        Unsigned32,
        tmnxSubHostInfoV2AcctMultiSessId TmnxSubAcctSessionId,
        tmnxSubHostInfoV2IngFilter       TOverruleFilterId,
        tmnxSubHostInfoV2EgrFilter       TOverruleFilterId,
        tmnxSubHostInfoV2OtHttpRdrState  INTEGER,
        tmnxSubHostInfoV2OtHttpRdrFilter TOverruleFilterId,
        tmnxSubHostInfoV2OtHttpRdrSource INTEGER,
        tmnxSubHostInfoV2HttpRdrUrlOvrd  TmnxHttpRedirectUrl,
        tmnxSubHostInfoV2GtpLclBrkout    TruthValue,
        tmnxSubHostInfoV2DiamSessId      DisplayString,
        tmnxSubHostInfoV2IpoeIndex       Unsigned32
    }
tmnxSubHostInfoV2IpAddressType OBJECT-TYPE
    SYNTAX      InetAddressType
    MAX-ACCESS  not-accessible
    STATUS      current
    DESCRIPTION
        "The value of tmnxSubHostInfoV2IpAddressType specifies the type of
         address stored in tmnxSubHostInfoV2IpAddress."
    ::= { tmnxSubHostInfoV2Entry 1 }

tmnxSubHostInfoV2IpAddress OBJECT-TYPE
    SYNTAX      InetAddress (SIZE(4|16))
    MAX-ACCESS  not-accessible
    STATUS      current
    DESCRIPTION
        "The value of tmnxSubHostInfoV2IpAddress specifies the IP address of
         this subscriber host."
    ::= { tmnxSubHostInfoV2Entry 2 }

tmnxSubHostInfoV2MacAddress OBJECT-TYPE
    SYNTAX      MacAddress
    MAX-ACCESS  not-accessible
    STATUS      current
    DESCRIPTION
        "The value of tmnxSubHostInfoV2MacAddress specifies the MAC address of
         this subscriber host."
    ::= { tmnxSubHostInfoV2Entry 3 }

tmnxSubHostInfoV2PppoeSessionId OBJECT-TYPE
    SYNTAX      TmnxPppoeSessionId
    MAX-ACCESS  not-accessible
    STATUS      current
    DESCRIPTION
        "The value of tmnxSubHostInfoV2PppoeSessionId specifies the PPPoE
         session id of this subscriber host."
    ::= { tmnxSubHostInfoV2Entry 4 }

tmnxSubHostInfoV2FwdingState OBJECT-TYPE
    SYNTAX      TmnxOperState
    MAX-ACCESS  read-only
    STATUS      current
    DESCRIPTION
        "The value of tmnxSubHostInfoV2FwdingState indicates the forwarding
         state of this subscriber host. When the value is 'outOfService', host
         traffic is not forwarded. When it is 'inService', host traffic is
         forwarded."
    ::= { tmnxSubHostInfoV2Entry 5 }

tmnxSubHostInfoV2Origin OBJECT-TYPE
    SYNTAX      TmnxSubHostOrigin
    MAX-ACCESS  read-only
    STATUS      current
    DESCRIPTION
        "The value of tmnxSubHostInfoV2Origin indicates the origin of this
         subscriber host."
    ::= { tmnxSubHostInfoV2Entry 6 }

tmnxSubHostInfoV2SubIdent OBJECT-TYPE
    SYNTAX      DisplayString
    MAX-ACCESS  read-only
    STATUS      current
    DESCRIPTION
        "The value of tmnxSubHostInfoV2SubIdent indicates the subscriber
         identification applicable for this subscriber host. If subscriber
         management is disabled for the corresponding SAP (see
         TIMETRA-SAP-MIB::sapSubMgmtAdminStatus), this object may contain an
         empty string."
    ::= { tmnxSubHostInfoV2Entry 7 }

tmnxSubHostInfoV2SubProfile OBJECT-TYPE
    SYNTAX      TNamedItemOrEmpty
    MAX-ACCESS  read-only
    STATUS      current
    DESCRIPTION
        "The value of tmnxSubHostInfoV2SubProfile indicates the subscriber
         profile (found in tmnxSubProfileTable) used by this subscriber host. If
         subscriber management is disabled for the corresponding SAP (see
         TIMETRA-SAP-MIB::sapSubMgmtAdminStatus), this object will contain an
         empty string."
    ::= { tmnxSubHostInfoV2Entry 8 }

tmnxSubHostInfoV2SLAProfile OBJECT-TYPE
    SYNTAX      TNamedItemOrEmpty
    MAX-ACCESS  read-only
    STATUS      current
    DESCRIPTION
        "The value of tmnxSubHostInfoV2SLAProfile indicates the SLA profile
         (found in tmnxSLAProfileTable) used by this subscriber host. If
         subscriber management is disabled for the corresponding SAP (see
         TIMETRA-SAP-MIB::sapSubMgmtAdminStatus), this object will contain an
         empty string."
    ::= { tmnxSubHostInfoV2Entry 9 }

tmnxSubHostInfoV2AppProfile OBJECT-TYPE
    SYNTAX      TNamedItemOrEmpty
    MAX-ACCESS  read-only
    STATUS      current
    DESCRIPTION
        "The value of tmnxSubHostInfoV2AppProfile indicates the application
         profile (found in TIMETRA-BSX-NG-MIB::tmnxBsxAppProfTable) used by
         this subscriber host. If subscriber management is disabled for the
         corresponding SAP (see TIMETRA-SAP-MIB::sapSubMgmtAdminStatus),
         this object will contain an empty string."
    ::= { tmnxSubHostInfoV2Entry 10 }

tmnxSubHostInfoV2RetailerSvcId OBJECT-TYPE
    SYNTAX      TmnxServId
    MAX-ACCESS  read-only
    STATUS      current
    DESCRIPTION
        "The value of tmnxSubHostInfoV2RetailerSvcId indicates the service ID of
         the retailer VPRN service to which this subscriber host belongs. When
         this object is non zero, the subscriber host belongs to a retailer
         VPRN."
    ::= { tmnxSubHostInfoV2Entry 11 }

tmnxSubHostInfoV2RetailerIf OBJECT-TYPE
    SYNTAX      InterfaceIndexOrZero
    MAX-ACCESS  read-only
    STATUS      current
    DESCRIPTION
        "The value of tmnxSubHostInfoV2RetailerIf indicates the interface index
         of the retailer VPRN interface to which this subscriber host belongs.
         When this object is non zero, the subscriber host belongs to a retailer
         VPRN."
    ::= { tmnxSubHostInfoV2Entry 12 }

tmnxSubHostInfoV2PfxLen OBJECT-TYPE
    SYNTAX      InetAddressPrefixLength (0..128)
    MAX-ACCESS  read-only
    STATUS      current
    DESCRIPTION 
        "The value of tmnxSubHostInfoV2PfxLen indicates
         the length of the prefix stored in tmnxSubHostInfoV2IpAddress."
    ::= { tmnxSubHostInfoV2Entry 13 }

tmnxSubHostInfoV2EgrQGrpName OBJECT-TYPE
    SYNTAX      TNamedItemOrEmpty
    MAX-ACCESS  read-only
    STATUS      current
    DESCRIPTION
        "The value of tmnxSubHostInfoV2EgrQGrpName indicates the port access
         egress queue group (found in
         TIMETRA-PORT-MIB.mib::tPortAccEgrQGrpTable) used by this subscriber
         host."
    ::= { tmnxSubHostInfoV2Entry 14 }

tmnxSubHostInfoV2EgrVPortName OBJECT-TYPE
    SYNTAX      TNamedItemOrEmpty
    MAX-ACCESS  read-only
    STATUS      current
    DESCRIPTION
        "The value of tmnxSubHostInfoV2EgrVPortName indicates the port access
         egress virtual port (found in
         TIMETRA-PORT-MIB.mib::tPortEgrVPortTable) used by this subscriber
         host."
    ::= { tmnxSubHostInfoV2Entry 15 }

tmnxSubHostInfoV2AcctSessionId OBJECT-TYPE
    SYNTAX      TmnxSubAcctSessionId
    MAX-ACCESS  read-only
    STATUS      current
    DESCRIPTION
        "The value of tmnxSubHostInfoV2AcctSessionId indicates the RADIUS
         accounting session id for this subscriber host."
    ::= { tmnxSubHostInfoV2Entry 16 }

tmnxSubHostInfoV2AddressOrigin OBJECT-TYPE
    SYNTAX      INTEGER {
                    notApplicable (0),
                    aaa (1),
                    dhcp (2),
                    ludb (3)
                }
    MAX-ACCESS  read-only
    STATUS      current
    DESCRIPTION
        "The value of tmnxSubHostInfoV2AddressOrigin indicates
         the origin of the subscriber host address.
         
         This object is only applicable for L3 subscriber hosts."
    ::= { tmnxSubHostInfoV2Entry 17 }

tmnxSubHostInfoV2PppIndex OBJECT-TYPE
    SYNTAX      Unsigned32
    MAX-ACCESS  read-only
    STATUS      current
    DESCRIPTION
        "The value of tmnxSubHostInfoV2PppIndex indicates
         the index in the tmnxSubPppTable for PPP hosts.
         
         The value of tmnxSubHostInfoV2PppIndex is equal to zero for other 
         types of hosts."
    ::= { tmnxSubHostInfoV2Entry 18 }
    
tmnxSubHostInfoV2AcctMultiSessId OBJECT-TYPE
    SYNTAX      TmnxSubAcctSessionId
    MAX-ACCESS  read-only
    STATUS      current
    DESCRIPTION
        "The value of tmnxSubHostInfoV2AcctMultiSessId indicates the RADIUS
         accounting session id of the queue-instance of this subscriber host. 
         This is the accounting session id of the SLA profile instance on a 
         non-hsmda or the accounting session id of the subscriber on a hsmda."
    ::= { tmnxSubHostInfoV2Entry 19 }

tmnxSubHostInfoV2IngFilter OBJECT-TYPE
    SYNTAX      TOverruleFilterId
    MAX-ACCESS  read-only
    STATUS      current
    DESCRIPTION
        "The value of tmnxSubHostInfoV2IngFilter indicates
         if and how for this host the ingress filter specified in the
         SLA-profile is overruled."
    ::= { tmnxSubHostInfoV2Entry 20 }
    
tmnxSubHostInfoV2EgrFilter OBJECT-TYPE
    SYNTAX      TOverruleFilterId
    MAX-ACCESS  read-only
    STATUS      current
    DESCRIPTION
        "The value of tmnxSubHostInfoV2EgrFilter indicates
         if and how for this host the egress filter specified in the
         SLA-profile is overruled."
    ::= { tmnxSubHostInfoV2Entry 21 }
        
tmnxSubHostInfoV2OtHttpRdrState OBJECT-TYPE
    SYNTAX      INTEGER {
                    off       (0),
                    active    (1),
                    triggered (2)
                }
    MAX-ACCESS  read-only
    STATUS      current
    DESCRIPTION
        "The value of tmnxSubHostInfoV2OtHttpRdrState indicates the state of
         One-Time HTTP redirection for this host."         
    ::= { tmnxSubHostInfoV2Entry 22 }      
        
tmnxSubHostInfoV2OtHttpRdrFilter OBJECT-TYPE
    SYNTAX      TOverruleFilterId
    MAX-ACCESS  read-only
    STATUS      current
    DESCRIPTION
        "The value of tmnxSubHostInfoV2OtHttpRdrFilter indicates 
         if and how for this host the one-time HTTP redirect filter 
         specified in the SLA-profile is overruled."
    ::= { tmnxSubHostInfoV2Entry 23 }         
    
tmnxSubHostInfoV2OtHttpRdrSource OBJECT-TYPE
    SYNTAX      INTEGER {
                    unknown      (0),
                    sla-profile  (1),
                    radius       (2),
                    radius-coa   (3),
                    diameter     (4),
                    diameter-rar (5)
                }
    MAX-ACCESS  read-only
    STATUS      current
    DESCRIPTION
        "The value of tmnxSubHostInfoV2OtHttpRdrSource indicates the source of
         One-Time HTTP redirection for this host."         
    ::= { tmnxSubHostInfoV2Entry 24 }       
    
tmnxSubHostInfoV2HttpRdrUrlOvrd OBJECT-TYPE
    SYNTAX      TmnxHttpRedirectUrl
    MAX-ACCESS  read-only
    STATUS      current
    DESCRIPTION
        "The value of tmnxSubHostInfoV2HttpRdrUrlOvrd indicates a possible 
         override of the HTTP redirect URL for this host. An empty string will
         be returned when the default redirect URL is used (found in
         TIMETRA-FILTER-MIB.mib::tIPFilterParamsTable or
         TIMETRA-FILTER-MIB.mib::tIPv6FilterParamsTable)"
    ::= { tmnxSubHostInfoV2Entry 25 }
    
tmnxSubHostInfoV2GtpLclBrkout OBJECT-TYPE
    SYNTAX      TruthValue
    MAX-ACCESS  read-only
    STATUS      current
    DESCRIPTION
        "The value of tmnxSubHostInfoV2GtpLclBrkout indicates
         if this host is a GTP (GPRS Tunnel Protocol) host
         with a local break-out.
         
         By default, the traffic of such a host would go into
         a GTP tunnel, but selected flows are redirected through
         a NAT function and routed in the context of
         the WLAN Gateway (this system); flows can be selected
         with a filter, specifying 'gtpLclBrkout' as filter action."
    ::= { tmnxSubHostInfoV2Entry 26 }
    
tmnxSubHostInfoV2DiamSessId OBJECT-TYPE
    SYNTAX      DisplayString (SIZE(0..102))
    MAX-ACCESS  read-only
    STATUS      current
    DESCRIPTION
        "The value of tmnxSubHostInfoV2DiamSessId indicates
         the identifier of the DIAMETER session associated
         with this subscriber host.
         
         The empty string indicates that there is no DIAMETER session
         associated with this subscriber host."
    ::= { tmnxSubHostInfoV2Entry 27 }
    

tmnxSubHostInfoV2IpoeIndex OBJECT-TYPE
    SYNTAX      Unsigned32
    MAX-ACCESS  read-only
    STATUS      current
    DESCRIPTION
        "The value of tmnxSubHostInfoV2IpoeIndex indicates
         the index in the tmnxSubIpoeTable for IPoE hosts.
         
         The value of tmnxSubHostInfoV2IpoeIndex is equal to zero for other 
         types of hosts."
    ::= { tmnxSubHostInfoV2Entry 30 }

-- ----------------------------------------
-- tmnxSLAProfInstSubHostV2Table
-- ----------------------------------------
tmnxSLAProfInstSubHostV2Table OBJECT-TYPE
    SYNTAX      SEQUENCE OF TmnxSLAProfInstSubHostV2Entry
    MAX-ACCESS  not-accessible
    STATUS      current
    DESCRIPTION
        "The tmnxSLAProfInstSubHostV2Table has an entry for each subscriber host
         found in the system, sorted by SLA profile instance."
    ::= { tmnxSubMgmtObjects 42 }

tmnxSLAProfInstSubHostV2Entry OBJECT-TYPE
    SYNTAX      TmnxSLAProfInstSubHostV2Entry
    MAX-ACCESS  not-accessible
    STATUS      current
    DESCRIPTION
        "Each row entry indicates a particular subscriber host available in the
         system."
    INDEX { tmnxSubInfoSubIdent,
            sapPortId,
            sapEncapValue,
            tmnxSLAProfName,
            tmnxSPISubHostV2IpAddressType,
            tmnxSPISubHostV2IpAddress,
            tmnxSPISubHostV2MacAddress,
            tmnxSPISubHostV2PppoeSessionId }
    ::= { tmnxSLAProfInstSubHostV2Table 1 }

TmnxSLAProfInstSubHostV2Entry ::=
    SEQUENCE {
        tmnxSPISubHostV2IpAddressType  InetAddressType,
        tmnxSPISubHostV2IpAddress      InetAddress,
        tmnxSPISubHostV2MacAddress     MacAddress,
        tmnxSPISubHostV2PppoeSessionId TmnxPppoeSessionId,
        tmnxSPISubHostV2Origin         TmnxSubHostOrigin,
        tmnxSPISubHostV2PfxLen         InetAddressPrefixLength,
        tmnxSPISubHostV2Service        TmnxServId
    }

tmnxSPISubHostV2IpAddressType OBJECT-TYPE
    SYNTAX      InetAddressType
    MAX-ACCESS  not-accessible
    STATUS      current
    DESCRIPTION
        "The value of tmnxSPISubHostV2IpAddressType specifies the type of
         address stored in tmnxSPISubHostV2IpAddress."
    ::= { tmnxSLAProfInstSubHostV2Entry 1 }

tmnxSPISubHostV2IpAddress OBJECT-TYPE
    SYNTAX      InetAddress (SIZE(4|16))
    MAX-ACCESS  not-accessible
    STATUS      current
    DESCRIPTION
        "The value of tmnxSPISubHostV2IpAddress specifies the IP address of this
         subscriber host."
    ::= { tmnxSLAProfInstSubHostV2Entry 2 }

tmnxSPISubHostV2MacAddress OBJECT-TYPE
    SYNTAX      MacAddress
    MAX-ACCESS  not-accessible
    STATUS      current
    DESCRIPTION
        "The value of tmnxSPISubHostV2MacAddress indicates the MAC address of
         this subscriber host."
    ::= { tmnxSLAProfInstSubHostV2Entry 3 }

tmnxSPISubHostV2PppoeSessionId OBJECT-TYPE
    SYNTAX      TmnxPppoeSessionId
    MAX-ACCESS  not-accessible
    STATUS      current
    DESCRIPTION
        "The value of tmnxSPISubHostV2PppoeSessionId specifies the PPPoE
         session id of this subscriber host."
    ::= { tmnxSLAProfInstSubHostV2Entry 4 }

tmnxSPISubHostV2Origin OBJECT-TYPE
    SYNTAX      TmnxSubHostOrigin
    MAX-ACCESS  read-only
    STATUS      current
    DESCRIPTION
        "The value of tmnxSPISubHostV2Origin indicates the origin of this
         subscriber host."
    ::= { tmnxSLAProfInstSubHostV2Entry 5 }

tmnxSPISubHostV2PfxLen OBJECT-TYPE
    SYNTAX      InetAddressPrefixLength (0..128)
    MAX-ACCESS  read-only
    STATUS      current
    DESCRIPTION 
        "The value of tmnxSPISubHostV2PfxLen indicates
         the prefix length associated with the subscriber host IP address
         indicated by tmnxSPISubHostV2IpAddress."
    ::= { tmnxSLAProfInstSubHostV2Entry 6 }

tmnxSPISubHostV2Service OBJECT-TYPE
    SYNTAX      TmnxServId
    MAX-ACCESS  read-only
    STATUS      current
    DESCRIPTION 
        "The value of tmnxSPISubHostV2Service indicates
         the identifier of the service where this host belongs to."
    ::= { tmnxSLAProfInstSubHostV2Entry 7 }

-- --------------------------------------------------------
-- tmnxSubTrkPlcyTable
-- --------------------------------------------------------
tmnxSubTrkPlcyTable OBJECT-TYPE
    SYNTAX      SEQUENCE OF TmnxSubTrkPlcyEntry
    MAX-ACCESS  not-accessible
    STATUS      current
    DESCRIPTION
        "The tmnxSubTrkPlcyTable allows configuration of subscriber IGMP Host
         tracking policy parameters."
    ::= { tmnxSubMgmtObjects 43 }

tmnxSubTrkPlcyEntry OBJECT-TYPE
    SYNTAX      TmnxSubTrkPlcyEntry
    MAX-ACCESS  not-accessible
    STATUS      current
    DESCRIPTION
        "tmnxSubTrkPlcyEntry is an entry (conceptual row) in the
         tmnxSubTrkPlcyTable.

         Each entry represents the configuration for an IGMP Host Tracking
         policy.

         Entries in this table can be created and deleted via
         SNMP SET operations to tmnxSubTrkPlcyRowStatus.

         Entries have a presumed StorageType of nonVolatile."
    INDEX { tmnxSubTrkPlcyName }
    ::= { tmnxSubTrkPlcyTable 1 }

TmnxSubTrkPlcyEntry ::= SEQUENCE {
    tmnxSubTrkPlcyName              TNamedItem,
    tmnxSubTrkPlcyRowStatus         RowStatus,
    tmnxSubTrkPlcyLastMgmtChange    TimeStamp,
    tmnxSubTrkPlcyDescription       TItemDescription,
    tmnxSubTrkPlcyEgrRateModType    TEgrRateModType,
    tmnxSubTrkPlcyEgrRateModSched   TNamedItemOrEmpty,
    tmnxSubTrkPlcyMcRprtDestName    TNamedItemOrEmpty,
    tmnxSubTrkPlcyMcRprtOptFields   BITS,
    tmnxSubTrkPlcyMcRprtAdminState  TmnxAdminState
}

tmnxSubTrkPlcyName OBJECT-TYPE
    SYNTAX      TNamedItem
    MAX-ACCESS  not-accessible
    STATUS      current
    DESCRIPTION
        "The value of tmnxSubTrkPlcyName specifies a specific subscriber
         IGMP Host Tracking policy."
    ::= { tmnxSubTrkPlcyEntry 1 }

tmnxSubTrkPlcyRowStatus OBJECT-TYPE
    SYNTAX      RowStatus
    MAX-ACCESS  read-create
    STATUS      current
    DESCRIPTION
        "The value of tmnxSubTrkPlcyRowStatus controls the creation and
         deletion of rows in the table."
    ::= { tmnxSubTrkPlcyEntry 2 }

tmnxSubTrkPlcyLastMgmtChange OBJECT-TYPE
    SYNTAX      TimeStamp
    MAX-ACCESS  read-only
    STATUS      current
    DESCRIPTION
        "The value of tmnxSubTrkPlcyLastMgmtChange indicates the sysUpTime at
         the time of the most recent management-initiated change to this
         policy."
    ::= { tmnxSubTrkPlcyEntry 3 }

tmnxSubTrkPlcyDescription OBJECT-TYPE
    SYNTAX      TItemDescription
    MAX-ACCESS  read-create
    STATUS      current
    DESCRIPTION
        "The value of tmnxSubTrkPlcyDescription specifies the user provided
         description of this subscriber IGMP Host Tracking policy."
    DEFVAL { "" }
    ::= { tmnxSubTrkPlcyEntry 4 }

tmnxSubTrkPlcyEgrRateModType OBJECT-TYPE
    SYNTAX      TEgrRateModType
    MAX-ACCESS  read-create
    STATUS      current
    DESCRIPTION
        "The value of tmnxSubTrkPlcyEgrRateModType specifies the egress-rate
         modification that is to be applied.

         If set to 'namedScheduler', the scheduler as defined in
         tmnxSubTrkPlcyEgrRateModSched is used."
    DEFVAL { none }
    ::= { tmnxSubTrkPlcyEntry 5 }

tmnxSubTrkPlcyEgrRateModSched OBJECT-TYPE
    SYNTAX      TNamedItemOrEmpty
    MAX-ACCESS  read-create
    STATUS      current
    DESCRIPTION
        "The value of tmnxSubTrkPlcyEgrRateModSched specifies the scheduler to
         be applied for egress rate modification.

         The value is only considered if tmnxSubTrkPlcyEgrRateModType is set to
         'namedScheduler'."
    DEFVAL { "" }
    ::= { tmnxSubTrkPlcyEntry 6 }

tmnxSubTrkPlcyMcRprtDestName OBJECT-TYPE
    SYNTAX      TNamedItemOrEmpty
    MAX-ACCESS  read-create
    STATUS      current
    DESCRIPTION
        "The value of tmnxSubTrkPlcyMcRprtDestName indicates the multicast
         reporting destination 
         (found in TIMETRA-MCAST-PATH-MGMT-MIB::tmnxMcPathRprtDestTable)
         or it can be an empty string."
    DEFVAL { ''H }
    ::= { tmnxSubTrkPlcyEntry 7 }

tmnxSubTrkPlcyMcRprtOptFields OBJECT-TYPE
    SYNTAX      BITS {
                    hostMac             (0),
                    pppoeSessionId      (1),
                    svcId               (2),
                    sapId               (3)
                }
    MAX-ACCESS  read-create
    STATUS      current
    DESCRIPTION
        "The value of tmnxSubTrkPlcyMcRprtOptFields specifies what optional
        fields should be included into the multicast reporting messages."
    DEFVAL { { } }
    ::= { tmnxSubTrkPlcyEntry 8 }

tmnxSubTrkPlcyMcRprtAdminState OBJECT-TYPE
    SYNTAX          TmnxAdminState
    MAX-ACCESS      read-create
    STATUS          current
    DESCRIPTION
        "The value of tmnxSubTrkPlcyMcRprtAdminState indicates the administrative
         state of the multicast reporting. When the value is 'outOfService', 
         no multicast reports are sent. When it is 'inService', multicast reports
         are sent to the destination as indicated by tmnxSubTrkPlcyMcRprtDestName."
    DEFVAL { outOfService }
    ::= { tmnxSubTrkPlcyEntry 9 }


-- ------------------------------------------------
-- tmnxSubTrkStatusTable
-- ------------------------------------------------

--  Sparse Dependent Extension of the tmnxSubscriberInfoTable
--  The same indexes are used for both the base table, tmnxSubscriberInfoTable,
--  and the sparse dependent table, tmnxSubTrkStatusTable.
--
--  This in effect extends the tmnxSubscriberInfoTable with additional columns.
--  A row is automatically created in the tmnxSubTrkStatusTable
--  for each applicable row in the tmnxSubscriberInfoTable .
--
--  Deletion of a row in the tmnxSubscriberInfoTable results in the
--  same fate for the row in the tmnxSubTrkStatusTable.

tmnxSubTrkStatusTable OBJECT-TYPE
    SYNTAX      SEQUENCE OF TmnxSubTrkStatusEntry
    MAX-ACCESS  not-accessible
    STATUS      current
    DESCRIPTION
        "The tmnxSubTrkStatusTable has an entry for each subscriber
         that is associated with a host tracking policy.

         A subscriber is associated with a host tracking policy if the value of
         the object tmnxSubInfoSubProfile refers to a subscriber policy where
         the value of the object tmnxSubProfHostTrackingPolicy is not empty."
    ::= { tmnxSubMgmtObjects 44 }

tmnxSubTrkStatusEntry OBJECT-TYPE
    SYNTAX      TmnxSubTrkStatusEntry
    MAX-ACCESS  not-accessible
    STATUS      current
    DESCRIPTION
        "Each row entry represents status and statistics information
         about the QoS scheduler adjustments based on video viewership of
         this subscriber's hosts.

         Rows are created or removed automatically by the system."
    INDEX { IMPLIED tmnxSubInfoSubIdent }
    ::= { tmnxSubTrkStatusTable 1 }

TmnxSubTrkStatusEntry ::= SEQUENCE
   {
        tmnxSubTrkStatusPlcyName         TNamedItemOrEmpty,
        tmnxSubTrkStatusEgrRateReduction Unsigned32
   }

tmnxSubTrkStatusPlcyName OBJECT-TYPE
    SYNTAX      TNamedItemOrEmpty
    MAX-ACCESS  read-only
    STATUS      current
    DESCRIPTION
        "The value of tmnxSubTrkStatusPlcyName indicates
         the name of the host tracking policy associated with this subscriber.

         An empty string indicates that no host tracking policy is associated
         with this subscriber."
    ::= { tmnxSubTrkStatusEntry 1 }

tmnxSubTrkStatusEgrRateReduction OBJECT-TYPE
    SYNTAX      Unsigned32
    UNITS       "kbps"
    MAX-ACCESS  read-only
    STATUS      current
    DESCRIPTION
        "The value of tmnxSubTrkStatusEgrRateReduction indicates
         the egress rate reduction to be applied for this subscriber
         in order to account for its video viewership."
    ::= { tmnxSubTrkStatusEntry 2 }

-- ------------------------------------------------
-- tmnxSubHostTrkTable
-- ------------------------------------------------

tmnxSubHostTrkTable OBJECT-TYPE
    SYNTAX      SEQUENCE OF TmnxSubHostTrkEntry
    MAX-ACCESS  not-accessible
    STATUS      current
    DESCRIPTION
        "The tmnxSubHostTrkTable shows status and statistics information
         about the video viewership of subscriber hosts."
    ::= { tmnxSubMgmtObjects 45 }

tmnxSubHostTrkEntry OBJECT-TYPE
    SYNTAX      TmnxSubHostTrkEntry
    MAX-ACCESS  not-accessible
    STATUS      current
    DESCRIPTION
        "Each row entry represents status information
         about a particular multicast stream associated with a particular
         subscriber host.

         Rows are created or removed automatically by the system.

         Rows are only created for a subscriber that is associated with
         a host tracking policy.

         A subscriber is associated with a host tracking policy if the value of
         the object tmnxSubInfoSubProfile refers to a subscriber policy where
         the value of the object tmnxSubProfHostTrackingPolicy is not empty"
    INDEX { tmnxSubInfoSubIdent,
            svcId, sapPortId, sapEncapValue,
            tmnxSubHostInfoV2IpAddressType, tmnxSubHostInfoV2IpAddress,
            tmnxSubHostTrkGrpAddrType, tmnxSubHostTrkGrpAddr,
            tmnxSubHostTrkSrcAddrType, tmnxSubHostTrkSrcAddr
          }
    ::= { tmnxSubHostTrkTable 1 }

TmnxSubHostTrkEntry ::= SEQUENCE
   {
        tmnxSubHostTrkGrpAddrType        InetAddressType,
        tmnxSubHostTrkGrpAddr            InetAddress,
        tmnxSubHostTrkSrcAddrType        InetAddressType,
        tmnxSubHostTrkSrcAddr            InetAddress,
        tmnxSubHostTrkBw                 Unsigned32,
        tmnxSubHostTrkUpTime             TimeInterval,
        tmnxSubHostTrkExpiryTime         Unsigned32
   }

tmnxSubHostTrkGrpAddrType OBJECT-TYPE
    SYNTAX      InetAddressType
    MAX-ACCESS  not-accessible
    STATUS      current
    DESCRIPTION
        "The value of tmnxSubHostTrkGrpAddrType indicates
         the address type of tmnxSubHostTrkGrpAddr."
    ::= { tmnxSubHostTrkEntry 1 }

tmnxSubHostTrkGrpAddr OBJECT-TYPE
    SYNTAX      InetAddress (SIZE(4|16))
    MAX-ACCESS  not-accessible
    STATUS      current
    DESCRIPTION     "The value of tmnxSubHostTrkGrpAddr indicates
                     the multicast group address."
    ::= { tmnxSubHostTrkEntry 2 }

tmnxSubHostTrkSrcAddrType OBJECT-TYPE
    SYNTAX      InetAddressType
    MAX-ACCESS  not-accessible
    STATUS      current
    DESCRIPTION
        "The value of tmnxSubHostTrkSrcAddrType indicates
         the address type of tmnxSubHostTrkSrcAddr."
    ::= { tmnxSubHostTrkEntry 3 }

tmnxSubHostTrkSrcAddr OBJECT-TYPE
    SYNTAX      InetAddress (SIZE(4|16))
    MAX-ACCESS  not-accessible
    STATUS      current
    DESCRIPTION
        "The value of tmnxSubHostTrkSrcAddr indicates
         the address of the source that sends multicast traffic
         to the group identified by tmnxSubHostTrkGrpAddr."
    ::= { tmnxSubHostTrkEntry 4 }

tmnxSubHostTrkBw OBJECT-TYPE
    SYNTAX      Unsigned32
    UNITS       "kbps"
    MAX-ACCESS  read-only
    STATUS      current
    DESCRIPTION
        "The value of tmnxSubHostTrkBw indicates
         the bandwidth allocated to this subscriber host for this multicast
         stream."
    ::= { tmnxSubHostTrkEntry 5 }

tmnxSubHostTrkUpTime OBJECT-TYPE
    SYNTAX      TimeInterval
    MAX-ACCESS  read-only
    STATUS      current
    DESCRIPTION
        "The value of tmnxSubHostTrkUpTime indicates
         the time (in hundredths of a second) that the subscriber host
         identified by tmnxSubInfoSubIdent is associated with
         the multicast group identified by tmnxSubHostTrkGrpAddr through
         the multicast source identified by tmnxSubHostTrkSrcAddr."
    ::= { tmnxSubHostTrkEntry 6 }

tmnxSubHostTrkExpiryTime OBJECT-TYPE
    SYNTAX      Unsigned32
    UNITS       "seconds"
    MAX-ACCESS  read-only
    STATUS      current
    DESCRIPTION
        "The value of tmnxSubHostTrkExpiryTime indicates
         the time in seconds that this system will continue to track this host."
    ::= { tmnxSubHostTrkEntry 7 }

-- ------------------------------------------------
-- tmnxSubHostSapTrkTable
-- ------------------------------------------------

tmnxSubHostSapTrkTable OBJECT-TYPE
    SYNTAX      SEQUENCE OF TmnxSubHostSapTrkEntry
    MAX-ACCESS  not-accessible
    STATUS      current
    DESCRIPTION
        "The tmnxSubHostSapTrkTable shows status information
         about the video viewership of hosts, ordered by SAP."
    ::= { tmnxSubMgmtObjects 46 }

tmnxSubHostSapTrkEntry OBJECT-TYPE
    SYNTAX      TmnxSubHostSapTrkEntry
    MAX-ACCESS  not-accessible
    STATUS      current
    DESCRIPTION
        "Each row entry represents status and statistics information
         about a particular host associated with a particular multicast stream.

         Rows are created or removed automatically by the system."
    INDEX { svcId, sapPortId, sapEncapValue,
            tmnxSubHostSapTrkHostAddrType, tmnxSubHostSapTrkHostAddr,
            tmnxSubHostSapTrkGrpAddrType, tmnxSubHostSapTrkGrpAddr,
            tmnxSubHostSapTrkSrcAddrType, tmnxSubHostSapTrkSrcAddr
          }
    ::= { tmnxSubHostSapTrkTable 1 }

TmnxSubHostSapTrkEntry ::= SEQUENCE
   {
        tmnxSubHostSapTrkHostAddrType    InetAddressType,
        tmnxSubHostSapTrkHostAddr        InetAddress,
        tmnxSubHostSapTrkGrpAddrType     InetAddressType,
        tmnxSubHostSapTrkGrpAddr         InetAddress,
        tmnxSubHostSapTrkSrcAddrType     InetAddressType,
        tmnxSubHostSapTrkSrcAddr         InetAddress,
        tmnxSubHostSapTrkBw              Unsigned32,
        tmnxSubHostSapTrkUpTime          TimeInterval,
        tmnxSubHostSapTrkExpiryTime      Unsigned32,
        tmnxSubHostSapTrkSubIdent        TmnxSubIdentStringOrEmpty
   }

tmnxSubHostSapTrkHostAddrType OBJECT-TYPE
    SYNTAX      InetAddressType
    MAX-ACCESS  not-accessible
    STATUS      current
    DESCRIPTION
        "The value of tmnxSubHostSapTrkHostAddrType indicates
         the address type of tmnxSubHostSapTrkHostAddr."
    ::= { tmnxSubHostSapTrkEntry 1 }

tmnxSubHostSapTrkHostAddr OBJECT-TYPE
    SYNTAX      InetAddress (SIZE(4|16))
    MAX-ACCESS  not-accessible
    STATUS      current
    DESCRIPTION
        "The value of tmnxSubHostSapTrkHostAddr indicates
         the address of the host."
    ::= { tmnxSubHostSapTrkEntry 2 }

tmnxSubHostSapTrkGrpAddrType OBJECT-TYPE
    SYNTAX      InetAddressType
    MAX-ACCESS  not-accessible
    STATUS      current
    DESCRIPTION
        "The value of tmnxSubHostSapTrkGrpAddrType indicates
                     the address type of tmnxSubHostSapTrkGrpAddr."
    ::= { tmnxSubHostSapTrkEntry 3 }

tmnxSubHostSapTrkGrpAddr OBJECT-TYPE
    SYNTAX      InetAddress (SIZE(4|16))
    MAX-ACCESS  not-accessible
    STATUS      current
    DESCRIPTION     "The value of tmnxSubHostSapTrkGrpAddr indicates
                     the multicast group address."
    ::= { tmnxSubHostSapTrkEntry 4 }

tmnxSubHostSapTrkSrcAddrType OBJECT-TYPE
    SYNTAX      InetAddressType
    MAX-ACCESS  not-accessible
    STATUS      current
    DESCRIPTION
        "The value of tmnxSubHostSapTrkSrcAddrType indicates
         the address type of tmnxSubHostSapTrkSrcAddr."
    ::= { tmnxSubHostSapTrkEntry 5 }

tmnxSubHostSapTrkSrcAddr OBJECT-TYPE
    SYNTAX      InetAddress (SIZE(4|16))
    MAX-ACCESS  not-accessible
    STATUS      current
    DESCRIPTION
        "The value of tmnxSubHostSapTrkSrcAddr indicates
         the address of the source that sends multicast traffic
         to the group identified by tmnxSubHostSapTrkGrpAddr."
    ::= { tmnxSubHostSapTrkEntry 6 }

tmnxSubHostSapTrkBw OBJECT-TYPE
    SYNTAX      Unsigned32
    UNITS       "kbps"
    MAX-ACCESS  read-only
    STATUS      current
    DESCRIPTION
        "The value of tmnxSubHostSapTrkBw indicates
         the bandwidth allocated to this host for this multicast
         stream."
    ::= { tmnxSubHostSapTrkEntry 7 }

tmnxSubHostSapTrkUpTime OBJECT-TYPE
    SYNTAX      TimeInterval
    MAX-ACCESS  read-only
    STATUS      current
    DESCRIPTION
        "The value of tmnxSubHostSapTrkUpTime indicates
         the time (in hundredths of a second) that the host is associated with
         the multicast group identified by tmnxSubHostSapTrkGrpAddr through
         the multicast source identified by tmnxSubHostSapTrkSrcAddr."
    ::= { tmnxSubHostSapTrkEntry 8 }

tmnxSubHostSapTrkExpiryTime OBJECT-TYPE
    SYNTAX      Unsigned32
    UNITS       "seconds"
    MAX-ACCESS  read-only
    STATUS      current
    DESCRIPTION
        "The value of tmnxSubHostSapTrkExpiryTime indicates
         the time in seconds that this system will continue to track this host."
    ::= { tmnxSubHostSapTrkEntry 9 }

tmnxSubHostSapTrkSubIdent OBJECT-TYPE
    SYNTAX      TmnxSubIdentStringOrEmpty
    MAX-ACCESS  read-only
    STATUS      current
    DESCRIPTION
        "The value of tmnxSubHostSapTrkSubIdent indicates
         the subscriber identification of this subscriber host.

         The subscriber identification is only available in case of
         enhanced subscriber management.

         In other cases, the value of tmnxSubHostSapTrkSubIdent is empty."
    ::= { tmnxSubHostSapTrkEntry 10 }

-- ------------------------------------------------
-- tmnxSubHostGrpTrkTable
-- ------------------------------------------------

tmnxSubHostGrpTrkTable OBJECT-TYPE
    SYNTAX      SEQUENCE OF TmnxSubHostGrpTrkEntry
    MAX-ACCESS  not-accessible
    STATUS      current
    DESCRIPTION
        "The tmnxSubHostGrpTrkTable shows status and statistics information
         about the video viewership of hosts, ordered by multicast group."
    ::= { tmnxSubMgmtObjects 47 }

tmnxSubHostGrpTrkEntry OBJECT-TYPE
    SYNTAX      TmnxSubHostGrpTrkEntry
    MAX-ACCESS  not-accessible
    STATUS      current
    DESCRIPTION
        "Each row entry represents status and statistics information
         about a particular multicast stream associated with a particular host.

         Rows are created or removed automatically by the system."
    INDEX {
            svcId,
            tmnxSubHostGrpTrkGrpAddrType, tmnxSubHostGrpTrkGrpAddr,
            tmnxSubHostGrpTrkSrcAddrType, tmnxSubHostGrpTrkSrcAddr,
            sapPortId, sapEncapValue,
            tmnxSubHostGrpTrkHostAddrType, tmnxSubHostGrpTrkHostAddr
          }
    ::= { tmnxSubHostGrpTrkTable 1 }

TmnxSubHostGrpTrkEntry ::= SEQUENCE
   {
        tmnxSubHostGrpTrkGrpAddrType     InetAddressType,
        tmnxSubHostGrpTrkGrpAddr         InetAddress,
        tmnxSubHostGrpTrkSrcAddrType     InetAddressType,
        tmnxSubHostGrpTrkSrcAddr         InetAddress,
        tmnxSubHostGrpTrkHostAddrType    InetAddressType,
        tmnxSubHostGrpTrkHostAddr        InetAddress,
        tmnxSubHostGrpTrkUpTime          TimeInterval,
        tmnxSubHostGrpTrkExpiryTime      Unsigned32,
        tmnxSubHostGrpTrkSubIdent        TmnxSubIdentStringOrEmpty
   }

tmnxSubHostGrpTrkGrpAddrType OBJECT-TYPE
    SYNTAX      InetAddressType
    MAX-ACCESS  not-accessible
    STATUS      current
    DESCRIPTION
        "The value of tmnxSubHostGrpTrkGrpAddrType indicates
         the address type of tmnxSubHostGrpTrkGrpAddr."
    ::= { tmnxSubHostGrpTrkEntry 1 }

tmnxSubHostGrpTrkGrpAddr OBJECT-TYPE
    SYNTAX      InetAddress (SIZE(4|16))
    MAX-ACCESS  not-accessible
    STATUS      current
    DESCRIPTION     "The value of tmnxSubHostGrpTrkGrpAddr indicates
                     the multicast group address."
    ::= { tmnxSubHostGrpTrkEntry 2 }

tmnxSubHostGrpTrkSrcAddrType OBJECT-TYPE
    SYNTAX      InetAddressType
    MAX-ACCESS  not-accessible
    STATUS      current
    DESCRIPTION
        "The value of tmnxSubHostGrpTrkSrcAddrType indicates
         the address type of tmnxSubHostGrpTrkSrcAddr."
    ::= { tmnxSubHostGrpTrkEntry 3 }

tmnxSubHostGrpTrkSrcAddr OBJECT-TYPE
    SYNTAX      InetAddress (SIZE(4|16))
    MAX-ACCESS  not-accessible
    STATUS      current
    DESCRIPTION
        "The value of tmnxSubHostGrpTrkSrcAddr indicates
         the address of the source that sends multicast traffic
         to the group identified by tmnxSubHostGrpTrkGrpAddr."
    ::= { tmnxSubHostGrpTrkEntry 4 }

tmnxSubHostGrpTrkHostAddrType OBJECT-TYPE
    SYNTAX      InetAddressType
    MAX-ACCESS  not-accessible
    STATUS      current
    DESCRIPTION
        "The value of tmnxSubHostGrpTrkHostAddrType indicates
         the address type of tmnxSubHostGrpTrkHostAddr."
    ::= { tmnxSubHostGrpTrkEntry 5 }

tmnxSubHostGrpTrkHostAddr OBJECT-TYPE
    SYNTAX      InetAddress (SIZE(4|16))
    MAX-ACCESS  not-accessible
    STATUS      current
    DESCRIPTION
        "The value of tmnxSubHostGrpTrkHostAddr indicates
         the address of the host."
    ::= { tmnxSubHostGrpTrkEntry 6 }

tmnxSubHostGrpTrkUpTime OBJECT-TYPE
    SYNTAX      TimeInterval
    MAX-ACCESS  read-only
    STATUS      current
    DESCRIPTION
        "The value of tmnxSubHostGrpTrkUpTime indicates
         the time (in hundredths of a second) that the host is associated with
         the multicast group identified by tmnxSubHostGrpTrkGrpAddr through
         the multicast source identified by tmnxSubHostGrpTrkSrcAddr."
    ::= { tmnxSubHostGrpTrkEntry 7 }

tmnxSubHostGrpTrkExpiryTime OBJECT-TYPE
    SYNTAX      Unsigned32
    UNITS       "seconds"
    MAX-ACCESS  read-only
    STATUS      current
    DESCRIPTION
        "The value of tmnxSubHostGrpTrkExpiryTime indicates
         the time in seconds that this system will continue to track this host."
    ::= { tmnxSubHostGrpTrkEntry 8 }

tmnxSubHostGrpTrkSubIdent OBJECT-TYPE
    SYNTAX      TmnxSubIdentStringOrEmpty
    MAX-ACCESS  read-only
    STATUS      current
    DESCRIPTION
        "The value of tmnxSubHostGrpTrkSubIdent indicates
         the subscriber identification of this subscriber host.

         The subscriber identification is only available in case of
         enhanced subscriber management.

         In other cases, the value of tmnxSubHostGrpTrkSubIdent is empty."
    ::= { tmnxSubHostGrpTrkEntry 9 }

-- ------------------------------------------------
-- tmnxSubGrpTrkTable
-- ------------------------------------------------

tmnxSubGrpTrkTable OBJECT-TYPE
    SYNTAX      SEQUENCE OF TmnxSubGrpTrkEntry
    MAX-ACCESS  not-accessible
    STATUS      current
    DESCRIPTION
        "The tmnxSubGrpTrkTable shows status and statistics information
         about the video viewership of subscriber hosts."
    ::= { tmnxSubMgmtObjects 48 }

tmnxSubGrpTrkEntry OBJECT-TYPE
    SYNTAX      TmnxSubGrpTrkEntry
    MAX-ACCESS  not-accessible
    STATUS      current
    DESCRIPTION
        "Each row entry represents status and statistics information
         about a particular subscriber host associated with a particular
         multicast stream.

         Rows are created or removed automatically by the system.

         Rows are only created for a subscriber that is associated with
         a host tracking policy.

         A subscriber is associated with a host tracking policy if the value of
         the object tmnxSubInfoSubProfile refers to a subscriber policy where
         the value of the object tmnxSubProfHostTrackingPolicy is not empty"
    INDEX {
            tmnxSubGrpTrkGrpAddrType, tmnxSubGrpTrkGrpAddr,
            tmnxSubGrpTrkSrcAddrType, tmnxSubGrpTrkSrcAddr,
            tmnxSubInfoSubIdent,
            svcId, sapPortId, sapEncapValue,
            tmnxSubHostInfoV2IpAddressType, tmnxSubHostInfoV2IpAddress
          }
    ::= { tmnxSubGrpTrkTable 1 }

TmnxSubGrpTrkEntry ::= SEQUENCE
   {
        tmnxSubGrpTrkGrpAddrType         InetAddressType,
        tmnxSubGrpTrkGrpAddr             InetAddress,
        tmnxSubGrpTrkSrcAddrType         InetAddressType,
        tmnxSubGrpTrkSrcAddr             InetAddress,
        tmnxSubGrpTrkBw                  Unsigned32,
        tmnxSubGrpTrkUpTime              TimeInterval,
        tmnxSubGrpTrkExpiryTime          Unsigned32
   }

tmnxSubGrpTrkGrpAddrType OBJECT-TYPE
    SYNTAX      InetAddressType
    MAX-ACCESS  not-accessible
    STATUS      current
    DESCRIPTION
        "The value of tmnxSubGrpTrkGrpAddrType indicates
         the address type of tmnxSubGrpTrkGrpAddr."
    ::= { tmnxSubGrpTrkEntry 1 }

tmnxSubGrpTrkGrpAddr OBJECT-TYPE
    SYNTAX      InetAddress (SIZE(4|16))
    MAX-ACCESS  not-accessible
    STATUS      current
    DESCRIPTION     "The value of tmnxSubGrpTrkGrpAddr indicates
                     the multicast group address."
    ::= { tmnxSubGrpTrkEntry 2 }

tmnxSubGrpTrkSrcAddrType OBJECT-TYPE
    SYNTAX      InetAddressType
    MAX-ACCESS  not-accessible
    STATUS      current
    DESCRIPTION
        "The value of tmnxSubGrpTrkSrcAddrType indicates
         the address type of tmnxSubGrpTrkSrcAddr."
    ::= { tmnxSubGrpTrkEntry 3 }

tmnxSubGrpTrkSrcAddr OBJECT-TYPE
    SYNTAX      InetAddress (SIZE(4|16))
    MAX-ACCESS  not-accessible
    STATUS      current
    DESCRIPTION
        "The value of tmnxSubGrpTrkSrcAddr indicates
         the address of the source that sends multicast traffic
         to the group identified by tmnxSubGrpTrkGrpAddr."
    ::= { tmnxSubGrpTrkEntry 4 }

tmnxSubGrpTrkBw OBJECT-TYPE
    SYNTAX      Unsigned32
    UNITS       "kbps"
    MAX-ACCESS  read-only
    STATUS      current
    DESCRIPTION
        "The value of tmnxSubGrpTrkBw indicates
         the bandwidth allocated to this subscriber host for this multicast
         stream."
    ::= { tmnxSubGrpTrkEntry 5 }

tmnxSubGrpTrkUpTime OBJECT-TYPE
    SYNTAX      TimeInterval
    MAX-ACCESS  read-only
    STATUS      current
    DESCRIPTION
        "The value of tmnxSubGrpTrkUpTime indicates
         the time (in hundredths of a second) that the subscriber host
         identified by tmnxSubInfoSubIdent is associated with
         the multicast group identified by tmnxSubGrpTrkGrpAddr through
         the multicast source identified by tmnxSubGrpTrkSrcAddr."
    ::= { tmnxSubGrpTrkEntry 6 }

tmnxSubGrpTrkExpiryTime OBJECT-TYPE
    SYNTAX      Unsigned32
    UNITS       "seconds"
    MAX-ACCESS  read-only
    STATUS      current
    DESCRIPTION
        "The value of tmnxSubGrpTrkExpiryTime indicates
         the time in seconds that this system will continue to track this host."
    ::= { tmnxSubGrpTrkEntry 7 }

-- ------------------------------------------------
-- tmnxSubApCustRecordTable
-- ------------------------------------------------
-- This augments  the tmnxSubAcctPlcyTable so that a custom accounting record
-- can be defined.
--
tmnxSubApCustRecordLastChnge  OBJECT-TYPE
    SYNTAX          TimeStamp
    MAX-ACCESS      read-only
    STATUS          current
    DESCRIPTION
        "The value of tmnxSubApCustRecordLastChnge indicates the
         sysUpTime at the time of the last modification
         of tmnxSubApCustRecordTable.

         If no changes were made to the entry since the last
         re-initialization of the local network management subsystem,
         then this object contains a zero value."
    ::= { tmnxSubMgmtObjects 49 }

tmnxSubApCustRecordTable OBJECT-TYPE
    SYNTAX      SEQUENCE OF TmnxSubApCustRecordEntry
    MAX-ACCESS  not-accessible
    STATUS      current
    DESCRIPTION
        "The Nokia SROS series tmnxSubApCustRecordTable augments
         tmnxSubAcctPlcyTable.

         The table allows to configure the layout and setting for
         a custom accounting record associated with this policy."
   ::= { tmnxSubMgmtObjects 50 }

tmnxSubApCustRecordEntry OBJECT-TYPE
    SYNTAX      TmnxSubApCustRecordEntry
    MAX-ACCESS  not-accessible
    STATUS      current
    DESCRIPTION
        "Defines an entry in the tmnxSubApCustRecordTable. Entries in this
         table are created and destroyed via SNMP Set requests to the
         tmnxSubAcctPlcyRowStatus object of the tmnxSubAcctPlcyTable."
    AUGMENTS { tmnxSubAcctPlcyEntry }
    ::= { tmnxSubApCustRecordTable 1 }

TmnxSubApCustRecordEntry ::=
    SEQUENCE {
        tmnxSubApCrLastChanged           TimeStamp,
        tmnxSubApCrSignChangeDelta       Unsigned32,
        tmnxSubApCrSignChangeQueue       TQueueIdOrAll,
        tmnxSubApCrSignChangeOCntr       THsmdaCounterIdOrZeroOrAll,
        tmnxSubApCrSignChangeQICounters  TmnxAccPlcyQICounters,
        tmnxSubApCrSignChangeQECounters  TmnxAccPlcyQECounters,
        tmnxSubApCrSignChangeOICounters  TmnxAccPlcyOICounters,
        tmnxSubApCrSignChangeOECounters  TmnxAccPlcyOECounters
    }

tmnxSubApCrLastChanged OBJECT-TYPE
    SYNTAX      TimeStamp
    MAX-ACCESS  read-only
    STATUS      current
    DESCRIPTION
        "The value of tmnxSubApCrLastChanged indicates the sysUpTime when
         an object in this table was last modified. A Value 0 means that
         no change was made to this row since the box was last initialized."
    ::= { tmnxSubApCustRecordEntry 1 }

tmnxSubApCrSignChangeDelta OBJECT-TYPE
    SYNTAX      Unsigned32
    MAX-ACCESS  read-write
    STATUS      current
    DESCRIPTION
        "The value of tmnxSubApCrSignChangeDelta specifies the delta
         change  (significant change) that is required for the custom record
         to be written to the xml file."
    DEFVAL { 0 }
    ::= { tmnxSubApCustRecordEntry 2 }

tmnxSubApCrSignChangeQueue OBJECT-TYPE
    SYNTAX      TQueueIdOrAll
    MAX-ACCESS  read-write
    STATUS      current
    DESCRIPTION
        "The value of tmnxSubApCrSignChangeQueue specifies the reference
        queue to which the significant change defined in
        tmnxSubApCrSignChangeDelta applies."
    DEFVAL { 0 }
    ::= { tmnxSubApCustRecordEntry 3 }

tmnxSubApCrSignChangeOCntr OBJECT-TYPE
    SYNTAX      THsmdaCounterIdOrZeroOrAll
    MAX-ACCESS  read-write
    STATUS      current
    DESCRIPTION
        "The value of tmnxSubApCrSignChangeOCntr specifies the counter-id
         that will be taken as reference to which the significant
         change defined in tmnxSubApCrSignChangeDelta applies."
    DEFVAL { 0 }
    ::= { tmnxSubApCustRecordEntry 4 }

tmnxSubApCrSignChangeQICounters OBJECT-TYPE
    SYNTAX      TmnxAccPlcyQICounters
    MAX-ACCESS  read-write
    STATUS      current
    DESCRIPTION
        "The value of tmnxSubApCrSignChangeQICounters specifies the ingress
         counter Ids in the queue defined by tmnxSubApCrSignChangeQueue to be
         taken as reference to which the significant change defined in
         tmnxSubApCrSignChangeDelta applies.

         A non-zero value of this object is only allowed if the object
         tmnxSubApCrSignChangeQueue has a non-zero value."
    DEFVAL { { } }
    ::= { tmnxSubApCustRecordEntry 5 }

tmnxSubApCrSignChangeQECounters OBJECT-TYPE
    SYNTAX      TmnxAccPlcyQECounters
    MAX-ACCESS  read-write
    STATUS      current
    DESCRIPTION
        "The value of tmnxSubApCrSignChangeQECounters specifies the egress
         counter Ids in the queue defined by tmnxSubApCrSignChangeQueue to be
         taken as reference to which the significant change defined in
         tmnxSubApCrSignChangeDelta applies.

         A non-zero value of this object is only allowed if the object
         tmnxSubApCrSignChangeQueue has a non-zero value."
    DEFVAL { { } }
    ::= { tmnxSubApCustRecordEntry 6 }

tmnxSubApCrSignChangeOICounters OBJECT-TYPE
    SYNTAX      TmnxAccPlcyOICounters
    MAX-ACCESS  read-write
    STATUS      current
    DESCRIPTION
        "The value of tmnxSubApCrSignChangeOICounters specifies the ingress
         counter Ids in the counter-group defined by tmnxSubApCrSignChangeOCntr
         to be taken as reference to which the significant change defined in
         tmnxSubApCrSignChangeDelta applies.

         A non-zero value of this object is only allowed if the object
         tmnxSubApCrSignChangeOCntr has a non-zero value."
    DEFVAL { { } }
    ::= { tmnxSubApCustRecordEntry 7 }

tmnxSubApCrSignChangeOECounters OBJECT-TYPE
    SYNTAX      TmnxAccPlcyOECounters
    MAX-ACCESS  read-write
    STATUS      current
    DESCRIPTION
        "The value of tmnxSubApCrSignChangeOECounters specifies the egress
         counter Ids in the counter-group defined by tmnxSubApCrSignChangeOCntr
         to be taken as reference to which the significant change defined in
         tmnxSubApCrSignChangeDelta applies.

         A non-zero value of this object is only allowed if the object
         tmnxSubApCrSignChangeOCntr has a non-zero value."
    DEFVAL { { } }
    ::= { tmnxSubApCustRecordEntry 8 }

-- ------------------------------------------------
-- tmnxSubApCustRecordQueueTable
-- ------------------------------------------------
-- Log Accounting Policy Table extensions to create a custom record
--
tmnxSubApCustRecQueueLastChnge  OBJECT-TYPE
    SYNTAX          TimeStamp
    MAX-ACCESS      read-only
    STATUS          current
    DESCRIPTION
        "The value of tmnxSubApCustRecQueueLastChnge indicates the
         sysUpTime at the time of the last modification
         of tmnxSubApCustRecordQueueTable.

         If no changes were made to the entry since the last
         re-initialization of the local network management subsystem,
         then this object contains a zero value."
    ::= { tmnxSubMgmtObjects 51 }

tmnxSubApCustRecordQueueTable OBJECT-TYPE
    SYNTAX      SEQUENCE OF TmnxSubApCustRecordQueueEntry
    MAX-ACCESS  not-accessible
    STATUS      current
    DESCRIPTION
        "The Nokia SROS series tmnxSubApCustRecordQueueTable
         allows to create custom record queue information for a given
         RADIUS accounting policy.
         Rows can only be created for existing accounting policies
         (as defined in tmnxSubApTable)."
    ::= { tmnxSubMgmtObjects 52 }

tmnxSubApCustRecordQueueEntry OBJECT-TYPE
    SYNTAX      TmnxSubApCustRecordQueueEntry
    MAX-ACCESS  not-accessible
    STATUS      current
    DESCRIPTION
        "Defines an entry in the tmnxSubApCustRecordQueueTable. Entries in this
         table are created and destroyed via SNMP Set requests."
    INDEX { tmnxSubAcctPlcyName,
            tmnxSubApCrQueueId }
    ::= { tmnxSubApCustRecordQueueTable 1 }

TmnxSubApCustRecordQueueEntry ::=
    SEQUENCE {
        tmnxSubApCrQueueId               TQueueId,
        tmnxSubApCrQueueRowStatus        RowStatus,
        tmnxSubApCrQueueLastChanged      TimeStamp,
        tmnxSubApCrQueueICounters        TmnxAccPlcyQICounters,
        tmnxSubApCrQueueECounters        TmnxAccPlcyQECounters
    }

tmnxSubApCrQueueId OBJECT-TYPE
    SYNTAX      TQueueId (1..32)
    MAX-ACCESS  not-accessible
    STATUS      current
    DESCRIPTION
        "The value of tmnxSubApCrQueueId specifies the queue-id for which
         counters will be collected in this custom record. The counters that
         will be collected are defined in tmnxSubApCrQueueICounters and
         tmnxSubApCrQueueECounters."
    ::= { tmnxSubApCustRecordQueueEntry 1 }

tmnxSubApCrQueueRowStatus OBJECT-TYPE
    SYNTAX      RowStatus
    MAX-ACCESS  read-create
    STATUS      current
    DESCRIPTION
        "Row Status of the entry. This allows creation/deletion of rows in this
         table."
    ::= { tmnxSubApCustRecordQueueEntry 2 }

tmnxSubApCrQueueLastChanged OBJECT-TYPE
    SYNTAX      TimeStamp
    MAX-ACCESS  read-only
    STATUS      current
    DESCRIPTION
        "The value of tmnxSubApCrQueueLastChanged indicates the sysUpTime when
         an object in this table was last modified. A Value 0 means that
         no change was made to this row since it was created."
    ::= { tmnxSubApCustRecordQueueEntry 3 }

tmnxSubApCrQueueICounters OBJECT-TYPE
    SYNTAX      TmnxAccPlcyQICounters
    MAX-ACCESS  read-create
    STATUS      current
    DESCRIPTION
        "The value of tmnxSubApCrQueueICounters indicates the list of
         ingress counters that need to be collected in this custom record.

         At least one of the objects tmnxSubApCrQueueICounters or
         tmnxSubApCrQueueECounters must have a non-zero value."
    DEFVAL { { } }
    ::= { tmnxSubApCustRecordQueueEntry 4 }

tmnxSubApCrQueueECounters OBJECT-TYPE
    SYNTAX      TmnxAccPlcyQECounters
    MAX-ACCESS  read-create
    STATUS      current
    DESCRIPTION
        "The value of tmnxSubApCrQueueECounters indicates the list of
         egress counters that need to be collected in this custom record.

         At least one of the objects tmnxSubApCrQueueICounters or
         tmnxSubApCrQueueECounters must have a non-zero value."
    DEFVAL { { } }
    ::= { tmnxSubApCustRecordQueueEntry 5 }

--
-- ------------------------------------------------
-- tmnxSubApCrOverrideCntrTable
-- ------------------------------------------------
-- Log Accounting Policy Table extensions to create a custom record
--
tmnxSubApCustRecOvrCtrLastChnge  OBJECT-TYPE
    SYNTAX          TimeStamp
    MAX-ACCESS      read-only
    STATUS          current
    DESCRIPTION
        "The value of tmnxSubApCustRecOvrCtrLastChnge indicates the
         sysUpTime at the time of the last modification
         of tmnxSubApCrOverrideCntrTable.

         If no changes were made to the entry since the last
         re-initialization of the local network management subsystem,
         then this object contains a zero value."
    ::= { tmnxSubMgmtObjects 53 }

tmnxSubApCrOverrideCntrTable OBJECT-TYPE
    SYNTAX      SEQUENCE OF TmnxSubApCrOverrideCntrEntry
    MAX-ACCESS  not-accessible
    STATUS      current
    DESCRIPTION
        "The Nokia SROS series tmnxSubApCrOverrideCntrTable
         allows to create custom record counter override information for a given
         accounting policy.
         Rows can only be created for existing accounting policies
         (as defined in tmnxSubApTable)."
    ::= { tmnxSubMgmtObjects 54 }

tmnxSubApCrOverrideCntrEntry OBJECT-TYPE
    SYNTAX      TmnxSubApCrOverrideCntrEntry
    MAX-ACCESS  not-accessible
    STATUS      current
    DESCRIPTION
        "Defines an entry in the tmnxSubApCrOverrideCntrTable. Entries in this
         table are created and destroyed via SNMP Set requests."
    INDEX { tmnxSubAcctPlcyName,
            tmnxSubApCrOverrideCntrId }
    ::= { tmnxSubApCrOverrideCntrTable 1 }

TmnxSubApCrOverrideCntrEntry ::=
    SEQUENCE {
        tmnxSubApCrOverrideCntrId        THsmdaCounterIdOrZero,
        tmnxSubApCrOverrideCntrRowStatus RowStatus,
        tmnxSubApCrOverrideCntrLastChngd TimeStamp,
        tmnxSubApCrOverrideCntrICounters TmnxAccPlcyOICounters,
        tmnxSubApCrOverrideCntrECounters TmnxAccPlcyOECounters
    }

tmnxSubApCrOverrideCntrId OBJECT-TYPE
    SYNTAX      THsmdaCounterIdOrZero (1..8)
    MAX-ACCESS  not-accessible
    STATUS      current
    DESCRIPTION
        "The value of tmnxSubApCrOverrideCntrId specifies the counter group
         for which counters will be collected in this custom record.
         The counters that will be collected are defined in
         tmnxSubApCrOverrideCntrICounters and tmnxSubApCrOverrideCntrECounters."
    ::= { tmnxSubApCrOverrideCntrEntry 1 }

tmnxSubApCrOverrideCntrRowStatus OBJECT-TYPE
    SYNTAX      RowStatus
    MAX-ACCESS  read-create
    STATUS      current
    DESCRIPTION
        "Row Status of the entry. This allows creation/deletion of rows in this
         table."
    ::= { tmnxSubApCrOverrideCntrEntry 2 }

tmnxSubApCrOverrideCntrLastChngd OBJECT-TYPE
    SYNTAX      TimeStamp
    MAX-ACCESS  read-only
    STATUS      current
    DESCRIPTION
        "The value of tmnxSubApCrOverrideCntrLastChngd indicates the sysUpTime
         when an object in this table was last modified. A Value 0 means that
         no change was made to this row since it was created."
    ::= { tmnxSubApCrOverrideCntrEntry 3 }

tmnxSubApCrOverrideCntrICounters OBJECT-TYPE
    SYNTAX      TmnxAccPlcyOICounters
    MAX-ACCESS  read-create
    STATUS      current
    DESCRIPTION
        "The value of tmnxSubApCrOverrideCntrICounters indicates the list of
         ingress counters that need to be collected in this custom record.

         At least one of the objects tmnxSubApCrOverrideCntrICounters or
         tmnxSubApCrOverrideCntrECounters must have a non-zero value."
    DEFVAL { { } }
    ::= { tmnxSubApCrOverrideCntrEntry 4 }

tmnxSubApCrOverrideCntrECounters OBJECT-TYPE
    SYNTAX      TmnxAccPlcyOECounters
    MAX-ACCESS  read-create
    STATUS      current
    DESCRIPTION
        "The value of tmnxSubApCrOverrideCntrECounters indicates the list of
         egress counters that need to be collected in this custom record.

         At least one of the objects tmnxSubApCrOverrideCntrICounters or
         tmnxSubApCrOverrideCntrECounters must have a non-zero value."
    DEFVAL { { } }
    ::= { tmnxSubApCrOverrideCntrEntry 5 }

-- ------------------------------------------------
-- tmnxSubApCreditControlPlcyTable
-- ------------------------------------------------
tmnxSubApCCPlcyTableLastChnge  OBJECT-TYPE
    SYNTAX          TimeStamp
    MAX-ACCESS      read-only
    STATUS          current
    DESCRIPTION
        "The value of tmnxSubApCCPlcyTableLastChnge indicates the
         sysUpTime at the time of the last modification
         of tmnxSubApCreditControlPlcyTable.

         If no changes were made to the entry since the last
         re-initialization of the local network management subsystem,
         then this object contains a zero value."
    ::= { tmnxSubMgmtObjects 55 }

tmnxSubApCreditControlPlcyTable OBJECT-TYPE
    SYNTAX      SEQUENCE OF TmnxSubApCreditControlPlcyEntry
    MAX-ACCESS  not-accessible
    STATUS      current
    DESCRIPTION
        "The Nokia SROS series tmnxSubApCreditControlPlcyTable
         allows to configure a Credit Control (CC) policy."
    ::= { tmnxSubMgmtObjects 56 }

tmnxSubApCreditControlPlcyEntry OBJECT-TYPE
    SYNTAX      TmnxSubApCreditControlPlcyEntry
    MAX-ACCESS  not-accessible
    STATUS      current
    DESCRIPTION
        "Defines an entry in the tmnxSubApCreditControlPlcyTable.
         Entries in this table are created and destroyed via SNMP
         Set requests."
    INDEX { tmnxSLAProfCreditControlPolicy }
    ::= { tmnxSubApCreditControlPlcyTable 1 }

TmnxSubApCreditControlPlcyEntry ::=
    SEQUENCE {
        tmnxSLAProfCreditControlPolicy   TNamedItem,
        tmnxSubCcPlcyRowStatus           RowStatus,
        tmnxSubCcPlcyLastChngd           TimeStamp,
        tmnxSubCcPlcyDescription         TItemDescription,
        tmnxSubCcPlcyDiameterPlcy        TNamedItemOrEmpty,
        tmnxSubCcPlcyDefaultCategoryMap  TNamedItemOrEmpty,
        tmnxSubCcPlcyOutOfCreditAction   TmnxSubCcOutOfCreditAction,
        tmnxSubCcPlcyErrorHandlingAction TmnxSubCcErrorAction
    }

tmnxSLAProfCreditControlPolicy OBJECT-TYPE
    SYNTAX      TNamedItem
    MAX-ACCESS  not-accessible
    STATUS      current
    DESCRIPTION
        "The value of tmnxSLAProfCreditControlPolicy specifies the
         Credit Control Policy name"
    ::= { tmnxSubApCreditControlPlcyEntry 1 }

tmnxSubCcPlcyRowStatus OBJECT-TYPE
    SYNTAX      RowStatus
    MAX-ACCESS  read-create
    STATUS      current
    DESCRIPTION
        "Row Status of the entry. This allows creation/deletion of rows in this
         table."
    ::= { tmnxSubApCreditControlPlcyEntry 2 }

tmnxSubCcPlcyLastChngd OBJECT-TYPE
    SYNTAX      TimeStamp
    MAX-ACCESS  read-only
    STATUS      current
    DESCRIPTION
        "The value of tmnxSubCcPlcyLastChngd indicates the sysUpTime when
         an object in this table was last modified. A Value 0 means that
         no change was made to this row since it was created."
    ::= { tmnxSubApCreditControlPlcyEntry 3 }

tmnxSubCcPlcyDescription OBJECT-TYPE
    SYNTAX      TItemDescription
    MAX-ACCESS  read-create
    STATUS      current
    DESCRIPTION
        "The value of tmnxSubCcPlcyDescription specifies a user provided
         description of this policy."
    DEFVAL { "" }
    ::= { tmnxSubApCreditControlPlcyEntry 4 }

tmnxSubCcPlcyDiameterPlcy OBJECT-TYPE
    SYNTAX      TNamedItemOrEmpty
    MAX-ACCESS  read-create
    STATUS      current
    DESCRIPTION
        "The value of the object tmnxSubCcPlcyDiameterPlcy specifies
         the Diameter policy to be used to access the Credit Control
         server.
         If set to the empty string, the RADIUS protocol is used by
         default."
    DEFVAL { ''H }
    ::= { tmnxSubApCreditControlPlcyEntry 5 }

tmnxSubCcPlcyDefaultCategoryMap OBJECT-TYPE
    SYNTAX      TNamedItemOrEmpty
    MAX-ACCESS  read-create
    STATUS      current
    DESCRIPTION
        "The value of the object tmnxSubCcPlcyDefaultCategoryMap specifies
         the category map to be used by this Credit Control policy. The
         category map must be defined in tmnxSubApCategoryMapTable."
    DEFVAL { ''H }
    ::= { tmnxSubApCreditControlPlcyEntry 6 }

tmnxSubCcPlcyOutOfCreditAction OBJECT-TYPE
    SYNTAX      TmnxSubCcOutOfCreditAction
    MAX-ACCESS  read-create
    STATUS      current
    DESCRIPTION
        "The value of the object tmnxSubCcPlcyOutOfCreditAction specifies
         the action to be taken when the available credit is used up.
         The value none(0) is not allowed for this object."
    DEFVAL { continue }
    ::= { tmnxSubApCreditControlPlcyEntry 7 }

tmnxSubCcPlcyErrorHandlingAction OBJECT-TYPE
    SYNTAX      TmnxSubCcErrorAction
    MAX-ACCESS  read-create
    STATUS      current
    DESCRIPTION
        "The value of the object tmnxSubCcPlcyErrorHandlingAction specifies
         the action to be taken when an error occurs in the CC determination."
    DEFVAL { continue }
    ::= { tmnxSubApCreditControlPlcyEntry 8 }

-- ------------------------------------------------
-- tmnxSubApCategoryMapTable
-- ------------------------------------------------
tmnxSubApCategoryMapTblLstChnge  OBJECT-TYPE
    SYNTAX          TimeStamp
    MAX-ACCESS      read-only
    STATUS          current
    DESCRIPTION
        "The value of tmnxSubApCategoryMapTblLstChnge indicates the
         sysUpTime at the time of the last modification
         of tmnxSubApCategoryMapTable.

         If no changes were made to the entry since the last
         re-initialization of the local network management subsystem,
         then this object contains a zero value."
    ::= { tmnxSubMgmtObjects 57 }

tmnxSubApCategoryMapTable OBJECT-TYPE
    SYNTAX      SEQUENCE OF TmnxSubApCategoryMapEntry
    MAX-ACCESS  not-accessible
    STATUS      current
    DESCRIPTION
        "The Nokia SROS series tmnxSubApCategoryMapTable
         allows to configure a Credit Conrol (CC) Category Map."
    ::= { tmnxSubMgmtObjects 58 }

tmnxSubApCategoryMapEntry OBJECT-TYPE
    SYNTAX      TmnxSubApCategoryMapEntry
    MAX-ACCESS  not-accessible
    STATUS      current
    DESCRIPTION
        "Defines an entry in the tmnxSubApCategoryMapTable.
         Entries in this table are created and destroyed via SNMP
         Set requests."
    INDEX { tmnxSubApCMapName }
    ::= { tmnxSubApCategoryMapTable 1 }

TmnxSubApCategoryMapEntry ::=
    SEQUENCE {
        tmnxSubApCMapName                TNamedItem,
        tmnxSubApCMapRowStatus           RowStatus,
        tmnxSubApCMapLastChngd           TimeStamp,
        tmnxSubApCMapDescription         TItemDescription,
        tmnxSubApCMapCreditType          TmnxSubCcAccountedResource,
        tmnxSubApCMapCreditExhstThrshld  Unsigned32,
        tmnxSubApCMapActivityThreshold   Unsigned32
    }

tmnxSubApCMapName OBJECT-TYPE
    SYNTAX      TNamedItem
    MAX-ACCESS  not-accessible
    STATUS      current
    DESCRIPTION
        "The value of tmnxSubApCMapName specifies the Category Map name"
    ::= { tmnxSubApCategoryMapEntry 1 }

tmnxSubApCMapRowStatus OBJECT-TYPE
    SYNTAX      RowStatus
    MAX-ACCESS  read-create
    STATUS      current
    DESCRIPTION
        "Row Status of the entry. This allows creation/deletion of rows in this
         table."
    ::= { tmnxSubApCategoryMapEntry 2 }

tmnxSubApCMapLastChngd OBJECT-TYPE
    SYNTAX      TimeStamp
    MAX-ACCESS  read-only
    STATUS      current
    DESCRIPTION
        "The value of tmnxSubApCMapLastChngd indicates the sysUpTime when
         an object in this table was last modified. A Value 0 means that
         no change was made to this row since it was created."
    ::= { tmnxSubApCategoryMapEntry 3 }

tmnxSubApCMapDescription OBJECT-TYPE
    SYNTAX      TItemDescription
    MAX-ACCESS  read-create
    STATUS      current
    DESCRIPTION
        "The value of tmnxSubApCMapDescription specifies a user provided
         description of this category map."
    DEFVAL { "" }
    ::= { tmnxSubApCategoryMapEntry 4 }

tmnxSubApCMapCreditType OBJECT-TYPE
    SYNTAX      TmnxSubCcAccountedResource
    MAX-ACCESS  read-create
    STATUS      current
    DESCRIPTION
        "The value of tmnxSubApCMapCreditType specifies whether volume or
        time based accounting is performed."
    DEFVAL { volume }
    ::= { tmnxSubApCategoryMapEntry 5 }

tmnxSubApCMapCreditExhstThrshld OBJECT-TYPE
    SYNTAX      Unsigned32(50..100)
    MAX-ACCESS  read-create
    STATUS      current
    DESCRIPTION
        "The value of tmnxSubApCMapCreditExhstThrshld specifies the credit
         exhaust threshold taken into account to take action."
    DEFVAL { 100 }
    ::= { tmnxSubApCategoryMapEntry 6 }

tmnxSubApCMapActivityThreshold OBJECT-TYPE
    SYNTAX      Unsigned32(0..100000000)
    MAX-ACCESS  read-create
    STATUS      current
    DESCRIPTION
        "The value of tmnxSubApCMapActivityThreshold specifies the threshold 
         (in Kbps) that is applied to determine whether or not activity is
         going on."
    DEFVAL { 0 }
    ::= { tmnxSubApCategoryMapEntry 7 }

-- ------------------------------------------------
-- tmnxSubApCategoryTable
-- ------------------------------------------------
tmnxSubApCategoryTblLstChnge  OBJECT-TYPE
    SYNTAX          TimeStamp
    MAX-ACCESS      read-only
    STATUS          current
    DESCRIPTION
        "The value of tmnxSubApCategoryTblLstChnge indicates the
         sysUpTime at the time of the last modification
         of tmnxSubApCategoryTable.

         If no changes were made to the entry since the last
         re-initialization of the local network management subsystem,
         then this object contains a zero value."
    ::= { tmnxSubMgmtObjects 59 }

tmnxSubApCategoryTable OBJECT-TYPE
    SYNTAX      SEQUENCE OF TmnxSubApCategoryEntry
    MAX-ACCESS  not-accessible
    STATUS      current
    DESCRIPTION
        "The Nokia SROS series tmnxSubApCategoryTable
         allows to configure a Credit Conrol (CC) Category."
    ::= { tmnxSubMgmtObjects 60 }

tmnxSubApCategoryEntry OBJECT-TYPE
    SYNTAX      TmnxSubApCategoryEntry
    MAX-ACCESS  not-accessible
    STATUS      current
    DESCRIPTION
        "Defines an entry in the tmnxSubApCategoryTable.
         Entries in this table are created and destroyed via SNMP
         Set requests."
    INDEX { tmnxSubApCMapName,
            tmnxSubApCategoryName }
    ::= { tmnxSubApCategoryTable 1 }

TmnxSubApCategoryEntry ::=
    SEQUENCE {
        tmnxSubApCategoryName            TNamedItem,
        tmnxSubApCategoryRowStatus       RowStatus,
        tmnxSubApCategoryLastChngd       TimeStamp,
        tmnxSubApCategoryDescription     TItemDescription,
        tmnxSubApCategoryIngressQueues   TmnxSubQueuesIngress,
        tmnxSubApCategoryEgressQueues    TmnxSubQueuesEgress,
        tmnxSubApCategoryUseRatingGroup  TruthValue,
        tmnxSubApCategoryRatingGroup     Unsigned32,
        tmnxSubApCategoryCTypeOverride   TmnxSubCcAccountedResourceOrNone,
        tmnxSubApCategoryDfltCrdtVolume  Unsigned32,
        tmnxSubApCategoryDfltCrdtVolUnit TmnxSubApCategoryDfltCrdtVolUnit,
        tmnxSubApCategoryDfltCrdtTime    Unsigned32,
        tmnxSubApCategoryOutOfCrdtAction TmnxSubCcOutOfCreditAction,
        tmnxSubApCategoryPir             THsmdaPIRKRateOverride,
        tmnxSubApCategoryIngressPolicers TmnxSubPolicersIngress,
        tmnxSubApCategoryEgressPolicers  TmnxSubPolicersEgress
    }

tmnxSubApCategoryName OBJECT-TYPE
    SYNTAX      TNamedItem
    MAX-ACCESS  not-accessible
    STATUS      current
    DESCRIPTION
        "The value of tmnxSubApCategoryName specifies the Category name"
    ::= { tmnxSubApCategoryEntry 1 }

tmnxSubApCategoryRowStatus OBJECT-TYPE
    SYNTAX      RowStatus
    MAX-ACCESS  read-create
    STATUS      current
    DESCRIPTION
        "Row Status of the entry. This allows creation/deletion of rows in this
         table."
    ::= { tmnxSubApCategoryEntry 2 }

tmnxSubApCategoryLastChngd OBJECT-TYPE
    SYNTAX      TimeStamp
    MAX-ACCESS  read-only
    STATUS      current
    DESCRIPTION
        "The value of tmnxSubApCategoryLastChngd indicates the sysUpTime when
         an object in this table was last modified. A Value 0 means that
         no change was made to this row since it was created."
    ::= { tmnxSubApCategoryEntry 3 }

tmnxSubApCategoryDescription OBJECT-TYPE
    SYNTAX      TItemDescription
    MAX-ACCESS  read-create
    STATUS      current
    DESCRIPTION
        "The value of tmnxSubApCategoryDescription specifies a user provided
         description of this category."
    DEFVAL { "" }
    ::= { tmnxSubApCategoryEntry 4 }

tmnxSubApCategoryIngressQueues OBJECT-TYPE
    SYNTAX      TmnxSubQueuesIngress
    MAX-ACCESS  read-create
    STATUS      current
    DESCRIPTION
        "The value of tmnxSubApCategoryIngressQueues specifies, 
         which ingress queues are defined in this category."
    DEFVAL { { } }
    ::= { tmnxSubApCategoryEntry 5 }

tmnxSubApCategoryEgressQueues OBJECT-TYPE
    SYNTAX      TmnxSubQueuesEgress
    MAX-ACCESS  read-create
    STATUS      current
    DESCRIPTION
        "The value of tmnxSubApCategoryEgressQueues specifies, 
         which egress queues are defined in this category."
    DEFVAL { { } }
    ::= { tmnxSubApCategoryEntry 6 }

tmnxSubApCategoryUseRatingGroup OBJECT-TYPE
    SYNTAX      TruthValue
    MAX-ACCESS  read-create
    STATUS      current
    DESCRIPTION
        "The value of tmnxSubApCategoryUseRatingGroup specifies whether or
         not the rating group defined in tmnxSubApCategoryRatingGroup is
         applicable for this category."
    DEFVAL { false }
    ::= { tmnxSubApCategoryEntry 7 }

tmnxSubApCategoryRatingGroup OBJECT-TYPE
    SYNTAX      Unsigned32
    MAX-ACCESS  read-create
    STATUS      current
    DESCRIPTION
        "The value of tmnxSubApCategoryRatingGroup specifies the rating
         group applicable for this category.

         The value of this object is only considered if the object
         tmnxSubApCategoryUseRatingGroup is set to 'true'."
    DEFVAL { 0 }
    ::= { tmnxSubApCategoryEntry 8 }

tmnxSubApCategoryCTypeOverride OBJECT-TYPE
    SYNTAX      TmnxSubCcAccountedResourceOrNone
    MAX-ACCESS  read-create
    STATUS      current
    DESCRIPTION
        "The value of tmnxSubApCategoryCTypeOverride, if different from
         'none' overrides the credit-type as defined in
         tmnxSubApCMapCreditType."
    DEFVAL { none }
    ::= { tmnxSubApCategoryEntry 9 }

tmnxSubApCategoryDfltCrdtVolume OBJECT-TYPE
    SYNTAX      Unsigned32
    MAX-ACCESS  read-create
    STATUS      current
    DESCRIPTION
        "The value of tmnxSubApCategoryDfltCrdtVolume, if different from
         0, specifies the default value for the Volume credit.
         Low values may be rejected or increased by the system depending
         on the systems resources."
    DEFVAL { 0 }
    ::= { tmnxSubApCategoryEntry 10 }

tmnxSubApCategoryDfltCrdtVolUnit OBJECT-TYPE
    SYNTAX      TmnxSubApCategoryDfltCrdtVolUnit
    MAX-ACCESS  read-create
    STATUS      current
    DESCRIPTION
        "The value of tmnxSubApCategoryDfltCrdtVolUnit specifies the unit in 
         which the default value for the Volume credit is expressed."
    DEFVAL { bytes }
    ::= { tmnxSubApCategoryEntry 11 }

tmnxSubApCategoryDfltCrdtTime OBJECT-TYPE
    SYNTAX      Unsigned32
    MAX-ACCESS  read-create
    STATUS      current
    DESCRIPTION
        "The value of tmnxSubApCategoryDfltCrdtTime, if different from
         0, specifies the default value for the Time credit.
         Low values may be rejected or increased by the system depending
         on the systems resources."
    DEFVAL { 0 }
    ::= { tmnxSubApCategoryEntry 12 }

tmnxSubApCategoryOutOfCrdtAction OBJECT-TYPE
    SYNTAX      TmnxSubCcOutOfCreditAction
    MAX-ACCESS  read-create
    STATUS      current
    DESCRIPTION
        "The value of tmnxSubApCategoryOutOfCrdtAction, if different from
         none, specifies the action to be taken if the credit es exhausted.
         If set to none, the action as specified in
         tmnxSubCcPlcyOutOfCreditAction aplies.
         The value disconnectHost(2) is not allowed for this object."
    DEFVAL { none }
    ::= { tmnxSubApCategoryEntry 13 }

tmnxSubApCategoryPir OBJECT-TYPE
    SYNTAX      THsmdaPIRKRateOverride
    MAX-ACCESS  read-create
    STATUS      current
    DESCRIPTION
        "The value of tmnxSubApCategoryPir, specifies the PIR rate
         overide value for this category."
    DEFVAL { -2 }
    ::= { tmnxSubApCategoryEntry 14 }

tmnxSubApCategoryIngressPolicers OBJECT-TYPE
    SYNTAX      TmnxSubPolicersIngress
    MAX-ACCESS  read-create
    STATUS      current
    DESCRIPTION
        "The value of tmnxSubApCategoryIngressPolicers specifies, 
         which ingress policers are defined in this category."
    DEFVAL { { } }
    ::= { tmnxSubApCategoryEntry 15 }

tmnxSubApCategoryEgressPolicers OBJECT-TYPE
    SYNTAX      TmnxSubPolicersEgress
    MAX-ACCESS  read-create
    STATUS      current
    DESCRIPTION
        "The value of tmnxSubApCategoryEgressPolicers specifies, 
         which egress policers are defined in this category."
    DEFVAL { { } }
    ::= { tmnxSubApCategoryEntry 66 }


-- ------------------------------------------------
-- tmnxSubTrkPlcySubscriberTable
-- ------------------------------------------------

tmnxSubTrkPlcySubscriberTable OBJECT-TYPE
    SYNTAX      SEQUENCE OF TmnxSubTrkPlcySubscriberEntry
    MAX-ACCESS  not-accessible
    STATUS      current
    DESCRIPTION
        "The tmnxSubTrkPlcySubscriberTable shows the subscribers associated
         with their IGMP Host Tracking policy."
    ::= { tmnxSubMgmtObjects 61 }

tmnxSubTrkPlcySubscriberEntry OBJECT-TYPE
    SYNTAX      TmnxSubTrkPlcySubscriberEntry
    MAX-ACCESS  not-accessible
    STATUS      current
    DESCRIPTION
        "Each row entry represents a particular subscriber 
         associated with a particular IGMP Host Tracking policy."
    INDEX {
            tmnxSubTrkPlcyName, 
            IMPLIED tmnxSubTrkPlcySubscriberId
          }
    ::= { tmnxSubTrkPlcySubscriberTable 1 }

TmnxSubTrkPlcySubscriberEntry ::= SEQUENCE
   {
        tmnxSubTrkPlcySubscriberId       DisplayString
   }

tmnxSubTrkPlcySubscriberId OBJECT-TYPE
    SYNTAX      DisplayString (SIZE (1..32))
    MAX-ACCESS  read-only
    STATUS      current
    DESCRIPTION
        "The value of tmnxSubTrkPlcySubscriberId indicates the subscriber
         identification."
    ::= { tmnxSubTrkPlcySubscriberEntry 1 }


-- ----------------------------------------
-- tmnxSPICatTable
-- ----------------------------------------

tmnxSPICatTable OBJECT-TYPE
    SYNTAX      SEQUENCE OF TmnxSPICatEntry
    MAX-ACCESS  not-accessible
    STATUS      current
    DESCRIPTION
        "The tmnxSPICatTable contains volume & time based accounting information for
         active subscribers."
    ::= { tmnxSubMgmtObjects 62 }

tmnxSPICatEntry OBJECT-TYPE
    SYNTAX      TmnxSPICatEntry
    MAX-ACCESS  not-accessible
    STATUS      current
    DESCRIPTION
        "Each row entry contains volume & time based accounting information for
         a subscriber, SLA profile and credit category."
    INDEX { tmnxSubInfoSubIdent,
            sapPortId,
            sapEncapValue,
            tmnxSLAProfName,
            tmnxSPICatName }
    ::= { tmnxSPICatTable 1 }

TmnxSPICatEntry ::=
    SEQUENCE {
        tmnxSPICatName                TNamedItem,
        tmnxSPICatMapName             TNamedItem,
        tmnxSPICatCreditControlPlcy   TNamedItem,
        tmnxSPICatCrdtVolumeUsed      CounterBasedGauge64,
        tmnxSPICatCrdtVolumeAvail     CounterBasedGauge64,
        tmnxSPICatCrdtVolumeThres     CounterBasedGauge64,
        tmnxSPICatCrdtTimeUsed        Gauge32,
        tmnxSPICatCrdtTimeAvail       Gauge32,
        tmnxSPICatCrdtTimeThres       Gauge32,
        tmnxSPICatCrdtExpired         TruthValue,
        tmnxSPICatCrdtNegotiating     TruthValue,
        tmnxSPICatOutOfCrdtAction     TmnxSubCcOutOfCreditAction,
        tmnxSPICatQuotaHoldingTime    Unsigned32,
        tmnxSPICatCrdtReset           TmnxActionType,
        tmnxSPICatAlias               TXLNamedItem
    }

tmnxSPICatName OBJECT-TYPE
    SYNTAX      TNamedItem
    MAX-ACCESS  not-accessible
    STATUS      current
    DESCRIPTION
        "The value of tmnxSPICatName indicates the credit category."
    ::= { tmnxSPICatEntry 1 }

tmnxSPICatMapName OBJECT-TYPE
    SYNTAX      TNamedItem
    MAX-ACCESS  read-only
    STATUS      current
    DESCRIPTION
        "The value of tmnxSPICatMapName indicates the credit category map."
    ::= { tmnxSPICatEntry 2 }

tmnxSPICatCreditControlPlcy OBJECT-TYPE
    SYNTAX      TNamedItem
    MAX-ACCESS  read-only
    STATUS      current
    DESCRIPTION
        "The value of tmnxSPICatCreditControlPlcy indicates the credit control policy."
    ::= { tmnxSPICatEntry 3 }

tmnxSPICatCrdtVolumeUsed OBJECT-TYPE
    SYNTAX      CounterBasedGauge64
    MAX-ACCESS  read-only
    STATUS      current
    DESCRIPTION
        "The value of tmnxSPICatCrdtVolumeUsed indicates the volume based credit used."
    ::= { tmnxSPICatEntry 4 }

tmnxSPICatCrdtVolumeAvail OBJECT-TYPE
    SYNTAX      CounterBasedGauge64
    MAX-ACCESS  read-only
    STATUS      current
    DESCRIPTION
        "The value of tmnxSPICatCrdtVolumeAvail indicates the volume based credit
        available."
    ::= { tmnxSPICatEntry 5 }

tmnxSPICatCrdtVolumeThres OBJECT-TYPE
    SYNTAX      CounterBasedGauge64
    MAX-ACCESS  read-only
    STATUS      current
    DESCRIPTION
        "The value of tmnxSPICatCrdtVolumeThres indicates the volume based credit 
        threshold.

         If tmnxSPICatCrdtVolumeAvail becomes lower, then credit negotiation will
         start."
    ::= { tmnxSPICatEntry 6 }

tmnxSPICatCrdtTimeUsed OBJECT-TYPE
    SYNTAX      Gauge32
    MAX-ACCESS  read-only
    STATUS      current
    DESCRIPTION
        "The value of tmnxSPICatCrdtTimeUsed indicates the time based credit used."
    ::= { tmnxSPICatEntry 7 }

tmnxSPICatCrdtTimeAvail OBJECT-TYPE
    SYNTAX      Gauge32
    MAX-ACCESS  read-only
    STATUS      current
    DESCRIPTION
        "The value of tmnxSPICatCrdtTimeAvail indicates the time based credit
        available."
    ::= { tmnxSPICatEntry 8 }

tmnxSPICatCrdtTimeThres OBJECT-TYPE
    SYNTAX      Gauge32
    MAX-ACCESS  read-only
    STATUS      current
    DESCRIPTION
        "The value of tmnxSPICatCrdtTimeThres indicates the time based credit
        threshold.
        
         If tmnxSPICatCrdtTimeAvail becomes lower, then credit negotiation will start."
    ::= { tmnxSPICatEntry 9 }

tmnxSPICatCrdtExpired OBJECT-TYPE
    SYNTAX      TruthValue
    MAX-ACCESS  read-only
    STATUS      current
    DESCRIPTION
        "The value of tmnxSPICatCrdtExpired indicates whether credit has expired."
    ::= { tmnxSPICatEntry 10 }

tmnxSPICatCrdtNegotiating OBJECT-TYPE
    SYNTAX      TruthValue
    MAX-ACCESS  read-only
    STATUS      current
    DESCRIPTION
        "The value of tmnxSPICatCrdtNegotiating indicates whether credit is being
        negotiated."
    ::= { tmnxSPICatEntry 11 }

tmnxSPICatOutOfCrdtAction OBJECT-TYPE
    SYNTAX      TmnxSubCcOutOfCreditAction
    MAX-ACCESS  read-only
    STATUS      current
    DESCRIPTION
        "The value of tmnxSPICatOutOfCrdtAction indicates what will happen when credit 
        gets exhausted."
    ::= { tmnxSPICatEntry 12 }

tmnxSPICatQuotaHoldingTime OBJECT-TYPE
    SYNTAX      Unsigned32
    UNITS       "seconds"
    MAX-ACCESS  read-only
    STATUS      current
    DESCRIPTION
        "The value of tmnxSPICatQuotaHoldingTime indicates the time after which credit
        negotiation will start when the subscriber activity rate falls below the 
        activity threshold."
    ::= { tmnxSPICatEntry 13 }

tmnxSPICatCrdtReset OBJECT-TYPE
    SYNTAX      TmnxActionType
    MAX-ACCESS  read-write
    STATUS      current
    DESCRIPTION
        "The object tmnxSPICatCrdtReset allows the operator to reset the
         credit for the accounting record represented by this row,
         by setting the object to 'doAction'.

         A GET on this object will always return 'notApplicable'."
    ::= { tmnxSPICatEntry 100 }

tmnxSPICatAlias OBJECT-TYPE
     SYNTAX      TXLNamedItem
     MAX-ACCESS  read-only
     STATUS      current
     DESCRIPTION
         "The value of tmnxSPICatAlias indicates the full name of the credit category.

          If the full name of the credit category exceeds 32 characters,
          it does not fit in the tmnxSPICatName object;
          in that case, the tmnxSPICatName object contains only the first 32 characters.
          
          It is not possible to have two different credit categories in this table
          where the first 32 characters of the name are identical."
     ::= { tmnxSPICatEntry 101 }

-- ------------------------------------------------
-- tmnxSubHostSapTrkStatsTable
-- ------------------------------------------------

tmnxSubHostSapTrkStatsTable OBJECT-TYPE
    SYNTAX      SEQUENCE OF TmnxSubHostSapTrkStatsEntry
    MAX-ACCESS  not-accessible
    STATUS      current
    DESCRIPTION
        "The tmnxSubHostSapTrkStatsTable shows statistics information
         about the video viewership of hosts, ordered by SAP."
    ::= { tmnxSubMgmtObjects 63 }

tmnxSubHostSapTrkStatsEntry OBJECT-TYPE
    SYNTAX      TmnxSubHostSapTrkStatsEntry
    MAX-ACCESS  not-accessible
    STATUS      current
    DESCRIPTION
        "Each row entry represents host tracking status and statistics 
         information about a particular host.

         Rows are created or removed automatically by the system.
         
         Rows are only created where the statistics value is nonzero;
         this allows faster walking through this table; hence, it is recommended
         to perform only get-next-request operations to retrieve information
         from this table."
    INDEX { svcId, sapPortId, sapEncapValue,
            tmnxSubHostSapTrkHostAddrType, tmnxSubHostSapTrkHostAddr,
            tmnxSubHostSapTrkStatsType
          }
    ::= { tmnxSubHostSapTrkStatsTable 1 }

TmnxSubHostSapTrkStatsEntry ::= SEQUENCE
   {
        tmnxSubHostSapTrkStatsType        TmnxSubHostTrkStatsType,
        tmnxSubHostSapTrkStatsVal         Counter32
   }

tmnxSubHostSapTrkStatsType OBJECT-TYPE
    SYNTAX      TmnxSubHostTrkStatsType
    MAX-ACCESS  not-accessible
    STATUS      current
    DESCRIPTION
        "The value of tmnxSubHostSapTrkStatsType indicates
         the type of host tracking statistics contained in 
         tmnxSubHostSapTrkStatsVal."
    ::= { tmnxSubHostSapTrkStatsEntry 1 }

tmnxSubHostSapTrkStatsVal OBJECT-TYPE
    SYNTAX      Counter32
    MAX-ACCESS  read-only
    STATUS      current
    DESCRIPTION
        "The value of tmnxSubHostSapTrkStatsType indicates the value of the
         host tracking statistics of the type indicated by 
         tmnxSubHostSapTrkStatsType, for this host."
    ::= { tmnxSubHostSapTrkStatsEntry 2 }

-- ------------------------------------------------
-- tmnxSubHostTrkStatsTable
-- ------------------------------------------------

tmnxSubHostTrkStatsTable OBJECT-TYPE
    SYNTAX      SEQUENCE OF TmnxSubHostTrkStatsEntry
    MAX-ACCESS  not-accessible
    STATUS      current
    DESCRIPTION
        "The tmnxSubHostTrkStatsTable shows statistics information
         about the video viewership of subscriber hosts."
    ::= { tmnxSubMgmtObjects 64 }

tmnxSubHostTrkStatsEntry OBJECT-TYPE
    SYNTAX      TmnxSubHostTrkStatsEntry
    MAX-ACCESS  not-accessible
    STATUS      current
    DESCRIPTION
        "Each row entry represents host tracking statistics information
         about a particular subscriber host.

         Rows are created or removed automatically by the system.

         Rows are only created for a subscriber that is associated with
         a host tracking policy.

         A subscriber is associated with a host tracking policy if the value of
         the object tmnxSubInfoSubProfile refers to a subscriber policy where
         the value of the object tmnxSubProfHostTrackingPolicy is not empty.
         
         Moreover, rows are only created where the statistics value is nonzero;
         this allows faster walking through this table; hence, it is recommended
         to perform only get-next-request operations to retrieve information
         from this table."
    INDEX { tmnxSubInfoSubIdent,
            svcId, sapPortId, sapEncapValue,
            tmnxSubHostInfoV2IpAddressType, tmnxSubHostInfoV2IpAddress,
            tmnxSubHostTrkStatsType
          }
    ::= { tmnxSubHostTrkStatsTable 1 }

TmnxSubHostTrkStatsEntry ::= SEQUENCE
   {
        tmnxSubHostTrkStatsType        TmnxSubHostTrkStatsType,
        tmnxSubHostTrkStatsVal         Counter32
   }

tmnxSubHostTrkStatsType OBJECT-TYPE
    SYNTAX      TmnxSubHostTrkStatsType
    MAX-ACCESS  not-accessible
    STATUS      current
    DESCRIPTION
        "The value of tmnxSubHostTrkStatsType indicates
         the type of host tracking statistics contained in 
         tmnxSubHostTrkStatsVal."
    ::= { tmnxSubHostTrkStatsEntry 1 }

tmnxSubHostTrkStatsVal OBJECT-TYPE
    SYNTAX      Counter32
    MAX-ACCESS  read-only
    STATUS      current
    DESCRIPTION
        "The value of tmnxSubHostTrkStatsType indicates the value of the
         host tracking statistics of the type indicated by 
         tmnxSubHostTrkStatsType, for this subscriber host."
    ::= { tmnxSubHostTrkStatsEntry 2 }

-- ----------------------------------------
-- tmnxSLAProfInstInfoTable
-- ----------------------------------------

tmnxSLAProfInstInfoTable OBJECT-TYPE
    SYNTAX      SEQUENCE OF TmnxSLAProfInstInfoEntry
    MAX-ACCESS  not-accessible
    STATUS      current
    DESCRIPTION
        "The tmnxSLAProfInstInfoTable has an entry for each SLA profile
         instance found in the system."
    ::= { tmnxSubMgmtObjects 65 }

tmnxSLAProfInstInfoEntry OBJECT-TYPE
    SYNTAX      TmnxSLAProfInstInfoEntry
    MAX-ACCESS  not-accessible
    STATUS      current
    DESCRIPTION
        "Each row entry contains information about a particular SLA
         profile instance available in the system."
    INDEX { tmnxSubInfoSubIdent,
            sapPortId,
            sapEncapValue,
            tmnxSLAProfName }
    ::= { tmnxSLAProfInstInfoTable 1 }

TmnxSLAProfInstInfoEntry ::=
    SEQUENCE {
        tmnxSPIInfoCategoryMapName TNamedItemOrEmpty,
        tmnxSPIInfoDiamSessId      DisplayString,
        tmnxSPIInfoIngQosPolIdOvr  TAnyQosPolicyIDorZero,
        tmnxSPIInfoEgrQosPolIdOvr  TAnyQosPolicyIDorZero
    }

tmnxSPIInfoCategoryMapName OBJECT-TYPE
    SYNTAX      TNamedItemOrEmpty
    MAX-ACCESS  read-only
    STATUS      current
    DESCRIPTION
        "The value of tmnxSPIInfoCategoryMapName indicates the name of
         the category map used by this SLA profile instance."
    ::= { tmnxSLAProfInstInfoEntry 1 }

tmnxSPIInfoDiamSessId OBJECT-TYPE
    SYNTAX      DisplayString (SIZE(0..102))
    MAX-ACCESS  read-only
    STATUS      current
    DESCRIPTION
        "The value of tmnxSPIInfoDiamSessId indicates the id of the diameter
         session used by this SLA profile instance."
    ::= { tmnxSLAProfInstInfoEntry 2 }

tmnxSPIInfoIngQosPolIdOvr OBJECT-TYPE
    SYNTAX      TAnyQosPolicyIDorZero
    MAX-ACCESS  read-only
    STATUS      current
    DESCRIPTION
        "If different from 0, the value of tmnxSPIInfoIngQosPolIdOvr
         indicates the ID of the overriding ingress Qos policy."
    ::= { tmnxSLAProfInstInfoEntry 3 }

tmnxSPIInfoEgrQosPolIdOvr OBJECT-TYPE
    SYNTAX      TAnyQosPolicyIDorZero
    MAX-ACCESS  read-only
    STATUS      current
    DESCRIPTION
        "If different from 0, the value of tmnxSPIInfoEgrQosPolIdOvr
         indicates the ID of the overriding egress Qos policy."
    ::= { tmnxSLAProfInstInfoEntry 4 }

-- ------------------------------------------------
-- tmnxSubCredCatIpFltrTable
-- ------------------------------------------------
tmnxCcIpFltrTableLastChange OBJECT-TYPE
    SYNTAX     TimeStamp
    MAX-ACCESS read-only
    STATUS     current
    DESCRIPTION
        "The value of tmnxCcIpFltrTableLastChange indicates the
         sysUpTime at the time of the last modification
         of tmnxSubCredCatIpFltrTable.

         If no changes were made to the entry since the last
         re-initialization of the local network management subsystem,
         then this object contains a zero value."
    ::= { tmnxSubMgmtObjects 66 }

tmnxSubCredCatIpFltrTable OBJECT-TYPE
    SYNTAX     SEQUENCE OF TmnxSubCredCatIpFltrEntry
    MAX-ACCESS not-accessible
    STATUS     current
    DESCRIPTION  "A table of all IP filter entries for all credit control
                  (CC) Categories."
    ::= { tmnxSubMgmtObjects 67 }

tmnxSubCredCatIpFltrEntry OBJECT-TYPE
    SYNTAX     TmnxSubCredCatIpFltrEntry
    MAX-ACCESS not-accessible
    STATUS     current
    DESCRIPTION
        "Information about a particular Credit Control (CC) Category IP Filter
         entry.
         Every Credit Control (CC) Category can have zero or more IP Filter
         entries."
    INDEX { tmnxSubApCMapName,
            tmnxSubApCategoryName,
            tmnxCcIpFltrDirection,
            tmnxCcIpFltrIndex }
    ::= { tmnxSubCredCatIpFltrTable 1 }


TmnxSubCredCatIpFltrEntry ::= SEQUENCE
{
    tmnxCcIpFltrDirection           TmnxSubDirection,
    tmnxCcIpFltrIndex               TEntryId,
    tmnxCcIpFltrRowStatus           RowStatus,
    tmnxCcIpFltrLastChanged         TimeStamp,
    tmnxCcIpFltrDescription         TItemDescription,
    tmnxCcIpFltrAction              TFilterAction,
    tmnxCcIpFltrRedirectURL         DisplayString,
    tmnxCcIpFltrProtocol            TIpProtocol,
    tmnxCcIpFltrDSCP                TDSCPNameOrEmpty,
    tmnxCcIpFltrSourceIpAddr        IpAddress,
    tmnxCcIpFltrSourceIpMask        IpAddress,
    tmnxCcIpFltrDestinationIpAddr   IpAddress,
    tmnxCcIpFltrDestinationIpMask   IpAddress,
    tmnxCcIpFltrSourcePortValue1    TTcpUdpPort,
    tmnxCcIpFltrSourcePortValue2    TTcpUdpPort,
    tmnxCcIpFltrSourcePortOperator  TTcpUdpPortOperator,
    tmnxCcIpFltrDestPortValue1      TTcpUdpPort,
    tmnxCcIpFltrDestPortValue2      TTcpUdpPort,
    tmnxCcIpFltrDestPortOperator    TTcpUdpPortOperator,
    tmnxCcIpFltrFragment            TItemMatch,
    tmnxCcIpFltrIcmpCode            INTEGER,
    tmnxCcIpFltrIcmpType            INTEGER,
    tmnxCcIpFltrIpOptionValue       TIpOption,
    tmnxCcIpFltrIpOptionMask        TIpOption,
    tmnxCcIpFltrMultipleOption      TItemMatch,
    tmnxCcIpFltrOptionPresent       TItemMatch,
    tmnxCcIpFltrTcpSyn              TItemMatch,
    tmnxCcIpFltrTcpAck              TItemMatch
}

tmnxCcIpFltrDirection OBJECT-TYPE
    SYNTAX     TmnxSubDirection
    MAX-ACCESS not-accessible
    STATUS     current
    DESCRIPTION
        "The value of tmnxCcIpFltrDirection serves as a primary index for the
         IP-filter entry and indicates whether this entry applies to the
         ingress/egress SAP."
    ::= { tmnxSubCredCatIpFltrEntry 1 }

tmnxCcIpFltrIndex OBJECT-TYPE
    SYNTAX     TEntryId
    MAX-ACCESS not-accessible
    STATUS     current
    DESCRIPTION
        "The value of tmnxCcIpFltrIndex serves as a secondary index for the
         IP-filter entry."
    ::= { tmnxSubCredCatIpFltrEntry 2 }

tmnxCcIpFltrRowStatus OBJECT-TYPE
    SYNTAX     RowStatus
    MAX-ACCESS read-create
    STATUS     current
    DESCRIPTION
        "The value of tmnxCcIpFltrRowStatus controls the creation and
         deletion of rows in the table.

         Max. 10 entries can be created for any combination of 
         tmnxSubApCMapName,tmnxSubApCategoryName."
    ::= { tmnxSubCredCatIpFltrEntry 3 }

tmnxCcIpFltrLastChanged OBJECT-TYPE
    SYNTAX     TimeStamp
    MAX-ACCESS read-only
    STATUS     current
    DESCRIPTION
        "The value of tmnxCcIpFltrLastChanged indicates the sysUpTime when
         an object in this table was last modified. A Value 0 means that
         no change was made to this row since it was created."
    ::= { tmnxSubCredCatIpFltrEntry 4 }

tmnxCcIpFltrDescription OBJECT-TYPE
    SYNTAX     TItemDescription
    MAX-ACCESS read-create
    STATUS     current
    DESCRIPTION
        "The value of tmnxCcIpFltrDescription specifies the user-provided
         description for this filter entry."
    DEFVAL { ''H }
    ::= { tmnxSubCredCatIpFltrEntry 5 }

tmnxCcIpFltrAction OBJECT-TYPE
    SYNTAX     TFilterAction
    MAX-ACCESS read-create
    STATUS     current
    DESCRIPTION
        "The value of tmnxCcIpFltrAction specifies the action to take for
         packets that match this filter entry.

         The default value of 'drop(1)' will drop all matching packets.
         The value nat(5) is not supported."
    DEFVAL { drop }
    ::= { tmnxSubCredCatIpFltrEntry 6 }

tmnxCcIpFltrRedirectURL OBJECT-TYPE
    SYNTAX     DisplayString
    MAX-ACCESS read-create
    STATUS     current
    DESCRIPTION
        "The value of tmnxCcIpFltrRedirectURL specifies the URL
         to redirect to, when the value of tmnxCcIpFltrAction is
         'httpRedirect'."
    ::= { tmnxSubCredCatIpFltrEntry 7 }    
    
tmnxCcIpFltrProtocol OBJECT-TYPE
    SYNTAX     TIpProtocol
    MAX-ACCESS read-create
    STATUS     current
    DESCRIPTION
        "The value of tmnxCcIpFltrProtocol specifies the IP protocol to match.
         If the protocol is changed the protocol specific parameters are reset.
         For instance if protocol is changed from TCP to UDP, then the objects
         tmnxCcIpFltrTcpSyn and tmnxCcIpFltrTcpAck will be turned off.

         The default value of -1 disables matching IP protocol."
    DEFVAL { -1 }
    ::= { tmnxSubCredCatIpFltrEntry 8 }

tmnxCcIpFltrDSCP OBJECT-TYPE
    SYNTAX     TDSCPNameOrEmpty
    MAX-ACCESS read-create
    STATUS     current
    DESCRIPTION
        "The value of tmnxCcIpFltrDSCP specifies the DSCP to be matched on the
        packet."
    DEFVAL { ''H }
    ::= { tmnxSubCredCatIpFltrEntry 9 }

tmnxCcIpFltrSourceIpAddr OBJECT-TYPE
    SYNTAX     IpAddress
    MAX-ACCESS read-create
    STATUS     current
    DESCRIPTION
        "The value of tmnxCcIpFltrSourceIpAddr specifies the IP address to match
         the source-ip of the packet.

         This field can only be set if the value of tmnxCcIpFltrDirection is set
         to egress."
    DEFVAL { '00000000'H }
    ::= { tmnxSubCredCatIpFltrEntry 10 }

tmnxCcIpFltrSourceIpMask OBJECT-TYPE
    SYNTAX     IpAddress
    MAX-ACCESS read-create
    STATUS     current
    DESCRIPTION
        "The value of tmnxCcIpFltrSourceIpMask specifies the IP Mask value for
         this policy IP Filter entry. The mask is ANDed with the received Source
         IP address to match the tmnxCcIpFltrSourceIpAddr.

         The default value of 0 disables matching on the Source IP address.

         This field can only be set if the value of tmnxCcIpFltrDirection is set
         to egress."
    DEFVAL { 0 }
    ::= { tmnxSubCredCatIpFltrEntry 11 }

tmnxCcIpFltrDestinationIpAddr OBJECT-TYPE
    SYNTAX     IpAddress
    MAX-ACCESS read-create
    STATUS     current
    DESCRIPTION
        "The value of tmnxCcIpFltrDestinationIpAddr specifies the IP address to
         match the destination-ip of the packet.

         This field can only be set if the value of tmnxCcIpFltrDirection is set
         to ingress."
    DEFVAL { '00000000'H }
    ::= { tmnxSubCredCatIpFltrEntry 12 }

tmnxCcIpFltrDestinationIpMask OBJECT-TYPE
    SYNTAX     IpAddress
    MAX-ACCESS read-create
    STATUS     current
    DESCRIPTION
        "The value of tmnxCcIpFltrDestinationIpMask specifies the IP Mask value
         for this policy IP Filter entry. The mask is ANDed with the received
         destination IP address to match the tmnxCcIpFltrDestinationIpAddr.

         The default value of 0 disables matching on the destination IP address.

         This field can only be set if the value of tmnxCcIpFltrDirection is set
         to ingress."
    DEFVAL { 0 }
    ::= { tmnxSubCredCatIpFltrEntry 13 }

tmnxCcIpFltrSourcePortValue1 OBJECT-TYPE
    SYNTAX     TTcpUdpPort
    MAX-ACCESS read-create
    STATUS     current
    DESCRIPTION
        "The value of tmnxCcIpFltrSourcePortValue1 specifies the TCP/UDP port
         value1. The value of this object is used as per the description for
         tmnxCcIpFltrSourcePortOperator."
    DEFVAL { 0 }
    ::= { tmnxSubCredCatIpFltrEntry 14 }

tmnxCcIpFltrSourcePortValue2  OBJECT-TYPE
    SYNTAX     TTcpUdpPort
    MAX-ACCESS read-create
    STATUS     current
    DESCRIPTION
        "The value of tmnxCcIpFltrSourcePortValue2 specifies the TCP/UDP port
         value2. The value of this object is used as per the description for
         tmnxCcIpFltrSourcePortOperator."
    DEFVAL { 0 }
    ::= { tmnxSubCredCatIpFltrEntry 15 }

tmnxCcIpFltrSourcePortOperator OBJECT-TYPE
    SYNTAX     TTcpUdpPortOperator
    MAX-ACCESS read-create
    STATUS     current
    DESCRIPTION
        "The value of tmnxCcIpFltrSourcePortOperator specifies the manner in
         which tmnxCcIpFltrSourcePortValue1 and tmnxCcIpFltrSourcePortValue2
         are to be used. The value of these latter 2 objects and
         tIPFilterParamsSourcePortOperator is used as described in
         TTcpUdpPortOperator."
    DEFVAL { none }
    ::= { tmnxSubCredCatIpFltrEntry 16 }

tmnxCcIpFltrDestPortValue1 OBJECT-TYPE
    SYNTAX     TTcpUdpPort
    MAX-ACCESS read-create
    STATUS     current
    DESCRIPTION
        "The value of tmnxCcIpFltrDestPortValue1 specifies the TCP/UDP
         port value1. The value of this object is used as per the description
         for tmnxCcIpFltrDestPortOperator."
    DEFVAL { 0 }
    ::= { tmnxSubCredCatIpFltrEntry 17 }

tmnxCcIpFltrDestPortValue2  OBJECT-TYPE
    SYNTAX     TTcpUdpPort
    MAX-ACCESS read-create
    STATUS     current
    DESCRIPTION
    "The value of tmnxCcIpFltrDestPortValue2 specifies the TCP/UDP
     port value2. The value of this object is used as per the description
     for tmnxCcIpFltrDestPortOperator."
    DEFVAL { 0 }
    ::= { tmnxSubCredCatIpFltrEntry 18 }

tmnxCcIpFltrDestPortOperator OBJECT-TYPE
    SYNTAX     TTcpUdpPortOperator
    MAX-ACCESS read-create
    STATUS     current
    DESCRIPTION
    "The value of tmnxCcIpFltrDestPortOperator specifies the manner in
     which tmnxCcIpFltrDestPortValue1 and
     tmnxCcIpFltrDestPortValue2 are to be used. The value of these latter
     2 objects and tmnxCcIpFltrDestPortOperator is used as described in
     TTcpUdpPortOperator."
    DEFVAL { none }
    ::= { tmnxSubCredCatIpFltrEntry 19 }

tmnxCcIpFltrFragment OBJECT-TYPE
    SYNTAX     TItemMatch
    MAX-ACCESS read-create
    STATUS     current
    DESCRIPTION
        "The value of tmnxCcIpFltrFragment specifies whether this filter applies
         to fragmented or unfragmented packets only.

         The default value of 'off(1)' disables fragmentation matching."
    DEFVAL { off }
    ::= { tmnxSubCredCatIpFltrEntry 20 }

tmnxCcIpFltrIcmpCode  OBJECT-TYPE
    SYNTAX     INTEGER (-1|0..255)
    MAX-ACCESS read-create
    STATUS     current
    DESCRIPTION
        "The value of tmnxCcIpFltrIcmpCode specifies the icmp code to be
         matched. tmnxCcIpFltrIcmpCode complements the object
         tmnxCcIpFltrIcmpType. Both of them need to be set to actually
         enable ICMP matching.

         The default value of -1 disables ICMP matching."
    DEFVAL { -1 }
    ::= { tmnxSubCredCatIpFltrEntry 21 }

tmnxCcIpFltrIcmpType  OBJECT-TYPE
    SYNTAX     INTEGER (-1|0..255)
    MAX-ACCESS read-create
    STATUS     current
    DESCRIPTION
        "The value of tmnxCcIpFltrIcmpType specifies the icmp type to be
         matched. tmnxCcIpFltrIcmpType complements the object
         tmnxCcIpFltrIcmpCode. Both of them need to be set to actually
         enable ICMP matching.

         The default value of -1 disables ICMP matching."
    DEFVAL { -1 }
    ::= { tmnxSubCredCatIpFltrEntry 22 }

tmnxCcIpFltrIpOptionValue OBJECT-TYPE
    SYNTAX     TIpOption
    MAX-ACCESS read-create
    STATUS     current
    DESCRIPTION
        "The value of tmnxCcIpFltrIpOptionValue specifies the value the first
         IP option of the IP header should have.

         If the value of tmnxCcIpFltrIpOptionMask is not 0 the IP option of the
         IP header will first be ANDed with the tmnxCcIpFltrIpOptionMask before
         it is compared with tmnxCcIpFltrIpOptionValue.

         The default value of 0 disables IP options matching."
    DEFVAL { 0 }
    ::= { tmnxSubCredCatIpFltrEntry 23 }

tmnxCcIpFltrIpOptionMask  OBJECT-TYPE
    SYNTAX       TIpOption
    MAX-ACCESS   read-create
    STATUS       current
    DESCRIPTION
        "The value of tmnxCcIpFltrIpOptionMask specifies the value with which
         the value of the first IP option of the IP header will be ANDed before
         it is compared with tmnxCcIpFltrIpOptionValue.

         The default value of 0 disables this behaviour."
    DEFVAL { 0 }
    ::= { tmnxSubCredCatIpFltrEntry 24 }

tmnxCcIpFltrMultipleOption  OBJECT-TYPE
    SYNTAX     TItemMatch
    MAX-ACCESS read-create
    STATUS     current
    DESCRIPTION
        "The value of tmnxCcIpFltrMultipleOption specifies whether the number
         of IP options in the IP header should be bigger than 1.

         The default value of 'off(1)' disables checking the number of IP
         options in the IP header."
    DEFVAL { off }
    ::= { tmnxSubCredCatIpFltrEntry 25 }

tmnxCcIpFltrOptionPresent OBJECT-TYPE
    SYNTAX     TItemMatch
    MAX-ACCESS read-create
    STATUS     current
    DESCRIPTION
        "The value of tmnxCcIpFltrOptionPresent specifies whether there
         should be any IP options in the IP header.

         The default value of 'off(1)' disables checking for the presence of
         IP options in the IP header."
    DEFVAL { off }
    ::= { tmnxSubCredCatIpFltrEntry 26 }

tmnxCcIpFltrTcpSyn  OBJECT-TYPE
     SYNTAX     TItemMatch
     MAX-ACCESS read-create
     STATUS     current
     DESCRIPTION
       "The value of tmnxCcIpFltrTcpSyn specifies whether the control bits of
        the TCP header should contain the SYN bit.

        The default value of 'off(1)' disables checking for the SYN bit."
     DEFVAL { off }
     ::= { tmnxSubCredCatIpFltrEntry 27 }

tmnxCcIpFltrTcpAck  OBJECT-TYPE
    SYNTAX     TItemMatch
    MAX-ACCESS read-create
    STATUS     current
    DESCRIPTION
      "The value of tmnxCcIpFltrTcpAck specifies whether the control bits of
       the TCP header should contain the ACK bit.

       The default value of 'off(1)' disables checking for the ACK bit."
    DEFVAL { off }
    ::= { tmnxSubCredCatIpFltrEntry 28 }

-- ------------------------------------------------
-- tmnxSubCredCatIpv6FltrTable
-- ------------------------------------------------
tmnxCcIpv6FltrTableLastChange OBJECT-TYPE
    SYNTAX      TimeStamp
    MAX-ACCESS  read-only
    STATUS      current
    DESCRIPTION
      "The value of tmnxCcIpv6FltrTableLastChange indicates the
       sysUpTime at the time of the last modification
       of tmnxSubCredCatIpv6FltrTable.

       If no changes were made to the entry since the last
       re-initialization of the local network management subsystem,
       then this object contains a zero value."
    ::= { tmnxSubMgmtObjects 68 }

tmnxSubCredCatIpv6FltrTable OBJECT-TYPE
    SYNTAX       SEQUENCE OF TmnxSubCredCatIpv6FltrEntry
    MAX-ACCESS   not-accessible
    STATUS       current
    DESCRIPTION  "A table of all IPv6 filter entries for all credit control
                (CC) Categories."
    ::= { tmnxSubMgmtObjects 69 }

tmnxSubCredCatIpv6FltrEntry OBJECT-TYPE
    SYNTAX       TmnxSubCredCatIpv6FltrEntry
    MAX-ACCESS   not-accessible
    STATUS       current
    DESCRIPTION
      "Information about a particular Credit Control (CC) Category IPv6 Filter
       entry.
       Every Credit Control (CC) Category can have zero or more IPv6 Filter
       entries."
    INDEX { tmnxSubApCMapName,
            tmnxSubApCategoryName,
            tmnxCcIpv6FltrDirection,
            tmnxCcIpv6FltrIndex }
    ::= { tmnxSubCredCatIpv6FltrTable 1 }


TmnxSubCredCatIpv6FltrEntry ::= SEQUENCE
{
    tmnxCcIpv6FltrDirection          TmnxSubDirection,
    tmnxCcIpv6FltrIndex              TEntryId,
    tmnxCcIpv6FltrRowStatus          RowStatus,
    tmnxCcIpv6FltrLastChanged        TimeStamp,
    tmnxCcIpv6FltrDescription        TItemDescription,
    tmnxCcIpv6FltrAction             TFilterAction,
    tmnxCcIpv6FltrRedirectURL        DisplayString,
    tmnxCcIpv6FltrNextHeader         TIpProtocol,
    tmnxCcIpv6FltrDSCP               TDSCPNameOrEmpty,
    tmnxCcIpv6FltrSourceIpAddr       InetAddressIPv6,
    tmnxCcIpv6FltrSourceIpMask       InetAddressPrefixLength,
    tmnxCcIpv6FltrDestinationIpAddr  InetAddressIPv6,
    tmnxCcIpv6FltrDestinationIpMask  InetAddressPrefixLength,
    tmnxCcIpv6FltrSourcePortValue1   TTcpUdpPort,
    tmnxCcIpv6FltrSourcePortValue2   TTcpUdpPort,
    tmnxCcIpv6FltrSourcePortOperator TTcpUdpPortOperator,
    tmnxCcIpv6FltrDestPortValue1     TTcpUdpPort,
    tmnxCcIpv6FltrDestPortValue2     TTcpUdpPort,
    tmnxCcIpv6FltrDestPortOperator   TTcpUdpPortOperator,
    tmnxCcIpv6FltrIcmpCode           INTEGER,
    tmnxCcIpv6FltrIcmpType           INTEGER,
    tmnxCcIpv6FltrTcpSyn             TItemMatch,
    tmnxCcIpv6FltrTcpAck             TItemMatch
}

tmnxCcIpv6FltrDirection OBJECT-TYPE
    SYNTAX     TmnxSubDirection
    MAX-ACCESS not-accessible
    STATUS     current
    DESCRIPTION
        "The value of tmnxCcIpv6FltrDirection serves as a primary index for the
         IPv6-filter entry and indicates whether this entry applies to the
         ingress/egress SAP."
    ::= { tmnxSubCredCatIpv6FltrEntry 1 }

tmnxCcIpv6FltrIndex OBJECT-TYPE
    SYNTAX     TEntryId
    MAX-ACCESS not-accessible
    STATUS     current
    DESCRIPTION
        "The value of tmnxCcIpv6FltrIndex serves as a secondary index for the
         IPv6-filter entry."
    ::= { tmnxSubCredCatIpv6FltrEntry 2 }

tmnxCcIpv6FltrRowStatus OBJECT-TYPE
    SYNTAX     RowStatus
    MAX-ACCESS read-create
    STATUS     current
    DESCRIPTION
        "The value of tmnxCcIpv6FltrRowStatus controls the creation and
         deletion of rows in the table.
  
         Max. 10 entries can be created for any combination of 
         tmnxSubApCMapName,tmnxSubApCategoryName."
    ::= { tmnxSubCredCatIpv6FltrEntry 3 }

tmnxCcIpv6FltrLastChanged OBJECT-TYPE
    SYNTAX     TimeStamp
    MAX-ACCESS read-only
    STATUS     current
    DESCRIPTION
        "The value of tmnxCcIpv6FltrLastChanged indicates the sysUpTime when
         an object in this table was last modified. A Value 0 means that
         no change was made to this row since it was created."
    ::= { tmnxSubCredCatIpv6FltrEntry 4 }

tmnxCcIpv6FltrDescription  OBJECT-TYPE
    SYNTAX     TItemDescription
    MAX-ACCESS read-create
    STATUS     current
    DESCRIPTION
        "The value of tmnxCcIpv6FltrDescription specifies the user-provided
         description for this filter entry."
    DEFVAL { ''H }
    ::= { tmnxSubCredCatIpv6FltrEntry 5 }

tmnxCcIpv6FltrAction OBJECT-TYPE
    SYNTAX     TFilterAction
    MAX-ACCESS read-create
    STATUS     current
    DESCRIPTION
        "The value of tmnxCcIpv6FltrAction specifies the action to take for
         packets that match this filter entry.

         The default value of 'drop(1)' will drop all matching packets.

         The values httpRedirect(4) and nat(5) are currently not
         supported."
    DEFVAL { drop }
    ::= { tmnxSubCredCatIpv6FltrEntry 6 }

tmnxCcIpv6FltrRedirectURL OBJECT-TYPE
    SYNTAX     DisplayString
    MAX-ACCESS read-create
    STATUS     current
    DESCRIPTION
        "The value of tmnxCcIpv6FltrRedirectURL specifies the URL
         to redirect to, when the value of tmnxCcIpv6FltrAction is
         'httpRedirect(4)'.

         However, currently this field is disabled."
    ::= { tmnxSubCredCatIpv6FltrEntry 7 }

tmnxCcIpv6FltrNextHeader OBJECT-TYPE
    SYNTAX     TIpProtocol
    MAX-ACCESS read-create
    STATUS     current
    DESCRIPTION
        "The value of tmnxCcIpv6FltrNextHeader specifies the IPv6 next header
         to match.
         If the value is changed the next header specific parameters are reset.
         For instance if value is changed from TCP to UDP, then the objects
         tmnxCcIpv6FltrTcpSyn and tmnxCcIpv6FltrTcpAck will be turned off.

         The default value of -1 disables matching IPv6 next header.

         Currently this field is not supported."
    DEFVAL { -1 }
    ::= { tmnxSubCredCatIpv6FltrEntry 8 }

tmnxCcIpv6FltrDSCP OBJECT-TYPE
    SYNTAX     TDSCPNameOrEmpty
    MAX-ACCESS read-create
    STATUS     current
    DESCRIPTION
        "The value of tmnxCcIpv6FltrDSCP specifies the DSCP to be matched on the
        packet."
    DEFVAL { ''H }
    ::= { tmnxSubCredCatIpv6FltrEntry 9 }

tmnxCcIpv6FltrSourceIpAddr OBJECT-TYPE
    SYNTAX     InetAddressIPv6
    MAX-ACCESS read-create
    STATUS     current
    DESCRIPTION
        "The value of tmnxCcIpv6FltrSourceIpAddr specifies the IP address to
         match the source-ip of the packet.

         This field can only be set if the value of tmnxCcIpv6FltrDirection is set
         to egress."
    DEFVAL { '00000000000000000000000000000000'H }
    ::= { tmnxSubCredCatIpv6FltrEntry 10 }

tmnxCcIpv6FltrSourceIpMask OBJECT-TYPE
    SYNTAX     InetAddressPrefixLength (0..128)
    MAX-ACCESS read-create
    STATUS     current
    DESCRIPTION
        "The value of tmnxCcIpv6FltrSourceIpMask specifies the IP Mask value
         for this policy IPv6 Filter entry. The mask is ANDed with the received
         source IP address to match the tmnxCcIpv6FltrSourceIpAddr.

         The default value of 0 disables matching on the Source IP address.

         This field can only be set if the value of tmnxCcIpv6FltrDirection is set
         to egress."
    DEFVAL { 0 }
    ::= { tmnxSubCredCatIpv6FltrEntry 11 }

tmnxCcIpv6FltrDestinationIpAddr OBJECT-TYPE
    SYNTAX     InetAddressIPv6
    MAX-ACCESS read-create
    STATUS     current
    DESCRIPTION
        "The value of tmnxCcIpv6FltrDestinationIpAddr specifies the IP address
         to match the destination-ip of the packet.

         This field can only be set if the value of tmnxCcIpv6FltrDirection is set
         to ingress."
    DEFVAL { '00000000000000000000000000000000'H }
    ::= { tmnxSubCredCatIpv6FltrEntry 12 }

tmnxCcIpv6FltrDestinationIpMask OBJECT-TYPE
    SYNTAX     InetAddressPrefixLength (0..128)
    MAX-ACCESS read-create
    STATUS     current
    DESCRIPTION
        "The value of tmnxCcIpv6FltrDestinationIpMask specifies the IP Mask value
         for this policy IPv6 Filter entry. The mask is ANDed with the received
         destination IP address to match the tmnxCcIpv6FltrDestinationIpAddr.

         The default value of 0 disables matching on the destination IP address.

         This field can only be set if the value of tmnxCcIpv6FltrDirection is set
         to ingress."
    DEFVAL { 0 }
    ::= { tmnxSubCredCatIpv6FltrEntry 13 }

tmnxCcIpv6FltrSourcePortValue1 OBJECT-TYPE
    SYNTAX     TTcpUdpPort
    MAX-ACCESS read-create
    STATUS     current
    DESCRIPTION
        "The value of tmnxCcIpv6FltrSourcePortValue1 specifies the TCP/UDP port
         value1. The value of this object is used as per the description for
         tmnxCcIpv6FltrSourcePortOperator."
    DEFVAL { 0 }
    ::= { tmnxSubCredCatIpv6FltrEntry 14 }

tmnxCcIpv6FltrSourcePortValue2 OBJECT-TYPE
    SYNTAX     TTcpUdpPort
    MAX-ACCESS read-create
    STATUS     current
    DESCRIPTION
        "The value of tmnxCcIpv6FltrSourcePortValue2 specifies the TCP/UDP port
         value2. The value of this object is used as per the description for
         tmnxCcIpv6FltrSourcePortOperator."
    DEFVAL { 0 }
    ::= { tmnxSubCredCatIpv6FltrEntry 15 }

tmnxCcIpv6FltrSourcePortOperator OBJECT-TYPE
    SYNTAX     TTcpUdpPortOperator
    MAX-ACCESS read-create
    STATUS     current
    DESCRIPTION
        "The value of tmnxCcIpv6FltrSourcePortOperator specifies the manner in
         which tmnxCcIpv6FltrSourcePortValue1 and tmnxCcIpv6FltrSourcePortValue2
         are to be used. The value of these latter 2 objects and
         tIPFilterParamsSourcePortOperator is used as described in
         TTcpUdpPortOperator."
    DEFVAL { none }
    ::= { tmnxSubCredCatIpv6FltrEntry 16 }

tmnxCcIpv6FltrDestPortValue1 OBJECT-TYPE
    SYNTAX     TTcpUdpPort
    MAX-ACCESS read-create
    STATUS     current
    DESCRIPTION
        "The value of tmnxCcIpv6FltrDestPortValue1 specifies the TCP/UDP
         port value1. The value of this object is used as per the description
         for tmnxCcIpv6FltrDestPortOperator."
    DEFVAL { 0 }
    ::= { tmnxSubCredCatIpv6FltrEntry 17 }

tmnxCcIpv6FltrDestPortValue2 OBJECT-TYPE
    SYNTAX     TTcpUdpPort
    MAX-ACCESS read-create
    STATUS     current
    DESCRIPTION
    "The value of tmnxCcIpv6FltrDestPortValue2 specifies the TCP/UDP
     port value2. The value of this object is used as per the description
     for tmnxCcIpv6FltrDestPortOperator."
    DEFVAL { 0 }
    ::= { tmnxSubCredCatIpv6FltrEntry 18 }

tmnxCcIpv6FltrDestPortOperator OBJECT-TYPE
    SYNTAX     TTcpUdpPortOperator
    MAX-ACCESS read-create
    STATUS     current
    DESCRIPTION
    "The value of tmnxCcIpv6FltrDestPortOperator specifies the manner in
     which tmnxCcIpv6FltrDestPortValue1 and
     tmnxCcIpv6FltrDestPortValue2 are to be used. The value of these latter
     2 objects and tmnxCcIpv6FltrDestPortOperator is used as described in
     TTcpUdpPortOperator."
    DEFVAL { none }
    ::= { tmnxSubCredCatIpv6FltrEntry 19 }

tmnxCcIpv6FltrIcmpCode OBJECT-TYPE
    SYNTAX     INTEGER (-1|0..255)
    MAX-ACCESS read-create
    STATUS     current
    DESCRIPTION
        "The value of tmnxCcIpv6FltrIcmpCode specifies the icmp code to be
         matched. tmnxCcIpv6FltrIcmpCode complements the object
         tmnxCcIpv6FltrIcmpType. Both of them need to be set to actually
         enable ICMP matching.

         The default value of -1 disables ICMP matching."
    DEFVAL { -1 }
    ::= { tmnxSubCredCatIpv6FltrEntry 20 }

tmnxCcIpv6FltrIcmpType OBJECT-TYPE
    SYNTAX     INTEGER (-1|0..255)
    MAX-ACCESS read-create
    STATUS     current
    DESCRIPTION
        "The value of tmnxCcIpv6FltrIcmpType specifies the icmp type to be
         matched. tmnxCcIpv6FltrIcmpType complements the object
         tmnxCcIpv6FltrIcmpCode. Both of them need to be set to actually
         enable ICMP matching.

         The default value of -1 disables ICMP matching."
    DEFVAL { -1 }
    ::= { tmnxSubCredCatIpv6FltrEntry 21 }

tmnxCcIpv6FltrTcpSyn OBJECT-TYPE
    SYNTAX     TItemMatch
    MAX-ACCESS read-create
    STATUS     current
    DESCRIPTION
        "The value of tmnxCcIpv6FltrTcpSyn specifies whether the control bits of
         the TCP header should contain the SYN bit.
    
         The default value of 'off(1)' disables checking for the SYN bit."
    DEFVAL { off }
    ::= { tmnxSubCredCatIpv6FltrEntry 22 }

tmnxCcIpv6FltrTcpAck OBJECT-TYPE
    SYNTAX     TItemMatch
    MAX-ACCESS read-create
    STATUS     current
    DESCRIPTION
        "The value of tmnxCcIpv6FltrTcpAck specifies whether the control bits of
         the TCP header should contain the ACK bit.
  
         The default value of 'off(1)' disables checking for the ACK bit."
    DEFVAL { off }
    ::= { tmnxSubCredCatIpv6FltrEntry 23 }

-- ------------------------------------------------
-- tmnxSubV6GrpIfRATable
-- ------------------------------------------------
tmnxSubV6GrpIfRATableLastChange OBJECT-TYPE
    SYNTAX      TimeStamp
    MAX-ACCESS  read-only
    STATUS      current
    DESCRIPTION
      "The value of tmnxSubV6GrpIfRATableLastChange indicates the sysUpTime
       at the time of the last modification of tmnxSubV6GrpIfRATable.

       If no changes were made to the entry since the last
       re-initialization of the local network management subsystem,
       then this object contains a zero value."
    ::= { tmnxSubMgmtObjects 70 }

tmnxSubV6GrpIfRATable OBJECT-TYPE
    SYNTAX      SEQUENCE OF TmnxSubV6GrpIfRAEntry
    MAX-ACCESS  not-accessible
    STATUS      current
    DESCRIPTION
      "A table configuring Router Advertisements for Neighbor Discovery in IPv6.
      
       Applies to IES and VPRN Group Interfaces.
   
       A row is automatically created in tmnxSubV6GrpIfRATable for each entry
       in iesIfTable where the value of the object iesIfType equals 'group (3)'."
    ::= { tmnxSubMgmtObjects 71 }

tmnxSubV6GrpIfRAEntry OBJECT-TYPE
    SYNTAX      TmnxSubV6GrpIfRAEntry
    MAX-ACCESS  not-accessible
    STATUS      current
    DESCRIPTION 
      "Information about the Router Advertisement configuration for 
       Neighbor Discovery in IPv6 for a particular IES or VPRN Group Interface."
    INDEX { svcId,
            iesIfIndex }
    ::= { tmnxSubV6GrpIfRATable 1 }

TmnxSubV6GrpIfRAEntry ::= SEQUENCE
{
    tmnxSubV6GrpIfRALastChanged        TimeStamp,
    tmnxSubV6GrpIfRAAdminState         TmnxAdminState,
    tmnxSubV6GrpIfRACurHopLimit        Unsigned32,
    tmnxSubV6GrpIfRAManagedCfg         TruthValue,
    tmnxSubV6GrpIfRAMaxInterval        Unsigned32,
    tmnxSubV6GrpIfRAMinInterval        Unsigned32,
    tmnxSubV6GrpIfRALinkMTU            Unsigned32,
    tmnxSubV6GrpIfRAOtherCfg           TruthValue,
    tmnxSubV6GrpIfRAPfxOptAutonomous   TruthValue,
    tmnxSubV6GrpIfRAPfxOptPrefLtime    Unsigned32,
    tmnxSubV6GrpIfRAPfxOptValidLtime   Unsigned32,
    tmnxSubV6GrpIfRAReachableTime      Unsigned32,
    tmnxSubV6GrpIfRARetransmitTime     Unsigned32,
    tmnxSubV6GrpIfRARouterLifetime     Unsigned32,
    tmnxSubV6GrpIfRADnsOptInclDns      TruthValue,
    tmnxSubV6GrpIfRADnsOptRdnssLtime   Integer32,
    tmnxSubV6GrpIfRAForceMcast         BITS,
    tmnxSubV6GrpIfRAPfxOptOnLink       TruthValue
}

tmnxSubV6GrpIfRALastChanged OBJECT-TYPE
    SYNTAX     TimeStamp
    MAX-ACCESS read-only
    STATUS     current
    DESCRIPTION
      "The value of tmnxSubV6GrpIfRALastChanged indicates the sysUpTime when
       an object in this table row was last modified. A Value 0 means that
       no change was made to this row since the box was last initialized."
    ::= { tmnxSubV6GrpIfRAEntry 1 }

tmnxSubV6GrpIfRAAdminState OBJECT-TYPE
    SYNTAX     TmnxAdminState
    MAX-ACCESS read-write
    STATUS     current
    DESCRIPTION
      "The value of tmnxSubV6GrpIfRAAdminState specifies the desired administrative
       state of the IPv6 Router Advertisements."
    DEFVAL { outOfService }
    ::= { tmnxSubV6GrpIfRAEntry 2 }

tmnxSubV6GrpIfRACurHopLimit OBJECT-TYPE
    SYNTAX     Unsigned32 (0..255)
    MAX-ACCESS read-write
    STATUS     current
    DESCRIPTION
      "The value of tmnxSubV6GrpIfRACurHopLimit specifies the default value to be 
       placed in the current hop limit field in router advertisements sent from this interface."
    REFERENCE "RFC4861 Section 6.2.1"
    DEFVAL { 64 }
    ::= { tmnxSubV6GrpIfRAEntry 3 }

tmnxSubV6GrpIfRAManagedCfg OBJECT-TYPE
    SYNTAX     TruthValue
    MAX-ACCESS read-write
    STATUS     current
    DESCRIPTION
      "The value of tmnxSubV6GrpIfRAManagedCfg specifies a 1 (true) or 0 (false) value
       to be placed into the 'managed address configuration' flag field in router
       advertisements sent from this interface."
    REFERENCE "RFC4861 Section 6.2.1"
    DEFVAL { false }
    ::= { tmnxSubV6GrpIfRAEntry 4 }

tmnxSubV6GrpIfRAMaxInterval OBJECT-TYPE
    SYNTAX     Unsigned32 (900..1800)
    UNITS      "seconds"
    MAX-ACCESS read-write
    STATUS     current
    DESCRIPTION
      "The value of tmnxSubV6GrpIfRAMaxInterval specifies the maximum time allowed between
       sending unsolicited router advertisements from this interface.

       The value of tmnxSubV6GrpIfRAMaxInterval shall not be smaller
       than the value of tmnxSubV6GrpIfRAMinInterval."
    REFERENCE "RFC4861 Section 6.2.1"
    DEFVAL { 1800 }
    ::= { tmnxSubV6GrpIfRAEntry 5 }

tmnxSubV6GrpIfRAMinInterval OBJECT-TYPE
    SYNTAX     Unsigned32 (900..1350)
    UNITS      "seconds"
    MAX-ACCESS read-write
    STATUS     current
    DESCRIPTION
      "The value of tmnxSubV6GrpIfRAMinInterval specifies the minimum time allowed between
       sending unsolicited router advertisements from this interface.

       The value of tmnxSubV6GrpIfRAMinInterval shall not be greater
       than the value of tmnxSubV6GrpIfRAMaxInterval."
    REFERENCE "RFC4861 Section 6.2.1"
    DEFVAL { 900 }
    ::= { tmnxSubV6GrpIfRAEntry 6 }

tmnxSubV6GrpIfRALinkMTU OBJECT-TYPE
    SYNTAX     Unsigned32 (0|1280..9212)
    UNITS      "bytes"
    MAX-ACCESS read-write
    STATUS     current
    DESCRIPTION
      "The value of tmnxSubV6GrpIfRALinkMTU specifies the value to be placed in link MTU
       options sent by the router on this interface.

       A value of zero indicates that no MTU options are sent."
    REFERENCE "RFC4861 Section 6.2.1"
    DEFVAL { 0 }
    ::= { tmnxSubV6GrpIfRAEntry 7 }

tmnxSubV6GrpIfRAOtherCfg OBJECT-TYPE
    SYNTAX     TruthValue
    MAX-ACCESS read-write
    STATUS     current
    DESCRIPTION
      "The value of tmnxSubV6GrpIfRAOtherCfg specifies a 1 (true) or 0 (false) value 
       to be placed into the 'other stateful configuration' flag field in router
       advertisements sent from this interface."
    REFERENCE "RFC4861 Section 6.2.1"
    DEFVAL { false }
    ::= { tmnxSubV6GrpIfRAEntry 8 }

tmnxSubV6GrpIfRAPfxOptAutonomous OBJECT-TYPE
    SYNTAX     TruthValue
    MAX-ACCESS read-write
    STATUS     current
    DESCRIPTION
      "The value of tmnxSubV6GrpIfRAPfxOptAutonomous specifies a true or false value
       that determines whether the prefix can be used for stateless address autoconfiguration."
    REFERENCE "RFC4861 Section 6.2.1"
    DEFVAL { false }
    ::= { tmnxSubV6GrpIfRAEntry 9 }

tmnxSubV6GrpIfRAPfxOptPrefLtime OBJECT-TYPE
    SYNTAX     Unsigned32
    UNITS      "seconds"
    MAX-ACCESS read-write
    STATUS     current
    DESCRIPTION
      "The value of tmnxSubV6GrpIfRAPfxOptPrefLtime specifies the remaining time for this prefix to
       be preferred, thus time until deprecation."
    REFERENCE "RFC4861 Section 6.2.1"
    DEFVAL { 3600 }
    ::= { tmnxSubV6GrpIfRAEntry 10 }

tmnxSubV6GrpIfRAPfxOptValidLtime OBJECT-TYPE
    SYNTAX     Unsigned32
    UNITS      "seconds"
    MAX-ACCESS read-write
    STATUS     current
    DESCRIPTION
      "The value of tmnxSubV6GrpIfRAPfxOptValidLtime specifies the remaining time for this prefix to
       be valid for the purpose of on-link determination.
            
       A value of 0xFFFFFFFF represents infinity."
    REFERENCE "RFC4861 Section 6.2.1"
    DEFVAL { 86400 }
    ::= { tmnxSubV6GrpIfRAEntry 11 }

tmnxSubV6GrpIfRAReachableTime OBJECT-TYPE
    SYNTAX     Unsigned32 (0..3600000)
    UNITS      "milliseconds"
    MAX-ACCESS read-write
    STATUS     current
    DESCRIPTION
      "The value of tmnxSubV6GrpIfRAReachableTime specifies the value to be placed in the reachable
       time field in router advertisement messages sent from this interface.

       A value of zero in the router advertisement indicates that
       the advertisement isn't specifying a value for reachable time."
    REFERENCE "RFC4861 Section 6.2.1"
    DEFVAL { 0 }
    ::= { tmnxSubV6GrpIfRAEntry 12 }

tmnxSubV6GrpIfRARetransmitTime OBJECT-TYPE
    SYNTAX     Unsigned32 (0..1800000)
    UNITS      "milliseconds"
    MAX-ACCESS read-write
    STATUS     current
    DESCRIPTION
      "The value of tmnxSubV6GrpIfRARetransmitTime specifies the value to be placed in the retransmit
       timer field in router advertisements sent from this interface.

       A value of zero in the router advertisement indicates that
       the advertisement isn't specifying a value for retransmit time."
    REFERENCE "RFC4861 Section 6.2.1"
    DEFVAL { 0 }
    ::= { tmnxSubV6GrpIfRAEntry 13 }

tmnxSubV6GrpIfRARouterLifetime OBJECT-TYPE
    SYNTAX     Unsigned32 (0|2700..9000)
    UNITS      "seconds"
    MAX-ACCESS read-write
    STATUS     current
    DESCRIPTION
      "The value of tmnxSubV6GrpIfRARouterLifetime specifies the value to be placed in the router 
       lifetime field of router advertisements sent from this interface.

       A value of zero indicates that the router is not to be used
       as a default router."
    REFERENCE "RFC4861 Section 6.2.1"
    DEFVAL { 4500 }
    ::= { tmnxSubV6GrpIfRAEntry 14 }

tmnxSubV6GrpIfRADnsOptInclDns OBJECT-TYPE
    SYNTAX     TruthValue
    MAX-ACCESS read-write
    STATUS     current
    DESCRIPTION
      "The value of tmnxSubV6GrpIfRADnsOptInclDns specifies whether The RDNSS
       server option '25' is included in the router advertisements sent from 
       this interface."
    REFERENCE "RFC6106 Section 5.1"
    DEFVAL { false }
    ::= { tmnxSubV6GrpIfRAEntry 15 }
    
tmnxSubV6GrpIfRADnsOptRdnssLtime OBJECT-TYPE
    SYNTAX     Integer32 (-1|900..3600)
    UNITS      "seconds"
    MAX-ACCESS read-write
    STATUS     current
    DESCRIPTION
      "The value of tmnxSubV6GrpIfRADnsOptRdnssLtime specifies the maximum time
       in seconds over which the RDNSS address in the RDNSS server option '25'
       is valid.

       A value of '-1' indicates that the lifetime is set to infinite."
    REFERENCE "RFC6106 Section 5.1"
    DEFVAL { 3600 }
    ::= { tmnxSubV6GrpIfRAEntry 16 }
    
tmnxSubV6GrpIfRAForceMcast OBJECT-TYPE
    SYNTAX     BITS { 
                   ip    (0),
                   mac   (1)
               }
    MAX-ACCESS read-write
    STATUS     current
    DESCRIPTION
      "The value of tmnxSubV6GrpIfRAForceMcast specifies the protcols
       for which multicast will be forced."
    DEFVAL { { } }
    ::= { tmnxSubV6GrpIfRAEntry 17 }

tmnxSubV6GrpIfRAPfxOptOnLink OBJECT-TYPE
    SYNTAX     TruthValue
    MAX-ACCESS read-write
    STATUS     current
    DESCRIPTION
      "The value of tmnxSubV6GrpIfRAPfxOptOnLink specifies whether the prefix will be
       assigned to an interface on the specified link."
    DEFVAL { true }
    ::= { tmnxSubV6GrpIfRAEntry 18 }

-- --------------------------------------------------------
-- tmnxSLAIngPolicerOverrideTable
-- --------------------------------------------------------
tmnxSLAIngPlcrOverrideTblLstChng OBJECT-TYPE
    SYNTAX      TimeStamp
    MAX-ACCESS  read-only
    STATUS      current
    DESCRIPTION
      "The value of tmnxSLAIngPlcrOverrideTblLstChng indicates the sysUpTime
       at the time of the last modification of tmnxSLAIngPolicerOverrideTable.

       If no changes were made to the entry since the last
       re-initialization of the local network management subsystem,
       then this object contains a zero value."
    ::= { tmnxSubMgmtObjects 72 }

tmnxSLAIngPolicerOverrideTable OBJECT-TYPE
    SYNTAX      SEQUENCE OF TmnxSLAIngPolicerOverrideEntry
    MAX-ACCESS  not-accessible
    STATUS      current
    DESCRIPTION
        "The tmnxSLAIngPolicerOverrideTable allows overriding of ingress QoS
         policy policer parameters on a per SLA profile basis."
    ::= { tmnxSubMgmtObjects 73 }

tmnxSLAIngPolicerOverrideEntry OBJECT-TYPE
    SYNTAX      TmnxSLAIngPolicerOverrideEntry
    MAX-ACCESS  not-accessible
    STATUS      current
    DESCRIPTION
        "Each entry of the tmnxSLAIngPolicerOverrideTable describes policer
         parameters which override the corresponding template policer
         parameters from the specified ingress QoS policy. Rows can be created
         and deleted by the operator (tmnxSLAIngPolicerOvrRowStatus). Rows can
         only be created for policers that exist in table
         TIMETRA-QOS-MIB::tSapIngPolicerTable."
    INDEX { tmnxSLAProfName,
            tSapIngressIndex,
            tSapIngPolicerId }
    ::= { tmnxSLAIngPolicerOverrideTable 1 }

TmnxSLAIngPolicerOverrideEntry ::=
    SEQUENCE {
        tmnxSLAIngPolicerOvrRowStatus    RowStatus,
        tmnxSLAIngPolicerOvrLastMgmtChg  TimeStamp,
        tmnxSLAIngPolicerOvrPIR          THPolPIRRateOverride,
        tmnxSLAIngPolicerOvrCIR          THPolCIRRateOverride,
        tmnxSLAIngPolicerOvrMBS          TPlcrBurstSizeBytesOverride,
        tmnxSLAIngPolicerOvrCBS          TPlcrBurstSizeBytesOverride,
        tmnxSLAIngPolicerOvrPktOffset    TPerPacketOffsetOvr,
        tmnxSLAIngPolicerOvrStatMode     INTEGER
    }

tmnxSLAIngPolicerOvrRowStatus OBJECT-TYPE
    SYNTAX      RowStatus
    MAX-ACCESS  read-create
    STATUS      current
    DESCRIPTION
        "The value of tmnxSLAIngPolicerOvrRowStatus controls the creation and
         deletion of rows in this table."
    ::= { tmnxSLAIngPolicerOverrideEntry 1 }

tmnxSLAIngPolicerOvrLastMgmtChg OBJECT-TYPE
    SYNTAX      TimeStamp
    MAX-ACCESS  read-only
    STATUS      current
    DESCRIPTION
        "The value of tmnxSLAIngPolicerOvrLastMgmtChg indicates the
         sysUpTime at the time of the most recent management-initiated change
         to this table row."
    ::= { tmnxSLAIngPolicerOverrideEntry 2 }

tmnxSLAIngPolicerOvrPIR OBJECT-TYPE
    SYNTAX      THPolPIRRateOverride
    UNITS       "kbps"
    MAX-ACCESS  read-create
    STATUS      current
    DESCRIPTION
        "The value of tmnxSLAIngPolicerOvrPIR specifies the PIR rate in kbps
         allowed for this policer."
    DEFVAL { -2 }
    ::= { tmnxSLAIngPolicerOverrideEntry 3 }

tmnxSLAIngPolicerOvrCIR OBJECT-TYPE
    SYNTAX      THPolCIRRateOverride
    UNITS       "kbps"
    MAX-ACCESS  read-create
    STATUS      current
    DESCRIPTION
        "The value of tmnxSLAIngPolicerOvrCIR specifies the CIR rate in kbps
         allowed for this policer."
    DEFVAL { -2 }
    ::= { tmnxSLAIngPolicerOverrideEntry 4 }

tmnxSLAIngPolicerOvrMBS OBJECT-TYPE
    SYNTAX      TPlcrBurstSizeBytesOverride
    UNITS       "bytes"
    MAX-ACCESS  read-create
    STATUS      current
    DESCRIPTION
        "The value of tmnxSLAIngPolicerOvrMBS specifies the maximum amount of
         buffer space (in bytes) allowed for the policer."
    DEFVAL { -2 }
    ::= { tmnxSLAIngPolicerOverrideEntry 5 }

tmnxSLAIngPolicerOvrCBS OBJECT-TYPE
    SYNTAX      TPlcrBurstSizeBytesOverride
    UNITS       "bytes"
    MAX-ACCESS  read-create
    STATUS      current
    DESCRIPTION
        "The value of tmnxSLAIngPolicerOvrCBS specifies the amount of reserved
         buffer space (in bytes) for the policer."
    DEFVAL { -2 }
    ::= { tmnxSLAIngPolicerOverrideEntry 6 }

tmnxSLAIngPolicerOvrPktOffset OBJECT-TYPE
    SYNTAX      TPerPacketOffsetOvr
    MAX-ACCESS  read-create
    STATUS      current
    DESCRIPTION
        "The value of tmnxSLAIngPolicerOvrPktOffset specifies the packet byte
         offset for addition of policing information for the policer."
    DEFVAL { -128 }
    ::= { tmnxSLAIngPolicerOverrideEntry 7 }

tmnxSLAIngPolicerOvrStatMode OBJECT-TYPE
    SYNTAX      INTEGER {
                    noOverride               (-1),
                    noStats                  (0),
                    minimal                  (1),
                    offeredProfileNoCIR      (2),
                    offeredTotalCIR          (3),
                    offeredPriorityNoCIR     (4),
                    offeredProfileCIR        (5),
                    offeredPriorityCIR       (6),
                    offeredLimitedProfileCIR (7),
                    offeredProfileCappedCIR  (8),
                    offeredLimitedCappedCIR  (9),
                    v4V6                     (10)
                }
    MAX-ACCESS  read-create
    STATUS      current
    DESCRIPTION
        "The value of tmnxSLAIngPolicerOvrStatMode specifies the mode of
         statistics collected for the policer."
    DEFVAL { noOverride }
    ::= { tmnxSLAIngPolicerOverrideEntry 8 }

-- --------------------------------------------------------
-- tmnxSLAEgrPolicerOverrideTable
-- --------------------------------------------------------
tmnxSLAEgrPlcrOverrideTblLstChng OBJECT-TYPE
    SYNTAX      TimeStamp
    MAX-ACCESS  read-only
    STATUS      current
    DESCRIPTION
      "The value of tmnxSLAEgrPlcrOverrideTblLstChng indicates the sysUpTime
       at the time of the last modification of tmnxSLAIngPolicerOverrideTable.

       If no changes were made to the entry since the last
       re-initialization of the local network management subsystem,
       then this object contains a zero value."
    ::= { tmnxSubMgmtObjects 74 }

tmnxSLAEgrPolicerOverrideTable OBJECT-TYPE
    SYNTAX      SEQUENCE OF TmnxSLAEgrPolicerOverrideEntry
    MAX-ACCESS  not-accessible
    STATUS      current
    DESCRIPTION
        "The tmnxSLAEgrPolicerOverrideTable allows overriding of egress QoS
         policy policer parameters on a per SLA profile basis."
    ::= { tmnxSubMgmtObjects 75 }

tmnxSLAEgrPolicerOverrideEntry OBJECT-TYPE
    SYNTAX      TmnxSLAEgrPolicerOverrideEntry
    MAX-ACCESS  not-accessible
    STATUS      current
    DESCRIPTION
        "Each entry of the tmnxSLAEgrPolicerOverrideTable describes policer
         parameters which override the corresponding template policer
         parameters from the specified egress QoS policy. Rows can be created
         and deleted by the operator (tmnxSLAEgrPolicerOvrRowStatus). Rows can
         only be created for policers that exist in table
         TIMETRA-QOS-MIB::tSapEgrPolicerTable."
    INDEX { tmnxSLAProfName,
            tSapEgressIndex,
            tSapEgrPolicerId }
    ::= { tmnxSLAEgrPolicerOverrideTable 1 }

TmnxSLAEgrPolicerOverrideEntry ::=
    SEQUENCE {
        tmnxSLAEgrPolicerOvrRowStatus    RowStatus,
        tmnxSLAEgrPolicerOvrLastMgmtChg  TimeStamp,
        tmnxSLAEgrPolicerOvrPIR          THPolPIRRateOverride,
        tmnxSLAEgrPolicerOvrCIR          THPolCIRRateOverride,
        tmnxSLAEgrPolicerOvrMBS          TPlcrBurstSizeBytesOverride,
        tmnxSLAEgrPolicerOvrCBS          TPlcrBurstSizeBytesOverride,
        tmnxSLAEgrPolicerOvrPktOffset    TEgressPerPacketOffsetOvr,
        tmnxSLAEgrPolicerOvrStatMode     INTEGER        
    }

tmnxSLAEgrPolicerOvrRowStatus OBJECT-TYPE
    SYNTAX      RowStatus
    MAX-ACCESS  read-create
    STATUS      current
    DESCRIPTION
        "The value of tmnxSLAEgrPolicerOvrRowStatus controls the creation and
         deletion of rows in this table."
    ::= { tmnxSLAEgrPolicerOverrideEntry 1 }

tmnxSLAEgrPolicerOvrLastMgmtChg OBJECT-TYPE
    SYNTAX      TimeStamp
    MAX-ACCESS  read-only
    STATUS      current
    DESCRIPTION
        "The value of tmnxSLAEgrPolicerOvrLastMgmtChg indicates the
         sysUpTime at the time of the most recent management-initiated change
         to this table row."
    ::= { tmnxSLAEgrPolicerOverrideEntry 2 }

tmnxSLAEgrPolicerOvrPIR OBJECT-TYPE
    SYNTAX      THPolPIRRateOverride
    UNITS       "kbps"
    MAX-ACCESS  read-create
    STATUS      current
    DESCRIPTION
        "The value of tmnxSLAEgrPolicerOvrPIR specifies the PIR rate in kbps
         allowed for this policer."
    DEFVAL { -2 }
    ::= { tmnxSLAEgrPolicerOverrideEntry 3 }

tmnxSLAEgrPolicerOvrCIR OBJECT-TYPE
    SYNTAX      THPolCIRRateOverride
    UNITS       "kbps"
    MAX-ACCESS  read-create
    STATUS      current
    DESCRIPTION
        "The value of tmnxSLAEgrPolicerOvrCIR specifies the CIR rate in kbps
         allowed for this policer."
    DEFVAL { -2 }
    ::= { tmnxSLAEgrPolicerOverrideEntry 4 }

tmnxSLAEgrPolicerOvrMBS OBJECT-TYPE
    SYNTAX      TPlcrBurstSizeBytesOverride
    UNITS       "bytes"
    MAX-ACCESS  read-create
    STATUS      current
    DESCRIPTION
        "The value of tmnxSLAEgrPolicerOvrMBS specifies the maximum amount of
         buffer space (in bytes) allowed for the policer."
    DEFVAL { -2 }
    ::= { tmnxSLAEgrPolicerOverrideEntry 5 }

tmnxSLAEgrPolicerOvrCBS OBJECT-TYPE
    SYNTAX      TPlcrBurstSizeBytesOverride
    UNITS       "bytes"
    MAX-ACCESS  read-create
    STATUS      current
    DESCRIPTION
        "The value of tmnxSLAEgrPolicerOvrCBS specifies the amount of reserved
         buffer space (in bytes) for the policer."
    DEFVAL { -2 }
    ::= { tmnxSLAEgrPolicerOverrideEntry 6 }

tmnxSLAEgrPolicerOvrPktOffset OBJECT-TYPE
    SYNTAX       TEgressPerPacketOffsetOvr
    MAX-ACCESS  read-create
    STATUS      current
    DESCRIPTION
        "The value of tmnxSLAEgrPolicerOvrPktOffset specifies the packet byte
         offset for addition of policing information for the policer."
    DEFVAL { -128 }
    ::= { tmnxSLAEgrPolicerOverrideEntry 7 }

tmnxSLAEgrPolicerOvrStatMode OBJECT-TYPE
    SYNTAX      INTEGER {
                    noOverride          (-1),
                    noStats             (0),
                    minimal             (1),
                    offeredProfileNoCIR (2),
                    offeredTotalCIR     (3),
                    offeredProfileCIR   (4),
                    offeredLimitedCappedCIR(5),
                    offeredProfileCappedCIR(6),
                    v4V6                   (7)
                }
    MAX-ACCESS  read-create
    STATUS      current
    DESCRIPTION
        "The value of tmnxSLAEgrPolicerOvrStatMode specifies the mode of
         statistics collected for the policer."
    DEFVAL { noOverride }
    ::= { tmnxSLAEgrPolicerOverrideEntry 8 }

-- --------------------------------------------------------
-- tmnxSubProfPolicerCtrlOvrTable
-- --------------------------------------------------------
tmnxSubProfPCtrlOvrTblLstChng OBJECT-TYPE
    SYNTAX      TimeStamp
    MAX-ACCESS  read-only
    STATUS      current
    DESCRIPTION
      "The value of tmnxSubProfPCtrlOvrTblLstChng indicates the sysUpTime at
       the time of the last modification of tmnxSubProfPolicerCtrlOvrTable.

       If no changes were made to the entry since the last
       re-initialization of the local network management subsystem, then this
       object contains a zero value."
    ::= { tmnxSubMgmtObjects 76 }

tmnxSubProfPolicerCtrlOvrTable OBJECT-TYPE
    SYNTAX      SEQUENCE OF TmnxSubProfPolicerCtrlOvrEntry
    MAX-ACCESS  not-accessible
    STATUS      current
    DESCRIPTION
        "The tmnxSubProfPolicerCtrlOvrTable allows overriding of ingress/egress
         root policers on a per subscriber profile basis."
    ::= { tmnxSubMgmtObjects 77 }

tmnxSubProfPolicerCtrlOvrEntry OBJECT-TYPE
    SYNTAX      TmnxSubProfPolicerCtrlOvrEntry
    MAX-ACCESS  not-accessible
    STATUS      current
    DESCRIPTION
        "Each entry of the tmnxSubProfPolicerCtrlOvrTable describes
         ingress/egress root policers which are overridden for the subscriber
         profile indicated by tmnxSubProfName. Rows can be created and deleted
         by the operator (tmnxSubProfPCtrlOvrRowStatus)."
    INDEX { tmnxSubProfName,
            tmnxSubProfPCtrlOvrDirection,
            tQosPolicerCtrlPolName }
    ::= { tmnxSubProfPolicerCtrlOvrTable 1 }

TmnxSubProfPolicerCtrlOvrEntry ::=
    SEQUENCE {
        tmnxSubProfPCtrlOvrDirection  TmnxSubDirection,
        tmnxSubProfPCtrlOvrRowStatus  RowStatus,
        tmnxSubProfPCtrlOvrLastChange TimeStamp,
        tmnxSubProfPCtrlOvrMaxRate    THPolPIRRateOverride,
        tmnxSubProfPCtrlOvrMinMBSSep  TPlcrBurstSizeBytesOverride
    }

tmnxSubProfPCtrlOvrDirection OBJECT-TYPE
    SYNTAX      TmnxSubDirection
    MAX-ACCESS  not-accessible
    STATUS      current
    DESCRIPTION
        "The value of tmnxSubProfPCtrlOvrDirection indicates whether this
         row specifies ingress or egress policer control override parameters."
    ::= { tmnxSubProfPolicerCtrlOvrEntry 1 }

tmnxSubProfPCtrlOvrRowStatus OBJECT-TYPE
    SYNTAX      RowStatus
    MAX-ACCESS  read-create
    STATUS      current
    DESCRIPTION
        "The value of tmnxSubProfPCtrlOvrRowStatus controls the creation and
         deletion of rows in this table."
    ::= { tmnxSubProfPolicerCtrlOvrEntry 2 }

tmnxSubProfPCtrlOvrLastChange OBJECT-TYPE
    SYNTAX      TimeStamp
    MAX-ACCESS  read-only
    STATUS      current
    DESCRIPTION
        "The value of tmnxSubProfPCtrlOvrLastChange indicates the sysUpTime at
         the time of the most recent management-initiated change to this table
         row."
    ::= { tmnxSubProfPolicerCtrlOvrEntry 3 }

tmnxSubProfPCtrlOvrMaxRate OBJECT-TYPE
    SYNTAX      THPolPIRRateOverride
    UNITS       "kbps"
    MAX-ACCESS  read-create
    STATUS      current
    DESCRIPTION
        "The value of tmnxSubProfPCtrlOvrMaxRate specifies the maximum frame
         based bandwidth limit of this policer."
    DEFVAL { -2 }
    ::= { tmnxSubProfPolicerCtrlOvrEntry 4 }

tmnxSubProfPCtrlOvrMinMBSSep OBJECT-TYPE
    SYNTAX      TPlcrBurstSizeBytesOverride
    UNITS       "bytes"
    MAX-ACCESS  read-create
    STATUS      current
    DESCRIPTION
        "The value of tmnxSubProfPCtrlOvrMinMBSSep specifies the minimum amount
         of seperation buffer space (in bytes) allowed by this policer."
    DEFVAL { -2 }
    ::= { tmnxSubProfPolicerCtrlOvrEntry 5 }

-- --------------------------------------------------------
-- tmnxSubProfPCtrlLevelOvrTable
-- --------------------------------------------------------
tmnxSubProfPCtrlLvlOvrTblLstChng OBJECT-TYPE
    SYNTAX      TimeStamp
    MAX-ACCESS  read-only
    STATUS      current
    DESCRIPTION
      "The value of tmnxSubProfPCtrlLvlOvrTblLstChng indicates the sysUpTime at
       the time of the last modification of tmnxSubProfPCtrlLevelOvrTable.

       If no changes were made to the entry since the last re-initialization of
       the local network management subsystem, then this object contains a zero
       value."
    ::= { tmnxSubMgmtObjects 78 }

tmnxSubProfPCtrlLevelOvrTable OBJECT-TYPE
    SYNTAX      SEQUENCE OF TmnxSubProfPCtrlLevelOvrEntry
    MAX-ACCESS  not-accessible
    STATUS      current
    DESCRIPTION
        "The tmnxSubProfPCtrlLevelOvrTable allows overriding of ingress/egress
         root policer levels on a per subscriber profile basis."
    ::= { tmnxSubMgmtObjects 79 }

tmnxSubProfPCtrlLevelOvrEntry OBJECT-TYPE
    SYNTAX      TmnxSubProfPCtrlLevelOvrEntry
    MAX-ACCESS  not-accessible
    STATUS      current
    DESCRIPTION
        "Each entry of the tmnxSubProfPCtrlLevelOvrTable describes
         ingress/egress root policer levels which are overridden for the
         subscriber profile indicated by tmnxSubProfName. Rows can be created
         and deleted by the operator (tmnxSubProfPCtrlLvlOvrRowStatus)."
    INDEX { tmnxSubProfName,
            tmnxSubProfPCtrlLvlOvrDirection,
            tQosPolicerCtrlPolName,
            tQosPolicerLevel }
    ::= { tmnxSubProfPCtrlLevelOvrTable 1 }

TmnxSubProfPCtrlLevelOvrEntry ::=
    SEQUENCE {
        tmnxSubProfPCtrlLvlOvrDirection  TmnxSubDirection,
        tmnxSubProfPCtrlLvlOvrRowStatus  RowStatus,
        tmnxSubProfPCtrlLvlOvrLastChange TimeStamp,
        tmnxSubProfPCtrlLvlOvrCumMBS     TPlcrBurstSizeBytesOverride
    }

tmnxSubProfPCtrlLvlOvrDirection OBJECT-TYPE
    SYNTAX      TmnxSubDirection
    MAX-ACCESS  not-accessible
    STATUS      current
    DESCRIPTION
        "The value of tmnxSubProfPCtrlLvlOvrDirection indicates whether this
         row specifies ingress or egress policer control level override
         parameters."
    ::= { tmnxSubProfPCtrlLevelOvrEntry 1 }

tmnxSubProfPCtrlLvlOvrRowStatus OBJECT-TYPE
    SYNTAX      RowStatus
    MAX-ACCESS  read-create
    STATUS      current
    DESCRIPTION
        "The value of tmnxSubProfPCtrlLvlOvrRowStatus controls the creation and
         deletion of rows in this table."
    ::= { tmnxSubProfPCtrlLevelOvrEntry 2 }

tmnxSubProfPCtrlLvlOvrLastChange OBJECT-TYPE
    SYNTAX      TimeStamp
    MAX-ACCESS  read-only
    STATUS      current
    DESCRIPTION
        "The value of tmnxSubProfPCtrlLvlOvrLastChange indicates the sysUpTime
         at the time of the most recent management-initiated change to this
         table row."
    ::= { tmnxSubProfPCtrlLevelOvrEntry 3 }

tmnxSubProfPCtrlLvlOvrCumMBS OBJECT-TYPE
    SYNTAX      TPlcrBurstSizeBytesOverride
    UNITS       "bytes"
    MAX-ACCESS  read-create
    STATUS      current
    DESCRIPTION
        "The value of tmnxSubProfPCtrlLvlOvrCumMBS specifies the maximum amount
         of cumulative buffer space (in bytes) allowed for this level by this
         policer."
    DEFVAL { -2 }
    ::= { tmnxSubProfPCtrlLevelOvrEntry 4 }


-- ----------------------------------------
-- tmnxSLAProfInstIngPStatsTable
-- ----------------------------------------
tmnxSLAProfInstIngPStatsTable OBJECT-TYPE
    SYNTAX      SEQUENCE OF TmnxSLAProfInstIngPStatsEntry
    MAX-ACCESS  not-accessible
    STATUS      current
    DESCRIPTION
        "The tmnxSLAProfInstIngPStatsTable contains ingress QoS policer
         statistics about SLA profile instances.
         In the descriptions below 'Pchip' refers to the Nokia SROS 
         series Packet Processing chip, while 'Qchip' refers to the 
         Nokia SROS series QoS Queueing Engine chip."
    ::= { tmnxSubMgmtObjects 80 }

tmnxSLAProfInstIngPStatsEntry OBJECT-TYPE
    SYNTAX      TmnxSLAProfInstIngPStatsEntry
    MAX-ACCESS  not-accessible
    STATUS      current
    DESCRIPTION
        "Each row entry contains ingress statistics about a particular SLA
         profile instance QoS policer."
    INDEX { tmnxSubInfoSubIdent,
            sapPortId,
            sapEncapValue,
            tmnxSLAProfName,
            tmnxSPIIngPStatsPolId }
    ::= { tmnxSLAProfInstIngPStatsTable 1 }

TmnxSLAProfInstIngPStatsEntry ::=
    SEQUENCE {
        tmnxSPIIngPStatsPolId            TIngressPolicerId,
        tmnxSPIIngPStatsMode             TmnxIngPolicerStatMode,
        tmnxSPIIngPStatsOffHiPrioPkts    Counter64,
        tmnxSPIIngPStatsOffHiPrioPktsL   Counter32,
        tmnxSPIIngPStatsOffHiPrioPktsH   Counter32,
        tmnxSPIIngPStatsDrpHiPrioPkts    Counter64,
        tmnxSPIIngPStatsDrpHiPrioPktsL   Counter32,
        tmnxSPIIngPStatsDrpHiPrioPktsH   Counter32,
        tmnxSPIIngPStatsOffLoPrioPkts    Counter64,
        tmnxSPIIngPStatsOffLoPrioPktsL   Counter32,
        tmnxSPIIngPStatsOffLoPrioPktsH   Counter32,
        tmnxSPIIngPStatsDrpLoPrioPkts    Counter64,
        tmnxSPIIngPStatsDrpLoPrioPktsL   Counter32,
        tmnxSPIIngPStatsDrpLoPrioPktsH   Counter32,
        tmnxSPIIngPStatsOffHiPrioOcts    Counter64,
        tmnxSPIIngPStatsOffHiPrioOctsL   Counter32,
        tmnxSPIIngPStatsOffHiPrioOctsH   Counter32,
        tmnxSPIIngPStatsDrpHiPrioOcts    Counter64,
        tmnxSPIIngPStatsDrpHiPrioOctsL   Counter32,
        tmnxSPIIngPStatsDrpHiPrioOctsH   Counter32,
        tmnxSPIIngPStatsOffLoPrioOcts    Counter64,
        tmnxSPIIngPStatsOffLoPrioOctsL   Counter32,
        tmnxSPIIngPStatsOffLoPrioOctsH   Counter32,
        tmnxSPIIngPStatsDrpLoPrioOcts    Counter64,
        tmnxSPIIngPStatsDrpLoPrioOctsL   Counter32,
        tmnxSPIIngPStatsDrpLoPrioOctsH   Counter32,
        tmnxSPIIngPStatsOffUncolPkts     Counter64,
        tmnxSPIIngPStatsOffUncolPktsL    Counter32,
        tmnxSPIIngPStatsOffUncolPktsH    Counter32,
        tmnxSPIIngPStatsOffUncolOcts     Counter64,
        tmnxSPIIngPStatsOffUncolOctsL    Counter32,
        tmnxSPIIngPStatsOffUncolOctsH    Counter32,
        tmnxSPIIngPStatsFwdInProfPkts    Counter64,
        tmnxSPIIngPStatsFwdInProfPktsL   Counter32,
        tmnxSPIIngPStatsFwdInProfPktsH   Counter32,
        tmnxSPIIngPStatsFwdOutProfPkts   Counter64,
        tmnxSPIIngPStatsFwdOutProfPktsL  Counter32,
        tmnxSPIIngPStatsFwdOutProfPktsH  Counter32,
        tmnxSPIIngPStatsFwdInProfOcts    Counter64,
        tmnxSPIIngPStatsFwdInProfOctsL   Counter32,
        tmnxSPIIngPStatsFwdInProfOctsH   Counter32,
        tmnxSPIIngPStatsFwdOutProfOcts   Counter64,
        tmnxSPIIngPStatsFwdOutProfOctsL  Counter32,
        tmnxSPIIngPStatsFwdOutProfOctsH  Counter32
    }

tmnxSPIIngPStatsPolId OBJECT-TYPE
    SYNTAX      TIngressPolicerId
    MAX-ACCESS  not-accessible
    STATUS      current
    DESCRIPTION
        "The value of tmnxSPIIngPStatsPolId specifies the index of the ingress QoS policer of this SLA profile instance."
    ::= { tmnxSLAProfInstIngPStatsEntry 1 }

tmnxSPIIngPStatsMode OBJECT-TYPE
    SYNTAX      TmnxIngPolicerStatMode
    MAX-ACCESS  read-only
    STATUS      current
    DESCRIPTION
        "The value of tmnxSPIIngPStatsMode indicates the stat mode used by the policer."
    ::= { tmnxSLAProfInstIngPStatsEntry 2 }

tmnxSPIIngPStatsOffHiPrioPkts OBJECT-TYPE
    SYNTAX      Counter64
    MAX-ACCESS  read-only
    STATUS      current
    DESCRIPTION
        "The value of tmnxSPIIngPStatsOffHiPrioPkts indicates the number of
         high priority packets, as determined by the SLA profile ingress QoS
         policy, offered by the Pchip to the Qchip."
    ::= { tmnxSLAProfInstIngPStatsEntry 3 }

tmnxSPIIngPStatsOffHiPrioPktsL OBJECT-TYPE
    SYNTAX      Counter32
    MAX-ACCESS  read-only
    STATUS      current
    DESCRIPTION
        "Indicates the lower 32 bits of tmnxSPIIngPStatsOffHiPrioPkts."
    ::= { tmnxSLAProfInstIngPStatsEntry 4 }

tmnxSPIIngPStatsOffHiPrioPktsH OBJECT-TYPE
    SYNTAX      Counter32
    MAX-ACCESS  read-only
    STATUS      current
    DESCRIPTION
        "Indicates the upper 32 bits of tmnxSPIIngPStatsOffHiPrioPkts."
    ::= { tmnxSLAProfInstIngPStatsEntry 5 }

tmnxSPIIngPStatsDrpHiPrioPkts OBJECT-TYPE
    SYNTAX      Counter64
    MAX-ACCESS  read-only
    STATUS      current
    DESCRIPTION
        "The value of tmnxSPIIngPStatsDrpHiPrioPkts indicates the number of
         high priority packets, as determined by the SLA profile ingress QoS
         policy, dropped by the Qchip."
    ::= { tmnxSLAProfInstIngPStatsEntry 6 }

tmnxSPIIngPStatsDrpHiPrioPktsL OBJECT-TYPE
    SYNTAX      Counter32
    MAX-ACCESS  read-only
    STATUS      current
    DESCRIPTION
        "Indicates the lower 32 bits of tmnxSPIIngPStatsDrpHiPrioPkts."
    ::= { tmnxSLAProfInstIngPStatsEntry 7 }

tmnxSPIIngPStatsDrpHiPrioPktsH OBJECT-TYPE
    SYNTAX      Counter32
    MAX-ACCESS  read-only
    STATUS      current
    DESCRIPTION
        "Indicates the upper 32 bits of tmnxSPIIngPStatsDrpHiPrioPkts."
    ::= { tmnxSLAProfInstIngPStatsEntry 8 }

tmnxSPIIngPStatsOffLoPrioPkts OBJECT-TYPE
    SYNTAX      Counter64
    MAX-ACCESS  read-only
    STATUS      current
    DESCRIPTION
        "The value of tmnxSPIIngPStatsOffLoPrioPkts indicates the number of low
         priority packets, as determined by the SLA profile ingress QoS policy,
         offered by the Pchip to the Qchip."
    ::= { tmnxSLAProfInstIngPStatsEntry 9 }

tmnxSPIIngPStatsOffLoPrioPktsL OBJECT-TYPE
    SYNTAX      Counter32
    MAX-ACCESS  read-only
    STATUS      current
    DESCRIPTION
        "Indicates the lower 32 bits of tmnxSPIIngPStatsOffLoPrioPkts."
    ::= { tmnxSLAProfInstIngPStatsEntry 10 }

tmnxSPIIngPStatsOffLoPrioPktsH OBJECT-TYPE
    SYNTAX      Counter32
    MAX-ACCESS  read-only
    STATUS      current
    DESCRIPTION
        "Indicates the upper 32 bits of tmnxSPIIngPStatsOffLoPrioPkts."
    ::= { tmnxSLAProfInstIngPStatsEntry 11 }

tmnxSPIIngPStatsDrpLoPrioPkts OBJECT-TYPE
    SYNTAX      Counter64
    MAX-ACCESS  read-only
    STATUS      current
    DESCRIPTION
        "The value of tmnxSPIIngPStatsDrpLoPrioPkts indicates the number of
         low priority packets, as determined by the SLA profile ingress QoS
         policy, dropped by the Pchip."
    ::= { tmnxSLAProfInstIngPStatsEntry 12 }

tmnxSPIIngPStatsDrpLoPrioPktsL OBJECT-TYPE
    SYNTAX      Counter32
    MAX-ACCESS  read-only
    STATUS      current
    DESCRIPTION
        "Indicates the lower 32 bits of tmnxSPIIngPStatsDrpLoPrioPkts."
    ::= { tmnxSLAProfInstIngPStatsEntry 13 }

tmnxSPIIngPStatsDrpLoPrioPktsH OBJECT-TYPE
    SYNTAX      Counter32
    MAX-ACCESS  read-only
    STATUS      current
    DESCRIPTION
        "Indicates the upper 32 bits of tmnxSPIIngPStatsDrpLoPrioPkts."
    ::= { tmnxSLAProfInstIngPStatsEntry 14 }

tmnxSPIIngPStatsOffHiPrioOcts OBJECT-TYPE
    SYNTAX      Counter64
    MAX-ACCESS  read-only
    STATUS      current
    DESCRIPTION
        "The value of tmnxSPIIngPStatsOffHiPrioOcts indicates the number
         of high priority octets, as determined by the SLA profile ingress QoS
         policy, offered by the Pchip to the Qchip."
    ::= { tmnxSLAProfInstIngPStatsEntry 15 }

tmnxSPIIngPStatsOffHiPrioOctsL OBJECT-TYPE
    SYNTAX      Counter32
    MAX-ACCESS  read-only
    STATUS      current
    DESCRIPTION
        "Indicates the lower 32 bits of tmnxSPIIngPStatsOffHiPrioOcts."
    ::= { tmnxSLAProfInstIngPStatsEntry 16 }

tmnxSPIIngPStatsOffHiPrioOctsH OBJECT-TYPE
    SYNTAX      Counter32
    MAX-ACCESS  read-only
    STATUS      current
    DESCRIPTION
        "Indicates the upper 32 bits of tmnxSPIIngPStatsOffHiPrioOcts."
    ::= { tmnxSLAProfInstIngPStatsEntry 17 }

tmnxSPIIngPStatsDrpHiPrioOcts OBJECT-TYPE
    SYNTAX      Counter64
    MAX-ACCESS  read-only
    STATUS      current
    DESCRIPTION
        "The value of tmnxSPIIngPStatsDrpHiPrioOcts indicates the number of
         high priority octets, as determined by the SLA profile ingress QoS
         policy, dropped by the Pchip."
    ::= { tmnxSLAProfInstIngPStatsEntry 18 }

tmnxSPIIngPStatsDrpHiPrioOctsL OBJECT-TYPE
    SYNTAX      Counter32
    MAX-ACCESS  read-only
    STATUS      current
    DESCRIPTION
        "Indicates the lower 32 bits of tmnxSPIIngPStatsDrpHiPrioOcts."
    ::= { tmnxSLAProfInstIngPStatsEntry 19 }

tmnxSPIIngPStatsDrpHiPrioOctsH OBJECT-TYPE
    SYNTAX      Counter32
    MAX-ACCESS  read-only
    STATUS      current
    DESCRIPTION
        "Indicates the upper 32 bits of tmnxSPIIngPStatsDrpHiPrioOcts."
    ::= { tmnxSLAProfInstIngPStatsEntry 20 }

tmnxSPIIngPStatsOffLoPrioOcts OBJECT-TYPE
    SYNTAX      Counter64
    MAX-ACCESS  read-only
    STATUS      current
    DESCRIPTION
        "The value of tmnxSPIIngPStatsOffLoPrioOcts indicates the number of
         low priority octets, as determined by the SLA profile ingress QoS
         policy, offered by the Pchip to the Qchip."
    ::= { tmnxSLAProfInstIngPStatsEntry 21 }

tmnxSPIIngPStatsOffLoPrioOctsL OBJECT-TYPE
    SYNTAX      Counter32
    MAX-ACCESS  read-only
    STATUS      current
    DESCRIPTION
        "Indicates the lower 32 bits of tmnxSPIIngPStatsOffLoPrioOcts."
    ::= { tmnxSLAProfInstIngPStatsEntry 22 }

tmnxSPIIngPStatsOffLoPrioOctsH OBJECT-TYPE
    SYNTAX      Counter32
    MAX-ACCESS  read-only
    STATUS      current
    DESCRIPTION
        "Indicates the upper 32 bits of tmnxSPIIngPStatsOffLoPrioOcts."
    ::= { tmnxSLAProfInstIngPStatsEntry 23 }

tmnxSPIIngPStatsDrpLoPrioOcts OBJECT-TYPE
    SYNTAX      Counter64
    MAX-ACCESS  read-only
    STATUS      current
    DESCRIPTION
        "The value of tmnxSPIIngPStatsDrpLoPrioOcts indicates the number of
         low priority octets, as determined by the SLA profile ingress QoS
         policy, dropped by the Pchip."
    ::= { tmnxSLAProfInstIngPStatsEntry 24 }

tmnxSPIIngPStatsDrpLoPrioOctsL OBJECT-TYPE
    SYNTAX      Counter32
    MAX-ACCESS  read-only
    STATUS      current
    DESCRIPTION
        "Indicates the lower 32 bits of tmnxSPIIngPStatsDrpLoPrioOcts."
    ::= { tmnxSLAProfInstIngPStatsEntry 25 }

tmnxSPIIngPStatsDrpLoPrioOctsH OBJECT-TYPE
    SYNTAX      Counter32
    MAX-ACCESS  read-only
    STATUS      current
    DESCRIPTION
        "Indicates the upper 32 bits of tmnxSPIIngPStatsDrpLoPrioOcts."
    ::= { tmnxSLAProfInstIngPStatsEntry 26 }

tmnxSPIIngPStatsOffUncolPkts OBJECT-TYPE
    SYNTAX      Counter64
    MAX-ACCESS  read-only
    STATUS      current
    DESCRIPTION
        "The value of tmnxSPIIngPStatsOffUncolPkts indicates the number of
         uncolored packets offered to the ingress Pchip."
    ::= { tmnxSLAProfInstIngPStatsEntry 27 }

tmnxSPIIngPStatsOffUncolPktsL OBJECT-TYPE
    SYNTAX      Counter32
    MAX-ACCESS  read-only
    STATUS      current
    DESCRIPTION
        "Indicates the lower 32 bits of tmnxSPIIngPStatsOffUncolPkts."
    ::= { tmnxSLAProfInstIngPStatsEntry 28 }

tmnxSPIIngPStatsOffUncolPktsH OBJECT-TYPE
    SYNTAX      Counter32
    MAX-ACCESS  read-only
    STATUS      current
    DESCRIPTION
        "Indicates the upper 32 bits of tmnxSPIIngPStatsOffUncolPkts."
    ::= { tmnxSLAProfInstIngPStatsEntry 29 }

tmnxSPIIngPStatsOffUncolOcts OBJECT-TYPE
    SYNTAX      Counter64
    MAX-ACCESS  read-only
    STATUS      current
    DESCRIPTION
        "The value of tmnxSPIIngPStatsOffUncolOcts indicates the number of
         uncolored octets offered to the ingress Pchip."
    ::= { tmnxSLAProfInstIngPStatsEntry 30 }

tmnxSPIIngPStatsOffUncolOctsL OBJECT-TYPE
    SYNTAX      Counter32
    MAX-ACCESS  read-only
    STATUS      current
    DESCRIPTION
        "Indicates the lower 32 bits of tmnxSPIIngPStatsOffUncolOcts."
    ::= { tmnxSLAProfInstIngPStatsEntry 31 }

tmnxSPIIngPStatsOffUncolOctsH OBJECT-TYPE
    SYNTAX      Counter32
    MAX-ACCESS  read-only
    STATUS      current
    DESCRIPTION
        "Indicates the upper 32 bits of tmnxSPIIngPStatsOffUncolOcts."
    ::= { tmnxSLAProfInstIngPStatsEntry 32 }

tmnxSPIIngPStatsFwdInProfPkts OBJECT-TYPE
    SYNTAX      Counter64
    MAX-ACCESS  read-only
    STATUS      current
    DESCRIPTION
        "The value of tmnxSPIIngPStatsFwdInProfPkts indicates the number of
         in-profile packets (rate below CIR) forwarded by the ingress Pchip."
    ::= { tmnxSLAProfInstIngPStatsEntry 33 }

tmnxSPIIngPStatsFwdInProfPktsL OBJECT-TYPE
    SYNTAX      Counter32
    MAX-ACCESS  read-only
    STATUS      current
    DESCRIPTION
        "Indicates the lower 32 bits of tmnxSPIIngPStatsFwdInProfPkts."
    ::= { tmnxSLAProfInstIngPStatsEntry 34 }

tmnxSPIIngPStatsFwdInProfPktsH OBJECT-TYPE
    SYNTAX      Counter32
    MAX-ACCESS  read-only
    STATUS      current
    DESCRIPTION
        "Indicates the upper 32 bits of tmnxSPIIngPStatsFwdInProfPkts."
    ::= { tmnxSLAProfInstIngPStatsEntry 35 }

tmnxSPIIngPStatsFwdOutProfPkts OBJECT-TYPE
    SYNTAX      Counter64
    MAX-ACCESS  read-only
    STATUS      current
    DESCRIPTION
        "The value of tmnxSPIIngPStatsFwdOutProfPkts indicates the number of
         out-of-profile packets (rate above CIR) forwarded by the ingress Pchip."
    ::= { tmnxSLAProfInstIngPStatsEntry 36 }

tmnxSPIIngPStatsFwdOutProfPktsL OBJECT-TYPE
    SYNTAX      Counter32
    MAX-ACCESS  read-only
    STATUS      current
    DESCRIPTION
        "Indicates the lower 32 bits of tmnxSPIIngPStatsFwdOutProfPkts."
    ::= { tmnxSLAProfInstIngPStatsEntry 37 }

tmnxSPIIngPStatsFwdOutProfPktsH OBJECT-TYPE
    SYNTAX      Counter32
    MAX-ACCESS  read-only
    STATUS      current
    DESCRIPTION
        "Indicates the upper 32 bits of tmnxSPIIngPStatsFwdOutProfPkts."
    ::= { tmnxSLAProfInstIngPStatsEntry 38 }

tmnxSPIIngPStatsFwdInProfOcts OBJECT-TYPE
    SYNTAX      Counter64
    MAX-ACCESS  read-only
    STATUS      current
    DESCRIPTION
        "The value of tmnxSPIIngPStatsFwdInProfOcts indicates the number of
         in-profile octets (rate below CIR) forwarded by the ingress Pchip."
    ::= { tmnxSLAProfInstIngPStatsEntry 39 }

tmnxSPIIngPStatsFwdInProfOctsL OBJECT-TYPE
    SYNTAX      Counter32
    MAX-ACCESS  read-only
    STATUS      current
    DESCRIPTION
        "Indicates the lower 32 bits of tmnxSPIIngPStatsFwdInProfOcts."
    ::= { tmnxSLAProfInstIngPStatsEntry 40 }

tmnxSPIIngPStatsFwdInProfOctsH OBJECT-TYPE
    SYNTAX      Counter32
    MAX-ACCESS  read-only
    STATUS      current
    DESCRIPTION
        "Indicates the upper 32 bits of tmnxSPIIngPStatsFwdInProfOcts."
    ::= { tmnxSLAProfInstIngPStatsEntry 41 }

tmnxSPIIngPStatsFwdOutProfOcts OBJECT-TYPE
    SYNTAX      Counter64
    MAX-ACCESS  read-only
    STATUS      current
    DESCRIPTION
        "The value of tmnxSPIIngPStatsFwdOutProfOcts indicates the number of
         out-of-profile octets (rate above CIR) forwarded by the ingress Pchip."
    ::= { tmnxSLAProfInstIngPStatsEntry 42 }

tmnxSPIIngPStatsFwdOutProfOctsL OBJECT-TYPE
    SYNTAX      Counter32
    MAX-ACCESS  read-only
    STATUS      current
    DESCRIPTION
        "Indicates the lower 32 bits of tmnxSPIIngPStatsFwdOutProfOcts."
    ::= { tmnxSLAProfInstIngPStatsEntry 43 }

tmnxSPIIngPStatsFwdOutProfOctsH OBJECT-TYPE
    SYNTAX      Counter32
    MAX-ACCESS  read-only
    STATUS      current
    DESCRIPTION
        "Indicates the upper 32 bits of tmnxSPIIngPStatsFwdOutProfOcts."
    ::= { tmnxSLAProfInstIngPStatsEntry 44 }

-- ----------------------------------------
-- tmnxSLAProfInstEgrPStatsTable
-- ----------------------------------------
tmnxSLAProfInstEgrPStatsTable OBJECT-TYPE
    SYNTAX      SEQUENCE OF TmnxSLAProfInstEgrPStatsEntry
    MAX-ACCESS  not-accessible
    STATUS      current
    DESCRIPTION
        "The tmnxSLAProfInstEgrPStatsTable contains egress QoS policer
         statistics about SLA profile instances.

         In the descriptions below 'Pchip' refers to the Nokia SROS 
         series Packet Processing chip, while 'Qchip' refers to the 
         Nokia SROS series QoS Queueing Engine chip."
    ::= { tmnxSubMgmtObjects 81 }

tmnxSLAProfInstEgrPStatsEntry OBJECT-TYPE
    SYNTAX      TmnxSLAProfInstEgrPStatsEntry
    MAX-ACCESS  not-accessible
    STATUS      current
    DESCRIPTION
        "Each row entry contains egress statistics about a particular SLA
         profile instance QoS policer."
    INDEX { tmnxSubInfoSubIdent,
            sapPortId,
            sapEncapValue,
            tmnxSLAProfName,
            tmnxSPIEgrPStatsPolId }
    ::= { tmnxSLAProfInstEgrPStatsTable 1 }

TmnxSLAProfInstEgrPStatsEntry ::=
    SEQUENCE {
        tmnxSPIEgrPStatsPolId            TEgressPolicerId,
        tmnxSPIEgrPStatsMode             TmnxEgrPolicerStatMode,
        tmnxSPIEgrPStatsOffInProfPkts    Counter64,
        tmnxSPIEgrPStatsOffInProfPktsL   Counter32,
        tmnxSPIEgrPStatsOffInProfPktsH   Counter32,
        tmnxSPIEgrPStatsFwdInProfPkts    Counter64,
        tmnxSPIEgrPStatsFwdInProfPktsL   Counter32,
        tmnxSPIEgrPStatsFwdInProfPktsH   Counter32,
        tmnxSPIEgrPStatsDrpInProfPkts    Counter64,
        tmnxSPIEgrPStatsDrpInProfPktsL   Counter32,
        tmnxSPIEgrPStatsDrpInProfPktsH   Counter32,
        tmnxSPIEgrPStatsOffOutProfPkts   Counter64,
        tmnxSPIEgrPStatsOffOutProfPktsL  Counter32,
        tmnxSPIEgrPStatsOffOutProfPktsH  Counter32,
        tmnxSPIEgrPStatsFwdOutProfPkts   Counter64,
        tmnxSPIEgrPStatsFwdOutProfPktsL  Counter32,
        tmnxSPIEgrPStatsFwdOutProfPktsH  Counter32,
        tmnxSPIEgrPStatsDrpOutProfPkts   Counter64,
        tmnxSPIEgrPStatsDrpOutProfPktsL  Counter32,
        tmnxSPIEgrPStatsDrpOutProfPktsH  Counter32,
        tmnxSPIEgrPStatsOffInProfOcts    Counter64,
        tmnxSPIEgrPStatsOffInProfOctsL   Counter32,
        tmnxSPIEgrPStatsOffInProfOctsH   Counter32,
        tmnxSPIEgrPStatsFwdInProfOcts    Counter64,
        tmnxSPIEgrPStatsFwdInProfOctsL   Counter32,
        tmnxSPIEgrPStatsFwdInProfOctsH   Counter32,
        tmnxSPIEgrPStatsDrpInProfOcts    Counter64,
        tmnxSPIEgrPStatsDrpInProfOctsL   Counter32,
        tmnxSPIEgrPStatsDrpInProfOctsH   Counter32,
        tmnxSPIEgrPStatsOffOutProfOcts   Counter64,
        tmnxSPIEgrPStatsOffOutProfOctsL  Counter32,
        tmnxSPIEgrPStatsOffOutProfOctsH  Counter32,
        tmnxSPIEgrPStatsFwdOutProfOcts   Counter64,
        tmnxSPIEgrPStatsFwdOutProfOctsL  Counter32,
        tmnxSPIEgrPStatsFwdOutProfOctsH  Counter32,
        tmnxSPIEgrPStatsDrpOutProfOcts   Counter64,
        tmnxSPIEgrPStatsDrpOutProfOctsL  Counter32,
        tmnxSPIEgrPStatsDrpOutProfOctsH  Counter32,
        tmnxSPIEgrPStatsOffUncolPkts     Counter64,
        tmnxSPIEgrPStatsOffUncolPktsL    Counter32,
        tmnxSPIEgrPStatsOffUncolPktsH    Counter32,
        tmnxSPIEgrPStatsOffUncolOcts     Counter64,
        tmnxSPIEgrPStatsOffUncolOctsL    Counter32,
        tmnxSPIEgrPStatsOffUncolOctsH    Counter32
    }

tmnxSPIEgrPStatsPolId OBJECT-TYPE
    SYNTAX      TEgressPolicerId
    MAX-ACCESS  not-accessible
    STATUS      current
    DESCRIPTION
        "The value of tmnxSPIEgrPStatsPolId specifies the index of the egress QoS policer of this SLA profile instance."
    ::= { tmnxSLAProfInstEgrPStatsEntry 1 }

tmnxSPIEgrPStatsMode OBJECT-TYPE
    SYNTAX      TmnxEgrPolicerStatMode
    MAX-ACCESS  read-only
    STATUS      current
    DESCRIPTION
        "The value of tmnxSPIEgrPStatsMode indicates the stat mode used by the policer."
    ::= { tmnxSLAProfInstEgrPStatsEntry 2 }

tmnxSPIEgrPStatsOffInProfPkts OBJECT-TYPE
    SYNTAX      Counter64
    MAX-ACCESS  read-only
    STATUS      current
    DESCRIPTION
        "The value of tmnxSPIEgrPStatsOffInProfPkts indicates the number of
         in-profile packets (rate below CIR) offered by the egress Pchip."
    ::= { tmnxSLAProfInstEgrPStatsEntry 3 }

tmnxSPIEgrPStatsOffInProfPktsL OBJECT-TYPE
    SYNTAX      Counter32
    MAX-ACCESS  read-only
    STATUS      current
    DESCRIPTION
        "Indicates the lower 32 bits of tmnxSPIEgrPStatsOffInProfPkts."
    ::= { tmnxSLAProfInstEgrPStatsEntry 4 }

tmnxSPIEgrPStatsOffInProfPktsH OBJECT-TYPE
    SYNTAX      Counter32
    MAX-ACCESS  read-only
    STATUS      current
    DESCRIPTION
        "Indicates the upper 32 bits of tmnxSPIEgrPStatsOffInProfPkts."
    ::= { tmnxSLAProfInstEgrPStatsEntry 5 }

tmnxSPIEgrPStatsFwdInProfPkts OBJECT-TYPE
    SYNTAX      Counter64
    MAX-ACCESS  read-only
    STATUS      current
    DESCRIPTION
        "The value of tmnxSPIEgrPStatsFwdInProfPkts indicates the number of
         in-profile packets (rate below CIR) forwarded by the egress Pchip."
    ::= { tmnxSLAProfInstEgrPStatsEntry 6 }

tmnxSPIEgrPStatsFwdInProfPktsL OBJECT-TYPE
    SYNTAX      Counter32
    MAX-ACCESS  read-only
    STATUS      current
    DESCRIPTION
        "Indicates the lower 32 bits of tmnxSPIEgrPStatsFwdInProfPkts."
    ::= { tmnxSLAProfInstEgrPStatsEntry 7 }

tmnxSPIEgrPStatsFwdInProfPktsH OBJECT-TYPE
    SYNTAX      Counter32
    MAX-ACCESS  read-only
    STATUS      current
    DESCRIPTION
        "Indicates the upper 32 bits of tmnxSPIEgrPStatsFwdInProfPkts."
    ::= { tmnxSLAProfInstEgrPStatsEntry 8 }

tmnxSPIEgrPStatsDrpInProfPkts OBJECT-TYPE
    SYNTAX      Counter64
    MAX-ACCESS  read-only
    STATUS      current
    DESCRIPTION
        "The value of tmnxSPIEgrPStatsDrpInProfPkts indicates the number of
         in-profile packets (rate below CIR) dropped by the egress Pchip."
    ::= { tmnxSLAProfInstEgrPStatsEntry 9 }

tmnxSPIEgrPStatsDrpInProfPktsL OBJECT-TYPE
    SYNTAX      Counter32
    MAX-ACCESS  read-only
    STATUS      current
    DESCRIPTION
        "Indicates the lower 32 bits of tmnxSPIEgrPStatsDrpInProfPkts."
    ::= { tmnxSLAProfInstEgrPStatsEntry 10 }

tmnxSPIEgrPStatsDrpInProfPktsH OBJECT-TYPE
    SYNTAX      Counter32
    MAX-ACCESS  read-only
    STATUS      current
    DESCRIPTION
        "Indicates the upper 32 bits of tmnxSPIEgrPStatsDrpInProfPkts."
    ::= { tmnxSLAProfInstEgrPStatsEntry 11 }

tmnxSPIEgrPStatsOffOutProfPkts OBJECT-TYPE
    SYNTAX      Counter64
    MAX-ACCESS  read-only
    STATUS      current
    DESCRIPTION
        "The value of tmnxSPIEgrPStatsOffOutProfPkts indicates the number of
         out-of-profile packets (rate above CIR) offered by the egress Pchip."
    ::= { tmnxSLAProfInstEgrPStatsEntry 12 }

tmnxSPIEgrPStatsOffOutProfPktsL OBJECT-TYPE
    SYNTAX      Counter32
    MAX-ACCESS  read-only
    STATUS      current
    DESCRIPTION
        "Indicates the lower 32 bits of tmnxSPIEgrPStatsOffOutProfPkts."
    ::= { tmnxSLAProfInstEgrPStatsEntry 13 }

tmnxSPIEgrPStatsOffOutProfPktsH OBJECT-TYPE
    SYNTAX      Counter32
    MAX-ACCESS  read-only
    STATUS      current
    DESCRIPTION
        "Indicates the upper 32 bits of tmnxSPIEgrPStatsOffOutProfPkts."
    ::= { tmnxSLAProfInstEgrPStatsEntry 14 }

tmnxSPIEgrPStatsFwdOutProfPkts OBJECT-TYPE
    SYNTAX      Counter64
    MAX-ACCESS  read-only
    STATUS      current
    DESCRIPTION
        "The value of tmnxSPIEgrPStatsFwdOutProfPkts indicates the number of
         out-of-profile packets (rate above CIR) forwarded by the egress Pchip."
    ::= { tmnxSLAProfInstEgrPStatsEntry 15 }

tmnxSPIEgrPStatsFwdOutProfPktsL OBJECT-TYPE
    SYNTAX      Counter32
    MAX-ACCESS  read-only
    STATUS      current
    DESCRIPTION
        "Indicates the lower 32 bits of tmnxSPIEgrPStatsFwdOutProfPkts."
    ::= { tmnxSLAProfInstEgrPStatsEntry 16 }

tmnxSPIEgrPStatsFwdOutProfPktsH OBJECT-TYPE
    SYNTAX      Counter32
    MAX-ACCESS  read-only
    STATUS      current
    DESCRIPTION
        "Indicates the upper 32 bits of tmnxSPIEgrPStatsFwdOutProfPkts."
    ::= { tmnxSLAProfInstEgrPStatsEntry 17 }

tmnxSPIEgrPStatsDrpOutProfPkts OBJECT-TYPE
    SYNTAX      Counter64
    MAX-ACCESS  read-only
    STATUS      current
    DESCRIPTION
        "The value of tmnxSPIEgrPStatsDrpOutProfPkts indicates the number of
         out-of-profile packets (rate above CIR) dropped by the egress Pchip."
    ::= { tmnxSLAProfInstEgrPStatsEntry 18 }

tmnxSPIEgrPStatsDrpOutProfPktsL OBJECT-TYPE
    SYNTAX      Counter32
    MAX-ACCESS  read-only
    STATUS      current
    DESCRIPTION
        "Indicates the lower 32 bits of tmnxSPIEgrPStatsDrpOutProfPkts."
    ::= { tmnxSLAProfInstEgrPStatsEntry 19 }

tmnxSPIEgrPStatsDrpOutProfPktsH OBJECT-TYPE
    SYNTAX      Counter32
    MAX-ACCESS  read-only
    STATUS      current
    DESCRIPTION
        "Indicates the upper 32 bits of tmnxSPIEgrPStatsDrpOutProfPkts."
    ::= { tmnxSLAProfInstEgrPStatsEntry 20 }

tmnxSPIEgrPStatsOffInProfOcts OBJECT-TYPE
    SYNTAX      Counter64
    MAX-ACCESS  read-only
    STATUS      current
    DESCRIPTION
        "The value of tmnxSPIEgrPStatsOffInProfOcts indicates the number of
         in-profile octets (rate below CIR) forwarded by the egress Pchip."
    ::= { tmnxSLAProfInstEgrPStatsEntry 21 }

tmnxSPIEgrPStatsOffInProfOctsL OBJECT-TYPE
    SYNTAX      Counter32
    MAX-ACCESS  read-only
    STATUS      current
    DESCRIPTION
        "Indicates the lower 32 bits of tmnxSPIEgrPStatsOffInProfOcts."
    ::= { tmnxSLAProfInstEgrPStatsEntry 22 }

tmnxSPIEgrPStatsOffInProfOctsH OBJECT-TYPE
    SYNTAX      Counter32
    MAX-ACCESS  read-only
    STATUS      current
    DESCRIPTION
        "Indicates the upper 32 bits of tmnxSPIEgrPStatsOffInProfOcts."
    ::= { tmnxSLAProfInstEgrPStatsEntry 23 }

tmnxSPIEgrPStatsFwdInProfOcts OBJECT-TYPE
    SYNTAX      Counter64
    MAX-ACCESS  read-only
    STATUS      current
    DESCRIPTION
        "The value of tmnxSPIEgrPStatsFwdInProfOcts indicates the number of
         in-profile octets (rate below CIR) forwarded by the egress Pchip."
    ::= { tmnxSLAProfInstEgrPStatsEntry 24 }

tmnxSPIEgrPStatsFwdInProfOctsL OBJECT-TYPE
    SYNTAX      Counter32
    MAX-ACCESS  read-only
    STATUS      current
    DESCRIPTION
        "Indicates the lower 32 bits of tmnxSPIEgrPStatsFwdInProfOcts."
    ::= { tmnxSLAProfInstEgrPStatsEntry 25 }

tmnxSPIEgrPStatsFwdInProfOctsH OBJECT-TYPE
    SYNTAX      Counter32
    MAX-ACCESS  read-only
    STATUS      current
    DESCRIPTION
        "Indicates the upper 32 bits of tmnxSPIEgrPStatsFwdInProfOcts."
    ::= { tmnxSLAProfInstEgrPStatsEntry 26 }

tmnxSPIEgrPStatsDrpInProfOcts OBJECT-TYPE
    SYNTAX      Counter64
    MAX-ACCESS  read-only
    STATUS      current
    DESCRIPTION
        "The value of tmnxSPIEgrPStatsDrpInProfOcts indicates the number of
         in-profile octets (rate below CIR) dropped by the egress Pchip."
    ::= { tmnxSLAProfInstEgrPStatsEntry 27 }

tmnxSPIEgrPStatsDrpInProfOctsL OBJECT-TYPE
    SYNTAX      Counter32
    MAX-ACCESS  read-only
    STATUS      current
    DESCRIPTION
        "Indicates the lower 32 bits of tmnxSPIEgrPStatsDrpInProfOcts."
    ::= { tmnxSLAProfInstEgrPStatsEntry 28 }

tmnxSPIEgrPStatsDrpInProfOctsH OBJECT-TYPE
    SYNTAX      Counter32
    MAX-ACCESS  read-only
    STATUS      current
    DESCRIPTION
        "Indicates the upper 32 bits of tmnxSPIEgrPStatsDrpInProfOcts."
    ::= { tmnxSLAProfInstEgrPStatsEntry 29 }

tmnxSPIEgrPStatsOffOutProfOcts OBJECT-TYPE
    SYNTAX      Counter64
    MAX-ACCESS  read-only
    STATUS      current
    DESCRIPTION
        "The value of tmnxSPIEgrPStatsOffOutProfOcts indicates the number of
         out-of-profile octets (rate above CIR) offered by the egress Pchip."
    ::= { tmnxSLAProfInstEgrPStatsEntry 30 }

tmnxSPIEgrPStatsOffOutProfOctsL OBJECT-TYPE
    SYNTAX      Counter32
    MAX-ACCESS  read-only
    STATUS      current
    DESCRIPTION
        "Indicates the lower 32 bits of tmnxSPIEgrPStatsOffOutProfOcts."
    ::= { tmnxSLAProfInstEgrPStatsEntry 31 }

tmnxSPIEgrPStatsOffOutProfOctsH OBJECT-TYPE
    SYNTAX      Counter32
    MAX-ACCESS  read-only
    STATUS      current
    DESCRIPTION
        "Indicates the upper 32 bits of tmnxSPIEgrPStatsOffOutProfOcts."
    ::= { tmnxSLAProfInstEgrPStatsEntry 32 }

tmnxSPIEgrPStatsFwdOutProfOcts OBJECT-TYPE
    SYNTAX      Counter64
    MAX-ACCESS  read-only
    STATUS      current
    DESCRIPTION
        "The value of tmnxSPIEgrPStatsFwdOutProfOcts indicates the number of
         out-of-profile octets (rate above CIR) forwarded by the egress Pchip."
    ::= { tmnxSLAProfInstEgrPStatsEntry 33 }

tmnxSPIEgrPStatsFwdOutProfOctsL OBJECT-TYPE
    SYNTAX      Counter32
    MAX-ACCESS  read-only
    STATUS      current
    DESCRIPTION
        "Indicates the lower 32 bits of tmnxSPIEgrPStatsFwdOutProfOcts."
    ::= { tmnxSLAProfInstEgrPStatsEntry 34 }

tmnxSPIEgrPStatsFwdOutProfOctsH OBJECT-TYPE
    SYNTAX      Counter32
    MAX-ACCESS  read-only
    STATUS      current
    DESCRIPTION
        "Indicates the upper 32 bits of tmnxSPIEgrPStatsFwdOutProfOcts."
    ::= { tmnxSLAProfInstEgrPStatsEntry 35 }

tmnxSPIEgrPStatsDrpOutProfOcts OBJECT-TYPE
    SYNTAX      Counter64
    MAX-ACCESS  read-only
    STATUS      current
    DESCRIPTION
        "The value of tmnxSPIEgrPStatsDrpOutProfOcts indicates the number of
         out-of-profile octets (rate above CIR) dropped by the egress Pchip."
    ::= { tmnxSLAProfInstEgrPStatsEntry 36 }

tmnxSPIEgrPStatsDrpOutProfOctsL OBJECT-TYPE
    SYNTAX      Counter32
    MAX-ACCESS  read-only
    STATUS      current
    DESCRIPTION
        "Indicates the lower 32 bits of tmnxSPIEgrPStatsDrpOutProfOcts."
    ::= { tmnxSLAProfInstEgrPStatsEntry 37 }

tmnxSPIEgrPStatsDrpOutProfOctsH OBJECT-TYPE
    SYNTAX      Counter32
    MAX-ACCESS  read-only
    STATUS      current
    DESCRIPTION
        "Indicates the upper 32 bits of tmnxSPIEgrPStatsDrpOutProfOcts."
    ::= { tmnxSLAProfInstEgrPStatsEntry 38 }

tmnxSPIEgrPStatsOffUncolPkts OBJECT-TYPE
    SYNTAX      Counter64
    MAX-ACCESS  read-only
    STATUS      current
    DESCRIPTION
        "The value of tmnxSPIEgrPStatsOffUncolPkts indicates the number of
         uncolored packets (rate above CIR) offered by the egress Pchip."
    ::= { tmnxSLAProfInstEgrPStatsEntry 39 }

tmnxSPIEgrPStatsOffUncolPktsL OBJECT-TYPE
    SYNTAX      Counter32
    MAX-ACCESS  read-only
    STATUS      current
    DESCRIPTION
        "Indicates the lower 32 bits of tmnxSPIEgrPStatsOffUncolPkts."
    ::= { tmnxSLAProfInstEgrPStatsEntry 40 }

tmnxSPIEgrPStatsOffUncolPktsH OBJECT-TYPE
    SYNTAX      Counter32
    MAX-ACCESS  read-only
    STATUS      current
    DESCRIPTION
        "Indicates the upper 32 bits of tmnxSPIEgrPStatsOffUncolPkts."
    ::= { tmnxSLAProfInstEgrPStatsEntry 41 }

tmnxSPIEgrPStatsOffUncolOcts OBJECT-TYPE
    SYNTAX      Counter64
    MAX-ACCESS  read-only
    STATUS      current
    DESCRIPTION
        "The value of tmnxSPIEgrPStatsOffUncolOcts indicates the number of
         uncolored octets (rate above CIR) offered by the egress Pchip."
    ::= { tmnxSLAProfInstEgrPStatsEntry 42 }

tmnxSPIEgrPStatsOffUncolOctsL OBJECT-TYPE
    SYNTAX      Counter32
    MAX-ACCESS  read-only
    STATUS      current
    DESCRIPTION
        "Indicates the lower 32 bits of tmnxSPIEgrPStatsOffUncolOcts."
    ::= { tmnxSLAProfInstEgrPStatsEntry 43 }

tmnxSPIEgrPStatsOffUncolOctsH OBJECT-TYPE
    SYNTAX      Counter32
    MAX-ACCESS  read-only
    STATUS      current
    DESCRIPTION
        "Indicates the upper 32 bits of tmnxSPIEgrPStatsOffUncolOcts."
    ::= { tmnxSLAProfInstEgrPStatsEntry 44 }


-- --------------------------------------------------------
-- tmnxSubRadiusAcceptTable
-- --------------------------------------------------------
tmnxSubRadiusAcceptTable OBJECT-TYPE
    SYNTAX      SEQUENCE OF TmnxSubRadiusAcceptEntry
    MAX-ACCESS  not-accessible
    STATUS      obsolete
    DESCRIPTION
        "The tmnxSubRadiusAcceptTable allows configuration of RADIUS
         attributes to be accepted."
    ::= { tmnxSubMgmtObjects 82 }

tmnxSubRadiusAcceptEntry OBJECT-TYPE
    SYNTAX      TmnxSubRadiusAcceptEntry
    MAX-ACCESS  not-accessible
    STATUS      obsolete
    DESCRIPTION
        "Each entry represents a RADIUS attribute that is to be accepted.
        
         Entries in this table can be created and deleted via
         SNMP SET operations."
    INDEX { tmnxSubAuthPlcyName,
            tmnxSubRadiusAcceptAttributeType,
            tmnxSubRadiusAcceptVendorId
          }
    ::= { tmnxSubRadiusAcceptTable 1 }

TmnxSubRadiusAcceptEntry ::= SEQUENCE {
    tmnxSubRadiusAcceptAttributeType TmnxSubRadiusAttrType,
    tmnxSubRadiusAcceptVendorId      TmnxSubRadiusVendorId,
    tmnxSubRadiusAcceptRowStatus     RowStatus,
    tmnxSubRadiusAcceptLastMgmtCh    TimeStamp,
    tmnxSubRadiusAcceptSelective     BITS
}                             

tmnxSubRadiusAcceptAttributeType OBJECT-TYPE
    SYNTAX      TmnxSubRadiusAttrType (1..255)
    MAX-ACCESS  not-accessible
    STATUS      obsolete
    DESCRIPTION
        "The value of tmnxSubRadiusAcceptAttributeType specifies
         the RADIUS Attribute Type to be accepted."
    ::= { tmnxSubRadiusAcceptEntry 1 }

tmnxSubRadiusAcceptVendorId OBJECT-TYPE
    SYNTAX      TmnxSubRadiusVendorId
    MAX-ACCESS  not-accessible
    STATUS      obsolete
    DESCRIPTION
        "The value of tmnxSubRadiusAcceptVendorId specifies
         the RADIUS Vendor-Id.
         
         If the value of tmnxSubRadiusAcceptVendorId is equal to zero, the
         attribute type specified by tmnxSubRadiusAcceptAttributeType must be
         accepted if it appears outside of a Vendor-Specific attribute.
         
         If the value of tmnxSubRadiusAcceptVendorId is not equal to zero, the
         attribute type specified by tmnxSubRadiusAcceptAttributeType must be
         accepted if it appears as a sub-attribute within a Vendor-Specific 
         attribute with Vendor-Id equal to the value of 
         tmnxSubRadiusAcceptVendorId."
    ::= { tmnxSubRadiusAcceptEntry 2 }

tmnxSubRadiusAcceptRowStatus OBJECT-TYPE
    SYNTAX      RowStatus
    MAX-ACCESS  read-create
    STATUS      obsolete
    DESCRIPTION
        "The value of tmnxSubRadiusAcceptRowStatus specifies the row status of
        this row."
    ::= { tmnxSubRadiusAcceptEntry 3 }

tmnxSubRadiusAcceptLastMgmtCh OBJECT-TYPE
    SYNTAX      TimeStamp
    MAX-ACCESS  read-only
    STATUS      obsolete
    DESCRIPTION
        "The value of tmnxSubRadiusAcceptLastMgmtCh indicates the sysUpTime at
         the time of the most recent management-initiated change to this
         table row."
    ::= { tmnxSubRadiusAcceptEntry 4 }

tmnxSubRadiusAcceptSelective OBJECT-TYPE
    SYNTAX BITS {
               auth (0),
               coa (1)
         }
    MAX-ACCESS  read-create
    STATUS      obsolete
    DESCRIPTION
        "The value of tmnxSubRadiusAcceptSelective specifies 
         any additional conditions that must apply in order to accept
         the attribute associated with this conceptual row.
         
         When the 'auth' bit is set, this attribute is only accepted in the 
         context of an authentication, initiated by this system.
         
         When the 'coa' bit is set, this attribute is only accepted in the
         context of a Change of Authorization sequence, initiated by the RADIUS
         server.
         
         By default, all bits are set, and this attribute is accepted without
         any additional conditions."
    DEFVAL {{auth, coa}}
    ::= { tmnxSubRadiusAcceptEntry 5 }

-- ----------------------------------------
-- tmnxSubIngQosArbitStatsTable
-- ----------------------------------------
tmnxSubIngQosArbitStatsTable OBJECT-TYPE
    SYNTAX      SEQUENCE OF TmnxSubIngQosArbitStatsEntry
    MAX-ACCESS  not-accessible
    STATUS      current
    DESCRIPTION
        "The tmnxSubIngQosArbitStatsTable contains ingress QoS arbiter
         statistics about subscribers.

         In the descriptions below 'Pchip' refers to the Nokia SROS 
         series Packet Processing chip, while 'Qchip' refers to the 
         Nokia SROS series QoS Queueing Engine chip."
    ::= { tmnxSubMgmtObjects 83 }

tmnxSubIngQosArbitStatsEntry OBJECT-TYPE
    SYNTAX      TmnxSubIngQosArbitStatsEntry
    MAX-ACCESS  not-accessible
    STATUS      current
    DESCRIPTION
        "Each row entry contains ingress statistics about a particular
         subscriber QoS arbiter."
    INDEX { tmnxSubInfoSubIdent,
            IMPLIED tmnxSubIngQosArbitStatsName }
    ::= { tmnxSubIngQosArbitStatsTable 1 }

TmnxSubIngQosArbitStatsEntry ::=
    SEQUENCE {
        tmnxSubIngQosArbitStatsName      TNamedItem,
        tmnxSubIngQosArbitStatsFwdPkts   Counter64,
        tmnxSubIngQosArbitStatsFwdPktsLo Counter32,
        tmnxSubIngQosArbitStatsFwdPktsHi Counter32,
        tmnxSubIngQosArbitStatsFwdOcts   Counter64,
        tmnxSubIngQosArbitStatsFwdOctsLo Counter32,
        tmnxSubIngQosArbitStatsFwdOctsHi Counter32
    }

tmnxSubIngQosArbitStatsName OBJECT-TYPE
    SYNTAX      TNamedItem
    MAX-ACCESS  not-accessible
    STATUS      current
    DESCRIPTION
        "The value of tmnxSubIngQosArbitStatsName specifies the ingress QoS
         arbiter of this subscriber."
    ::= { tmnxSubIngQosArbitStatsEntry 1 }

tmnxSubIngQosArbitStatsFwdPkts OBJECT-TYPE
    SYNTAX      Counter64
    MAX-ACCESS  read-only
    STATUS      current
    DESCRIPTION
        "The value of tmnxSubIngQosArbitStatsFwdPkts indicates the number of
         forwarded packets, as determined by the subscriber ingress policer
         control policy, offered by the Pchip to the Qchip."
    ::= { tmnxSubIngQosArbitStatsEntry 2 }

tmnxSubIngQosArbitStatsFwdPktsLo OBJECT-TYPE
    SYNTAX          Counter32
    MAX-ACCESS      read-only
    STATUS          current
    DESCRIPTION     "Indicates the lower 32 bits of tmnxSubIngQosArbitStatsFwdPkts."
    ::= { tmnxSubIngQosArbitStatsEntry 3 }

tmnxSubIngQosArbitStatsFwdPktsHi OBJECT-TYPE
    SYNTAX          Counter32
    MAX-ACCESS      read-only
    STATUS          current
    DESCRIPTION     "Indicates the upper 32 bits of tmnxSubIngQosArbitStatsFwdPkts."
    ::= { tmnxSubIngQosArbitStatsEntry 4 }

tmnxSubIngQosArbitStatsFwdOcts OBJECT-TYPE
    SYNTAX      Counter64
    MAX-ACCESS  read-only
    STATUS      current
    DESCRIPTION
        "The value of tmnxSubIngQosArbitStatsFwdOcts indicates the number of
         forwarded octets, as determined by the subscriber ingress policer
         control policy, offered by the Pchip to the Qchip."
    ::= { tmnxSubIngQosArbitStatsEntry 5 }

tmnxSubIngQosArbitStatsFwdOctsLo OBJECT-TYPE
    SYNTAX          Counter32
    MAX-ACCESS      read-only
    STATUS          current
    DESCRIPTION     "Indicates the lower 32 bits of tmnxSubIngQosArbitStatsFwdOcts."
    ::= { tmnxSubIngQosArbitStatsEntry 6 }

tmnxSubIngQosArbitStatsFwdOctsHi OBJECT-TYPE
    SYNTAX          Counter32
    MAX-ACCESS      read-only
    STATUS          current
    DESCRIPTION     "Indicates the upper 32 bits of tmnxSubIngQosArbitStatsFwdOcts."
    ::= { tmnxSubIngQosArbitStatsEntry 7 }

-- ----------------------------------------
-- tmnxSubEgrQosArbitStatsTable
-- ----------------------------------------
tmnxSubEgrQosArbitStatsTable OBJECT-TYPE
    SYNTAX      SEQUENCE OF TmnxSubEgrQosArbitStatsEntry
    MAX-ACCESS  not-accessible
    STATUS      current
    DESCRIPTION
        "The tmnxSubEgrQosArbitStatsTable contains egress QoS arbiter
         statistics about subscribers.

         In the descriptions below 'Pchip' refers to the Nokia SROS 
         series Packet Processing chip, while 'Qchip' refers to the 
         Nokia SROS series QoS Queueing Engine chip."
    ::= { tmnxSubMgmtObjects 84 }

tmnxSubEgrQosArbitStatsEntry OBJECT-TYPE
    SYNTAX      TmnxSubEgrQosArbitStatsEntry
    MAX-ACCESS  not-accessible
    STATUS      current
    DESCRIPTION
        "Each row entry contains egress statistics about a particular
         subscriber QoS arbiter."
    INDEX { tmnxSubInfoSubIdent,
            IMPLIED tmnxSubEgrQosArbitStatsName }
    ::= { tmnxSubEgrQosArbitStatsTable 1 }

TmnxSubEgrQosArbitStatsEntry ::=
    SEQUENCE {
        tmnxSubEgrQosArbitStatsName      TNamedItem,
        tmnxSubEgrQosArbitStatsFwdPkts   Counter64,
        tmnxSubEgrQosArbitStatsFwdPktsLo Counter32,
        tmnxSubEgrQosArbitStatsFwdPktsHi Counter32,
        tmnxSubEgrQosArbitStatsFwdOcts   Counter64,
        tmnxSubEgrQosArbitStatsFwdOctsLo Counter32,
        tmnxSubEgrQosArbitStatsFwdOctsHi Counter32
    }

tmnxSubEgrQosArbitStatsName OBJECT-TYPE
    SYNTAX      TNamedItem
    MAX-ACCESS  not-accessible
    STATUS      current
    DESCRIPTION
        "The value of tmnxSubEgrQosArbitStatsName specifies the egress QoS
         arbiter of this subscriber."
    ::= { tmnxSubEgrQosArbitStatsEntry 1 }

tmnxSubEgrQosArbitStatsFwdPkts OBJECT-TYPE
    SYNTAX      Counter64
    MAX-ACCESS  read-only
    STATUS      current
    DESCRIPTION
        "The value of tmnxSubEgrQosArbitStatsFwdPkts indicates the number of
         forwarded packets, as determined by the subscriber egress policer
         control policy, offered by the Pchip to the Qchip."
    ::= { tmnxSubEgrQosArbitStatsEntry 2 }

tmnxSubEgrQosArbitStatsFwdPktsLo OBJECT-TYPE
    SYNTAX          Counter32
    MAX-ACCESS      read-only
    STATUS          current
    DESCRIPTION     "Indicates the lower 32 bits of tmnxSubEgrQosArbitStatsFwdPkts."
    ::= { tmnxSubEgrQosArbitStatsEntry 3 }

tmnxSubEgrQosArbitStatsFwdPktsHi OBJECT-TYPE
    SYNTAX          Counter32
    MAX-ACCESS      read-only
    STATUS          current
    DESCRIPTION     "Indicates the upper 32 bits of tmnxSubEgrQosArbitStatsFwdPkts."
    ::= { tmnxSubEgrQosArbitStatsEntry 4 }

tmnxSubEgrQosArbitStatsFwdOcts OBJECT-TYPE
    SYNTAX      Counter64
    MAX-ACCESS  read-only
    STATUS      current
    DESCRIPTION
        "The value of tmnxSubEgrQosArbitStatsFwdOcts indicates the number of
         forwarded octets, as determined by the subscriber egress policer
         control policy, offered by the Pchip to the Qchip."
    ::= { tmnxSubEgrQosArbitStatsEntry 5 }

tmnxSubEgrQosArbitStatsFwdOctsLo OBJECT-TYPE
    SYNTAX          Counter32
    MAX-ACCESS      read-only
    STATUS          current
    DESCRIPTION     "Indicates the lower 32 bits of tmnxSubEgrQosArbitStatsFwdOcts."
    ::= { tmnxSubEgrQosArbitStatsEntry 6 }

tmnxSubEgrQosArbitStatsFwdOctsHi OBJECT-TYPE
    SYNTAX          Counter32
    MAX-ACCESS      read-only
    STATUS          current
    DESCRIPTION     "Indicates the upper 32 bits of tmnxSubEgrQosArbitStatsFwdOcts."
    ::= { tmnxSubEgrQosArbitStatsEntry 7 }

-- --------------------------------------------------------
-- tmnxSubIPolFltrProfileMapTable
-- --------------------------------------------------------
tmnxSubIPolFltrProfileMapTable OBJECT-TYPE
    SYNTAX      SEQUENCE OF TmnxSubIPolFltrProfileMapEntry
    MAX-ACCESS  not-accessible
    STATUS      current
    DESCRIPTION
        "The tmnxSubIPolFltrProfileMapTable has an entry for each filter profile
         string to fitler profile name mapping defined under a subscriber
         identification policy configured in the system."
    ::= { tmnxSubMgmtObjects 96 }

tmnxSubIPolFltrProfileMapEntry OBJECT-TYPE
    SYNTAX      TmnxSubIPolFltrProfileMapEntry
    MAX-ACCESS  not-accessible
    STATUS      current
    DESCRIPTION
        "Each row entry represents a filter profile string to filter profile name
         mapping defined under a subscriber identification policy configured in
         the system. Entries can be created and deleted via SNMP SET operations
         on the object tmnxSubIPolFltrProfMapRowStatus."
    INDEX {         tmnxSubIPolName,
            IMPLIED tmnxSubIPolFltrProfMapFltrString }
    ::= { tmnxSubIPolFltrProfileMapTable 1 }

TmnxSubIPolFltrProfileMapEntry ::=
    SEQUENCE {
        tmnxSubIPolFltrProfMapFltrString DisplayString,
        tmnxSubIPolFltrProfMapRowStatus  RowStatus,
        tmnxSubIPolFltrProfMapLastMgmtCh TimeStamp,
        tmnxSubIPolFltrProfMapFltrProf   TNamedItem
    }

tmnxSubIPolFltrProfMapFltrString OBJECT-TYPE
    SYNTAX      DisplayString (SIZE (1..16))
    MAX-ACCESS  not-accessible
    STATUS      current
    DESCRIPTION
        "The value of tmnxSubIPolFltrProfMapFltrString specifies the filter
         profile string for this row."
    ::= { tmnxSubIPolFltrProfileMapEntry 1 }

tmnxSubIPolFltrProfMapRowStatus OBJECT-TYPE
    SYNTAX      RowStatus
    MAX-ACCESS  read-create
    STATUS      current
    DESCRIPTION
        "The value of tmnxSubIPolFltrProfMapRowStatus controls the creation and
         deletion of rows in this table."
    ::= { tmnxSubIPolFltrProfileMapEntry 2 }

tmnxSubIPolFltrProfMapLastMgmtCh OBJECT-TYPE
    SYNTAX      TimeStamp
    MAX-ACCESS  read-only
    STATUS      current
    DESCRIPTION
        "The value of tmnxSubIPolFltrProfMapLastMgmtCh indicates the
         sysUpTime at the time of the most recent management-initiated change to
         this table row."
    ::= { tmnxSubIPolFltrProfileMapEntry 3 }

tmnxSubIPolFltrProfMapFltrProf OBJECT-TYPE
    SYNTAX      TNamedItem
    MAX-ACCESS  read-create
    STATUS      current
    DESCRIPTION
        "The value of tmnxSubIPolFltrProfMapFltrProf specifies the filter
         profile name corresponding to this row."
    ::= { tmnxSubIPolFltrProfileMapEntry 4 }

-- ------------------------------------------------
-- tmnxSubHostSapTrkMcRDstStatTable
-- ------------------------------------------------

tmnxSubHostSapTrkMcRDstStatTable OBJECT-TYPE
    SYNTAX      SEQUENCE OF TmnxSubHostSapTrkMcRDstStatEntry
    MAX-ACCESS  not-accessible
    STATUS      current
    DESCRIPTION
        "The tmnxSubHostSapTrkMcRDstStatTable shows mcast reporting destination
         statistics information for hosts, ordered by SAP."
    ::= { tmnxSubMgmtObjects 97 }

tmnxSubHostSapTrkMcRDstStatEntry OBJECT-TYPE
    SYNTAX      TmnxSubHostSapTrkMcRDstStatEntry
    MAX-ACCESS  not-accessible
    STATUS      current
    DESCRIPTION
        "Each row entry represents mcast reporting destination statistics 
         information for a particular host.

         Rows are created or removed automatically by the system.
         
         Rows are only created where the statistics value is nonzero;
         this allows faster walking through this table; hence, it is recommended
         to perform only get-next-request operations to retrieve information
         from this table."
    INDEX { svcId, sapPortId, sapEncapValue,
            tmnxSubHostSapTrkHostAddrType, tmnxSubHostSapTrkHostAddr,
            tmnxSubHostSapTrkMcRDstStatType
          }
    ::= { tmnxSubHostSapTrkMcRDstStatTable 1 }

TmnxSubHostSapTrkMcRDstStatEntry ::= SEQUENCE
   {
        tmnxSubHostSapTrkMcRDstStatType  VRtrIgmpHostMcRDstStatType,
        tmnxSubHostSapTrkMcRDstStatVal   Counter32
   }

tmnxSubHostSapTrkMcRDstStatType OBJECT-TYPE
    SYNTAX      VRtrIgmpHostMcRDstStatType
    MAX-ACCESS  not-accessible
    STATUS      current
    DESCRIPTION
        "The value of tmnxSubHostSapTrkMcRDstStatType indicates
         the type of mcast reporting destination statistics
         contained in tmnxSubHostSapTrkMcRDstStatVal."
    ::= { tmnxSubHostSapTrkMcRDstStatEntry 1 }

tmnxSubHostSapTrkMcRDstStatVal OBJECT-TYPE
    SYNTAX      Counter32
    MAX-ACCESS  read-only
    STATUS      current
    DESCRIPTION
        "The value of tmnxSubHostSapTrkMcRDstStatVal indicates the value of the
         mcast reporting destination statistics of the type
         indicated by tmnxSubHostSapTrkMcRDstStatType."
    ::= { tmnxSubHostSapTrkMcRDstStatEntry 2 }


-- --------------------------------------------------------
-- tmnxSubAleTable
-- --------------------------------------------------------
tmnxSubAleTable OBJECT-TYPE
    SYNTAX      SEQUENCE OF TmnxSubAleEntry
    MAX-ACCESS  not-accessible
    STATUS      current
    DESCRIPTION
        "The tmnxSubAleTable contains information about
         subscribers' DSL Access Loop Encapsulation."
    ::= { tmnxSubMgmtObjects 93 }

tmnxSubAleEntry OBJECT-TYPE
    SYNTAX      TmnxSubAleEntry
    MAX-ACCESS  not-accessible
    STATUS      current
    DESCRIPTION
        "Each conceptual row represents DSL Access Loop information
         about a particular subscriber SLA profile instance."
    INDEX { tmnxSubInfoSubIdent,
            sapPortId,
            sapEncapValue,
            tmnxSLAProfName
          }
    ::= { tmnxSubAleTable 1 }

TmnxSubAleEntry ::=
    SEQUENCE {
        tmnxSubAleEncapOffset           Integer32,
        tmnxSubAleDatalink              INTEGER
    }

tmnxSubAleEncapOffset OBJECT-TYPE
    SYNTAX          Integer32
    UNITS           "bytes"
    MAX-ACCESS      read-only
    STATUS          current
    DESCRIPTION     
        "The value of tmnxSubAleEncapOffset indicates the number of bytes
         added to or subtracted from the packet size while performing rate
         calculations, in order to take into account 
         the encapsulation overhead in the DSL Access Loop.
         
         A positive number indicates that bytes are added to, a negative number
         indicates that bytes are subtracted from the actual packet size."
    ::= { tmnxSubAleEntry 1 }

tmnxSubAleDatalink OBJECT-TYPE
    SYNTAX          INTEGER { 
                        unknown (0), 
                        other (1), 
                        atm (2)  
                    }
    MAX-ACCESS      read-only
    STATUS          current
    DESCRIPTION     
        "The value of tmnxSubAleDatalink indicates the type of data link
         in the DSL Access Loop."
    ::= { tmnxSubAleEntry 2 }


--
--  The IGMP Policy Table
--

tmnxSubIgmpPolicyTable OBJECT-TYPE
    SYNTAX     SEQUENCE OF TmnxSubIgmpPolicyEntry
    MAX-ACCESS not-accessible
    STATUS     current
    DESCRIPTION
        "The table listing the host IGMP policies."
    ::= { tmnxSubIgmpHostObjs 1 }

tmnxSubIgmpPolicyEntry OBJECT-TYPE
    SYNTAX     TmnxSubIgmpPolicyEntry
    MAX-ACCESS not-accessible
    STATUS     current
    DESCRIPTION
        "Each row entry in the tmnxSubIgmpPolicyTable represents a 
         host IGMP policy."
    INDEX      { tmnxSubIgmpPlcyName }
    ::= { tmnxSubIgmpPolicyTable 1 }

TmnxSubIgmpPolicyEntry ::= SEQUENCE {
    tmnxSubIgmpPlcyName              TNamedItem,
    tmnxSubIgmpPlcyRowStatus         RowStatus,
    tmnxSubIgmpPlcyDescription       TItemDescription,
    tmnxSubIgmpPlcyImportPolicy      TPolicyStatementNameOrEmpty,
    tmnxSubIgmpPlcyHostMaxGroups     Unsigned32,
    tmnxSubIgmpPlcyAdminVersion      TmnxIgmpVersion,
    tmnxSubIgmpPlcyFastLeave         TmnxSubAdminStatus,
    tmnxSubIgmpPlcyRedirectionPolicy TPolicyStatementNameOrEmpty,    
    tmnxSubIgmpPlcyEgrRateModType    TEgrRateModType,
    tmnxSubIgmpPlcyEgrRateModSched   TNamedItemOrEmpty,
    tmnxSubIgmpPlcyPerHostReplic     TmnxSubAdminStatus,
    tmnxSubIgmpPlcyMcRprtDestName    TNamedItemOrEmpty,
    tmnxSubIgmpPlcyMcRprtOptFields   BITS,
    tmnxSubIgmpPlcyMcRprtAdminState  TmnxAdminState,
    tmnxSubIgmpPlcyHostMaxSources    Unsigned32,
    tmnxSubIgmpPlcyHostMaxGrpSources Unsigned32,
    tmnxSubIgmpPlcyPerHostMcastMac   TruthValue
}

tmnxSubIgmpPlcyName       OBJECT-TYPE
    SYNTAX      TNamedItem
    MAX-ACCESS  not-accessible
    STATUS      current
    DESCRIPTION
        "The value of tmnxSubIgmpPlcyName indicates the name of the host IGMP policy."
    ::= { tmnxSubIgmpPolicyEntry 1 }

tmnxSubIgmpPlcyRowStatus OBJECT-TYPE
    SYNTAX     RowStatus
    MAX-ACCESS read-create
    STATUS     current
    DESCRIPTION
        "The value of tmnxSubIgmpPlcyRowStatus controls the creation and
         deletion of rows in the table."
    ::= { tmnxSubIgmpPolicyEntry 2 }

tmnxSubIgmpPlcyDescription OBJECT-TYPE
    SYNTAX      TItemDescription
    MAX-ACCESS  read-create
    STATUS      current
    DESCRIPTION
        "The value of tmnxSubIgmpPlcyDescription specifies the user provided
         description of this host IGMP policy."
    DEFVAL { ''H }
    ::= { tmnxSubIgmpPolicyEntry 3 }

tmnxSubIgmpPlcyImportPolicy OBJECT-TYPE
    SYNTAX     TPolicyStatementNameOrEmpty
    MAX-ACCESS read-create
    STATUS     current
    DESCRIPTION
        "tmnxSubIgmpPlcyImportPolicy specifies the import policy that is to be applied
         on this host IGMP policy."
    DEFVAL { ''H }
    ::= { tmnxSubIgmpPolicyEntry 4 }

tmnxSubIgmpPlcyHostMaxGroups OBJECT-TYPE
    SYNTAX     Unsigned32 (0|1..16000)
    MAX-ACCESS read-create
    STATUS     current
    DESCRIPTION
        "The value of tmnxSubIgmpPlcyHostMaxGroups specifies the maximum number of groups
         for which IGMP can have local receiver information based on received
         IGMP reports for this host. When this configuration is changed 
         dynamically to a value lower than currently accepted number of groups,
         the groups that are already accepted are not deleted.  Only new groups 
         will not be allowed.  When this object has a value of 0, there is no 
         limit to the number of groups."
    DEFVAL { 0 }
    ::= { tmnxSubIgmpPolicyEntry 5 }

tmnxSubIgmpPlcyAdminVersion OBJECT-TYPE
    SYNTAX     TmnxIgmpVersion
    MAX-ACCESS read-create
    STATUS     current
    DESCRIPTION
        "The configured version of IGMP which is running for this host.
         This object can be used to configure a router capable of
         running either value.  For IGMP to function correctly, all
         routers on a LAN must be configured to run the same version
         of IGMP on that LAN."
    DEFVAL { version3 }
    ::= { tmnxSubIgmpPolicyEntry 6 }

tmnxSubIgmpPlcyFastLeave OBJECT-TYPE
    SYNTAX     TmnxSubAdminStatus
    MAX-ACCESS read-create
    STATUS     current
    DESCRIPTION
        "The value of the object tmnxSubIgmpPlcyFastLeave specifies
         whether fast leave is allowed for this host.
         
         If set to 'enabled(1)', the system prunes the port on which an IGMP
         'leave' message has been received without waiting for the Group
         Specific Query to timeout."
    DEFVAL { enabled }
    ::= { tmnxSubIgmpPolicyEntry 7 }

tmnxSubIgmpPlcyRedirectionPolicy OBJECT-TYPE
    SYNTAX     TPolicyStatementNameOrEmpty
    MAX-ACCESS read-create
    STATUS     current
    DESCRIPTION
        "tmnxSubIgmpPlcyRedirectionPolicy specifies the redirection policy that
         is to be applied on this host IGMP policy."
    DEFVAL { ''H }
    ::= { tmnxSubIgmpPolicyEntry 8}

tmnxSubIgmpPlcyEgrRateModType OBJECT-TYPE
    SYNTAX      TEgrRateModType
    MAX-ACCESS  read-create
    STATUS      current
    DESCRIPTION
        "The value of tmnxSubIgmpPlcyEgrRateModType specifies the egress-rate
         modification that is to be applied.

         If set to 'namedScheduler', the scheduler as defined in
         tmnxSubIgmpPlcyEgrRateModSched is used."
    DEFVAL { none }
    ::= { tmnxSubIgmpPolicyEntry 9 }

tmnxSubIgmpPlcyEgrRateModSched OBJECT-TYPE
    SYNTAX      TNamedItemOrEmpty
    MAX-ACCESS  read-create
    STATUS      current
    DESCRIPTION
        "The value of tmnxSubIgmpPlcyEgrRateModSched specifies the scheduler to
         be applied for egress rate modification.

         The value is only considered if tmnxSubIgmpPlcyEgrRateModType is set to
         'namedScheduler'."
    DEFVAL { "" }
    ::= { tmnxSubIgmpPolicyEntry 10 }

tmnxSubIgmpPlcyPerHostReplic OBJECT-TYPE
    SYNTAX     TmnxSubAdminStatus
    MAX-ACCESS read-create
    STATUS     current
    DESCRIPTION
        "The value of the object tmnxSubIgmpPlcyPerHostReplic specifies
         whether per-host replication is allowed for this host.
         
         If set to 'enabled(1)', outgoing traffic will be replicated per host,
         else it will be replicated per SAP.
         
         When traffic is replicated per host, a copy of each outgoing 
         multicast traffic packet will be sent to the unicast MAC address of 
         each host individually, else a single copy will be sent to the 
         multicast MAC address per SAP.
         
         This is only applicable for non-PPP hosts. In case of PPP host,
         traffic is always replicated per host."
    DEFVAL { disabled }
    ::= { tmnxSubIgmpPolicyEntry 11 }

tmnxSubIgmpPlcyMcRprtDestName OBJECT-TYPE
    SYNTAX      TNamedItemOrEmpty
    MAX-ACCESS  read-create
    STATUS      current
    DESCRIPTION
        "The value of tmnxSubIgmpPlcyMcRprtDestName indicates the multicast
         reporting destination 
         (found in TIMETRA-MCAST-PATH-MGMT-MIB::tmnxMcPathRprtDestTable)
         or it can be an empty string."
    DEFVAL { ''H }
    ::= { tmnxSubIgmpPolicyEntry 12 }

tmnxSubIgmpPlcyMcRprtOptFields OBJECT-TYPE
    SYNTAX      BITS {
                    hostMac             (0),
                    pppoeSessionId      (1),
                    svcId               (2),
                    sapId               (3)
                }
    MAX-ACCESS  read-create
    STATUS      current
    DESCRIPTION
        "The value of tmnxSubIgmpPlcyMcRprtOptFields specifies what optional
        fields should be included into the multicast reporting messages."
    DEFVAL { { } }
    ::= { tmnxSubIgmpPolicyEntry 13 }

tmnxSubIgmpPlcyMcRprtAdminState OBJECT-TYPE
    SYNTAX          TmnxAdminState
    MAX-ACCESS      read-create
    STATUS          current
    DESCRIPTION
        "The value of tmnxSubIgmpPlcyMcRprtAdminState indicates the administrative
         state of the multicast reporting. When the value is 'outOfService', 
         no multicast reports are sent. When it is 'inService', multicast reports
         are sent to the destination as indicated by tmnxSubIgmpPlcyMcRprtDestName."
    DEFVAL { outOfService }
    ::= { tmnxSubIgmpPolicyEntry 14 }

tmnxSubIgmpPlcyHostMaxSources OBJECT-TYPE
    SYNTAX     Unsigned32 (0|1..1000)
    MAX-ACCESS read-create
    STATUS     current
    DESCRIPTION
        "The value of tmnxSubIgmpPlcyHostMaxSources specifies the maximum number
         of sources for which IGMP can have local receiver information based on 
         received IGMP reports for this host. When this configuration is changed 
         dynamically to a value lower than currently accepted number of sources,
         the sources that are already accepted are not deleted. Only new sources 
         will not be allowed.  When this object has a value of 0, there is no 
         limit to the number of sources."
    DEFVAL { 0 }
    ::= { tmnxSubIgmpPolicyEntry 15 }

tmnxSubIgmpPlcyHostMaxGrpSources OBJECT-TYPE
    SYNTAX     Unsigned32 (0|1..32000)
    MAX-ACCESS read-create
    STATUS     current
    DESCRIPTION
        "The value of tmnxSubIgmpPlcyHostMaxGrpSources specifies the maximum
         number of group sources for which IGMP can have local receiver 
         information based on received IGMP reports for this host. When this 
         configuration is changed dynamically to a value lower than currently 
         accepted number of group sources, the group sources that are already
         accepted are not deleted. Only new group sources will not be allowed.
         When this object has a value of 0, there is no limit to the number 
         of group sources."
    DEFVAL { 0 }
    ::= { tmnxSubIgmpPolicyEntry 16 }

tmnxSubIgmpPlcyPerHostMcastMac OBJECT-TYPE
    SYNTAX     TruthValue
    MAX-ACCESS read-create
    STATUS     current
    DESCRIPTION
        "The value of the object tmnxSubIgmpPlcyPerHostMcastMac specifies
         which type of destination mac address will be used for outgoing traffic 
         when tmnxSubIgmpPlcyPerHostReplic is set to 'enabled(1)'.
         
         If set to 'true', outgoing traffic will be sent to a multicast mac
         address.  If set to 'false' it will be sent to the host unicast mac
         address."
    DEFVAL { false }
    ::= { tmnxSubIgmpPolicyEntry 17 }

-- --------------------------------------------------------
-- tmnxSLAProfInstOverridesTable
-- --------------------------------------------------------
tmnxSLAProfInstOverridesTable OBJECT-TYPE
    SYNTAX      SEQUENCE OF TmnxSLAProfInstOverridesEntry
    MAX-ACCESS  not-accessible
    STATUS      current
    DESCRIPTION
        "A table that contains SLA Profile instance qos overrides."
    ::= { tmnxSubMgmtObjects 85 }

tmnxSLAProfInstOverridesEntry OBJECT-TYPE
    SYNTAX      TmnxSLAProfInstOverridesEntry
    MAX-ACCESS  not-accessible
    STATUS      current
    DESCRIPTION
        "Information about a specific SLA Profile instance qos override."
    INDEX { tmnxSubInfoSubIdent,
            sapPortId,
            sapEncapValue,
            tmnxSLAProfName,
            tmnxSLAProfInstOvrDirection,
            tmnxSLAProfInstOvrType,
            tmnxSLAProfInstOvrTypeId,
            tmnxSLAProfInstOvrTypeName
            }
    ::= { tmnxSLAProfInstOverridesTable 1 }

TmnxSLAProfInstOverridesEntry ::=
    SEQUENCE {
        tmnxSLAProfInstOvrDirection     TDirectionIngEgr,
        tmnxSLAProfInstOvrType          TQosOverrideType,
        tmnxSLAProfInstOvrTypeId        Integer32,
        tmnxSLAProfInstOvrTypeName      TNamedItemOrEmpty,
        tmnxSLAProfInstOvrPIR           TPIRRateOverride,
        tmnxSLAProfInstOvrCIR           TCIRRateOverride,
        tmnxSLAProfInstOvrCBS           TBurstSizeBytesOvr,
        tmnxSLAProfInstOvrMBS           TBurstSizeBytesOvr,
        tmnxSLAProfInstOvrWrrWeight     THsmdaWrrWeightOverride,
        tmnxSLAProfInstOvrPIRHi         Unsigned32,
        tmnxSLAProfInstOvrPIRLo         Unsigned32,
        tmnxSLAProfInstOvrCIRHi         Unsigned32,
        tmnxSLAProfInstOvrCIRLo         Unsigned32,
        tmnxSLAProfInstOvrSummedCIR     TruthValue
    }

tmnxSLAProfInstOvrDirection OBJECT-TYPE
    SYNTAX          TDirectionIngEgr
    MAX-ACCESS      not-accessible
    STATUS          current
    DESCRIPTION     "The value of tmnxSLAProfInstOvrDirection indicates whether
                     this row specifies ingress or egress qos override 
                     parameters."
    ::= { tmnxSLAProfInstOverridesEntry 1 }

tmnxSLAProfInstOvrType OBJECT-TYPE
    SYNTAX          TQosOverrideType
    MAX-ACCESS      not-accessible
    STATUS          current
    DESCRIPTION     "The value of tmnxSLAProfInstOvrType indicates what field
                     has been overwritten by this row."
    ::= { tmnxSLAProfInstOverridesEntry 2 }

tmnxSLAProfInstOvrTypeId OBJECT-TYPE
    SYNTAX          Integer32
    MAX-ACCESS      not-accessible
    STATUS          current
    DESCRIPTION     "The value of tmnxSLAProfInstOvrTypeId indicates the id of
                     the queue/policer that has been overwritten by this row.
                     
                     If the value of tmnxSLAProfInstOvrType is not 'queue (1)'
                     or 'policer (2)', this field must be set to zero (0)."
    ::= { tmnxSLAProfInstOverridesEntry 3 }

tmnxSLAProfInstOvrTypeName OBJECT-TYPE
    SYNTAX          TNamedItemOrEmpty
    MAX-ACCESS      not-accessible
    STATUS          current
    DESCRIPTION     "The value of tmnxSLAProfInstOvrTypeName indicates the
                     name of the scheduler/arbiter that has been overwritten by
                     this row.
                     
                     If the value of tmnxSLAProfInstOvrTypeId is not 
                     'arbiter (4)' or 'scheduler (5)', this field must be set to
                     zero (0)."
    ::= { tmnxSLAProfInstOverridesEntry 4 }

tmnxSLAProfInstOvrPIR OBJECT-TYPE
    SYNTAX          TPIRRateOverride
    MAX-ACCESS      read-only
    STATUS          obsolete
    DESCRIPTION     "The value of tmnxSLAProfInstOvrPIR indicates the PIR rate
                     in kbps allowed for the object overwritten by this row.

                     This object is obsoleted in 11.0 Release. It is replaced by 
                     tmnxSLAProfInstOvrPIRHi and tmnxSLAProfInstOvrPIRLo."
    ::= { tmnxSLAProfInstOverridesEntry 5 }

tmnxSLAProfInstOvrCIR OBJECT-TYPE
    SYNTAX          TCIRRateOverride
    MAX-ACCESS      read-only
    STATUS          obsolete
    DESCRIPTION     "The value of tmnxSLAProfInstOvrCIR indicates the CIR rate
                     in kbps allowed for the object overwritten by this row.

                     This object is obsoleted in 11.0 Release. It is replaced by 
                     tmnxSLAProfInstOvrCIRHi and tmnxSLAProfInstOvrCIRLo."
    ::= { tmnxSLAProfInstOverridesEntry 6 }

tmnxSLAProfInstOvrCBS OBJECT-TYPE
    SYNTAX          TBurstSizeBytesOvr
    MAX-ACCESS      read-only
    STATUS          current
    DESCRIPTION     "The value of tmnxSLAProfInstOvrCBS indicates the amount of
                     reserved buffer space (in bytes) for the object
                     overwritten by this row."
    ::= { tmnxSLAProfInstOverridesEntry 7 }

tmnxSLAProfInstOvrMBS OBJECT-TYPE
    SYNTAX          TBurstSizeBytesOvr
    MAX-ACCESS      read-only
    STATUS          current
    DESCRIPTION     "The value of tmnxSLAProfInstOvrMBS indicates the maximum
                     amount of reserved buffer space (in bytes) for the object
                     overwritten by this row."
    ::= { tmnxSLAProfInstOverridesEntry 8 }

tmnxSLAProfInstOvrWrrWeight OBJECT-TYPE
    SYNTAX          THsmdaWrrWeightOverride
    MAX-ACCESS      read-only
    STATUS          current
    DESCRIPTION     
    "The value of tmnxSLAProfInstOvrWrrWeight specifies the weight of this queue
     for the HSMDA scheduler.
     
     The weight determines how much bandwidth this queue gets out of the 
     total rate for the scheduling class.
     
     The value of tmnxSLAProfInstOvrWrrWeight is only relevant if the value of
     tmnxSLAProfInstOvrType is equal to 'queue', and if the queue specified in
     tmnxSLAProfInstOvrTypeId is referenced in the value of 
     TIMETRA-QOS-MIB::tHsmdaWrrPolicyIncludeQueues of the Weighted Round Robin
     policy associated wit this PPP session."
    ::= { tmnxSLAProfInstOverridesEntry 9 }

tmnxSLAProfInstOvrPIRHi OBJECT-TYPE
    SYNTAX       Unsigned32 (0 | 4294967295)
    UNITS        "kbps"
    MAX-ACCESS   read-only
    STATUS       current
    DESCRIPTION
        "The value of tmnxSLAProfInstOvrPIRHi indicates upper 32 bits of the PIR
         rate allowed for the object overwritten by this row.    

         When the value of tmnxSLAProfInstOvrPIRHi along with the value of 
         tmnxSLAProfInstOvrPIRLo is equal to 4294967295 (0xFFFFFFFF), rate for
         this scheduler indicates maximum rate.

         The value of tmnxSLAProfInstOvrPIRHi equal to 4294967295 (0xFFFFFFFF)
         and the value of tmnxSLAProfInstOvrPIRLo equal to 
         4294967294 (0xFFFFFFFE) indicates no overrides."
    ::= { tmnxSLAProfInstOverridesEntry 10 }

tmnxSLAProfInstOvrPIRLo OBJECT-TYPE
    SYNTAX       Unsigned32 (1..3200000000 | 4294967294 | 4294967295)
    UNITS        "kbps"
    MAX-ACCESS   read-only
    STATUS       current
    DESCRIPTION
        "The value of tmnxSLAProfInstOvrPIRHi indicates lower 32 bits of the PIR
         rate allowed for the object overwritten by this row.    
    
         When the value of tmnxSLAProfInstOvrPIRHi along with the value of 
         tmnxSLAProfInstOvrPIRLo is equal to 4294967295 (0xFFFFFFFF), rate for
         this scheduler indicates maximum rate.
    
         The value of tmnxSLAProfInstOvrPIRHi equal to 4294967295 (0xFFFFFFFF)
         and the value of tmnxSLAProfInstOvrPIRLo equal to 
         4294967294 (0xFFFFFFFE) indicates no overrides."
    ::= { tmnxSLAProfInstOverridesEntry 11 }

tmnxSLAProfInstOvrCIRHi OBJECT-TYPE
    SYNTAX       Unsigned32 (0 | 4294967295)
    UNITS        "kbps"
    MAX-ACCESS   read-only
    STATUS       current
    DESCRIPTION
        "The value of tmnxSLAProfInstOvrCIRHi indicates upper 32 bits of the CIR
         rate allowed for the object overwritten by this row.    

         When the value of tmnxSLAProfInstOvrCIRHi along with the value of 
         tmnxSLAProfInstOvrCIRLo is equal to 4294967295 (0xFFFFFFFF), rate for
         this scheduler indicates maximum rate.

         The value of tmnxSLAProfInstOvrCIRHi equal to 4294967295 (0xFFFFFFFF)
         and the value of tmnxSLAProfInstOvrCIRLo equal to 
         4294967294 (0xFFFFFFFE) indicates no overrides."
    ::= { tmnxSLAProfInstOverridesEntry 12 }

tmnxSLAProfInstOvrCIRLo OBJECT-TYPE
    SYNTAX       Unsigned32 (0..3200000000 | 4294967294 | 4294967295)
    UNITS        "kbps"
    MAX-ACCESS   read-only
    STATUS       current
    DESCRIPTION
        "The value of tmnxSLAProfInstOvrCIRHi indicates lower 32 bits of the CIR
         rate allowed for the object overwritten by this row.    
    
         When the value of tmnxSLAProfInstOvrCIRHi along with the value of 
         tmnxSLAProfInstOvrCIRLo is equal to 4294967295 (0xFFFFFFFF), rate for
         this scheduler indicates maximum rate.
    
         The value of tmnxSLAProfInstOvrCIRHi equal to 4294967295 (0xFFFFFFFF)
         and the value of tmnxSLAProfInstOvrCIRLo equal to 
         4294967294 (0xFFFFFFFE) indicates no overrides."
    ::= { tmnxSLAProfInstOverridesEntry 13 }

tmnxSLAProfInstOvrSummedCIR OBJECT-TYPE
    SYNTAX      TruthValue
    MAX-ACCESS  read-only
    STATUS      current
    DESCRIPTION
        "The value of tmnxSLAProfInstOvrSummedCIR indicates if the CIR should
         be used as the summed CIR values of the children schedulers or queues.
         If set to 'true', the applicable scheduler CIR (tmnxSLAProfInstOvrCIRHi
         and tmnxSLAProfInstOvrCIRLo) loses its meaning.

         The value of tmnxSLAProfInstOvrCIRHi equal to 4294967295 (0xFFFFFFFF)
         and the value of tmnxSLAProfInstOvrCIRLo equal to 
         4294967294 (0xFFFFFFFE) indicates no overrides."
    ::= { tmnxSLAProfInstOverridesEntry 14 }

--
--  The IGMP Policy Static Table
--

tmnxSubIgmpPolicyStaticTable OBJECT-TYPE
    SYNTAX     SEQUENCE OF TmnxSubIgmpPolicyStaticEntry
    MAX-ACCESS not-accessible
    STATUS     current
    DESCRIPTION
        "The table listing the host IGMP policy statics."
    ::= { tmnxSubIgmpHostObjs 2 }

tmnxSubIgmpPolicyStaticEntry OBJECT-TYPE
    SYNTAX     TmnxSubIgmpPolicyStaticEntry
    MAX-ACCESS not-accessible
    STATUS     current
    DESCRIPTION
        "Each row entry in the tmnxSubIgmpPolicyStaticTable represents a 
         host IGMP policy statics."
    INDEX      { tmnxSubIgmpPlcyName,
                 tmnxSubIgmpHostGroupAddress,
                 tmnxSubIgmpHostGrpSrcAddress }
    ::= { tmnxSubIgmpPolicyStaticTable 1 }

TmnxSubIgmpPolicyStaticEntry ::= SEQUENCE {
    tmnxSubIgmpHostGroupAddress      IpAddress,
    tmnxSubIgmpHostGrpSrcAddress     IpAddress,
    tmnxSubIgmpPlcyStaticRowStatus   RowStatus
}

tmnxSubIgmpHostGroupAddress OBJECT-TYPE
    SYNTAX     IpAddress
    MAX-ACCESS not-accessible
    STATUS     current
    DESCRIPTION
        "The IP multicast group address for which this entry
         contains information."
    ::= { tmnxSubIgmpPolicyStaticEntry 1 }

tmnxSubIgmpHostGrpSrcAddress OBJECT-TYPE
    SYNTAX     IpAddress
    MAX-ACCESS not-accessible
    STATUS     current
    DESCRIPTION
        "The address of the source sending multicast traffic to the group
         identified by tmnxSubIgmpHostGroupAddress."
    ::= { tmnxSubIgmpPolicyStaticEntry 2 }

tmnxSubIgmpPlcyStaticRowStatus OBJECT-TYPE
    SYNTAX     RowStatus
    MAX-ACCESS read-create
    STATUS     current
    DESCRIPTION
        "The activation of a row enables IGMP for the host. The
         destruction of a row disables IGMP for the host."
    ::= { tmnxSubIgmpPolicyStaticEntry 3 }


-- ----------------------------------------
-- tmnxSubIgmpHostsTable
-- ----------------------------------------
tmnxSubIgmpHostsTable OBJECT-TYPE
    SYNTAX      SEQUENCE OF TmnxSubIgmpHostsEntry
    MAX-ACCESS  not-accessible
    STATUS      current
    DESCRIPTION
        "The tmnxSubIgmpHostsTable has an entry for each subscriber having 
         IGMP hosts in the system."
    ::= { tmnxSubIgmpHostObjs 3 }

tmnxSubIgmpHostsEntry OBJECT-TYPE
    SYNTAX      TmnxSubIgmpHostsEntry
    MAX-ACCESS  not-accessible
    STATUS      current
    DESCRIPTION
        "Each row entry contains information about a particular subscriber
         host available in the system."
    INDEX      { tmnxSubIgmpHostsSubIdent,
                 vRtrID, 
                 tmnxSubIgmpHostsHostAddress }
    ::= { tmnxSubIgmpHostsTable 1 }


TmnxSubIgmpHostsEntry ::= SEQUENCE {
    tmnxSubIgmpHostsSubIdent         DisplayString,
    tmnxSubIgmpHostsHostAddress      IpAddress,
    tmnxSubIgmpHostsCreated          TimeStamp
}

tmnxSubIgmpHostsSubIdent OBJECT-TYPE
    SYNTAX      DisplayString (SIZE (1..32))
    MAX-ACCESS  not-accessible
    STATUS      current
    DESCRIPTION
        "The value of tmnxSubIgmpHostsSubIdent specifies the subscriber
         identification of this subscriber."
    ::= { tmnxSubIgmpHostsEntry 1 }

tmnxSubIgmpHostsHostAddress OBJECT-TYPE
    SYNTAX     IpAddress
    MAX-ACCESS not-accessible
    STATUS     current
    DESCRIPTION
        "The IP host address for which this entry contains information."
    ::= { tmnxSubIgmpHostsEntry 2 }

tmnxSubIgmpHostsCreated OBJECT-TYPE
    SYNTAX      TimeStamp
    MAX-ACCESS  read-only
    STATUS      current
    DESCRIPTION
        "The sysUpTime when this row was created."
    ::= { tmnxSubIgmpHostsEntry 3 }


-- ------------------------------------------------
-- tmnxSubIgmpPlcySubscriberTable
-- ------------------------------------------------
tmnxSubIgmpPlcySubscriberTable OBJECT-TYPE
    SYNTAX      SEQUENCE OF TmnxSubIgmpPlcySubscriberEntry
    MAX-ACCESS  not-accessible
    STATUS      current
    DESCRIPTION
        "The tmnxSubIgmpPlcySubscriberTable shows the subscribers associated
         with their IGMP Host Tracking policy."
    ::= { tmnxSubIgmpHostObjs 4 }

tmnxSubIgmpPlcySubscriberEntry OBJECT-TYPE
    SYNTAX      TmnxSubIgmpPlcySubscriberEntry
    MAX-ACCESS  not-accessible
    STATUS      current
    DESCRIPTION
        "Each row entry represents a particular subscriber 
         associated with a particular IGMP Host Tracking policy."
    INDEX {
            tmnxSubIgmpPlcyName, 
            IMPLIED tmnxSubIgmpPlcySubscriberId
          }
    ::= { tmnxSubIgmpPlcySubscriberTable 1 }

TmnxSubIgmpPlcySubscriberEntry ::= SEQUENCE
   {
        tmnxSubIgmpPlcySubscriberId       DisplayString
   }

tmnxSubIgmpPlcySubscriberId OBJECT-TYPE
    SYNTAX      DisplayString (SIZE (1..32))
    MAX-ACCESS  read-only
    STATUS      current
    DESCRIPTION
        "The value of tmnxSubIgmpPlcySubscriberId indicates the subscriber
         identification."
    ::= { tmnxSubIgmpPlcySubscriberEntry 1 }


-- ------------------------------------------------
-- tmnxSubIgmpStatusTable
-- ------------------------------------------------
--  Sparse Dependent Extension of the tmnxSubscriberInfoTable
--  The same indexes are used for both the base table, tmnxSubscriberInfoTable,
--  and the sparse dependent table, tmnxSubIgmpStatusTable.
--
--  This in effect extends the tmnxSubscriberInfoTable with additional columns.
--  A row is automatically created in the tmnxSubIgmpStatusTable
--  for each applicable row in the tmnxSubscriberInfoTable .
--
--  Deletion of a row in the tmnxSubscriberInfoTable results in the
--  same fate for the row in the tmnxSubIgmpStatusTable.

tmnxSubIgmpStatusTable OBJECT-TYPE
    SYNTAX      SEQUENCE OF TmnxSubIgmpStatusEntry
    MAX-ACCESS  not-accessible
    STATUS      current
    DESCRIPTION
        "The tmnxSubIgmpStatusTable has an entry for each subscriber
         that is associated with a IGMP policy.

         A subscriber is associated with a IGMP policy if the value of
         the object tmnxSubInfoSubProfile refers to a subscriber policy where
         the value of the object tmnxSubProfIgmpPolicy is not empty."
    ::= { tmnxSubIgmpHostObjs 5 }

tmnxSubIgmpStatusEntry OBJECT-TYPE
    SYNTAX      TmnxSubIgmpStatusEntry
    MAX-ACCESS  not-accessible
    STATUS      current
    DESCRIPTION
        "Each row entry represents status information about the IGMP policy
         of this subscriber's hosts.

         Rows are created or removed automatically by the system."
    INDEX { IMPLIED tmnxSubInfoSubIdent }
    ::= { tmnxSubIgmpStatusTable 1 }

TmnxSubIgmpStatusEntry ::= SEQUENCE
   {
        tmnxSubIgmpStatusPlcyName         TNamedItemOrEmpty
   }

tmnxSubIgmpStatusPlcyName OBJECT-TYPE
    SYNTAX      TNamedItemOrEmpty
    MAX-ACCESS  read-only
    STATUS      current
    DESCRIPTION
        "The value of tmnxSubIgmpStatusPlcyName indicates
         the name of the IGMP policy associated with this subscriber.

         An empty string indicates that no IGMP policy is associated
         with this subscriber."
    ::= { tmnxSubIgmpStatusEntry 1 }


-- --------------------------------------------------------
-- tmnxSLAProfCMapTable
-- --------------------------------------------------------
--  Augmentation of the tmnxSLAProfileTable
--  Use of AUGMENTS clause implies a one-to-one dependent relationship
--  between the base table, tmnxSLAProfileTable, and the augmenting table,
--  tmnxSLAProfCMapTable. This in effect extends the tmnxSLAProfileTable
--  with additional columns. Creation (or deletion) of a row in the
--  tmnxSLAProfileTable results in the same fate for the row in the
--  tmnxSLAProfCMapTable.

tmnxSLAProfCMapTable OBJECT-TYPE
    SYNTAX      SEQUENCE OF TmnxSLAProfCMapEntry
    MAX-ACCESS  not-accessible
    STATUS      current
    DESCRIPTION
        "The tmnxSLAProfCMapTable contains objects to configure a Credit Control
         category map per SLA Profile."
    ::= { tmnxSubMgmtObjects 86 }

tmnxSLAProfCMapEntry OBJECT-TYPE
    SYNTAX      TmnxSLAProfCMapEntry
    MAX-ACCESS  not-accessible
    STATUS      current
    DESCRIPTION
        "Each conceptual row represents configuration of a particular Credit
         Control category map for a particular SLA profile.
         
         Entries in this table are created and destroyed automatically
         by the system."
    AUGMENTS { tmnxSLAProfileEntry }
    ::= { tmnxSLAProfCMapTable 1 }

TmnxSLAProfCMapEntry ::=
    SEQUENCE {
        tmnxSLAProfCMapName              TNamedItemOrEmpty
    }

    tmnxSLAProfCMapName OBJECT-TYPE
    SYNTAX      TNamedItemOrEmpty
    MAX-ACCESS  read-create
    STATUS      current
    DESCRIPTION
        "The value of tmnxSLAProfCMapName specifies
         the Credit Control category map associated with this SLA profile.
         
         Either the value of this object must be empty or the value of 
         tmnxSLAProfCreditControlPlcy must be empty."
    ::= { tmnxSLAProfCMapEntry 1 }
    
-- --------------------------------------------------------
-- tmnxSLAProfCatTable
-- --------------------------------------------------------
tmnxSLAProfCatTable OBJECT-TYPE
    SYNTAX      SEQUENCE OF TmnxSLAProfCatEntry
    MAX-ACCESS  not-accessible
    STATUS      current
    DESCRIPTION
        "The tmnxSLAProfCatTable contains objects to configure Credit Control
         categories per SLA Profile.

         Entries in this table can be created or deleted via SNMP operations."
    ::= { tmnxSubMgmtObjects 87 }

tmnxSLAProfCatEntry OBJECT-TYPE
    SYNTAX      TmnxSLAProfCatEntry
    MAX-ACCESS  not-accessible
    STATUS      current
    DESCRIPTION
        "Each conceptual row represents configuration of a particular Credit
         Control category for a particular SLA profile.
         
         The SLA profile cannot have a row in this table while the value of
         its object tmnxSLAProfCreditControlPlcy is not empty."
    INDEX { tmnxSLAProfName,
            tmnxSubApCMapName,
            tmnxSubApCategoryName
          }
    ::= { tmnxSLAProfCatTable 1 }

TmnxSLAProfCatEntry ::=
    SEQUENCE {
        tmnxSLAProfCatLastMgmtChange     TimeStamp,
        tmnxSLAProfCatRowStatus          RowStatus,
        tmnxSLAProfCatTimeout            Unsigned32,
        tmnxSLAProfCatTimeoutAction      INTEGER
    }

tmnxSLAProfCatLastMgmtChange OBJECT-TYPE
    SYNTAX      TimeStamp
    MAX-ACCESS  read-only
    STATUS      current
    DESCRIPTION
        "The value of tmnxSLAProfCatLastMgmtChange indicates the sysUpTime at
         the time of the most recent management-initiated change to this
         table row."
    ::= { tmnxSLAProfCatEntry 1 }

tmnxSLAProfCatRowStatus OBJECT-TYPE
    SYNTAX      RowStatus
    MAX-ACCESS  read-create
    STATUS      current
    DESCRIPTION
       "The value of tmnxSLAProfCatRowStatus specifies the row status of this row."
    ::= { tmnxSLAProfCatEntry 2 }

tmnxSLAProfCatTimeout OBJECT-TYPE
    SYNTAX      Unsigned32 (0|60..15552000)
    UNITS       "seconds"
    MAX-ACCESS  read-create
    STATUS      current
    DESCRIPTION
        "The value of tmnxSLAProfCatTimeout specifies 
         the time that this category can stay below its activity-threshold 
         before action is taken."
    DEFVAL { 0 }
    ::= { tmnxSLAProfCatEntry 3 }

tmnxSLAProfCatTimeoutAction OBJECT-TYPE
    SYNTAX      INTEGER {
                    terminate                        (1),
                    shcvCheck                        (2) 
                }
    UNITS       "seconds"
    MAX-ACCESS  read-create
    STATUS      current
    DESCRIPTION
        "The value of tmnxSLAProfCatTimeoutAction specifies 
         the action to be taken when the idle time is elapsed.
         
         The value of this object is only relevant when the 
         actual idle time is not equal to zero.
         
         The actual idle time is the value of the object tmnxSLAProfCatTimeout
         or the value of the object tmnxSPICatQuotaHoldingTime in the
         corresponding row in the tmnxSPICatTable.
         
         The value 'shcvCheck' specifies that a Subscriber Host
         Connectivity Verification check be started."
    DEFVAL { terminate }
    ::= { tmnxSLAProfCatEntry 4 }

-- --------------------------------------------------------
-- tmnxSubOverridesTable
-- --------------------------------------------------------
tmnxSubOverridesTable OBJECT-TYPE
    SYNTAX      SEQUENCE OF TmnxSubOverridesEntry
    MAX-ACCESS  not-accessible
    STATUS      current
    DESCRIPTION
        "A table that contains subscriber qos overrides."
    ::= { tmnxSubMgmtObjects 88 }

tmnxSubOverridesEntry OBJECT-TYPE
    SYNTAX      TmnxSubOverridesEntry
    MAX-ACCESS  not-accessible
    STATUS      current
    DESCRIPTION
        "Information about a specific subscriber qos override."
    INDEX { tmnxSubInfoSubIdent,
            tmnxSubOvrDirection,
            tmnxSubOvrType,
            tmnxSubOvrTypeId,
            tmnxSubOvrTypeName
            }
    ::= { tmnxSubOverridesTable 1 }

TmnxSubOverridesEntry ::=
    SEQUENCE {
        tmnxSubOvrDirection     TDirectionIngEgr,
        tmnxSubOvrType          TQosOverrideType,
        tmnxSubOvrTypeId        Integer32,
        tmnxSubOvrTypeName      TNamedItemOrEmpty,
        tmnxSubOvrPIR           TPIRRateOverride,
        tmnxSubOvrCIR           TCIRRateOverride,
        tmnxSubOvrCBS           TBurstSizeBytesOvr,
        tmnxSubOvrMBS           TBurstSizeBytesOvr,
        tmnxSubOvrWrrWeight     THsmdaWrrWeightOverride,
        tmnxSubOvrPIRHi         Unsigned32,
        tmnxSubOvrPIRLo         Unsigned32,
        tmnxSubOvrCIRHi         Unsigned32,
        tmnxSubOvrCIRLo         Unsigned32,
        tmnxSubOvrSummedCIR     TruthValue
    }

tmnxSubOvrDirection OBJECT-TYPE
    SYNTAX          TDirectionIngEgr
    MAX-ACCESS      not-accessible
    STATUS          current
    DESCRIPTION     "The value of tmnxSubOvrDirection indicates whether
                     this row specifies ingress or egress qos override 
                     parameters."
    ::= { tmnxSubOverridesEntry 1 }

tmnxSubOvrType OBJECT-TYPE
    SYNTAX          TQosOverrideType
    MAX-ACCESS      not-accessible
    STATUS          current
    DESCRIPTION     "The value of tmnxSubOvrType indicates what field
                     has been overwritten by this row."
    ::= { tmnxSubOverridesEntry 2 }

tmnxSubOvrTypeId OBJECT-TYPE
    SYNTAX          Integer32
    MAX-ACCESS      not-accessible
    STATUS          current
    DESCRIPTION     "The value of tmnxSubOvrTypeId indicates the id of
                     the queue/policer that has been overwritten by this row.
                     
                     If the value of tmnxSubOvrType is not 'queue (1)'
                     or 'policer (2)', this field must be set to zero (0)."
    ::= { tmnxSubOverridesEntry 3 }

tmnxSubOvrTypeName OBJECT-TYPE
    SYNTAX          TNamedItemOrEmpty
    MAX-ACCESS      not-accessible
    STATUS          current
    DESCRIPTION     "The value of tmnxSubOvrTypeName indicates the
                     name of the scheduler/arbiter that has been overwritten by
                     this row.
                     
                     If the value of tmnxSubOvrTypeId is not 
                     'arbiter (4)' or 'scheduler (5)', this field must be set to
                     zero (0)."
    ::= { tmnxSubOverridesEntry 4 }

tmnxSubOvrPIR OBJECT-TYPE
    SYNTAX          TPIRRateOverride
    MAX-ACCESS      read-only
    STATUS          obsolete
    DESCRIPTION     "The value of tmnxSubOvrPIR indicates the PIR rate
                     in kbps allowed for the object overwritten by this row.

                     This object is obsoleted in 11.0 Release. It is replaced by 
                     tmnxSubOvrPIRHi and tmnxSubOvrPIRLo."
    ::= { tmnxSubOverridesEntry 5 }

tmnxSubOvrCIR OBJECT-TYPE
    SYNTAX          TCIRRateOverride
    MAX-ACCESS      read-only
    STATUS          obsolete
    DESCRIPTION     "The value of tmnxSubOvrCIR indicates the CIR rate
                     in kbps allowed for the object overwritten by this row.

                     This object is obsoleted in 11.0 Release. It is replaced by 
                     tmnxSubOvrCIRHi and tmnxSubOvrCIRLo."
    ::= { tmnxSubOverridesEntry 6 }

tmnxSubOvrCBS OBJECT-TYPE
    SYNTAX          TBurstSizeBytesOvr
    MAX-ACCESS      read-only
    STATUS          current
    DESCRIPTION     "The value of tmnxSubOvrCBS indicates the amount of
                     reserved buffer space (in bytes) for the object
                     overwritten by this row."
    ::= { tmnxSubOverridesEntry 7 }

tmnxSubOvrMBS OBJECT-TYPE
    SYNTAX          TBurstSizeBytesOvr
    MAX-ACCESS      read-only
    STATUS          current
    DESCRIPTION     "The value of tmnxSubOvrMBS indicates the maximum
                     amount of reserved buffer space (in bytes) for the object
                     overwritten by this row."
    ::= { tmnxSubOverridesEntry 8 }

tmnxSubOvrWrrWeight OBJECT-TYPE
    SYNTAX          THsmdaWrrWeightOverride
    MAX-ACCESS      read-only
    STATUS          current
    DESCRIPTION     
    "The value of tmnxSubOvrWrrWeight specifies the weight of this queue
     for the HSMDA scheduler.
     
     The weight determines how much bandwidth this queue gets out of the 
     total rate for the scheduling class.
     
     The value of tmnxSubOvrWrrWeight is only relevant if the value of
     tmnxSubOvrType is equal to 'queue', and if the queue specified in
     tmnxSubOvrTypeId is referenced in the value of 
     TIMETRA-QOS-MIB::tHsmdaWrrPolicyIncludeQueues of the Weighted Round Robin
     policy associated wit this PPP session."
    ::= { tmnxSubOverridesEntry 9 }

tmnxSubOvrPIRHi OBJECT-TYPE
    SYNTAX       Unsigned32 (0 | 4294967295)
    UNITS        "kbps"
    MAX-ACCESS   read-only
    STATUS       current
    DESCRIPTION
        "The value of tmnxSubOvrPIRHi indicates upper 32 bits of the PIR rate
         allowed for the object overwritten by this row.    

         When the value of tmnxSubOvrPIRHi along with the value of 
         tmnxSubOvrPIRLo is equal to 4294967295 (0xFFFFFFFF), rate for this
         scheduler indicates maximum rate.

         The value of tmnxSubOvrPIRHi equal to 4294967295 (0xFFFFFFFF) and the
         value of tmnxSubOvrPIRLo equal to 4294967294 (0xFFFFFFFE) indicates 
         no overrides."
    ::= { tmnxSubOverridesEntry 10 }

tmnxSubOvrPIRLo OBJECT-TYPE
    SYNTAX       Unsigned32 (1..3200000000 | 4294967294 | 4294967295)
    UNITS        "kbps"
    MAX-ACCESS   read-only
    STATUS       current
    DESCRIPTION
        "The value of tmnxSubOvrPIRHi indicates lower 32 bits of the PIR rate
         allowed for the object overwritten by this row.    
    
         When the value of tmnxSubOvrPIRHi along with the value of 
         tmnxSubOvrPIRLo is equal to 4294967295 (0xFFFFFFFF), rate for
         this scheduler indicates maximum rate.
    
         The value of tmnxSubOvrPIRHi equal to 4294967295 (0xFFFFFFFF) and the
         value of tmnxSubOvrPIRLo equal to 4294967294 (0xFFFFFFFE) indicates 
         no overrides."
    ::= { tmnxSubOverridesEntry 11 }

tmnxSubOvrCIRHi OBJECT-TYPE
    SYNTAX       Unsigned32 (0 | 4294967295)
    UNITS        "kbps"
    MAX-ACCESS   read-only
    STATUS       current
    DESCRIPTION
        "The value of tmnxSubOvrCIRHi indicates upper 32 bits of the CIR rate
         allowed for the object overwritten by this row.    

         When the value of tmnxSubOvrCIRHi along with the value of 
         tmnxSubOvrCIRLo is equal to 4294967295 (0xFFFFFFFF), rate for
         this scheduler indicates maximum rate.

         The value of tmnxSubOvrCIRHi equal to 4294967295 (0xFFFFFFFF) and the
         value of tmnxSubOvrCIRLo equal to 4294967294 (0xFFFFFFFE) indicates
         no overrides."
    ::= { tmnxSubOverridesEntry 12 }

tmnxSubOvrCIRLo OBJECT-TYPE
    SYNTAX       Unsigned32 (0..3200000000 | 4294967294 | 4294967295)
    UNITS        "kbps"
    MAX-ACCESS   read-only
    STATUS       current
    DESCRIPTION
        "The value of tmnxSubOvrCIRHi indicates lower 32 bits of the CIR rate
         allowed for the object overwritten by this row.    
    
         When the value of tmnxSubOvrCIRHi along with the value of 
         tmnxSubOvrCIRLo is equal to 4294967295 (0xFFFFFFFF), rate for
         this scheduler indicates maximum rate.
    
         The value of tmnxSubOvrCIRHi equal to 4294967295 (0xFFFFFFFF) and the
         value of tmnxSubOvrCIRLo equal to 4294967294 (0xFFFFFFFE) indicates 
         no overrides."
    ::= { tmnxSubOverridesEntry 13 }

tmnxSubOvrSummedCIR OBJECT-TYPE
    SYNTAX      TruthValue
    MAX-ACCESS  read-only
    STATUS      current
    DESCRIPTION
        "The value of tmnxSubOvrSummedCIR indicates if the CIR should
         be used as the summed CIR values of the children schedulers or queues.
         If set to 'true', the applicable scheduler CIR (tmnxSubOvrCIRHi and
         tmnxSubOvrCIRLo) loses its meaning.

         The value of tmnxSubOvrCIRHi equal to 4294967295 (0xFFFFFFFF) and the
         value of tmnxSubOvrCIRLo equal to 4294967294 (0xFFFFFFFE) indicates 
         no overrides."
    ::= { tmnxSubOverridesEntry 14 }

-- --------------------------------------------------------
-- tmnxSubFilterProfileTable
-- --------------------------------------------------------
tmnxSubFlterProfTbleLastMgmtChg OBJECT-TYPE
    SYNTAX      TimeStamp
    MAX-ACCESS  read-only
    STATUS      current
    DESCRIPTION
        "The value of tmnxSubFlterProfTbleLastMgmtChg indicates the sysUpTime at
         the time of the most recent management-initiated change to the
         tmnxSubFilterProfileTable."
    ::= { tmnxSubMgmtObjects 89 }

tmnxSubFilterProfileTable OBJECT-TYPE
    SYNTAX      SEQUENCE OF TmnxSubFilterProfileEntry
    MAX-ACCESS  not-accessible
    STATUS      current
    DESCRIPTION
        "A table that contains filter profiles."
    ::= { tmnxSubMgmtObjects 90 }

tmnxSubFilterProfileEntry OBJECT-TYPE
    SYNTAX      TmnxSubFilterProfileEntry
    MAX-ACCESS  not-accessible
    STATUS      current
    DESCRIPTION
        "Information about a specific subscriber qos filter profile"
    INDEX { tmnxSubFlterProfName }
    ::= { tmnxSubFilterProfileTable 1 }

TmnxSubFilterProfileEntry ::=
    SEQUENCE {
        tmnxSubFlterProfName             TNamedItem,
        tmnxSubFlterProfRowStatus        RowStatus,
        tmnxSubFlterProfLastMgmtChange   TimeStamp,
        tmnxSubFlterProfDescription      TItemDescription,
        tmnxSubFlterProfIngIpFltrId      TIPFilterID,
        tmnxSubFlterProfEgrIpFltrId      TIPFilterID,
        tmnxSubFlterProfIngIpv6FltrId    TIPFilterID,
        tmnxSubFlterProfEgrIpv6FltrId    TIPFilterID
    }

tmnxSubFlterProfName OBJECT-TYPE
    SYNTAX      TNamedItem
    MAX-ACCESS  not-accessible
    STATUS      current
    DESCRIPTION
        "The value of tmnxSubFlterProfName specifies the name of the
         subscriber mgmt filter profile."
    ::= { tmnxSubFilterProfileEntry 1 }

tmnxSubFlterProfRowStatus OBJECT-TYPE
    SYNTAX      RowStatus
    MAX-ACCESS  read-create
    STATUS      current
    DESCRIPTION
        "The value of tmnxSubFlterProfRowStatus controls the creation and
         deletion of rows in this table."
    ::= { tmnxSubFilterProfileEntry 2 }

tmnxSubFlterProfLastMgmtChange OBJECT-TYPE
    SYNTAX      TimeStamp
    MAX-ACCESS  read-only
    STATUS      current
    DESCRIPTION
        "The value of tmnxSubFlterProfLastMgmtChange indicates the sysUpTime at
         the time of the most recent management-initiated change to this table
         row."
    ::= { tmnxSubFilterProfileEntry 3 }

tmnxSubFlterProfDescription OBJECT-TYPE
    SYNTAX      TItemDescription
    MAX-ACCESS  read-create
    STATUS      current
    DESCRIPTION
        "The value of tmnxSubFlterProfDescription specifies the user provided
         description of this filter profile."
    DEFVAL { ''H }
    ::= { tmnxSubFilterProfileEntry 4 }

tmnxSubFlterProfIngIpFltrId OBJECT-TYPE
    SYNTAX      TIPFilterID
    MAX-ACCESS  read-create
    STATUS      current
    DESCRIPTION
        "The value of tmnxSubFlterProfIngIpFltrId specifies the ingress IP
         filter (from TIMETRA-FILTER-MIB::tIPFilterTable) applicable to this
         filter profile.
         The value '0' specifies that no filter is applied."
    DEFVAL { 0 }
    ::= { tmnxSubFilterProfileEntry 5 }

tmnxSubFlterProfEgrIpFltrId OBJECT-TYPE
    SYNTAX      TIPFilterID
    MAX-ACCESS  read-create
    STATUS      current
    DESCRIPTION
        "The value of tmnxSubFlterProfEgrIpFltrId specifies the egress IP filter
         (from TIMETRA-FILTER-MIB::tIPFilterTable) applicable to this filter
         profile.
         The value '0' specifies that no filter is applied."
    DEFVAL { 0 }
    ::= { tmnxSubFilterProfileEntry 6 }

tmnxSubFlterProfIngIpv6FltrId OBJECT-TYPE
    SYNTAX      TIPFilterID
    MAX-ACCESS  read-create
    STATUS      current
    DESCRIPTION
        "The value of tmnxSubFlterProfIngIpv6FltrId specifies the ingress IP
         filter (from TIMETRA-FILTER-MIB::tIPv6FilterTable) applicable to this
         filter profile.
         The value '0' specifies that no filter is applied."
    DEFVAL { 0 }
    ::= { tmnxSubFilterProfileEntry 7 }

tmnxSubFlterProfEgrIpv6FltrId OBJECT-TYPE
    SYNTAX      TIPFilterID
    MAX-ACCESS  read-create
    STATUS      current
    DESCRIPTION
        "The value of tmnxSubFlterProfEgrIpv6FltrId specifies the egress IP 
         filter (from TIMETRA-FILTER-MIB::tIPv6FilterTable) applicable to this
         filter profile.
         The value '0' specifies that no filter is applied."
    DEFVAL { 0 }
    ::= { tmnxSubFilterProfileEntry 8 }

-- --------------------------------------------------------
-- tmnxSubProfFltrProfileMapTable
-- --------------------------------------------------------
tmnxSPFltrProfMapTblLstMgtChg OBJECT-TYPE
    SYNTAX      TimeStamp
    MAX-ACCESS  read-only
    STATUS      current
    DESCRIPTION
        "The value of tmnxSPFltrProfMapTblLstMgtChg indicates the sysUpTime at
         the time of the most recent management-initiated change to the
         tmnxSubProfFltrProfileMapTable."
    ::= { tmnxSubMgmtObjects 91 }

tmnxSubProfFltrProfileMapTable OBJECT-TYPE
    SYNTAX      SEQUENCE OF TmnxSubProfFltrProfileMapEntry
    MAX-ACCESS  not-accessible
    STATUS      current
    DESCRIPTION
        "The tmnxSubProfFltrProfileMapTable has an entry for each Filter profile
         string to Filter profile name mapping defined under a subscriber
         profile configured in the system."
    ::= { tmnxSubMgmtObjects 92 }

tmnxSubProfFltrProfileMapEntry OBJECT-TYPE
    SYNTAX      TmnxSubProfFltrProfileMapEntry
    MAX-ACCESS  not-accessible
    STATUS      current
    DESCRIPTION
        "Each row entry represents a Filter profile string to filter profile
         name mapping defined under a subscriber profile configured in the
         system.
         Entries can be created and deleted via SNMP SET operations on the
         object tmnxSPFltrProfMapRowStatus."
    INDEX { tmnxSubProfName,
            IMPLIED tmnxSPFltrProfMapFltrString }
    ::= { tmnxSubProfFltrProfileMapTable 1 }

TmnxSubProfFltrProfileMapEntry ::=
    SEQUENCE {
        tmnxSPFltrProfMapFltrString DisplayString,
        tmnxSPFltrProfMapRowStatus  RowStatus,
        tmnxSPFltrProfMapLstMgmtChg TimeStamp,
        tmnxSPFltrProfMapFltrProfile TNamedItem
    }

tmnxSPFltrProfMapFltrString OBJECT-TYPE
    SYNTAX      DisplayString (SIZE (1..16))
    MAX-ACCESS  not-accessible
    STATUS      current
    DESCRIPTION
        "The value of tmnxSPFltrProfMapFltrString specifies the filter
         profile string for this row."
    ::= { tmnxSubProfFltrProfileMapEntry 1 }

tmnxSPFltrProfMapRowStatus OBJECT-TYPE
    SYNTAX      RowStatus
    MAX-ACCESS  read-create
    STATUS      current
    DESCRIPTION
        "The value of tmnxSPFltrProfMapRowStatus controls the creation and
         deletion of rows in this table."
    ::= { tmnxSubProfFltrProfileMapEntry 2 }

tmnxSPFltrProfMapLstMgmtChg OBJECT-TYPE
    SYNTAX      TimeStamp
    MAX-ACCESS  read-only
    STATUS      current
    DESCRIPTION
        "The value of tmnxSPFltrProfMapLstMgmtChg indicates the
         sysUpTime at the time of the most recent management-initiated change to
         this table row."
    ::= { tmnxSubProfFltrProfileMapEntry 3 }

tmnxSPFltrProfMapFltrProfile OBJECT-TYPE
    SYNTAX      TNamedItem
    MAX-ACCESS  read-create
    STATUS      current
    DESCRIPTION
        "The value of tmnxSPFltrProfMapFltrProfile specifies the filter
         profile name corresponding to this row."
    ::= { tmnxSubProfFltrProfileMapEntry 4 }

-- --------------------------------------------------------
-- tmnxSubLcktPlcyTable
-- --------------------------------------------------------
tmnxSubLcktPlcyTable OBJECT-TYPE
    SYNTAX      SEQUENCE OF TmnxSubLcktPlcyEntry
    MAX-ACCESS  not-accessible
    STATUS      current
    DESCRIPTION
        "The tmnxSubLcktPlcyTable allows configuration of subscriber Host
         Lockout Policy parameters."
    ::= { tmnxSubMgmtObjects 98 }

tmnxSubLcktPlcyEntry OBJECT-TYPE
    SYNTAX      TmnxSubLcktPlcyEntry
    MAX-ACCESS  not-accessible
    STATUS      current
    DESCRIPTION
        "tmnxSubLcktPlcyEntry is an entry (conceptual row) in the
         tmnxSubLcktPlcyTable.

         Each entry represents the configuration for a subscriber Host Lockout
         Policy.

         Entries in this table can be created and deleted via
         SNMP SET operations to tmnxSubLcktPlcyRowStatus.

         Entries have a presumed StorageType of nonVolatile."
    INDEX { tmnxSubLcktPlcyName }
    ::= { tmnxSubLcktPlcyTable 1 }

TmnxSubLcktPlcyEntry ::= SEQUENCE {
    tmnxSubLcktPlcyName             TNamedItem,
    tmnxSubLcktPlcyRowStatus        RowStatus,
    tmnxSubLcktPlcyLastMgmtChange   TimeStamp,
    tmnxSubLcktPlcyDescription      TItemDescription,
    tmnxSubLcktPlcyLcktTimeMin      Unsigned32,
    tmnxSubLcktPlcyLcktTimeMax      Unsigned32,
    tmnxSubLcktPlcyLcktResetTime    Unsigned32,
    tmnxSubLcktPlcyMaxLcktHosts     Unsigned32,
    tmnxSubLcktPlcyHostKey          TmnxSubLcktPlcyHostKey 
}

tmnxSubLcktPlcyName OBJECT-TYPE
    SYNTAX      TNamedItem
    MAX-ACCESS  not-accessible
    STATUS      current
    DESCRIPTION
        "The value of tmnxSubLcktPlcyName specifies a specific subscriber
         Host Lockout Policy."
    ::= { tmnxSubLcktPlcyEntry 1 }

tmnxSubLcktPlcyRowStatus OBJECT-TYPE
    SYNTAX      RowStatus
    MAX-ACCESS  read-create
    STATUS      current
    DESCRIPTION
        "The value of tmnxSubLcktPlcyRowStatus controls the creation and
         deletion of rows in the table."
    ::= { tmnxSubLcktPlcyEntry 2 }

tmnxSubLcktPlcyLastMgmtChange OBJECT-TYPE
    SYNTAX      TimeStamp
    MAX-ACCESS  read-only
    STATUS      current
    DESCRIPTION
        "The value of tmnxSubLcktPlcyLastMgmtChange indicates the sysUpTime at
         the time of the most recent management-initiated change to this
         policy."
    ::= { tmnxSubLcktPlcyEntry 3 }

tmnxSubLcktPlcyDescription OBJECT-TYPE
    SYNTAX      TItemDescription
    MAX-ACCESS  read-create
    STATUS      current
    DESCRIPTION
        "The value of tmnxSubLcktPlcyDescription specifies the user provided
         description of this subscriber Host Lockout Policy."
    DEFVAL { "" }
    ::= { tmnxSubLcktPlcyEntry 4 }

tmnxSubLcktPlcyLcktTimeMin OBJECT-TYPE
    SYNTAX      Unsigned32(1..86400)
    MAX-ACCESS  read-create
    STATUS      current
    DESCRIPTION
        "The value of tmnxSubLcktPlcyLcktTimeMin specifies the minimum 
         lockout-time for this Host Lockout Policy."
    DEFVAL { 10 }
    ::= { tmnxSubLcktPlcyEntry 5 }

tmnxSubLcktPlcyLcktTimeMax OBJECT-TYPE
    SYNTAX      Unsigned32(1..86400)
    MAX-ACCESS  read-create
    STATUS      current
    DESCRIPTION
        "The value of tmnxSubLcktPlcyLcktTimeMax specifies the maximum
         lockout-time for this Host Lockout Policy."
    DEFVAL { 3600 }
    ::= { tmnxSubLcktPlcyEntry 6 }

tmnxSubLcktPlcyLcktResetTime OBJECT-TYPE
    SYNTAX      Unsigned32(1..86400)
    MAX-ACCESS  read-create
    STATUS      current
    DESCRIPTION
        "The value of tmnxSubLcktPlcyLcktResetTime specifies the lockout
         reset time for this Host Lockout Policy."
    DEFVAL { 60 }
    ::= { tmnxSubLcktPlcyEntry 7 }

tmnxSubLcktPlcyMaxLcktHosts OBJECT-TYPE
    SYNTAX      Unsigned32(1..32000)
    MAX-ACCESS  read-create
    STATUS      current
    DESCRIPTION
        "The value of tmnxSubLcktPlcyMaxLcktHosts indicates the maximum
         number of locked out hosts for this Host Lockout Policy."
    DEFVAL { 100 }
    ::= { tmnxSubLcktPlcyEntry 8 }

tmnxSubLcktPlcyHostKey OBJECT-TYPE
    SYNTAX      TmnxSubLcktPlcyHostKey
    MAX-ACCESS  read-create
    STATUS      current
    DESCRIPTION     
        "The value of tmnxSubLcktPlcyHostKey indicates the method
         for host matching."
    DEFVAL { all }
    ::= { tmnxSubLcktPlcyEntry 9 }

-- --------------------------------------------------------
-- tmnxSubMgmtAutoSubIdObjs
-- --------------------------------------------------------
tmnxSubMgmtAutoSubIdObjs OBJECT IDENTIFIER ::= { tmnxSubMgmtObjects 99 }

tmnxSubAutoSubIdPppKey1 OBJECT-TYPE
    SYNTAX      TmnxSubAutoSubIdKey
    MAX-ACCESS  read-write
    STATUS      current
    DESCRIPTION
        "The value of tmnxSubAutoSubIdPppKey1 specifies
         the first key that defines the auto-generated subscriber
         identification key for PPP hosts."
    DEFVAL { mac }
    ::= { tmnxSubMgmtAutoSubIdObjs 1 }

tmnxSubAutoSubIdPppKey2 OBJECT-TYPE
    SYNTAX      TmnxSubAutoSubIdKey
    MAX-ACCESS  read-write
    STATUS      current
    DESCRIPTION
        "The value of tmnxSubAutoSubIdPppKey2 specifies
         the second key that defines the auto-generated subscriber
         identification key for PPP hosts."
    DEFVAL { sapId }
    ::= { tmnxSubMgmtAutoSubIdObjs 2 }

tmnxSubAutoSubIdPppKey3 OBJECT-TYPE
    SYNTAX      TmnxSubAutoSubIdKey
    MAX-ACCESS  read-write
    STATUS      current
    DESCRIPTION
        "The value of tmnxSubAutoSubIdPppKey3 specifies
         the third key that defines the auto-generated subscriber
         identification key for PPP hosts."
    DEFVAL { sessionId }
    ::= { tmnxSubMgmtAutoSubIdObjs 3 }

tmnxSubAutoSubIdPppKey4 OBJECT-TYPE
    SYNTAX      TmnxSubAutoSubIdKey
    MAX-ACCESS  read-write
    STATUS      current
    DESCRIPTION
        "The value of tmnxSubAutoSubIdPppKey4 specifies
         the fourth key that defines the auto-generated subscriber
         identification key for PPP hosts."
    DEFVAL { none }
    ::= { tmnxSubMgmtAutoSubIdObjs 4 }

tmnxSubAutoSubIdPppKey5 OBJECT-TYPE
    SYNTAX      TmnxSubAutoSubIdKey
    MAX-ACCESS  read-write
    STATUS      current
    DESCRIPTION
        "The value of tmnxSubAutoSubIdPppKey5 specifies
         the fifth key that defines the auto-generated subscriber
         identification key for PPP hosts."
    DEFVAL { none }
    ::= { tmnxSubMgmtAutoSubIdObjs 5 }

tmnxSubAutoSubIdIpoeKey1 OBJECT-TYPE
    SYNTAX      TmnxSubAutoSubIdKey
    MAX-ACCESS  read-write
    STATUS      current
    DESCRIPTION
        "The value of tmnxSubAutoSubIdIpoeKey1 specifies
         the first key that defines the auto-generated subscriber
         identification key for IPoE hosts."
    DEFVAL { mac }
    ::= { tmnxSubMgmtAutoSubIdObjs 6 }

tmnxSubAutoSubIdIpoeKey2 OBJECT-TYPE
    SYNTAX      TmnxSubAutoSubIdKey
    MAX-ACCESS  read-write
    STATUS      current
    DESCRIPTION
        "The value of tmnxSubAutoSubIdIpoeKey2 specifies
         the second key that defines the auto-generated subscriber
         identification key for IPoE hosts."
    DEFVAL { sapId }
    ::= { tmnxSubMgmtAutoSubIdObjs 7 }

tmnxSubAutoSubIdIpoeKey3 OBJECT-TYPE
    SYNTAX      TmnxSubAutoSubIdKey
    MAX-ACCESS  read-write
    STATUS      current
    DESCRIPTION
        "The value of tmnxSubAutoSubIdIpoeKey3 specifies
         the third key that defines the auto-generated subscriber
         identification key for IPoE hosts."
    DEFVAL { none }
    ::= { tmnxSubMgmtAutoSubIdObjs 8 }

tmnxSubAutoSubIdIpoeKey4 OBJECT-TYPE
    SYNTAX      TmnxSubAutoSubIdKey
    MAX-ACCESS  read-write
    STATUS      current
    DESCRIPTION
        "The value of tmnxSubAutoSubIdIpoeKey4 specifies
         the fourth key that defines the auto-generated subscriber
         identification key for IPoE hosts."
    DEFVAL { none }
    ::= { tmnxSubMgmtAutoSubIdObjs 9 }

-- ------------------------------------------------
-- tmnxSubIpoeLinkTable
-- ------------------------------------------------
tmnxSubIpoeLinkTableLastChange OBJECT-TYPE
    SYNTAX      TimeStamp
    MAX-ACCESS  read-only
    STATUS      current
    DESCRIPTION
      "The value of tmnxSubIpoeLinkTableLastChange indicates the sysUpTime
       at the time of the last modification of tmnxSubIpoeLinkTable.

       If no changes were made to the entry since the last
       re-initialization of the local network management subsystem,
       then this object contains a zero value."
    ::= { tmnxSubMgmtObjects 100 }

tmnxSubIpoeLinkTable OBJECT-TYPE
    SYNTAX      SEQUENCE OF TmnxSubIpoeLinkEntry
    MAX-ACCESS  not-accessible
    STATUS      current
    DESCRIPTION
      "A table configuring IPoE host linking.

       A row is automatically created in tmnxSubIpoeLinkTable for each entry
       in iesIfTable where the value of the object iesIfType equals 'group (3)'."
    ::= { tmnxSubMgmtObjects 101 }

tmnxSubIpoeLinkEntry OBJECT-TYPE
    SYNTAX      TmnxSubIpoeLinkEntry
    MAX-ACCESS  not-accessible
    STATUS      current
    DESCRIPTION
      "Information about the IPoE host linking
       for a particular IES or VPRN Group Interface."
    INDEX { svcId,
            iesIfIndex }
    ::= { tmnxSubIpoeLinkTable 1 }

TmnxSubIpoeLinkEntry ::=
    SEQUENCE {
        tmnxSubIpoeLinkLastMgmtChange    TimeStamp,
        tmnxSubIpoeLinkAdminState        TmnxAdminState,
        tmnxSubIpoeLinkShareCircId       TruthValue,
        tmnxSubIpoeLinkGratRtrAdv        TruthValue
    }   

tmnxSubIpoeLinkLastMgmtChange OBJECT-TYPE
    SYNTAX      TimeStamp
    MAX-ACCESS  read-only
    STATUS      current
    DESCRIPTION
        "The value of tmnxSubIpoeLinkLastMgmtChange indicates the sysUpTime at
         the time of the most recent management-initiated change to this entry."
    ::= { tmnxSubIpoeLinkEntry 1 }

tmnxSubIpoeLinkAdminState OBJECT-TYPE
    SYNTAX      TmnxAdminState
    MAX-ACCESS  read-create
    STATUS      current
    DESCRIPTION
        "The value of the object tmnxSubIpoeLinkAdminState specifies
         whether hosts with matching SAP id and MAC address are groupped.

         One group contains up to three hosts (DHCP lease state, DHCPv6
         delegated prefix, DHCPv6 non-temporary address or SLAAC prefix).

         The value of this object can only be set to 'inService'
         when no IPoE hosts are present."
    DEFVAL { outOfService }
    ::= { tmnxSubIpoeLinkEntry 2 }

tmnxSubIpoeLinkShareCircId OBJECT-TYPE
    SYNTAX      TruthValue
    MAX-ACCESS  read-create
    STATUS      current
    DESCRIPTION
        "The value of tmnxSubIpoeLinkShareCircId indicates
         whether the circuit ID is shared among IPv4 and IPv6 IPoE hosts.

         When the value of this object is to 'true',
         the incoming request without a circuit ID inherits
         the circuit ID of a host from the same group."
    DEFVAL { false }
    ::= { tmnxSubIpoeLinkEntry 3 }

tmnxSubIpoeLinkGratRtrAdv OBJECT-TYPE
    SYNTAX      TruthValue
    MAX-ACCESS  read-create
    STATUS      current
    DESCRIPTION
        "The value of tmnxSubIpoeLinkGratRtrAdv indicates
         whether router advertisments are also sent to DHCP hosts or not.

         If the value of this object is set to 'true',
         and the value of tmnxSubV6GrpIfRAAdminState is set to 'enabled',
         router advertisements are sent to the DHCP host."
    DEFVAL { false }
    ::= { tmnxSubIpoeLinkEntry 4 }

--
--  The Subscriber SLAAC Host Table
--

tmnxSubSlaacTable   OBJECT-TYPE
    SYNTAX      SEQUENCE OF TmnxSubSlaacEntry
    MAX-ACCESS  not-accessible
    STATUS      current
    DESCRIPTION
       "The tmnxSubSlaacTable has an entry for each
        stateless address autoconfiguration (SLAAC) host."
    ::= { tmnxSubMgmtObjects 102 }

tmnxSubSlaacEntry   OBJECT-TYPE
    SYNTAX      TmnxSubSlaacEntry
    MAX-ACCESS  not-accessible
    STATUS      current
    DESCRIPTION
       "Each conceptual row represents a slaac host.

        Entries in this table are created and destroyed by the system."
    INDEX       { svcId,
                  tmnxSubSlaacPfxType,
                  tmnxSubSlaacPfx,
                  tmnxSubSlaacMacAddr }
    ::= { tmnxSubSlaacTable 1 }

TmnxSubSlaacEntry ::=
    SEQUENCE {
        tmnxSubSlaacPfxType              InetAddressType,
        tmnxSubSlaacPfx                  InetAddress,
        tmnxSubSlaacMacAddr              MacAddress,
        tmnxSubSlaacPfxLen               InetAddressPrefixLength,
        tmnxSubSlaacPortId               TmnxPortID,
        tmnxSubSlaacEncapValue           TmnxEncapVal,
        tmnxSubSlaacPppIndex             Unsigned32,
        tmnxSubSlaacPersistKey           Unsigned32,
        tmnxSubSlaacInterfaceId          OCTET STRING,
        tmnxSubSlaacCircuitId            OCTET STRING,
        tmnxSubSlaacRemoteId             OCTET STRING,
        tmnxSubSlaacSubscrIdent          DisplayString,
        tmnxSubSlaacSubProfString        DisplayString,
        tmnxSubSlaacSlaProfString        DisplayString,
        tmnxSubSlaacAppProfString        DisplayString,
        tmnxSubSlaacCategoryMapName      TNamedItemOrEmpty,
        tmnxSubSlaacAncpString           TmnxAncpStringOrZero,
        tmnxSubSlaacInterDestId          DisplayString,
        tmnxSubSlaacRadiusClassAttr      OCTET STRING,
        tmnxSubSlaacShcvOperState        ServShcvOperState,
        tmnxSubSlaacShcvChecks           Unsigned32,
        tmnxSubSlaacShcvReplies          Unsigned32,
        tmnxSubSlaacShcvReplyTime        TimeStamp,
        tmnxSubSlaacPrimaryDnsType       InetAddressType,
        tmnxSubSlaacPrimaryDns           InetAddress,
        tmnxSubSlaacSecondaryDnsType     InetAddressType,
        tmnxSubSlaacSecondaryDns         InetAddress,
        tmnxSubSlaacCreationTime         DateAndTime,
        tmnxSubSlaacOriginSubscrId       TmnxSubSlaacInfoOrigin,
        tmnxSubSlaacOriginStrings        TmnxSubSlaacInfoOrigin,
        tmnxSubSlaacOriginPfxInfo        TmnxSubSlaacInfoOrigin,
        tmnxSubSlaacLastRsAuth           DateAndTime,
        tmnxSubSlaacInactivityTimeExp    Unsigned32,
        tmnxSubSlaacPfxPool              TNamedItemOrEmpty,
        tmnxSubSlaacRetailerSvcId        TmnxServId,
        tmnxSubSlaacRetailerIf           InterfaceIndexOrZero,
        tmnxSubSlaacTerminationType      TmnxSubTerminationType,
        tmnxSubSlaacIpoeSessionHost      TruthValue,   
        tmnxSubSlaacPppSessionHost       TruthValue   
    }

tmnxSubSlaacPfxType OBJECT-TYPE
    SYNTAX          InetAddressType
    MAX-ACCESS      not-accessible
    STATUS          current
    DESCRIPTION     "The value of tmnxSubSlaacPfxType indicates the
                     address type of tmnxSubSlaacPfx."
    ::= { tmnxSubSlaacEntry 1 }

tmnxSubSlaacPfx OBJECT-TYPE
    SYNTAX          InetAddress (SIZE (0|16))
    MAX-ACCESS      not-accessible
    STATUS          current
    DESCRIPTION     "The value of tmnxSubSlaacPfx indicates the IPv6
                     prefix of the SLAAC host."
    ::= { tmnxSubSlaacEntry 2 }

tmnxSubSlaacMacAddr OBJECT-TYPE
    SYNTAX          MacAddress
    MAX-ACCESS      not-accessible
    STATUS          current
    DESCRIPTION     "The value of tmnxSubSlaacMacAddr indicates the MAC
                     address of the this SLAAC host."
    ::= { tmnxSubSlaacEntry 3 }

tmnxSubSlaacPfxLen  OBJECT-TYPE
    SYNTAX          InetAddressPrefixLength (0..128)
    MAX-ACCESS      read-only
    STATUS          current
    DESCRIPTION     "The value of tmnxSubSlaacPfxLen indicates the prefix
                     length of the SLAAC prefix."
    ::= { tmnxSubSlaacEntry 4 }

tmnxSubSlaacPortId OBJECT-TYPE
    SYNTAX          TmnxPortID
    MAX-ACCESS      read-only
    STATUS          current
    DESCRIPTION     "The object tmnxSubSlaacPortId along with the object
                     tmnxSubSlaacEncapValue, indicates the SAP for which
                     this entry contains information."
    ::= { tmnxSubSlaacEntry 5 }

tmnxSubSlaacEncapValue OBJECT-TYPE
    SYNTAX          TmnxEncapVal
    MAX-ACCESS      read-only
    STATUS          current
    DESCRIPTION     "The object tmnxSubSlaacPortId along with the object
                     tmnxSubSlaacEncapValue, indicates the SAP for which
                     this entry contains information."
    ::= { tmnxSubSlaacEntry 6 }

tmnxSubSlaacPppIndex OBJECT-TYPE
    SYNTAX          Unsigned32
    MAX-ACCESS      read-only
    STATUS          current
    DESCRIPTION     "The value of tmnxSubSlaacPppIndex indicates the ppp
                     session identifier from the tmnxSubPppTable."
    ::= { tmnxSubSlaacEntry 7 }

tmnxSubSlaacPersistKey OBJECT-TYPE
    SYNTAX          Unsigned32
    MAX-ACCESS      read-only
    STATUS          current
    DESCRIPTION     "The value of tmnxSubSlaacPersistKey indicates a key
                     value that can be used to track this SLAAC host in the
                     persistence file."
    ::= { tmnxSubSlaacEntry 8 }

tmnxSubSlaacInterfaceId OBJECT-TYPE
    SYNTAX          OCTET STRING (SIZE (8))
    MAX-ACCESS      read-only
    STATUS          current
    DESCRIPTION     "The value of tmnxSubSlaacInterfaceId indicates the
                     interface identifier of this SLAAC host.

                     If the SLAAC host has multiple addresses, this field will
                     only show the interface identifier of one of them.
                     To see all SLAAC addresses, see
                     TIMETRA-SUBSCRIBER-MGMT-MIB:tmnxSubSlaacAddressTable.
                    "
    ::= { tmnxSubSlaacEntry 9 }

tmnxSubSlaacCircuitId OBJECT-TYPE
    SYNTAX          OCTET STRING (SIZE (0..256))
    MAX-ACCESS      read-only
    STATUS          current
    DESCRIPTION     "The value of tmnxSubSlaacCircuitId indicates the
                     circuit-id of this host."
    ::= { tmnxSubSlaacEntry 10 }

tmnxSubSlaacRemoteId OBJECT-TYPE
    SYNTAX          OCTET STRING (SIZE (0..256))
    MAX-ACCESS      read-only
    STATUS          current
    DESCRIPTION     "The value of tmnxSubSlaacRemoteId indicates the
                     remote-id of this host."
    ::= { tmnxSubSlaacEntry 11 }

tmnxSubSlaacSubscrIdent OBJECT-TYPE
    SYNTAX          DisplayString
    MAX-ACCESS      read-only
    STATUS          current
    DESCRIPTION     "The value of tmnxSubSlaacSubscrIdent indicates the
                     id of the parent subscriber of this SLAAC host."
    ::= { tmnxSubSlaacEntry 12 }

tmnxSubSlaacSubProfString OBJECT-TYPE
    SYNTAX          DisplayString
    MAX-ACCESS      read-only
    STATUS          current
    DESCRIPTION     "The value of tmnxSubSlaacSubProfString indicates the
                     subscriber profile string applicable for this SLAAC host."
    ::= { tmnxSubSlaacEntry 13 }

tmnxSubSlaacSlaProfString OBJECT-TYPE
    SYNTAX          DisplayString
    MAX-ACCESS      read-only
    STATUS          current
    DESCRIPTION     "The value of tmnxSubSlaacSlaProfString indicates the
                     SLA profile string applicable for this SLAAC host."
    ::= { tmnxSubSlaacEntry 14 }

tmnxSubSlaacAppProfString OBJECT-TYPE
    SYNTAX          DisplayString
    MAX-ACCESS      read-only
    STATUS          current
    DESCRIPTION     "The value of tmnxSubSlaacAppProfString indicates the
                     application profile string applicable for this SLAAC
                     host."
    ::= { tmnxSubSlaacEntry 15 }

tmnxSubSlaacCategoryMapName OBJECT-TYPE
    SYNTAX          TNamedItemOrEmpty
    MAX-ACCESS      read-only
    STATUS          current
    DESCRIPTION     "The object tmnxSubSlaacCategoryMapName indicates the
                     value of the category map name."
    ::= { tmnxSubSlaacEntry 16 }

tmnxSubSlaacAncpString OBJECT-TYPE
    SYNTAX          TmnxAncpStringOrZero
    MAX-ACCESS      read-only
    STATUS          current
    DESCRIPTION     "The object tmnxSubSlaacAncpString indicates the
                     value of the ancp-string."
    ::= { tmnxSubSlaacEntry 17 }

tmnxSubSlaacInterDestId OBJECT-TYPE
    SYNTAX          DisplayString (SIZE (0..32))
    MAX-ACCESS      read-only
    STATUS          current
    DESCRIPTION     "The object tmnxSubSlaacInterDestId indicates the
                     intermediate destination identifier."
    ::= { tmnxSubSlaacEntry 18 }

tmnxSubSlaacRadiusClassAttr OBJECT-TYPE
    SYNTAX          OCTET STRING (SIZE (0..253))
    MAX-ACCESS      read-only
    STATUS          current
    DESCRIPTION     "The value of tmnxSubSlaacRadiusClassAttr indicates the
                     Class attribute returned by the RADIUS server in an
                     Access-Accept message."
    ::= { tmnxSubSlaacEntry 19 }

tmnxSubSlaacShcvOperState OBJECT-TYPE
    SYNTAX          ServShcvOperState
    MAX-ACCESS      read-only
    STATUS          current
    DESCRIPTION     "The value of tmnxSubSlaacShcvOperState indicates the
                     state of the subscriber host connectivity check for
                     this SLAAC host."
    ::= { tmnxSubSlaacEntry 20 }

tmnxSubSlaacShcvChecks OBJECT-TYPE
    SYNTAX          Unsigned32
    MAX-ACCESS      read-only
    STATUS          current
    DESCRIPTION     "The value of tmnxSubSlaacShcvChecks indicates the
                     number of host connectivity check requests for
                     this SLAAC host."
    ::= { tmnxSubSlaacEntry 21 }

tmnxSubSlaacShcvReplies OBJECT-TYPE
    SYNTAX          Unsigned32
    MAX-ACCESS      read-only
    STATUS          current
    DESCRIPTION     "The value of tmnxSubSlaacShcvReplies indicates the
                     number of host connectivity replies for
                     this SLAAC host."
    ::= { tmnxSubSlaacEntry 22 }

tmnxSubSlaacShcvReplyTime OBJECT-TYPE
    SYNTAX          TimeStamp
    MAX-ACCESS      read-only
    STATUS          current
    DESCRIPTION     "The value of tmnxSubSlaacShcvReplyTime indicates the
                     time of the last successful host connectivity check for
                     this SLAAC host."
    ::= { tmnxSubSlaacEntry 23 }

tmnxSubSlaacPrimaryDnsType OBJECT-TYPE
    SYNTAX          InetAddressType
    MAX-ACCESS      read-only
    STATUS          current
    DESCRIPTION     "The value of tmnxSubSlaacPrimaryDnsType indicates the
                     address type of tmnxSubSlaacPrimaryDns."
    ::= { tmnxSubSlaacEntry 24 }

tmnxSubSlaacPrimaryDns OBJECT-TYPE
    SYNTAX          InetAddress (SIZE (0|16))
    MAX-ACCESS      read-only
    STATUS          current
    DESCRIPTION     "The value of tmnxSubSlaacPrimaryDns indicates the
                     primary DNS server."
    ::= { tmnxSubSlaacEntry 25 }

tmnxSubSlaacSecondaryDnsType OBJECT-TYPE
    SYNTAX          InetAddressType
    MAX-ACCESS      read-only
    STATUS          current
    DESCRIPTION     "The value of tmnxSubSlaacSecondaryDnsType indicates the
                     address type of tmnxSubSlaacSecondaryDns."
    ::= { tmnxSubSlaacEntry 26 }

tmnxSubSlaacSecondaryDns OBJECT-TYPE
    SYNTAX          InetAddress (SIZE (0|16))
    MAX-ACCESS      read-only
    STATUS          current
    DESCRIPTION     "The value of tmnxSubSlaacSecondaryDns indicates the
                     secondary DNS server."
    ::= { tmnxSubSlaacEntry 27 }

tmnxSubSlaacCreationTime OBJECT-TYPE
    SYNTAX          DateAndTime
    MAX-ACCESS      read-only
    STATUS          current
    DESCRIPTION     "The value of tmnxSubSlaacCreationTime indicates
                     when this host was created."
    ::= { tmnxSubSlaacEntry 28 }

tmnxSubSlaacOriginSubscrId OBJECT-TYPE
    SYNTAX          TmnxSubSlaacInfoOrigin
    MAX-ACCESS      read-only
    STATUS          obsolete
    DESCRIPTION     "The value of tmnxSubSlaacOriginSubscrId indicates
                     which source provided the subscriber-id."
    ::= { tmnxSubSlaacEntry 29 }

tmnxSubSlaacOriginStrings OBJECT-TYPE
    SYNTAX          TmnxSubSlaacInfoOrigin
    MAX-ACCESS      read-only
    STATUS          obsolete
    DESCRIPTION     "The value of tmnxSubSlaacOriginStrings indicates
                     which server provided the Sub-profile, SLA profile,
                     Ancp string and Intermediate Destination Id."
    ::= { tmnxSubSlaacEntry 30 }

tmnxSubSlaacOriginPfxInfo OBJECT-TYPE
    SYNTAX          TmnxSubSlaacInfoOrigin
    MAX-ACCESS      read-only
    STATUS          current
    DESCRIPTION     "The value of tmnxSubSlaacOriginPfxInfo indicates
                     which server provided the address information."
    ::= { tmnxSubSlaacEntry 31 }

tmnxSubSlaacLastRsAuth OBJECT-TYPE
    SYNTAX          DateAndTime
    MAX-ACCESS      read-only
    STATUS          current
    DESCRIPTION     "The value of tmnxSubSlaacLastRsAuth indicates the time
                     of the last router solicit authentication."
    ::= { tmnxSubSlaacEntry 32 }

tmnxSubSlaacInactivityTimeExp OBJECT-TYPE
    SYNTAX          Unsigned32
    UNITS           "seconds"
    MAX-ACCESS      read-only
    STATUS          current
    DESCRIPTION     "The value of tmnxSubSlaacInactivityTimeExp indicates the 
                     remaining time in seconds before the host is removed.
                     A value of 0 indicates no inactivity timer is active."
    ::= { tmnxSubSlaacEntry 33 }

tmnxSubSlaacPfxPool OBJECT-TYPE
    SYNTAX          TNamedItemOrEmpty
    MAX-ACCESS      read-only
    STATUS          current
    DESCRIPTION     "The value of tmnxSubSlaacPfxPool indicates
                     the DHCP server pool from which the SLAAC prefix
                     is allocated."
    ::= { tmnxSubSlaacEntry 34 }

tmnxSubSlaacRetailerSvcId OBJECT-TYPE  
    SYNTAX          TmnxServId
    MAX-ACCESS      read-only
    STATUS          current
    DESCRIPTION     "The value of tmnxSubSlaacRetailerSvcId indicates the
                     service ID of the retailer VPRN service to which this 
                     SLAAC host belongs. When this object is non zero, the
                     SLAAC host belongs to a retailer VPRN."
    ::= { tmnxSubSlaacEntry 35 }

tmnxSubSlaacRetailerIf OBJECT-TYPE
     SYNTAX         InterfaceIndexOrZero
     MAX-ACCESS     read-only
     STATUS         current
     DESCRIPTION    "The value of tmnxSubSlaacRetailerIf indicates the
                     interface index of the retailer VPRN interface to 
                     which this SLAAC host belongs. When this object is 
                     non zero, the SLAAC host belongs to a retailer VPRN."
     ::= { tmnxSubSlaacEntry 36 }

tmnxSubSlaacTerminationType OBJECT-TYPE
    SYNTAX      TmnxSubTerminationType
    MAX-ACCESS  read-only
    STATUS      current
    DESCRIPTION
        "The value of tmnxSubSlaacTerminationType indicates the termination type
         of this SLAAC host."
    ::= { tmnxSubSlaacEntry 37 }

tmnxSubSlaacIpoeSessionHost OBJECT-TYPE
    SYNTAX      TruthValue
    MAX-ACCESS  read-only
    STATUS      current
    DESCRIPTION
        "The value of tmnxSubSlaacIpoeSessionHost indicates whether or not
         this SLAAC host belongs to an IPoE session.
         
         If the value is 'true', the SLAAC host belongs to an IPoE session."
    ::= { tmnxSubSlaacEntry 38 }

tmnxSubSlaacPppSessionHost OBJECT-TYPE
    SYNTAX      TruthValue
    MAX-ACCESS  read-only
    STATUS      current
    DESCRIPTION
        "The value of tmnxSubSlaacPppSessionHost indicates whether or not
         this SLAAC host belongs to an PPP session.
         
         If the value is 'true', the SLAAC host belongs to an PPP session."
    ::= { tmnxSubSlaacEntry 39 }

--
--  The Subscriber Mgmt per Port Statistics Table
--

tmnxSubMgmtPortStatsTable   OBJECT-TYPE
    SYNTAX      SEQUENCE OF TmnxSubMgmtPortStatsEntry
    MAX-ACCESS  not-accessible
    STATUS      current
    DESCRIPTION
       "The tmnxSubMgmtPortStatsTable has an entry with statistics for each
        port on which subscriber hosts are allocated."
    ::= { tmnxSubMgmtObjects 104 }

tmnxSubMgmtPortStatsEntry   OBJECT-TYPE
    SYNTAX      TmnxSubMgmtPortStatsEntry
    MAX-ACCESS  not-accessible
    STATUS      current
    DESCRIPTION
       "Each conceptual row represents statistics for a port on which subscriber
        hosts are allocated."
    INDEX       { tmnxChassisIndex,
                  tmnxSubMgmtPortID }
    ::= { tmnxSubMgmtPortStatsTable 1 }

TmnxSubMgmtPortStatsEntry ::= SEQUENCE {
        tmnxSubMgmtPortID                TmnxPortID,
        tmnxSubMgmtPortSIpcp             Counter32,
        tmnxSubMgmtPortSIpcpPeak         Counter32,
        tmnxSubMgmtPortSL2tpHost         Counter32,
        tmnxSubMgmtPortSL2tpHostPeak     Counter32,
        tmnxSubMgmtPortSDhcp             Counter32,
        tmnxSubMgmtPortSDhcpPeak         Counter32,
        tmnxSubMgmtPortSArp              Counter32,
        tmnxSubMgmtPortSArpPeak          Counter32,
        tmnxSubMgmtPortSStatic           Counter32,
        tmnxSubMgmtPortSStaticPeak       Counter32,
        tmnxSubMgmtPortSNonSub           Counter32,
        tmnxSubMgmtPortSNonSubPeak       Counter32,
        tmnxSubMgmtPortSPppSlaac         Counter32,
        tmnxSubMgmtPortSPppSlaacPeak     Counter32,
        tmnxSubMgmtPortSPppDhcp6Pd       Counter32,
        tmnxSubMgmtPortSPppDhcp6PdPeak   Counter32,
        tmnxSubMgmtPortSPppDhcp6Na       Counter32,
        tmnxSubMgmtPortSPppDhcp6NaPeak   Counter32,
        tmnxSubMgmtPortSIpoeSlaac        Counter32,
        tmnxSubMgmtPortSIpoeSlaacPeak    Counter32,
        tmnxSubMgmtPortSIpoeDhcp6Pd      Counter32,
        tmnxSubMgmtPortSIpoeDhcp6PdPeak  Counter32,
        tmnxSubMgmtPortSIpoeDhcp6Na      Counter32,
        tmnxSubMgmtPortSIpoeDhcp6NaPeak  Counter32,
        tmnxSubMgmtPortSV4               Counter32,
        tmnxSubMgmtPortSV4Peak           Counter32,
        tmnxSubMgmtPortSV6               Counter32,
        tmnxSubMgmtPortSV6Peak           Counter32,
        tmnxSubMgmtPortSPppHosts         Counter32,
        tmnxSubMgmtPortSPppHostsPeak     Counter32,
        tmnxSubMgmtPortSIpoeHosts        Counter32,
        tmnxSubMgmtPortSIpoeHostsPeak    Counter32,
        tmnxSubMgmtPortSTotal            Counter32,
        tmnxSubMgmtPortSTotalPeak        Counter32,
        tmnxSubMgmtPortSPppLclOE         Counter32,
        tmnxSubMgmtPortSPppLclOEPeak     Counter32,
        tmnxSubMgmtPortSPppLclOEOA       Counter32,
        tmnxSubMgmtPortSPppLclOEOAPeak   Counter32,
        tmnxSubMgmtPortSPppLclOA         Counter32,
        tmnxSubMgmtPortSPppLclOAPeak     Counter32,
        tmnxSubMgmtPortSPppLclL2tp       Counter32,
        tmnxSubMgmtPortSPppLclL2tpPeak   Counter32,
        tmnxSubMgmtPortSPppLclTotal      Counter32,
        tmnxSubMgmtPortSPppLclTotalPeak  Counter32,
        tmnxSubMgmtPortSPppLacOE         Counter32,
        tmnxSubMgmtPortSPppLacOEPeak     Counter32,
        tmnxSubMgmtPortSPppLacOEOA       Counter32,
        tmnxSubMgmtPortSPppLacOEOAPeak   Counter32,
        tmnxSubMgmtPortSPppLacOA         Counter32,
        tmnxSubMgmtPortSPppLacOAPeak     Counter32,
        tmnxSubMgmtPortSPppLacL2tp       Counter32,
        tmnxSubMgmtPortSPppLacL2tpPeak   Counter32,
        tmnxSubMgmtPortSPppLacTotal      Counter32,
        tmnxSubMgmtPortSPppLacTotalPeak  Counter32,
        tmnxSubMgmtPortSPppSessIs        Counter32,
        tmnxSubMgmtPortSPppSessIsPeak    Counter32,
        tmnxSubMgmtPortSPppSessTotal     Counter32,
        tmnxSubMgmtPortSPppSessTotalPeak Counter32,
        tmnxSubMgmtPortSSubscribers      Counter32,
        tmnxSubMgmtPortSSubscribersPeak  Counter32,
        tmnxSubMgmtPortSDhcpBsmAs        Counter32,
        tmnxSubMgmtPortSDhcpBsmAsPeak    Counter32,
        tmnxSubMgmtPortSStaticBsmAs      Counter32,
        tmnxSubMgmtPortSStaticBsmAsPeak  Counter32,
        tmnxSubMgmtPortSDhcpBsm          Counter32,
        tmnxSubMgmtPortSDhcpBsmPeak      Counter32,
        tmnxSubMgmtPortSStaticBsm        Counter32,
        tmnxSubMgmtPortSStaticBsmPeak    Counter32,
        tmnxSubMgmtPortSPppDhcp6Mr       Counter32,
        tmnxSubMgmtPortSPppDhcp6MrPeak   Counter32,
        tmnxSubMgmtPortSIpoeDhcp6Mr      Counter32,
        tmnxSubMgmtPortSIpoeDhcp6MrPeak  Counter32,
        tmnxSubMgmtPortSV6StaticWan      Counter32,
        tmnxSubMgmtPortSV6StaticWanPeak  Counter32,
        tmnxSubMgmtPortSBsmDhcp6Pd       Counter32,
        tmnxSubMgmtPortSBsmDhcp6PdPeak   Counter32,
        tmnxSubMgmtPortSBsmDhcp6Na       Counter32,
        tmnxSubMgmtPortSBsmDhcp6NaPeak   Counter32,
        tmnxSubMgmtPortSTotInternal      Counter32,
        tmnxSubMgmtPortSTotInternalPeak  Counter32,
        tmnxSubMgmtPortSTotDhcp          Counter32,
        tmnxSubMgmtPortSTotDhcpPeak      Counter32,
        tmnxSubMgmtPortSTotDhcpV6        Counter32,
        tmnxSubMgmtPortSTotDhcpV6Peak    Counter32,
        tmnxSubMgmtPortSTotMngdRt        Counter32,
        tmnxSubMgmtPortSTotMngdRtPeak    Counter32,
        tmnxSubMgmtPortSIpoeSesIs        Counter32,
        tmnxSubMgmtPortSIpoeSesIsPeak    Counter32,
        tmnxSubMgmtPortSIpoeSesTotal     Counter32,
        tmnxSubMgmtPortSIpoeSesTotalPeak Counter32,
        tmnxSubMgmtPortSV6StaticPd       Counter32,
        tmnxSubMgmtPortSV6StaticPdPeak   Counter32
    }

tmnxSubMgmtPortID OBJECT-TYPE
    SYNTAX          TmnxPortID
    MAX-ACCESS      not-accessible
    STATUS          current
    DESCRIPTION
        "tmnxSubMgmtPortID is an index into this table. It maps this port to 
         its entry in the mib-2 interfaces table."
    ::= { tmnxSubMgmtPortStatsEntry 1 }

tmnxSubMgmtPortSIpcp OBJECT-TYPE
    SYNTAX          Counter32
    MAX-ACCESS      read-only
    STATUS          current
    DESCRIPTION     "The value of tmnxSubMgmtPortSIpcp indicates the number
                     of current PPP hosts (IPCP) on this port."
    ::= { tmnxSubMgmtPortStatsEntry 2 }

tmnxSubMgmtPortSIpcpPeak OBJECT-TYPE
    SYNTAX          Counter32
    MAX-ACCESS      read-only
    STATUS          current
    DESCRIPTION     "The value of tmnxSubMgmtPortSIpcpPeak indicates the peak
                     number of PPP hosts (IPCP) on this port."
    ::= { tmnxSubMgmtPortStatsEntry 3 }

tmnxSubMgmtPortSL2tpHost OBJECT-TYPE
    SYNTAX          Counter32
    MAX-ACCESS      read-only
    STATUS          current
    DESCRIPTION     "The value of tmnxSubMgmtPortSL2tpHost indicates the number
                     of current L2TP hosts (LAC) on this port."
    ::= { tmnxSubMgmtPortStatsEntry 4 }

tmnxSubMgmtPortSL2tpHostPeak OBJECT-TYPE
    SYNTAX          Counter32
    MAX-ACCESS      read-only
    STATUS          current
    DESCRIPTION     "The value of tmnxSubMgmtPortSL2tpHostPeak indicates the peak
                     number of L2TP hosts (LAC) on this port."
    ::= { tmnxSubMgmtPortStatsEntry 5 }

tmnxSubMgmtPortSDhcp OBJECT-TYPE
    SYNTAX          Counter32
    MAX-ACCESS      read-only
    STATUS          current
    DESCRIPTION     "The value of tmnxSubMgmtPortSDhcp indicates the number
                     of current IPOE hosts (DHCP) on this port."
    ::= { tmnxSubMgmtPortStatsEntry 6 }

tmnxSubMgmtPortSDhcpPeak OBJECT-TYPE
    SYNTAX          Counter32
    MAX-ACCESS      read-only
    STATUS          current
    DESCRIPTION     "The value of tmnxSubMgmtPortSDhcpPeak indicates the peak
                     number of IPOE hosts (DHCP) on this port."
    ::= { tmnxSubMgmtPortStatsEntry 7 }

tmnxSubMgmtPortSArp OBJECT-TYPE
    SYNTAX          Counter32
    MAX-ACCESS      read-only
    STATUS          current
    DESCRIPTION     "The value of tmnxSubMgmtPortSArp indicates the number
                     of current IPOE hosts (ARP) on this port."
    ::= { tmnxSubMgmtPortStatsEntry 8 }

tmnxSubMgmtPortSArpPeak OBJECT-TYPE
    SYNTAX          Counter32
    MAX-ACCESS      read-only
    STATUS          current
    DESCRIPTION     "The value of tmnxSubMgmtPortSArpPeak indicates the peak
                     number of IPOE hosts (ARP) on this port."
    ::= { tmnxSubMgmtPortStatsEntry 9 }

tmnxSubMgmtPortSStatic OBJECT-TYPE
    SYNTAX          Counter32
    MAX-ACCESS      read-only
    STATUS          current
    DESCRIPTION     "The value of tmnxSubMgmtPortSStatic indicates the number
                     of current IPOE hosts (Static) on this port."
    ::= { tmnxSubMgmtPortStatsEntry 10 }

tmnxSubMgmtPortSStaticPeak OBJECT-TYPE
    SYNTAX          Counter32
    MAX-ACCESS      read-only
    STATUS          current
    DESCRIPTION     "The value of tmnxSubMgmtPortSStaticPeak indicates the peak
                     number of IPOE hosts (Static) on this port."
    ::= { tmnxSubMgmtPortStatsEntry 11 }

tmnxSubMgmtPortSNonSub OBJECT-TYPE
    SYNTAX          Counter32
    MAX-ACCESS      read-only
    STATUS          current
    DESCRIPTION     "The value of tmnxSubMgmtPortSNonSub indicates the number
                     of current Non Sub hosts on this port."
    ::= { tmnxSubMgmtPortStatsEntry 12 }

tmnxSubMgmtPortSNonSubPeak OBJECT-TYPE
    SYNTAX          Counter32
    MAX-ACCESS      read-only
    STATUS          current
    DESCRIPTION     "The value of tmnxSubMgmtPortSNonSubPeak indicates the peak
                     number of Non Sub hosts on this port."
    ::= { tmnxSubMgmtPortStatsEntry 13 }

tmnxSubMgmtPortSPppSlaac OBJECT-TYPE
    SYNTAX          Counter32
    MAX-ACCESS      read-only
    STATUS          current
    DESCRIPTION     "The value of tmnxSubMgmtPortSPppSlaac indicates the number
                     of current PPP hosts (SLAAC) on this port."
    ::= { tmnxSubMgmtPortStatsEntry 14 }

tmnxSubMgmtPortSPppSlaacPeak OBJECT-TYPE
    SYNTAX          Counter32
    MAX-ACCESS      read-only
    STATUS          current
    DESCRIPTION     "The value of tmnxSubMgmtPortSPppSlaacPeak indicates the 
                     peak number of PPP hosts (SLAAC) on this port."
    ::= { tmnxSubMgmtPortStatsEntry 15 }

tmnxSubMgmtPortSPppDhcp6Pd OBJECT-TYPE
    SYNTAX          Counter32
    MAX-ACCESS      read-only
    STATUS          current
    DESCRIPTION     "The value of tmnxSubMgmtPortSPppDhcp6Pd indicates the number
                     of current PPP hosts (DHCP6 PD) on this port."
    ::= { tmnxSubMgmtPortStatsEntry 16 }

tmnxSubMgmtPortSPppDhcp6PdPeak OBJECT-TYPE
    SYNTAX          Counter32
    MAX-ACCESS      read-only
    STATUS          current
    DESCRIPTION     "The value of tmnxSubMgmtPortSPppDhcp6PdPeak indicates the 
                     peak number of PPP hosts (DHCP6 PD) on this port."
    ::= { tmnxSubMgmtPortStatsEntry 17 }

tmnxSubMgmtPortSPppDhcp6Na OBJECT-TYPE
    SYNTAX          Counter32
    MAX-ACCESS      read-only
    STATUS          current
    DESCRIPTION     "The value of tmnxSubMgmtPortSPppDhcp6Na indicates the number
                     of current PPP hosts (DHCP6 NA) on this port."
    ::= { tmnxSubMgmtPortStatsEntry 18 }

tmnxSubMgmtPortSPppDhcp6NaPeak OBJECT-TYPE
    SYNTAX          Counter32
    MAX-ACCESS      read-only
    STATUS          current
    DESCRIPTION     "The value of tmnxSubMgmtPortSPppDhcp6NaPeak indicates the 
                     peak number of PPP hosts (DHCP6 NA) on this port."
    ::= { tmnxSubMgmtPortStatsEntry 19 }

tmnxSubMgmtPortSIpoeSlaac OBJECT-TYPE
    SYNTAX          Counter32
    MAX-ACCESS      read-only
    STATUS          current
    DESCRIPTION     "The value of tmnxSubMgmtPortSIpoeSlaac indicates the 
                     number of current IPOE hosts (SLAAC) on this port."
    ::= { tmnxSubMgmtPortStatsEntry 20 }

tmnxSubMgmtPortSIpoeSlaacPeak OBJECT-TYPE
    SYNTAX          Counter32
    MAX-ACCESS      read-only
    STATUS          current
    DESCRIPTION     "The value of tmnxSubMgmtPortSIpoeSlaacPeak indicates the 
                     peak number of IPOE hosts (SLAAC) on this port."
    ::= { tmnxSubMgmtPortStatsEntry 21 }

tmnxSubMgmtPortSIpoeDhcp6Pd OBJECT-TYPE
    SYNTAX          Counter32
    MAX-ACCESS      read-only
    STATUS          current
    DESCRIPTION     "The value of tmnxSubMgmtPortSIpoeDhcp6Pd indicates the 
                     number of current IPOE hosts (DHCP6 PD) on this port."
    ::= { tmnxSubMgmtPortStatsEntry 22 }

tmnxSubMgmtPortSIpoeDhcp6PdPeak OBJECT-TYPE
    SYNTAX          Counter32
    MAX-ACCESS      read-only
    STATUS          current
    DESCRIPTION     "The value of tmnxSubMgmtPortSIpoeDhcp6PdPeak indicates the 
                     peak number of IPOE hosts (DHCP6 PD) on this port."
    ::= { tmnxSubMgmtPortStatsEntry 23 }

tmnxSubMgmtPortSIpoeDhcp6Na OBJECT-TYPE
    SYNTAX          Counter32
    MAX-ACCESS      read-only
    STATUS          current
    DESCRIPTION     "The value of tmnxSubMgmtPortSIpoeDhcp6Na indicates the 
                     number of current IPOE hosts (DHCP6 NA) on this port."
    ::= { tmnxSubMgmtPortStatsEntry 24 }

tmnxSubMgmtPortSIpoeDhcp6NaPeak OBJECT-TYPE
    SYNTAX          Counter32
    MAX-ACCESS      read-only
    STATUS          current
    DESCRIPTION     "The value of tmnxSubMgmtPortSIpoeDhcp6NaPeak indicates the 
                     peak number of IPOE hosts (DHCP6 NA) on this port."
    ::= { tmnxSubMgmtPortStatsEntry 25 }

tmnxSubMgmtPortSV4 OBJECT-TYPE
    SYNTAX          Counter32
    MAX-ACCESS      read-only
    STATUS          current
    DESCRIPTION     "The value of tmnxSubMgmtPortSV4 indicates the number
                     of current V4 hosts on this port."
    ::= { tmnxSubMgmtPortStatsEntry 26 }

tmnxSubMgmtPortSV4Peak OBJECT-TYPE
    SYNTAX          Counter32
    MAX-ACCESS      read-only
    STATUS          current
    DESCRIPTION     "The value of tmnxSubMgmtPortSV4Peak indicates the peak
                     number of V4 hosts on this port."
    ::= { tmnxSubMgmtPortStatsEntry 27 }

tmnxSubMgmtPortSV6 OBJECT-TYPE
    SYNTAX          Counter32
    MAX-ACCESS      read-only
    STATUS          current
    DESCRIPTION     "The value of tmnxSubMgmtPortSV6 indicates the number
                     of current V6 hosts on this port."
    ::= { tmnxSubMgmtPortStatsEntry 28 }

tmnxSubMgmtPortSV6Peak OBJECT-TYPE
    SYNTAX          Counter32
    MAX-ACCESS      read-only
    STATUS          current
    DESCRIPTION     "The value of tmnxSubMgmtPortSV6Peak indicates the peak
                     number of V6 hosts on this port."
    ::= { tmnxSubMgmtPortStatsEntry 29 }

tmnxSubMgmtPortSPppHosts OBJECT-TYPE
    SYNTAX          Counter32
    MAX-ACCESS      read-only
    STATUS          current
    DESCRIPTION     "The value of tmnxSubMgmtPortSPppHosts indicates the 
                     number of current PPP hosts on this port."
    ::= { tmnxSubMgmtPortStatsEntry 30 }

tmnxSubMgmtPortSPppHostsPeak OBJECT-TYPE
    SYNTAX          Counter32
    MAX-ACCESS      read-only
    STATUS          current
    DESCRIPTION     "The value of tmnxSubMgmtPortSPppHostsPeak indicates the
                     peak number of PPP hosts on this port."
    ::= { tmnxSubMgmtPortStatsEntry 31 }

tmnxSubMgmtPortSIpoeHosts OBJECT-TYPE
    SYNTAX          Counter32
    MAX-ACCESS      read-only
    STATUS          current
    DESCRIPTION     "The value of tmnxSubMgmtPortSIpoeHosts indicates the 
                     number of current IPOE hosts on this port."
    ::= { tmnxSubMgmtPortStatsEntry 32 }

tmnxSubMgmtPortSIpoeHostsPeak OBJECT-TYPE
    SYNTAX          Counter32
    MAX-ACCESS      read-only
    STATUS          current
    DESCRIPTION     "The value of tmnxSubMgmtPortSIpoeHostsPeak indicates the
                     peak number of IPOE hosts on this port."
    ::= { tmnxSubMgmtPortStatsEntry 33 }

tmnxSubMgmtPortSTotal OBJECT-TYPE
    SYNTAX          Counter32
    MAX-ACCESS      read-only
    STATUS          current
    DESCRIPTION     "The value of tmnxSubMgmtPortSTotal indicates the number
                     of current total hosts on this port."
    ::= { tmnxSubMgmtPortStatsEntry 34 }

tmnxSubMgmtPortSTotalPeak OBJECT-TYPE
    SYNTAX          Counter32
    MAX-ACCESS      read-only
    STATUS          current
    DESCRIPTION     "The value of tmnxSubMgmtPortSTotalPeak indicates the peak
                     number of total hosts on this port."
    ::= { tmnxSubMgmtPortStatsEntry 35 }

tmnxSubMgmtPortSPppLclOE OBJECT-TYPE
    SYNTAX          Counter32
    MAX-ACCESS      read-only
    STATUS          current
    DESCRIPTION     "The value of tmnxSubMgmtPortSPppLclOE indicates the
                     number of current locally terminated PPP sessions (PPPoE)
                     on this port."
    ::= { tmnxSubMgmtPortStatsEntry 36 }

tmnxSubMgmtPortSPppLclOEPeak OBJECT-TYPE
    SYNTAX          Counter32
    MAX-ACCESS      read-only
    STATUS          current
    DESCRIPTION     "The value of tmnxSubMgmtPortSPppLclOEPeak indicates the 
                     peak number of locally terminated PPP sessions (PPPoE) 
                     on this port."
    ::= { tmnxSubMgmtPortStatsEntry 37 }

tmnxSubMgmtPortSPppLclOEOA OBJECT-TYPE
    SYNTAX          Counter32
    MAX-ACCESS      read-only
    STATUS          current
    DESCRIPTION     "The value of tmnxSubMgmtPortSPppLclOEOA indicates the 
                     number of current locally terminated PPP sessions (PPPoEoA)
                     on this port."
    ::= { tmnxSubMgmtPortStatsEntry 38 }

tmnxSubMgmtPortSPppLclOEOAPeak OBJECT-TYPE
    SYNTAX          Counter32
    MAX-ACCESS      read-only
    STATUS          current
    DESCRIPTION     "The value of tmnxSubMgmtPortSPppLclOEOAPeak indicates the 
                     peak number of locally terminated PPP sessions (PPPoEoA) 
                     on this port."
    ::= { tmnxSubMgmtPortStatsEntry 39 }

tmnxSubMgmtPortSPppLclOA OBJECT-TYPE
    SYNTAX          Counter32
    MAX-ACCESS      read-only
    STATUS          current
    DESCRIPTION     "The value of tmnxSubMgmtPortSPppLclOA indicates the number
                     of current locally terminated PPP sessions (PPPoA)
                     on this port."
    ::= { tmnxSubMgmtPortStatsEntry 40 }

tmnxSubMgmtPortSPppLclOAPeak OBJECT-TYPE
    SYNTAX          Counter32
    MAX-ACCESS      read-only
    STATUS          current
    DESCRIPTION     "The value of tmnxSubMgmtPortSPppLclOAPeak indicates the 
                     peak number of locally terminated PPP sessions (PPPoA) 
                     on this port."
    ::= { tmnxSubMgmtPortStatsEntry 41 }

tmnxSubMgmtPortSPppLclL2tp OBJECT-TYPE
    SYNTAX          Counter32
    MAX-ACCESS      read-only
    STATUS          current
    DESCRIPTION     "The value of tmnxSubMgmtPortSPppLclL2tp indicates the 
                     number of current locally terminated PPP sessions (L2TP LNS)
                     on this port."
    ::= { tmnxSubMgmtPortStatsEntry 42 }
    
tmnxSubMgmtPortSPppLclL2tpPeak OBJECT-TYPE
    SYNTAX          Counter32
    MAX-ACCESS      read-only
    STATUS          current
    DESCRIPTION     "The value of tmnxSubMgmtPortSPppLclL2tpPeak indicates the 
                     peak number of locally terminated PPP sessions (L2TP LNS)
                     on this port."
    ::= { tmnxSubMgmtPortStatsEntry 43 }

tmnxSubMgmtPortSPppLclTotal OBJECT-TYPE
    SYNTAX          Counter32
    MAX-ACCESS      read-only
    STATUS          current
    DESCRIPTION     "The value of tmnxSubMgmtPortSPppLclTotal indicates the 
                     total number of current locally terminated PPP sessions
                     on this port."
    ::= { tmnxSubMgmtPortStatsEntry 44 }

tmnxSubMgmtPortSPppLclTotalPeak OBJECT-TYPE
    SYNTAX          Counter32
    MAX-ACCESS      read-only
    STATUS          current
    DESCRIPTION     "The value of tmnxSubMgmtPortSPppLclTotalPeak indicates the 
                     total peak number of locally terminated PPP sessions
                     on this port."
    ::= { tmnxSubMgmtPortStatsEntry 45 }

tmnxSubMgmtPortSPppLacOE OBJECT-TYPE
    SYNTAX          Counter32
    MAX-ACCESS      read-only
    STATUS          current
    DESCRIPTION     "The value of tmnxSubMgmtPortSPppLacOE indicates the
                     number of current PPP sessions (PPPoE) tunneled over L2TP 
                     on this port."
    ::= { tmnxSubMgmtPortStatsEntry 46 }

tmnxSubMgmtPortSPppLacOEPeak OBJECT-TYPE
    SYNTAX          Counter32
    MAX-ACCESS      read-only
    STATUS          current
    DESCRIPTION     "The value of tmnxSubMgmtPortSPppLacOEPeak indicates the 
                     peak number of PPP sessions (PPPoE) tunneled over L2TP 
                     on this port."
    ::= { tmnxSubMgmtPortStatsEntry 47 }

tmnxSubMgmtPortSPppLacOEOA OBJECT-TYPE
    SYNTAX          Counter32
    MAX-ACCESS      read-only
    STATUS          current
    DESCRIPTION     "The value of tmnxSubMgmtPortSPppLacOEOA indicates the 
                     number of current PPP sessions (PPPoEoA) tunneled over L2TP 
                     on this port."
    ::= { tmnxSubMgmtPortStatsEntry 48 }

tmnxSubMgmtPortSPppLacOEOAPeak OBJECT-TYPE
    SYNTAX          Counter32
    MAX-ACCESS      read-only
    STATUS          current
    DESCRIPTION     "The value of tmnxSubMgmtPortSPppLacOEOAPeak indicates the 
                     peak number of PPP sessions (PPPoEoA) tunneled over L2TP 
                     on this port."
    ::= { tmnxSubMgmtPortStatsEntry 49 }

tmnxSubMgmtPortSPppLacOA OBJECT-TYPE
    SYNTAX          Counter32
    MAX-ACCESS      read-only
    STATUS          current
    DESCRIPTION     "The value of tmnxSubMgmtPortSPppLacOA indicates the 
                     number of current PPP sessions (PPPoA) tunneled over L2TP 
                     on this port."
    ::= { tmnxSubMgmtPortStatsEntry 50 }

tmnxSubMgmtPortSPppLacOAPeak OBJECT-TYPE
    SYNTAX          Counter32
    MAX-ACCESS      read-only
    STATUS          current
    DESCRIPTION     "The value of tmnxSubMgmtPortSPppLacOAPeak indicates the 
                     peak number of PPP sessions (PPPoA) tunneled over L2TP
                     on this port."
    ::= { tmnxSubMgmtPortStatsEntry 51 }

tmnxSubMgmtPortSPppLacL2tp OBJECT-TYPE
    SYNTAX          Counter32
    MAX-ACCESS      read-only
    STATUS          current
    DESCRIPTION     "The value of tmnxSubMgmtPortSPppLacL2tp indicates the 
                     number of current PPP sessions (L2TP LTS) tunneled over L2TP
                     on this port."
    ::= { tmnxSubMgmtPortStatsEntry 52 }

tmnxSubMgmtPortSPppLacL2tpPeak OBJECT-TYPE
    SYNTAX          Counter32
    MAX-ACCESS      read-only
    STATUS          current
    DESCRIPTION     "The value of tmnxSubMgmtPortSPppLacL2tpPeak indicates the 
                     peak number of PPP sessions (L2TP LTS) tunneled over L2TP 
                     on this port."
    ::= { tmnxSubMgmtPortStatsEntry 53 }

tmnxSubMgmtPortSPppLacTotal OBJECT-TYPE
    SYNTAX          Counter32
    MAX-ACCESS      read-only
    STATUS          current
    DESCRIPTION     "The value of tmnxSubMgmtPortSPppLacTotal indicates the 
                     total number of current PPP sessions tunneled over L2TP
                     on this port."
    ::= { tmnxSubMgmtPortStatsEntry 54 }

tmnxSubMgmtPortSPppLacTotalPeak OBJECT-TYPE
    SYNTAX          Counter32
    MAX-ACCESS      read-only
    STATUS          current
    DESCRIPTION     "The value of tmnxSubMgmtPortSPppLacTotalPeak indicates the 
                     total peak number of PPP sessions tunneled over L2TP 
                     on this port."
    ::= { tmnxSubMgmtPortStatsEntry 55 }

tmnxSubMgmtPortSPppSessIs OBJECT-TYPE
    SYNTAX          Counter32
    MAX-ACCESS      read-only
    STATUS          current
    DESCRIPTION     "The value of tmnxSubMgmtPortSPppSessIs indicates the 
                     number of current PPP sessions in setup on this port."
    ::= { tmnxSubMgmtPortStatsEntry 56 }

tmnxSubMgmtPortSPppSessIsPeak OBJECT-TYPE
    SYNTAX          Counter32
    MAX-ACCESS      read-only
    STATUS          current
    DESCRIPTION     "The value of tmnxSubMgmtPortSPppSessIsPeak indicates the 
                     peak number of PPP sessions in setup on this port."
    ::= { tmnxSubMgmtPortStatsEntry 57 }

tmnxSubMgmtPortSPppSessTotal OBJECT-TYPE
    SYNTAX          Counter32
    MAX-ACCESS      read-only
    STATUS          current
    DESCRIPTION     "The value of tmnxSubMgmtPortSPppSessTotal indicates the 
                     total number of current PPP sessions established on this port."
    ::= { tmnxSubMgmtPortStatsEntry 58 }

tmnxSubMgmtPortSPppSessTotalPeak OBJECT-TYPE
    SYNTAX          Counter32
    MAX-ACCESS      read-only
    STATUS          current
    DESCRIPTION     "The value of tmnxSubMgmtPortSPppSessTotalPeak indicates the 
                     total peak number of PPP sessions established on this port."
    ::= { tmnxSubMgmtPortStatsEntry 59 }

tmnxSubMgmtPortSSubscribers OBJECT-TYPE
    SYNTAX          Counter32
    MAX-ACCESS      read-only
    STATUS          current
    DESCRIPTION     "The value of tmnxSubMgmtPortSSubscribers indicates the number
                     of current subscribers on this port."
    ::= { tmnxSubMgmtPortStatsEntry 60 }

tmnxSubMgmtPortSSubscribersPeak OBJECT-TYPE
    SYNTAX          Counter32
    MAX-ACCESS      read-only
    STATUS          current
    DESCRIPTION     "The value of tmnxSubMgmtPortSSubscribersPeak indicates the peak
                     number of subscribers on this port."
    ::= { tmnxSubMgmtPortStatsEntry 61 }

tmnxSubMgmtPortSDhcpBsmAs OBJECT-TYPE
    SYNTAX          Counter32
    MAX-ACCESS      read-only
    STATUS          current
    DESCRIPTION     "The value of tmnxSubMgmtPortSDhcpBsmAs indicates the number
                     of current IPOE BSM hosts with antispoof (DHCP) on this port."
    ::= { tmnxSubMgmtPortStatsEntry 62 }

tmnxSubMgmtPortSDhcpBsmAsPeak OBJECT-TYPE
    SYNTAX          Counter32
    MAX-ACCESS      read-only
    STATUS          current
    DESCRIPTION     "The value of tmnxSubMgmtPortSDhcpBsmAsPeak indicates the peak
                     number of IPOE BSM hosts with antispoof (DHCP) on this port."
    ::= { tmnxSubMgmtPortStatsEntry 63 }

tmnxSubMgmtPortSStaticBsmAs OBJECT-TYPE
    SYNTAX          Counter32
    MAX-ACCESS      read-only
    STATUS          current
    DESCRIPTION     "The value of tmnxSubMgmtPortSStaticBsmAs indicates the number
                     of current IPOE BSM static hosts with antispoof on this port."
    ::= { tmnxSubMgmtPortStatsEntry 64 }

tmnxSubMgmtPortSStaticBsmAsPeak OBJECT-TYPE
    SYNTAX          Counter32
    MAX-ACCESS      read-only
    STATUS          current
    DESCRIPTION     "The value of tmnxSubMgmtPortSStaticBsmAsPeak indicates the peak
                     number of IPOE BSM static hosts with antispoof on this port."
    ::= { tmnxSubMgmtPortStatsEntry 65 }

tmnxSubMgmtPortSDhcpBsm OBJECT-TYPE
    SYNTAX          Counter32
    MAX-ACCESS      read-only
    STATUS          current
    DESCRIPTION     "The value of tmnxSubMgmtPortSDhcpBsm indicates the number
                     of current IPOE BSM hosts (DHCP) on this port."
    ::= { tmnxSubMgmtPortStatsEntry 66 }

tmnxSubMgmtPortSDhcpBsmPeak OBJECT-TYPE
    SYNTAX          Counter32
    MAX-ACCESS      read-only
    STATUS          current
    DESCRIPTION     "The value of tmnxSubMgmtPortSDhcpBsmPeak indicates the peak
                     number of IPOE BSM hosts (DHCP) on this port."
    ::= { tmnxSubMgmtPortStatsEntry 67 }

tmnxSubMgmtPortSStaticBsm OBJECT-TYPE
    SYNTAX          Counter32
    MAX-ACCESS      read-only
    STATUS          current
    DESCRIPTION     "The value of tmnxSubMgmtPortSStaticBsm indicates the number
                     of current IPOE BSM static hosts on this port."
    ::= { tmnxSubMgmtPortStatsEntry 68 }

tmnxSubMgmtPortSStaticBsmPeak OBJECT-TYPE
    SYNTAX          Counter32
    MAX-ACCESS      read-only
    STATUS          current
    DESCRIPTION     "The value of tmnxSubMgmtPortSStaticBsmPeak indicates the peak
                     number of IPOE BSM static hosts on this port."
    ::= { tmnxSubMgmtPortStatsEntry 69 }

tmnxSubMgmtPortSPppDhcp6Mr OBJECT-TYPE
    SYNTAX          Counter32
    MAX-ACCESS      read-only
    STATUS          current
    DESCRIPTION     "The value of tmnxSubMgmtPortSPppDhcp6Mr indicates the number
                     of current PPP PD Managed Routes on this port."
    ::= { tmnxSubMgmtPortStatsEntry 70 }

tmnxSubMgmtPortSPppDhcp6MrPeak OBJECT-TYPE
    SYNTAX          Counter32
    MAX-ACCESS      read-only
    STATUS          current
    DESCRIPTION     "The value of tmnxSubMgmtPortSPppDhcp6MrPeak indicates the peak
                     number of PPP PD Managed Routes on this port."
    ::= { tmnxSubMgmtPortStatsEntry 71 }

tmnxSubMgmtPortSIpoeDhcp6Mr OBJECT-TYPE
    SYNTAX          Counter32
    MAX-ACCESS      read-only
    STATUS          current
    DESCRIPTION     "The value of tmnxSubMgmtPortSIpoeDhcp6Mr indicates the number
                     of current IPOE PD Managed Routes on this port."
    ::= { tmnxSubMgmtPortStatsEntry 72 }

tmnxSubMgmtPortSIpoeDhcp6MrPeak OBJECT-TYPE
    SYNTAX          Counter32
    MAX-ACCESS      read-only
    STATUS          current
    DESCRIPTION     "The value of tmnxSubMgmtPortSIpoeDhcp6MrPeak indicates the peak
                     number of IPOE PD Managed Routes on this port."
    ::= { tmnxSubMgmtPortStatsEntry 73 }

tmnxSubMgmtPortSV6StaticWan OBJECT-TYPE
    SYNTAX          Counter32
    MAX-ACCESS      read-only
    STATUS          current
    DESCRIPTION     "The value of tmnxSubMgmtPortSV6StaticWan indicates the number
                     of current IPOE IPv6 static WAN hosts on this port."
    ::= { tmnxSubMgmtPortStatsEntry 74 }

tmnxSubMgmtPortSV6StaticWanPeak OBJECT-TYPE
    SYNTAX          Counter32
    MAX-ACCESS      read-only
    STATUS          current
    DESCRIPTION     "The value of tmnxSubMgmtPortSV6StaticWanPeak indicates the peak
                     number of IPOE IPv6 static WAN hosts on this port."
    ::= { tmnxSubMgmtPortStatsEntry 75 }

tmnxSubMgmtPortSBsmDhcp6Pd OBJECT-TYPE
    SYNTAX          Counter32
    MAX-ACCESS      read-only
    STATUS          current
    DESCRIPTION     "The value of tmnxSubMgmtPortSBsmDhcp6Pd indicates the number
                     of current IPOE BSM hosts (DHCP6 PD) on this port."
    ::= { tmnxSubMgmtPortStatsEntry 76 }

tmnxSubMgmtPortSBsmDhcp6PdPeak OBJECT-TYPE
    SYNTAX          Counter32
    MAX-ACCESS      read-only
    STATUS          current
    DESCRIPTION     "The value of tmnxSubMgmtPortSBsmDhcp6PdPeak indicates the 
                     peak number of IPOE BSM hosts (DHCP6 PD) on this port."
    ::= { tmnxSubMgmtPortStatsEntry 77 }

tmnxSubMgmtPortSBsmDhcp6Na OBJECT-TYPE
    SYNTAX          Counter32
    MAX-ACCESS      read-only
    STATUS          current
    DESCRIPTION     "The value of tmnxSubMgmtPortSBsmDhcp6Na indicates the number
                     of current IPOE BSM hosts (DHCP6 NA) on this port."
    ::= { tmnxSubMgmtPortStatsEntry 78 }

tmnxSubMgmtPortSBsmDhcp6NaPeak OBJECT-TYPE
    SYNTAX          Counter32
    MAX-ACCESS      read-only
    STATUS          current
    DESCRIPTION     "The value of tmnxSubMgmtPortSBsmDhcp6NaPeak indicates the 
                     peak number of IPOE BSM hosts (DHCP6 NA) on this port."
    ::= { tmnxSubMgmtPortStatsEntry 79 }

tmnxSubMgmtPortSTotInternal OBJECT-TYPE
    SYNTAX          Counter32
    MAX-ACCESS      read-only
    STATUS          current
    DESCRIPTION     "The value of tmnxSubMgmtPortSTotInternal indicates the number
                     of current internal hosts on this port."
    ::= { tmnxSubMgmtPortStatsEntry 80 }

tmnxSubMgmtPortSTotInternalPeak OBJECT-TYPE
    SYNTAX          Counter32
    MAX-ACCESS      read-only
    STATUS          current
    DESCRIPTION     "The value of tmnxSubMgmtPortSTotInternalPeak indicates the 
                     peak number of internal hosts on this port."
    ::= { tmnxSubMgmtPortStatsEntry 81 }

tmnxSubMgmtPortSTotDhcp OBJECT-TYPE
    SYNTAX          Counter32
    MAX-ACCESS      read-only
    STATUS          current
    DESCRIPTION     "The value of tmnxSubMgmtPortSTotDhcp indicates the number
                     of current DHCP hosts on this port."
    ::= { tmnxSubMgmtPortStatsEntry 82 }

tmnxSubMgmtPortSTotDhcpPeak OBJECT-TYPE
    SYNTAX          Counter32
    MAX-ACCESS      read-only
    STATUS          current
    DESCRIPTION     "The value of tmnxSubMgmtPortSTotDhcpPeak indicates the 
                     peak number of DHCP hosts on this port."
    ::= { tmnxSubMgmtPortStatsEntry 83 }

tmnxSubMgmtPortSTotDhcpV6 OBJECT-TYPE
    SYNTAX          Counter32
    MAX-ACCESS      read-only
    STATUS          current
    DESCRIPTION     "The value of tmnxSubMgmtPortSTotDhcpV6 indicates the number
                     of current DHCPv6 hosts on this port."
    ::= { tmnxSubMgmtPortStatsEntry 84 }

tmnxSubMgmtPortSTotDhcpV6Peak OBJECT-TYPE
    SYNTAX          Counter32
    MAX-ACCESS      read-only
    STATUS          current
    DESCRIPTION     "The value of tmnxSubMgmtPortSTotDhcpV6Peak indicates the 
                     peak number of DHCPv6 hosts on this port."
    ::= { tmnxSubMgmtPortStatsEntry 85 }

tmnxSubMgmtPortSTotMngdRt OBJECT-TYPE
    SYNTAX          Counter32
    MAX-ACCESS      read-only
    STATUS          current
    DESCRIPTION     "The value of tmnxSubMgmtPortSTotMngdRt indicates the number
                     of current PD Managed Routes on this port."
    ::= { tmnxSubMgmtPortStatsEntry 86 }

tmnxSubMgmtPortSTotMngdRtPeak OBJECT-TYPE
    SYNTAX          Counter32
    MAX-ACCESS      read-only
    STATUS          current
    DESCRIPTION     "The value of tmnxSubMgmtPortSTotMngdRtPeak indicates the 
                     peak number of PD Managed Routes on this port."
    ::= { tmnxSubMgmtPortStatsEntry 87 }

tmnxSubMgmtPortSIpoeSesIs OBJECT-TYPE
    SYNTAX          Counter32
    MAX-ACCESS      read-only
    STATUS          current
    DESCRIPTION     "The value of tmnxSubMgmtPortSIpoeSesIs indicates the number
                     of current IPOE sessions in setup on this port."
    ::= { tmnxSubMgmtPortStatsEntry 88 }

tmnxSubMgmtPortSIpoeSesIsPeak OBJECT-TYPE
    SYNTAX          Counter32
    MAX-ACCESS      read-only
    STATUS          current
    DESCRIPTION     "The value of tmnxSubMgmtPortSIpoeSesIsPeak indicates the 
                     peak number of IPOE sessions in setup on this port."
    ::= { tmnxSubMgmtPortStatsEntry 89 }

tmnxSubMgmtPortSIpoeSesTotal OBJECT-TYPE
    SYNTAX          Counter32
    MAX-ACCESS      read-only
    STATUS          current
    DESCRIPTION     "The value of tmnxSubMgmtPortSIpoeSesTotal indicates the number
                     of current IPOE sessions on this port."
    ::= { tmnxSubMgmtPortStatsEntry 90 }

tmnxSubMgmtPortSIpoeSesTotalPeak OBJECT-TYPE
    SYNTAX          Counter32
    MAX-ACCESS      read-only
    STATUS          current
    DESCRIPTION     "The value of tmnxSubMgmtPortSIpoeSesTotalPeak indicates the 
                     peak number of IPOE sessions on this port."
    ::= { tmnxSubMgmtPortStatsEntry 91 }

tmnxSubMgmtPortSV6StaticPd OBJECT-TYPE
    SYNTAX          Counter32
    MAX-ACCESS      read-only
    STATUS          current
    DESCRIPTION     "The value of tmnxSubMgmtPortSV6StaticPd indicates the number
                     of current IPOE IPv6 static prefixes on this port."
    ::= { tmnxSubMgmtPortStatsEntry 92 }

tmnxSubMgmtPortSV6StaticPdPeak OBJECT-TYPE
    SYNTAX          Counter32
    MAX-ACCESS      read-only
    STATUS          current
    DESCRIPTION     "The value of tmnxSubMgmtPortSV6StaticPdPeak indicates the peak
                     number of IPOE IPv6 static prefixes on this port."
    ::= { tmnxSubMgmtPortStatsEntry 93 }

--
--  The Subscriber Mgmt per MDA Statistics Table
--

tmnxSubMgmtMdaStatsTable   OBJECT-TYPE
    SYNTAX      SEQUENCE OF TmnxSubMgmtMdaStatsEntry
    MAX-ACCESS  not-accessible
    STATUS      current
    DESCRIPTION
       "The tmnxSubMgmtMdaStatsTable has an entry with statistics for each
        MDA on which subscriber hosts are allocated."
    ::= { tmnxSubMgmtObjects 105 }

tmnxSubMgmtMdaStatsEntry   OBJECT-TYPE
    SYNTAX      TmnxSubMgmtMdaStatsEntry
    MAX-ACCESS  not-accessible
    STATUS      current
    DESCRIPTION
       "Each conceptual row represents statistics for a MDA on which subscriber
        hosts are allocated."
    INDEX       { tmnxChassisIndex,
                  tmnxCardSlotNum, 
                  tmnxMDASlotNum }
    ::= { tmnxSubMgmtMdaStatsTable 1 }

TmnxSubMgmtMdaStatsEntry ::= SEQUENCE {
        tmnxSubMgmtMdaSIpcp              Counter32,
        tmnxSubMgmtMdaSIpcpPeak          Counter32,
        tmnxSubMgmtMdaSL2tpHost          Counter32,
        tmnxSubMgmtMdaSL2tpHostPeak      Counter32,
        tmnxSubMgmtMdaSDhcp              Counter32,
        tmnxSubMgmtMdaSDhcpPeak          Counter32,
        tmnxSubMgmtMdaSArp               Counter32,
        tmnxSubMgmtMdaSArpPeak           Counter32,
        tmnxSubMgmtMdaSStatic            Counter32,
        tmnxSubMgmtMdaSStaticPeak        Counter32,
        tmnxSubMgmtMdaSNonSub            Counter32,
        tmnxSubMgmtMdaSNonSubPeak        Counter32,
        tmnxSubMgmtMdaSPppSlaac          Counter32,
        tmnxSubMgmtMdaSPppSlaacPeak      Counter32,
        tmnxSubMgmtMdaSPppDhcp6Pd        Counter32,
        tmnxSubMgmtMdaSPppDhcp6PdPeak    Counter32,
        tmnxSubMgmtMdaSPppDhcp6Na        Counter32,
        tmnxSubMgmtMdaSPppDhcp6NaPeak    Counter32,
        tmnxSubMgmtMdaSIpoeSlaac         Counter32,
        tmnxSubMgmtMdaSIpoeSlaacPeak     Counter32,
        tmnxSubMgmtMdaSIpoeDhcp6Pd       Counter32,
        tmnxSubMgmtMdaSIpoeDhcp6PdPeak   Counter32,
        tmnxSubMgmtMdaSIpoeDhcp6Na       Counter32,
        tmnxSubMgmtMdaSIpoeDhcp6NaPeak   Counter32,
        tmnxSubMgmtMdaSV4                Counter32,
        tmnxSubMgmtMdaSV4Peak            Counter32,
        tmnxSubMgmtMdaSV6                Counter32,
        tmnxSubMgmtMdaSV6Peak            Counter32,
        tmnxSubMgmtMdaSPppHosts          Counter32,
        tmnxSubMgmtMdaSPppHostsPeak      Counter32,
        tmnxSubMgmtMdaSIpoeHosts         Counter32,
        tmnxSubMgmtMdaSIpoeHostsPeak     Counter32,
        tmnxSubMgmtMdaSTotal             Counter32,
        tmnxSubMgmtMdaSTotalPeak         Counter32,
        tmnxSubMgmtMdaSPppLclOE          Counter32,
        tmnxSubMgmtMdaSPppLclOEPeak      Counter32,
        tmnxSubMgmtMdaSPppLclOEOA        Counter32,
        tmnxSubMgmtMdaSPppLclOEOAPeak    Counter32,
        tmnxSubMgmtMdaSPppLclOA          Counter32,
        tmnxSubMgmtMdaSPppLclOAPeak      Counter32,
        tmnxSubMgmtMdaSPppLclL2tp        Counter32,
        tmnxSubMgmtMdaSPppLclL2tpPeak    Counter32,
        tmnxSubMgmtMdaSPppLclTotal       Counter32,
        tmnxSubMgmtMdaSPppLclTotalPeak   Counter32,
        tmnxSubMgmtMdaSPppLacOE          Counter32,
        tmnxSubMgmtMdaSPppLacOEPeak      Counter32,
        tmnxSubMgmtMdaSPppLacOEOA        Counter32,
        tmnxSubMgmtMdaSPppLacOEOAPeak    Counter32,
        tmnxSubMgmtMdaSPppLacOA          Counter32,
        tmnxSubMgmtMdaSPppLacOAPeak      Counter32,
        tmnxSubMgmtMdaSPppLacL2tp        Counter32,
        tmnxSubMgmtMdaSPppLacL2tpPeak    Counter32,
        tmnxSubMgmtMdaSPppLacTotal       Counter32,
        tmnxSubMgmtMdaSPppLacTotalPeak   Counter32,
        tmnxSubMgmtMdaSPppSessIs         Counter32,
        tmnxSubMgmtMdaSPppSessIsPeak     Counter32,
        tmnxSubMgmtMdaSPppSessTotal      Counter32,
        tmnxSubMgmtMdaSPppSessTotalPeak  Counter32,
        tmnxSubMgmtMdaSSubscribers       Counter32,
        tmnxSubMgmtMdaSSubscribersPeak   Counter32,
        tmnxSubMgmtMdaSDhcpBsmAs         Counter32,
        tmnxSubMgmtMdaSDhcpBsmAsPeak     Counter32,
        tmnxSubMgmtMdaSStaticBsmAs       Counter32,
        tmnxSubMgmtMdaSStaticBsmAsPeak   Counter32,
        tmnxSubMgmtMdaSDhcpBsm           Counter32,
        tmnxSubMgmtMdaSDhcpBsmPeak       Counter32,
        tmnxSubMgmtMdaSStaticBsm         Counter32,
        tmnxSubMgmtMdaSStaticBsmPeak     Counter32,
        tmnxSubMgmtMdaSPppDhcp6Mr        Counter32,
        tmnxSubMgmtMdaSPppDhcp6MrPeak    Counter32,
        tmnxSubMgmtMdaSIpoeDhcp6Mr       Counter32,
        tmnxSubMgmtMdaSIpoeDhcp6MrPeak   Counter32,
        tmnxSubMgmtMdaSV6StaticWan       Counter32,
        tmnxSubMgmtMdaSV6StaticWanPeak   Counter32,
        tmnxSubMgmtMdaSBsmDhcp6Pd        Counter32,
        tmnxSubMgmtMdaSBsmDhcp6PdPeak    Counter32,
        tmnxSubMgmtMdaSBsmDhcp6Na        Counter32,
        tmnxSubMgmtMdaSBsmDhcp6NaPeak    Counter32,
        tmnxSubMgmtMdaSTotInternal       Counter32,
        tmnxSubMgmtMdaSTotInternalPeak   Counter32,
        tmnxSubMgmtMdaSTotDhcp           Counter32,
        tmnxSubMgmtMdaSTotDhcpPeak       Counter32,
        tmnxSubMgmtMdaSTotDhcpV6         Counter32,
        tmnxSubMgmtMdaSTotDhcpV6Peak     Counter32,
        tmnxSubMgmtMdaSTotMngdRt         Counter32,
        tmnxSubMgmtMdaSTotMngdRtPeak     Counter32,
        tmnxSubMgmtMdaSIpoeSesIs         Counter32,
        tmnxSubMgmtMdaSIpoeSesIsPeak     Counter32,
        tmnxSubMgmtMdaSIpoeSesTotal      Counter32,
        tmnxSubMgmtMdaSIpoeSesTotalPeak  Counter32,
        tmnxSubMgmtMdaSV6StaticPd        Counter32,
        tmnxSubMgmtMdaSV6StaticPdPeak    Counter32
    }

tmnxSubMgmtMdaSIpcp OBJECT-TYPE
    SYNTAX          Counter32
    MAX-ACCESS      read-only
    STATUS          current
    DESCRIPTION     "The value of tmnxSubMgmtMdaSIpcp indicates the number
                     of current PPP hosts (IPCP) on this MDA."
    ::= { tmnxSubMgmtMdaStatsEntry 1 }

tmnxSubMgmtMdaSIpcpPeak OBJECT-TYPE
    SYNTAX          Counter32
    MAX-ACCESS      read-only
    STATUS          current
    DESCRIPTION     "The value of tmnxSubMgmtMdaSIpcpPeak indicates the peak
                     number of PPP hosts (IPCP) on this MDA."
    ::= { tmnxSubMgmtMdaStatsEntry 2 }

tmnxSubMgmtMdaSL2tpHost OBJECT-TYPE
    SYNTAX          Counter32
    MAX-ACCESS      read-only
    STATUS          current
    DESCRIPTION     "The value of tmnxSubMgmtMdaSL2tpHost indicates the number
                     of current L2TP hosts (LAC) on this MDA."
    ::= { tmnxSubMgmtMdaStatsEntry 3 }

tmnxSubMgmtMdaSL2tpHostPeak OBJECT-TYPE
    SYNTAX          Counter32
    MAX-ACCESS      read-only
    STATUS          current
    DESCRIPTION     "The value of tmnxSubMgmtMdaSL2tpHostPeak indicates the peak
                     number of L2TP hosts (LAC) on this MDA."
    ::= { tmnxSubMgmtMdaStatsEntry 4 }

tmnxSubMgmtMdaSDhcp OBJECT-TYPE
    SYNTAX          Counter32
    MAX-ACCESS      read-only
    STATUS          current
    DESCRIPTION     "The value of tmnxSubMgmtMdaSDhcp indicates the number
                     of current IPOE hosts (DHCP) on this MDA."
    ::= { tmnxSubMgmtMdaStatsEntry 5 }

tmnxSubMgmtMdaSDhcpPeak OBJECT-TYPE
    SYNTAX          Counter32
    MAX-ACCESS      read-only
    STATUS          current
    DESCRIPTION     "The value of tmnxSubMgmtMdaSDhcpPeak indicates the peak
                     number of IPOE hosts (DHCP) on this MDA."
    ::= { tmnxSubMgmtMdaStatsEntry 6 }

tmnxSubMgmtMdaSArp OBJECT-TYPE
    SYNTAX          Counter32
    MAX-ACCESS      read-only
    STATUS          current
    DESCRIPTION     "The value of tmnxSubMgmtMdaSArp indicates the number
                     of current IPOE hosts (ARP) on this MDA."
    ::= { tmnxSubMgmtMdaStatsEntry 7 }

tmnxSubMgmtMdaSArpPeak OBJECT-TYPE
    SYNTAX          Counter32
    MAX-ACCESS      read-only
    STATUS          current
    DESCRIPTION     "The value of tmnxSubMgmtMdaSArpPeak indicates the peak
                     number of IPOE hosts (ARP) on this MDA."
    ::= { tmnxSubMgmtMdaStatsEntry 8 }

tmnxSubMgmtMdaSStatic OBJECT-TYPE
    SYNTAX          Counter32
    MAX-ACCESS      read-only
    STATUS          current
    DESCRIPTION     "The value of tmnxSubMgmtMdaSStatic indicates the number
                     of current IPOE hosts (Static) on this MDA."
    ::= { tmnxSubMgmtMdaStatsEntry 9 }

tmnxSubMgmtMdaSStaticPeak OBJECT-TYPE
    SYNTAX          Counter32
    MAX-ACCESS      read-only
    STATUS          current
    DESCRIPTION     "The value of tmnxSubMgmtMdaSStaticPeak indicates the peak
                     number of IPOE hosts (Static) on this MDA."
    ::= { tmnxSubMgmtMdaStatsEntry 10 }

tmnxSubMgmtMdaSNonSub OBJECT-TYPE
    SYNTAX          Counter32
    MAX-ACCESS      read-only
    STATUS          current
    DESCRIPTION     "The value of tmnxSubMgmtMdaSNonSub indicates the number
                     of current Non Sub hosts on this MDA."
    ::= { tmnxSubMgmtMdaStatsEntry 11 }

tmnxSubMgmtMdaSNonSubPeak OBJECT-TYPE
    SYNTAX          Counter32
    MAX-ACCESS      read-only
    STATUS          current
    DESCRIPTION     "The value of tmnxSubMgmtMdaSNonSubPeak indicates the peak
                     number of Non Sub hosts on this MDA."
    ::= { tmnxSubMgmtMdaStatsEntry 12 }

tmnxSubMgmtMdaSPppSlaac OBJECT-TYPE
    SYNTAX          Counter32
    MAX-ACCESS      read-only
    STATUS          current
    DESCRIPTION     "The value of tmnxSubMgmtMdaSPppSlaac indicates the number
                     of current PPP hosts (SLAAC) on this MDA."
    ::= { tmnxSubMgmtMdaStatsEntry 13 }

tmnxSubMgmtMdaSPppSlaacPeak OBJECT-TYPE
    SYNTAX          Counter32
    MAX-ACCESS      read-only
    STATUS          current
    DESCRIPTION     "The value of tmnxSubMgmtMdaSPppSlaacPeak indicates the 
                     peak number of PPP hosts (SLAAC) on this MDA."
    ::= { tmnxSubMgmtMdaStatsEntry 14 }

tmnxSubMgmtMdaSPppDhcp6Pd OBJECT-TYPE
    SYNTAX          Counter32
    MAX-ACCESS      read-only
    STATUS          current
    DESCRIPTION     "The value of tmnxSubMgmtMdaSPppDhcp6Pd indicates the number
                     of current PPP hosts (DHCP6 PD) on this MDA."
    ::= { tmnxSubMgmtMdaStatsEntry 15 }

tmnxSubMgmtMdaSPppDhcp6PdPeak OBJECT-TYPE
    SYNTAX          Counter32
    MAX-ACCESS      read-only
    STATUS          current
    DESCRIPTION     "The value of tmnxSubMgmtMdaSPppDhcp6PdPeak indicates the 
                     peak number of PPP hosts (DHCP6 PD) on this MDA."
    ::= { tmnxSubMgmtMdaStatsEntry 16 }

tmnxSubMgmtMdaSPppDhcp6Na OBJECT-TYPE
    SYNTAX          Counter32
    MAX-ACCESS      read-only
    STATUS          current
    DESCRIPTION     "The value of tmnxSubMgmtMdaSPppDhcp6Na indicates the number
                     of current PPP hosts (DHCP6 NA) on this MDA."
    ::= { tmnxSubMgmtMdaStatsEntry 17 }

tmnxSubMgmtMdaSPppDhcp6NaPeak OBJECT-TYPE
    SYNTAX          Counter32
    MAX-ACCESS      read-only
    STATUS          current
    DESCRIPTION     "The value of tmnxSubMgmtMdaSPppDhcp6NaPeak indicates the 
                     peak number of PPP hosts (DHCP6 NA) on this MDA."
    ::= { tmnxSubMgmtMdaStatsEntry 18 }

tmnxSubMgmtMdaSIpoeSlaac OBJECT-TYPE
    SYNTAX          Counter32
    MAX-ACCESS      read-only
    STATUS          current
    DESCRIPTION     "The value of tmnxSubMgmtMdaSIpoeSlaac indicates the 
                     number of current IPOE hosts (SLAAC) on this MDA."
    ::= { tmnxSubMgmtMdaStatsEntry 19 }

tmnxSubMgmtMdaSIpoeSlaacPeak OBJECT-TYPE
    SYNTAX          Counter32
    MAX-ACCESS      read-only
    STATUS          current
    DESCRIPTION     "The value of tmnxSubMgmtMdaSIpoeSlaacPeak indicates the 
                     peak number of IPOE hosts (SLAAC) on this MDA."
    ::= { tmnxSubMgmtMdaStatsEntry 20 }

tmnxSubMgmtMdaSIpoeDhcp6Pd OBJECT-TYPE
    SYNTAX          Counter32
    MAX-ACCESS      read-only
    STATUS          current
    DESCRIPTION     "The value of tmnxSubMgmtMdaSIpoeDhcp6Pd indicates the 
                     number of current IPOE hosts (DHCP6 PD) on this MDA."
    ::= { tmnxSubMgmtMdaStatsEntry 21 }

tmnxSubMgmtMdaSIpoeDhcp6PdPeak OBJECT-TYPE
    SYNTAX          Counter32
    MAX-ACCESS      read-only
    STATUS          current
    DESCRIPTION     "The value of tmnxSubMgmtMdaSIpoeDhcp6PdPeak indicates the 
                     peak number of IPOE hosts (DHCP6 PD) on this MDA."
    ::= { tmnxSubMgmtMdaStatsEntry 22 }

tmnxSubMgmtMdaSIpoeDhcp6Na OBJECT-TYPE
    SYNTAX          Counter32
    MAX-ACCESS      read-only
    STATUS          current
    DESCRIPTION     "The value of tmnxSubMgmtMdaSIpoeDhcp6Na indicates the 
                     number of current IPOE hosts (DHCP6 NA) on this MDA."
    ::= { tmnxSubMgmtMdaStatsEntry 23 }

tmnxSubMgmtMdaSIpoeDhcp6NaPeak OBJECT-TYPE
    SYNTAX          Counter32
    MAX-ACCESS      read-only
    STATUS          current
    DESCRIPTION     "The value of tmnxSubMgmtMdaSIpoeDhcp6NaPeak indicates the 
                     peak number of IPOE hosts (DHCP6 NA) on this MDA."
    ::= { tmnxSubMgmtMdaStatsEntry 24 }

tmnxSubMgmtMdaSV4 OBJECT-TYPE
    SYNTAX          Counter32
    MAX-ACCESS      read-only
    STATUS          current
    DESCRIPTION     "The value of tmnxSubMgmtMdaSV4 indicates the number
                     of current V4 hosts on this MDA."
    ::= { tmnxSubMgmtMdaStatsEntry 25 }

tmnxSubMgmtMdaSV4Peak OBJECT-TYPE
    SYNTAX          Counter32
    MAX-ACCESS      read-only
    STATUS          current
    DESCRIPTION     "The value of tmnxSubMgmtMdaSV4Peak indicates the peak
                     number of V4 hosts on this MDA."
    ::= { tmnxSubMgmtMdaStatsEntry 26 }

tmnxSubMgmtMdaSV6 OBJECT-TYPE
    SYNTAX          Counter32
    MAX-ACCESS      read-only
    STATUS          current
    DESCRIPTION     "The value of tmnxSubMgmtMdaSV6 indicates the number
                     of current V6 hosts on this MDA."
    ::= { tmnxSubMgmtMdaStatsEntry 27 }

tmnxSubMgmtMdaSV6Peak OBJECT-TYPE
    SYNTAX          Counter32
    MAX-ACCESS      read-only
    STATUS          current
    DESCRIPTION     "The value of tmnxSubMgmtMdaSV6Peak indicates the peak
                     number of V6 hosts on this MDA."
    ::= { tmnxSubMgmtMdaStatsEntry 28 }

tmnxSubMgmtMdaSPppHosts OBJECT-TYPE
    SYNTAX          Counter32
    MAX-ACCESS      read-only
    STATUS          current
    DESCRIPTION     "The value of tmnxSubMgmtMdaSPppHosts indicates the 
                     number of current PPP hosts on this MDA."
    ::= { tmnxSubMgmtMdaStatsEntry 29 }

tmnxSubMgmtMdaSPppHostsPeak OBJECT-TYPE
    SYNTAX          Counter32
    MAX-ACCESS      read-only
    STATUS          current
    DESCRIPTION     "The value of tmnxSubMgmtMdaSPppHostsPeak indicates the
                     peak number of PPP hosts on this MDA."
    ::= { tmnxSubMgmtMdaStatsEntry 30 }

tmnxSubMgmtMdaSIpoeHosts OBJECT-TYPE
    SYNTAX          Counter32
    MAX-ACCESS      read-only
    STATUS          current
    DESCRIPTION     "The value of tmnxSubMgmtMdaSIpoeHosts indicates the 
                     number of current IPOE hosts on this MDA."
    ::= { tmnxSubMgmtMdaStatsEntry 31 }

tmnxSubMgmtMdaSIpoeHostsPeak OBJECT-TYPE
    SYNTAX          Counter32
    MAX-ACCESS      read-only
    STATUS          current
    DESCRIPTION     "The value of tmnxSubMgmtMdaSIpoeHostsPeak indicates the
                     peak number of IPOE hosts on this MDA."
    ::= { tmnxSubMgmtMdaStatsEntry 32 }

tmnxSubMgmtMdaSTotal OBJECT-TYPE
    SYNTAX          Counter32
    MAX-ACCESS      read-only
    STATUS          current
    DESCRIPTION     "The value of tmnxSubMgmtMdaSTotal indicates the number
                     of current total hosts on this MDA."
    ::= { tmnxSubMgmtMdaStatsEntry 33 }

tmnxSubMgmtMdaSTotalPeak OBJECT-TYPE
    SYNTAX          Counter32
    MAX-ACCESS      read-only
    STATUS          current
    DESCRIPTION     "The value of tmnxSubMgmtMdaSTotalPeak indicates the peak
                     number of total hosts on this MDA."
    ::= { tmnxSubMgmtMdaStatsEntry 34 }

tmnxSubMgmtMdaSPppLclOE OBJECT-TYPE
    SYNTAX          Counter32
    MAX-ACCESS      read-only
    STATUS          current
    DESCRIPTION     "The value of tmnxSubMgmtMdaSPppLclOE indicates the
                     number of current locally terminated PPP sessions (PPPoE)
                     on this MDA."
    ::= { tmnxSubMgmtMdaStatsEntry 35 }

tmnxSubMgmtMdaSPppLclOEPeak OBJECT-TYPE
    SYNTAX          Counter32
    MAX-ACCESS      read-only
    STATUS          current
    DESCRIPTION     "The value of tmnxSubMgmtMdaSPppLclOEPeak indicates the 
                     peak number of locally terminated PPP sessions (PPPoE) 
                     on this MDA."
    ::= { tmnxSubMgmtMdaStatsEntry 36 }

tmnxSubMgmtMdaSPppLclOEOA OBJECT-TYPE
    SYNTAX          Counter32
    MAX-ACCESS      read-only
    STATUS          current
    DESCRIPTION     "The value of tmnxSubMgmtMdaSPppLclOEOA indicates the 
                     number of current locally terminated PPP sessions (PPPoEoA)
                     on this MDA."
    ::= { tmnxSubMgmtMdaStatsEntry 37 }

tmnxSubMgmtMdaSPppLclOEOAPeak OBJECT-TYPE
    SYNTAX          Counter32
    MAX-ACCESS      read-only
    STATUS          current
    DESCRIPTION     "The value of tmnxSubMgmtMdaSPppLclOEOAPeak indicates the 
                     peak number of locally terminated PPP sessions (PPPoEoA) 
                     on this MDA."
    ::= { tmnxSubMgmtMdaStatsEntry 38 }

tmnxSubMgmtMdaSPppLclOA OBJECT-TYPE
    SYNTAX          Counter32
    MAX-ACCESS      read-only
    STATUS          current
    DESCRIPTION     "The value of tmnxSubMgmtMdaSPppLclOA indicates the number
                     of current locally terminated PPP sessions (PPPoA)
                     on this MDA."
    ::= { tmnxSubMgmtMdaStatsEntry 39 }

tmnxSubMgmtMdaSPppLclOAPeak OBJECT-TYPE
    SYNTAX          Counter32
    MAX-ACCESS      read-only
    STATUS          current
    DESCRIPTION     "The value of tmnxSubMgmtMdaSPppLclOAPeak indicates the 
                     peak number of locally terminated PPP sessions (PPPoA) 
                     on this MDA."
    ::= { tmnxSubMgmtMdaStatsEntry 40 }

tmnxSubMgmtMdaSPppLclL2tp OBJECT-TYPE
    SYNTAX          Counter32
    MAX-ACCESS      read-only
    STATUS          current
    DESCRIPTION     "The value of tmnxSubMgmtMdaSPppLclL2tp indicates the 
                     number of current locally terminated PPP sessions (L2TP LNS)
                     on this MDA."
    ::= { tmnxSubMgmtMdaStatsEntry 41 }
    
tmnxSubMgmtMdaSPppLclL2tpPeak OBJECT-TYPE
    SYNTAX          Counter32
    MAX-ACCESS      read-only
    STATUS          current
    DESCRIPTION     "The value of tmnxSubMgmtMdaSPppLclL2tpPeak indicates the 
                     peak number of locally terminated PPP sessions (L2TP LNS)
                     on this MDA."
    ::= { tmnxSubMgmtMdaStatsEntry 42 }

tmnxSubMgmtMdaSPppLclTotal OBJECT-TYPE
    SYNTAX          Counter32
    MAX-ACCESS      read-only
    STATUS          current
    DESCRIPTION     "The value of tmnxSubMgmtMdaSPppLclTotal indicates the 
                     total number of current locally terminated PPP sessions
                     on this MDA."
    ::= { tmnxSubMgmtMdaStatsEntry 43 }

tmnxSubMgmtMdaSPppLclTotalPeak OBJECT-TYPE
    SYNTAX          Counter32
    MAX-ACCESS      read-only
    STATUS          current
    DESCRIPTION     "The value of tmnxSubMgmtMdaSPppLclTotalPeak indicates the 
                     total peak number of locally terminated PPP sessions
                     on this MDA."
    ::= { tmnxSubMgmtMdaStatsEntry 44 }

tmnxSubMgmtMdaSPppLacOE OBJECT-TYPE
    SYNTAX          Counter32
    MAX-ACCESS      read-only
    STATUS          current
    DESCRIPTION     "The value of tmnxSubMgmtMdaSPppLacOE indicates the
                     number of current PPP sessions (PPPoE) tunneled over L2TP 
                     on this MDA."
    ::= { tmnxSubMgmtMdaStatsEntry 45 }

tmnxSubMgmtMdaSPppLacOEPeak OBJECT-TYPE
    SYNTAX          Counter32
    MAX-ACCESS      read-only
    STATUS          current
    DESCRIPTION     "The value of tmnxSubMgmtMdaSPppLacOEPeak indicates the 
                     peak number of PPP sessions (PPPoE) tunneled over L2TP 
                     on this MDA."
    ::= { tmnxSubMgmtMdaStatsEntry 46 }

tmnxSubMgmtMdaSPppLacOEOA OBJECT-TYPE
    SYNTAX          Counter32
    MAX-ACCESS      read-only
    STATUS          current
    DESCRIPTION     "The value of tmnxSubMgmtMdaSPppLacOEOA indicates the 
                     number of current PPP sessions (PPPoEoA) tunneled over L2TP 
                     on this MDA."
    ::= { tmnxSubMgmtMdaStatsEntry 47 }

tmnxSubMgmtMdaSPppLacOEOAPeak OBJECT-TYPE
    SYNTAX          Counter32
    MAX-ACCESS      read-only
    STATUS          current
    DESCRIPTION     "The value of tmnxSubMgmtMdaSPppLacOEOAPeak indicates the 
                     peak number of PPP sessions (PPPoEoA) tunneled over L2TP 
                     on this MDA."
    ::= { tmnxSubMgmtMdaStatsEntry 48 }

tmnxSubMgmtMdaSPppLacOA OBJECT-TYPE
    SYNTAX          Counter32
    MAX-ACCESS      read-only
    STATUS          current
    DESCRIPTION     "The value of tmnxSubMgmtMdaSPppLacOA indicates the 
                     number of current PPP sessions (PPPoA) tunneled over L2TP 
                     on this MDA."
    ::= { tmnxSubMgmtMdaStatsEntry 49 }

tmnxSubMgmtMdaSPppLacOAPeak OBJECT-TYPE
    SYNTAX          Counter32
    MAX-ACCESS      read-only
    STATUS          current
    DESCRIPTION     "The value of tmnxSubMgmtMdaSPppLacOAPeak indicates the 
                     peak number of PPP sessions (PPPoA) tunneled over L2TP
                     on this MDA."
    ::= { tmnxSubMgmtMdaStatsEntry 50 }

tmnxSubMgmtMdaSPppLacL2tp OBJECT-TYPE
    SYNTAX          Counter32
    MAX-ACCESS      read-only
    STATUS          current
    DESCRIPTION     "The value of tmnxSubMgmtMdaSPppLacL2tp indicates the 
                     number of current PPP sessions (L2TP LTS) tunneled over L2TP
                     on this MDA."
    ::= { tmnxSubMgmtMdaStatsEntry 51 }

tmnxSubMgmtMdaSPppLacL2tpPeak OBJECT-TYPE
    SYNTAX          Counter32
    MAX-ACCESS      read-only
    STATUS          current
    DESCRIPTION     "The value of tmnxSubMgmtMdaSPppLacL2tpPeak indicates the 
                     peak number of PPP sessions (L2TP LTS) tunneled over L2TP 
                     on this MDA."
    ::= { tmnxSubMgmtMdaStatsEntry 52 }

tmnxSubMgmtMdaSPppLacTotal OBJECT-TYPE
    SYNTAX          Counter32
    MAX-ACCESS      read-only
    STATUS          current
    DESCRIPTION     "The value of tmnxSubMgmtMdaSPppLacTotal indicates the 
                     total number of current PPP sessions tunneled over L2TP
                     on this MDA."
    ::= { tmnxSubMgmtMdaStatsEntry 53 }

tmnxSubMgmtMdaSPppLacTotalPeak OBJECT-TYPE
    SYNTAX          Counter32
    MAX-ACCESS      read-only
    STATUS          current
    DESCRIPTION     "The value of tmnxSubMgmtMdaSPppLacTotalPeak indicates the 
                     total peak number of PPP sessions tunneled over L2TP 
                     on this MDA."
    ::= { tmnxSubMgmtMdaStatsEntry 54 }

tmnxSubMgmtMdaSPppSessIs OBJECT-TYPE
    SYNTAX          Counter32
    MAX-ACCESS      read-only
    STATUS          current
    DESCRIPTION     "The value of tmnxSubMgmtMdaSPppSessIs indicates the 
                     number of current PPP sessions in setup on this MDA."
    ::= { tmnxSubMgmtMdaStatsEntry 55 }

tmnxSubMgmtMdaSPppSessIsPeak OBJECT-TYPE
    SYNTAX          Counter32
    MAX-ACCESS      read-only
    STATUS          current
    DESCRIPTION     "The value of tmnxSubMgmtMdaSPppSessIsPeak indicates the 
                     peak number of PPP sessions in setup on this MDA."
    ::= { tmnxSubMgmtMdaStatsEntry 56 }

tmnxSubMgmtMdaSPppSessTotal OBJECT-TYPE
    SYNTAX          Counter32
    MAX-ACCESS      read-only
    STATUS          current
    DESCRIPTION     "The value of tmnxSubMgmtMdaSPppSessTotal indicates the 
                     total number of current PPP sessions established on this MDA."
    ::= { tmnxSubMgmtMdaStatsEntry 57 }

tmnxSubMgmtMdaSPppSessTotalPeak OBJECT-TYPE
    SYNTAX          Counter32
    MAX-ACCESS      read-only
    STATUS          current
    DESCRIPTION     "The value of tmnxSubMgmtMdaSPppSessTotalPeak indicates the 
                     total peak number of PPP sessions established on this MDA."
    ::= { tmnxSubMgmtMdaStatsEntry 58 }

tmnxSubMgmtMdaSSubscribers OBJECT-TYPE
    SYNTAX          Counter32
    MAX-ACCESS      read-only
    STATUS          current
    DESCRIPTION     "The value of tmnxSubMgmtMdaSSubscribers indicates the number
                     of current subscribers on this MDA."
    ::= { tmnxSubMgmtMdaStatsEntry 59 }

tmnxSubMgmtMdaSSubscribersPeak OBJECT-TYPE
    SYNTAX          Counter32
    MAX-ACCESS      read-only
    STATUS          current
    DESCRIPTION     "The value of tmnxSubMgmtMdaSSubscribersPeak indicates the peak
                     number of subscribers on this MDA."
    ::= { tmnxSubMgmtMdaStatsEntry 60 }

tmnxSubMgmtMdaSDhcpBsmAs OBJECT-TYPE
    SYNTAX          Counter32
    MAX-ACCESS      read-only
    STATUS          current
    DESCRIPTION     "The value of tmnxSubMgmtMdaSDhcpBsmAs indicates the number
                     of current IPOE BSM hosts with antispoof (DHCP) on this MDA."
    ::= { tmnxSubMgmtMdaStatsEntry 61 }

tmnxSubMgmtMdaSDhcpBsmAsPeak OBJECT-TYPE
    SYNTAX          Counter32
    MAX-ACCESS      read-only
    STATUS          current
    DESCRIPTION     "The value of tmnxSubMgmtMdaSDhcpBsmAsPeak indicates the peak
                     number of IPOE BSM hosts with antispoof (DHCP) on this MDA."
    ::= { tmnxSubMgmtMdaStatsEntry 62 }

tmnxSubMgmtMdaSStaticBsmAs OBJECT-TYPE
    SYNTAX          Counter32
    MAX-ACCESS      read-only
    STATUS          current
    DESCRIPTION     "The value of tmnxSubMgmtMdaSStaticBsmAs indicates the number
                     of current IPOE BSM static hosts with antispoof on this MDA."
    ::= { tmnxSubMgmtMdaStatsEntry 63 }

tmnxSubMgmtMdaSStaticBsmAsPeak OBJECT-TYPE
    SYNTAX          Counter32
    MAX-ACCESS      read-only
    STATUS          current
    DESCRIPTION     "The value of tmnxSubMgmtMdaSStaticBsmAsPeak indicates the peak
                     number of IPOE BSM static hosts with antispoof on this MDA."
    ::= { tmnxSubMgmtMdaStatsEntry 64 }

tmnxSubMgmtMdaSDhcpBsm OBJECT-TYPE
    SYNTAX          Counter32
    MAX-ACCESS      read-only
    STATUS          current
    DESCRIPTION     "The value of tmnxSubMgmtMdaSDhcpBsm indicates the number
                     of current IPOE BSM hosts (DHCP) on this MDA."
    ::= { tmnxSubMgmtMdaStatsEntry 65 }

tmnxSubMgmtMdaSDhcpBsmPeak OBJECT-TYPE
    SYNTAX          Counter32
    MAX-ACCESS      read-only
    STATUS          current
    DESCRIPTION     "The value of tmnxSubMgmtMdaSDhcpBsmPeak indicates the peak
                     number of IPOE BSM hosts (DHCP) on this MDA."
    ::= { tmnxSubMgmtMdaStatsEntry 66 }

tmnxSubMgmtMdaSStaticBsm OBJECT-TYPE
    SYNTAX          Counter32
    MAX-ACCESS      read-only
    STATUS          current
    DESCRIPTION     "The value of tmnxSubMgmtMdaSStaticBsm indicates the number
                     of current IPOE BSM static hosts on this MDA."
    ::= { tmnxSubMgmtMdaStatsEntry 67 }

tmnxSubMgmtMdaSStaticBsmPeak OBJECT-TYPE
    SYNTAX          Counter32
    MAX-ACCESS      read-only
    STATUS          current
    DESCRIPTION     "The value of tmnxSubMgmtMdaSStaticBsmPeak indicates the peak
                     number of IPOE BSM static hosts on this MDA."
    ::= { tmnxSubMgmtMdaStatsEntry 68 }

tmnxSubMgmtMdaSPppDhcp6Mr OBJECT-TYPE
    SYNTAX          Counter32
    MAX-ACCESS      read-only
    STATUS          current
    DESCRIPTION     "The value of tmnxSubMgmtMdaSPppDhcp6Mr indicates the number
                     of current PPP PD Managed Routes on this MDA."
    ::= { tmnxSubMgmtMdaStatsEntry 69 }

tmnxSubMgmtMdaSPppDhcp6MrPeak OBJECT-TYPE
    SYNTAX          Counter32
    MAX-ACCESS      read-only
    STATUS          current
    DESCRIPTION     "The value of tmnxSubMgmtMdaSPppDhcp6MrPeak indicates the peak
                     number of PPP PD Managed Routes on this MDA."
    ::= { tmnxSubMgmtMdaStatsEntry 70 }

tmnxSubMgmtMdaSIpoeDhcp6Mr OBJECT-TYPE
    SYNTAX          Counter32
    MAX-ACCESS      read-only
    STATUS          current
    DESCRIPTION     "The value of tmnxSubMgmtMdaSIpoeDhcp6Mr indicates the number
                     of current IPOE PD Managed Routes on this MDA."
    ::= { tmnxSubMgmtMdaStatsEntry 71 }

tmnxSubMgmtMdaSIpoeDhcp6MrPeak OBJECT-TYPE
    SYNTAX          Counter32
    MAX-ACCESS      read-only
    STATUS          current
    DESCRIPTION     "The value of tmnxSubMgmtMdaSIpoeDhcp6MrPeak indicates the peak
                     number of IPOE PD Managed Routes on this MDA."
    ::= { tmnxSubMgmtMdaStatsEntry 72 }

tmnxSubMgmtMdaSV6StaticWan OBJECT-TYPE
    SYNTAX          Counter32
    MAX-ACCESS      read-only
    STATUS          current
    DESCRIPTION     "The value of tmnxSubMgmtMdaSV6StaticWan indicates the number
                     of current IPOE IPv6 static WAN hosts on this MDA."
    ::= { tmnxSubMgmtMdaStatsEntry 73 }

tmnxSubMgmtMdaSV6StaticWanPeak OBJECT-TYPE
    SYNTAX          Counter32
    MAX-ACCESS      read-only
    STATUS          current
    DESCRIPTION     "The value of tmnxSubMgmtMdaSV6StaticWanPeak indicates the peak
                     number of IPOE IPv6 static WAN hosts on this MDA."
    ::= { tmnxSubMgmtMdaStatsEntry 74 }

tmnxSubMgmtMdaSBsmDhcp6Pd OBJECT-TYPE
    SYNTAX          Counter32
    MAX-ACCESS      read-only
    STATUS          current
    DESCRIPTION     "The value of tmnxSubMgmtMdaSBsmDhcp6Pd indicates the number
                     of current IPOE BSM hosts (DHCP6 PD) on this MDA."
    ::= { tmnxSubMgmtMdaStatsEntry 75 }

tmnxSubMgmtMdaSBsmDhcp6PdPeak OBJECT-TYPE
    SYNTAX          Counter32
    MAX-ACCESS      read-only
    STATUS          current
    DESCRIPTION     "The value of tmnxSubMgmtMdaSBsmDhcp6PdPeak indicates the 
                     peak number of IPOE BSM hosts (DHCP6 PD) on this MDA."
    ::= { tmnxSubMgmtMdaStatsEntry 76 }

tmnxSubMgmtMdaSBsmDhcp6Na OBJECT-TYPE
    SYNTAX          Counter32
    MAX-ACCESS      read-only
    STATUS          current
    DESCRIPTION     "The value of tmnxSubMgmtMdaSBsmDhcp6Na indicates the number
                     of current IPOE BSM hosts (DHCP6 NA) on this MDA."
    ::= { tmnxSubMgmtMdaStatsEntry 77 }

tmnxSubMgmtMdaSBsmDhcp6NaPeak OBJECT-TYPE
    SYNTAX          Counter32
    MAX-ACCESS      read-only
    STATUS          current
    DESCRIPTION     "The value of tmnxSubMgmtMdaSBsmDhcp6NaPeak indicates the 
                     peak number of IPOE BSM hosts (DHCP6 NA) on this MDA."
    ::= { tmnxSubMgmtMdaStatsEntry 78 }

tmnxSubMgmtMdaSTotInternal OBJECT-TYPE
    SYNTAX          Counter32
    MAX-ACCESS      read-only
    STATUS          current
    DESCRIPTION     "The value of tmnxSubMgmtMdaSTotInternal indicates the number
                     of current internal hosts on this MDA."
    ::= { tmnxSubMgmtMdaStatsEntry 79 }

tmnxSubMgmtMdaSTotInternalPeak OBJECT-TYPE
    SYNTAX          Counter32
    MAX-ACCESS      read-only
    STATUS          current
    DESCRIPTION     "The value of tmnxSubMgmtMdaSTotInternalPeak indicates the 
                     peak number of internal hosts on this MDA."
    ::= { tmnxSubMgmtMdaStatsEntry 80 } 

tmnxSubMgmtMdaSTotDhcp OBJECT-TYPE
    SYNTAX          Counter32
    MAX-ACCESS      read-only
    STATUS          current
    DESCRIPTION     "The value of tmnxSubMgmtMdaSTotDhcp indicates the number
                     of current DHCP hosts on this MDA."
    ::= { tmnxSubMgmtMdaStatsEntry 81 }

tmnxSubMgmtMdaSTotDhcpPeak OBJECT-TYPE
    SYNTAX          Counter32
    MAX-ACCESS      read-only
    STATUS          current
    DESCRIPTION     "The value of tmnxSubMgmtMdaSTotDhcpPeak indicates the 
                     peak number of DHCP hosts on this MDA."
    ::= { tmnxSubMgmtMdaStatsEntry 82 }

tmnxSubMgmtMdaSTotDhcpV6 OBJECT-TYPE
    SYNTAX          Counter32
    MAX-ACCESS      read-only
    STATUS          current
    DESCRIPTION     "The value of tmnxSubMgmtMdaSTotDhcpV6 indicates the number
                     of current DHCPv6 hosts on this MDA."
    ::= { tmnxSubMgmtMdaStatsEntry 83 }

tmnxSubMgmtMdaSTotDhcpV6Peak OBJECT-TYPE
    SYNTAX          Counter32
    MAX-ACCESS      read-only
    STATUS          current
    DESCRIPTION     "The value of tmnxSubMgmtMdaSTotDhcpV6Peak indicates the 
                     peak number of DHCPv6 hosts on this MDA."
    ::= { tmnxSubMgmtMdaStatsEntry 84 }

tmnxSubMgmtMdaSTotMngdRt OBJECT-TYPE
    SYNTAX          Counter32
    MAX-ACCESS      read-only
    STATUS          current
    DESCRIPTION     "The value of tmnxSubMgmtMdaSTotMngdRt indicates the number
                     of current PD Managed Routes on this MDA."
    ::= { tmnxSubMgmtMdaStatsEntry 85 }

tmnxSubMgmtMdaSTotMngdRtPeak OBJECT-TYPE
    SYNTAX          Counter32
    MAX-ACCESS      read-only
    STATUS          current
    DESCRIPTION     "The value of tmnxSubMgmtMdaSTotMngdRtPeak indicates the 
                     peak number of PD Managed Routes on this MDA."
    ::= { tmnxSubMgmtMdaStatsEntry 86 }

tmnxSubMgmtMdaSIpoeSesIs OBJECT-TYPE
    SYNTAX          Counter32
    MAX-ACCESS      read-only
    STATUS          current
    DESCRIPTION     "The value of tmnxSubMgmtMdaSIpoeSesIs indicates the number
                     of current IPOE sessions in setup on this MDA."
    ::= { tmnxSubMgmtMdaStatsEntry 87 }

tmnxSubMgmtMdaSIpoeSesIsPeak OBJECT-TYPE
    SYNTAX          Counter32
    MAX-ACCESS      read-only
    STATUS          current
    DESCRIPTION     "The value of tmnxSubMgmtMdaSIpoeSesIsPeak indicates the 
                     peak number of IPOE sessions in setup on this MDA."
    ::= { tmnxSubMgmtMdaStatsEntry 88 }

tmnxSubMgmtMdaSIpoeSesTotal OBJECT-TYPE
    SYNTAX          Counter32
    MAX-ACCESS      read-only
    STATUS          current
    DESCRIPTION     "The value of tmnxSubMgmtMdaSIpoeSesTotal indicates the number
                     of current IPOE sessions on this MDA."
    ::= { tmnxSubMgmtMdaStatsEntry 89 }

tmnxSubMgmtMdaSIpoeSesTotalPeak OBJECT-TYPE
    SYNTAX          Counter32
    MAX-ACCESS      read-only
    STATUS          current
    DESCRIPTION     "The value of tmnxSubMgmtMdaSIpoeSesTotalPeak indicates the 
                     peak number of IPOE sessions on this MDA."
    ::= { tmnxSubMgmtMdaStatsEntry 90 }

tmnxSubMgmtMdaSV6StaticPd OBJECT-TYPE
    SYNTAX          Counter32
    MAX-ACCESS      read-only
    STATUS          current
    DESCRIPTION     "The value of tmnxSubMgmtMdaSV6StaticPd indicates the number
                     of current IPOE IPv6 static prefixes on this MDA."
    ::= { tmnxSubMgmtMdaStatsEntry 91 }

tmnxSubMgmtMdaSV6StaticPdPeak OBJECT-TYPE
    SYNTAX          Counter32
    MAX-ACCESS      read-only
    STATUS          current
    DESCRIPTION     "The value of tmnxSubMgmtMdaSV6StaticPdPeak indicates the peak
                     number of IPOE IPv6 static prefixes on this MDA."
    ::= { tmnxSubMgmtMdaStatsEntry 92 }

--
--  The Subscriber Mgmt per Slot Statistics Table
--

tmnxSubMgmtSlotStatsTable   OBJECT-TYPE
    SYNTAX      SEQUENCE OF TmnxSubMgmtSlotStatsEntry
    MAX-ACCESS  not-accessible
    STATUS      current
    DESCRIPTION
       "The tmnxSubMgmtSlotStatsTable has an entry with statistics for each
        Slot on which subscriber hosts are allocated."
    ::= { tmnxSubMgmtObjects 106 }

tmnxSubMgmtSlotStatsEntry   OBJECT-TYPE
    SYNTAX      TmnxSubMgmtSlotStatsEntry
    MAX-ACCESS  not-accessible
    STATUS      current
    DESCRIPTION
       "Each conceptual row represents statistics for a Slot on which subscriber
        hosts are allocated."
    INDEX       { tmnxChassisIndex,
                  tmnxSubMgmtSlotID }
    ::= { tmnxSubMgmtSlotStatsTable 1 }

TmnxSubMgmtSlotStatsEntry ::= SEQUENCE {
        tmnxSubMgmtSlotID                TmnxPortID,
        tmnxSubMgmtSlotSIpcp             Counter32,
        tmnxSubMgmtSlotSIpcpPeak         Counter32,
        tmnxSubMgmtSlotSL2tpHost         Counter32,
        tmnxSubMgmtSlotSL2tpHostPeak     Counter32,
        tmnxSubMgmtSlotSDhcp             Counter32,
        tmnxSubMgmtSlotSDhcpPeak         Counter32,
        tmnxSubMgmtSlotSArp              Counter32,
        tmnxSubMgmtSlotSArpPeak          Counter32,
        tmnxSubMgmtSlotSStatic           Counter32,
        tmnxSubMgmtSlotSStaticPeak       Counter32,
        tmnxSubMgmtSlotSNonSub           Counter32,
        tmnxSubMgmtSlotSNonSubPeak       Counter32,
        tmnxSubMgmtSlotSPppSlaac         Counter32,
        tmnxSubMgmtSlotSPppSlaacPeak     Counter32,
        tmnxSubMgmtSlotSPppDhcp6Pd       Counter32,
        tmnxSubMgmtSlotSPppDhcp6PdPeak   Counter32,
        tmnxSubMgmtSlotSPppDhcp6Na       Counter32,
        tmnxSubMgmtSlotSPppDhcp6NaPeak   Counter32,
        tmnxSubMgmtSlotSIpoeSlaac        Counter32,
        tmnxSubMgmtSlotSIpoeSlaacPeak    Counter32,
        tmnxSubMgmtSlotSIpoeDhcp6Pd      Counter32,
        tmnxSubMgmtSlotSIpoeDhcp6PdPeak  Counter32,
        tmnxSubMgmtSlotSIpoeDhcp6Na      Counter32,
        tmnxSubMgmtSlotSIpoeDhcp6NaPeak  Counter32,
        tmnxSubMgmtSlotSV4               Counter32,
        tmnxSubMgmtSlotSV4Peak           Counter32,
        tmnxSubMgmtSlotSV6               Counter32,
        tmnxSubMgmtSlotSV6Peak           Counter32,
        tmnxSubMgmtSlotSPppHosts         Counter32,
        tmnxSubMgmtSlotSPppHostsPeak     Counter32,
        tmnxSubMgmtSlotSIpoeHosts        Counter32,
        tmnxSubMgmtSlotSIpoeHostsPeak    Counter32,
        tmnxSubMgmtSlotSTotal            Counter32,
        tmnxSubMgmtSlotSTotalPeak        Counter32,
        tmnxSubMgmtSlotSPppLclOE         Counter32,
        tmnxSubMgmtSlotSPppLclOEPeak     Counter32,
        tmnxSubMgmtSlotSPppLclOEOA       Counter32,
        tmnxSubMgmtSlotSPppLclOEOAPeak   Counter32,
        tmnxSubMgmtSlotSPppLclOA         Counter32,
        tmnxSubMgmtSlotSPppLclOAPeak     Counter32,
        tmnxSubMgmtSlotSPppLclL2tp       Counter32,
        tmnxSubMgmtSlotSPppLclL2tpPeak   Counter32,
        tmnxSubMgmtSlotSPppLclTotal      Counter32,
        tmnxSubMgmtSlotSPppLclTotalPeak  Counter32,
        tmnxSubMgmtSlotSPppLacOE         Counter32,
        tmnxSubMgmtSlotSPppLacOEPeak     Counter32,
        tmnxSubMgmtSlotSPppLacOEOA       Counter32,
        tmnxSubMgmtSlotSPppLacOEOAPeak   Counter32,
        tmnxSubMgmtSlotSPppLacOA         Counter32,
        tmnxSubMgmtSlotSPppLacOAPeak     Counter32,
        tmnxSubMgmtSlotSPppLacL2tp       Counter32,
        tmnxSubMgmtSlotSPppLacL2tpPeak   Counter32,
        tmnxSubMgmtSlotSPppLacTotal      Counter32,
        tmnxSubMgmtSlotSPppLacTotalPeak  Counter32,
        tmnxSubMgmtSlotSPppSessIs        Counter32,
        tmnxSubMgmtSlotSPppSessIsPeak    Counter32,
        tmnxSubMgmtSlotSPppSessTotal     Counter32,
        tmnxSubMgmtSlotSPppSessTotalPeak Counter32,
        tmnxSubMgmtSlotSSubscribers      Counter32,
        tmnxSubMgmtSlotSSubscribersPeak  Counter32,
        tmnxSubMgmtSlotSDhcpBsmAs        Counter32,
        tmnxSubMgmtSlotSDhcpBsmAsPeak    Counter32,
        tmnxSubMgmtSlotSStaticBsmAs      Counter32,
        tmnxSubMgmtSlotSStaticBsmAsPeak  Counter32,
        tmnxSubMgmtSlotSDhcpBsm          Counter32,
        tmnxSubMgmtSlotSDhcpBsmPeak      Counter32,
        tmnxSubMgmtSlotSStaticBsm        Counter32,
        tmnxSubMgmtSlotSStaticBsmPeak    Counter32,
        tmnxSubMgmtSlotSPppDhcp6Mr       Counter32,
        tmnxSubMgmtSlotSPppDhcp6MrPeak   Counter32,
        tmnxSubMgmtSlotSIpoeDhcp6Mr      Counter32,
        tmnxSubMgmtSlotSIpoeDhcp6MrPeak  Counter32,
        tmnxSubMgmtSlotSV6StaticWan      Counter32,
        tmnxSubMgmtSlotSV6StaticWanPeak  Counter32,
        tmnxSubMgmtSlotSBsmDhcp6Pd       Counter32,
        tmnxSubMgmtSlotSBsmDhcp6PdPeak   Counter32,
        tmnxSubMgmtSlotSBsmDhcp6Na       Counter32,
        tmnxSubMgmtSlotSBsmDhcp6NaPeak   Counter32,
        tmnxSubMgmtSlotSTotInternal      Counter32,
        tmnxSubMgmtSlotSTotInternalPeak  Counter32,
        tmnxSubMgmtSlotSTotDhcp          Counter32,
        tmnxSubMgmtSlotSTotDhcpPeak      Counter32,
        tmnxSubMgmtSlotSTotDhcpV6        Counter32,
        tmnxSubMgmtSlotSTotDhcpV6Peak    Counter32,
        tmnxSubMgmtSlotSTotMngdRt        Counter32,
        tmnxSubMgmtSlotSTotMngdRtPeak    Counter32,
        tmnxSubMgmtSlotSIpoeSesIs        Counter32,
        tmnxSubMgmtSlotSIpoeSesIsPeak    Counter32,
        tmnxSubMgmtSlotSIpoeSesTotal     Counter32,
        tmnxSubMgmtSlotSIpoeSesTotalPeak Counter32,
        tmnxSubMgmtSlotSV6StaticPd       Counter32,
        tmnxSubMgmtSlotSV6StaticPdPeak   Counter32
    }

tmnxSubMgmtSlotID OBJECT-TYPE
    SYNTAX          TmnxPortID
    MAX-ACCESS      not-accessible
    STATUS          current
    DESCRIPTION
        "tmnxSubMgmtSlotID is an index into this table. It maps this Slot to 
         its entry in the mib-2 interfaces table."
    ::= { tmnxSubMgmtSlotStatsEntry 1 }

tmnxSubMgmtSlotSIpcp OBJECT-TYPE
    SYNTAX          Counter32
    MAX-ACCESS      read-only
    STATUS          current
    DESCRIPTION     "The value of tmnxSubMgmtSlotSIpcp indicates the number
                     of current PPP hosts (IPCP) on this Slot."
    ::= { tmnxSubMgmtSlotStatsEntry 2 }

tmnxSubMgmtSlotSIpcpPeak OBJECT-TYPE
    SYNTAX          Counter32
    MAX-ACCESS      read-only
    STATUS          current
    DESCRIPTION     "The value of tmnxSubMgmtSlotSIpcpPeak indicates the peak
                     number of PPP hosts (IPCP) on this Slot."
    ::= { tmnxSubMgmtSlotStatsEntry 3 }

tmnxSubMgmtSlotSL2tpHost OBJECT-TYPE
    SYNTAX          Counter32
    MAX-ACCESS      read-only
    STATUS          current
    DESCRIPTION     "The value of tmnxSubMgmtSlotSL2tpHost indicates the number
                     of current L2TP hosts (LAC) on this Slot."
    ::= { tmnxSubMgmtSlotStatsEntry 4 }

tmnxSubMgmtSlotSL2tpHostPeak OBJECT-TYPE
    SYNTAX          Counter32
    MAX-ACCESS      read-only
    STATUS          current
    DESCRIPTION     "The value of tmnxSubMgmtSlotSL2tpHostPeak indicates the peak
                     number of L2TP hosts (LAC) on this Slot."
    ::= { tmnxSubMgmtSlotStatsEntry 5 }

tmnxSubMgmtSlotSDhcp OBJECT-TYPE
    SYNTAX          Counter32
    MAX-ACCESS      read-only
    STATUS          current
    DESCRIPTION     "The value of tmnxSubMgmtSlotSDhcp indicates the number
                     of current IPOE hosts (DHCP) on this Slot."
    ::= { tmnxSubMgmtSlotStatsEntry 6 }

tmnxSubMgmtSlotSDhcpPeak OBJECT-TYPE
    SYNTAX          Counter32
    MAX-ACCESS      read-only
    STATUS          current
    DESCRIPTION     "The value of tmnxSubMgmtSlotSDhcpPeak indicates the peak
                     number of IPOE hosts (DHCP) on this Slot."
    ::= { tmnxSubMgmtSlotStatsEntry 7 }

tmnxSubMgmtSlotSArp OBJECT-TYPE
    SYNTAX          Counter32
    MAX-ACCESS      read-only
    STATUS          current
    DESCRIPTION     "The value of tmnxSubMgmtSlotSArp indicates the number
                     of current IPOE hosts (ARP) on this Slot."
    ::= { tmnxSubMgmtSlotStatsEntry 8 }

tmnxSubMgmtSlotSArpPeak OBJECT-TYPE
    SYNTAX          Counter32
    MAX-ACCESS      read-only
    STATUS          current
    DESCRIPTION     "The value of tmnxSubMgmtSlotSArpPeak indicates the peak
                     number of IPOE hosts (ARP) on this Slot."
    ::= { tmnxSubMgmtSlotStatsEntry 9 }

tmnxSubMgmtSlotSStatic OBJECT-TYPE
    SYNTAX          Counter32
    MAX-ACCESS      read-only
    STATUS          current
    DESCRIPTION     "The value of tmnxSubMgmtSlotSStatic indicates the number
                     of current IPOE hosts (Static) on this Slot."
    ::= { tmnxSubMgmtSlotStatsEntry 10 }

tmnxSubMgmtSlotSStaticPeak OBJECT-TYPE
    SYNTAX          Counter32
    MAX-ACCESS      read-only
    STATUS          current
    DESCRIPTION     "The value of tmnxSubMgmtSlotSStaticPeak indicates the peak
                     number of IPOE hosts (Static) on this Slot."
    ::= { tmnxSubMgmtSlotStatsEntry 11 }

tmnxSubMgmtSlotSNonSub OBJECT-TYPE
    SYNTAX          Counter32
    MAX-ACCESS      read-only
    STATUS          current
    DESCRIPTION     "The value of tmnxSubMgmtSlotSNonSub indicates the number
                     of current Non Sub hosts on this Slot."
    ::= { tmnxSubMgmtSlotStatsEntry 12 }

tmnxSubMgmtSlotSNonSubPeak OBJECT-TYPE
    SYNTAX          Counter32
    MAX-ACCESS      read-only
    STATUS          current
    DESCRIPTION     "The value of tmnxSubMgmtSlotSNonSubPeak indicates the peak
                     number of Non Sub hosts on this Slot."
    ::= { tmnxSubMgmtSlotStatsEntry 13 }

tmnxSubMgmtSlotSPppSlaac OBJECT-TYPE
    SYNTAX          Counter32
    MAX-ACCESS      read-only
    STATUS          current
    DESCRIPTION     "The value of tmnxSubMgmtSlotSPppSlaac indicates the number
                     of current PPP hosts (SLAAC) on this Slot."
    ::= { tmnxSubMgmtSlotStatsEntry 14 }

tmnxSubMgmtSlotSPppSlaacPeak OBJECT-TYPE
    SYNTAX          Counter32
    MAX-ACCESS      read-only
    STATUS          current
    DESCRIPTION     "The value of tmnxSubMgmtSlotSPppSlaacPeak indicates the 
                     peak number of PPP hosts (SLAAC) on this Slot."
    ::= { tmnxSubMgmtSlotStatsEntry 15 }

tmnxSubMgmtSlotSPppDhcp6Pd OBJECT-TYPE
    SYNTAX          Counter32
    MAX-ACCESS      read-only
    STATUS          current
    DESCRIPTION     "The value of tmnxSubMgmtSlotSPppDhcp6Pd indicates the number
                     of current PPP hosts (DHCP6 PD) on this Slot."
    ::= { tmnxSubMgmtSlotStatsEntry 16 }

tmnxSubMgmtSlotSPppDhcp6PdPeak OBJECT-TYPE
    SYNTAX          Counter32
    MAX-ACCESS      read-only
    STATUS          current
    DESCRIPTION     "The value of tmnxSubMgmtSlotSPppDhcp6PdPeak indicates the 
                     peak number of PPP hosts (DHCP6 PD) on this Slot."
    ::= { tmnxSubMgmtSlotStatsEntry 17 }

tmnxSubMgmtSlotSPppDhcp6Na OBJECT-TYPE
    SYNTAX          Counter32
    MAX-ACCESS      read-only
    STATUS          current
    DESCRIPTION     "The value of tmnxSubMgmtSlotSPppDhcp6Na indicates the number
                     of current PPP hosts (DHCP6 NA) on this Slot."
    ::= { tmnxSubMgmtSlotStatsEntry 18 }

tmnxSubMgmtSlotSPppDhcp6NaPeak OBJECT-TYPE
    SYNTAX          Counter32
    MAX-ACCESS      read-only
    STATUS          current
    DESCRIPTION     "The value of tmnxSubMgmtSlotSPppDhcp6NaPeak indicates the 
                     peak number of PPP hosts (DHCP6 NA) on this Slot."
    ::= { tmnxSubMgmtSlotStatsEntry 19 }

tmnxSubMgmtSlotSIpoeSlaac OBJECT-TYPE
    SYNTAX          Counter32
    MAX-ACCESS      read-only
    STATUS          current
    DESCRIPTION     "The value of tmnxSubMgmtSlotSIpoeSlaac indicates the 
                     number of current IPOE hosts (SLAAC) on this Slot."
    ::= { tmnxSubMgmtSlotStatsEntry 20 }

tmnxSubMgmtSlotSIpoeSlaacPeak OBJECT-TYPE
    SYNTAX          Counter32
    MAX-ACCESS      read-only
    STATUS          current
    DESCRIPTION     "The value of tmnxSubMgmtSlotSIpoeSlaacPeak indicates the 
                     peak number of IPOE hosts (SLAAC) on this Slot."
    ::= { tmnxSubMgmtSlotStatsEntry 21 }

tmnxSubMgmtSlotSIpoeDhcp6Pd OBJECT-TYPE
    SYNTAX          Counter32
    MAX-ACCESS      read-only
    STATUS          current
    DESCRIPTION     "The value of tmnxSubMgmtSlotSIpoeDhcp6Pd indicates the 
                     number of current IPOE hosts (DHCP6 PD) on this Slot."
    ::= { tmnxSubMgmtSlotStatsEntry 22 }

tmnxSubMgmtSlotSIpoeDhcp6PdPeak OBJECT-TYPE
    SYNTAX          Counter32
    MAX-ACCESS      read-only
    STATUS          current
    DESCRIPTION     "The value of tmnxSubMgmtSlotSIpoeDhcp6PdPeak indicates the 
                     peak number of IPOE hosts (DHCP6 PD) on this Slot."
    ::= { tmnxSubMgmtSlotStatsEntry 23 }

tmnxSubMgmtSlotSIpoeDhcp6Na OBJECT-TYPE
    SYNTAX          Counter32
    MAX-ACCESS      read-only
    STATUS          current
    DESCRIPTION     "The value of tmnxSubMgmtSlotSIpoeDhcp6Na indicates the 
                     number of current IPOE hosts (DHCP6 NA) on this Slot."
    ::= { tmnxSubMgmtSlotStatsEntry 24 }

tmnxSubMgmtSlotSIpoeDhcp6NaPeak OBJECT-TYPE
    SYNTAX          Counter32
    MAX-ACCESS      read-only
    STATUS          current
    DESCRIPTION     "The value of tmnxSubMgmtSlotSIpoeDhcp6NaPeak indicates the 
                     peak number of IPOE hosts (DHCP6 NA) on this Slot."
    ::= { tmnxSubMgmtSlotStatsEntry 25 }

tmnxSubMgmtSlotSV4 OBJECT-TYPE
    SYNTAX          Counter32
    MAX-ACCESS      read-only
    STATUS          current
    DESCRIPTION     "The value of tmnxSubMgmtSlotSV4 indicates the number
                     of current V4 hosts on this Slot."
    ::= { tmnxSubMgmtSlotStatsEntry 26 }

tmnxSubMgmtSlotSV4Peak OBJECT-TYPE
    SYNTAX          Counter32
    MAX-ACCESS      read-only
    STATUS          current
    DESCRIPTION     "The value of tmnxSubMgmtSlotSV4Peak indicates the peak
                     number of V4 hosts on this Slot."
    ::= { tmnxSubMgmtSlotStatsEntry 27 }

tmnxSubMgmtSlotSV6 OBJECT-TYPE
    SYNTAX          Counter32
    MAX-ACCESS      read-only
    STATUS          current
    DESCRIPTION     "The value of tmnxSubMgmtSlotSV6 indicates the number
                     of current V6 hosts on this Slot."
    ::= { tmnxSubMgmtSlotStatsEntry 28 }

tmnxSubMgmtSlotSV6Peak OBJECT-TYPE
    SYNTAX          Counter32
    MAX-ACCESS      read-only
    STATUS          current
    DESCRIPTION     "The value of tmnxSubMgmtSlotSV6Peak indicates the peak
                     number of V6 hosts on this Slot."
    ::= { tmnxSubMgmtSlotStatsEntry 29 }

tmnxSubMgmtSlotSPppHosts OBJECT-TYPE
    SYNTAX          Counter32
    MAX-ACCESS      read-only
    STATUS          current
    DESCRIPTION     "The value of tmnxSubMgmtSlotSPppHosts indicates the 
                     number of current PPP hosts on this Slot."
    ::= { tmnxSubMgmtSlotStatsEntry 30 }

tmnxSubMgmtSlotSPppHostsPeak OBJECT-TYPE
    SYNTAX          Counter32
    MAX-ACCESS      read-only
    STATUS          current
    DESCRIPTION     "The value of tmnxSubMgmtSlotSPppHostsPeak indicates the
                     peak number of PPP hosts on this Slot."
    ::= { tmnxSubMgmtSlotStatsEntry 31 }

tmnxSubMgmtSlotSIpoeHosts OBJECT-TYPE
    SYNTAX          Counter32
    MAX-ACCESS      read-only
    STATUS          current
    DESCRIPTION     "The value of tmnxSubMgmtSlotSIpoeHosts indicates the 
                     number of current IPOE hosts on this Slot."
    ::= { tmnxSubMgmtSlotStatsEntry 32 }

tmnxSubMgmtSlotSIpoeHostsPeak OBJECT-TYPE
    SYNTAX          Counter32
    MAX-ACCESS      read-only
    STATUS          current
    DESCRIPTION     "The value of tmnxSubMgmtSlotSIpoeHostsPeak indicates the
                     peak number of IPOE hosts on this Slot."
    ::= { tmnxSubMgmtSlotStatsEntry 33 }

tmnxSubMgmtSlotSTotal OBJECT-TYPE
    SYNTAX          Counter32
    MAX-ACCESS      read-only
    STATUS          current
    DESCRIPTION     "The value of tmnxSubMgmtSlotSTotal indicates the number
                     of current total hosts on this Slot."
    ::= { tmnxSubMgmtSlotStatsEntry 34 }

tmnxSubMgmtSlotSTotalPeak OBJECT-TYPE
    SYNTAX          Counter32
    MAX-ACCESS      read-only
    STATUS          current
    DESCRIPTION     "The value of tmnxSubMgmtSlotSTotalPeak indicates the peak
                     number of total hosts on this Slot."
    ::= { tmnxSubMgmtSlotStatsEntry 35 }

tmnxSubMgmtSlotSPppLclOE OBJECT-TYPE
    SYNTAX          Counter32
    MAX-ACCESS      read-only
    STATUS          current
    DESCRIPTION     "The value of tmnxSubMgmtSlotSPppLclOE indicates the
                     number of current locally terminated PPP sessions (PPPoE)
                     on this Slot."
    ::= { tmnxSubMgmtSlotStatsEntry 36 }

tmnxSubMgmtSlotSPppLclOEPeak OBJECT-TYPE
    SYNTAX          Counter32
    MAX-ACCESS      read-only
    STATUS          current
    DESCRIPTION     "The value of tmnxSubMgmtSlotSPppLclOEPeak indicates the 
                     peak number of locally terminated PPP sessions (PPPoE) 
                     on this Slot."
    ::= { tmnxSubMgmtSlotStatsEntry 37 }

tmnxSubMgmtSlotSPppLclOEOA OBJECT-TYPE
    SYNTAX          Counter32
    MAX-ACCESS      read-only
    STATUS          current
    DESCRIPTION     "The value of tmnxSubMgmtSlotSPppLclOEOA indicates the 
                     number of current locally terminated PPP sessions (PPPoEoA)
                     on this Slot."
    ::= { tmnxSubMgmtSlotStatsEntry 38 }

tmnxSubMgmtSlotSPppLclOEOAPeak OBJECT-TYPE
    SYNTAX          Counter32
    MAX-ACCESS      read-only
    STATUS          current
    DESCRIPTION     "The value of tmnxSubMgmtSlotSPppLclOEOAPeak indicates the 
                     peak number of locally terminated PPP sessions (PPPoEoA) 
                     on this Slot."
    ::= { tmnxSubMgmtSlotStatsEntry 39 }

tmnxSubMgmtSlotSPppLclOA OBJECT-TYPE
    SYNTAX          Counter32
    MAX-ACCESS      read-only
    STATUS          current
    DESCRIPTION     "The value of tmnxSubMgmtSlotSPppLclOA indicates the number
                     of current locally terminated PPP sessions (PPPoA)
                     on this Slot."
    ::= { tmnxSubMgmtSlotStatsEntry 40 }

tmnxSubMgmtSlotSPppLclOAPeak OBJECT-TYPE
    SYNTAX          Counter32
    MAX-ACCESS      read-only
    STATUS          current
    DESCRIPTION     "The value of tmnxSubMgmtSlotSPppLclOAPeak indicates the 
                     peak number of locally terminated PPP sessions (PPPoA) 
                     on this Slot."
    ::= { tmnxSubMgmtSlotStatsEntry 41 }

tmnxSubMgmtSlotSPppLclL2tp OBJECT-TYPE
    SYNTAX          Counter32
    MAX-ACCESS      read-only
    STATUS          current
    DESCRIPTION     "The value of tmnxSubMgmtSlotSPppLclL2tp indicates the 
                     number of current locally terminated PPP sessions (L2TP LNS)
                     on this Slot."
    ::= { tmnxSubMgmtSlotStatsEntry 42 }
    
tmnxSubMgmtSlotSPppLclL2tpPeak OBJECT-TYPE
    SYNTAX          Counter32
    MAX-ACCESS      read-only
    STATUS          current
    DESCRIPTION     "The value of tmnxSubMgmtSlotSPppLclL2tpPeak indicates the 
                     peak number of locally terminated PPP sessions (L2TP LNS)
                     on this Slot."
    ::= { tmnxSubMgmtSlotStatsEntry 43 }

tmnxSubMgmtSlotSPppLclTotal OBJECT-TYPE
    SYNTAX          Counter32
    MAX-ACCESS      read-only
    STATUS          current
    DESCRIPTION     "The value of tmnxSubMgmtSlotSPppLclTotal indicates the 
                     total number of current locally terminated PPP sessions
                     on this Slot."
    ::= { tmnxSubMgmtSlotStatsEntry 44 }

tmnxSubMgmtSlotSPppLclTotalPeak OBJECT-TYPE
    SYNTAX          Counter32
    MAX-ACCESS      read-only
    STATUS          current
    DESCRIPTION     "The value of tmnxSubMgmtSlotSPppLclTotalPeak indicates the 
                     total peak number of locally terminated PPP sessions
                     on this Slot."
    ::= { tmnxSubMgmtSlotStatsEntry 45 }

tmnxSubMgmtSlotSPppLacOE OBJECT-TYPE
    SYNTAX          Counter32
    MAX-ACCESS      read-only
    STATUS          current
    DESCRIPTION     "The value of tmnxSubMgmtSlotSPppLacOE indicates the
                     number of current PPP sessions (PPPoE) tunneled over L2TP 
                     on this Slot."
    ::= { tmnxSubMgmtSlotStatsEntry 46 }

tmnxSubMgmtSlotSPppLacOEPeak OBJECT-TYPE
    SYNTAX          Counter32
    MAX-ACCESS      read-only
    STATUS          current
    DESCRIPTION     "The value of tmnxSubMgmtSlotSPppLacOEPeak indicates the 
                     peak number of PPP sessions (PPPoE) tunneled over L2TP 
                     on this Slot."
    ::= { tmnxSubMgmtSlotStatsEntry 47 }

tmnxSubMgmtSlotSPppLacOEOA OBJECT-TYPE
    SYNTAX          Counter32
    MAX-ACCESS      read-only
    STATUS          current
    DESCRIPTION     "The value of tmnxSubMgmtSlotSPppLacOEOA indicates the 
                     number of current PPP sessions (PPPoEoA) tunneled over L2TP 
                     on this Slot."
    ::= { tmnxSubMgmtSlotStatsEntry 48 }

tmnxSubMgmtSlotSPppLacOEOAPeak OBJECT-TYPE
    SYNTAX          Counter32
    MAX-ACCESS      read-only
    STATUS          current
    DESCRIPTION     "The value of tmnxSubMgmtSlotSPppLacOEOAPeak indicates the 
                     peak number of PPP sessions (PPPoEoA) tunneled over L2TP 
                     on this Slot."
    ::= { tmnxSubMgmtSlotStatsEntry 49 }

tmnxSubMgmtSlotSPppLacOA OBJECT-TYPE
    SYNTAX          Counter32
    MAX-ACCESS      read-only
    STATUS          current
    DESCRIPTION     "The value of tmnxSubMgmtSlotSPppLacOA indicates the 
                     number of current PPP sessions (PPPoA) tunneled over L2TP 
                     on this Slot."
    ::= { tmnxSubMgmtSlotStatsEntry 50 }

tmnxSubMgmtSlotSPppLacOAPeak OBJECT-TYPE
    SYNTAX          Counter32
    MAX-ACCESS      read-only
    STATUS          current
    DESCRIPTION     "The value of tmnxSubMgmtSlotSPppLacOAPeak indicates the 
                     peak number of PPP sessions (PPPoA) tunneled over L2TP
                     on this Slot."
    ::= { tmnxSubMgmtSlotStatsEntry 51 }

tmnxSubMgmtSlotSPppLacL2tp OBJECT-TYPE
    SYNTAX          Counter32
    MAX-ACCESS      read-only
    STATUS          current
    DESCRIPTION     "The value of tmnxSubMgmtSlotSPppLacL2tp indicates the 
                     number of current PPP sessions (L2TP LTS) tunneled over L2TP
                     on this Slot."
    ::= { tmnxSubMgmtSlotStatsEntry 52 }

tmnxSubMgmtSlotSPppLacL2tpPeak OBJECT-TYPE
    SYNTAX          Counter32
    MAX-ACCESS      read-only
    STATUS          current
    DESCRIPTION     "The value of tmnxSubMgmtSlotSPppLacL2tpPeak indicates the 
                     peak number of PPP sessions (L2TP LTS) tunneled over L2TP 
                     on this Slot."
    ::= { tmnxSubMgmtSlotStatsEntry 53 }

tmnxSubMgmtSlotSPppLacTotal OBJECT-TYPE
    SYNTAX          Counter32
    MAX-ACCESS      read-only
    STATUS          current
    DESCRIPTION     "The value of tmnxSubMgmtSlotSPppLacTotal indicates the 
                     total number of current PPP sessions tunneled over L2TP
                     on this Slot."
    ::= { tmnxSubMgmtSlotStatsEntry 54 }

tmnxSubMgmtSlotSPppLacTotalPeak OBJECT-TYPE
    SYNTAX          Counter32
    MAX-ACCESS      read-only
    STATUS          current
    DESCRIPTION     "The value of tmnxSubMgmtSlotSPppLacTotalPeak indicates the 
                     total peak number of PPP sessions tunneled over L2TP 
                     on this Slot."
    ::= { tmnxSubMgmtSlotStatsEntry 55 }

tmnxSubMgmtSlotSPppSessIs OBJECT-TYPE
    SYNTAX          Counter32
    MAX-ACCESS      read-only
    STATUS          current
    DESCRIPTION     "The value of tmnxSubMgmtSlotSPppSessIs indicates the 
                     number of current PPP sessions in setup on this Slot."
    ::= { tmnxSubMgmtSlotStatsEntry 56 }

tmnxSubMgmtSlotSPppSessIsPeak OBJECT-TYPE
    SYNTAX          Counter32
    MAX-ACCESS      read-only
    STATUS          current
    DESCRIPTION     "The value of tmnxSubMgmtSlotSPppSessIsPeak indicates the 
                     peak number of PPP sessions in setup on this Slot."
    ::= { tmnxSubMgmtSlotStatsEntry 57 }

tmnxSubMgmtSlotSPppSessTotal OBJECT-TYPE
    SYNTAX          Counter32
    MAX-ACCESS      read-only
    STATUS          current
    DESCRIPTION     "The value of tmnxSubMgmtSlotSPppSessTotal indicates the 
                     total number of current PPP sessions established on this Slot."
    ::= { tmnxSubMgmtSlotStatsEntry 58 }

tmnxSubMgmtSlotSPppSessTotalPeak OBJECT-TYPE
    SYNTAX          Counter32
    MAX-ACCESS      read-only
    STATUS          current
    DESCRIPTION     "The value of tmnxSubMgmtSlotSPppSessTotalPeak indicates the 
                     total peak number of PPP sessions established on this Slot."
    ::= { tmnxSubMgmtSlotStatsEntry 59 }

tmnxSubMgmtSlotSSubscribers OBJECT-TYPE
    SYNTAX          Counter32
    MAX-ACCESS      read-only
    STATUS          current
    DESCRIPTION     "The value of tmnxSubMgmtSlotSSubscribers indicates the number
                     of current subscribers on this Slot."
    ::= { tmnxSubMgmtSlotStatsEntry 60 }

tmnxSubMgmtSlotSSubscribersPeak OBJECT-TYPE
    SYNTAX          Counter32
    MAX-ACCESS      read-only
    STATUS          current
    DESCRIPTION     "The value of tmnxSubMgmtSlotSSubscribersPeak indicates the peak
                     number of subscribers on this Slot."
    ::= { tmnxSubMgmtSlotStatsEntry 61 }

tmnxSubMgmtSlotSDhcpBsmAs OBJECT-TYPE
    SYNTAX          Counter32
    MAX-ACCESS      read-only
    STATUS          current
    DESCRIPTION     "The value of tmnxSubMgmtSlotSDhcpBsmAs indicates the number
                     of current IPOE BSM hosts with antispoof (DHCP) on this Slot."
    ::= { tmnxSubMgmtSlotStatsEntry 62 }

tmnxSubMgmtSlotSDhcpBsmAsPeak OBJECT-TYPE
    SYNTAX          Counter32
    MAX-ACCESS      read-only
    STATUS          current
    DESCRIPTION     "The value of tmnxSubMgmtSlotSDhcpBsmAsPeak indicates the peak
                     number of IPOE BSM hosts with antispoof (DHCP) on this Slot."
    ::= { tmnxSubMgmtSlotStatsEntry 63 }

tmnxSubMgmtSlotSStaticBsmAs OBJECT-TYPE
    SYNTAX          Counter32
    MAX-ACCESS      read-only
    STATUS          current
    DESCRIPTION     "The value of tmnxSubMgmtSlotSStaticBsmAs indicates the number
                     of current IPOE BSM static hosts with antispoof on this Slot."
    ::= { tmnxSubMgmtSlotStatsEntry 64 }

tmnxSubMgmtSlotSStaticBsmAsPeak OBJECT-TYPE
    SYNTAX          Counter32
    MAX-ACCESS      read-only
    STATUS          current
    DESCRIPTION     "The value of tmnxSubMgmtSlotSStaticBsmAsPeak indicates the peak
                     number of IPOE BSM static hosts with antispoof on this Slot."
    ::= { tmnxSubMgmtSlotStatsEntry 65 }

tmnxSubMgmtSlotSDhcpBsm OBJECT-TYPE
    SYNTAX          Counter32
    MAX-ACCESS      read-only
    STATUS          current
    DESCRIPTION     "The value of tmnxSubMgmtSlotSDhcpBsm indicates the number
                     of current IPOE BSM hosts (DHCP) on this Slot."
    ::= { tmnxSubMgmtSlotStatsEntry 66 }

tmnxSubMgmtSlotSDhcpBsmPeak OBJECT-TYPE
    SYNTAX          Counter32
    MAX-ACCESS      read-only
    STATUS          current
    DESCRIPTION     "The value of tmnxSubMgmtSlotSDhcpBsmPeak indicates the peak
                     number of IPOE BSM hosts (DHCP) on this Slot."
    ::= { tmnxSubMgmtSlotStatsEntry 67 }

tmnxSubMgmtSlotSStaticBsm OBJECT-TYPE
    SYNTAX          Counter32
    MAX-ACCESS      read-only
    STATUS          current
    DESCRIPTION     "The value of tmnxSubMgmtSlotSStaticBsm indicates the number
                     of current IPOE BSM static hosts on this Slot."
    ::= { tmnxSubMgmtSlotStatsEntry 68 }

tmnxSubMgmtSlotSStaticBsmPeak OBJECT-TYPE
    SYNTAX          Counter32
    MAX-ACCESS      read-only
    STATUS          current
    DESCRIPTION     "The value of tmnxSubMgmtSlotSStaticBsmPeak indicates the peak
                     number of IPOE BSM static hosts on this Slot."
    ::= { tmnxSubMgmtSlotStatsEntry 69 }

tmnxSubMgmtSlotSPppDhcp6Mr OBJECT-TYPE
    SYNTAX          Counter32
    MAX-ACCESS      read-only
    STATUS          current
    DESCRIPTION     "The value of tmnxSubMgmtSlotSPppDhcp6Mr indicates the number
                     of current PPP PD Managed Routes on this Slot."
    ::= { tmnxSubMgmtSlotStatsEntry 70 }

tmnxSubMgmtSlotSPppDhcp6MrPeak OBJECT-TYPE
    SYNTAX          Counter32
    MAX-ACCESS      read-only
    STATUS          current
    DESCRIPTION     "The value of tmnxSubMgmtSlotSPppDhcp6MrPeak indicates the peak
                     number of PPP PD Managed Routes on this Slot."
    ::= { tmnxSubMgmtSlotStatsEntry 71 }

tmnxSubMgmtSlotSIpoeDhcp6Mr OBJECT-TYPE
    SYNTAX          Counter32
    MAX-ACCESS      read-only
    STATUS          current
    DESCRIPTION     "The value of tmnxSubMgmtSlotSIpoeDhcp6Mr indicates the number
                     of current IPOE PD Managed Routes on this Slot."
    ::= { tmnxSubMgmtSlotStatsEntry 72 }

tmnxSubMgmtSlotSIpoeDhcp6MrPeak OBJECT-TYPE
    SYNTAX          Counter32
    MAX-ACCESS      read-only
    STATUS          current
    DESCRIPTION     "The value of tmnxSubMgmtSlotSIpoeDhcp6MrPeak indicates the peak
                     number of IPOE PD Managed Routes on this Slot."
    ::= { tmnxSubMgmtSlotStatsEntry 73 }

tmnxSubMgmtSlotSV6StaticWan OBJECT-TYPE
    SYNTAX          Counter32
    MAX-ACCESS      read-only
    STATUS          current
    DESCRIPTION     "The value of tmnxSubMgmtSlotSV6StaticWan indicates the number
                     of current IPOE IPv6 static WAN hosts on this Slot."
    ::= { tmnxSubMgmtSlotStatsEntry 74 }

tmnxSubMgmtSlotSV6StaticWanPeak OBJECT-TYPE
    SYNTAX          Counter32
    MAX-ACCESS      read-only
    STATUS          current
    DESCRIPTION     "The value of tmnxSubMgmtSlotSV6StaticWanPeak indicates the peak
                     number of IPOE IPv6 static WAN hosts on this Slot."
    ::= { tmnxSubMgmtSlotStatsEntry 75 }

tmnxSubMgmtSlotSBsmDhcp6Pd OBJECT-TYPE
    SYNTAX          Counter32
    MAX-ACCESS      read-only
    STATUS          current
    DESCRIPTION     "The value of tmnxSubMgmtSlotSBsmDhcp6Pd indicates the number
                     of current IPOE BSM hosts (DHCP6 PD) on this Slot."
    ::= { tmnxSubMgmtSlotStatsEntry 76 }

tmnxSubMgmtSlotSBsmDhcp6PdPeak OBJECT-TYPE
    SYNTAX          Counter32
    MAX-ACCESS      read-only
    STATUS          current
    DESCRIPTION     "The value of tmnxSubMgmtSlotSBsmDhcp6PdPeak indicates the 
                     peak number of IPOE BSM hosts (DHCP6 PD) on this Slot."
    ::= { tmnxSubMgmtSlotStatsEntry 77 }

tmnxSubMgmtSlotSBsmDhcp6Na OBJECT-TYPE
    SYNTAX          Counter32
    MAX-ACCESS      read-only
    STATUS          current
    DESCRIPTION     "The value of tmnxSubMgmtSlotSBsmDhcp6Na indicates the number
                     of current IPOE BSM hosts (DHCP6 NA) on this Slot."
    ::= { tmnxSubMgmtSlotStatsEntry 78 }

tmnxSubMgmtSlotSBsmDhcp6NaPeak OBJECT-TYPE
    SYNTAX          Counter32
    MAX-ACCESS      read-only
    STATUS          current
    DESCRIPTION     "The value of tmnxSubMgmtSlotSBsmDhcp6NaPeak indicates the 
                     peak number of IPOE BSM hosts (DHCP6 NA) on this Slot."
    ::= { tmnxSubMgmtSlotStatsEntry 79 }

tmnxSubMgmtSlotSTotInternal OBJECT-TYPE
    SYNTAX          Counter32
    MAX-ACCESS      read-only
    STATUS          current
    DESCRIPTION     "The value of tmnxSubMgmtSlotSTotInternal indicates the number
                     of current internal hosts on this Slot."
    ::= { tmnxSubMgmtSlotStatsEntry 80 }

tmnxSubMgmtSlotSTotInternalPeak OBJECT-TYPE
    SYNTAX          Counter32
    MAX-ACCESS      read-only
    STATUS          current
    DESCRIPTION     "The value of tmnxSubMgmtSlotSTotInternalPeak indicates the 
                     peak number of internal hosts on this Slot."
    ::= { tmnxSubMgmtSlotStatsEntry 81 }

tmnxSubMgmtSlotSTotDhcp OBJECT-TYPE
    SYNTAX          Counter32
    MAX-ACCESS      read-only
    STATUS          current
    DESCRIPTION     "The value of tmnxSubMgmtSlotSTotDhcp indicates the number
                     of current DHCP hosts on this Slot."
    ::= { tmnxSubMgmtSlotStatsEntry 82 }

tmnxSubMgmtSlotSTotDhcpPeak OBJECT-TYPE
    SYNTAX          Counter32
    MAX-ACCESS      read-only
    STATUS          current
    DESCRIPTION     "The value of tmnxSubMgmtSlotSTotDhcpPeak indicates the 
                     peak number of DHCP hosts on this Slot."
    ::= { tmnxSubMgmtSlotStatsEntry 83 }

tmnxSubMgmtSlotSTotDhcpV6 OBJECT-TYPE
    SYNTAX          Counter32
    MAX-ACCESS      read-only
    STATUS          current
    DESCRIPTION     "The value of tmnxSubMgmtSlotSTotDhcpV6 indicates the number
                     of current DHCPv6 hosts on this Slot."
    ::= { tmnxSubMgmtSlotStatsEntry 84 }

tmnxSubMgmtSlotSTotDhcpV6Peak OBJECT-TYPE
    SYNTAX          Counter32
    MAX-ACCESS      read-only
    STATUS          current
    DESCRIPTION     "The value of tmnxSubMgmtSlotSTotDhcpV6Peak indicates the 
                     peak number of DHCPv6 hosts on this Slot."
    ::= { tmnxSubMgmtSlotStatsEntry 85 }

tmnxSubMgmtSlotSTotMngdRt OBJECT-TYPE
    SYNTAX          Counter32
    MAX-ACCESS      read-only
    STATUS          current
    DESCRIPTION     "The value of tmnxSubMgmtSlotSTotMngdRt indicates the number
                     of current PD Managed Routes on this Slot."
    ::= { tmnxSubMgmtSlotStatsEntry 86 }

tmnxSubMgmtSlotSTotMngdRtPeak OBJECT-TYPE
    SYNTAX          Counter32
    MAX-ACCESS      read-only
    STATUS          current
    DESCRIPTION     "The value of tmnxSubMgmtSlotSTotMngdRtPeak indicates the 
                     peak number of PD Managed Routes on this Slot."
    ::= { tmnxSubMgmtSlotStatsEntry 87 }

tmnxSubMgmtSlotSIpoeSesIs OBJECT-TYPE
    SYNTAX          Counter32
    MAX-ACCESS      read-only
    STATUS          current
    DESCRIPTION     "The value of tmnxSubMgmtSlotSIpoeSesIs indicates the number
                     of current IPOE sessions in setup on this Slot."
    ::= { tmnxSubMgmtSlotStatsEntry 88 }

tmnxSubMgmtSlotSIpoeSesIsPeak OBJECT-TYPE
    SYNTAX          Counter32
    MAX-ACCESS      read-only
    STATUS          current
    DESCRIPTION     "The value of tmnxSubMgmtSlotSIpoeSesIsPeak indicates the 
                     peak number of IPOE sessions in setup on this Slot."
    ::= { tmnxSubMgmtSlotStatsEntry 89 }

tmnxSubMgmtSlotSIpoeSesTotal OBJECT-TYPE
    SYNTAX          Counter32
    MAX-ACCESS      read-only
    STATUS          current
    DESCRIPTION     "The value of tmnxSubMgmtSlotSIpoeSesTotal indicates the number
                     of current IPOE sessions on this Slot."
    ::= { tmnxSubMgmtSlotStatsEntry 90 }

tmnxSubMgmtSlotSIpoeSesTotalPeak OBJECT-TYPE
    SYNTAX          Counter32
    MAX-ACCESS      read-only
    STATUS          current
    DESCRIPTION     "The value of tmnxSubMgmtSlotSIpoeSesTotalPeak indicates the 
                     peak number of IPOE sessions on this Slot."
    ::= { tmnxSubMgmtSlotStatsEntry 91 }

tmnxSubMgmtSlotSV6StaticPd OBJECT-TYPE
    SYNTAX          Counter32
    MAX-ACCESS      read-only
    STATUS          current
    DESCRIPTION     "The value of tmnxSubMgmtSlotSV6StaticPd indicates the number
                     of current IPOE IPv6 static prefixes on this Slot."
    ::= { tmnxSubMgmtSlotStatsEntry 92 }

tmnxSubMgmtSlotSV6StaticPdPeak OBJECT-TYPE
    SYNTAX          Counter32
    MAX-ACCESS      read-only
    STATUS          current
    DESCRIPTION     "The value of tmnxSubMgmtSlotSV6StaticPdPeak indicates the peak
                     number of IPOE IPv6 static prefixes on this Slot."
    ::= { tmnxSubMgmtSlotStatsEntry 93 }
      
--
--  The Subscriber Mgmt per System Statistics Table
--

tmnxSubMgmtSystStatsTable   OBJECT-TYPE
    SYNTAX      SEQUENCE OF TmnxSubMgmtSystStatsEntry
    MAX-ACCESS  not-accessible
    STATUS      current
    DESCRIPTION
       "The tmnxSubMgmtSystStatsTable has an entry with statistics for each
        system on which subscriber hosts are allocated."
    ::= { tmnxSubMgmtObjects 107 }

tmnxSubMgmtSystStatsEntry   OBJECT-TYPE
    SYNTAX      TmnxSubMgmtSystStatsEntry
    MAX-ACCESS  not-accessible
    STATUS      current
    DESCRIPTION
       "Each conceptual row represents statistics for a system on which
        subscriber hosts are allocated."
    INDEX       { tmnxChassisIndex }
    ::= { tmnxSubMgmtSystStatsTable 1 }

TmnxSubMgmtSystStatsEntry ::= SEQUENCE {
        tmnxSubMgmtSystSIpcp             Counter32,
        tmnxSubMgmtSystSIpcpPeak         Counter32,
        tmnxSubMgmtSystSL2tpHost         Counter32,
        tmnxSubMgmtSystSL2tpHostPeak     Counter32,
        tmnxSubMgmtSystSDhcp             Counter32,
        tmnxSubMgmtSystSDhcpPeak         Counter32,
        tmnxSubMgmtSystSArp              Counter32,
        tmnxSubMgmtSystSArpPeak          Counter32,
        tmnxSubMgmtSystSStatic           Counter32,
        tmnxSubMgmtSystSStaticPeak       Counter32,
        tmnxSubMgmtSystSNonSub           Counter32,
        tmnxSubMgmtSystSNonSubPeak       Counter32,
        tmnxSubMgmtSystSPppSlaac         Counter32,
        tmnxSubMgmtSystSPppSlaacPeak     Counter32,
        tmnxSubMgmtSystSPppDhcp6Pd       Counter32,
        tmnxSubMgmtSystSPppDhcp6PdPeak   Counter32,
        tmnxSubMgmtSystSPppDhcp6Na       Counter32,
        tmnxSubMgmtSystSPppDhcp6NaPeak   Counter32,
        tmnxSubMgmtSystSIpoeSlaac        Counter32,
        tmnxSubMgmtSystSIpoeSlaacPeak    Counter32,
        tmnxSubMgmtSystSIpoeDhcp6Pd      Counter32,
        tmnxSubMgmtSystSIpoeDhcp6PdPeak  Counter32,
        tmnxSubMgmtSystSIpoeDhcp6Na      Counter32,
        tmnxSubMgmtSystSIpoeDhcp6NaPeak  Counter32,
        tmnxSubMgmtSystSV4               Counter32,
        tmnxSubMgmtSystSV4Peak           Counter32,
        tmnxSubMgmtSystSV6               Counter32,
        tmnxSubMgmtSystSV6Peak           Counter32,
        tmnxSubMgmtSystSPppHosts         Counter32,
        tmnxSubMgmtSystSPppHostsPeak     Counter32,
        tmnxSubMgmtSystSIpoeHosts        Counter32,
        tmnxSubMgmtSystSIpoeHostsPeak    Counter32,
        tmnxSubMgmtSystSTotal            Counter32,
        tmnxSubMgmtSystSTotalPeak        Counter32,
        tmnxSubMgmtSystSPppLclOE         Counter32,
        tmnxSubMgmtSystSPppLclOEPeak     Counter32,
        tmnxSubMgmtSystSPppLclOEOA       Counter32,
        tmnxSubMgmtSystSPppLclOEOAPeak   Counter32,
        tmnxSubMgmtSystSPppLclOA         Counter32,
        tmnxSubMgmtSystSPppLclOAPeak     Counter32,
        tmnxSubMgmtSystSPppLclL2tp       Counter32,
        tmnxSubMgmtSystSPppLclL2tpPeak   Counter32,
        tmnxSubMgmtSystSPppLclTotal      Counter32,
        tmnxSubMgmtSystSPppLclTotalPeak  Counter32,
        tmnxSubMgmtSystSPppLacOE         Counter32,
        tmnxSubMgmtSystSPppLacOEPeak     Counter32,
        tmnxSubMgmtSystSPppLacOEOA       Counter32,
        tmnxSubMgmtSystSPppLacOEOAPeak   Counter32,
        tmnxSubMgmtSystSPppLacOA         Counter32,
        tmnxSubMgmtSystSPppLacOAPeak     Counter32,
        tmnxSubMgmtSystSPppLacL2tp       Counter32,
        tmnxSubMgmtSystSPppLacL2tpPeak   Counter32,
        tmnxSubMgmtSystSPppLacTotal      Counter32,
        tmnxSubMgmtSystSPppLacTotalPeak  Counter32,
        tmnxSubMgmtSystSPppSessIs        Counter32,
        tmnxSubMgmtSystSPppSessIsPeak    Counter32,
        tmnxSubMgmtSystSPppSessTotal     Counter32,
        tmnxSubMgmtSystSPppSessTotalPeak Counter32,
        tmnxSubMgmtSystSL2tpTunOrig      Counter32,
        tmnxSubMgmtSystSL2tpTunOrigPeak  Counter32,
        tmnxSubMgmtSystSL2tpTunRecv      Counter32,
        tmnxSubMgmtSystSL2tpTunRecvPeak  Counter32,
        tmnxSubMgmtSystSL2tpTunTotal     Counter32,
        tmnxSubMgmtSystSL2tpTunTotalPeak Counter32,
        tmnxSubMgmtSystSSubscribers      Counter32,
        tmnxSubMgmtSystSSubscribersPeak  Counter32,
        tmnxSubMgmtSystSDhcpBsmAs        Counter32,
        tmnxSubMgmtSystSDhcpBsmAsPeak    Counter32,
        tmnxSubMgmtSystSStaticBsmAs      Counter32,
        tmnxSubMgmtSystSStaticBsmAsPeak  Counter32,
        tmnxSubMgmtSystSDhcpBsm          Counter32,
        tmnxSubMgmtSystSDhcpBsmPeak      Counter32,
        tmnxSubMgmtSystSStaticBsm        Counter32,
        tmnxSubMgmtSystSStaticBsmPeak    Counter32,
        tmnxSubMgmtSystSPppDhcp6Mr       Counter32,
        tmnxSubMgmtSystSPppDhcp6MrPeak   Counter32,
        tmnxSubMgmtSystSIpoeDhcp6Mr      Counter32,
        tmnxSubMgmtSystSIpoeDhcp6MrPeak  Counter32,
        tmnxSubMgmtSystSV6StaticWan      Counter32,
        tmnxSubMgmtSystSV6StaticWanPeak  Counter32,
        tmnxSubMgmtSystSBsmDhcp6Pd       Counter32,
        tmnxSubMgmtSystSBsmDhcp6PdPeak   Counter32,
        tmnxSubMgmtSystSBsmDhcp6Na       Counter32,
        tmnxSubMgmtSystSBsmDhcp6NaPeak   Counter32,
        tmnxSubMgmtSystSTotInternal      Counter32,
        tmnxSubMgmtSystSTotInternalPeak  Counter32,
        tmnxSubMgmtSystSTotDhcp          Counter32,
        tmnxSubMgmtSystSTotDhcpPeak      Counter32,
        tmnxSubMgmtSystSTotDhcpV6        Counter32,
        tmnxSubMgmtSystSTotDhcpV6Peak    Counter32,
        tmnxSubMgmtSystSTotMngdRt        Counter32,
        tmnxSubMgmtSystSTotMngdRtPeak    Counter32,
        tmnxSubMgmtSystSIpoeSesIs        Counter32,
        tmnxSubMgmtSystSIpoeSesIsPeak    Counter32,
        tmnxSubMgmtSystSIpoeSesTotal     Counter32,
        tmnxSubMgmtSystSIpoeSesTotalPeak Counter32,
        tmnxSubMgmtSystSHostsScale       Counter32,
        tmnxSubMgmtSystSHostsScalePeak   Counter32,
        tmnxSubMgmtSystSV6StaticPd       Counter32,
        tmnxSubMgmtSystSV6StaticPdPeak   Counter32
    }

tmnxSubMgmtSystSIpcp OBJECT-TYPE
    SYNTAX          Counter32
    MAX-ACCESS      read-only
    STATUS          current
    DESCRIPTION     "The value of tmnxSubMgmtSystSIpcp indicates the number
                     of current PPP hosts (IPCP) on this system."
    ::= { tmnxSubMgmtSystStatsEntry 1 }

tmnxSubMgmtSystSIpcpPeak OBJECT-TYPE
    SYNTAX          Counter32
    MAX-ACCESS      read-only
    STATUS          current
    DESCRIPTION     "The value of tmnxSubMgmtSystSIpcpPeak indicates the peak
                     number of PPP hosts (IPCP) on this system."
    ::= { tmnxSubMgmtSystStatsEntry 2 }

tmnxSubMgmtSystSL2tpHost OBJECT-TYPE
    SYNTAX          Counter32
    MAX-ACCESS      read-only
    STATUS          current
    DESCRIPTION     "The value of tmnxSubMgmtSystSL2tpHost indicates the number
                     of current L2TP hosts (LAC) on this system."
    ::= { tmnxSubMgmtSystStatsEntry 3 }

tmnxSubMgmtSystSL2tpHostPeak OBJECT-TYPE
    SYNTAX          Counter32
    MAX-ACCESS      read-only
    STATUS          current
    DESCRIPTION     "The value of tmnxSubMgmtSystSL2tpHostPeak indicates the peak
                     number of L2TP hosts (LAC) on this system."
    ::= { tmnxSubMgmtSystStatsEntry 4 }

tmnxSubMgmtSystSDhcp OBJECT-TYPE
    SYNTAX          Counter32
    MAX-ACCESS      read-only
    STATUS          current
    DESCRIPTION     "The value of tmnxSubMgmtSystSDhcp indicates the number
                     of current IPOE hosts (DHCP) on this system."
    ::= { tmnxSubMgmtSystStatsEntry 5 }

tmnxSubMgmtSystSDhcpPeak OBJECT-TYPE
    SYNTAX          Counter32
    MAX-ACCESS      read-only
    STATUS          current
    DESCRIPTION     "The value of tmnxSubMgmtSystSDhcpPeak indicates the peak
                     number of IPOE hosts (DHCP) on this system."
    ::= { tmnxSubMgmtSystStatsEntry 6 }

tmnxSubMgmtSystSArp OBJECT-TYPE
    SYNTAX          Counter32
    MAX-ACCESS      read-only
    STATUS          current
    DESCRIPTION     "The value of tmnxSubMgmtSystSArp indicates the number
                     of current IPOE hosts (ARP) on this system."
    ::= { tmnxSubMgmtSystStatsEntry 7 }

tmnxSubMgmtSystSArpPeak OBJECT-TYPE
    SYNTAX          Counter32
    MAX-ACCESS      read-only
    STATUS          current
    DESCRIPTION     "The value of tmnxSubMgmtSystSArpPeak indicates the peak
                     number of IPOE hosts (ARP) on this system."
    ::= { tmnxSubMgmtSystStatsEntry 8 }

tmnxSubMgmtSystSStatic OBJECT-TYPE
    SYNTAX          Counter32
    MAX-ACCESS      read-only
    STATUS          current
    DESCRIPTION     "The value of tmnxSubMgmtSystSStatic indicates the number
                     of current IPOE hosts (Static) on this system."
    ::= { tmnxSubMgmtSystStatsEntry 9 }

tmnxSubMgmtSystSStaticPeak OBJECT-TYPE
    SYNTAX          Counter32
    MAX-ACCESS      read-only
    STATUS          current
    DESCRIPTION     "The value of tmnxSubMgmtSystSStaticPeak indicates the peak
                     number of IPOE hosts (Static) on this system."
    ::= { tmnxSubMgmtSystStatsEntry 10 }

tmnxSubMgmtSystSNonSub OBJECT-TYPE
    SYNTAX          Counter32
    MAX-ACCESS      read-only
    STATUS          current
    DESCRIPTION     "The value of tmnxSubMgmtSystSNonSub indicates the number
                     of current Non Sub hosts on this system."
    ::= { tmnxSubMgmtSystStatsEntry 11 }

tmnxSubMgmtSystSNonSubPeak OBJECT-TYPE
    SYNTAX          Counter32
    MAX-ACCESS      read-only
    STATUS          current
    DESCRIPTION     "The value of tmnxSubMgmtSystSNonSubPeak indicates the peak
                     number of Non Sub hosts on this system."
    ::= { tmnxSubMgmtSystStatsEntry 12 }

tmnxSubMgmtSystSPppSlaac OBJECT-TYPE
    SYNTAX          Counter32
    MAX-ACCESS      read-only
    STATUS          current
    DESCRIPTION     "The value of tmnxSubMgmtSystSPppSlaac indicates the number
                     of current PPP hosts (SLAAC) on this system."
    ::= { tmnxSubMgmtSystStatsEntry 13 }

tmnxSubMgmtSystSPppSlaacPeak OBJECT-TYPE
    SYNTAX          Counter32
    MAX-ACCESS      read-only
    STATUS          current
    DESCRIPTION     "The value of tmnxSubMgmtSystSPppSlaacPeak indicates the 
                     peak number of PPP hosts (SLAAC) on this system."
    ::= { tmnxSubMgmtSystStatsEntry 14 }

tmnxSubMgmtSystSPppDhcp6Pd OBJECT-TYPE
    SYNTAX          Counter32
    MAX-ACCESS      read-only
    STATUS          current
    DESCRIPTION     "The value of tmnxSubMgmtSystSPppDhcp6Pd indicates the number
                     of current PPP hosts (DHCP6 PD) on this system."
    ::= { tmnxSubMgmtSystStatsEntry 15 }

tmnxSubMgmtSystSPppDhcp6PdPeak OBJECT-TYPE
    SYNTAX          Counter32
    MAX-ACCESS      read-only
    STATUS          current
    DESCRIPTION     "The value of tmnxSubMgmtSystSPppDhcp6PdPeak indicates the 
                     peak number of PPP hosts (DHCP6 PD) on this system."
    ::= { tmnxSubMgmtSystStatsEntry 16 }

tmnxSubMgmtSystSPppDhcp6Na OBJECT-TYPE
    SYNTAX          Counter32
    MAX-ACCESS      read-only
    STATUS          current
    DESCRIPTION     "The value of tmnxSubMgmtSystSPppDhcp6Na indicates the number
                     of current PPP hosts (DHCP6 NA) on this system."
    ::= { tmnxSubMgmtSystStatsEntry 17 }

tmnxSubMgmtSystSPppDhcp6NaPeak OBJECT-TYPE
    SYNTAX          Counter32
    MAX-ACCESS      read-only
    STATUS          current
    DESCRIPTION     "The value of tmnxSubMgmtSystSPppDhcp6NaPeak indicates the 
                     peak number of PPP hosts (DHCP6 NA) on this system."
    ::= { tmnxSubMgmtSystStatsEntry 18 }

tmnxSubMgmtSystSIpoeSlaac OBJECT-TYPE
    SYNTAX          Counter32
    MAX-ACCESS      read-only
    STATUS          current
    DESCRIPTION     "The value of tmnxSubMgmtSystSIpoeSlaac indicates the 
                     number of current IPOE hosts (SLAAC) on this system."
    ::= { tmnxSubMgmtSystStatsEntry 19 }

tmnxSubMgmtSystSIpoeSlaacPeak OBJECT-TYPE
    SYNTAX          Counter32
    MAX-ACCESS      read-only
    STATUS          current
    DESCRIPTION     "The value of tmnxSubMgmtSystSIpoeSlaacPeak indicates the 
                     peak number of IPOE hosts (SLAAC) on this system."
    ::= { tmnxSubMgmtSystStatsEntry 20 }

tmnxSubMgmtSystSIpoeDhcp6Pd OBJECT-TYPE
    SYNTAX          Counter32
    MAX-ACCESS      read-only
    STATUS          current
    DESCRIPTION     "The value of tmnxSubMgmtSystSIpoeDhcp6Pd indicates the 
                     number of current IPOE hosts (DHCP6 PD) on this system."
    ::= { tmnxSubMgmtSystStatsEntry 21 }

tmnxSubMgmtSystSIpoeDhcp6PdPeak OBJECT-TYPE
    SYNTAX          Counter32
    MAX-ACCESS      read-only
    STATUS          current
    DESCRIPTION     "The value of tmnxSubMgmtSystSIpoeDhcp6PdPeak indicates the 
                     peak number of IPOE hosts (DHCP6 PD) on this system."
    ::= { tmnxSubMgmtSystStatsEntry 22 }

tmnxSubMgmtSystSIpoeDhcp6Na OBJECT-TYPE
    SYNTAX          Counter32
    MAX-ACCESS      read-only
    STATUS          current
    DESCRIPTION     "The value of tmnxSubMgmtSystSIpoeDhcp6Na indicates the 
                     number of current IPOE hosts (DHCP6 NA) on this system."
    ::= { tmnxSubMgmtSystStatsEntry 23 }

tmnxSubMgmtSystSIpoeDhcp6NaPeak OBJECT-TYPE
    SYNTAX          Counter32
    MAX-ACCESS      read-only
    STATUS          current
    DESCRIPTION     "The value of tmnxSubMgmtSystSIpoeDhcp6NaPeak indicates the 
                     peak number of IPOE hosts (DHCP6 NA) on this system."
    ::= { tmnxSubMgmtSystStatsEntry 24 }

tmnxSubMgmtSystSV4 OBJECT-TYPE
    SYNTAX          Counter32
    MAX-ACCESS      read-only
    STATUS          current
    DESCRIPTION     "The value of tmnxSubMgmtSystSV4 indicates the number
                     of current V4 hosts on this system."
    ::= { tmnxSubMgmtSystStatsEntry 25 }

tmnxSubMgmtSystSV4Peak OBJECT-TYPE
    SYNTAX          Counter32
    MAX-ACCESS      read-only
    STATUS          current
    DESCRIPTION     "The value of tmnxSubMgmtSystSV4Peak indicates the peak
                     number of V4 hosts on this system."
    ::= { tmnxSubMgmtSystStatsEntry 26 }

tmnxSubMgmtSystSV6 OBJECT-TYPE
    SYNTAX          Counter32
    MAX-ACCESS      read-only
    STATUS          current
    DESCRIPTION     "The value of tmnxSubMgmtSystSV6 indicates the number
                     of current V6 hosts on this system."
    ::= { tmnxSubMgmtSystStatsEntry 27 }

tmnxSubMgmtSystSV6Peak OBJECT-TYPE
    SYNTAX          Counter32
    MAX-ACCESS      read-only
    STATUS          current
    DESCRIPTION     "The value of tmnxSubMgmtSystSV6Peak indicates the peak
                     number of V6 hosts on this system."
    ::= { tmnxSubMgmtSystStatsEntry 28 }

tmnxSubMgmtSystSPppHosts OBJECT-TYPE
    SYNTAX          Counter32
    MAX-ACCESS      read-only
    STATUS          current
    DESCRIPTION     "The value of tmnxSubMgmtSystSPppHosts indicates the 
                     number of current PPP hosts on this system."
    ::= { tmnxSubMgmtSystStatsEntry 29 }

tmnxSubMgmtSystSPppHostsPeak OBJECT-TYPE
    SYNTAX          Counter32
    MAX-ACCESS      read-only
    STATUS          current
    DESCRIPTION     "The value of tmnxSubMgmtSystSPppHostsPeak indicates the
                     peak number of PPP hosts on this system."
    ::= { tmnxSubMgmtSystStatsEntry 30 }

tmnxSubMgmtSystSIpoeHosts OBJECT-TYPE
    SYNTAX          Counter32
    MAX-ACCESS      read-only
    STATUS          current
    DESCRIPTION     "The value of tmnxSubMgmtSystSIpoeHosts indicates the 
                     number of current IPOE hosts on this system."
    ::= { tmnxSubMgmtSystStatsEntry 31 }

tmnxSubMgmtSystSIpoeHostsPeak OBJECT-TYPE
    SYNTAX          Counter32
    MAX-ACCESS      read-only
    STATUS          current
    DESCRIPTION     "The value of tmnxSubMgmtSystSIpoeHostsPeak indicates the
                     peak number of IPOE hosts on this system."
    ::= { tmnxSubMgmtSystStatsEntry 32 }

tmnxSubMgmtSystSTotal OBJECT-TYPE
    SYNTAX          Counter32
    MAX-ACCESS      read-only
    STATUS          current
    DESCRIPTION     "The value of tmnxSubMgmtSystSTotal indicates the 
                     number of current total hosts on this system."
    ::= { tmnxSubMgmtSystStatsEntry 33 }

tmnxSubMgmtSystSTotalPeak OBJECT-TYPE
    SYNTAX          Counter32
    MAX-ACCESS      read-only
    STATUS          current
    DESCRIPTION     "The value of tmnxSubMgmtSystSTotalPeak indicates the 
                     peak number of total hosts on this system."
    ::= { tmnxSubMgmtSystStatsEntry 34 }

tmnxSubMgmtSystSPppLclOE OBJECT-TYPE
    SYNTAX          Counter32
    MAX-ACCESS      read-only
    STATUS          current
    DESCRIPTION     "The value of tmnxSubMgmtSystSPppLclOE indicates the
                     number of current locally terminated PPP sessions (PPPoE)
                     on this system."
    ::= { tmnxSubMgmtSystStatsEntry 35 }

tmnxSubMgmtSystSPppLclOEPeak OBJECT-TYPE
    SYNTAX          Counter32
    MAX-ACCESS      read-only
    STATUS          current
    DESCRIPTION     "The value of tmnxSubMgmtSystSPppLclOEPeak indicates the 
                     peak number of locally terminated PPP sessions (PPPoE) 
                     on this system."
    ::= { tmnxSubMgmtSystStatsEntry 36 }

tmnxSubMgmtSystSPppLclOEOA OBJECT-TYPE
    SYNTAX          Counter32
    MAX-ACCESS      read-only
    STATUS          current
    DESCRIPTION     "The value of tmnxSubMgmtSystSPppLclOEOA indicates the 
                     number of current locally terminated PPP sessions (PPPoEoA)
                     on this system."
    ::= { tmnxSubMgmtSystStatsEntry 37 }

tmnxSubMgmtSystSPppLclOEOAPeak OBJECT-TYPE
    SYNTAX          Counter32
    MAX-ACCESS      read-only
    STATUS          current
    DESCRIPTION     "The value of tmnxSubMgmtSystSPppLclOEOAPeak indicates the 
                     peak number of locally terminated PPP sessions (PPPoEoA) 
                     on this system."
    ::= { tmnxSubMgmtSystStatsEntry 38 }

tmnxSubMgmtSystSPppLclOA OBJECT-TYPE
    SYNTAX          Counter32
    MAX-ACCESS      read-only
    STATUS          current
    DESCRIPTION     "The value of tmnxSubMgmtSystSPppLclOA indicates the number
                     of current locally terminated PPP sessions (PPPoA)
                     on this system."
    ::= { tmnxSubMgmtSystStatsEntry 39 }

tmnxSubMgmtSystSPppLclOAPeak OBJECT-TYPE
    SYNTAX          Counter32
    MAX-ACCESS      read-only
    STATUS          current
    DESCRIPTION     "The value of tmnxSubMgmtSystSPppLclOAPeak indicates the 
                     peak number of locally terminated PPP sessions (PPPoA) 
                     on this system."
    ::= { tmnxSubMgmtSystStatsEntry 40 }

tmnxSubMgmtSystSPppLclL2tp OBJECT-TYPE
    SYNTAX          Counter32
    MAX-ACCESS      read-only
    STATUS          current
    DESCRIPTION     "The value of tmnxSubMgmtSystSPppLclL2tp indicates the 
                     number of current locally terminated PPP sessions (L2TP LNS)
                     on this system."
    ::= { tmnxSubMgmtSystStatsEntry 41 }
    
tmnxSubMgmtSystSPppLclL2tpPeak OBJECT-TYPE
    SYNTAX          Counter32
    MAX-ACCESS      read-only
    STATUS          current
    DESCRIPTION     "The value of tmnxSubMgmtSystSPppLclL2tpPeak indicates the 
                     peak number of locally terminated PPP sessions (L2TP LNS)
                     on this system."
    ::= { tmnxSubMgmtSystStatsEntry 42 }

tmnxSubMgmtSystSPppLclTotal OBJECT-TYPE
    SYNTAX          Counter32
    MAX-ACCESS      read-only
    STATUS          current
    DESCRIPTION     "The value of tmnxSubMgmtSystSPppLclTotal indicates the 
                     total number of current locally terminated PPP sessions
                     on this system."
    ::= { tmnxSubMgmtSystStatsEntry 43 }

tmnxSubMgmtSystSPppLclTotalPeak OBJECT-TYPE
    SYNTAX          Counter32
    MAX-ACCESS      read-only
    STATUS          current
    DESCRIPTION     "The value of tmnxSubMgmtSystSPppLclTotalPeak indicates the 
                     total peak number of locally terminated PPP sessions
                     on this system."
    ::= { tmnxSubMgmtSystStatsEntry 44 }

tmnxSubMgmtSystSPppLacOE OBJECT-TYPE
    SYNTAX          Counter32
    MAX-ACCESS      read-only
    STATUS          current
    DESCRIPTION     "The value of tmnxSubMgmtSystSPppLacOE indicates the
                     number of current PPP sessions (PPPoE) tunneled over L2TP 
                     on this system."
    ::= { tmnxSubMgmtSystStatsEntry 45 }

tmnxSubMgmtSystSPppLacOEPeak OBJECT-TYPE
    SYNTAX          Counter32
    MAX-ACCESS      read-only
    STATUS          current
    DESCRIPTION     "The value of tmnxSubMgmtSystSPppLacOEPeak indicates the 
                     peak number of PPP sessions (PPPoE) tunneled over L2TP 
                     on this system."
    ::= { tmnxSubMgmtSystStatsEntry 46 }

tmnxSubMgmtSystSPppLacOEOA OBJECT-TYPE
    SYNTAX          Counter32
    MAX-ACCESS      read-only
    STATUS          current
    DESCRIPTION     "The value of tmnxSubMgmtSystSPppLacOEOA indicates the 
                     number of current PPP sessions (PPPoEoA) tunneled over L2TP 
                     on this system."
    ::= { tmnxSubMgmtSystStatsEntry 47 }

tmnxSubMgmtSystSPppLacOEOAPeak OBJECT-TYPE
    SYNTAX          Counter32
    MAX-ACCESS      read-only
    STATUS          current
    DESCRIPTION     "The value of tmnxSubMgmtSystSPppLacOEOAPeak indicates the 
                     peak number of PPP sessions (PPPoEoA) tunneled over L2TP 
                     on this system."
    ::= { tmnxSubMgmtSystStatsEntry 48 }

tmnxSubMgmtSystSPppLacOA OBJECT-TYPE
    SYNTAX          Counter32
    MAX-ACCESS      read-only
    STATUS          current
    DESCRIPTION     "The value of tmnxSubMgmtSystSPppLacOA indicates the 
                     number of current PPP sessions (PPPoA) tunneled over L2TP 
                     on this system."
    ::= { tmnxSubMgmtSystStatsEntry 49 }

tmnxSubMgmtSystSPppLacOAPeak OBJECT-TYPE
    SYNTAX          Counter32
    MAX-ACCESS      read-only
    STATUS          current
    DESCRIPTION     "The value of tmnxSubMgmtSystSPppLacOAPeak indicates the 
                     peak number of PPP sessions (PPPoA) tunneled over L2TP
                     on this system."
    ::= { tmnxSubMgmtSystStatsEntry 50 }

tmnxSubMgmtSystSPppLacL2tp OBJECT-TYPE
    SYNTAX          Counter32
    MAX-ACCESS      read-only
    STATUS          current
    DESCRIPTION     "The value of tmnxSubMgmtSystSPppLacL2tp indicates the 
                     number of current PPP sessions (L2TP LTS) tunneled over L2TP
                     on this system."
    ::= { tmnxSubMgmtSystStatsEntry 51 }

tmnxSubMgmtSystSPppLacL2tpPeak OBJECT-TYPE
    SYNTAX          Counter32
    MAX-ACCESS      read-only
    STATUS          current
    DESCRIPTION     "The value of tmnxSubMgmtSystSPppLacL2tpPeak indicates the 
                     peak number of PPP sessions (L2TP LTS) tunneled over L2TP 
                     on this system."
    ::= { tmnxSubMgmtSystStatsEntry 52 }

tmnxSubMgmtSystSPppLacTotal OBJECT-TYPE
    SYNTAX          Counter32
    MAX-ACCESS      read-only
    STATUS          current
    DESCRIPTION     "The value of tmnxSubMgmtSystSPppLacTotal indicates the 
                     total number of current PPP sessions tunneled over L2TP
                     on this system."
    ::= { tmnxSubMgmtSystStatsEntry 53 }

tmnxSubMgmtSystSPppLacTotalPeak OBJECT-TYPE
    SYNTAX          Counter32
    MAX-ACCESS      read-only
    STATUS          current
    DESCRIPTION     "The value of tmnxSubMgmtSystSPppLacTotalPeak indicates the 
                     total peak number of PPP sessions tunneled over L2TP 
                     on this system."
    ::= { tmnxSubMgmtSystStatsEntry 54 }

tmnxSubMgmtSystSPppSessIs OBJECT-TYPE
    SYNTAX          Counter32
    MAX-ACCESS      read-only
    STATUS          current
    DESCRIPTION     "The value of tmnxSubMgmtSystSPppSessIs indicates the 
                     number of current PPP sessions in setup on this system."
    ::= { tmnxSubMgmtSystStatsEntry 55 }

tmnxSubMgmtSystSPppSessIsPeak OBJECT-TYPE
    SYNTAX          Counter32
    MAX-ACCESS      read-only
    STATUS          current
    DESCRIPTION     "The value of tmnxSubMgmtSystSPppSessIsPeak indicates the 
                     peak number of PPP sessions in setup on this system."
    ::= { tmnxSubMgmtSystStatsEntry 56 }

tmnxSubMgmtSystSPppSessTotal OBJECT-TYPE
    SYNTAX          Counter32
    MAX-ACCESS      read-only
    STATUS          current
    DESCRIPTION     "The value of tmnxSubMgmtSystSPppSessTotal indicates the 
                     total number of current PPP sessions established on this
                     system."
    ::= { tmnxSubMgmtSystStatsEntry 57 }

tmnxSubMgmtSystSPppSessTotalPeak OBJECT-TYPE
    SYNTAX          Counter32
    MAX-ACCESS      read-only
    STATUS          current
    DESCRIPTION     "The value of tmnxSubMgmtSystSPppSessTotalPeak indicates the 
                     total peak number of PPP sessions established on this
                     system."
    ::= { tmnxSubMgmtSystStatsEntry 58 }

tmnxSubMgmtSystSL2tpTunOrig OBJECT-TYPE
    SYNTAX          Counter32
    MAX-ACCESS      read-only
    STATUS          current
    DESCRIPTION     "The value of tmnxSubMgmtSystSL2tpTunOrig indicates the 
                     number of current L2TP Tunnels (originator) on this system."
    ::= { tmnxSubMgmtSystStatsEntry 59 }

tmnxSubMgmtSystSL2tpTunOrigPeak OBJECT-TYPE
    SYNTAX          Counter32
    MAX-ACCESS      read-only
    STATUS          current
    DESCRIPTION     "The value of tmnxSubMgmtSystSL2tpTunOrigPeak indicates the 
                     peak number of L2TP Tunnels (originator) on this system."
    ::= { tmnxSubMgmtSystStatsEntry 60 }

tmnxSubMgmtSystSL2tpTunRecv OBJECT-TYPE
    SYNTAX          Counter32
    MAX-ACCESS      read-only
    STATUS          current
    DESCRIPTION     "The value of tmnxSubMgmtSystSL2tpTunRecv indicates the 
                     number of current L2TP Tunnels (receiver) on this system."
    ::= { tmnxSubMgmtSystStatsEntry 61 }

tmnxSubMgmtSystSL2tpTunRecvPeak OBJECT-TYPE
    SYNTAX          Counter32
    MAX-ACCESS      read-only
    STATUS          current
    DESCRIPTION     "The value of tmnxSubMgmtSystSL2tpTunRecvPeak indicates the 
                     peak number of L2TP Tunnels (receiver) on this system."
    ::= { tmnxSubMgmtSystStatsEntry 62 }

tmnxSubMgmtSystSL2tpTunTotal OBJECT-TYPE
    SYNTAX          Counter32
    MAX-ACCESS      read-only
    STATUS          current
    DESCRIPTION     "The value of tmnxSubMgmtSystSL2tpTunTotal indicates the 
                     total number of current L2TP Tunnels on this system."
    ::= { tmnxSubMgmtSystStatsEntry 63 }

tmnxSubMgmtSystSL2tpTunTotalPeak OBJECT-TYPE
    SYNTAX          Counter32
    MAX-ACCESS      read-only
    STATUS          current
    DESCRIPTION     "The value of tmnxSubMgmtSystSL2tpTunTotalPeak indicates the 
                     peak total number of L2TP Tunnels on this system."
    ::= { tmnxSubMgmtSystStatsEntry 64 }

tmnxSubMgmtSystSSubscribers OBJECT-TYPE
    SYNTAX          Counter32
    MAX-ACCESS      read-only
    STATUS          current
    DESCRIPTION     "The value of tmnxSubMgmtSystSSubscribers indicates the number
                     of current subscribers on this system."
    ::= { tmnxSubMgmtSystStatsEntry 65 }

tmnxSubMgmtSystSSubscribersPeak OBJECT-TYPE
    SYNTAX          Counter32
    MAX-ACCESS      read-only
    STATUS          current
    DESCRIPTION     "The value of tmnxSubMgmtSystSSubscribersPeak indicates the peak
                     number of subscribers on this system."
    ::= { tmnxSubMgmtSystStatsEntry 66 }

tmnxSubMgmtSystSDhcpBsmAs OBJECT-TYPE
    SYNTAX          Counter32
    MAX-ACCESS      read-only
    STATUS          current
    DESCRIPTION     "The value of tmnxSubMgmtSystSDhcpBsmAs indicates the number
                     of current IPOE BSM hosts with antispoof (DHCP) on this system."
    ::= { tmnxSubMgmtSystStatsEntry 67 }

tmnxSubMgmtSystSDhcpBsmAsPeak OBJECT-TYPE
    SYNTAX          Counter32
    MAX-ACCESS      read-only
    STATUS          current
    DESCRIPTION     "The value of tmnxSubMgmtSystSDhcpBsmAsPeak indicates the peak
                     number of IPOE BSM hosts with antispoof (DHCP) on this system."
    ::= { tmnxSubMgmtSystStatsEntry 68 }

tmnxSubMgmtSystSStaticBsmAs OBJECT-TYPE
    SYNTAX          Counter32
    MAX-ACCESS      read-only
    STATUS          current
    DESCRIPTION     "The value of tmnxSubMgmtSystSStaticBsmAs indicates the number
                     of current IPOE BSM static hosts with antispoof on this system."
    ::= { tmnxSubMgmtSystStatsEntry 69 }

tmnxSubMgmtSystSStaticBsmAsPeak OBJECT-TYPE
    SYNTAX          Counter32
    MAX-ACCESS      read-only
    STATUS          current
    DESCRIPTION     "The value of tmnxSubMgmtSystSStaticBsmAsPeak indicates the peak
                     number of IPOE BSM static hosts with antispoof on this system."
    ::= { tmnxSubMgmtSystStatsEntry 70 }

tmnxSubMgmtSystSDhcpBsm OBJECT-TYPE
    SYNTAX          Counter32
    MAX-ACCESS      read-only
    STATUS          current
    DESCRIPTION     "The value of tmnxSubMgmtSystSDhcpBsm indicates the number
                     of current IPOE BSM hosts (DHCP) on this system."
    ::= { tmnxSubMgmtSystStatsEntry 71 }

tmnxSubMgmtSystSDhcpBsmPeak OBJECT-TYPE
    SYNTAX          Counter32
    MAX-ACCESS      read-only
    STATUS          current
    DESCRIPTION     "The value of tmnxSubMgmtSystSDhcpBsmPeak indicates the peak
                     number of IPOE BSM hosts (DHCP) on this system."
    ::= { tmnxSubMgmtSystStatsEntry 72 }

tmnxSubMgmtSystSStaticBsm OBJECT-TYPE
    SYNTAX          Counter32
    MAX-ACCESS      read-only
    STATUS          current
    DESCRIPTION     "The value of tmnxSubMgmtSystSStaticBsm indicates the number
                     of current IPOE BSM static hosts on this system."
    ::= { tmnxSubMgmtSystStatsEntry 73 }

tmnxSubMgmtSystSStaticBsmPeak OBJECT-TYPE
    SYNTAX          Counter32
    MAX-ACCESS      read-only
    STATUS          current
    DESCRIPTION     "The value of tmnxSubMgmtSystSStaticBsmPeak indicates the peak
                     number of IPOE BSM static hosts on this system."
    ::= { tmnxSubMgmtSystStatsEntry 74 }

tmnxSubMgmtSystSPppDhcp6Mr OBJECT-TYPE
    SYNTAX          Counter32
    MAX-ACCESS      read-only
    STATUS          current
    DESCRIPTION     "The value of tmnxSubMgmtSystSPppDhcp6Mr indicates the number
                     of current PPP PD Managed Routes on this system."
    ::= { tmnxSubMgmtSystStatsEntry 75 }

tmnxSubMgmtSystSPppDhcp6MrPeak OBJECT-TYPE
    SYNTAX          Counter32
    MAX-ACCESS      read-only
    STATUS          current
    DESCRIPTION     "The value of tmnxSubMgmtSystSPppDhcp6MrPeak indicates the peak
                     number of PPP PD Managed Routes on this system."
    ::= { tmnxSubMgmtSystStatsEntry 76 }

tmnxSubMgmtSystSIpoeDhcp6Mr OBJECT-TYPE
    SYNTAX          Counter32
    MAX-ACCESS      read-only
    STATUS          current
    DESCRIPTION     "The value of tmnxSubMgmtSystSIpoeDhcp6Mr indicates the number
                     of current IPOE PD Managed Routes on this system."
    ::= { tmnxSubMgmtSystStatsEntry 77 }

tmnxSubMgmtSystSIpoeDhcp6MrPeak OBJECT-TYPE
    SYNTAX          Counter32
    MAX-ACCESS      read-only
    STATUS          current
    DESCRIPTION     "The value of tmnxSubMgmtSystSIpoeDhcp6MrPeak indicates the peak
                     number of IPOE PD Managed Routes on this system."
    ::= { tmnxSubMgmtSystStatsEntry 78 }

tmnxSubMgmtSystSV6StaticWan OBJECT-TYPE
    SYNTAX          Counter32
    MAX-ACCESS      read-only
    STATUS          current
    DESCRIPTION     "The value of tmnxSubMgmtSystSV6StaticWan indicates the number
                     of current IPOE IPv6 static WAN hosts on this system."
    ::= { tmnxSubMgmtSystStatsEntry 79 }

tmnxSubMgmtSystSV6StaticWanPeak OBJECT-TYPE
    SYNTAX          Counter32
    MAX-ACCESS      read-only
    STATUS          current
    DESCRIPTION     "The value of tmnxSubMgmtSystSV6StaticWanPeak indicates the peak
                     number of IPOE IPv6 static WAN hosts on this system."
    ::= { tmnxSubMgmtSystStatsEntry 80 }

tmnxSubMgmtSystSBsmDhcp6Pd OBJECT-TYPE
    SYNTAX          Counter32
    MAX-ACCESS      read-only
    STATUS          current
    DESCRIPTION     "The value of tmnxSubMgmtSystSBsmDhcp6Pd indicates the number
                     of current IPOE BSM hosts (DHCP6 PD) on this system."
    ::= { tmnxSubMgmtSystStatsEntry 81 }

tmnxSubMgmtSystSBsmDhcp6PdPeak OBJECT-TYPE
    SYNTAX          Counter32
    MAX-ACCESS      read-only
    STATUS          current
    DESCRIPTION     "The value of tmnxSubMgmtSystSBsmDhcp6PdPeak indicates the 
                     peak number of IPOE BSM hosts (DHCP6 PD) on this system."
    ::= { tmnxSubMgmtSystStatsEntry 82 }

tmnxSubMgmtSystSBsmDhcp6Na OBJECT-TYPE
    SYNTAX          Counter32
    MAX-ACCESS      read-only
    STATUS          current
    DESCRIPTION     "The value of tmnxSubMgmtSystSBsmDhcp6Na indicates the number
                     of current IPOE BSM hosts (DHCP6 NA) on this system."
    ::= { tmnxSubMgmtSystStatsEntry 83 }

tmnxSubMgmtSystSBsmDhcp6NaPeak OBJECT-TYPE
    SYNTAX          Counter32
    MAX-ACCESS      read-only
    STATUS          current
    DESCRIPTION     "The value of tmnxSubMgmtSystSBsmDhcp6NaPeak indicates the 
                     peak number of IPOE BSM hosts (DHCP6 NA) on this system."
    ::= { tmnxSubMgmtSystStatsEntry 84 }

tmnxSubMgmtSystSTotInternal OBJECT-TYPE
    SYNTAX          Counter32
    MAX-ACCESS      read-only
    STATUS          current
    DESCRIPTION     "The value of tmnxSubMgmtSystSTotInternal indicates the number
                     of current internal hosts on this system."
    ::= { tmnxSubMgmtSystStatsEntry 85 }

tmnxSubMgmtSystSTotInternalPeak OBJECT-TYPE
    SYNTAX          Counter32
    MAX-ACCESS      read-only
    STATUS          current
    DESCRIPTION     "The value of tmnxSubMgmtSystSTotInternalPeak indicates the 
                     peak number of internal hosts on this system."
    ::= { tmnxSubMgmtSystStatsEntry 86 }

tmnxSubMgmtSystSTotDhcp OBJECT-TYPE
    SYNTAX          Counter32
    MAX-ACCESS      read-only
    STATUS          current
    DESCRIPTION     "The value of tmnxSubMgmtSystSTotDhcp indicates the number
                     of current DHCP hosts on this system."
    ::= { tmnxSubMgmtSystStatsEntry 87 }

tmnxSubMgmtSystSTotDhcpPeak OBJECT-TYPE
    SYNTAX          Counter32
    MAX-ACCESS      read-only
    STATUS          current
    DESCRIPTION     "The value of tmnxSubMgmtSystSTotDhcpPeak indicates the 
                     peak number of DHCP hosts on this system."
    ::= { tmnxSubMgmtSystStatsEntry 88 }

tmnxSubMgmtSystSTotDhcpV6 OBJECT-TYPE
    SYNTAX          Counter32
    MAX-ACCESS      read-only
    STATUS          current
    DESCRIPTION     "The value of tmnxSubMgmtSystSTotDhcpV6 indicates the number
                     of current DHCPv6 hosts on this system."
    ::= { tmnxSubMgmtSystStatsEntry 89 }

tmnxSubMgmtSystSTotDhcpV6Peak OBJECT-TYPE
    SYNTAX          Counter32
    MAX-ACCESS      read-only
    STATUS          current
    DESCRIPTION     "The value of tmnxSubMgmtSystSTotDhcpV6Peak indicates the 
                     peak number of DHCPv6 hosts on this system."
    ::= { tmnxSubMgmtSystStatsEntry 90 }

tmnxSubMgmtSystSTotMngdRt OBJECT-TYPE
    SYNTAX          Counter32
    MAX-ACCESS      read-only
    STATUS          current
    DESCRIPTION     "The value of tmnxSubMgmtSystSTotMngdRt indicates the number
                     of current PD Managed Routes on this system."
    ::= { tmnxSubMgmtSystStatsEntry 91 }

tmnxSubMgmtSystSTotMngdRtPeak OBJECT-TYPE
    SYNTAX          Counter32
    MAX-ACCESS      read-only
    STATUS          current
    DESCRIPTION     "The value of tmnxSubMgmtSystSTotMngdRtPeak indicates the 
                     peak number of PD Managed Routes on this system."
    ::= { tmnxSubMgmtSystStatsEntry 92 }

tmnxSubMgmtSystSIpoeSesIs OBJECT-TYPE
    SYNTAX          Counter32
    MAX-ACCESS      read-only
    STATUS          current
    DESCRIPTION     "The value of tmnxSubMgmtSystSIpoeSesIs indicates the number
                     of current IPOE sessions in setup on this system."
    ::= { tmnxSubMgmtSystStatsEntry 93 }

tmnxSubMgmtSystSIpoeSesIsPeak OBJECT-TYPE
    SYNTAX          Counter32
    MAX-ACCESS      read-only
    STATUS          current
    DESCRIPTION     "The value of tmnxSubMgmtSystSIpoeSesIsPeak indicates the 
                     peak number of IPOE sessions in setup on this system."
    ::= { tmnxSubMgmtSystStatsEntry 94 }

tmnxSubMgmtSystSIpoeSesTotal OBJECT-TYPE
    SYNTAX          Counter32
    MAX-ACCESS      read-only
    STATUS          current
    DESCRIPTION     "The value of tmnxSubMgmtSystSIpoeSesTotal indicates the number
                     of current IPOE sessions on this system."
    ::= { tmnxSubMgmtSystStatsEntry 95 }

tmnxSubMgmtSystSIpoeSesTotalPeak OBJECT-TYPE
    SYNTAX          Counter32
    MAX-ACCESS      read-only
    STATUS          current
    DESCRIPTION     "The value of tmnxSubMgmtSystSIpoeSesTotalPeak indicates the 
                     peak number of IPOE sessions on this system."
    ::= { tmnxSubMgmtSystStatsEntry 96 }

tmnxSubMgmtSystSHostsScale OBJECT-TYPE
    SYNTAX          Counter32
    MAX-ACCESS      read-only
    STATUS          current
    DESCRIPTION     "The value of tmnxSubMgmtSystSHostsScale indicates the 
                     number of current total hosts on this system, including 
                     internal hosts."
    ::= { tmnxSubMgmtSystStatsEntry 97 }

tmnxSubMgmtSystSHostsScalePeak OBJECT-TYPE
    SYNTAX          Counter32
    MAX-ACCESS      read-only
    STATUS          current
    DESCRIPTION     "The value of tmnxSubMgmtSystSHostsScalePeak indicates the 
                     peak number of total hosts on this system, including 
                     internal hosts."
    ::= { tmnxSubMgmtSystStatsEntry 98 }

tmnxSubMgmtSystSV6StaticPd OBJECT-TYPE
    SYNTAX          Counter32
    MAX-ACCESS      read-only
    STATUS          current
    DESCRIPTION     "The value of tmnxSubMgmtSystSV6StaticPd indicates the number
                     of current IPOE IPv6 static prefixes on this system."
    ::= { tmnxSubMgmtSystStatsEntry 99 }

tmnxSubMgmtSystSV6StaticPdPeak OBJECT-TYPE
    SYNTAX          Counter32
    MAX-ACCESS      read-only
    STATUS          current
    DESCRIPTION     "The value of tmnxSubMgmtSystSV6StaticPdPeak indicates the peak
                     number of IPOE IPv6 static prefixes on this system."
    ::= { tmnxSubMgmtSystStatsEntry 100 }
  
--
--  The Subscriber Mgmt per Pseudo Wire Port Statistics Table
--

tmnxSubMgmtPwPortStatsTable   OBJECT-TYPE
    SYNTAX      SEQUENCE OF TmnxSubMgmtPwPortStatsEntry
    MAX-ACCESS  not-accessible
    STATUS      current
    DESCRIPTION
       "The tmnxSubMgmtPwPortStatsTable has an entry with statistics for each
        PW-port on which subscriber hosts are allocated."
    ::= { tmnxSubMgmtObjects 113 }

tmnxSubMgmtPwPortStatsEntry   OBJECT-TYPE
    SYNTAX      TmnxSubMgmtPwPortStatsEntry
    MAX-ACCESS  not-accessible
    STATUS      current
    DESCRIPTION
       "Each conceptual row represents statistics for a PW-port on which
        subscriber hosts are allocated."
    INDEX       { tmnxChassisIndex,
                  tmnxPwPortId }
    ::= { tmnxSubMgmtPwPortStatsTable 1 }

TmnxSubMgmtPwPortStatsEntry ::= SEQUENCE {
        tmnxSubMgmtPwPortSIpcp           Counter32,
        tmnxSubMgmtPwPortSIpcpPk         Counter32,
        tmnxSubMgmtPwPortSL2tpHost       Counter32,
        tmnxSubMgmtPwPortSL2tpHostPk     Counter32,
        tmnxSubMgmtPwPortSDhcp           Counter32,
        tmnxSubMgmtPwPortSDhcpPk         Counter32,
        tmnxSubMgmtPwPortSArp            Counter32,
        tmnxSubMgmtPwPortSArpPk          Counter32,
        tmnxSubMgmtPwPortSStatic         Counter32,
        tmnxSubMgmtPwPortSStaticPk       Counter32,
        tmnxSubMgmtPwPortSNonSub         Counter32,
        tmnxSubMgmtPwPortSNonSubPk       Counter32,
        tmnxSubMgmtPwPortSPppSlaac       Counter32,
        tmnxSubMgmtPwPortSPppSlaacPk     Counter32,
        tmnxSubMgmtPwPortSPppDhcp6Pd     Counter32,
        tmnxSubMgmtPwPortSPppDhcp6PdPk   Counter32,
        tmnxSubMgmtPwPortSPppDhcp6Na     Counter32,
        tmnxSubMgmtPwPortSPppDhcp6NaPk   Counter32,
        tmnxSubMgmtPwPortSIpoeSlaac      Counter32,
        tmnxSubMgmtPwPortSIpoeSlaacPk    Counter32,
        tmnxSubMgmtPwPortSIpoeDhcp6Pd    Counter32,
        tmnxSubMgmtPwPortSIpoeDhcp6PdPk  Counter32,
        tmnxSubMgmtPwPortSIpoeDhcp6Na    Counter32,
        tmnxSubMgmtPwPortSIpoeDhcp6NaPk  Counter32,
        tmnxSubMgmtPwPortSV4             Counter32,
        tmnxSubMgmtPwPortSV4Pk           Counter32,
        tmnxSubMgmtPwPortSV6             Counter32,
        tmnxSubMgmtPwPortSV6Pk           Counter32,
        tmnxSubMgmtPwPortSPppHosts       Counter32,
        tmnxSubMgmtPwPortSPppHostsPk     Counter32,
        tmnxSubMgmtPwPortSIpoeHosts      Counter32,
        tmnxSubMgmtPwPortSIpoeHostsPk    Counter32,
        tmnxSubMgmtPwPortSTotal          Counter32,
        tmnxSubMgmtPwPortSTotalPk        Counter32,
        tmnxSubMgmtPwPortSPppLclOE       Counter32,
        tmnxSubMgmtPwPortSPppLclOEPk     Counter32,
        tmnxSubMgmtPwPortSPppLclOEOA     Counter32,
        tmnxSubMgmtPwPortSPppLclOEOAPk   Counter32,
        tmnxSubMgmtPwPortSPppLclOA       Counter32,
        tmnxSubMgmtPwPortSPppLclOAPk     Counter32,
        tmnxSubMgmtPwPortSPppLclL2tp     Counter32,
        tmnxSubMgmtPwPortSPppLclL2tpPk   Counter32,
        tmnxSubMgmtPwPortSPppLclTotal    Counter32,
        tmnxSubMgmtPwPortSPppLclTotalPk  Counter32,
        tmnxSubMgmtPwPortSPppLacOE       Counter32,
        tmnxSubMgmtPwPortSPppLacOEPk     Counter32,
        tmnxSubMgmtPwPortSPppLacOEOA     Counter32,
        tmnxSubMgmtPwPortSPppLacOEOAPk   Counter32,
        tmnxSubMgmtPwPortSPppLacOA       Counter32,
        tmnxSubMgmtPwPortSPppLacOAPk     Counter32,
        tmnxSubMgmtPwPortSPppLacL2tp     Counter32,
        tmnxSubMgmtPwPortSPppLacL2tpPk   Counter32,
        tmnxSubMgmtPwPortSPppLacTotal    Counter32,
        tmnxSubMgmtPwPortSPppLacTotalPk  Counter32,
        tmnxSubMgmtPwPortSPppSessIs      Counter32,
        tmnxSubMgmtPwPortSPppSessIsPk    Counter32,
        tmnxSubMgmtPwPortSPppSessTotal   Counter32,
        tmnxSubMgmtPwPortSPppSessTotalPk Counter32,
        tmnxSubMgmtPwPortSSubscribers    Counter32,
        tmnxSubMgmtPwPortSSubscribersPk  Counter32,
        tmnxSubMgmtPwPortSDhcpBsmAs      Counter32,
        tmnxSubMgmtPwPortSDhcpBsmAsPk    Counter32,
        tmnxSubMgmtPwPortSStaticBsmAs    Counter32,
        tmnxSubMgmtPwPortSStaticBsmAsPk  Counter32,
        tmnxSubMgmtPwPortSDhcpBsm        Counter32,
        tmnxSubMgmtPwPortSDhcpBsmPk      Counter32,
        tmnxSubMgmtPwPortSStaticBsm      Counter32,
        tmnxSubMgmtPwPortSStaticBsmPk    Counter32,
        tmnxSubMgmtPwPortSPppDhcp6Mr     Counter32,
        tmnxSubMgmtPwPortSPppDhcp6MrPk   Counter32,
        tmnxSubMgmtPwPortSIpoeDhcp6Mr    Counter32,
        tmnxSubMgmtPwPortSIpoeDhcp6MrPk  Counter32,
        tmnxSubMgmtPwPortSV6StaticWan    Counter32,
        tmnxSubMgmtPwPortSV6StaticWanPk  Counter32,
        tmnxSubMgmtPwPortSBsmDhcp6Pd     Counter32,
        tmnxSubMgmtPwPortSBsmDhcp6PdPk   Counter32,
        tmnxSubMgmtPwPortSBsmDhcp6Na     Counter32,
        tmnxSubMgmtPwPortSBsmDhcp6NaPk   Counter32,
        tmnxSubMgmtPwPortSTotInternal    Counter32,
        tmnxSubMgmtPwPortSTotInternalPk  Counter32,
        tmnxSubMgmtPwPortSTotDhcp        Counter32,
        tmnxSubMgmtPwPortSTotDhcpPk      Counter32,
        tmnxSubMgmtPwPortSTotDhcpV6      Counter32,
        tmnxSubMgmtPwPortSTotDhcpV6Pk    Counter32,
        tmnxSubMgmtPwPortSTotMngdRt      Counter32,
        tmnxSubMgmtPwPortSTotMngdRtPk    Counter32,
        tmnxSubMgmtPwPortSIpoeSesIs      Counter32,
        tmnxSubMgmtPwPortSIpoeSesIsPk    Counter32,
        tmnxSubMgmtPwPortSIpoeSesTotal   Counter32,
        tmnxSubMgmtPwPortSIpoeSesTotalPk Counter32,
        tmnxSubMgmtPwPortSV6StaticPd     Counter32,
        tmnxSubMgmtPwPortSV6StaticPdPk   Counter32
    }

tmnxSubMgmtPwPortSIpcp OBJECT-TYPE
    SYNTAX          Counter32
    MAX-ACCESS      read-only
    STATUS          current
    DESCRIPTION     "The value of tmnxSubMgmtPwPortSIpcp indicates the number
                     of current PPP hosts (IPCP) on this PW-port."
    ::= { tmnxSubMgmtPwPortStatsEntry 1 }

tmnxSubMgmtPwPortSIpcpPk OBJECT-TYPE
    SYNTAX          Counter32
    MAX-ACCESS      read-only
    STATUS          current
    DESCRIPTION     "The value of tmnxSubMgmtPwPortSIpcpPk indicates the peak
                     number of PPP hosts (IPCP) on this PW-port."
    ::= { tmnxSubMgmtPwPortStatsEntry 2 }

tmnxSubMgmtPwPortSL2tpHost OBJECT-TYPE
    SYNTAX          Counter32
    MAX-ACCESS      read-only
    STATUS          current
    DESCRIPTION     "The value of tmnxSubMgmtPwPortSL2tpHost indicates the number
                     of current L2TP hosts (LAC) on this PW-port."
    ::= { tmnxSubMgmtPwPortStatsEntry 3 }

tmnxSubMgmtPwPortSL2tpHostPk OBJECT-TYPE
    SYNTAX          Counter32
    MAX-ACCESS      read-only
    STATUS          current
    DESCRIPTION     "The value of tmnxSubMgmtPwPortSL2tpHostPk indicates the peak
                     number of L2TP hosts (LAC) on this PW-port."
    ::= { tmnxSubMgmtPwPortStatsEntry 4 }

tmnxSubMgmtPwPortSDhcp OBJECT-TYPE
    SYNTAX          Counter32
    MAX-ACCESS      read-only
    STATUS          current
    DESCRIPTION     "The value of tmnxSubMgmtPwPortSDhcp indicates the number
                     of current IPOE hosts (DHCP) on this PW-port."
    ::= { tmnxSubMgmtPwPortStatsEntry 5 }

tmnxSubMgmtPwPortSDhcpPk OBJECT-TYPE
    SYNTAX          Counter32
    MAX-ACCESS      read-only
    STATUS          current
    DESCRIPTION     "The value of tmnxSubMgmtPwPortSDhcpPk indicates the peak
                     number of IPOE hosts (DHCP) on this PW-port."
    ::= { tmnxSubMgmtPwPortStatsEntry 6 }

tmnxSubMgmtPwPortSArp OBJECT-TYPE
    SYNTAX          Counter32
    MAX-ACCESS      read-only
    STATUS          current
    DESCRIPTION     "The value of tmnxSubMgmtPwPortSArp indicates the number
                     of current IPOE hosts (ARP) on this PW-port."
    ::= { tmnxSubMgmtPwPortStatsEntry 7 }

tmnxSubMgmtPwPortSArpPk OBJECT-TYPE
    SYNTAX          Counter32
    MAX-ACCESS      read-only
    STATUS          current
    DESCRIPTION     "The value of tmnxSubMgmtPwPortSArpPk indicates the peak
                     number of IPOE hosts (ARP) on this PW-port."
    ::= { tmnxSubMgmtPwPortStatsEntry 8 }

tmnxSubMgmtPwPortSStatic OBJECT-TYPE
    SYNTAX          Counter32
    MAX-ACCESS      read-only
    STATUS          current
    DESCRIPTION     "The value of tmnxSubMgmtPwPortSStatic indicates the number
                     of current IPOE hosts (Static) on this PW-port."
    ::= { tmnxSubMgmtPwPortStatsEntry 9 }

tmnxSubMgmtPwPortSStaticPk OBJECT-TYPE
    SYNTAX          Counter32
    MAX-ACCESS      read-only
    STATUS          current
    DESCRIPTION     "The value of tmnxSubMgmtPwPortSStaticPk indicates the peak
                     number of IPOE hosts (Static) on this PW-port."
    ::= { tmnxSubMgmtPwPortStatsEntry 10 }

tmnxSubMgmtPwPortSNonSub OBJECT-TYPE
    SYNTAX          Counter32
    MAX-ACCESS      read-only
    STATUS          current
    DESCRIPTION     "The value of tmnxSubMgmtPwPortSNonSub indicates the number
                     of current Non Sub hosts on this PW-port."
    ::= { tmnxSubMgmtPwPortStatsEntry 11 }

tmnxSubMgmtPwPortSNonSubPk OBJECT-TYPE
    SYNTAX          Counter32
    MAX-ACCESS      read-only
    STATUS          current
    DESCRIPTION     "The value of tmnxSubMgmtPwPortSNonSubPk indicates the peak
                     number of Non Sub hosts on this PW-port."
    ::= { tmnxSubMgmtPwPortStatsEntry 12 }

tmnxSubMgmtPwPortSPppSlaac OBJECT-TYPE
    SYNTAX          Counter32
    MAX-ACCESS      read-only
    STATUS          current
    DESCRIPTION     "The value of tmnxSubMgmtPwPortSPppSlaac indicates the number
                     of current PPP hosts (SLAAC) on this PW-port."
    ::= { tmnxSubMgmtPwPortStatsEntry 13 }

tmnxSubMgmtPwPortSPppSlaacPk OBJECT-TYPE
    SYNTAX          Counter32
    MAX-ACCESS      read-only
    STATUS          current
    DESCRIPTION     "The value of tmnxSubMgmtPwPortSPppSlaacPk indicates the 
                     Pk number of PPP hosts (SLAAC) on this PW-port."
    ::= { tmnxSubMgmtPwPortStatsEntry 14 }

tmnxSubMgmtPwPortSPppDhcp6Pd OBJECT-TYPE
    SYNTAX          Counter32
    MAX-ACCESS      read-only
    STATUS          current
    DESCRIPTION     "The value of tmnxSubMgmtPwPortSPppDhcp6Pd indicates the number
                     of current PPP hosts (DHCP6 PD) on this PW-port."
    ::= { tmnxSubMgmtPwPortStatsEntry 15 }

tmnxSubMgmtPwPortSPppDhcp6PdPk OBJECT-TYPE
    SYNTAX          Counter32
    MAX-ACCESS      read-only
    STATUS          current
    DESCRIPTION     "The value of tmnxSubMgmtPwPortSPppDhcp6PdPk indicates the 
                     Pk number of PPP hosts (DHCP6 PD) on this PW-port."
    ::= { tmnxSubMgmtPwPortStatsEntry 16 }

tmnxSubMgmtPwPortSPppDhcp6Na OBJECT-TYPE
    SYNTAX          Counter32
    MAX-ACCESS      read-only
    STATUS          current
    DESCRIPTION     "The value of tmnxSubMgmtPwPortSPppDhcp6Na indicates the number
                     of current PPP hosts (DHCP6 NA) on this PW-port."
    ::= { tmnxSubMgmtPwPortStatsEntry 17 }

tmnxSubMgmtPwPortSPppDhcp6NaPk OBJECT-TYPE
    SYNTAX          Counter32
    MAX-ACCESS      read-only
    STATUS          current
    DESCRIPTION     "The value of tmnxSubMgmtPwPortSPppDhcp6NaPk indicates the 
                     Pk number of PPP hosts (DHCP6 NA) on this PW-port."
    ::= { tmnxSubMgmtPwPortStatsEntry 18 }

tmnxSubMgmtPwPortSIpoeSlaac OBJECT-TYPE
    SYNTAX          Counter32
    MAX-ACCESS      read-only
    STATUS          current
    DESCRIPTION     "The value of tmnxSubMgmtPwPortSIpoeSlaac indicates the 
                     number of current IPOE hosts (SLAAC) on this PW-port."
    ::= { tmnxSubMgmtPwPortStatsEntry 19 }

tmnxSubMgmtPwPortSIpoeSlaacPk OBJECT-TYPE
    SYNTAX          Counter32
    MAX-ACCESS      read-only
    STATUS          current
    DESCRIPTION     "The value of tmnxSubMgmtPwPortSIpoeSlaacPk indicates the 
                     Pk number of IPOE hosts (SLAAC) on this PW-port."
    ::= { tmnxSubMgmtPwPortStatsEntry 20 }

tmnxSubMgmtPwPortSIpoeDhcp6Pd OBJECT-TYPE
    SYNTAX          Counter32
    MAX-ACCESS      read-only
    STATUS          current
    DESCRIPTION     "The value of tmnxSubMgmtPwPortSIpoeDhcp6Pd indicates the 
                     number of current IPOE hosts (DHCP6 PD) on this PW-port."
    ::= { tmnxSubMgmtPwPortStatsEntry 21 }

tmnxSubMgmtPwPortSIpoeDhcp6PdPk OBJECT-TYPE
    SYNTAX          Counter32
    MAX-ACCESS      read-only
    STATUS          current
    DESCRIPTION     "The value of tmnxSubMgmtPwPortSIpoeDhcp6PdPk indicates the 
                     Pk number of IPOE hosts (DHCP6 PD) on this PW-port."
    ::= { tmnxSubMgmtPwPortStatsEntry 22 }

tmnxSubMgmtPwPortSIpoeDhcp6Na OBJECT-TYPE
    SYNTAX          Counter32
    MAX-ACCESS      read-only
    STATUS          current
    DESCRIPTION     "The value of tmnxSubMgmtPwPortSIpoeDhcp6Na indicates the 
                     number of current IPOE hosts (DHCP6 NA) on this PW-port."
    ::= { tmnxSubMgmtPwPortStatsEntry 23 }

tmnxSubMgmtPwPortSIpoeDhcp6NaPk OBJECT-TYPE
    SYNTAX          Counter32
    MAX-ACCESS      read-only
    STATUS          current
    DESCRIPTION     "The value of tmnxSubMgmtPwPortSIpoeDhcp6NaPk indicates the 
                     Pk number of IPOE hosts (DHCP6 NA) on this PW-port."
    ::= { tmnxSubMgmtPwPortStatsEntry 24 }

tmnxSubMgmtPwPortSV4 OBJECT-TYPE
    SYNTAX          Counter32
    MAX-ACCESS      read-only
    STATUS          current
    DESCRIPTION     "The value of tmnxSubMgmtPwPortSV4 indicates the number
                     of current V4 hosts on this PW-port."
    ::= { tmnxSubMgmtPwPortStatsEntry 25 }

tmnxSubMgmtPwPortSV4Pk OBJECT-TYPE
    SYNTAX          Counter32
    MAX-ACCESS      read-only
    STATUS          current
    DESCRIPTION     "The value of tmnxSubMgmtPwPortSV4Pk indicates the peak
                     number of V4 hosts on this PW-port."
    ::= { tmnxSubMgmtPwPortStatsEntry 26 }

tmnxSubMgmtPwPortSV6 OBJECT-TYPE
    SYNTAX          Counter32
    MAX-ACCESS      read-only
    STATUS          current
    DESCRIPTION     "The value of tmnxSubMgmtPwPortSV6 indicates the number
                     of current V6 hosts on this PW-port."
    ::= { tmnxSubMgmtPwPortStatsEntry 27 }

tmnxSubMgmtPwPortSV6Pk OBJECT-TYPE
    SYNTAX          Counter32
    MAX-ACCESS      read-only
    STATUS          current
    DESCRIPTION     "The value of tmnxSubMgmtPwPortSV6Pk indicates the peak
                     number of V6 hosts on this PW-port."
    ::= { tmnxSubMgmtPwPortStatsEntry 28 }

tmnxSubMgmtPwPortSPppHosts OBJECT-TYPE
    SYNTAX          Counter32
    MAX-ACCESS      read-only
    STATUS          current
    DESCRIPTION     "The value of tmnxSubMgmtPwPortSPppHosts indicates the 
                     number of current PPP hosts on this PW-port."
    ::= { tmnxSubMgmtPwPortStatsEntry 29 }

tmnxSubMgmtPwPortSPppHostsPk OBJECT-TYPE
    SYNTAX          Counter32
    MAX-ACCESS      read-only
    STATUS          current
    DESCRIPTION     "The value of tmnxSubMgmtPwPortSPppHostsPk indicates the
                     Pk number of PPP hosts on this PW-port."
    ::= { tmnxSubMgmtPwPortStatsEntry 30 }

tmnxSubMgmtPwPortSIpoeHosts OBJECT-TYPE
    SYNTAX          Counter32
    MAX-ACCESS      read-only
    STATUS          current
    DESCRIPTION     "The value of tmnxSubMgmtPwPortSIpoeHosts indicates the 
                     number of current IPOE hosts on this PW-port."
    ::= { tmnxSubMgmtPwPortStatsEntry 31 }

tmnxSubMgmtPwPortSIpoeHostsPk OBJECT-TYPE
    SYNTAX          Counter32
    MAX-ACCESS      read-only
    STATUS          current
    DESCRIPTION     "The value of tmnxSubMgmtPwPortSIpoeHostsPk indicates the
                     Pk number of IPOE hosts on this PW-port."
    ::= { tmnxSubMgmtPwPortStatsEntry 32 }

tmnxSubMgmtPwPortSTotal OBJECT-TYPE
    SYNTAX          Counter32
    MAX-ACCESS      read-only
    STATUS          current
    DESCRIPTION     "The value of tmnxSubMgmtPwPortSTotal indicates the number
                     of current total hosts on this PW-port."
    ::= { tmnxSubMgmtPwPortStatsEntry 33 }

tmnxSubMgmtPwPortSTotalPk OBJECT-TYPE
    SYNTAX          Counter32
    MAX-ACCESS      read-only
    STATUS          current
    DESCRIPTION     "The value of tmnxSubMgmtPwPortSTotalPk indicates the peak
                     number of total hosts on this PW-port."
    ::= { tmnxSubMgmtPwPortStatsEntry 34 }

tmnxSubMgmtPwPortSPppLclOE OBJECT-TYPE
    SYNTAX          Counter32
    MAX-ACCESS      read-only
    STATUS          current
    DESCRIPTION     "The value of tmnxSubMgmtPwPortSPppLclOE indicates the
                     number of current locally terminated PPP sessions (PPPoE)
                     on this PW-port."
    ::= { tmnxSubMgmtPwPortStatsEntry 35 }

tmnxSubMgmtPwPortSPppLclOEPk OBJECT-TYPE
    SYNTAX          Counter32
    MAX-ACCESS      read-only
    STATUS          current
    DESCRIPTION     "The value of tmnxSubMgmtPwPortSPppLclOEPk indicates the 
                     Pk number of locally terminated PPP sessions (PPPoE) 
                     on this PW-port."
    ::= { tmnxSubMgmtPwPortStatsEntry 36 }

tmnxSubMgmtPwPortSPppLclOEOA OBJECT-TYPE
    SYNTAX          Counter32
    MAX-ACCESS      read-only
    STATUS          current
    DESCRIPTION     "The value of tmnxSubMgmtPwPortSPppLclOEOA indicates the 
                     number of current locally terminated PPP sessions (PPPoEoA)
                     on this PW-port."
    ::= { tmnxSubMgmtPwPortStatsEntry 37 }

tmnxSubMgmtPwPortSPppLclOEOAPk OBJECT-TYPE
    SYNTAX          Counter32
    MAX-ACCESS      read-only
    STATUS          current
    DESCRIPTION     "The value of tmnxSubMgmtPwPortSPppLclOEOAPk indicates the 
                     Pk number of locally terminated PPP sessions (PPPoEoA) 
                     on this PW-port."
    ::= { tmnxSubMgmtPwPortStatsEntry 38 }

tmnxSubMgmtPwPortSPppLclOA OBJECT-TYPE
    SYNTAX          Counter32
    MAX-ACCESS      read-only
    STATUS          current
    DESCRIPTION     "The value of tmnxSubMgmtPwPortSPppLclOA indicates the number
                     of current locally terminated PPP sessions (PPPoA)
                     on this PW-port."
    ::= { tmnxSubMgmtPwPortStatsEntry 39 }

tmnxSubMgmtPwPortSPppLclOAPk OBJECT-TYPE
    SYNTAX          Counter32
    MAX-ACCESS      read-only
    STATUS          current
    DESCRIPTION     "The value of tmnxSubMgmtPwPortSPppLclOAPk indicates the 
                     Pk number of locally terminated PPP sessions (PPPoA) 
                     on this PW-port."
    ::= { tmnxSubMgmtPwPortStatsEntry 40 }

tmnxSubMgmtPwPortSPppLclL2tp OBJECT-TYPE
    SYNTAX          Counter32
    MAX-ACCESS      read-only
    STATUS          current
    DESCRIPTION     "The value of tmnxSubMgmtPwPortSPppLclL2tp indicates the 
                     number of current locally terminated PPP sessions (L2TP LNS)
                     on this PW-port."
    ::= { tmnxSubMgmtPwPortStatsEntry 41 }
    
tmnxSubMgmtPwPortSPppLclL2tpPk OBJECT-TYPE
    SYNTAX          Counter32
    MAX-ACCESS      read-only
    STATUS          current
    DESCRIPTION     "The value of tmnxSubMgmtPwPortSPppLclL2tpPk indicates the 
                     Pk number of locally terminated PPP sessions (L2TP LNS)
                     on this PW-port."
    ::= { tmnxSubMgmtPwPortStatsEntry 42 }

tmnxSubMgmtPwPortSPppLclTotal OBJECT-TYPE
    SYNTAX          Counter32
    MAX-ACCESS      read-only
    STATUS          current
    DESCRIPTION     "The value of tmnxSubMgmtPwPortSPppLclTotal indicates the 
                     total number of current locally terminated PPP sessions
                     on this PW-port."
    ::= { tmnxSubMgmtPwPortStatsEntry 43 }

tmnxSubMgmtPwPortSPppLclTotalPk OBJECT-TYPE
    SYNTAX          Counter32
    MAX-ACCESS      read-only
    STATUS          current
    DESCRIPTION     "The value of tmnxSubMgmtPwPortSPppLclTotalPk indicates the 
                     total Pk number of locally terminated PPP sessions
                     on this PW-port."
    ::= { tmnxSubMgmtPwPortStatsEntry 44 }

tmnxSubMgmtPwPortSPppLacOE OBJECT-TYPE
    SYNTAX          Counter32
    MAX-ACCESS      read-only
    STATUS          current
    DESCRIPTION     "The value of tmnxSubMgmtPwPortSPppLacOE indicates the
                     number of current PPP sessions (PPPoE) tunneled over L2TP 
                     on this PW-port."
    ::= { tmnxSubMgmtPwPortStatsEntry 45 }

tmnxSubMgmtPwPortSPppLacOEPk OBJECT-TYPE
    SYNTAX          Counter32
    MAX-ACCESS      read-only
    STATUS          current
    DESCRIPTION     "The value of tmnxSubMgmtPwPortSPppLacOEPk indicates the 
                     Pk number of PPP sessions (PPPoE) tunneled over L2TP 
                     on this PW-port."
    ::= { tmnxSubMgmtPwPortStatsEntry 46 }

tmnxSubMgmtPwPortSPppLacOEOA OBJECT-TYPE
    SYNTAX          Counter32
    MAX-ACCESS      read-only
    STATUS          current
    DESCRIPTION     "The value of tmnxSubMgmtPwPortSPppLacOEOA indicates the 
                     number of current PPP sessions (PPPoEoA) tunneled over L2TP 
                     on this PW-port."
    ::= { tmnxSubMgmtPwPortStatsEntry 47 }

tmnxSubMgmtPwPortSPppLacOEOAPk OBJECT-TYPE
    SYNTAX          Counter32
    MAX-ACCESS      read-only
    STATUS          current
    DESCRIPTION     "The value of tmnxSubMgmtPwPortSPppLacOEOAPk indicates the 
                     Pk number of PPP sessions (PPPoEoA) tunneled over L2TP 
                     on this PW-port."
    ::= { tmnxSubMgmtPwPortStatsEntry 48 }

tmnxSubMgmtPwPortSPppLacOA OBJECT-TYPE
    SYNTAX          Counter32
    MAX-ACCESS      read-only
    STATUS          current
    DESCRIPTION     "The value of tmnxSubMgmtPwPortSPppLacOA indicates the 
                     number of current PPP sessions (PPPoA) tunneled over L2TP 
                     on this PW-port."
    ::= { tmnxSubMgmtPwPortStatsEntry 49 }

tmnxSubMgmtPwPortSPppLacOAPk OBJECT-TYPE
    SYNTAX          Counter32
    MAX-ACCESS      read-only
    STATUS          current
    DESCRIPTION     "The value of tmnxSubMgmtPwPortSPppLacOAPk indicates the 
                     Pk number of PPP sessions (PPPoA) tunneled over L2TP
                     on this PW-port."
    ::= { tmnxSubMgmtPwPortStatsEntry 50 }

tmnxSubMgmtPwPortSPppLacL2tp OBJECT-TYPE
    SYNTAX          Counter32
    MAX-ACCESS      read-only
    STATUS          current
    DESCRIPTION     "The value of tmnxSubMgmtPwPortSPppLacL2tp indicates the 
                     number of current PPP sessions (L2TP LTS) tunneled over L2TP
                     on this PW-port."
    ::= { tmnxSubMgmtPwPortStatsEntry 51 }

tmnxSubMgmtPwPortSPppLacL2tpPk OBJECT-TYPE
    SYNTAX          Counter32
    MAX-ACCESS      read-only
    STATUS          current
    DESCRIPTION     "The value of tmnxSubMgmtPwPortSPppLacL2tpPk indicates the 
                     Pk number of PPP sessions (L2TP LTS) tunneled over L2TP 
                     on this PW-port."
    ::= { tmnxSubMgmtPwPortStatsEntry 52 }

tmnxSubMgmtPwPortSPppLacTotal OBJECT-TYPE
    SYNTAX          Counter32
    MAX-ACCESS      read-only
    STATUS          current
    DESCRIPTION     "The value of tmnxSubMgmtPwPortSPppLacTotal indicates the 
                     total number of current PPP sessions tunneled over L2TP
                     on this PW-port."
    ::= { tmnxSubMgmtPwPortStatsEntry 53 }

tmnxSubMgmtPwPortSPppLacTotalPk OBJECT-TYPE
    SYNTAX          Counter32
    MAX-ACCESS      read-only
    STATUS          current
    DESCRIPTION     "The value of tmnxSubMgmtPwPortSPppLacTotalPk indicates the 
                     total Pk number of PPP sessions tunneled over L2TP 
                     on this PW-port."
    ::= { tmnxSubMgmtPwPortStatsEntry 54 }

tmnxSubMgmtPwPortSPppSessIs OBJECT-TYPE
    SYNTAX          Counter32
    MAX-ACCESS      read-only
    STATUS          current
    DESCRIPTION     "The value of tmnxSubMgmtPwPortSPppSessIs indicates the 
                     number of current PPP sessions in setup on this PW-port."
    ::= { tmnxSubMgmtPwPortStatsEntry 55 }

tmnxSubMgmtPwPortSPppSessIsPk OBJECT-TYPE
    SYNTAX          Counter32
    MAX-ACCESS      read-only
    STATUS          current
    DESCRIPTION     "The value of tmnxSubMgmtPwPortSPppSessIsPk indicates the 
                     Pk number of PPP sessions in setup on this PW-port."
    ::= { tmnxSubMgmtPwPortStatsEntry 56 }

tmnxSubMgmtPwPortSPppSessTotal OBJECT-TYPE
    SYNTAX          Counter32
    MAX-ACCESS      read-only
    STATUS          current
    DESCRIPTION     "The value of tmnxSubMgmtPwPortSPppSessTotal indicates the 
                     total number of current PPP sessions established on this PW-port."
    ::= { tmnxSubMgmtPwPortStatsEntry 57 }

tmnxSubMgmtPwPortSPppSessTotalPk OBJECT-TYPE
    SYNTAX          Counter32
    MAX-ACCESS      read-only
    STATUS          current
    DESCRIPTION     "The value of tmnxSubMgmtPwPortSPppSessTotalPk indicates the 
                     total Pk number of PPP sessions established on this PW-port."
    ::= { tmnxSubMgmtPwPortStatsEntry 58 }

tmnxSubMgmtPwPortSSubscribers OBJECT-TYPE
    SYNTAX          Counter32
    MAX-ACCESS      read-only
    STATUS          current
    DESCRIPTION     "The value of tmnxSubMgmtPwPortSSubscribers indicates the number
                     of current subscribers on this PW-port."
    ::= { tmnxSubMgmtPwPortStatsEntry 59 }

tmnxSubMgmtPwPortSSubscribersPk OBJECT-TYPE
    SYNTAX          Counter32
    MAX-ACCESS      read-only
    STATUS          current
    DESCRIPTION     "The value of tmnxSubMgmtPwPortSSubscribersPk indicates the peak
                     number of subscribers on this PW-port."
    ::= { tmnxSubMgmtPwPortStatsEntry 60 }

tmnxSubMgmtPwPortSDhcpBsmAs OBJECT-TYPE
    SYNTAX          Counter32
    MAX-ACCESS      read-only
    STATUS          current
    DESCRIPTION     "The value of tmnxSubMgmtPwPortSDhcpBsmAs indicates the number
                     of current IPOE BSM hosts with antispoof (DHCP) on this PW-port."
    ::= { tmnxSubMgmtPwPortStatsEntry 61 }

tmnxSubMgmtPwPortSDhcpBsmAsPk OBJECT-TYPE
    SYNTAX          Counter32
    MAX-ACCESS      read-only
    STATUS          current
    DESCRIPTION     "The value of tmnxSubMgmtPwPortSDhcpBsmAsPk indicates the peak
                     number of IPOE BSM hosts with antispoof (DHCP) on this PW-port."
    ::= { tmnxSubMgmtPwPortStatsEntry 62 }

tmnxSubMgmtPwPortSStaticBsmAs OBJECT-TYPE
    SYNTAX          Counter32
    MAX-ACCESS      read-only
    STATUS          current
    DESCRIPTION     "The value of tmnxSubMgmtPwPortSStaticBsmAs indicates the number
                     of current IPOE BSM static hosts with antispoof on this PW-port."
    ::= { tmnxSubMgmtPwPortStatsEntry 63 }

tmnxSubMgmtPwPortSStaticBsmAsPk OBJECT-TYPE
    SYNTAX          Counter32
    MAX-ACCESS      read-only
    STATUS          current
    DESCRIPTION     "The value of tmnxSubMgmtPwPortSStaticBsmAsPk indicates the peak
                     number of IPOE BSM static hosts with antispoof on this PW-port."
    ::= { tmnxSubMgmtPwPortStatsEntry 64 }

tmnxSubMgmtPwPortSDhcpBsm OBJECT-TYPE
    SYNTAX          Counter32
    MAX-ACCESS      read-only
    STATUS          current
    DESCRIPTION     "The value of tmnxSubMgmtPwPortSDhcpBsm indicates the number
                     of current IPOE BSM hosts (DHCP) on this PW-port."
    ::= { tmnxSubMgmtPwPortStatsEntry 65 }

tmnxSubMgmtPwPortSDhcpBsmPk OBJECT-TYPE
    SYNTAX          Counter32
    MAX-ACCESS      read-only
    STATUS          current
    DESCRIPTION     "The value of tmnxSubMgmtPwPortSDhcpBsmPk indicates the peak
                     number of IPOE BSM hosts (DHCP) on this PW-port."
    ::= { tmnxSubMgmtPwPortStatsEntry 66 }

tmnxSubMgmtPwPortSStaticBsm OBJECT-TYPE
    SYNTAX          Counter32
    MAX-ACCESS      read-only
    STATUS          current
    DESCRIPTION     "The value of tmnxSubMgmtPwPortSStaticBsm indicates the number
                     of current IPOE BSM static hosts on this PW-port."
    ::= { tmnxSubMgmtPwPortStatsEntry 67 }

tmnxSubMgmtPwPortSStaticBsmPk OBJECT-TYPE
    SYNTAX          Counter32
    MAX-ACCESS      read-only
    STATUS          current
    DESCRIPTION     "The value of tmnxSubMgmtPwPortSStaticBsmPk indicates the peak
                     number of IPOE BSM static hosts on this PW-port."
    ::= { tmnxSubMgmtPwPortStatsEntry 68 }

tmnxSubMgmtPwPortSPppDhcp6Mr OBJECT-TYPE
    SYNTAX          Counter32
    MAX-ACCESS      read-only
    STATUS          current
    DESCRIPTION     "The value of tmnxSubMgmtPwPortSPppDhcp6Mr indicates the number
                     of current PPP PD Managed Routes on this PW-port."
    ::= { tmnxSubMgmtPwPortStatsEntry 69 }

tmnxSubMgmtPwPortSPppDhcp6MrPk OBJECT-TYPE
    SYNTAX          Counter32
    MAX-ACCESS      read-only
    STATUS          current
    DESCRIPTION     "The value of tmnxSubMgmtPwPortSPppDhcp6MrPk indicates the peak
                     number of PPP PD Managed Routes on this PW-port."
    ::= { tmnxSubMgmtPwPortStatsEntry 70 }

tmnxSubMgmtPwPortSIpoeDhcp6Mr OBJECT-TYPE
    SYNTAX          Counter32
    MAX-ACCESS      read-only
    STATUS          current
    DESCRIPTION     "The value of tmnxSubMgmtPwPortSIpoeDhcp6Mr indicates the number
                     of current IPOE PD Managed Routes on this PW-port."
    ::= { tmnxSubMgmtPwPortStatsEntry 71 }

tmnxSubMgmtPwPortSIpoeDhcp6MrPk OBJECT-TYPE
    SYNTAX          Counter32
    MAX-ACCESS      read-only
    STATUS          current
    DESCRIPTION     "The value of tmnxSubMgmtPwPortSIpoeDhcp6MrPk indicates the peak
                     number of IPOE PD Managed Routes on this PW-port."
    ::= { tmnxSubMgmtPwPortStatsEntry 72 }

tmnxSubMgmtPwPortSV6StaticWan OBJECT-TYPE
    SYNTAX          Counter32
    MAX-ACCESS      read-only
    STATUS          current
    DESCRIPTION     "The value of tmnxSubMgmtPwPortSV6StaticWan indicates the number
                     of current IPOE IPv6 static WAN hosts on this PW-port."
    ::= { tmnxSubMgmtPwPortStatsEntry 73 }

tmnxSubMgmtPwPortSV6StaticWanPk OBJECT-TYPE
    SYNTAX          Counter32
    MAX-ACCESS      read-only
    STATUS          current
    DESCRIPTION     "The value of tmnxSubMgmtPwPortSV6StaticWanPk indicates the peak
                     number of IPOE IPv6 static WAN hosts on this PW-port."
    ::= { tmnxSubMgmtPwPortStatsEntry 74 }

tmnxSubMgmtPwPortSBsmDhcp6Pd OBJECT-TYPE
    SYNTAX          Counter32
    MAX-ACCESS      read-only
    STATUS          current
    DESCRIPTION     "The value of tmnxSubMgmtPwPortSBsmDhcp6Pd indicates the number
                     of current IPOE BSM hosts (DHCP6 PD) on this PW-port."
    ::= { tmnxSubMgmtPwPortStatsEntry 75 }

tmnxSubMgmtPwPortSBsmDhcp6PdPk OBJECT-TYPE
    SYNTAX          Counter32
    MAX-ACCESS      read-only
    STATUS          current
    DESCRIPTION     "The value of tmnxSubMgmtPwPortSBsmDhcp6PdPk indicates the 
                     peak number of IPOE BSM hosts (DHCP6 PD) on this PW-port."
    ::= { tmnxSubMgmtPwPortStatsEntry 76 }

tmnxSubMgmtPwPortSBsmDhcp6Na OBJECT-TYPE
    SYNTAX          Counter32
    MAX-ACCESS      read-only
    STATUS          current
    DESCRIPTION     "The value of tmnxSubMgmtPwPortSBsmDhcp6Na indicates the number
                     of current IPOE BSM hosts (DHCP6 NA) on this PW-port."
    ::= { tmnxSubMgmtPwPortStatsEntry 77 }

tmnxSubMgmtPwPortSBsmDhcp6NaPk OBJECT-TYPE
    SYNTAX          Counter32
    MAX-ACCESS      read-only
    STATUS          current
    DESCRIPTION     "The value of tmnxSubMgmtPwPortSBsmDhcp6NaPk indicates the 
                     peak number of IPOE BSM hosts (DHCP6 NA) on this PW-port."
    ::= { tmnxSubMgmtPwPortStatsEntry 78 }
 
tmnxSubMgmtPwPortSTotInternal OBJECT-TYPE
    SYNTAX          Counter32
    MAX-ACCESS      read-only
    STATUS          current
    DESCRIPTION     "The value of tmnxSubMgmtPwPortSTotInternal indicates the number
                     of current internal hosts on this PW-port."
    ::= { tmnxSubMgmtPwPortStatsEntry 79 }

tmnxSubMgmtPwPortSTotInternalPk OBJECT-TYPE
    SYNTAX          Counter32
    MAX-ACCESS      read-only
    STATUS          current
    DESCRIPTION     "The value of tmnxSubMgmtPwPortSTotInternalPk indicates the 
                     peak number of internal hosts on this PW-port."
    ::= { tmnxSubMgmtPwPortStatsEntry 80 }

tmnxSubMgmtPwPortSTotDhcp OBJECT-TYPE
    SYNTAX          Counter32
    MAX-ACCESS      read-only
    STATUS          current
    DESCRIPTION     "The value of tmnxSubMgmtPwPortSTotDhcp indicates the number
                     of current DHCP hosts on this PW-port."
    ::= { tmnxSubMgmtPwPortStatsEntry 81 }

tmnxSubMgmtPwPortSTotDhcpPk OBJECT-TYPE
    SYNTAX          Counter32
    MAX-ACCESS      read-only
    STATUS          current
    DESCRIPTION     "The value of tmnxSubMgmtPwPortSTotDhcpPk indicates the 
                     peak number of DHCP hosts on this PW-port."
    ::= { tmnxSubMgmtPwPortStatsEntry 82 }

tmnxSubMgmtPwPortSTotDhcpV6 OBJECT-TYPE
    SYNTAX          Counter32
    MAX-ACCESS      read-only
    STATUS          current
    DESCRIPTION     "The value of tmnxSubMgmtPwPortSTotDhcpV6 indicates the number
                     of current DHCPv6 hosts on this PW-port."
    ::= { tmnxSubMgmtPwPortStatsEntry 83 }

tmnxSubMgmtPwPortSTotDhcpV6Pk OBJECT-TYPE
    SYNTAX          Counter32
    MAX-ACCESS      read-only
    STATUS          current
    DESCRIPTION     "The value of tmnxSubMgmtPwPortSTotDhcpV6Pk indicates the 
                     peak number of DHCPv6 hosts on this PW-port."
    ::= { tmnxSubMgmtPwPortStatsEntry 84 }

tmnxSubMgmtPwPortSTotMngdRt OBJECT-TYPE
    SYNTAX          Counter32
    MAX-ACCESS      read-only
    STATUS          current
    DESCRIPTION     "The value of tmnxSubMgmtPwPortSTotMngdRt indicates the number
                     of current PD Managed Routes on this PW-port."
    ::= { tmnxSubMgmtPwPortStatsEntry 85 }

tmnxSubMgmtPwPortSTotMngdRtPk OBJECT-TYPE
    SYNTAX          Counter32
    MAX-ACCESS      read-only
    STATUS          current
    DESCRIPTION     "The value of tmnxSubMgmtPwPortSTotMngdRtPk indicates the 
                     peak number of PD Managed Routes on this PW-port."
    ::= { tmnxSubMgmtPwPortStatsEntry 86 }

tmnxSubMgmtPwPortSIpoeSesIs OBJECT-TYPE
    SYNTAX          Counter32
    MAX-ACCESS      read-only
    STATUS          current
    DESCRIPTION     "The value of tmnxSubMgmtPwPortSIpoeSesIs indicates the number
                     of current IPOE sessions in setup on this PW-port."
    ::= { tmnxSubMgmtPwPortStatsEntry 87 }

tmnxSubMgmtPwPortSIpoeSesIsPk OBJECT-TYPE
    SYNTAX          Counter32
    MAX-ACCESS      read-only
    STATUS          current
    DESCRIPTION     "The value of tmnxSubMgmtPwPortSIpoeSesIsPk indicates the 
                     peak number of IPOE sessions in setup on this PW-port."
    ::= { tmnxSubMgmtPwPortStatsEntry 88 }

tmnxSubMgmtPwPortSIpoeSesTotal OBJECT-TYPE
    SYNTAX          Counter32
    MAX-ACCESS      read-only
    STATUS          current
    DESCRIPTION     "The value of tmnxSubMgmtPwPortSIpoeSesTotal indicates the number
                     of current IPOE sessions on this PW-port."
    ::= { tmnxSubMgmtPwPortStatsEntry 89 }

tmnxSubMgmtPwPortSIpoeSesTotalPk OBJECT-TYPE
    SYNTAX          Counter32
    MAX-ACCESS      read-only
    STATUS          current
    DESCRIPTION     "The value of tmnxSubMgmtPwPortSIpoeSesTotalPk indicates the 
                     peak number of IPOE sessions on this PW-port."
    ::= { tmnxSubMgmtPwPortStatsEntry 90 }
 
tmnxSubMgmtPwPortSV6StaticPd OBJECT-TYPE
    SYNTAX          Counter32
    MAX-ACCESS      read-only
    STATUS          current
    DESCRIPTION     "The value of tmnxSubMgmtPwPortSV6StaticPd indicates the number
                     of current IPOE IPv6 static prefixes on this PW-port."
    ::= { tmnxSubMgmtPwPortStatsEntry 91 }

tmnxSubMgmtPwPortSV6StaticPdPk OBJECT-TYPE
    SYNTAX          Counter32
    MAX-ACCESS      read-only
    STATUS          current
    DESCRIPTION     "The value of tmnxSubMgmtPwPortSV6StaticPdPk indicates the peak
                     number of IPOE IPv6 static prefixes on this PW-port."
    ::= { tmnxSubMgmtPwPortStatsEntry 92 }

--
--  The Subscriber Lockout Host Table
--

tmnxSubLcktHostTable OBJECT-TYPE
    SYNTAX          SEQUENCE OF TmnxSubLcktHostEntry
    MAX-ACCESS      not-accessible
    STATUS          current
    DESCRIPTION     "A table that contains host lockout information."
    ::= { tmnxSubMgmtObjects 103 }

tmnxSubLcktHostEntry OBJECT-TYPE
    SYNTAX          TmnxSubLcktHostEntry
    MAX-ACCESS      not-accessible
    STATUS          current
    DESCRIPTION     "Information about a specific locked out host."
    INDEX           { sapPortId, 
                      sapEncapValue,
                      tmnxSubLcktHostId
                    }
    ::= { tmnxSubLcktHostTable 1 }

TmnxSubLcktHostEntry ::=
    SEQUENCE {
        tmnxSubLcktHostId                Unsigned32,
        tmnxSubLcktHostMacAddr           MacAddress,
        tmnxSubLcktHostCctId             OCTET STRING,
        tmnxSubLcktHostRemId             OCTET STRING,
        tmnxSubLcktHostResetTimeElapsed  Unsigned32,
        tmnxSubLcktHostLockTimeCurrent   Unsigned32,
        tmnxSubLcktHostLockTimeElapsed   Unsigned32,
        tmnxSubLcktHostLockTimeNext      Unsigned32,
        tmnxSubLcktHostNumLockouts       Unsigned32
    }

tmnxSubLcktHostId OBJECT-TYPE
SYNTAX          Unsigned32
    MAX-ACCESS      not-accessible
    STATUS          current
    DESCRIPTION     "The value of the object tmnxSubLcktHostId specifies
                     the ID of this locked out host."
    ::= { tmnxSubLcktHostEntry 1 }

tmnxSubLcktHostMacAddr OBJECT-TYPE
    SYNTAX          MacAddress
    MAX-ACCESS      read-only
    STATUS          current
    DESCRIPTION     "The value of the object tmnxSubLcktHostMacAddr specifies
                     the MAC address of this locked out host."
    DEFVAL { '000000000000'h }
    ::= { tmnxSubLcktHostEntry 2 }

tmnxSubLcktHostCctId OBJECT-TYPE
    SYNTAX          OCTET STRING (SIZE (0..256))
    MAX-ACCESS      read-only
    STATUS          current
    DESCRIPTION     "The value of tmnxSubLcktHostCctId indicates the
                     circuit-id of this locked out host."
    DEFVAL { ''H }
    ::= { tmnxSubLcktHostEntry 3 }

tmnxSubLcktHostRemId OBJECT-TYPE
    SYNTAX          OCTET STRING (SIZE (0..256))
    MAX-ACCESS      read-only
    STATUS          current
    DESCRIPTION     "The value of tmnxSubLcktHostRemId indicates the
                     remote-id of this locked out host."
    DEFVAL { ''H }
    ::= { tmnxSubLcktHostEntry 4 }

tmnxSubLcktHostResetTimeElapsed  OBJECT-TYPE
    SYNTAX          Unsigned32
    MAX-ACCESS      read-only
    STATUS          current
    DESCRIPTION     "The value of tmnxSubLcktHostResetTimeElapsed specifies
                     the elapsed reset time for this host."
    DEFVAL           { 0 }
    ::= { tmnxSubLcktHostEntry 5 }

tmnxSubLcktHostLockTimeCurrent  OBJECT-TYPE
    SYNTAX          Unsigned32
    MAX-ACCESS      read-only
    STATUS          current
    DESCRIPTION     "The value of tmnxSubLcktHostLockTimeCurrent specifies
                     the current lockout time for this host."
    DEFVAL           { 0 }
    ::= { tmnxSubLcktHostEntry 6 }

tmnxSubLcktHostLockTimeElapsed  OBJECT-TYPE
    SYNTAX          Unsigned32
    MAX-ACCESS      read-only
    STATUS          current
    DESCRIPTION     "The value of tmnxSubLcktHostLockTimeElapsed specifies
                     the locktime elapsed for this host."
    DEFVAL           { 0 }
    ::= { tmnxSubLcktHostEntry 7 }

tmnxSubLcktHostLockTimeNext  OBJECT-TYPE
    SYNTAX          Unsigned32
    MAX-ACCESS      read-only
    STATUS          current
    DESCRIPTION     "The value of tmnxSubLcktHostLockTimeNext specifies
                     the next lock time for this host."
    DEFVAL           { 0 }
    ::= { tmnxSubLcktHostEntry 8 }

tmnxSubLcktHostNumLockouts  OBJECT-TYPE
    SYNTAX          Unsigned32
    MAX-ACCESS      read-only
    STATUS          current
    DESCRIPTION     "The value of tmnxSubLcktHostNumLockouts specifies
                     the number of lockouts for this host."
    DEFVAL           { 0 }
    ::= { tmnxSubLcktHostEntry 9 }

--
--  The IGMP Host Mcac Policy Table
--

tmnxSubMcacPlcyTable OBJECT-TYPE
    SYNTAX     SEQUENCE OF TmnxSubMcacPlcyEntry
    MAX-ACCESS not-accessible
    STATUS     current
    DESCRIPTION
        "The table listing the subscriber MCAC policies."
    ::= { tmnxSubIgmpHostObjs 6 }

tmnxSubMcacPlcyEntry OBJECT-TYPE
    SYNTAX     TmnxSubMcacPlcyEntry
    MAX-ACCESS not-accessible
    STATUS     current
    DESCRIPTION
        "Each row entry in the tmnxSubMcacPlcyTable represents a 
         subscriber MCAC policy."
    INDEX      { tmnxSubMcacPlcyName }
    ::= { tmnxSubMcacPlcyTable 1 }

TmnxSubMcacPlcyEntry ::= SEQUENCE {
    tmnxSubMcacPlcyName              TNamedItem,
    tmnxSubMcacPlcyRowStatus         RowStatus,
    tmnxSubMcacPlcyDescription       TItemDescription,
    tmnxSubMcacPlcyAdminState        TmnxAdminState,
    tmnxSubMcacPlcyUnconstrainedBW   Integer32,
    tmnxSubMcacPlcyPreRsvdMandBW     Integer32,
    tmnxSubMcacPlcyLastMgmtChange    TimeStamp
    }

tmnxSubMcacPlcyName       OBJECT-TYPE
    SYNTAX      TNamedItem
    MAX-ACCESS  not-accessible
    STATUS      current
    DESCRIPTION
        "The value of tmnxSubMcacPlcyName indicates the name of the
         subscriber MCAC policy."
    ::= { tmnxSubMcacPlcyEntry 1 }

tmnxSubMcacPlcyRowStatus OBJECT-TYPE
    SYNTAX     RowStatus
    MAX-ACCESS read-create
    STATUS     current
    DESCRIPTION
        "The value of tmnxSubMcacPlcyRowStatus controls the creation and
         deletion of rows in the table."
    ::= { tmnxSubMcacPlcyEntry 2 }

tmnxSubMcacPlcyDescription OBJECT-TYPE
    SYNTAX      TItemDescription
    MAX-ACCESS  read-create
    STATUS      current
    DESCRIPTION
        "The value of tmnxSubMcacPlcyDescription specifies the user provided
         description of this subscriber MCAC policy."
    DEFVAL { ''H }
    ::= { tmnxSubMcacPlcyEntry 3 }

tmnxSubMcacPlcyAdminState OBJECT-TYPE
    SYNTAX     TmnxAdminState
    MAX-ACCESS read-create
    STATUS     current
    DESCRIPTION
        "The value of the object tmnxSubMcacPlcyAdminState specifies
         the administrative state of this subscriber MCAC policy."
    DEFVAL { outOfService }
    ::= { tmnxSubMcacPlcyEntry 4 }

tmnxSubMcacPlcyUnconstrainedBW OBJECT-TYPE
    SYNTAX      Integer32 (-1|0..2147483647)
    UNITS       "kbps"
    MAX-ACCESS  read-create
    STATUS      current
    DESCRIPTION
        "The value of tmnxSubMcacPlcyUnconstrainedBW specifies the bandwidth
         assigned to this subscriber MCAC policy in kilo-bits per second(kbps). 
                 
         If the default value of '-1' is set, there is no constraint on 
         bandwidth allocated. 
                 
         If the value of tmnxSubMcacPlcyUnconstrainedBW is set to '0' and if 
         an MCAC policy is assigned on the subscriber, then 
         no group (channel) from that policy is allowed on that subscriber."
    DEFVAL { -1 }
    ::= { tmnxSubMcacPlcyEntry 5 }

tmnxSubMcacPlcyPreRsvdMandBW OBJECT-TYPE
    SYNTAX      Integer32 (-1|0..2147483647)
    UNITS       "kbps"
    MAX-ACCESS  read-create
    STATUS      current
    DESCRIPTION
        "The value of tmnxSubMcacPlcyPreRsvdMandBW specifies the bandwidth
         pre-reserved for all the mandatory channels on a given subscriber
         in kilo-bits per second(kbps). 
                          
         If the value of tmnxSubMcacPlcyUnconstrainedBW is '0', no mandatory
         channels are allowed. If the value of tmnxSubMcacPlcyUnconstrainedBW 
         is '-1', then all mandatory and optional channels are allowed.

         If the value of tmnxSubMcacPlcyPreRsvdMandBW is equal to the value of
         tmnxSubMcacPlcyUnconstrainedBW, then all the unconstrained bandwidth
         on a given subscriber is allocated to mandatory channels configured 
         through MCAC policy on that subscriber and no optional 
         groups (channels) are allowed.

         The value of tmnxSubMcacPlcyPreRsvdMandBW should always be less than
         or equal to that of tmnxSubMcacPlcyUnconstrainedBW. An attempt to set
         the value of tmnxSubMcacPlcyPreRsvdMandBW greater than that of 
         tmnxSubMcacPlcyUnconstrainedBW will result in inconsistent value error."
    DEFVAL { -1 }
    ::= { tmnxSubMcacPlcyEntry 6 }

tmnxSubMcacPlcyLastMgmtChange OBJECT-TYPE
    SYNTAX      TimeStamp
    MAX-ACCESS  read-only
    STATUS      current
    DESCRIPTION
        "The value of tmnxSubMcacPlcyLastMgmtChange indicates the sysUpTime at
         the time of the most recent management-initiated change to this policy."
    ::= { tmnxSubMcacPlcyEntry 7 }

--
--  The IGMP Host Mcac Policy Subscriber Table
--

tmnxSubMcacPlcySubscriberTable OBJECT-TYPE
    SYNTAX     SEQUENCE OF TmnxSubMcacPlcySubscriberEntry
    MAX-ACCESS not-accessible
    STATUS     current
    DESCRIPTION
        "The tmnxSubMcacPlcySubscriberTable shows the subscribers associated
         with their MCAC policy."
    ::= { tmnxSubIgmpHostObjs 7 }

tmnxSubMcacPlcySubscriberEntry OBJECT-TYPE
    SYNTAX     TmnxSubMcacPlcySubscriberEntry
    MAX-ACCESS not-accessible
    STATUS     current
    DESCRIPTION
        "Each row entry represents a particular subscriber 
         associated with a particular MCAC policy."
    INDEX      { tmnxSubMcacPlcyName,
                 IMPLIED tmnxSubMcacPlcySubscriberId }
    ::= { tmnxSubMcacPlcySubscriberTable 1 }

TmnxSubMcacPlcySubscriberEntry ::= SEQUENCE
    {
    tmnxSubMcacPlcySubscriberId      DisplayString
    }

tmnxSubMcacPlcySubscriberId OBJECT-TYPE
    SYNTAX      DisplayString (SIZE (1..32))
    MAX-ACCESS  read-only
    STATUS      current
    DESCRIPTION
        "The value of tmnxSubMcacPlcySubscriberId indicates
         the subscriber identification."
    ::= { tmnxSubMcacPlcySubscriberEntry 1 }

--
--  The IGMP Host Mcac Status Table
--

tmnxSubMcacStatusTable OBJECT-TYPE
    SYNTAX     SEQUENCE OF TmnxSubMcacStatusEntry
    MAX-ACCESS not-accessible
    STATUS     current
    DESCRIPTION
        "The tmnxSubMcacStatusTable has an entry for each subscriber
         that is associated with a subscriber MCAC policy.

         A subscriber is associated with a subscriber MCAC policy if the value of
         the object tmnxSubInfoSubProfile refers to a subscriber MCAC policy where
         the value of the object tmnxSubProfSubMcacPolicy is not empty."
    ::= { tmnxSubIgmpHostObjs 8 }

tmnxSubMcacStatusEntry OBJECT-TYPE
    SYNTAX     TmnxSubMcacStatusEntry
    MAX-ACCESS not-accessible
    STATUS     current
    DESCRIPTION
        "Each row entry represents status information about the MCAC policy
         of this subscriber's hosts.

         Rows are created or removed automatically by the system."
    INDEX      { IMPLIED tmnxSubInfoSubIdent }
    ::= { tmnxSubMcacStatusTable 1 }

TmnxSubMcacStatusEntry ::= SEQUENCE {
    tmnxSubMcacStatusPlcyName        TNamedItem,
    
    tmnxSubMcacStatusinUseMandBw     Unsigned32,
    tmnxSubMcacStatusinUseOpnlBw     Unsigned32,
    tmnxSubMcacStatusAvailMandBw     Unsigned32,
    tmnxSubMcacStatusAvailOpnlBw     Unsigned32
    }

tmnxSubMcacStatusPlcyName OBJECT-TYPE
    SYNTAX      TNamedItem
    MAX-ACCESS  read-only
    STATUS      current
    DESCRIPTION
        "The value of tmnxSubMcacStatusPlcyName indicates
         the name of the subscriber MCAC policy associated with this subscriber.

         An empty string indicates that no subscriber MCAC policy is associated
         with this subscriber."
    ::= { tmnxSubMcacStatusEntry 1 }

tmnxSubMcacStatusinUseMandBw  OBJECT-TYPE
    SYNTAX     Unsigned32
    UNITS      "kbps"
    MAX-ACCESS read-only
    STATUS     current
    DESCRIPTION
        "The value of tmnxSubMcacStatusinUseMandBw indicates the 
         in-use bandwidth in kilo-bits per second(kbps) for the 
         mandatory channels for this protocol host instance."
    ::= { tmnxSubMcacStatusEntry 2 }

tmnxSubMcacStatusinUseOpnlBw  OBJECT-TYPE
    SYNTAX     Unsigned32
    UNITS      "kbps"
    MAX-ACCESS read-only
    STATUS     current
    DESCRIPTION
        "The value of tmnxSubMcacStatusinUseOpnlBw indicates the 
         in-use bandwidth in kilo-bits per second(kbps) for the 
         optional channels for this protocol host instance."
    ::= { tmnxSubMcacStatusEntry 3 }

tmnxSubMcacStatusAvailMandBw  OBJECT-TYPE
    SYNTAX     Unsigned32
    UNITS      "kbps"
    MAX-ACCESS read-only
    STATUS     current
    DESCRIPTION
        "The value of tmnxSubMcacStatusAvailMandBw indicates the 
         pre-reserved bandwidth in kilo-bits per second(kbps) 
         for the mandatory channels for this host instance."
    ::= { tmnxSubMcacStatusEntry 4 }

tmnxSubMcacStatusAvailOpnlBw  OBJECT-TYPE
    SYNTAX     Unsigned32
    UNITS      "kbps"
    MAX-ACCESS read-only
    STATUS     current
    DESCRIPTION
        "The value of tmnxSubMcacStatusAvailOpnlBw indicates the 
         available bandwidth in kilo-bits per second(kbps) for this 
         host instance."
    ::= { tmnxSubMcacStatusEntry 5 }

--
--  The MLD Policy Table
--

tmnxSubMldPolicyTable OBJECT-TYPE
    SYNTAX     SEQUENCE OF TmnxSubMldPolicyEntry
    MAX-ACCESS not-accessible
    STATUS     current
    DESCRIPTION
        "The table listing the host MLD policies."
    ::= { tmnxSubIgmpHostObjs 9 }

tmnxSubMldPolicyEntry OBJECT-TYPE
    SYNTAX     TmnxSubMldPolicyEntry
    MAX-ACCESS not-accessible
    STATUS     current
    DESCRIPTION
        "Each row entry in the tmnxSubMldPolicyTable represents a 
         host MLD policy."
    INDEX      { tmnxSubMldPlcyName }
    ::= { tmnxSubMldPolicyTable 1 }

TmnxSubMldPolicyEntry ::= SEQUENCE {
    tmnxSubMldPlcyName              TNamedItem,
    tmnxSubMldPlcyRowStatus         RowStatus,
    tmnxSubMldPlcyDescription       TItemDescription,
    tmnxSubMldPlcyImportPolicy      TPolicyStatementNameOrEmpty,
    tmnxSubMldPlcyHostMaxGroups     Unsigned32,
    tmnxSubMldPlcyAdminVersion      TmnxMldVersion,
    tmnxSubMldPlcyFastLeave         TmnxSubAdminStatus,
    tmnxSubMldPlcyRedirectionPolicy TPolicyStatementNameOrEmpty,    
    tmnxSubMldPlcyEgrRateModType    TEgrRateModType,
    tmnxSubMldPlcyEgrRateModSched   TNamedItemOrEmpty,
    tmnxSubMldPlcyPerHostReplic     TmnxSubAdminStatus,
    tmnxSubMldPlcyMcRprtDestName    TNamedItemOrEmpty,
    tmnxSubMldPlcyMcRprtOptFields   BITS,
    tmnxSubMldPlcyMcRprtAdminState  TmnxAdminState,
    tmnxSubMldPlcyHostMaxSources    Unsigned32,
    tmnxSubMldPlcyHostMaxGrpSources Unsigned32,
    tmnxSubMldPlcyPerHostMcastMac   TruthValue
}

tmnxSubMldPlcyName       OBJECT-TYPE
    SYNTAX      TNamedItem
    MAX-ACCESS  not-accessible
    STATUS      current
    DESCRIPTION
        "The value of tmnxSubMldPlcyName indicates the name of the host MLD policy."
    ::= { tmnxSubMldPolicyEntry 1 }

tmnxSubMldPlcyRowStatus OBJECT-TYPE
    SYNTAX     RowStatus
    MAX-ACCESS read-create
    STATUS     current
    DESCRIPTION
        "The value of tmnxSubMldPlcyRowStatus controls the creation and
         deletion of rows in the table."
    ::= { tmnxSubMldPolicyEntry 2 }

tmnxSubMldPlcyDescription OBJECT-TYPE
    SYNTAX      TItemDescription
    MAX-ACCESS  read-create
    STATUS      current
    DESCRIPTION
        "The value of tmnxSubMldPlcyDescription specifies the user provided
         description of this host MLD policy."
    DEFVAL { ''H }
    ::= { tmnxSubMldPolicyEntry 3 }

tmnxSubMldPlcyImportPolicy OBJECT-TYPE
    SYNTAX     TPolicyStatementNameOrEmpty
    MAX-ACCESS read-create
    STATUS     current
    DESCRIPTION
        "tmnxSubMldPlcyImportPolicy specifies the import policy that is to be applied
         on this host MLD policy."
    DEFVAL { ''H }
    ::= { tmnxSubMldPolicyEntry 4 }

tmnxSubMldPlcyHostMaxGroups OBJECT-TYPE
    SYNTAX     Unsigned32 (0|1..16000)
    MAX-ACCESS read-create
    STATUS     current
    DESCRIPTION
        "The value of tmnxSubMldPlcyHostMaxGroups specifies the maximum number of groups
         for which MLD can have local receiver information based on received
         MLD reports for this host. When this configuration is changed 
         dynamically to a value lower than currently accepted number of groups,
         the groups that are already accepted are not deleted.  Only new groups 
         will not be allowed.  When this object has a value of 0, there is no 
         limit to the number of groups."
    DEFVAL { 0 }
    ::= { tmnxSubMldPolicyEntry 5 }

tmnxSubMldPlcyAdminVersion OBJECT-TYPE
    SYNTAX     TmnxMldVersion
    MAX-ACCESS read-create
    STATUS     current
    DESCRIPTION
        "The configured version of MLD which is running for this host.
         This object can be used to configure a router capable of
         running either value.  For MLD to function correctly, all
         routers on a LAN must be configured to run the same version
         of MLD on that LAN."
    DEFVAL { version2 }
    ::= { tmnxSubMldPolicyEntry 6 }

tmnxSubMldPlcyFastLeave OBJECT-TYPE
    SYNTAX     TmnxSubAdminStatus
    MAX-ACCESS read-create
    STATUS     current
    DESCRIPTION
        "The value of the object tmnxSubMldPlcyFastLeave specifies
         whether fast leave is allowed for this host.
         
         If set to 'enabled(1)', the system prunes the port on which an MLD
         'leave' message has been received without waiting for the Group
         Specific Query to timeout."
    DEFVAL { enabled }
    ::= { tmnxSubMldPolicyEntry 7 }

tmnxSubMldPlcyRedirectionPolicy OBJECT-TYPE
    SYNTAX     TPolicyStatementNameOrEmpty
    MAX-ACCESS read-create
    STATUS     current
    DESCRIPTION
        "tmnxSubMldPlcyRedirectionPolicy specifies the redirection policy that
         is to be applied on this host Mld policy."
    DEFVAL { ''H }
    ::= { tmnxSubMldPolicyEntry 8}

tmnxSubMldPlcyEgrRateModType OBJECT-TYPE
    SYNTAX      TEgrRateModType
    MAX-ACCESS  read-create
    STATUS      current
    DESCRIPTION
        "The value of tmnxSubMldPlcyEgrRateModType specifies the egress-rate
         modification that is to be applied.

         If set to 'namedScheduler', the scheduler as defined in
         tmnxSubMldPlcyEgrRateModSched is used."
    DEFVAL { none }
    ::= { tmnxSubMldPolicyEntry 9 }

tmnxSubMldPlcyEgrRateModSched OBJECT-TYPE
    SYNTAX      TNamedItemOrEmpty
    MAX-ACCESS  read-create
    STATUS      current
    DESCRIPTION
        "The value of tmnxSubMldPlcyEgrRateModSched specifies the scheduler to
         be applied for egress rate modification.

         The value is only considered if tmnxSubMldPlcyEgrRateModType is set to
         'namedScheduler'."
    DEFVAL { "" }
    ::= { tmnxSubMldPolicyEntry 10 }

tmnxSubMldPlcyPerHostReplic OBJECT-TYPE
    SYNTAX     TmnxSubAdminStatus
    MAX-ACCESS read-create
    STATUS     current
    DESCRIPTION
        "The value of the object tmnxSubMldPlcyPerHostReplic specifies
         whether per-host replication is allowed for this host.
         
         If set to 'enabled(1)', outgoing traffic will be replicated per host,
         else it will be replicated per SAP.
         
         When traffic is replicated per host, a copy of each outgoing 
         multicast traffic packet will be sent to the unicast MAC address of 
         each host individually, else a single copy will be sent to the 
         multicast MAC address per SAP.
         
         This is only applicable for non-PPP hosts. In case of PPP host,
         traffic is always replicated per host."
    DEFVAL { disabled }
    ::= { tmnxSubMldPolicyEntry 11 }

tmnxSubMldPlcyMcRprtDestName OBJECT-TYPE
    SYNTAX      TNamedItemOrEmpty
    MAX-ACCESS  read-create
    STATUS      current
    DESCRIPTION
        "The value of tmnxSubMldPlcyMcRprtDestName indicates the multicast
         reporting destination 
         (found in TIMETRA-MCAST-PATH-MGMT-MIB::tmnxMcPathRprtDestTable)
         or it can be an empty string."
    DEFVAL { ''H }
    ::= { tmnxSubMldPolicyEntry 12 }

tmnxSubMldPlcyMcRprtOptFields OBJECT-TYPE
    SYNTAX      BITS {
                    hostMac             (0),
                    pppoeSessionId      (1),
                    svcId               (2),
                    sapId               (3)
                }
    MAX-ACCESS  read-create
    STATUS      current
    DESCRIPTION
        "The value of tmnxSubMldPlcyMcRprtOptFields specifies what optional
        fields should be included into the multicast reporting messages."
    DEFVAL { { } }
    ::= { tmnxSubMldPolicyEntry 13 }

tmnxSubMldPlcyMcRprtAdminState OBJECT-TYPE
    SYNTAX          TmnxAdminState
    MAX-ACCESS      read-create
    STATUS          current
    DESCRIPTION
        "The value of tmnxSubMldPlcyMcRprtAdminState indicates the administrative
         state of the multicast reporting. When the value is 'outOfService', 
         no multicast reports are sent. When it is 'inService', multicast reports
         are sent to the destination as indicated by tmnxSubMldPlcyMcRprtDestName."
    DEFVAL { outOfService }
    ::= { tmnxSubMldPolicyEntry 14 }

tmnxSubMldPlcyHostMaxSources OBJECT-TYPE
    SYNTAX     Unsigned32 (0|1..1000)
    MAX-ACCESS read-create
    STATUS     current
    DESCRIPTION
        "The value of tmnxSubMldPlcyHostMaxSources specifies the maximum number
         of sources for which MLD can have local receiver information based on 
         received MLD reports for this host. When this configuration is changed 
         dynamically to a value lower than currently accepted number of sources,
         the sources that are already accepted are not deleted. Only new sources 
         will not be allowed.  When this object has a value of 0, there is no 
         limit to the number of sources."
    DEFVAL { 0 }
    ::= { tmnxSubMldPolicyEntry 15 }

tmnxSubMldPlcyHostMaxGrpSources OBJECT-TYPE
    SYNTAX     Unsigned32 (0|1..32000)
    MAX-ACCESS read-create
    STATUS     current
    DESCRIPTION
        "The value of tmnxSubMldPlcyHostMaxGrpSources specifies the maximum
         number of group sources for which MLD can have local receiver 
         information based on received MLD reports for this host. When this 
         configuration is changed dynamically to a value lower than currently 
         accepted number of group sources, the group sources that are already
         accepted are not deleted. Only new group sources will not be allowed.
         When this object has a value of 0, there is no limit to the number 
         of group sources."
    DEFVAL { 0 }
    ::= { tmnxSubMldPolicyEntry 16 }

tmnxSubMldPlcyPerHostMcastMac OBJECT-TYPE
    SYNTAX     TruthValue
    MAX-ACCESS read-create
    STATUS     current
    DESCRIPTION
        "The value of the object tmnxSubMldPlcyPerHostMcastMac specifies
         which type of destination mac address will be used for outgoing traffic 
         when tmnxSubMldPlcyPerHostReplic is set to 'enabled(1)'.
         
         If set to 'true', outgoing traffic will be sent to a multicast mac
         address.  If set to 'false' it will be sent to the host unicast mac
         address."
    DEFVAL { false }
    ::= { tmnxSubMldPolicyEntry 17 }
        

--
--  The MLD Policy Static Table
--

tmnxSubMldPolicyStaticTable OBJECT-TYPE
    SYNTAX     SEQUENCE OF TmnxSubMldPolicyStaticEntry
    MAX-ACCESS not-accessible
    STATUS     current
    DESCRIPTION
        "The table listing the host MLD policy statics."
    ::= { tmnxSubIgmpHostObjs 10 }

tmnxSubMldPolicyStaticEntry OBJECT-TYPE
    SYNTAX     TmnxSubMldPolicyStaticEntry
    MAX-ACCESS not-accessible
    STATUS     current
    DESCRIPTION
        "Each row entry in the tmnxSubMldPolicyStaticTable represents a 
         host MLD policy statics."
    INDEX      { tmnxSubMldPlcyName,
                 tmnxSubMldHostGroupAddressType,
                 tmnxSubMldHostGroupAddress,
                 tmnxSubMldHostGrpSrcAddressType,
                 tmnxSubMldHostGrpSrcAddress }
    ::= { tmnxSubMldPolicyStaticTable 1 }

TmnxSubMldPolicyStaticEntry ::= SEQUENCE {
    tmnxSubMldHostGroupAddressType  InetAddressType,
    tmnxSubMldHostGroupAddress      InetAddress,
    tmnxSubMldHostGrpSrcAddressType InetAddressType,
    tmnxSubMldHostGrpSrcAddress     InetAddress,
    tmnxSubMldPlcyStaticRowStatus   RowStatus
}

tmnxSubMldHostGroupAddressType OBJECT-TYPE
    SYNTAX      InetAddressType
    MAX-ACCESS  not-accessible
    STATUS      current
    DESCRIPTION
        "The value of tmnxSubMldHostGroupAddressType specifies the type of
         address stored in tmnxSubMldHostGroupAddress."
    ::= { tmnxSubMldPolicyStaticEntry 1 }

tmnxSubMldHostGroupAddress OBJECT-TYPE
    SYNTAX     InetAddress (SIZE(16))
    MAX-ACCESS not-accessible
    STATUS     current
    DESCRIPTION
        "The IP multicast group address for which this entry
         contains information."
    ::= { tmnxSubMldPolicyStaticEntry 2 }

tmnxSubMldHostGrpSrcAddressType OBJECT-TYPE
    SYNTAX      InetAddressType
    MAX-ACCESS  not-accessible
    STATUS      current
    DESCRIPTION
        "The value of tmnxSubMldHostGrpSrcAddressType specifies the type of
         address stored in tmnxSubMldHostGrpSrcAddress."
    ::= { tmnxSubMldPolicyStaticEntry 3 }

tmnxSubMldHostGrpSrcAddress OBJECT-TYPE
    SYNTAX     InetAddress (SIZE(16))
    MAX-ACCESS not-accessible
    STATUS     current
    DESCRIPTION
        "The address of the source sending multicast traffic to the group
         identified by tmnxSubMldHostGroupAddress."
    ::= { tmnxSubMldPolicyStaticEntry 4 }

tmnxSubMldPlcyStaticRowStatus OBJECT-TYPE
    SYNTAX     RowStatus
    MAX-ACCESS read-create
    STATUS     current
    DESCRIPTION
        "The activation of a row enables MLD for the host. The
         destruction of a row disables MLD for the host."
    ::= { tmnxSubMldPolicyStaticEntry 5 }

-- ----------------------------------------
-- tmnxSubMldHostsTable
-- ----------------------------------------
tmnxSubMldHostsTable OBJECT-TYPE
    SYNTAX      SEQUENCE OF TmnxSubMldHostsEntry
    MAX-ACCESS  not-accessible
    STATUS      current
    DESCRIPTION
        "The tmnxSubMldHostsTable has an entry for each subscriber having 
         MLD hosts in the system."
    ::= { tmnxSubIgmpHostObjs 11 }

tmnxSubMldHostsEntry OBJECT-TYPE
    SYNTAX      TmnxSubMldHostsEntry
    MAX-ACCESS  not-accessible
    STATUS      current
    DESCRIPTION
        "Each row entry contains information about a particular subscriber
         host available in the system."
    INDEX      { tmnxSubMldHostsSubIdent,
                 vRtrID, 
                 tmnxSubMldHostsHostAddressType,
                 tmnxSubMldHostsHostAddress,
                 tmnxSubMldHostMacAddress,
                 tmnxSubMldHostPppoeSessionId }
    ::= { tmnxSubMldHostsTable 1 }


TmnxSubMldHostsEntry ::= SEQUENCE {
    tmnxSubMldHostsSubIdent         DisplayString,
    tmnxSubMldHostsHostAddressType  InetAddressType,
    tmnxSubMldHostsHostAddress      InetAddress,
    tmnxSubMldHostMacAddress        MacAddress,
    tmnxSubMldHostPppoeSessionId    TmnxPppoeSessionId,
    tmnxSubMldHostsCreated          TimeStamp
}

tmnxSubMldHostsSubIdent OBJECT-TYPE
    SYNTAX      DisplayString (SIZE (1..32))
    MAX-ACCESS  not-accessible
    STATUS      current
    DESCRIPTION
        "The value of tmnxSubMldHostsSubIdent specifies the subscriber
         identification of this subscriber."
    ::= { tmnxSubMldHostsEntry 1 }

tmnxSubMldHostsHostAddressType OBJECT-TYPE
    SYNTAX      InetAddressType
    MAX-ACCESS  not-accessible
    STATUS      current
    DESCRIPTION
        "The value of tmnxSubMldHostsHostAddressType specifies the type of
         address stored in tmnxSubMldHostsHostAddress."
    ::= { tmnxSubMldHostsEntry 2 }

tmnxSubMldHostsHostAddress OBJECT-TYPE
    SYNTAX     InetAddress (SIZE(16))
    MAX-ACCESS not-accessible
    STATUS     current
    DESCRIPTION
        "The IP host address for which this entry contains information."
    ::= { tmnxSubMldHostsEntry 3 }

tmnxSubMldHostMacAddress OBJECT-TYPE
    SYNTAX      MacAddress
    MAX-ACCESS  not-accessible
    STATUS      current
    DESCRIPTION
        "The value of tmnxSubMldHostMacAddress specifies the MAC address of
         this subscriber host."
    ::= { tmnxSubMldHostsEntry 4 }

tmnxSubMldHostPppoeSessionId OBJECT-TYPE
    SYNTAX      TmnxPppoeSessionId
    MAX-ACCESS  not-accessible
    STATUS      current
    DESCRIPTION
        "The value of tmnxSubMldHostPppoeSessionId specifies the PPPoE
         session id of this subscriber host."
    ::= { tmnxSubMldHostsEntry 5 }

tmnxSubMldHostsCreated OBJECT-TYPE
    SYNTAX      TimeStamp
    MAX-ACCESS  read-only
    STATUS      current
    DESCRIPTION
        "The sysUpTime when this row was created."
    ::= { tmnxSubMldHostsEntry 6 }


-- ------------------------------------------------
-- tmnxSubMldPlcySubscriberTable
-- ------------------------------------------------
tmnxSubMldPlcySubscriberTable OBJECT-TYPE
    SYNTAX      SEQUENCE OF TmnxSubMldPlcySubscriberEntry
    MAX-ACCESS  not-accessible
    STATUS      current
    DESCRIPTION
        "The tmnxSubMldPlcySubscriberTable shows the subscribers associated
         with their MLD Host Tracking policy."
    ::= { tmnxSubIgmpHostObjs 12 }

tmnxSubMldPlcySubscriberEntry OBJECT-TYPE
    SYNTAX      TmnxSubMldPlcySubscriberEntry
    MAX-ACCESS  not-accessible
    STATUS      current
    DESCRIPTION
        "Each row entry represents a particular subscriber 
         associated with a particular Mld Host Tracking policy."
    INDEX {
            tmnxSubMldPlcyName, 
            IMPLIED tmnxSubMldPlcySubscriberId
          }
    ::= { tmnxSubMldPlcySubscriberTable 1 }

TmnxSubMldPlcySubscriberEntry ::= SEQUENCE
   {
        tmnxSubMldPlcySubscriberId       DisplayString
   }

tmnxSubMldPlcySubscriberId OBJECT-TYPE
    SYNTAX      DisplayString (SIZE (1..32))
    MAX-ACCESS  read-only
    STATUS      current
    DESCRIPTION
        "The value of tmnxSubMldPlcySubscriberId indicates the subscriber
         identification."
    ::= { tmnxSubMldPlcySubscriberEntry 1 }


-- ------------------------------------------------
-- tmnxSubMldStatusTable
-- ------------------------------------------------
--  Sparse Dependent Extension of the tmnxSubscriberInfoTable
--  The same indexes are used for both the base table, tmnxSubscriberInfoTable,
--  and the sparse dependent table, tmnxSubMldStatusTable.
--
--  This in effect extends the tmnxSubscriberInfoTable with additional columns.
--  A row is automatically created in the tmnxSubMldStatusTable
--  for each applicable row in the tmnxSubscriberInfoTable .
--
--  Deletion of a row in the tmnxSubscriberInfoTable results in the
--  same fate for the row in the tmnxSubMldStatusTable.

tmnxSubMldStatusTable OBJECT-TYPE
    SYNTAX      SEQUENCE OF TmnxSubMldStatusEntry
    MAX-ACCESS  not-accessible
    STATUS      current
    DESCRIPTION
        "The tmnxSubMldStatusTable has an entry for each subscriber
         that is associated with a MLD policy.

         A subscriber is associated with a MLD policy if the value of
         the object tmnxSubInfoSubProfile refers to a subscriber policy where
         the value of the object tmnxSubProfMldPolicy is not empty."
    ::= { tmnxSubIgmpHostObjs 13 }

tmnxSubMldStatusEntry OBJECT-TYPE
    SYNTAX      TmnxSubMldStatusEntry
    MAX-ACCESS  not-accessible
    STATUS      current
    DESCRIPTION
        "Each row entry represents status information about the MLD policy
         of this subscriber's hosts.

         Rows are created or removed automatically by the system."
    INDEX { IMPLIED tmnxSubInfoSubIdent }
    ::= { tmnxSubMldStatusTable 1 }

TmnxSubMldStatusEntry ::= SEQUENCE
   {
        tmnxSubMldStatusPlcyName         TNamedItemOrEmpty
   }

tmnxSubMldStatusPlcyName OBJECT-TYPE
    SYNTAX      TNamedItemOrEmpty
    MAX-ACCESS  read-only
    STATUS      current
    DESCRIPTION
        "The value of tmnxSubMldStatusPlcyName indicates
         the name of the MLD policy associated with this subscriber.

         An empty string indicates that no MLD policy is associated
         with this subscriber."
    ::= { tmnxSubMldStatusEntry 1 }

--
--      The Subscriber PPP Session Table
--

tmnxSubPppTable   OBJECT-TYPE
    SYNTAX      SEQUENCE OF TmnxSubPppEntry
    MAX-ACCESS  not-accessible
    STATUS      current
    DESCRIPTION
       "The tmnxSubPppTable has an entry for each subscriber PPP Session.
       
        Any MLPPP bundle and link sessions are also present in this table."
    ::= { tmnxSubPppObjs 1 }

tmnxSubPppEntry   OBJECT-TYPE
    SYNTAX      TmnxSubPppEntry
    MAX-ACCESS  not-accessible
    STATUS      current
    DESCRIPTION
       "Each conceptual row represents a subscriber PPP Session.

        Entries in this table are created and destroyed by the system."
    INDEX { tmnxSubPppIndex }
    ::= { tmnxSubPppTable 1 }

TmnxSubPppEntry ::= 
    SEQUENCE {
        tmnxSubPppIndex                  Unsigned32,
        tmnxSubPppType                   TmnxSubPppType,
        tmnxSubPppUpTime                 TimeTicks,
        tmnxSubPppDescription            DisplayString,
        tmnxSubPppLcpState               TmnxPppCpState,
        tmnxSubPppIpcpState              TmnxPppCpState,
        tmnxSubPppIpv6cpState            TmnxPppCpState,
        tmnxSubPppPppMtu                 Unsigned32,
        tmnxSubPppPppAuthProtocol        INTEGER,
        tmnxSubPppPppUserName            TmnxPppoeUserNameOrEmpty,
        tmnxSubPppSubIdent               TmnxSubIdentStringOrEmpty,
        tmnxSubPppOriginSubIdent         TmnxPppoeSessionInfoOrigin,
        tmnxSubPppSubProfString          TmnxSubProfileStringOrEmpty,
        tmnxSubPppSlaProfString          TmnxSlaProfileStringOrEmpty,
        tmnxSubPppAncpString             TmnxAncpStringOrZero,
        tmnxSubPppInterDestId            TmnxSubMgtIntDestIdOrEmpty,
        tmnxSubPppAppProfString          TmnxAppProfileStringOrEmpty,
        tmnxSubPppCategoryMapName        TNamedItemOrEmpty,
        tmnxSubPppOriginStrings          TmnxPppoeSessionInfoOrigin,
        tmnxSubPppIpAddrType             InetAddressType,
        tmnxSubPppIpAddr                 InetAddress,
        tmnxSubPppIpAddrPrefixLength     InetAddressPrefixLength,
        tmnxSubPppOriginIp               TmnxPppoeSessionInfoOrigin,
        tmnxSubPppPrimaryDnsType         InetAddressType,
        tmnxSubPppPrimaryDns             InetAddress,
        tmnxSubPppSecondaryDnsType       InetAddressType,
        tmnxSubPppSecondaryDns           InetAddress,
        tmnxSubPppOriginDns              TmnxPppoeSessionInfoOrigin,
        tmnxSubPppPrimaryNbnsType        InetAddressType,
        tmnxSubPppPrimaryNbns            InetAddress,
        tmnxSubPppSecondaryNbnsType      InetAddressType,
        tmnxSubPppSecondaryNbns          InetAddress,
        tmnxSubPppOriginNbns             TmnxPppoeSessionInfoOrigin,
        tmnxSubPppInterfaceId            OCTET STRING,
        tmnxSubPppOriginIpv6cpInfo       TmnxPppoeSessionInfoOrigin,
        tmnxSubPppIpv6Dns1Type           InetAddressType,
        tmnxSubPppIpv6Dns1               InetAddress,
        tmnxSubPppIpv6Dns2Type           InetAddressType,
        tmnxSubPppIpv6Dns2               InetAddress,
        tmnxSubPppIpv6DelPfxType         InetAddressType,
        tmnxSubPppIpv6DelPfx             InetAddress,
        tmnxSubPppIpv6DelPfxLen          InetAddressPrefixLength,
        tmnxSubPppIpv6DelPfxOrigin       TmnxPppoeSessionInfoOrigin,
        tmnxSubPppIpv6DelPfxPool         TNamedItemOrEmpty,
        tmnxSubPppIpv6PrefixType         InetAddressType,
        tmnxSubPppIpv6Prefix             InetAddress,
        tmnxSubPppIpv6PrefixLen          InetAddressPrefixLength,
        tmnxSubPppTerminationType        TmnxSubPppTerminationType,
        tmnxSubPppRetailerSvcId          TmnxServId,
        tmnxSubPppRetailerIf             InterfaceIndexOrZero,
        tmnxSubPppLacVrtrId              TmnxVRtrIDOrZero,
        tmnxSubPppLacConnectionId        Unsigned32,
        tmnxSubPppSessionTimeout         Unsigned32,
        tmnxSubPppCircuitId              OCTET STRING,
        tmnxSubPppRemoteId               OCTET STRING,
        tmnxSubPppAddressPool            DisplayString,
        tmnxSubPppRadiusClassAttr        OCTET STRING,
        tmnxSubPppRadiusUserName         DisplayString,
        tmnxSubPppSvcId                  TmnxServId,
        tmnxSubPppSubIf                  InterfaceIndexOrZero,
        tmnxSubPppGrpIf                  InterfaceIndexOrZero,
        tmnxSubPppPortId                 TmnxPortID,
        tmnxSubPppEncapValue             TmnxEncapVal,
        tmnxSubPppMlpppRole              INTEGER,
        tmnxSubPppMlpppBundleId          Unsigned32,
        tmnxSubPppAcctSessionId          TmnxSubAcctSessionId,
        tmnxSubPppIpv6AddrType           InetAddressType,
        tmnxSubPppIpv6Addr               InetAddress,
        tmnxSubPppIpv6AddrOrigin         TmnxPppoeSessionInfoOrigin,
        tmnxSubPppIpv6AddrPool           TNamedItemOrEmpty,
        tmnxSubPppSessionTimeLeft        Unsigned32,
        tmnxSubPppLogicalLineId          OCTET STRING,
        tmnxSubPppIpv6PrefixOrigin       TmnxPppoeSessionInfoOrigin,
        tmnxSubPppSapSessionIndex        Unsigned32,
        tmnxSubPppIpv6PrefixPool         TNamedItemOrEmpty,
        tmnxSubPppIgnoringDfBit          TruthValue
    }
        
tmnxSubPppIndex OBJECT-TYPE
    SYNTAX      Unsigned32
    MAX-ACCESS  not-accessible
    STATUS      current
    DESCRIPTION
       "The value of the object tmnxSubPppIndex indicates the local  
        identifier of the session."
    ::= { tmnxSubPppEntry 1 }

tmnxSubPppType OBJECT-TYPE
    SYNTAX      TmnxSubPppType
    MAX-ACCESS  read-only
    STATUS      current
    DESCRIPTION
       "The value of the object tmnxSubPppType indicates the type of
        the session."
    ::= { tmnxSubPppEntry 2 }

tmnxSubPppUpTime OBJECT-TYPE
    SYNTAX      TimeTicks
    MAX-ACCESS  read-only
    STATUS      current
    DESCRIPTION
        "The value of tmnxSubPppUpTime indicates how long (in hundredths
         of a second) that the session already exists in this table."
    ::= { tmnxSubPppEntry 3 }

 tmnxSubPppDescription OBJECT-TYPE
     SYNTAX      DisplayString (SIZE(0..80))
     MAX-ACCESS  read-only
     STATUS      current
     DESCRIPTION
         "The value of tmnxSubPppDescription indicates 
          an automatically generated description of the session."
     ::= { tmnxSubPppEntry 4 }

tmnxSubPppLcpState OBJECT-TYPE
    SYNTAX      TmnxPppCpState
    MAX-ACCESS  read-only
    STATUS      current
    DESCRIPTION
        "The value of tmnxSubPppLcpState indicates the current state of
         the PPP Link Control Protocol of the session."
    ::= { tmnxSubPppEntry 5 }

tmnxSubPppIpcpState OBJECT-TYPE
    SYNTAX      TmnxPppCpState
    MAX-ACCESS  read-only
    STATUS      current
    DESCRIPTION
        "The value of tmnxSubPppIpcpState indicates the current state of
         the PPP IP Control Protocol of the session."
    ::= { tmnxSubPppEntry 6 }

tmnxSubPppIpv6cpState OBJECT-TYPE
    SYNTAX      TmnxPppCpState
    MAX-ACCESS  read-only
    STATUS      current
    DESCRIPTION
        "The value of tmnxSubPppIpv6cpState indicates the current state of
         the PPP IPv6 Control Protocol of the session."
    ::= { tmnxSubPppEntry 7 }

tmnxSubPppPppMtu OBJECT-TYPE
    SYNTAX      Unsigned32
    UNITS       "bytes"
    MAX-ACCESS  read-only
    STATUS      current
    DESCRIPTION
        "The value of tmnxSubPppPppMtu indicates the PPP MTU of the
         session."
    ::= { tmnxSubPppEntry 8 }

tmnxSubPppPppAuthProtocol OBJECT-TYPE
    SYNTAX      INTEGER {
                    none (1),
                    pap  (2),
                    chap (3)
                }
    MAX-ACCESS  read-only
    STATUS      current
    DESCRIPTION
        "The value of tmnxSubPppPppAuthProtocol indicates the
         PPP protocol used to authenticate the session.

         The value 'none' indicates that no PPP authentication was done. The
         value 'pap' indicates that authentication was done via the Password
         Authentication Protocol. The value 'chap' indicates that
         authentication was done via the Challenge-Handshake Authentication
         Protocol."
    ::= { tmnxSubPppEntry 9 }

tmnxSubPppPppUserName OBJECT-TYPE
    SYNTAX      TmnxPppoeUserNameOrEmpty
    MAX-ACCESS  read-only
    STATUS      current
    DESCRIPTION
        "The value of tmnxSubPppPppUserName indicates the user name
         learned during the PPP authentication phase."
    ::= { tmnxSubPppEntry 10 }

tmnxSubPppSubIdent OBJECT-TYPE
    SYNTAX      TmnxSubIdentStringOrEmpty
    MAX-ACCESS  read-only
    STATUS      current
    DESCRIPTION
        "The value of tmnxSubPppSubIdent indicates the subscriber
         applicable for this session."
    ::= { tmnxSubPppEntry 11 }

tmnxSubPppOriginSubIdent OBJECT-TYPE
    SYNTAX      TmnxPppoeSessionInfoOrigin
    MAX-ACCESS  read-only
    STATUS      obsolete
    DESCRIPTION
        "The value of tmnxSubPppOriginSubIdent indicates which source
         provided the subscriber."
    ::= { tmnxSubPppEntry 12 }

tmnxSubPppSubProfString OBJECT-TYPE
    SYNTAX      TmnxSubProfileStringOrEmpty
    MAX-ACCESS  read-only
    STATUS      current
    DESCRIPTION
        "The value of tmnxSubPppSubProfString indicates the subscriber
         profile string applicable for this session."
    ::= { tmnxSubPppEntry 13 }

tmnxSubPppSlaProfString OBJECT-TYPE
    SYNTAX      TmnxSlaProfileStringOrEmpty
    MAX-ACCESS  read-only
    STATUS      current
    DESCRIPTION
        "The value of tmnxSubPppSlaProfString indicates the SLA profile
         string applicable for this session."
    ::= { tmnxSubPppEntry 14 }

tmnxSubPppAncpString OBJECT-TYPE
    SYNTAX      TmnxAncpStringOrZero
    MAX-ACCESS  read-only
    STATUS      current
    DESCRIPTION
        "The value of tmnxSubPppAncpString indicates the ANCP string
         applicable for this session."
    ::= { tmnxSubPppEntry 15 }

tmnxSubPppInterDestId OBJECT-TYPE
    SYNTAX      TmnxSubMgtIntDestIdOrEmpty
    MAX-ACCESS  read-only
    STATUS      current
    DESCRIPTION
        "The value of tmnxSubPppInterDestId indicates the intermediate
         destination identifier applicable for this session."
    ::= { tmnxSubPppEntry 16 }

tmnxSubPppAppProfString OBJECT-TYPE
    SYNTAX      TmnxAppProfileStringOrEmpty
    MAX-ACCESS  read-only
    STATUS      current
    DESCRIPTION
        "The value of tmnxSubPppAppProfString indicates the application
         profile string applicable for this session."
    ::= { tmnxSubPppEntry 17 }

tmnxSubPppCategoryMapName OBJECT-TYPE
    SYNTAX      TNamedItemOrEmpty
    MAX-ACCESS  read-only
    STATUS      current
    DESCRIPTION
        "The value of tmnxSubPppCategoryMapName indicates the
         category map name applicable for this session."
    ::= { tmnxSubPppEntry 18 }

tmnxSubPppOriginStrings OBJECT-TYPE
    SYNTAX      TmnxPppoeSessionInfoOrigin
    MAX-ACCESS  read-only
    STATUS      obsolete
    DESCRIPTION
        "The value of tmnxSubPppOriginStrings indicates which source
         provided the subscriber identification strings
         (subscriber profile string, SLA profile string, ANCP string,
         intermediate destination identifier, application profile string
         and category map name)."
    ::= { tmnxSubPppEntry 19 }

tmnxSubPppIpAddrType OBJECT-TYPE
    SYNTAX      InetAddressType
    MAX-ACCESS  read-only
    STATUS      current
    DESCRIPTION
        "The value of tmnxSubPppIpAddrType indicates the address type of
         tmnxSubPppIpAddr."
    ::= { tmnxSubPppEntry 20 }

tmnxSubPppIpAddr OBJECT-TYPE
    SYNTAX      InetAddress (SIZE (0|4))
    MAX-ACCESS  read-only
    STATUS      current
    DESCRIPTION
        "The value of tmnxSubPppIpAddr indicates the IP address of the
         session.

         The value of tmnxSubPppOriginIp indicates from what source this
         IP address was received."
    ::= { tmnxSubPppEntry 21 }

tmnxSubPppIpAddrPrefixLength OBJECT-TYPE
    SYNTAX      InetAddressPrefixLength
    MAX-ACCESS  read-only
    STATUS      current
    DESCRIPTION
        "The value of tmnxSubPppIpAddr indicates 
         the prefix length of tmnxSubPppIpAddr."
    ::= { tmnxSubPppEntry 22 }

tmnxSubPppOriginIp OBJECT-TYPE
    SYNTAX      TmnxPppoeSessionInfoOrigin
    MAX-ACCESS  read-only
    STATUS      current
    DESCRIPTION
        "The value of tmnxSubPppOriginIp indicates which source
         provided the IP address."
    ::= { tmnxSubPppEntry 23 }

tmnxSubPppPrimaryDnsType OBJECT-TYPE
    SYNTAX      InetAddressType
    MAX-ACCESS  read-only
    STATUS      current
    DESCRIPTION
        "The value of tmnxSubPppPrimaryDnsType indicates the address
         type of tmnxSubPppPrimaryDns."
    ::= { tmnxSubPppEntry 24 }

tmnxSubPppPrimaryDns OBJECT-TYPE
    SYNTAX      InetAddress (SIZE (0|4))
    MAX-ACCESS  read-only
    STATUS      current
    DESCRIPTION
        "The value of tmnxSubPppPrimaryDns indicates the primary DNS
         server.

         The value of this object is ''H when not applicable.

         The value of tmnxSubPppOriginDns indicates from what source this
         IP address was received."
    ::= { tmnxSubPppEntry 25 }

tmnxSubPppSecondaryDnsType OBJECT-TYPE
    SYNTAX      InetAddressType
    MAX-ACCESS  read-only
    STATUS      current
    DESCRIPTION
        "The value of tmnxSubPppSecondaryDnsType indicates the address
         type of tmnxSubPppSecondaryDns."
    ::= { tmnxSubPppEntry 26 }

tmnxSubPppSecondaryDns OBJECT-TYPE
    SYNTAX      InetAddress (SIZE (0|4))
    MAX-ACCESS  read-only
    STATUS      current
    DESCRIPTION
        "The value of tmnxSubPppSecondaryDns indicates the secondary DNS
         server.

         The value of this object is ''H when not applicable.

         The value of tmnxSubPppOriginDns indicates from what source this
         IP address was received."
    ::= { tmnxSubPppEntry 27 }

tmnxSubPppOriginDns OBJECT-TYPE
    SYNTAX      TmnxPppoeSessionInfoOrigin
    MAX-ACCESS  read-only
    STATUS      current
    DESCRIPTION
        "The value of tmnxSubPppOriginDns indicates which source provided
         the DNS addresses."
    ::= { tmnxSubPppEntry 28 }

tmnxSubPppPrimaryNbnsType OBJECT-TYPE
    SYNTAX      InetAddressType
    MAX-ACCESS  read-only
    STATUS      current
    DESCRIPTION
        "The value of tmnxSubPppPrimaryNbnsType indicates the address
         type of tmnxSubPppPrimaryNbns."
    ::= { tmnxSubPppEntry 29 }

tmnxSubPppPrimaryNbns OBJECT-TYPE
    SYNTAX      InetAddress (SIZE (0|4))
    MAX-ACCESS  read-only
    STATUS      current
    DESCRIPTION
        "The value of tmnxSubPppPrimaryNbns indicates the primary NBNS
         server.

         The value of this object is ''H when not applicable.

         The value of tmnxSubPppOriginNbns indicates from what source this
         IP address was received."
    ::= { tmnxSubPppEntry 30 }

tmnxSubPppSecondaryNbnsType OBJECT-TYPE
    SYNTAX      InetAddressType
    MAX-ACCESS  read-only
    STATUS      current
    DESCRIPTION
        "The value of tmnxSubPppSecondaryNbnsType indicates the address
         type of tmnxSubPppSecondaryNbns."
    ::= { tmnxSubPppEntry 31 }

tmnxSubPppSecondaryNbns OBJECT-TYPE
    SYNTAX      InetAddress (SIZE(0|4))
    MAX-ACCESS  read-only
    STATUS      current
    DESCRIPTION
        "The value of tmnxSubPppSecondaryNbns indicates the secondary
         NBNS server.

         The value of this object is ''H when not applicable.

         The value of tmnxSubPppOriginNbns indicates from what source this
         IP address was received."
    ::= { tmnxSubPppEntry 32 }

tmnxSubPppOriginNbns OBJECT-TYPE
    SYNTAX      TmnxPppoeSessionInfoOrigin
    MAX-ACCESS  read-only
    STATUS      current
    DESCRIPTION
        "The value of tmnxSubPppOriginNbns indicates which source provided
         the NBNS addresses."
    ::= { tmnxSubPppEntry 33 }

tmnxSubPppInterfaceId OBJECT-TYPE
    SYNTAX      OCTET STRING (SIZE (8))
    MAX-ACCESS  read-only
    STATUS      current
    DESCRIPTION
        "The value of tmnxSubPppInterfaceId indicates the IPv6
         Interface Identifier negotiated via IPv6CP."
    ::= { tmnxSubPppEntry 34 }

tmnxSubPppOriginIpv6cpInfo OBJECT-TYPE
    SYNTAX      TmnxPppoeSessionInfoOrigin
    MAX-ACCESS  read-only
    STATUS      obsolete
    DESCRIPTION
        "The value of tmnxSubPppOriginIpv6cpInfo indicates which source
         provided the IPv6CP information."
    ::= { tmnxSubPppEntry 35 }

tmnxSubPppIpv6Dns1Type OBJECT-TYPE
    SYNTAX      InetAddressType
    MAX-ACCESS  read-only
    STATUS      current
    DESCRIPTION
        "The value of tmnxSubPppIpv6Dns1Type indicates the address
         type of tmnxSubPppIpv6Dns1."
    ::= { tmnxSubPppEntry 36 }

tmnxSubPppIpv6Dns1 OBJECT-TYPE
    SYNTAX      InetAddress (SIZE (0|16))
    MAX-ACCESS  read-only
    STATUS      current
    DESCRIPTION
        "The value of tmnxSubPppIpv6Dns1 indicates the primary DNS
         server."
    ::= { tmnxSubPppEntry 37 }

tmnxSubPppIpv6Dns2Type OBJECT-TYPE
    SYNTAX      InetAddressType
    MAX-ACCESS  read-only
    STATUS      current
    DESCRIPTION
        "The value of tmnxSubPppIpv6Dns2Type indicates the address
         type of tmnxSubPppIpv6Dns2."
    ::= { tmnxSubPppEntry 38 }

tmnxSubPppIpv6Dns2 OBJECT-TYPE
    SYNTAX      InetAddress (SIZE (0|16))
    MAX-ACCESS  read-only
    STATUS      current
    DESCRIPTION
        "The value of tmnxSubPppIpv6Dns2 indicates the secondary DNS
         server."
    ::= { tmnxSubPppEntry 39 }

tmnxSubPppIpv6DelPfxType OBJECT-TYPE
    SYNTAX      InetAddressType
    MAX-ACCESS  read-only
    STATUS      current
    DESCRIPTION
        "The value of tmnxSubPppIpv6DelPfxType indicates the address
         type of tmnxSubPppIpv6DelPfx."
    ::= { tmnxSubPppEntry 40 }

tmnxSubPppIpv6DelPfx OBJECT-TYPE
    SYNTAX      InetAddress (SIZE (0|16))
    MAX-ACCESS  read-only
    STATUS      current
    DESCRIPTION
        "The value of tmnxSubPppIpv6DelPfx indicates the IPv6
         Delegated Prefix.

         The value of this object is ''H when not applicable."
    ::= { tmnxSubPppEntry 41 }

tmnxSubPppIpv6DelPfxLen OBJECT-TYPE
    SYNTAX      InetAddressPrefixLength (0..128)
    MAX-ACCESS  read-only
    STATUS      current
    DESCRIPTION 
        "The value of tmnxSubPppIpv6DelPfxLen indicates
         the length of tmnxSubPppIpv6DelPfx."
    ::= { tmnxSubPppEntry 42 }

tmnxSubPppIpv6DelPfxOrigin OBJECT-TYPE
    SYNTAX      TmnxPppoeSessionInfoOrigin
    MAX-ACCESS  read-only
    STATUS      current
    DESCRIPTION 
        "The value of tmnxSubPppIpv6DelPfxOrigin indicates
         the origin of tmnxSubPppIpv6DelPfx and tmnxSubPppIpv6DelPfxLen."
    ::= { tmnxSubPppEntry 43 }

tmnxSubPppIpv6DelPfxPool OBJECT-TYPE
    SYNTAX      TNamedItemOrEmpty
    MAX-ACCESS  read-only
    STATUS      current
    DESCRIPTION 
        "The value of tmnxSubPppIpv6DelPfxPool indicates
         the DHCP server pool from which the delegated prefix,
         indicated by tmnxSubPppIpv6DelPfx, is allocated."
    ::= { tmnxSubPppEntry 44 }

tmnxSubPppIpv6PrefixType OBJECT-TYPE
    SYNTAX      InetAddressType
    MAX-ACCESS  read-only
    STATUS      current
    DESCRIPTION
        "The value of tmnxSubPppIpv6PrefixType indicates the address
         type of tmnxSubPppIpv6Prefix."
    ::= { tmnxSubPppEntry 45 }

tmnxSubPppIpv6Prefix OBJECT-TYPE
    SYNTAX      InetAddress (SIZE (0|16))
    MAX-ACCESS  read-only
    STATUS      current
    DESCRIPTION
        "The value of tmnxSubPppIpv6Prefix indicates the IPv6 prefix.

         The value of this object is ''H when not applicable."
    ::= { tmnxSubPppEntry 46 }
    
tmnxSubPppIpv6PrefixLen OBJECT-TYPE
    SYNTAX      InetAddressPrefixLength (0..128)
    MAX-ACCESS  read-only
    STATUS      current
    DESCRIPTION 
        "The value of tmnxSubPppIpv6PrefixLen indicates
         the length of tmnxSubPppIpv6Prefix."
    ::= { tmnxSubPppEntry 47 }

tmnxSubPppTerminationType OBJECT-TYPE
    SYNTAX      TmnxSubPppTerminationType
    MAX-ACCESS  read-only
    STATUS      current
    DESCRIPTION
        "The value of tmnxSubPppTerminationType indicates the termination type
         of this session."
    ::= { tmnxSubPppEntry 48 }

tmnxSubPppRetailerSvcId OBJECT-TYPE
    SYNTAX      TmnxServId
    MAX-ACCESS  read-only
    STATUS      current
    DESCRIPTION
        "The value of tmnxSubPppRetailerSvcId indicates the service ID of
         the retailer VPRN service to which this session belongs. If the value
         of this object is non-zero, the session belongs to a retailer VPRN."
    ::= { tmnxSubPppEntry 49 }

tmnxSubPppRetailerIf OBJECT-TYPE
    SYNTAX      InterfaceIndexOrZero
    MAX-ACCESS  read-only
    STATUS      current
    DESCRIPTION
        "The value of tmnxSubPppRetailerIf indicates the interface index
         of the retailer VPRN interface to which this session belongs. If the
         value of this object is non-zero, the session belongs to a retailer
         VPRN."
    ::= { tmnxSubPppEntry 50 }

tmnxSubPppLacVrtrId OBJECT-TYPE
    SYNTAX      TmnxVRtrIDOrZero
    MAX-ACCESS  read-only
    STATUS      current
    DESCRIPTION
        "The value of tmnxSubPppLacVrtrId indicates the virtual router 
         ID of the LAC L2TP session associated with this session. 

         The value of this object is only applicable if
         tmnxSubPppTerminationType is 'lac', otherwise it is equal to zero."
    ::= { tmnxSubPppEntry 51 }

tmnxSubPppLacConnectionId OBJECT-TYPE
    SYNTAX      Unsigned32
    MAX-ACCESS  read-only
    STATUS      current
    DESCRIPTION
        "The value of tmnxSubPppLacConnectionId indicates the connection 
         ID of the LAC L2TP session associated with this session.

         The values of tmnxSubPppLacVrtrId and 
         tmnxSubPppLacConnectionId are the index in the table
         TIMETRA-L2TP-MIB::tmnxL2tpSeStatusTable of the L2TP session
         associated with this session.
         
         The value of this object is only applicable if
         tmnxSubPppTerminationType is 'lac', otherwise it is equal to zero."
    ::= { tmnxSubPppEntry 52 }

tmnxSubPppSessionTimeout OBJECT-TYPE
    SYNTAX      Unsigned32 (0..65535)
    UNITS       "seconds"
    MAX-ACCESS  read-only
    STATUS      current
    DESCRIPTION
        "The value of tmnxSubPppSessionTimeout indicates the session
         timeout received from the Radius server (if applicable)."
    ::= { tmnxSubPppEntry 53 }

tmnxSubPppCircuitId OBJECT-TYPE
    SYNTAX      OCTET STRING (SIZE (0..256))
    MAX-ACCESS  read-only
    STATUS      current
    DESCRIPTION
        "The value of tmnxSubPppCircuitId indicates the value of the
         circuit-id sub-option."
    ::= { tmnxSubPppEntry 54 }

tmnxSubPppRemoteId OBJECT-TYPE
    SYNTAX      OCTET STRING (SIZE (0..256))
    MAX-ACCESS  read-only
    STATUS      current
    DESCRIPTION
        "The value of tmnxSubPppRemoteId indicates the value of the
         remote-id sub-option."
    ::= { tmnxSubPppEntry 55 }

tmnxSubPppAddressPool OBJECT-TYPE
    SYNTAX      DisplayString (SIZE (0..255))
    MAX-ACCESS  read-only
    STATUS      current
    DESCRIPTION
        "The value of tmnxSubPppAddressPool indicates the IP address pool
         which is used to search for an IP address for this session."
    ::= { tmnxSubPppEntry 56 }

tmnxSubPppRadiusClassAttr OBJECT-TYPE
    SYNTAX      OCTET STRING (SIZE (0..253))
    MAX-ACCESS  read-only
    STATUS      current
    DESCRIPTION
        "The value of tmnxSubPppRadiusClassAttr indicates the Class
         attribute returned by the RADIUS server in an Access-Accept message.
         
         If no RADIUS authentication is performed for this session, or RADIUS
         did not return this attribute, the value of this object is empty."
    ::= { tmnxSubPppEntry 57 }

tmnxSubPppRadiusUserName OBJECT-TYPE
    SYNTAX      DisplayString (SIZE (0..253))
    MAX-ACCESS  read-only
    STATUS      current
    DESCRIPTION
        "The value of tmnxSubPppRadiusUserName indicates the User-Name
         attribute returned by the RADIUS server in an Access-Accept message.

         If RADIUS did not return this attribute, the value of this object
         is equal to the User-Name attribute sent in the original
         Access-Request message.
         
         If no RADIUS authentication is performed for this session, the value
         of this object is empty."
    ::= { tmnxSubPppEntry 58 }

tmnxSubPppSvcId OBJECT-TYPE
    SYNTAX      TmnxServId
    MAX-ACCESS  read-only
    STATUS      current
    DESCRIPTION
        "The value of tmnxSubPppSvcId indicates the service ID of
         the IES/VPRN service to which this session belongs."
    ::= { tmnxSubPppEntry 59 }

tmnxSubPppSubIf OBJECT-TYPE
    SYNTAX      InterfaceIndexOrZero
    MAX-ACCESS  read-only
    STATUS      current
    DESCRIPTION
        "The value of tmnxSubPppSubIf indicates the interface index
         of the subscriber-interface to which this session belongs."
    ::= { tmnxSubPppEntry 60 }

tmnxSubPppGrpIf OBJECT-TYPE
    SYNTAX      InterfaceIndexOrZero
    MAX-ACCESS  read-only
    STATUS      current
    DESCRIPTION
        "The value of tmnxSubPppGrpIf indicates the interface index
         of the group-interface to which this session belongs."
    ::= { tmnxSubPppEntry 61 }

tmnxSubPppPortId OBJECT-TYPE
    SYNTAX      TmnxPortID
    MAX-ACCESS  read-only
    STATUS      current
    DESCRIPTION     
        "The value of tmnxSubPppPortId indicates the ID of the access port
         to which this session belongs."
    ::= { tmnxSubPppEntry 62 }

tmnxSubPppEncapValue OBJECT-TYPE
    SYNTAX      TmnxEncapVal
    MAX-ACCESS  read-only
    STATUS      current
    DESCRIPTION     
        "The value of tmnxSubPppEncapValue indicates the value of the label
         used to identify this SAP on the access port 
         specified by tmnxSubPppPortId."
    ::= { tmnxSubPppEntry 63 }

tmnxSubPppMlpppRole OBJECT-TYPE
    SYNTAX      INTEGER {
                    no (0),
                    link (1),
                    bundle (2)
                }
    MAX-ACCESS  read-only
    STATUS      current
    DESCRIPTION     
        "The value of tmnxSubPppMlpppRole indicates the Multi Link PPP (MLPPP)
         role of this session.
         
         Only sessions where the value of tmnxSubPppType is equal to 'oL2tp'
         can have a value of tmnxSubPppMlpppRole different from 'no'."
    REFERENCE "RFC 1990 The PPP Multilink Protocol"
    ::= { tmnxSubPppEntry 70 }

tmnxSubPppMlpppBundleId OBJECT-TYPE
    SYNTAX      Unsigned32
    MAX-ACCESS  read-only
    STATUS      current
    DESCRIPTION
        "The value of tmnxSubPppMlpppBundleId indicates the 
         MLPPP bundle identifier of the session.
         
         If the value of tmnxSubPppMlpppRole is equal to 'no', the value of
         tmnxSubPppMlpppBundleId is equal to zero."
    ::= { tmnxSubPppEntry 71 }

tmnxSubPppAcctSessionId OBJECT-TYPE
    SYNTAX      TmnxSubAcctSessionId
    MAX-ACCESS  read-only
    STATUS      current
    DESCRIPTION     
        "The value of tmnxSubPppAcctSessionId indicates
         the accounting session id of the PPP session."
    ::= { tmnxSubPppEntry 74 }

tmnxSubPppIpv6AddrType OBJECT-TYPE
    SYNTAX      InetAddressType
    MAX-ACCESS  read-only
    STATUS      current
    DESCRIPTION
        "The value of tmnxSubPppIpv6AddrType indicates the address
         type of tmnxSubPppIpv6Addr."
    ::= { tmnxSubPppEntry 75 }

tmnxSubPppIpv6Addr OBJECT-TYPE
    SYNTAX      InetAddress (SIZE (0|16))
    MAX-ACCESS  read-only
    STATUS      current
    DESCRIPTION
        "The value of tmnxSubPppIpv6Addr indicates the IPv6
         address.

         The value of this object is ''H when not applicable."
    ::= { tmnxSubPppEntry 76 }

tmnxSubPppIpv6AddrOrigin OBJECT-TYPE
    SYNTAX      TmnxPppoeSessionInfoOrigin
    MAX-ACCESS  read-only
    STATUS      current
    DESCRIPTION 
        "The value of tmnxSubPppIpv6AddrOrigin indicates
         the origin of tmnxSubPppIpv6Addr."
    ::= { tmnxSubPppEntry 77 }

tmnxSubPppIpv6AddrPool OBJECT-TYPE
    SYNTAX      TNamedItemOrEmpty
    MAX-ACCESS  read-only
    STATUS      current
    DESCRIPTION 
        "The value of tmnxSubPppIpv6AddrPool indicates
         the DHCP server pool from which the address,
         indicated by tmnxSubPppIpv6Addr, is allocated."
    ::= { tmnxSubPppEntry 78 }

tmnxSubPppSessionTimeLeft OBJECT-TYPE
    SYNTAX      Unsigned32
    UNITS       "seconds"
    MAX-ACCESS  read-only
    STATUS      current
    DESCRIPTION
        "The value of tmnxSubPppSessionTimeLeft indicates the session
         time left when a session timeout is active for this session.
         A value of 0 indicates no session timeout is active."
    ::= { tmnxSubPppEntry 79 }

tmnxSubPppLogicalLineId OBJECT-TYPE
    SYNTAX      OCTET STRING (SIZE (0..64))
    MAX-ACCESS  read-only
    STATUS      current
    DESCRIPTION
        "The value of tmnxSubPppLogicalLineId indicates the value of the
         Logical Line ID (LLID).
         
         This value is first obtained from a RADIUS server in a pre-authentication phase,
         and subsequently transmitted in the Access-Request message for the
         actual authentication."
    ::= { tmnxSubPppEntry 100 }

tmnxSubPppIpv6PrefixOrigin OBJECT-TYPE
    SYNTAX      TmnxPppoeSessionInfoOrigin
    MAX-ACCESS  read-only
    STATUS      current
    DESCRIPTION 
        "The value of tmnxSubPppIpv6PrefixOrigin indicates
         the origin of tmnxSubPppIpv6Prefix."
    ::= { tmnxSubPppEntry 101 }

tmnxSubPppSapSessionIndex OBJECT-TYPE
    SYNTAX      Unsigned32
    MAX-ACCESS  read-only
    STATUS      current
    DESCRIPTION     
        "The value of tmnxSubPppSapSessionIndex indicates the 
         sap session index of the PPP session."
    ::= { tmnxSubPppEntry 102 }

tmnxSubPppIpv6PrefixPool OBJECT-TYPE
    SYNTAX      TNamedItemOrEmpty
    MAX-ACCESS  read-only
    STATUS      current
    DESCRIPTION 
        "The value of tmnxSubPppIpv6PrefixPool indicates
         the DHCP server pool from which the SLAAC prefix,
         indicated by tmnxSubPppIpv6Prefix, is allocated."
    ::= { tmnxSubPppEntry 103 }

tmnxSubPppIgnoringDfBit OBJECT-TYPE
    SYNTAX      TruthValue
    MAX-ACCESS  read-only
    STATUS      current
    DESCRIPTION 
        "The value of tmnxSubPppIgnoringDfBit indicates
         if this system ignores the Don't Fragment (DF) bit
         in the IPv4 header of traffic received for this session."
    ::= { tmnxSubPppEntry 104 }

--
--      The Subscriber PPP Session Statistics Table
--
--  Augmentation of the tmnxSubPppTable
--  Use of AUGMENTS clause implies a one-to-one dependent relationship
--  between the base table, tmnxSubPppTable, and the augmenting table,
--  tmnxSubPppStatTable. This in effect extends the tmnxSubPppStatTable
--  with additional columns. Creation (or deletion) of a row in the
--  tmnxSubPppTable results in the same fate for the row in the
--  tmnxSubPppStatTable.

tmnxSubPppStatTable   OBJECT-TYPE
    SYNTAX      SEQUENCE OF TmnxSubPppStatEntry
    MAX-ACCESS  not-accessible
    STATUS      current
    DESCRIPTION
       "The tmnxSubPppStatTable has an entry for each 
        Subscriber PPP Session."
    ::= { tmnxSubPppObjs 2 }

tmnxSubPppStatEntry   OBJECT-TYPE
    SYNTAX      TmnxSubPppStatEntry
    MAX-ACCESS  not-accessible
    STATUS      current
    DESCRIPTION
       "Each conceptual row represents statistics information about
        a Subscriber PPP Session.

        Entries in this table are created and destroyed by the system."
    AUGMENTS { tmnxSubPppEntry }
    ::= { tmnxSubPppStatTable 1 }

TmnxSubPppStatEntry ::= 
    SEQUENCE {
        tmnxSubPppStatRxUnknownProto     Counter32,
        tmnxSubPppStatRxLcpConfReq       Counter32,
        tmnxSubPppStatRxLcpConfAck       Counter32,
        tmnxSubPppStatRxLcpConfNak       Counter32,
        tmnxSubPppStatRxLcpConfRej       Counter32,
        tmnxSubPppStatRxLcpTermReq       Counter32,
        tmnxSubPppStatRxLcpTermAck       Counter32,
        tmnxSubPppStatRxLcpCodeRej       Counter32,
        tmnxSubPppStatRxLcpEchoReq       Counter32,
        tmnxSubPppStatRxLcpEchoRep       Counter32,
        tmnxSubPppStatRxLcpProtRej       Counter32,
        tmnxSubPppStatRxLcpDiscReq       Counter32,
        tmnxSubPppStatTxLcpConfReq       Counter32,
        tmnxSubPppStatTxLcpConfAck       Counter32,
        tmnxSubPppStatTxLcpConfNak       Counter32,
        tmnxSubPppStatTxLcpConfRej       Counter32,
        tmnxSubPppStatTxLcpTermReq       Counter32,
        tmnxSubPppStatTxLcpTermAck       Counter32,
        tmnxSubPppStatTxLcpCodeRej       Counter32,
        tmnxSubPppStatTxLcpEchoReq       Counter32,
        tmnxSubPppStatTxLcpEchoRep       Counter32,
        tmnxSubPppStatTxLcpProtRej       Counter32,
        tmnxSubPppStatTxLcpDiscReq       Counter32,
        tmnxSubPppStatRxPapAuthReq       Counter32,
        tmnxSubPppStatTxPapAuthAck       Counter32,
        tmnxSubPppStatTxPapAuthNak       Counter32,
        tmnxSubPppStatRxChapResponse     Counter32,
        tmnxSubPppStatTxChapChallenge    Counter32,
        tmnxSubPppStatTxChapSuccess      Counter32,
        tmnxSubPppStatTxChapFailure      Counter32,
        tmnxSubPppStatRxIpcpConfReq      Counter32,
        tmnxSubPppStatRxIpcpConfAck      Counter32,
        tmnxSubPppStatRxIpcpConfNak      Counter32,
        tmnxSubPppStatRxIpcpConfRej      Counter32,
        tmnxSubPppStatRxIpcpTermReq      Counter32,
        tmnxSubPppStatRxIpcpTermAck      Counter32,
        tmnxSubPppStatRxIpcpCodeRej      Counter32,
        tmnxSubPppStatTxIpcpConfReq      Counter32,
        tmnxSubPppStatTxIpcpConfAck      Counter32,
        tmnxSubPppStatTxIpcpConfNak      Counter32,
        tmnxSubPppStatTxIpcpConfRej      Counter32,
        tmnxSubPppStatTxIpcpTermReq      Counter32,
        tmnxSubPppStatTxIpcpTermAck      Counter32,
        tmnxSubPppStatTxIpcpCodeRej      Counter32,
        tmnxSubPppStatRxIpv6cpConfReq    Counter32,
        tmnxSubPppStatRxIpv6cpConfAck    Counter32,
        tmnxSubPppStatRxIpv6cpConfNak    Counter32,
        tmnxSubPppStatRxIpv6cpConfRej    Counter32,
        tmnxSubPppStatRxIpv6cpTermReq    Counter32,
        tmnxSubPppStatRxIpv6cpTermAck    Counter32,
        tmnxSubPppStatRxIpv6cpCodeRej    Counter32,
        tmnxSubPppStatTxIpv6cpConfReq    Counter32,
        tmnxSubPppStatTxIpv6cpConfAck    Counter32,
        tmnxSubPppStatTxIpv6cpConfNak    Counter32,
        tmnxSubPppStatTxIpv6cpConfRej    Counter32,
        tmnxSubPppStatTxIpv6cpTermReq    Counter32,
        tmnxSubPppStatTxIpv6cpTermAck    Counter32,
        tmnxSubPppStatTxIpv6cpCodeRej    Counter32
    }
        
tmnxSubPppStatRxUnknownProto OBJECT-TYPE
    SYNTAX      Counter32
    MAX-ACCESS  read-only
    STATUS      current
    DESCRIPTION
        "The value of tmnxSubPppStatRxUnknownProto indicates the number of
         packets with unknown PPP protocol received for this PPP session."
    ::= { tmnxSubPppStatEntry 2 }

tmnxSubPppStatRxLcpConfReq OBJECT-TYPE
    SYNTAX      Counter32
    MAX-ACCESS  read-only
    STATUS      current
    DESCRIPTION
        "The value of tmnxSubPppStatRxLcpConfReq indicates the number of
         LCP configure requests received for this PPP session."
    ::= { tmnxSubPppStatEntry 3 }

tmnxSubPppStatRxLcpConfAck OBJECT-TYPE
    SYNTAX      Counter32
    MAX-ACCESS  read-only
    STATUS      current
    DESCRIPTION
        "The value of tmnxSubPppStatRxLcpConfAck indicates the number of
         LCP configure acknowledgements received for this PPP session."
    ::= { tmnxSubPppStatEntry 4 }

tmnxSubPppStatRxLcpConfNak OBJECT-TYPE
    SYNTAX      Counter32
    MAX-ACCESS  read-only
    STATUS      current
    DESCRIPTION
        "The value of tmnxSubPppStatRxLcpConfNak indicates the number of
         negative LCP configure acknowledgements received for this PPP
         session."
    ::= { tmnxSubPppStatEntry 5 }

tmnxSubPppStatRxLcpConfRej OBJECT-TYPE
    SYNTAX      Counter32
    MAX-ACCESS  read-only
    STATUS      current
    DESCRIPTION
        "The value of tmnxSubPppStatRxLcpConfRej indicates the number of
         LCP configure rejects received for this PPP session."
    ::= { tmnxSubPppStatEntry 6 }

tmnxSubPppStatRxLcpTermReq OBJECT-TYPE
    SYNTAX      Counter32
    MAX-ACCESS  read-only
    STATUS      current
    DESCRIPTION
        "The value of tmnxSubPppStatRxLcpTermReq indicates the number of
         LCP terminate requests received for this PPP session."
    ::= { tmnxSubPppStatEntry 7 }

tmnxSubPppStatRxLcpTermAck OBJECT-TYPE
    SYNTAX      Counter32
    MAX-ACCESS  read-only
    STATUS      current
    DESCRIPTION
        "The value of tmnxSubPppStatRxLcpTermAck indicates the number of
         LCP terminate acknowledgements received for this PPP session."
    ::= { tmnxSubPppStatEntry 8 }

tmnxSubPppStatRxLcpCodeRej OBJECT-TYPE
    SYNTAX      Counter32
    MAX-ACCESS  read-only
    STATUS      current
    DESCRIPTION
        "The value of tmnxSubPppStatRxLcpCodeRej indicates the number of
         LCP code rejects received for this PPP session."
    ::= { tmnxSubPppStatEntry 9 }

tmnxSubPppStatRxLcpEchoReq OBJECT-TYPE
    SYNTAX      Counter32
    MAX-ACCESS  read-only
    STATUS      current
    DESCRIPTION
        "The value of tmnxSubPppStatRxLcpEchoReq indicates the number of
         LCP echo requests received for this PPP session."
    ::= { tmnxSubPppStatEntry 10 }

tmnxSubPppStatRxLcpEchoRep OBJECT-TYPE
    SYNTAX      Counter32
    MAX-ACCESS  read-only
    STATUS      current
    DESCRIPTION
        "The value of tmnxSubPppStatRxLcpEchoRep indicates the number of
         LCP echo replies received for this PPP session."
    ::= { tmnxSubPppStatEntry 11 }

tmnxSubPppStatRxLcpProtRej OBJECT-TYPE
    SYNTAX      Counter32
    MAX-ACCESS  read-only
    STATUS      current
    DESCRIPTION
        "The value of tmnxSubPppStatRxLcpProtRej indicates the number of
         LCP protocol rejects received for this PPP session."
    ::= { tmnxSubPppStatEntry 12 }

tmnxSubPppStatRxLcpDiscReq OBJECT-TYPE
    SYNTAX      Counter32
    MAX-ACCESS  read-only
    STATUS      current
    DESCRIPTION
        "The value of tmnxSubPppStatRxLcpDiscReq indicates the number of
         LCP discard requests received for this PPP session."
    ::= { tmnxSubPppStatEntry 13 }

tmnxSubPppStatTxLcpConfReq OBJECT-TYPE
    SYNTAX      Counter32
    MAX-ACCESS  read-only
    STATUS      current
    DESCRIPTION
        "The value of tmnxSubPppStatTxLcpConfReq indicates the number of
         LCP configure requests transmitted for this PPP session."
    ::= { tmnxSubPppStatEntry 14 }

tmnxSubPppStatTxLcpConfAck OBJECT-TYPE
    SYNTAX      Counter32
    MAX-ACCESS  read-only
    STATUS      current
    DESCRIPTION
        "The value of tmnxSubPppStatTxLcpConfAck indicates the number of
         LCP configure acknowledgements transmitted for this PPP session."
    ::= { tmnxSubPppStatEntry 15 }

tmnxSubPppStatTxLcpConfNak OBJECT-TYPE
    SYNTAX      Counter32
    MAX-ACCESS  read-only
    STATUS      current
    DESCRIPTION
        "The value of tmnxSubPppStatTxLcpConfNak indicates the number of
         negative LCP configure acknowledgements transmitted for this PPP
         session."
    ::= { tmnxSubPppStatEntry 16 }

tmnxSubPppStatTxLcpConfRej OBJECT-TYPE
    SYNTAX      Counter32
    MAX-ACCESS  read-only
    STATUS      current
    DESCRIPTION
        "The value of tmnxSubPppStatTxLcpConfRej indicates the number of
         LCP configure rejects transmitted for this PPP session."
    ::= { tmnxSubPppStatEntry 17 }

tmnxSubPppStatTxLcpTermReq OBJECT-TYPE
    SYNTAX      Counter32
    MAX-ACCESS  read-only
    STATUS      current
    DESCRIPTION
        "The value of tmnxSubPppStatTxLcpTermReq indicates the number of
         LCP terminate requests transmitted for this PPP session."
    ::= { tmnxSubPppStatEntry 18 }

tmnxSubPppStatTxLcpTermAck OBJECT-TYPE
    SYNTAX      Counter32
    MAX-ACCESS  read-only
    STATUS      current
    DESCRIPTION
        "The value of tmnxSubPppStatTxLcpTermAck indicates the number of
         LCP terminate acknowledgements transmitted for this PPP session."
    ::= { tmnxSubPppStatEntry 19 }

tmnxSubPppStatTxLcpCodeRej OBJECT-TYPE
    SYNTAX      Counter32
    MAX-ACCESS  read-only
    STATUS      current
    DESCRIPTION
        "The value of tmnxSubPppStatTxLcpCodeRej indicates the number of
         LCP code rejects transmitted for this PPP session."
    ::= { tmnxSubPppStatEntry 20 }

tmnxSubPppStatTxLcpEchoReq OBJECT-TYPE
    SYNTAX      Counter32
    MAX-ACCESS  read-only
    STATUS      current
    DESCRIPTION
        "The value of tmnxSubPppStatTxLcpEchoReq indicates the number of
         LCP echo requests transmitted for this PPP session."
    ::= { tmnxSubPppStatEntry 21 }

tmnxSubPppStatTxLcpEchoRep OBJECT-TYPE
    SYNTAX      Counter32
    MAX-ACCESS  read-only
    STATUS      current
    DESCRIPTION
        "The value of tmnxSubPppStatTxLcpEchoRep indicates the number of
         LCP echo replies transmitted for this PPP session."
    ::= { tmnxSubPppStatEntry 22 }

tmnxSubPppStatTxLcpProtRej OBJECT-TYPE
    SYNTAX      Counter32
    MAX-ACCESS  read-only
    STATUS      current
    DESCRIPTION
        "The value of tmnxSubPppStatTxLcpProtRej indicates the number of
         LCP protocol rejects transmitted for this PPP session."
    ::= { tmnxSubPppStatEntry 23 }

tmnxSubPppStatTxLcpDiscReq OBJECT-TYPE
    SYNTAX      Counter32
    MAX-ACCESS  read-only
    STATUS      current
    DESCRIPTION
        "The value of tmnxSubPppStatTxLcpDiscReq indicates the number of
         LCP discard requests transmitted for this PPP session."
    ::= { tmnxSubPppStatEntry 24 }

tmnxSubPppStatRxPapAuthReq OBJECT-TYPE
    SYNTAX      Counter32
    MAX-ACCESS  read-only
    STATUS      current
    DESCRIPTION
        "The value of tmnxSubPppStatRxPapAuthReq indicates the number of
         PAP authentication requests received for this PPP session."
    ::= { tmnxSubPppStatEntry 25 }

tmnxSubPppStatTxPapAuthAck OBJECT-TYPE
    SYNTAX      Counter32
    MAX-ACCESS  read-only
    STATUS      current
    DESCRIPTION
        "The value of tmnxSubPppStatTxPapAuthAck indicates the number of
         PAP authentication acknowledgements transmitted for this PPP
         session."
    ::= { tmnxSubPppStatEntry 26 }

tmnxSubPppStatTxPapAuthNak OBJECT-TYPE
    SYNTAX      Counter32
    MAX-ACCESS  read-only
    STATUS      current
    DESCRIPTION
        "The value of tmnxSubPppStatTxPapAuthNak indicates the number of
         negative PAP authentication acknowledgements transmitted for this
         PPP session."
    ::= { tmnxSubPppStatEntry 27 }

tmnxSubPppStatRxChapResponse OBJECT-TYPE
    SYNTAX      Counter32
    MAX-ACCESS  read-only
    STATUS      current
    DESCRIPTION
        "The value of tmnxSubPppStatRxChapResponse indicates the number of
         CHAP authentication responses received for this PPP session."
    ::= { tmnxSubPppStatEntry 28 }

tmnxSubPppStatTxChapChallenge OBJECT-TYPE
    SYNTAX      Counter32
    MAX-ACCESS  read-only
    STATUS      current
    DESCRIPTION
        "The value of tmnxSubPppStatTxChapChallenge indicates the number of
         CHAP authentication challenges transmitted for this PPP session."
    ::= { tmnxSubPppStatEntry 29 }

tmnxSubPppStatTxChapSuccess OBJECT-TYPE
    SYNTAX      Counter32
    MAX-ACCESS  read-only
    STATUS      current
    DESCRIPTION
        "The value of tmnxSubPppStatTxChapSuccess indicates the number of
         CHAP authentication acknowledgements transmitted for this PPP
         session."
    ::= { tmnxSubPppStatEntry 30 }

tmnxSubPppStatTxChapFailure OBJECT-TYPE
    SYNTAX      Counter32
    MAX-ACCESS  read-only
    STATUS      current
    DESCRIPTION
        "The value of tmnxSubPppStatTxChapFailure indicates the number of
         negative CHAP authentication acknowledgements transmitted for this
         PPP session."
    ::= { tmnxSubPppStatEntry 31 }

tmnxSubPppStatRxIpcpConfReq OBJECT-TYPE
    SYNTAX      Counter32
    MAX-ACCESS  read-only
    STATUS      current
    DESCRIPTION
        "The value of tmnxSubPppStatRxIpcpConfReq indicates the number of
         IPCP configure requests received for this PPP session."
    ::= { tmnxSubPppStatEntry 32 }

tmnxSubPppStatRxIpcpConfAck OBJECT-TYPE
    SYNTAX      Counter32
    MAX-ACCESS  read-only
    STATUS      current
    DESCRIPTION
        "The value of tmnxSubPppStatRxIpcpConfAck indicates the number of
         IPCP configure acknowledgements received for this PPP session."
    ::= { tmnxSubPppStatEntry 33 }

tmnxSubPppStatRxIpcpConfNak OBJECT-TYPE
    SYNTAX      Counter32
    MAX-ACCESS  read-only
    STATUS      current
    DESCRIPTION
        "The value of tmnxSubPppStatRxIpcpConfNak indicates the number of
         negative IPCP configure acknowledgements received for this PPP
         session."
    ::= { tmnxSubPppStatEntry 34 }

tmnxSubPppStatRxIpcpConfRej OBJECT-TYPE
    SYNTAX      Counter32
    MAX-ACCESS  read-only
    STATUS      current
    DESCRIPTION
        "The value of tmnxSubPppStatRxIpcpConfRej indicates the number of
         IPCP configure rejects received for this PPP session."
    ::= { tmnxSubPppStatEntry 35 }

tmnxSubPppStatRxIpcpTermReq OBJECT-TYPE
    SYNTAX      Counter32
    MAX-ACCESS  read-only
    STATUS      current
    DESCRIPTION
        "The value of tmnxSubPppStatRxIpcpTermReq indicates the number of
         IPCP terminate requests received for this PPP session."
    ::= { tmnxSubPppStatEntry 36 }

tmnxSubPppStatRxIpcpTermAck OBJECT-TYPE
    SYNTAX      Counter32
    MAX-ACCESS  read-only
    STATUS      current
    DESCRIPTION
        "The value of tmnxSubPppStatRxIpcpTermAck indicates the number of
         IPCP terminate acknowledgements received for this PPP session."
    ::= { tmnxSubPppStatEntry 37 }

tmnxSubPppStatRxIpcpCodeRej OBJECT-TYPE
    SYNTAX      Counter32
    MAX-ACCESS  read-only
    STATUS      current
    DESCRIPTION
        "The value of tmnxSubPppStatRxIpcpCodeRej indicates the number of
         IPCP code rejects received for this PPP session."
    ::= { tmnxSubPppStatEntry 38 }

tmnxSubPppStatTxIpcpConfReq OBJECT-TYPE
    SYNTAX      Counter32
    MAX-ACCESS  read-only
    STATUS      current
    DESCRIPTION
        "The value of tmnxSubPppStatTxIpcpConfReq indicates the number of
         IPCP configure requests transmitted for this PPP session."
    ::= { tmnxSubPppStatEntry 39 }

tmnxSubPppStatTxIpcpConfAck OBJECT-TYPE
    SYNTAX      Counter32
    MAX-ACCESS  read-only
    STATUS      current
    DESCRIPTION
        "The value of tmnxSubPppStatTxIpcpConfAck indicates the number of
         IPCP configure acknowledgements transmitted for this PPP session."
    ::= { tmnxSubPppStatEntry 40 }

tmnxSubPppStatTxIpcpConfNak OBJECT-TYPE
    SYNTAX      Counter32
    MAX-ACCESS  read-only
    STATUS      current
    DESCRIPTION
        "The value of tmnxSubPppStatTxIpcpConfNak indicates the number of
         negative IPCP configure acknowledgements transmitted for this PPP
         session."
    ::= { tmnxSubPppStatEntry 41 }

tmnxSubPppStatTxIpcpConfRej OBJECT-TYPE
    SYNTAX      Counter32
    MAX-ACCESS  read-only
    STATUS      current
    DESCRIPTION
        "The value of tmnxSubPppStatTxIpcpConfRej indicates the number of
         IPCP configure rejects transmitted for this PPP session."
    ::= { tmnxSubPppStatEntry 42 }

tmnxSubPppStatTxIpcpTermReq OBJECT-TYPE
    SYNTAX      Counter32
    MAX-ACCESS  read-only
    STATUS      current
    DESCRIPTION
        "The value of tmnxSubPppStatTxIpcpTermReq indicates the number of
         IPCP terminate requests transmitted for this PPP session."
    ::= { tmnxSubPppStatEntry 43 }

tmnxSubPppStatTxIpcpTermAck OBJECT-TYPE
    SYNTAX      Counter32
    MAX-ACCESS  read-only
    STATUS      current
    DESCRIPTION
        "The value of tmnxSubPppStatTxIpcpTermAck indicates the number of
         IPCP terminate acknowledgements transmitted for this PPP session."
    ::= { tmnxSubPppStatEntry 44 }

tmnxSubPppStatTxIpcpCodeRej OBJECT-TYPE
    SYNTAX      Counter32
    MAX-ACCESS  read-only
    STATUS      current
    DESCRIPTION
        "The value of tmnxSubPppStatTxIpcpCodeRej indicates the number of
         IPCP code rejects transmitted for this PPP session."
    ::= { tmnxSubPppStatEntry 45 }

tmnxSubPppStatRxIpv6cpConfReq OBJECT-TYPE
    SYNTAX      Counter32
    MAX-ACCESS  read-only
    STATUS      current
    DESCRIPTION
        "The value of tmnxSubPppStatRxIpv6cpConfReq indicates the number of
         IPv6 Control Protocol (IPv6CP) configure requests received 
         for this PPP session."
    ::= { tmnxSubPppStatEntry 46 }

tmnxSubPppStatRxIpv6cpConfAck OBJECT-TYPE
    SYNTAX      Counter32
    MAX-ACCESS  read-only
    STATUS      current
    DESCRIPTION
        "The value of tmnxSubPppStatRxIpv6cpConfAck indicates the number of
         IPv6CP configure acknowledgements received for this PPP session."
    ::= { tmnxSubPppStatEntry 47 }

tmnxSubPppStatRxIpv6cpConfNak OBJECT-TYPE
    SYNTAX      Counter32
    MAX-ACCESS  read-only
    STATUS      current
    DESCRIPTION
        "The value of tmnxSubPppStatRxIpv6cpConfNak indicates the number of
         negative IPv6CP configure acknowledgements received for this PPP
         session."
    ::= { tmnxSubPppStatEntry 48 }

tmnxSubPppStatRxIpv6cpConfRej OBJECT-TYPE
    SYNTAX      Counter32
    MAX-ACCESS  read-only
    STATUS      current
    DESCRIPTION
        "The value of tmnxSubPppStatRxIpv6cpConfRej indicates the number of
         IPv6CP configure rejects received for this PPP session."
    ::= { tmnxSubPppStatEntry 49 }

tmnxSubPppStatRxIpv6cpTermReq OBJECT-TYPE
    SYNTAX      Counter32
    MAX-ACCESS  read-only
    STATUS      current
    DESCRIPTION
        "The value of tmnxSubPppStatRxIpv6cpTermReq indicates the number of
         IPv6CP terminate requests received for this PPP session."
    ::= { tmnxSubPppStatEntry 50 }

tmnxSubPppStatRxIpv6cpTermAck OBJECT-TYPE
    SYNTAX      Counter32
    MAX-ACCESS  read-only
    STATUS      current
    DESCRIPTION
        "The value of tmnxSubPppStatRxIpv6cpTermAck indicates the number of
         IPv6CP terminate acknowledgements received for this PPP session."
    ::= { tmnxSubPppStatEntry 51 }

tmnxSubPppStatRxIpv6cpCodeRej OBJECT-TYPE
    SYNTAX      Counter32
    MAX-ACCESS  read-only
    STATUS      current
    DESCRIPTION
        "The value of tmnxSubPppStatRxIpv6cpCodeRej indicates the number of
         IPv6CP code rejects received for this PPP session."
    ::= { tmnxSubPppStatEntry 52 }

tmnxSubPppStatTxIpv6cpConfReq OBJECT-TYPE
    SYNTAX      Counter32
    MAX-ACCESS  read-only
    STATUS      current
    DESCRIPTION
        "The value of tmnxSubPppStatTxIpv6cpConfReq indicates the number of
         IPv6CP configure requests transmitted for this PPP session."
    ::= { tmnxSubPppStatEntry 53 }

tmnxSubPppStatTxIpv6cpConfAck OBJECT-TYPE
    SYNTAX      Counter32
    MAX-ACCESS  read-only
    STATUS      current
    DESCRIPTION
        "The value of tmnxSubPppStatTxIpv6cpConfAck indicates the number of
         IPv6CP configure acknowledgements transmitted for this PPP session."
    ::= { tmnxSubPppStatEntry 54 }

tmnxSubPppStatTxIpv6cpConfNak OBJECT-TYPE
    SYNTAX      Counter32
    MAX-ACCESS  read-only
    STATUS      current
    DESCRIPTION
        "The value of tmnxSubPppStatTxIpv6cpConfNak indicates the number of
         negative IPv6CP configure acknowledgements transmitted for this PPP
         session."
    ::= { tmnxSubPppStatEntry 55 }

tmnxSubPppStatTxIpv6cpConfRej OBJECT-TYPE
    SYNTAX      Counter32
    MAX-ACCESS  read-only
    STATUS      current
    DESCRIPTION
        "The value of tmnxSubPppStatTxIpv6cpConfRej indicates the number of
         IPv6CP configure rejects transmitted for this PPP session."
    ::= { tmnxSubPppStatEntry 56 }

tmnxSubPppStatTxIpv6cpTermReq OBJECT-TYPE
    SYNTAX      Counter32
    MAX-ACCESS  read-only
    STATUS      current
    DESCRIPTION
        "The value of tmnxSubPppStatTxIpv6cpTermReq indicates the number of
         IPv6CP terminate requests transmitted for this PPP session."
    ::= { tmnxSubPppStatEntry 57 }

tmnxSubPppStatTxIpv6cpTermAck OBJECT-TYPE
    SYNTAX      Counter32
    MAX-ACCESS  read-only
    STATUS      current
    DESCRIPTION
        "The value of tmnxSubPppStatTxIpv6cpTermAck indicates the number of
         IPv6CP terminate acknowledgements transmitted for this PPP session."
    ::= { tmnxSubPppStatEntry 58 }

tmnxSubPppStatTxIpv6cpCodeRej OBJECT-TYPE
    SYNTAX      Counter32
    MAX-ACCESS  read-only
    STATUS      current
    DESCRIPTION
        "The value of tmnxSubPppStatTxIpv6cpCodeRej indicates the number of
         IPv6CP code rejects transmitted for this PPP session."
        ::= { tmnxSubPppStatEntry 59 }

--
--      The Subscriber PPP Session Managed Route Table
--

tmnxSubPppMRtTable   OBJECT-TYPE
    SYNTAX      SEQUENCE OF TmnxSubPppMRtEntry
    MAX-ACCESS  not-accessible
    STATUS      current
    DESCRIPTION
       "The tmnxSubPppMRtTable contains managed routes  
        for Subscriber PPP Sessions.

        Entries in this table are created and destroyed by the system."
    ::= { tmnxSubPppObjs 3 }

tmnxSubPppMRtEntry   OBJECT-TYPE
    SYNTAX      TmnxSubPppMRtEntry
    MAX-ACCESS  not-accessible
    STATUS      current
    DESCRIPTION
       "Each conceptual row represents a managed route
        of a Subscriber PPP Session."
    INDEX { tmnxSubPppIndex,
            tmnxSubPppMRtAddrType,
            tmnxSubPppMRtAddr,
            tmnxSubPppMRtPrefixLen }
    ::= { tmnxSubPppMRtTable 1 }

TmnxSubPppMRtEntry ::= 
    SEQUENCE {
        tmnxSubPppMRtAddrType          InetAddressType,
        tmnxSubPppMRtAddr              InetAddress,
        tmnxSubPppMRtPrefixLen         InetAddressPrefixLength,
        tmnxSubPppMRtStatus            TmnxManagedRouteStatus
       ,tmnxSubPppMRtMetric            TmnxRadiusFramedRouteMetric,
        tmnxSubPppMRtPreference        TmnxRadiusFramedRoutePreference,
        tmnxSubPppMRtTag               TmnxRadiusFramedRouteTag             
    }
        
tmnxSubPppMRtAddrType OBJECT-TYPE
    SYNTAX          InetAddressType
    MAX-ACCESS      not-accessible
    STATUS          current
    DESCRIPTION     "The value of tmnxSubPppMRtAddrType indicates
                     the address type of tmnxSubPppMRtAddr."
    ::= { tmnxSubPppMRtEntry 1 }

tmnxSubPppMRtAddr OBJECT-TYPE
    SYNTAX          InetAddress (SIZE(4|16))
    MAX-ACCESS      not-accessible
    STATUS          current
    DESCRIPTION     "The value of tmnxSubPppMRtAddr indicates
                     the IP address of the managed route."
    ::= { tmnxSubPppMRtEntry 2 }

tmnxSubPppMRtPrefixLen OBJECT-TYPE
    SYNTAX          InetAddressPrefixLength
    MAX-ACCESS      not-accessible
    STATUS          current
    DESCRIPTION     "The value of tmnxSubPppMRtPrefixLen indicates
                     the prefix length of the subnet associated with
                     tmnxSubPppMRtAddr."
    ::= { tmnxSubPppMRtEntry 3 }

tmnxSubPppMRtStatus OBJECT-TYPE
    SYNTAX          TmnxManagedRouteStatus
    MAX-ACCESS      read-only
    STATUS          current
    DESCRIPTION     "The value of tmnxSubPppMRtStatus indicates
                     the state of this managed route."
    ::= { tmnxSubPppMRtEntry 4 }

tmnxSubPppMRtMetric OBJECT-TYPE
    SYNTAX          TmnxRadiusFramedRouteMetric
    MAX-ACCESS      read-only
    STATUS          current
    DESCRIPTION     "The value of tmnxSubPppMRtMetric indicates
                     the metric of this managed route as specified
                     in the RADIUS option 22 Framed-Route or 
                     option 99 Framed-IPv6-Route."
    ::= { tmnxSubPppMRtEntry 5 }

tmnxSubPppMRtPreference OBJECT-TYPE
    SYNTAX          TmnxRadiusFramedRoutePreference
    MAX-ACCESS      read-only
    STATUS          current
    DESCRIPTION     "The value of tmnxSubPppMRtPreference indicates
                     the preference of this managed route as specified
                     in the RADIUS option 22 Framed-Route or 
                     option 99 Framed-IPv6-Route."
    ::= { tmnxSubPppMRtEntry 6 }

tmnxSubPppMRtTag OBJECT-TYPE
    SYNTAX          TmnxRadiusFramedRouteTag
    MAX-ACCESS      read-only
    STATUS          current
    DESCRIPTION     "The value of tmnxSubPppMRtTag indicates
                     the tag of this managed route as specified
                     in the RADIUS option 22 Framed-Route or 
                     option 99 Framed-IPv6-Route."
    ::= { tmnxSubPppMRtEntry 7 }

--
--      The Subscriber PPP Session Overrides Table
--

tmnxSubPppOvrTable   OBJECT-TYPE
    SYNTAX      SEQUENCE OF TmnxSubPppOvrEntry
    MAX-ACCESS  not-accessible
    STATUS      current
    DESCRIPTION
       "The tmnxSubPppOvrTable contains QoS (Quality of Service) overrides for 
        Subscriber PPP Sessions.

        Entries in this table are created and destroyed by the system."
        ::= { tmnxSubPppObjs 4 }

tmnxSubPppOvrEntry   OBJECT-TYPE
    SYNTAX      TmnxSubPppOvrEntry
    MAX-ACCESS  not-accessible
    STATUS      current
    DESCRIPTION
       "Each conceptual row represents QoS overrides information
        of a Subscriber PPP Session."
    INDEX { tmnxSubPppIndex,
            tmnxSubPppOvrDirection,
            tmnxSubPppOvrType,
            tmnxSubPppOvrTypeId,
            tmnxSubPppOvrTypeName }
    ::= { tmnxSubPppOvrTable 1 }

TmnxSubPppOvrEntry ::= 
    SEQUENCE {
        tmnxSubPppOvrDirection         TDirectionIngEgr,
        tmnxSubPppOvrType              TQosOverrideType,
        tmnxSubPppOvrTypeId            Integer32,
        tmnxSubPppOvrTypeName          TNamedItemOrEmpty,
        tmnxSubPppOvrPIR               TPIRRateOverride,
        tmnxSubPppOvrCIR               TCIRRateOverride,
        tmnxSubPppOvrCBS               TBurstSizeBytesOvr,
        tmnxSubPppOvrMBS               TBurstSizeBytesOvr,
        tmnxSubPppOvrWrrWeight         THsmdaWrrWeightOverride,
        tmnxSubPppOvrPIRHi             Unsigned32,
        tmnxSubPppOvrPIRLo             Unsigned32,
        tmnxSubPppOvrCIRHi             Unsigned32,
        tmnxSubPppOvrCIRLo             Unsigned32,
        tmnxSubPppOvrSummedCIR         TruthValue
    }
        
tmnxSubPppOvrDirection OBJECT-TYPE
    SYNTAX          TDirectionIngEgr
    MAX-ACCESS      not-accessible
    STATUS          current
    DESCRIPTION     "The value of tmnxSubPppOvrDirection indicates if
                     this row specifies ingress or egress qos override 
                     parameters."
    ::= { tmnxSubPppOvrEntry 1 }

tmnxSubPppOvrType OBJECT-TYPE
    SYNTAX          TQosOverrideType
    MAX-ACCESS      not-accessible
    STATUS          current
    DESCRIPTION     "The value of tmnxSubPppOvrType indicates what field
                     has been overridden by this row."
    ::= { tmnxSubPppOvrEntry 2 }

tmnxSubPppOvrTypeId OBJECT-TYPE
    SYNTAX          Integer32
    MAX-ACCESS      not-accessible
    STATUS          current
    DESCRIPTION     "The value of tmnxSubPppOvrTypeId indicates the ID of
                     the queue/policer that has been overridden by this row.
                     
                     If the value of tmnxSubPppOvrType is not 'queue (1)'
                     or 'policer (2)', this field must be set to zero (0)."
    ::= { tmnxSubPppOvrEntry 3 }

tmnxSubPppOvrTypeName OBJECT-TYPE
    SYNTAX          TNamedItemOrEmpty
    MAX-ACCESS      not-accessible
    STATUS          current
    DESCRIPTION     "The value of tmnxSubPppOvrTypeName indicates the
                     name of the scheduler/arbiter that has been overridden by
                     this row.
                     
                     If the value of tmnxSubPppOvrType is not 
                     'arbiter (4)' or 'scheduler (5)', this field must be set to
                     zero (0)."
    ::= { tmnxSubPppOvrEntry 4 }

tmnxSubPppOvrPIR OBJECT-TYPE
    SYNTAX          TPIRRateOverride
    MAX-ACCESS      read-only
    STATUS          obsolete
    DESCRIPTION     "The value of tmnxSubPppOvrPIR indicates the PIR rate
                     in kbps allowed for the object overridden by this row.

                     This object is obsoleted in 11.0 Release. It is replaced by 
                     tmnxSubPppOvrPIRHi and tmnxSubPppOvrPIRLo."
    ::= { tmnxSubPppOvrEntry 5 }

tmnxSubPppOvrCIR OBJECT-TYPE
    SYNTAX          TCIRRateOverride
    MAX-ACCESS      read-only
    STATUS          obsolete
    DESCRIPTION     "The value of tmnxSubPppOvrCIR indicates the CIR rate
                     in kbps allowed for the object overridden by this row.

                     This object is obsoleted in 11.0 Release. It is replaced by 
                     tmnxSubPppOvrCIRHi and tmnxSubPppOvrCIRLo."
    ::= { tmnxSubPppOvrEntry 6 }

tmnxSubPppOvrCBS OBJECT-TYPE
    SYNTAX          TBurstSizeBytesOvr
    MAX-ACCESS      read-only
    STATUS          current
    DESCRIPTION     "The value of tmnxSubPppOvrCBS indicates the amount of
                     reserved buffer space (in bytes) for the object
                     overridden by this row."
    ::= { tmnxSubPppOvrEntry 7 }

tmnxSubPppOvrMBS OBJECT-TYPE
    SYNTAX          TBurstSizeBytesOvr
    MAX-ACCESS      read-only
    STATUS          current
    DESCRIPTION     "The value of tmnxSubPppOvrMBS indicates the maximum
                     amount of reserved buffer space (in bytes) for the object
                     overridden by this row."
    ::= { tmnxSubPppOvrEntry 8 }

tmnxSubPppOvrWrrWeight OBJECT-TYPE
    SYNTAX          THsmdaWrrWeightOverride
    MAX-ACCESS      read-only
    STATUS          current
    DESCRIPTION     
    "The value of tmnxSubPppOvrWrrWeight specifies the weight of this queue
     for the HSMDA scheduler.
     
     The weight determines how much bandwidth this queue gets out of the 
     total rate for the scheduling class.
     
     The value of tmnxSubPppOvrWrrWeight is only relevant if the value of
     tmnxSubPppOvrType is equal to 'queue', and if the queue specified in
     tmnxSubPppOvrTypeId is referenced in the value of 
     TIMETRA-QOS-MIB::tHsmdaWrrPolicyIncludeQueues of the Weighted Round Robin
     policy associated wit this PPP session."
    ::= { tmnxSubPppOvrEntry 9 }

tmnxSubPppOvrPIRHi OBJECT-TYPE
    SYNTAX       Unsigned32 (0 | 4294967295)
    UNITS        "kbps"
    MAX-ACCESS   read-only
    STATUS       current
    DESCRIPTION
        "The value of tmnxSubPppOvrPIRHi indicates upper 32 bits of the PIR rate
         allowed for the object overwritten by this row.    

         When the value of tmnxSubPppOvrPIRHi along with the value of 
         tmnxSubPppOvrPIRLo is equal to 4294967295 (0xFFFFFFFF), rate for this
         scheduler indicates maximum rate.

         The value of tmnxSubPppOvrPIRHi equal to 4294967295 (0xFFFFFFFF) and 
         the value of tmnxSubPppOvrPIRLo equal to 4294967294 (0xFFFFFFFE) 
         indicates no overrides."
    ::= { tmnxSubPppOvrEntry 10 }

tmnxSubPppOvrPIRLo OBJECT-TYPE
    SYNTAX       Unsigned32 (1..3200000000 | 4294967294 | 4294967295)
    UNITS        "kbps"
    MAX-ACCESS   read-only
    STATUS       current
    DESCRIPTION
        "The value of tmnxSubPppOvrPIRHi indicates lower 32 bits of the PIR rate
         allowed for the object overwritten by this row.    
    
         When the value of tmnxSubPppOvrPIRHi along with the value of 
         tmnxSubPppOvrPIRLo is equal to 4294967295 (0xFFFFFFFF), rate for
         this scheduler indicates maximum rate.
    
         The value of tmnxSubPppOvrPIRHi equal to 4294967295 (0xFFFFFFFF) and 
         the value of tmnxSubPppOvrPIRLo equal to 4294967294 (0xFFFFFFFE) 
         indicates no overrides."
    ::= { tmnxSubPppOvrEntry 11 }

tmnxSubPppOvrCIRHi OBJECT-TYPE
    SYNTAX       Unsigned32 (0 | 4294967295)
    UNITS        "kbps"
    MAX-ACCESS   read-only
    STATUS       current
    DESCRIPTION
        "The value of tmnxSubPppOvrCIRHi indicates upper 32 bits of the CIR rate
         allowed for the object overwritten by this row.    

         When the value of tmnxSubPppOvrCIRHi along with the value of 
         tmnxSubPppOvrCIRLo is equal to 4294967295 (0xFFFFFFFF), rate for
         this scheduler indicates maximum rate.

         The value of tmnxSubPppOvrCIRHi equal to 4294967295 (0xFFFFFFFF) and 
         the value of tmnxSubPppOvrCIRLo equal to 4294967294 (0xFFFFFFFE) 
         indicates no overrides."
    ::= { tmnxSubPppOvrEntry 12 }

tmnxSubPppOvrCIRLo OBJECT-TYPE
    SYNTAX       Unsigned32 (0..3200000000 | 4294967294 | 4294967295)
    UNITS        "kbps"
    MAX-ACCESS   read-only
    STATUS       current
    DESCRIPTION
        "The value of tmnxSubPppOvrCIRHi indicates lower 32 bits of the CIR rate
         allowed for the object overwritten by this row.    
    
         When the value of tmnxSubPppOvrCIRHi along with the value of 
         tmnxSubPppOvrCIRLo is equal to 4294967295 (0xFFFFFFFF), rate for
         this scheduler indicates maximum rate.
    
         The value of tmnxSubPppOvrCIRHi equal to 4294967295 (0xFFFFFFFF) and 
         the value of tmnxSubPppOvrCIRLo equal to 4294967294 (0xFFFFFFFE) 
         indicates no overrides."
    ::= { tmnxSubPppOvrEntry 13 }

tmnxSubPppOvrSummedCIR OBJECT-TYPE
    SYNTAX      TruthValue
    MAX-ACCESS  read-only
    STATUS      current
    DESCRIPTION
        "The value of tmnxSubPppOvrSummedCIR indicates if the CIR should
         be used as the summed CIR values of the children schedulers or queues.
         If set to 'true', the applicable scheduler CIR (tmnxSubPppOvrCIRHi and
         tmnxSubPppOvrCIRLo) loses its meaning.

         The value of tmnxSubPppOvrCIRHi equal to 4294967295 (0xFFFFFFFF) and 
         the value of tmnxSubPppOvrCIRLo equal to 4294967294 (0xFFFFFFFE) 
         indicates no overrides."
    ::= { tmnxSubPppOvrEntry 14 }

--
--      The Subscriber PPP Session Access Loop Encapsulation Table
--

tmnxSubPppAleTable   OBJECT-TYPE
    SYNTAX      SEQUENCE OF TmnxSubPppAleEntry
    MAX-ACCESS  not-accessible
    STATUS      current
    DESCRIPTION
       "The tmnxSubPppAleTable contains Access Loop (Encapsulation) information
        for Subscriber PPP Sessions .

        Entries in this table are created and destroyed by the system.
        
        This table is a sparse augment of the tmnxSubPppTable: entries
        are created only for Subscriber PPP sessions 
        for which Access Loop (Encapsulation) information is available."
    ::= { tmnxSubPppObjs 5 }

tmnxSubPppAleEntry   OBJECT-TYPE
    SYNTAX      TmnxSubPppAleEntry
    MAX-ACCESS  not-accessible
    STATUS      current
    DESCRIPTION
       "Each conceptual row represents access loop (encapsulation) information
        of a Subscriber PPP session."
    INDEX { tmnxSubPppIndex }
    ::= { tmnxSubPppAleTable 1 }

TmnxSubPppAleEntry ::= 
    SEQUENCE {
        tmnxSubPppAleDatalink           TmnxAccessLoopEncapDataLink,
        tmnxSubPppAleEncaps1            TmnxAccessLoopEncaps1,      
        tmnxSubPppAleEncaps2            TmnxAccessLoopEncaps2,
        tmnxSubPppAleOrigin             TmnxPppoeSessionInfoOrigin,
        tmnxSubPppAleLinkRateDown       Unsigned32,
        tmnxSubPppAleLinkRateDownOrigin TmnxPppoeSessionInfoOrigin              
    }
        
tmnxSubPppAleDatalink OBJECT-TYPE
    SYNTAX          TmnxAccessLoopEncapDataLink
    MAX-ACCESS      read-only
    STATUS          current
    DESCRIPTION     "The value of tmnxSubPppAleDatalink indicates 
                     the data link used by the subscriber host 
                     on the DSL access loop."
    ::= { tmnxSubPppAleEntry 1 }

tmnxSubPppAleEncaps1 OBJECT-TYPE
    SYNTAX          TmnxAccessLoopEncaps1
    MAX-ACCESS      read-only
    STATUS          current
    DESCRIPTION     "The value of tmnxSubPppAleEncaps1 indicates 
                     the encapsulation used by the subscriber host 
                     on the DSL access loop."
    ::= { tmnxSubPppAleEntry 2 }

tmnxSubPppAleEncaps2 OBJECT-TYPE
    SYNTAX          TmnxAccessLoopEncaps2
    MAX-ACCESS      read-only
    STATUS          current
    DESCRIPTION     "The value of tmnxSubPppAleEncaps2 indicates 
                     the encapsulation used by the subscriber host 
                     on the DSL access loop."
    ::= { tmnxSubPppAleEntry 3 }

tmnxSubPppAleOrigin OBJECT-TYPE
    SYNTAX          TmnxPppoeSessionInfoOrigin
    MAX-ACCESS      read-only
    STATUS          current
    DESCRIPTION     "The value of tmnxSubPppAleOrigin indicates the origin of 
                     the information in this conceptual row."
    ::= { tmnxSubPppAleEntry 4 }

tmnxSubPppAleLinkRateDown OBJECT-TYPE
    SYNTAX          Unsigned32
    UNITS           "kbps"
    MAX-ACCESS      read-only
    STATUS          current
    DESCRIPTION     "The value of tmnxSubPppAleLinkRateDown indicates 
                     the nominal downstream rate for the link 
                     associated with this session.
         
                     If the link rate is not applicable or unknown, 
                     the value of this object is equal to zero."
    ::= { tmnxSubPppAleEntry 5 }
    
tmnxSubPppAleLinkRateDownOrigin OBJECT-TYPE
    SYNTAX          TmnxPppoeSessionInfoOrigin
    MAX-ACCESS      read-only
    STATUS          current
    DESCRIPTION     "The value of tmnxSubPppAleLinkRateDownOrigin indicates
                     the origin of tmnxSubPppAleLinkRateDown."
    ::= { tmnxSubPppAleEntry 6 }


--
--      The Subscriber PPP Session BGP Peering Table
--

--  Augmentation of the tmnxSubPppTable
--  Use of AUGMENTS clause implies a one-to-one dependent relationship
--  between the base table, tmnxSubPppTable, and the augmenting table,
--  tmnxSubPppBgpTable. This in effect extends the tmnxSubPppTable
--  with additional columns. Creation (or deletion) of a row in the
--  tmnxSubPppTable results in the same fate for the row in the
--  tmnxSubPppBgpTable.

tmnxSubPppBgpTable OBJECT-TYPE
    SYNTAX          SEQUENCE OF TmnxSubPppBgpEntry
    MAX-ACCESS      not-accessible
    STATUS          current
    DESCRIPTION     
        "The tmnxSubPppBgpTable augments the tmnxSubPppTable."
    ::= { tmnxSubPppObjs 6 }

tmnxSubPppBgpEntry OBJECT-TYPE
    SYNTAX          TmnxSubPppBgpEntry
    MAX-ACCESS      not-accessible
    STATUS          current
    DESCRIPTION     
        "Each conceptual row contains BGP peering information about a
         Subscriber PPP session."
    AUGMENTS { tmnxSubPppEntry }
    ::= { tmnxSubPppBgpTable 1 }

TmnxSubPppBgpEntry ::=
    SEQUENCE {
        tmnxSubPppBgpPrngPlcyName   TNamedItemOrEmpty,
        tmnxSubPppBgpAuthKeyChain   TNamedItemOrEmpty,
        tmnxSubPppBgpMD5AuthKey     OCTET STRING,
        tmnxSubPppBgpImportPolicy   TPolicyStatementNameOrEmpty,
        tmnxSubPppBgpExportPolicy   TPolicyStatementNameOrEmpty,
        tmnxSubPppBgpPeerAS         InetAutonomousSystemNumber,
        tmnxSubPppBgpPeeringStatus  BgpPeeringStatus
    }

tmnxSubPppBgpPrngPlcyName OBJECT-TYPE
    SYNTAX          TNamedItemOrEmpty
    MAX-ACCESS      read-only
    STATUS          current
    DESCRIPTION
        "The value of tmnxSubPppBgpPrngPlcyName indicates the
         peering policy which is used to set up the BGP peer for this
         session."
    ::= { tmnxSubPppBgpEntry 1 }

tmnxSubPppBgpAuthKeyChain OBJECT-TYPE
    SYNTAX          TNamedItemOrEmpty
    MAX-ACCESS      read-only
    STATUS          current
    DESCRIPTION
        "The value of tmnxSubPppBgpAuthKeyChain indicates the
         keychain which is used to sign and/or authenticate the BGP
         protocol stream."
    ::= { tmnxSubPppBgpEntry 2 }

tmnxSubPppBgpMD5AuthKey OBJECT-TYPE
    SYNTAX          OCTET STRING (SIZE(0..255))
    MAX-ACCESS      read-only
    STATUS          current
    DESCRIPTION     
        "The value of tmnxSubPppBgpMD5AuthKey indicates the 
         authentication key used between BGP peers neighbors before
         establishing sessions. Authentication is done using the
         MD-5 message based digest protocol."
    ::= { tmnxSubPppBgpEntry 3 }

tmnxSubPppBgpImportPolicy OBJECT-TYPE
    SYNTAX          TPolicyStatementNameOrEmpty
    MAX-ACCESS      read-only
    STATUS          current
    DESCRIPTION     
        "The value of tmnxSubPppBgpImportPolicy indicates 
         the import policy."
    ::= { tmnxSubPppBgpEntry 4 }

tmnxSubPppBgpExportPolicy OBJECT-TYPE
    SYNTAX          TPolicyStatementNameOrEmpty
    MAX-ACCESS      read-only
    STATUS          current
    DESCRIPTION     
        "The value of tmnxSubPppBgpExportPolicy indicates 
         the export policy."
    ::= { tmnxSubPppBgpEntry 5 }

tmnxSubPppBgpPeerAS OBJECT-TYPE
    SYNTAX          InetAutonomousSystemNumber
    MAX-ACCESS      read-only
    STATUS          current
    DESCRIPTION     
        "The value of tmnxSubPppBgpPeerAS indicates the Autonomous System
         number for the remote peer."
    ::= { tmnxSubPppBgpEntry 6 }

tmnxSubPppBgpPeeringStatus OBJECT-TYPE
    SYNTAX          BgpPeeringStatus
    MAX-ACCESS      read-only
    STATUS          current
    DESCRIPTION
        "The value of tmnxSubPppBgpPeeringStatus indicates
         the status of the BGP peering session."
    ::= { tmnxSubPppBgpEntry 7 }

-- 
-- tmnxSubPppModTable
-- 

--  Augmentation of the tmnxSubPppTable
--  Use of AUGMENTS clause implies a one-to-one dependent relationship
--  between the base table, tmnxSubPppTable, and the augmenting table,
--  tmnxSubPppModTable. This in effect extends the tmnxSubPppTable
--  with additional columns. Creation (or deletion) of a row in the
--  tmnxSubPppTable results in the same fate for the row in the
--  tmnxSubPppModTable.

tmnxSubPppModTable OBJECT-TYPE
    SYNTAX      SEQUENCE OF TmnxSubPppModEntry
    MAX-ACCESS  not-accessible
    STATUS      current
    DESCRIPTION
        "The tmnxSubPppModTable augments the tmnxSubPppTable.
         The table allows the operator to modify attributes 
         of the Subscriber PPP Session."
    ::= { tmnxSubPppObjs 7 }

tmnxSubPppModEntry OBJECT-TYPE
    SYNTAX      TmnxSubPppModEntry
    MAX-ACCESS  not-accessible
    STATUS      current
    DESCRIPTION
        "Each row entry contains parameters that allow to modify a
         subscriber PPP session's attributes."
    AUGMENTS { tmnxSubPppEntry }
    ::= { tmnxSubPppModTable 1 }

TmnxSubPppModEntry ::=
    SEQUENCE {
        tmnxSubPppModSubIdent            TmnxSubIdentStringOrEmpty,
        tmnxSubPppModSubProfStr          TmnxSubProfileStringOrEmpty,
        tmnxSubPppModSlaProfStr          TmnxSlaProfileStringOrEmpty,
        tmnxSubPppModAncpStr             TmnxAncpStringOrZero,
        tmnxSubPppModInterDestId         TmnxSubMgtIntDestIdOrEmpty,
        tmnxSubPppModAppProfStr          TmnxAppProfileStringOrEmpty,
        tmnxSubPppModEvaluateState       TruthValue
    }

tmnxSubPppModSubIdent OBJECT-TYPE
    SYNTAX      TmnxSubIdentStringOrEmpty
    MAX-ACCESS  read-write
    STATUS      current
    DESCRIPTION
        "The value of tmnxSubPppModSubIdent allows to specify a new
         subscriber name for this session.

         When a SET of this object is done with a non empty string, the system
         will attempt to assign a new subscriber name.

         A SET with an empty string has no effect on the system. (NOOP).

         GETs and GETNEXTs on this variable return an empty string."
    DEFVAL { "" }
    ::= { tmnxSubPppModEntry 1 }

tmnxSubPppModSubProfStr OBJECT-TYPE
    SYNTAX      TmnxSubProfileStringOrEmpty
    MAX-ACCESS  read-write
    STATUS      current
    DESCRIPTION
        "The value of tmnxSubPppModSubProfStr allows to specify a new
         subscriber profile string for this session.

         When a SET of this object is done with a non empty string, the system
         will attempt to assign a new subscriber profile string.

         A SET with an empty string has no effect on the system. (NOOP).

         GETs and GETNEXTs on this variable return an empty string."
    DEFVAL { "" }
    ::= { tmnxSubPppModEntry 2 }

tmnxSubPppModSlaProfStr OBJECT-TYPE
    SYNTAX      TmnxSlaProfileStringOrEmpty
    MAX-ACCESS  read-write
    STATUS      current
    DESCRIPTION
        "The value of tmnxSubPppModSlaProfStr allows to specify a new
         SLA profile string for this session.

         When a SET of this object is done with a non empty string, the system
         will attempt to assign a new SLA profile string.

         A SET with an empty string has no effect on the system. (NOOP).

         GETs and GETNEXTs on this variable return an empty string."
    DEFVAL { "" }
    ::= { tmnxSubPppModEntry 3 }

tmnxSubPppModAncpStr OBJECT-TYPE
    SYNTAX      TmnxAncpStringOrZero
    MAX-ACCESS  read-write
    STATUS      current
    DESCRIPTION
        "The value of tmnxSubPppModAncpStr allows to specify a new
         ANCP-string for this session.

         When a SET of this object is done with a non empty string, the system
         will attempt to assign a new ANCP-string.

         A SET with an empty string has no effect on the system. (NOOP).

         GETs and GETNEXTs on this variable return an empty string."
    DEFVAL { "" }
    ::= { tmnxSubPppModEntry 4 }

tmnxSubPppModInterDestId OBJECT-TYPE
    SYNTAX      TmnxSubMgtIntDestIdOrEmpty
    MAX-ACCESS  read-write
    STATUS      current
    DESCRIPTION
        "The value of tmnxSubPppModInterDestId allows to specify a new
         intermediate destination id for this session.

         When a SET of this object is done with a non empty string, the system
         will attempt to assign a new intermediate destination id.

         A SET with an empty string has no effect on the system. (NOOP).

         GETs and GETNEXTs on this variable return an empty string."
    DEFVAL { "" }
    ::= { tmnxSubPppModEntry 5 }

tmnxSubPppModAppProfStr OBJECT-TYPE
    SYNTAX      TmnxAppProfileStringOrEmpty
    MAX-ACCESS  read-write
    STATUS      current
    DESCRIPTION
        "The value of tmnxSubPppModAppProfStr specifies a new
         application profile string for this session.

         When a SET of this object is done with a non empty string, the system
         will attempt to assign a new application profile string.

         A SET with an empty string has no effect on the system. (NOOP).

         GETs and GETNEXTs on this variable return an empty string."
    DEFVAL { "" }
    ::= { tmnxSubPppModEntry 6 }

tmnxSubPppModEvaluateState OBJECT-TYPE
    SYNTAX      TruthValue
    MAX-ACCESS  read-write
    STATUS      current
    DESCRIPTION
        "The value of tmnxSubPppModEvaluateState allows to cause a
         re-evaluation of the specified session.

         When this object is set to 'true', the system will perform a
         re-evaluation of the session.

         GETs and GETNEXTs on this variable return false.

         It is not possible to simultaneously request for a session
         re-evaluation, and modify any of the strings."
    DEFVAL { false }
    ::= { tmnxSubPppModEntry 7 }

--
--      The Subscriber PPP Types Table
--

tmnxSubPppSessions  OBJECT-TYPE
    SYNTAX          Gauge32
    MAX-ACCESS      read-only
    STATUS          current
    DESCRIPTION
        "The value of tmnxSubPppSessions indicates the
         actual number of subscriber PPP sessions in the system."
     ::= { tmnxSubPppObjs 8 }

tmnxSubPppTypeTable   OBJECT-TYPE
    SYNTAX      SEQUENCE OF TmnxSubPppTypeEntry
    MAX-ACCESS  not-accessible
    STATUS      current
    DESCRIPTION
       "The tmnxSubPppTypeTable has an entry for each each type of
        subscriber PPP Session."
    ::= { tmnxSubPppObjs 9 }

tmnxSubPppTypeEntry   OBJECT-TYPE
    SYNTAX      TmnxSubPppTypeEntry
    MAX-ACCESS  not-accessible
    STATUS      current
    DESCRIPTION
       "Each conceptual row represents information about a specific type of
        subscriber PPP.

        Entries in this table are created and destroyed by the system."
    INDEX { tmnxSubPppTypeIndex }
    ::= { tmnxSubPppTypeTable 1 }

TmnxSubPppTypeEntry ::= 
    SEQUENCE {
        tmnxSubPppTypeIndex              TmnxSubPppType,
        tmnxSubPppTypeSessions           Gauge32
    }
        
tmnxSubPppTypeIndex OBJECT-TYPE
    SYNTAX      TmnxSubPppType
    MAX-ACCESS  not-accessible
    STATUS      current
    DESCRIPTION
       "The value of the object tmnxSubPppTypeIndex indicates the type of
        subscriber PPP."
    ::= { tmnxSubPppTypeEntry 1 }

tmnxSubPppTypeSessions OBJECT-TYPE
    SYNTAX      Gauge32
    MAX-ACCESS  read-only
    STATUS      current
    DESCRIPTION
       "The value of the object tmnxSubPppTypeSessions indicates  
        the actual number of PPP session of this type."
    ::= { tmnxSubPppTypeEntry 2 }

--
--      The Subscriber PPP User Table
--

tmnxSubPppUserTable   OBJECT-TYPE
    SYNTAX      SEQUENCE OF TmnxSubPppUserEntry
    MAX-ACCESS  not-accessible
    STATUS      current
    DESCRIPTION
       "The tmnxSubPppUserTable represents the subscriber PPP sessions
        ordered by user name.
        
        Any MLPPP bundle sessions are present in this table, but not MLPPP
        link sessions."
    ::= { tmnxSubPppObjs 10 }

tmnxSubPppUserEntry   OBJECT-TYPE
    SYNTAX      TmnxSubPppUserEntry
    MAX-ACCESS  not-accessible
    STATUS      current
    DESCRIPTION
       "Each conceptual row represents a Subscriber PPP Session.

        Entries in this table are created and destroyed by the system."
    INDEX { svcId,
            tmnxSubPppUserName,
            tmnxSubPppIndex
          }
    ::= { tmnxSubPppUserTable 1 }

TmnxSubPppUserEntry ::= 
    SEQUENCE {
        tmnxSubPppUserName                   DisplayString,
        tmnxSubPppUserType                   TmnxSubPppType
    }
        
tmnxSubPppUserName OBJECT-TYPE
    SYNTAX      DisplayString (SIZE(0..110))
    MAX-ACCESS  not-accessible
    STATUS      current
    DESCRIPTION
        "The value of tmnxSubPppUserName indicates the user name
         learned during the PPP authentication phase."
    ::= { tmnxSubPppUserEntry 1 }

tmnxSubPppUserType OBJECT-TYPE
    SYNTAX      TmnxSubPppType
    MAX-ACCESS  read-only
    STATUS      current
    DESCRIPTION
       "The value of the object tmnxSubPppUserType indicates the type of
        the session."
    ::= { tmnxSubPppUserEntry 2 }

--
--      The per-service Subscriber PPP Types Table
--

tmnxSubPppSvcTypeTable   OBJECT-TYPE
    SYNTAX      SEQUENCE OF TmnxSubPppSvcTypeEntry
    MAX-ACCESS  not-accessible
    STATUS      current
    DESCRIPTION
       "The tmnxSubPppSvcTypeTable has information for each each type of
        subscriber PPP Session, ordered per service."
    ::= { tmnxSubPppObjs 11 }

tmnxSubPppSvcTypeEntry   OBJECT-TYPE
    SYNTAX      TmnxSubPppSvcTypeEntry
    MAX-ACCESS  not-accessible
    STATUS      current
    DESCRIPTION
       "Each conceptual row represents information about a specific type of
        subscriber PPP in a specific service.

        Entries in this table are created and destroyed by the system."
    INDEX { svcId,
            tmnxSubPppSvcTypeIndex }
    ::= { tmnxSubPppSvcTypeTable 1 }

TmnxSubPppSvcTypeEntry ::= 
    SEQUENCE {
        tmnxSubPppSvcTypeIndex           TmnxSubPppType,
        tmnxSubPppSvcTypeSessions        Gauge32
    }
        
tmnxSubPppSvcTypeIndex OBJECT-TYPE
    SYNTAX      TmnxSubPppType
    MAX-ACCESS  not-accessible
    STATUS      current
    DESCRIPTION
       "The value of the object tmnxSubPppSvcTypeIndex indicates the type of
        subscriber PPP."
    ::= { tmnxSubPppSvcTypeEntry 1 }

tmnxSubPppSvcTypeSessions OBJECT-TYPE
    SYNTAX      Gauge32
    MAX-ACCESS  read-only
    STATUS      current
    DESCRIPTION
       "The value of the object tmnxSubPppSvcTypeSessions indicates  
        the actual number of PPP session of this type."
    ::= { tmnxSubPppSvcTypeEntry 2 }

--
--      The SLAAC Host Managed Route Table
--

tmnxSubSlaacMRtTable   OBJECT-TYPE
    SYNTAX      SEQUENCE OF TmnxSubSlaacMRtEntry
    MAX-ACCESS  not-accessible
    STATUS      current
    DESCRIPTION
       "The tmnxSubSlaacMRtTable contains managed routes  
        for SLAAC hosts.

        Entries in this table are created and destroyed by the system."
    ::= { tmnxSubMgmtObjects 112 }

tmnxSubSlaacMRtEntry   OBJECT-TYPE
    SYNTAX      TmnxSubSlaacMRtEntry
    MAX-ACCESS  not-accessible
    STATUS      current
    DESCRIPTION
       "Each conceptual row represents a managed route
        of a SLAAC host."
    INDEX { svcId,
            tmnxSubSlaacPfxType,
            tmnxSubSlaacPfx,
            tmnxSubSlaacMacAddr,
            tmnxSubSlaacMRtAddrType,
            tmnxSubSlaacMRtAddr,
            tmnxSubSlaacMRtPrefixLen }
    ::= { tmnxSubSlaacMRtTable 1 }

TmnxSubSlaacMRtEntry ::= 
    SEQUENCE {
        tmnxSubSlaacMRtAddrType        InetAddressType,
        tmnxSubSlaacMRtAddr            InetAddress,
        tmnxSubSlaacMRtPrefixLen       InetAddressPrefixLength,
        tmnxSubSlaacMRtStatus          TmnxManagedRouteStatus
       ,tmnxSubSlaacMRtMetric          TmnxRadiusFramedRouteMetric,
        tmnxSubSlaacMRtPreference      TmnxRadiusFramedRoutePreference,
        tmnxSubSlaacMRtTag             TmnxRadiusFramedRouteTag             
    }
        
tmnxSubSlaacMRtAddrType OBJECT-TYPE
    SYNTAX          InetAddressType
    MAX-ACCESS      not-accessible
    STATUS          current
    DESCRIPTION     "The value of tmnxSubSlaacMRtAddrType indicates
                     the address type of tmnxSubSlaacMRtAddr."
    ::= { tmnxSubSlaacMRtEntry 1 }

tmnxSubSlaacMRtAddr OBJECT-TYPE
    SYNTAX          InetAddress (SIZE(4|16))
    MAX-ACCESS      not-accessible
    STATUS          current
    DESCRIPTION     "The value of tmnxSubSlaacMRtAddr indicates
                     the IP address of the managed route."
    ::= { tmnxSubSlaacMRtEntry 2 }

tmnxSubSlaacMRtPrefixLen OBJECT-TYPE
    SYNTAX          InetAddressPrefixLength
    MAX-ACCESS      not-accessible
    STATUS          current
    DESCRIPTION     "The value of tmnxSubSlaacMRtPrefixLen indicates
                     the prefix length of the subnet associated with
                     tmnxSubSlaacMRtAddr."
    ::= { tmnxSubSlaacMRtEntry 3 }

tmnxSubSlaacMRtStatus OBJECT-TYPE
    SYNTAX          TmnxManagedRouteStatus
    MAX-ACCESS      read-only
    STATUS          current
    DESCRIPTION     "The value of tmnxSubSlaacMRtStatus indicates
                     the state of this managed route."
    ::= { tmnxSubSlaacMRtEntry 4 }

tmnxSubSlaacMRtMetric OBJECT-TYPE
    SYNTAX          TmnxRadiusFramedRouteMetric
    MAX-ACCESS      read-only
    STATUS          current
    DESCRIPTION     "The value of tmnxSubSlaacMRtMetric indicates
                     the metric of this managed route as specified
                     in the RADIUS option 22 Framed-Route or 
                     option 99 Framed-IPv6-Route."
    ::= { tmnxSubSlaacMRtEntry 5 }

tmnxSubSlaacMRtPreference OBJECT-TYPE
    SYNTAX          TmnxRadiusFramedRoutePreference
    MAX-ACCESS      read-only
    STATUS          current
    DESCRIPTION     "The value of tmnxSubSlaacMRtPreference indicates
                     the preference of this managed route as specified
                     in the RADIUS option 22 Framed-Route or 
                     option 99 Framed-IPv6-Route."
    ::= { tmnxSubSlaacMRtEntry 6 }

tmnxSubSlaacMRtTag OBJECT-TYPE
    SYNTAX          TmnxRadiusFramedRouteTag
    MAX-ACCESS      read-only
    STATUS          current
    DESCRIPTION     "The value of tmnxSubSlaacMRtTag indicates
                     the tag of this managed route as specified
                     in the RADIUS option 22 Framed-Route or 
                     option 99 Framed-IPv6-Route."
    ::= { tmnxSubSlaacMRtEntry 7 }


-- --------------------------------------------------------
-- tmnxSubHsmdaEgrQosQTable
-- --------------------------------------------------------
tmnxSubHsmdaEgrQosQTableLastCh  OBJECT-TYPE
    SYNTAX          TimeStamp
    MAX-ACCESS      read-only
    STATUS          current
    DESCRIPTION
        "The value of tmnxSubHsmdaEgrQosQTableLastCh indicates the
         sysUpTime at the time of the last modification
         of tmnxSubHsmdaEgrQosQTable.

         If no changes were made to the entry since the last
         re-initialization of the local network management subsystem,
         then this object contains a zero value."
    ::= { tmnxSubHsmda2Objs 1 }

tmnxSubHsmdaEgrQosQTable OBJECT-TYPE
    SYNTAX      SEQUENCE OF TmnxSubHsmdaEgrQosQEntry
    MAX-ACCESS  not-accessible
    STATUS      current
    DESCRIPTION
        "The tmnxSubHsmdaEgrQosQTable has an entry for each HSMDA egress
         queue override configured on the system."
    ::= { tmnxSubHsmda2Objs 2 }

tmnxSubHsmdaEgrQosQEntry     OBJECT-TYPE
    SYNTAX      TmnxSubHsmdaEgrQosQEntry
    MAX-ACCESS  not-accessible
    STATUS      current
    DESCRIPTION
        "Each row entry represents a HSMDA egress queue override record.

         Entries are created and deleted via SNMP SET operations on
         tmnxSubHsmdaEgrQosQRowStatus."
    INDEX { tmnxSubProfName,
            tSapEgressIndex,
            tSapEgressHsmdaQueue }
    ::= { tmnxSubHsmdaEgrQosQTable 1}

TmnxSubHsmdaEgrQosQEntry ::= SEQUENCE
    {
        tmnxSubHsmdaEgrQosQRowStatus    RowStatus,
        tmnxSubHsmdaEgrQosQLastChgd     TimeStamp,
        tmnxSubHsmdaEgrQosQPIR          THsmdaPIRKRateOverride,
        tmnxSubHsmdaEgrQosQSlopePlcy    TNamedItemOrEmpty,
        tmnxSubHsmdaEgrQosQWrrWeight    THsmdaWrrWeightOverride,
        tmnxSubHsmdaEgrQosQMBS          THSMDABurstSizeBytesOverride,
        tmnxSubHsmdaEgrQosQStatMode     INTEGER
    }

tmnxSubHsmdaEgrQosQRowStatus OBJECT-TYPE
    SYNTAX      RowStatus
    MAX-ACCESS  read-create
    STATUS      current
    DESCRIPTION
        "The value of tmnxSubHsmdaEgrQosQRowStatus controls the creation
         and deletion of rows in this table."
    ::= { tmnxSubHsmdaEgrQosQEntry  1 }

tmnxSubHsmdaEgrQosQLastChgd OBJECT-TYPE
    SYNTAX      TimeStamp
    MAX-ACCESS  read-only
    STATUS      current
    DESCRIPTION
        "The value of tmnxSubHsmdaEgrQosQLastChgd indicates the sysUpTime
         at the time of the most recent management-initiated change to this
         table row."
    ::= { tmnxSubHsmdaEgrQosQEntry  2 }

tmnxSubHsmdaEgrQosQPIR OBJECT-TYPE
    SYNTAX      THsmdaPIRKRateOverride
    UNITS       "kbps"
    MAX-ACCESS  read-create
    STATUS      current
    DESCRIPTION
        "The value of tmnxSubHsmdaEgrQosQPIR specifies the PIR rate in kbps
         allowed for this HSMDA egress queue."
    DEFVAL { -2 }
    ::= { tmnxSubHsmdaEgrQosQEntry  3 }

tmnxSubHsmdaEgrQosQSlopePlcy OBJECT-TYPE
    SYNTAX      TNamedItemOrEmpty
    MAX-ACCESS  read-create
    STATUS      current
    DESCRIPTION
        "The value of tmnxSubHsmdaEgrQosQSlopePlcy specifies the slope
         policy that defines the RED slopes for this HSMDA egress queue."
    DEFVAL { "" }
    ::= { tmnxSubHsmdaEgrQosQEntry  5 }

tmnxSubHsmdaEgrQosQWrrWeight OBJECT-TYPE
    SYNTAX      THsmdaWrrWeightOverride
    MAX-ACCESS  read-create
    STATUS      current
    DESCRIPTION
        "The value of tmnxSubHsmdaEgrQosQWrrWeight specifies the weight with 
         which this queue should parent into the HSMDA scheduler, provided it is
         not superseded by the Weighted Round Robin (WRR) policy. The weight of 
         each queue determines how much bandwidth that queue gets out of the 
         total rate for the scheduling class."
    DEFVAL      { -2 }
    ::= { tmnxSubHsmdaEgrQosQEntry 6 }

tmnxSubHsmdaEgrQosQMBS OBJECT-TYPE
    SYNTAX      THSMDABurstSizeBytesOverride
    UNITS       "bytes"
    MAX-ACCESS  read-create
    STATUS      current
    DESCRIPTION
        "The value of tmnxSubHsmdaEgrQosQMBS specifies the maximum amount of 
         buffer space (in bytes) allowed for this HSMDA queue."
    DEFVAL      { -2 }
    ::= { tmnxSubHsmdaEgrQosQEntry 7 }
    
tmnxSubHsmdaEgrQosQStatMode OBJECT-TYPE
    SYNTAX      INTEGER {
                    noOverride   (-1),
                    v4V6         (0)
                }
    MAX-ACCESS  read-create
    STATUS      current
    DESCRIPTION
        "The value of tmnxSubHsmdaEgrQosQStatMode specifies the mode of
         statistics collected for this HSMDA queue.
         
         A value of 'v4V6(0)' indicates seperate counters are collected
         for IPv4 and IPv6 instead of the normal queue statistics."
    DEFVAL { noOverride }
    ::= { tmnxSubHsmdaEgrQosQEntry 8 }
             
-- ----------------------------------------
-- tmnxSubIngPStatsTable
-- ----------------------------------------
tmnxSubIngPStatsTable OBJECT-TYPE
    SYNTAX      SEQUENCE OF TmnxSubIngPStatsEntry
    MAX-ACCESS  not-accessible
    STATUS      current
    DESCRIPTION
        "The tmnxSubIngPStatsTable contains ingress QoS policer
         statistics about HSMDA-2 subscribers."
    ::= { tmnxSubHsmda2Objs 3 }

tmnxSubIngPStatsEntry OBJECT-TYPE
    SYNTAX      TmnxSubIngPStatsEntry
    MAX-ACCESS  not-accessible
    STATUS      current
    DESCRIPTION
        "Each row entry contains ingress QoS policer
         statistics about a particular HSMDA-2 subscriber and policer.
         
         In the descriptions below 'Pchip' refers to the Nokia SROS 
         series Packet Processing chip, while 'Qchip' refers to the 
         Nokia SROS series QoS Queueing Engine chip."
    INDEX { tmnxSubInfoSubIdent,
            tSapIngPolicerId }
    ::= { tmnxSubIngPStatsTable 1 }

TmnxSubIngPStatsEntry ::=
    SEQUENCE {
        tmnxSubIngPStatsMode             TmnxIngPolicerStatMode,
        tmnxSubIngPStatsOffHiPrioPkts    Counter64,
        tmnxSubIngPStatsOffHiPrioPktsL   Counter32,
        tmnxSubIngPStatsOffHiPrioPktsH   Counter32,
        tmnxSubIngPStatsDrpHiPrioPkts    Counter64,
        tmnxSubIngPStatsDrpHiPrioPktsL   Counter32,
        tmnxSubIngPStatsDrpHiPrioPktsH   Counter32,
        tmnxSubIngPStatsOffLoPrioPkts    Counter64,
        tmnxSubIngPStatsOffLoPrioPktsL   Counter32,
        tmnxSubIngPStatsOffLoPrioPktsH   Counter32,
        tmnxSubIngPStatsDrpLoPrioPkts    Counter64,
        tmnxSubIngPStatsDrpLoPrioPktsL   Counter32,
        tmnxSubIngPStatsDrpLoPrioPktsH   Counter32,
        tmnxSubIngPStatsOffHiPrioOcts    Counter64,
        tmnxSubIngPStatsOffHiPrioOctsL   Counter32,
        tmnxSubIngPStatsOffHiPrioOctsH   Counter32,
        tmnxSubIngPStatsDrpHiPrioOcts    Counter64,
        tmnxSubIngPStatsDrpHiPrioOctsL   Counter32,
        tmnxSubIngPStatsDrpHiPrioOctsH   Counter32,
        tmnxSubIngPStatsOffLoPrioOcts    Counter64,
        tmnxSubIngPStatsOffLoPrioOctsL   Counter32,
        tmnxSubIngPStatsOffLoPrioOctsH   Counter32,
        tmnxSubIngPStatsDrpLoPrioOcts    Counter64,
        tmnxSubIngPStatsDrpLoPrioOctsL   Counter32,
        tmnxSubIngPStatsDrpLoPrioOctsH   Counter32,
        tmnxSubIngPStatsOffUncolPkts     Counter64,
        tmnxSubIngPStatsOffUncolPktsL    Counter32,
        tmnxSubIngPStatsOffUncolPktsH    Counter32,
        tmnxSubIngPStatsOffUncolOcts     Counter64,
        tmnxSubIngPStatsOffUncolOctsL    Counter32,
        tmnxSubIngPStatsOffUncolOctsH    Counter32,
        tmnxSubIngPStatsFwdInProfPkts    Counter64,
        tmnxSubIngPStatsFwdInProfPktsL   Counter32,
        tmnxSubIngPStatsFwdInProfPktsH   Counter32,
        tmnxSubIngPStatsFwdOutProfPkts   Counter64,
        tmnxSubIngPStatsFwdOutProfPktsL  Counter32,
        tmnxSubIngPStatsFwdOutProfPktsH  Counter32,
        tmnxSubIngPStatsFwdInProfOcts    Counter64,
        tmnxSubIngPStatsFwdInProfOctsL   Counter32,
        tmnxSubIngPStatsFwdInProfOctsH   Counter32,
        tmnxSubIngPStatsFwdOutProfOcts   Counter64,
        tmnxSubIngPStatsFwdOutProfOctsL  Counter32,
        tmnxSubIngPStatsFwdOutProfOctsH  Counter32
    }

tmnxSubIngPStatsMode OBJECT-TYPE
    SYNTAX      TmnxIngPolicerStatMode
    MAX-ACCESS  read-only
    STATUS      current
    DESCRIPTION
        "The value of tmnxSPIIngPStatsMode indicates
         the stat mode used by the policer."
    ::= { tmnxSubIngPStatsEntry 2 }

tmnxSubIngPStatsOffHiPrioPkts OBJECT-TYPE
    SYNTAX      Counter64
    MAX-ACCESS  read-only
    STATUS      current
    DESCRIPTION
        "The value of tmnxSubIngPStatsOffHiPrioPkts indicates the number of
         high priority packets offered by the Pchip to the Qchip."
    ::= { tmnxSubIngPStatsEntry 3 }

tmnxSubIngPStatsOffHiPrioPktsL OBJECT-TYPE
    SYNTAX      Counter32
    MAX-ACCESS  read-only
    STATUS      current
    DESCRIPTION
        "Indicates the lower 32 bits of tmnxSubIngPStatsOffHiPrioPkts."
    ::= { tmnxSubIngPStatsEntry 4 }

tmnxSubIngPStatsOffHiPrioPktsH OBJECT-TYPE
    SYNTAX      Counter32
    MAX-ACCESS  read-only
    STATUS      current
    DESCRIPTION
        "Indicates the upper 32 bits of tmnxSubIngPStatsOffHiPrioPkts."
    ::= { tmnxSubIngPStatsEntry 5 }

tmnxSubIngPStatsDrpHiPrioPkts OBJECT-TYPE
    SYNTAX      Counter64
    MAX-ACCESS  read-only
    STATUS      current
    DESCRIPTION
        "The value of tmnxSubIngPStatsDrpHiPrioPkts indicates the number of
         high priority packets dropped by the Qchip."
    ::= { tmnxSubIngPStatsEntry 6 }

tmnxSubIngPStatsDrpHiPrioPktsL OBJECT-TYPE
    SYNTAX      Counter32
    MAX-ACCESS  read-only
    STATUS      current
    DESCRIPTION
        "Indicates the lower 32 bits of tmnxSubIngPStatsDrpHiPrioPkts."
    ::= { tmnxSubIngPStatsEntry 7 }

tmnxSubIngPStatsDrpHiPrioPktsH OBJECT-TYPE
    SYNTAX      Counter32
    MAX-ACCESS  read-only
    STATUS      current
    DESCRIPTION
        "Indicates the upper 32 bits of tmnxSubIngPStatsDrpHiPrioPkts."
    ::= { tmnxSubIngPStatsEntry 8 }

tmnxSubIngPStatsOffLoPrioPkts OBJECT-TYPE
    SYNTAX      Counter64
    MAX-ACCESS  read-only
    STATUS      current
    DESCRIPTION
        "The value of tmnxSubIngPStatsOffLoPrioPkts indicates the number of low
         priority packets offered by the Pchip to the Qchip."
    ::= { tmnxSubIngPStatsEntry 9 }

tmnxSubIngPStatsOffLoPrioPktsL OBJECT-TYPE
    SYNTAX      Counter32
    MAX-ACCESS  read-only
    STATUS      current
    DESCRIPTION
        "Indicates the lower 32 bits of tmnxSubIngPStatsOffLoPrioPkts."
    ::= { tmnxSubIngPStatsEntry 10 }

tmnxSubIngPStatsOffLoPrioPktsH OBJECT-TYPE
    SYNTAX      Counter32
    MAX-ACCESS  read-only
    STATUS      current
    DESCRIPTION
        "Indicates the upper 32 bits of tmnxSubIngPStatsOffLoPrioPkts."
    ::= { tmnxSubIngPStatsEntry 11 }

tmnxSubIngPStatsDrpLoPrioPkts OBJECT-TYPE
    SYNTAX      Counter64
    MAX-ACCESS  read-only
    STATUS      current
    DESCRIPTION
        "The value of tmnxSubIngPStatsDrpLoPrioPkts indicates the number of
         low priority packets dropped by the Pchip."
    ::= { tmnxSubIngPStatsEntry 12 }

tmnxSubIngPStatsDrpLoPrioPktsL OBJECT-TYPE
    SYNTAX      Counter32
    MAX-ACCESS  read-only
    STATUS      current
    DESCRIPTION
        "Indicates the lower 32 bits of tmnxSubIngPStatsDrpLoPrioPkts."
    ::= { tmnxSubIngPStatsEntry 13 }

tmnxSubIngPStatsDrpLoPrioPktsH OBJECT-TYPE
    SYNTAX      Counter32
    MAX-ACCESS  read-only
    STATUS      current
    DESCRIPTION
        "Indicates the upper 32 bits of tmnxSubIngPStatsDrpLoPrioPkts."
    ::= { tmnxSubIngPStatsEntry 14 }

tmnxSubIngPStatsOffHiPrioOcts OBJECT-TYPE
    SYNTAX      Counter64
    MAX-ACCESS  read-only
    STATUS      current
    DESCRIPTION
        "The value of tmnxSubIngPStatsOffHiPrioOcts indicates the number
         of high priority octets, as determined by the SLA profile ingress QoS
         policy, offered by the Pchip to the Qchip."
    ::= { tmnxSubIngPStatsEntry 15 }

tmnxSubIngPStatsOffHiPrioOctsL OBJECT-TYPE
    SYNTAX      Counter32
    MAX-ACCESS  read-only
    STATUS      current
    DESCRIPTION
        "Indicates the lower 32 bits of tmnxSubIngPStatsOffHiPrioOcts."
    ::= { tmnxSubIngPStatsEntry 16 }

tmnxSubIngPStatsOffHiPrioOctsH OBJECT-TYPE
    SYNTAX      Counter32
    MAX-ACCESS  read-only
    STATUS      current
    DESCRIPTION
        "Indicates the upper 32 bits of tmnxSubIngPStatsOffHiPrioOcts."
    ::= { tmnxSubIngPStatsEntry 17 }

tmnxSubIngPStatsDrpHiPrioOcts OBJECT-TYPE
    SYNTAX      Counter64
    MAX-ACCESS  read-only
    STATUS      current
    DESCRIPTION
        "The value of tmnxSubIngPStatsDrpHiPrioOcts indicates the number of
         high priority octets, as determined by the SLA profile ingress QoS
         policy, dropped by the Pchip."
    ::= { tmnxSubIngPStatsEntry 18 }

tmnxSubIngPStatsDrpHiPrioOctsL OBJECT-TYPE
    SYNTAX      Counter32
    MAX-ACCESS  read-only
    STATUS      current
    DESCRIPTION
        "Indicates the lower 32 bits of tmnxSubIngPStatsDrpHiPrioOcts."
    ::= { tmnxSubIngPStatsEntry 19 }

tmnxSubIngPStatsDrpHiPrioOctsH OBJECT-TYPE
    SYNTAX      Counter32
    MAX-ACCESS  read-only
    STATUS      current
    DESCRIPTION
        "Indicates the upper 32 bits of tmnxSubIngPStatsDrpHiPrioOcts."
    ::= { tmnxSubIngPStatsEntry 20 }

tmnxSubIngPStatsOffLoPrioOcts OBJECT-TYPE
    SYNTAX      Counter64
    MAX-ACCESS  read-only
    STATUS      current
    DESCRIPTION
        "The value of tmnxSubIngPStatsOffLoPrioOcts indicates the number of
         low priority octets, as determined by the SLA profile ingress QoS
         policy, offered by the Pchip to the Qchip."
    ::= { tmnxSubIngPStatsEntry 21 }

tmnxSubIngPStatsOffLoPrioOctsL OBJECT-TYPE
    SYNTAX      Counter32
    MAX-ACCESS  read-only
    STATUS      current
    DESCRIPTION
        "Indicates the lower 32 bits of tmnxSubIngPStatsOffLoPrioOcts."
    ::= { tmnxSubIngPStatsEntry 22 }

tmnxSubIngPStatsOffLoPrioOctsH OBJECT-TYPE
    SYNTAX      Counter32
    MAX-ACCESS  read-only
    STATUS      current
    DESCRIPTION
        "Indicates the upper 32 bits of tmnxSubIngPStatsOffLoPrioOcts."
    ::= { tmnxSubIngPStatsEntry 23 }

tmnxSubIngPStatsDrpLoPrioOcts OBJECT-TYPE
    SYNTAX      Counter64
    MAX-ACCESS  read-only
    STATUS      current
    DESCRIPTION
        "The value of tmnxSubIngPStatsDrpLoPrioOcts indicates the number of
         low priority octets, as determined by the SLA profile ingress QoS
         policy, dropped by the Pchip."
    ::= { tmnxSubIngPStatsEntry 24 }

tmnxSubIngPStatsDrpLoPrioOctsL OBJECT-TYPE
    SYNTAX      Counter32
    MAX-ACCESS  read-only
    STATUS      current
    DESCRIPTION
        "Indicates the lower 32 bits of tmnxSubIngPStatsDrpLoPrioOcts."
    ::= { tmnxSubIngPStatsEntry 25 }

tmnxSubIngPStatsDrpLoPrioOctsH OBJECT-TYPE
    SYNTAX      Counter32
    MAX-ACCESS  read-only
    STATUS      current
    DESCRIPTION
        "Indicates the upper 32 bits of tmnxSubIngPStatsDrpLoPrioOcts."
    ::= { tmnxSubIngPStatsEntry 26 }

tmnxSubIngPStatsOffUncolPkts OBJECT-TYPE
    SYNTAX      Counter64
    MAX-ACCESS  read-only
    STATUS      current
    DESCRIPTION
        "The value of tmnxSubIngPStatsOffUncolPkts indicates the number of
         uncolored packets offered to the ingress Pchip."
    ::= { tmnxSubIngPStatsEntry 27 }

tmnxSubIngPStatsOffUncolPktsL OBJECT-TYPE
    SYNTAX      Counter32
    MAX-ACCESS  read-only
    STATUS      current
    DESCRIPTION
        "Indicates the lower 32 bits of tmnxSubIngPStatsOffUncolPkts."
    ::= { tmnxSubIngPStatsEntry 28 }

tmnxSubIngPStatsOffUncolPktsH OBJECT-TYPE
    SYNTAX      Counter32
    MAX-ACCESS  read-only
    STATUS      current
    DESCRIPTION
        "Indicates the upper 32 bits of tmnxSubIngPStatsOffUncolPkts."
    ::= { tmnxSubIngPStatsEntry 29 }

tmnxSubIngPStatsOffUncolOcts OBJECT-TYPE
    SYNTAX      Counter64
    MAX-ACCESS  read-only
    STATUS      current
    DESCRIPTION
        "The value of tmnxSubIngPStatsOffUncolOcts indicates the number of
         uncolored octets offered to the ingress Pchip."
    ::= { tmnxSubIngPStatsEntry 30 }

tmnxSubIngPStatsOffUncolOctsL OBJECT-TYPE
    SYNTAX      Counter32
    MAX-ACCESS  read-only
    STATUS      current
    DESCRIPTION
        "Indicates the lower 32 bits of tmnxSubIngPStatsOffUncolOcts."
    ::= { tmnxSubIngPStatsEntry 31 }

tmnxSubIngPStatsOffUncolOctsH OBJECT-TYPE
    SYNTAX      Counter32
    MAX-ACCESS  read-only
    STATUS      current
    DESCRIPTION
        "Indicates the upper 32 bits of tmnxSubIngPStatsOffUncolOcts."
    ::= { tmnxSubIngPStatsEntry 32 }

tmnxSubIngPStatsFwdInProfPkts OBJECT-TYPE
    SYNTAX      Counter64
    MAX-ACCESS  read-only
    STATUS      current
    DESCRIPTION
        "The value of tmnxSubIngPStatsFwdInProfPkts indicates the number of
         in-profile packets (rate below CIR) forwarded by the ingress Pchip."
    ::= { tmnxSubIngPStatsEntry 33 }

tmnxSubIngPStatsFwdInProfPktsL OBJECT-TYPE
    SYNTAX      Counter32
    MAX-ACCESS  read-only
    STATUS      current
    DESCRIPTION
        "Indicates the lower 32 bits of tmnxSubIngPStatsFwdInProfPkts."
    ::= { tmnxSubIngPStatsEntry 34 }

tmnxSubIngPStatsFwdInProfPktsH OBJECT-TYPE
    SYNTAX      Counter32
    MAX-ACCESS  read-only
    STATUS      current
    DESCRIPTION
        "Indicates the upper 32 bits of tmnxSubIngPStatsFwdInProfPkts."
    ::= { tmnxSubIngPStatsEntry 35 }

tmnxSubIngPStatsFwdOutProfPkts OBJECT-TYPE
    SYNTAX      Counter64
    MAX-ACCESS  read-only
    STATUS      current
    DESCRIPTION
        "The value of tmnxSubIngPStatsFwdOutProfPkts indicates the number of
         out-of-profile packets (rate above CIR) forwarded by the ingress Pchip."
    ::= { tmnxSubIngPStatsEntry 36 }

tmnxSubIngPStatsFwdOutProfPktsL OBJECT-TYPE
    SYNTAX      Counter32
    MAX-ACCESS  read-only
    STATUS      current
    DESCRIPTION
        "Indicates the lower 32 bits of tmnxSubIngPStatsFwdOutProfPkts."
    ::= { tmnxSubIngPStatsEntry 37 }

tmnxSubIngPStatsFwdOutProfPktsH OBJECT-TYPE
    SYNTAX      Counter32
    MAX-ACCESS  read-only
    STATUS      current
    DESCRIPTION
        "Indicates the upper 32 bits of tmnxSubIngPStatsFwdOutProfPkts."
    ::= { tmnxSubIngPStatsEntry 38 }

tmnxSubIngPStatsFwdInProfOcts OBJECT-TYPE
    SYNTAX      Counter64
    MAX-ACCESS  read-only
    STATUS      current
    DESCRIPTION
        "The value of tmnxSubIngPStatsFwdInProfOcts indicates the number of
         in-profile octets (rate below CIR) forwarded by the ingress Pchip."
    ::= { tmnxSubIngPStatsEntry 39 }

tmnxSubIngPStatsFwdInProfOctsL OBJECT-TYPE
    SYNTAX      Counter32
    MAX-ACCESS  read-only
    STATUS      current
    DESCRIPTION
        "Indicates the lower 32 bits of tmnxSubIngPStatsFwdInProfOcts."
    ::= { tmnxSubIngPStatsEntry 40 }

tmnxSubIngPStatsFwdInProfOctsH OBJECT-TYPE
    SYNTAX      Counter32
    MAX-ACCESS  read-only
    STATUS      current
    DESCRIPTION
        "Indicates the upper 32 bits of tmnxSubIngPStatsFwdInProfOcts."
    ::= { tmnxSubIngPStatsEntry 41 }

tmnxSubIngPStatsFwdOutProfOcts OBJECT-TYPE
    SYNTAX      Counter64
    MAX-ACCESS  read-only
    STATUS      current
    DESCRIPTION
        "The value of tmnxSubIngPStatsFwdOutProfOcts indicates the number of
         out-of-profile octets (rate above CIR) forwarded by the ingress Pchip."
    ::= { tmnxSubIngPStatsEntry 42 }

tmnxSubIngPStatsFwdOutProfOctsL OBJECT-TYPE
    SYNTAX      Counter32
    MAX-ACCESS  read-only
    STATUS      current
    DESCRIPTION
        "Indicates the lower 32 bits of tmnxSubIngPStatsFwdOutProfOcts."
    ::= { tmnxSubIngPStatsEntry 43 }

tmnxSubIngPStatsFwdOutProfOctsH OBJECT-TYPE
    SYNTAX      Counter32
    MAX-ACCESS  read-only
    STATUS      current
    DESCRIPTION
        "Indicates the upper 32 bits of tmnxSubIngPStatsFwdOutProfOcts."
    ::= { tmnxSubIngPStatsEntry 44 }

-- --------------------------------------------------------
-- tmnxSubHsmdaIngQosQTable
-- --------------------------------------------------------
tmnxSubHsmdaIngQosQTableLastCh  OBJECT-TYPE
    SYNTAX          TimeStamp
    MAX-ACCESS      read-only
    STATUS          current
    DESCRIPTION
        "The value of tmnxSubHsmdaIngQosQTableLastCh indicates the
         sysUpTime at the time of the last modification
         of tmnxSubHsmdaIngQosQTable.

         If no changes were made to the entry since the last
         re-initialization of the local network management subsystem,
         then this object contains a zero value."
    ::= { tmnxSubHsmda2Objs 4 }

tmnxSubHsmdaIngQosQTable OBJECT-TYPE
    SYNTAX      SEQUENCE OF TmnxSubHsmdaIngQosQEntry
    MAX-ACCESS  not-accessible
    STATUS      current
    DESCRIPTION
        "The tmnxSubHsmdaIngQosQTable has an entry for each HSMDA ingress
         queue override configured on the system."
    ::= { tmnxSubHsmda2Objs 5 }

tmnxSubHsmdaIngQosQEntry     OBJECT-TYPE
    SYNTAX      TmnxSubHsmdaIngQosQEntry
    MAX-ACCESS  not-accessible
    STATUS      current
    DESCRIPTION
        "Each row entry represents a HSMDA ingress queue override record.

         Entries are created and deleted via SNMP SET operations on
         tmnxSubHsmdaIngQosQRowStatus."
    INDEX { tmnxSubProfName,
            tSapIngressIndex,
            tSapIngressQueue }
    ::= { tmnxSubHsmdaIngQosQTable 1}

TmnxSubHsmdaIngQosQEntry ::= SEQUENCE
    {
        tmnxSubHsmdaIngQosQRowStatus    RowStatus,
        tmnxSubHsmdaIngQosQLastChgd     TimeStamp,
        tmnxSubHsmdaIngQosQStatMode     INTEGER
    }

tmnxSubHsmdaIngQosQRowStatus OBJECT-TYPE
    SYNTAX      RowStatus
    MAX-ACCESS  read-create
    STATUS      current
    DESCRIPTION
        "The value of tmnxSubHsmdaIngQosQRowStatus controls the creation
         and deletion of rows in this table."
    ::= { tmnxSubHsmdaIngQosQEntry  1 }

tmnxSubHsmdaIngQosQLastChgd OBJECT-TYPE
    SYNTAX      TimeStamp
    MAX-ACCESS  read-only
    STATUS      current
    DESCRIPTION
        "The value of tmnxSubHsmdaIngQosQLastChgd indicates the sysUpTime
         at the time of the most recent management-initiated change to this
         table row."
    ::= { tmnxSubHsmdaIngQosQEntry  2 }

tmnxSubHsmdaIngQosQStatMode OBJECT-TYPE
    SYNTAX      INTEGER {
                    noOverride   (-1),
                    v4V6         (0)
                }
    MAX-ACCESS  read-create
    STATUS      current
    DESCRIPTION
        "The value of tmnxSubHsmdaIngQosQStatMode specifies the mode of
         statistics collected for this HSMDA queue.

         A value of 'v4V6(0)' indicates seperate counters are collected
         for IPv4 and IPv6 instead of the normal queue statistics."
    DEFVAL { noOverride }
    ::= { tmnxSubHsmdaIngQosQEntry 3 }

-- --------------------------------------------------------
-- tmnxSubHsmdaIngQosPolTable
-- --------------------------------------------------------
tmnxSubHsmdaIngQosPolTableLastCh  OBJECT-TYPE
    SYNTAX          TimeStamp
    MAX-ACCESS      read-only
    STATUS          current
    DESCRIPTION
        "The value of tmnxSubHsmdaIngQosPolTableLastCh indicates the
         sysUpTime at the time of the last modification
         of tmnxSubHsmdaIngQosPolTable.

         If no changes were made to the entry since the last
         re-initialization of the local network management subsystem,
         then this object contains a zero value."
    ::= { tmnxSubHsmda2Objs 6 }

tmnxSubHsmdaIngQosPolTable OBJECT-TYPE
    SYNTAX      SEQUENCE OF TmnxSubHsmdaIngQosPolEntry
    MAX-ACCESS  not-accessible
    STATUS      current
    DESCRIPTION
        "The tmnxSubHsmdaIngQosPolTable has an entry for each HSMDA ingress
         policer override configured on the system."
    ::= { tmnxSubHsmda2Objs 7 }

tmnxSubHsmdaIngQosPolEntry     OBJECT-TYPE
    SYNTAX      TmnxSubHsmdaIngQosPolEntry
    MAX-ACCESS  not-accessible
    STATUS      current
    DESCRIPTION
        "Each row entry represents a HSMDA ingress policer override record.

         Entries are created and deleted via SNMP SET operations on
         tmnxSubHsmdaIngQosPolRowStatus."
    INDEX { tmnxSubProfName,
            tSapIngressIndex,
            tSapIngPolicerId }
    ::= { tmnxSubHsmdaIngQosPolTable 1}

TmnxSubHsmdaIngQosPolEntry ::= SEQUENCE
    {
        tmnxSubHsmdaIngQosPolRowStatus    RowStatus,
        tmnxSubHsmdaIngQosPolLastChgd     TimeStamp,
        tmnxSubHsmdaIngQosPolStatMode     INTEGER
    }

tmnxSubHsmdaIngQosPolRowStatus OBJECT-TYPE
    SYNTAX      RowStatus
    MAX-ACCESS  read-create
    STATUS      current
    DESCRIPTION
        "The value of tmnxSubHsmdaIngQosPolRowStatus controls the creation
         and deletion of rows in this table."
    ::= { tmnxSubHsmdaIngQosPolEntry  1 }

tmnxSubHsmdaIngQosPolLastChgd OBJECT-TYPE
    SYNTAX      TimeStamp
    MAX-ACCESS  read-only
    STATUS      current
    DESCRIPTION
        "The value of tmnxSubHsmdaIngQosPolLastChgd indicates the sysUpTime
         at the time of the most recent management-initiated change to this
         table row."
    ::= { tmnxSubHsmdaIngQosPolEntry  2 }

tmnxSubHsmdaIngQosPolStatMode OBJECT-TYPE
    SYNTAX      INTEGER {
                    noOverride   (-1),
                    v4V6         (0)
                }
    MAX-ACCESS  read-create
    STATUS      current
    DESCRIPTION
        "The value of tmnxSubHsmdaIngQosPolStatMode specifies the mode of
         statistics collected for this HSMDA policer.

         A value of 'v4V6(0)' indicates seperate counters are collected
         for IPv4 and IPv6 instead of the normal policer statistics."
    DEFVAL { noOverride }
    ::= { tmnxSubHsmdaIngQosPolEntry 3 }

-- --------------------------------------------------------
-- HTTP Redirect group
-- --------------------------------------------------------
-- The system can be configured to perform HTTP Redirect
-- for certain types of subscribers, whose set-up is 
-- initiated on the ISA cards.
-- For example, HTTP traffic from migrant User Equipment
-- in a Wifi offload scenario can be redirected to an
-- authentication web portal.
-- --------------------------------------------------------
-- tmnxSubHttpRdrPlcyTable
-- --------------------------------------------------------
tmnxSubHttpRdrPlcyTableLastCh  OBJECT-TYPE
    SYNTAX          TimeStamp
    MAX-ACCESS      read-only
    STATUS          current
    DESCRIPTION
        "The value of tmnxSubHttpRdrPlcyTableLastCh indicates the
         sysUpTime at the time of the last modification
         of the tmnxSubHttpRdrPlcyTable.

         If no changes were made to the entry since the last
         re-initialization of the local network management subsystem,
         then this object contains a zero value."
    ::= { tmnxSubMgmtObjects 108 }

tmnxSubHttpRdrPlcyTable OBJECT-TYPE
    SYNTAX      SEQUENCE OF TmnxSubHttpRdrPlcyEntry
    MAX-ACCESS  not-accessible
    STATUS      current
    DESCRIPTION
        "The tmnxSubHttpRdrPlcyTable contains objects to configure
         HTTP redirect policies."
    ::= { tmnxSubHttpRedirectObjs 1 }

tmnxSubHttpRdrPlcyEntry     OBJECT-TYPE
    SYNTAX      TmnxSubHttpRdrPlcyEntry
    MAX-ACCESS  not-accessible
    STATUS      current
    DESCRIPTION
        "Each conceptual row represents configuration of an HTTP redirect policy
         for subscriber traffic.

         Entries are created and deleted via SNMP SET operations on
         tmnxSubHttpRdrPlcyRowStatus."
    INDEX { IMPLIED tmnxSubHttpRdrPlcyName }
    ::= { tmnxSubHttpRdrPlcyTable 1}

TmnxSubHttpRdrPlcyEntry ::= SEQUENCE
    {
        tmnxSubHttpRdrPlcyName           TNamedItem,
        tmnxSubHttpRdrPlcyRowStatus      RowStatus,
        tmnxSubHttpRdrPlcyLastCh         TimeStamp,
        tmnxSubHttpRdrPlcyDescription    TItemDescription,
        tmnxSubHttpRdrPlcyUrl            TmnxHttpRedirectUrl,
        tmnxSubHttpRdrPlcyDestPort       InetPortNumber,
        tmnxSubHttpRdrPlcyPortalHoldTime Unsigned32
    }

tmnxSubHttpRdrPlcyName OBJECT-TYPE
    SYNTAX      TNamedItem
    MAX-ACCESS  not-accessible
    STATUS      current
    DESCRIPTION
        "The value of tmnxSubHttpRdrPlcyName specifies the name of this HTTP
         redirect policy."
   ::= { tmnxSubHttpRdrPlcyEntry 1 }
   
tmnxSubHttpRdrPlcyRowStatus OBJECT-TYPE
    SYNTAX      RowStatus
    MAX-ACCESS  read-create
    STATUS      current
    DESCRIPTION
        "The value of tmnxSubHttpRdrPlcyRowStatus controls the creation
         and deletion of rows in this table."
    ::= { tmnxSubHttpRdrPlcyEntry  2 }

tmnxSubHttpRdrPlcyLastCh OBJECT-TYPE
    SYNTAX      TimeStamp
    MAX-ACCESS  read-only
    STATUS      current
    DESCRIPTION
        "The value of tmnxSubHttpRdrPlcyLastCh indicates the sysUpTime
         at the time of the most recent management-initiated change to this
         table row."
    ::= { tmnxSubHttpRdrPlcyEntry  3 }

tmnxSubHttpRdrPlcyDescription OBJECT-TYPE
    SYNTAX      TItemDescription
    MAX-ACCESS  read-create
    STATUS      current
    DESCRIPTION
        "The value of tmnxSubHttpRdrPlcyDescription specifies
         the user-defined description of this policy."
    DEFVAL { "" }
    ::= { tmnxSubHttpRdrPlcyEntry  4 }

tmnxSubHttpRdrPlcyUrl OBJECT-TYPE
    SYNTAX      TmnxHttpRedirectUrl
    MAX-ACCESS  read-create
    STATUS      current
    DESCRIPTION
        "The value of tmnxSubHttpRdrPlcyUrl specifies the HTTP URL to
         re-direct HTTP traffic to.
         
         Actual HTTP re-direction is triggered per subscriber during
         the authentication phase, by the presence of certain vendor-
         specific attributes in the RADIUS Access-Accept message
         (Alc-Wifi-Portal-Redirect or Alc-Wifi-Portal-Url).
         
         During the set-up of a particular subscriber, this value may be
         overruled by the value of a vendor-specific attribute in the
         RADIUS Access-Accept message (Alc-Wifi-Portal-Url).
         
         This string may contain a number of substitution macro's:
         - $URL: specifies that '$URL' must be substituted with the content of the
                 Request-URI in the HTTP GET Request received.
                 
         - $MAC: specifies that '$MAC' must be replaced with a string that
                 represents the MAC address of the subscriber host;
                 the MAC address is formatted in Nokia SROS style,
                 like 00:0c:f1:99:85:b8.
                 
         - $IP:  specifies that '$IP' must be replaced with a string that represents
                 the IP address of the subscriber host."
    DEFVAL { "" }
    ::= { tmnxSubHttpRdrPlcyEntry  5 }

tmnxSubHttpRdrPlcyDestPort OBJECT-TYPE
    SYNTAX      InetPortNumber
    MAX-ACCESS  read-create
    STATUS      current
    DESCRIPTION
        "The value of tmnxSubHttpRdrPlcyDestPort specifies
         the port to match the destination port in the HTTP request.
         
         HTTP traffic that does not match this port, is not redirected.
         
         The value zero is not allowed."
    DEFVAL { 80 }
    ::= { tmnxSubHttpRdrPlcyEntry  6 }

tmnxSubHttpRdrPlcyPortalHoldTime OBJECT-TYPE
    SYNTAX      Unsigned32 (0..60)
    UNITS       "seconds"
    MAX-ACCESS  read-create
    STATUS      current
    DESCRIPTION
        "The value of tmnxSubHttpRdrPlcyPortalHoldTime specifies
         how long the system holds on to re-direct forwarding resources 
         of a subscriber, after it has left the re-direct portal."
    DEFVAL { 0 }
    ::= { tmnxSubHttpRdrPlcyEntry  7 }

-- --------------------------------------------------------
-- tmnxSubHttpRdrFwdTable
-- --------------------------------------------------------
tmnxSubHttpRdrFwdTableLastCh  OBJECT-TYPE
    SYNTAX          TimeStamp
    MAX-ACCESS      read-only
    STATUS          current
    DESCRIPTION
        "The value of tmnxSubHttpRdrFwdTableLastCh indicates the
         sysUpTime at the time of the last modification
         of the tmnxSubHttpRdrFwdTable.

         If no changes were made to the entry since the last
         re-initialization of the local network management subsystem,
         then this object contains a zero value."
    ::= { tmnxSubMgmtObjects 109 }

tmnxSubHttpRdrFwdTable OBJECT-TYPE
    SYNTAX      SEQUENCE OF TmnxSubHttpRdrFwdEntry
    MAX-ACCESS  not-accessible
    STATUS      current
    DESCRIPTION
        "The tmnxSubHttpRdrFwdTable contains objects to configure
         HTTP redirect policy forwarding entries."
    ::= { tmnxSubHttpRedirectObjs 2 }

tmnxSubHttpRdrFwdEntry     OBJECT-TYPE
    SYNTAX      TmnxSubHttpRdrFwdEntry
    MAX-ACCESS  not-accessible
    STATUS      current
    DESCRIPTION
        "Each conceptual row represents configuration of an HTTP redirect policy
         forwarding entry. 
         
         Subscriber traffic matching a forwarding entry is not re-directed
         but forwarded.

         Entries are created and deleted via SNMP SET operations on
         tmnxSubHttpRdrFwdRowStatus."
    INDEX { tmnxSubHttpRdrPlcyName,
            tmnxSubHttpRdrFwdDestIpAddrType,
            tmnxSubHttpRdrFwdDestIpAddr,
            tmnxSubHttpRdrFwdProtocol,
            tmnxSubHttpRdrFwdDestPort
          }
    ::= { tmnxSubHttpRdrFwdTable 1}

TmnxSubHttpRdrFwdEntry ::= SEQUENCE
    {
        tmnxSubHttpRdrFwdDestIpAddrType InetAddressType,
        tmnxSubHttpRdrFwdDestIpAddr     InetAddress,
        tmnxSubHttpRdrFwdProtocol       INTEGER,
        tmnxSubHttpRdrFwdDestPort       InetPortNumber,
        tmnxSubHttpRdrFwdRowStatus      RowStatus,
        tmnxSubHttpRdrFwdLastCh         TimeStamp
      , tmnxSubHttpRdrFwdDestIpPfxLen   InetAddressPrefixLength
    }

tmnxSubHttpRdrFwdDestIpAddrType OBJECT-TYPE
    SYNTAX      InetAddressType
    MAX-ACCESS  not-accessible
    STATUS      current
    DESCRIPTION 
        "The value of tmnxSubHttpRdrFwdDestIpAddrType specifies
         the address type of tmnxSubHttpRdrFwdDestIpAddr."
    ::= { tmnxSubHttpRdrFwdEntry 1 }

tmnxSubHttpRdrFwdDestIpAddr OBJECT-TYPE
    SYNTAX      InetAddress (SIZE(4|16))
    MAX-ACCESS  not-accessible
    STATUS      current
    DESCRIPTION 
        "The value of tmnxSubHttpRdrFwdDestIpAddr specifies
         the IP address to match the destination IP address in the IP header
         of the traffic received from the subscriber.
         
         IP traffic that does not match this address, is not forwarded."
    ::= { tmnxSubHttpRdrFwdEntry 2 }

tmnxSubHttpRdrFwdProtocol OBJECT-TYPE
    SYNTAX      INTEGER {
                    tcp (6),
                    udp (17)
                }
    MAX-ACCESS  not-accessible
    STATUS      current
    DESCRIPTION
        "The value of tmnxSubHttpRdrFwdProtocol specifies
         the protocol to match the IP protocol in the IP header
         of the traffic received from the subscriber.
         
         Traffic that does not match this protocol, is not forwarded."
    ::= { tmnxSubHttpRdrFwdEntry 3 }
    
tmnxSubHttpRdrFwdDestPort OBJECT-TYPE
    SYNTAX      InetPortNumber (1..65535)
    MAX-ACCESS  not-accessible
    STATUS      current
    DESCRIPTION
        "The value of tmnxSubHttpRdrFwdDestPort specifies
         the port to match the destination port in the HTTP request.
         
         HTTP traffic that does not match this port, is not forwarded."
    ::= { tmnxSubHttpRdrFwdEntry 4 }

tmnxSubHttpRdrFwdRowStatus OBJECT-TYPE
    SYNTAX      RowStatus
    MAX-ACCESS  read-create
    STATUS      current
    DESCRIPTION
        "The value of tmnxSubHttpRdrFwdRowStatus controls the creation
         and deletion of rows in this table."
    ::= { tmnxSubHttpRdrFwdEntry 5 }

tmnxSubHttpRdrFwdLastCh OBJECT-TYPE
    SYNTAX      TimeStamp
    MAX-ACCESS  read-only
    STATUS      current
    DESCRIPTION
        "The value of tmnxSubHttpRdrFwdLastCh indicates the sysUpTime
         at the time of the most recent management-initiated change to this
         table row."
    ::= { tmnxSubHttpRdrFwdEntry 6 } 

tmnxSubHttpRdrFwdDestIpPfxLen OBJECT-TYPE
    SYNTAX      InetAddressPrefixLength (0 | 1..128)
    MAX-ACCESS  read-create
    STATUS      current
    DESCRIPTION
        "The value of tmnxSubHttpRdrFwdDestIpPfxLen specifies 
         the prefix length associated with the object tmnxSubHttpRdrFwdDestIpAddr.
         
         Setting the value to anything other than zero or the value equal to the full
         prefix length corresponding to the value of tmnxSubHttpRdrFwdDestIpAddrType,
         is only permitted while the conceptual row is created.
         
         Changing the value of this object is not allowed.
         
         The value zero has the same effect as the value equal to the full
         prefix length corresponding to the value of tmnxSubHttpRdrFwdDestIpAddrType,
         meaning 32 for IPv4 and 128 for IPv6 addresses."
    ::= { tmnxSubHttpRdrFwdEntry 7 }

-- --------------------------------------------------------
-- tmnxSubSvcTable
-- --------------------------------------------------------

tmnxSubSvcTable OBJECT-TYPE
    SYNTAX      SEQUENCE OF TmnxSubSvcEntry
    MAX-ACCESS  not-accessible
    STATUS      current
    DESCRIPTION
        "The tmnxSubSvcTable has an entry for each subscriber service
         applied to a host."
    ::= { tmnxSubMgmtObjects 110 }

tmnxSubSvcEntry OBJECT-TYPE
    SYNTAX      TmnxSubSvcEntry
    MAX-ACCESS  not-accessible
    STATUS      current
    DESCRIPTION
        "Each row entry contains information about a particular subscriber
         service."
    INDEX { svcId,
            sapPortId,
            sapEncapValue,
            tmnxSubHostInfoV2IpAddressType,
            tmnxSubHostInfoV2IpAddress,
            tmnxSubHostInfoV2MacAddress,
            tmnxSubHostInfoV2PppoeSessionId,
            tmnxSubSvcId }
    ::= { tmnxSubSvcTable 1 }

TmnxSubSvcEntry ::=
    SEQUENCE {
        tmnxSubSvcId                     Unsigned32,
        tmnxSubSvcName                   DisplayString,
        tmnxSubSvcType                   DisplayString,
        tmnxSubSvcAcctType               INTEGER,
        tmnxSubSvcAcctUpdateIvl          TimeInterval,
        tmnxSubSvcAcctSessionId          TmnxSubAcctSessionId,
        tmnxSubSvcUpTime                 TimeInterval,
        tmnxSubSvcInPckts                Counter64,
        tmnxSubSvcInOcts                 Counter64,
        tmnxSubSvcOutPckts               Counter64,
        tmnxSubSvcOutOcts                Counter64
    }

tmnxSubSvcId OBJECT-TYPE
    SYNTAX      Unsigned32
    MAX-ACCESS  not-accessible
    STATUS      current
    DESCRIPTION
       "The value of tmnxSubSvcId indicates the identifier of this
        subscriber service."
    ::= { tmnxSubSvcEntry 1 }

tmnxSubSvcName OBJECT-TYPE
    SYNTAX      DisplayString
    MAX-ACCESS  read-only
    STATUS      current
    DESCRIPTION
       "The value of tmnxSubSvcName indicates the name of this
        subscriber service."
    ::= { tmnxSubSvcEntry 2 }

tmnxSubSvcType OBJECT-TYPE
    SYNTAX      DisplayString
    MAX-ACCESS  read-only
    STATUS      current
    DESCRIPTION
       "The value of tmnxSubSvcType indicates the type of this
        subscriber service."
    ::= { tmnxSubSvcEntry 3 }

tmnxSubSvcAcctType OBJECT-TYPE
    SYNTAX      INTEGER {
                    off         (1),
                    volumeTime  (2),
                    time        (3)
                }
    MAX-ACCESS  read-only
    STATUS      current
    DESCRIPTION
       "The value of tmnxSubSvcAcctType indicates the accounting type of this
        subscriber service."
    ::= { tmnxSubSvcEntry 4 }

tmnxSubSvcAcctUpdateIvl OBJECT-TYPE
    SYNTAX      TimeInterval
    MAX-ACCESS  read-only
    STATUS      current
    DESCRIPTION
       "The value of tmnxSubSvcAcctUpdateIvl indicates the interval at which
        accounting interim updates are sent for this subscriber service."
    ::= { tmnxSubSvcEntry 5 }

tmnxSubSvcAcctSessionId OBJECT-TYPE
    SYNTAX      TmnxSubAcctSessionId
    MAX-ACCESS  read-only
    STATUS      current
    DESCRIPTION
       "The value of tmnxSubSvcAcctSessionId indicates the accounting
        session-id for this subscriber service."
    ::= { tmnxSubSvcEntry 6 }

tmnxSubSvcUpTime OBJECT-TYPE
    SYNTAX      TimeInterval
    MAX-ACCESS  read-only
    STATUS      current
    DESCRIPTION
       "The value of tmnxSubSvcUpTime indicates the time (duration in hundredths
        of a second) that this subscriber service is active."
    ::= { tmnxSubSvcEntry 7 }

tmnxSubSvcInPckts OBJECT-TYPE
    SYNTAX      Counter64
    MAX-ACCESS  read-only
    STATUS      current
    DESCRIPTION
       "The value of tmnxSubSvcInPckts indicates the number of ingress packets
        sent for this subscriber service."
    ::= { tmnxSubSvcEntry 8 }

tmnxSubSvcInOcts OBJECT-TYPE
    SYNTAX      Counter64
    MAX-ACCESS  read-only
    STATUS      current
    DESCRIPTION
       "The value of tmnxSubSvcInOcts indicates the number of ingress octets
        sent for this subscriber service."
    ::= { tmnxSubSvcEntry 9 }

tmnxSubSvcOutPckts OBJECT-TYPE
    SYNTAX      Counter64
    MAX-ACCESS  read-only
    STATUS      current
    DESCRIPTION
       "The value of tmnxSubSvcOutPckts indicates the number of egress packets
        sent for this subscriber service."
    ::= { tmnxSubSvcEntry 10 }

tmnxSubSvcOutOcts OBJECT-TYPE
    SYNTAX      Counter64
    MAX-ACCESS  read-only
    STATUS      current
    DESCRIPTION
       "The value of tmnxSubSvcOutOcts indicates the number of egress octets
        sent for this subscriber service."
    ::= { tmnxSubSvcEntry 11 }

-- --------------------------------------------------------
-- tmnxSubSvcAttrTable
-- --------------------------------------------------------

tmnxSubSvcAttrTable OBJECT-TYPE
    SYNTAX      SEQUENCE OF TmnxSubSvcAttrEntry
    MAX-ACCESS  not-accessible
    STATUS      current
    DESCRIPTION
        "The tmnxSubSvcAttrTable has an entry for each attribute of a
         subscriber service applied to a host."
    ::= { tmnxSubMgmtObjects 111 }

tmnxSubSvcAttrEntry OBJECT-TYPE
    SYNTAX      TmnxSubSvcAttrEntry
    MAX-ACCESS  not-accessible
    STATUS      current
    DESCRIPTION
        "Each row entry contains information about a particular attribute
         of a subscriber service."
    INDEX { svcId,
            sapPortId,
            sapEncapValue,
            tmnxSubHostInfoV2IpAddressType,
            tmnxSubHostInfoV2IpAddress,
            tmnxSubHostInfoV2MacAddress,
            tmnxSubHostInfoV2PppoeSessionId,
            tmnxSubSvcId,
            tmnxSubSvcAttrId }
    ::= { tmnxSubSvcAttrTable 1 }

TmnxSubSvcAttrEntry ::=
    SEQUENCE {
        tmnxSubSvcAttrId                 Unsigned32,
        tmnxSubSvcAttrType               DisplayString,
        tmnxSubSvcAttrString             DisplayString
    }

tmnxSubSvcAttrId OBJECT-TYPE
    SYNTAX      Unsigned32
    MAX-ACCESS  not-accessible
    STATUS      current
    DESCRIPTION
       "The value of tmnxSubSvcAttrId indicates the identifier of this
        subscriber service attribute."
    ::= { tmnxSubSvcAttrEntry 1 }

tmnxSubSvcAttrType OBJECT-TYPE
    SYNTAX      DisplayString
    MAX-ACCESS  read-only
    STATUS      current
    DESCRIPTION
       "The value of tmnxSubSvcName indicates the type of this
        subscriber service attribute."
    ::= { tmnxSubSvcAttrEntry 2 }

tmnxSubSvcAttrString OBJECT-TYPE
    SYNTAX      DisplayString
    MAX-ACCESS  read-only
    STATUS      current
    DESCRIPTION
       "The value of tmnxSubSvcAttrString indicates the textual description
        of the action applied to this host by this attribute."
    ::= { tmnxSubSvcAttrEntry 3 }

-- --------------------------------------------------------
-- tmnxSLAProfSchedOverrideTable
-- --------------------------------------------------------
tmnxSLAProfSchedOverrideTable OBJECT-TYPE
    SYNTAX      SEQUENCE OF TmnxSLAProfSchedOverrideEntry
    MAX-ACCESS  not-accessible
    STATUS      current
    DESCRIPTION
        "The tmnxSLAProfSchedOverrideTable allows overriding of ingress/egress
         scheduler rates on a per SLA profile basis."
    ::= { tmnxSubMgmtObjects 114 }

tmnxSLAProfSchedOverrideEntry OBJECT-TYPE
    SYNTAX      TmnxSLAProfSchedOverrideEntry
    MAX-ACCESS  not-accessible
    STATUS      current
    DESCRIPTION
        "Each entry of the tmnxSLAProfSchedOverrideTable describes
         ingress/egress scheduler rates which are overridden for the SLA
         profile indicated by tmnxSLAProfName. Rows can be created and deleted
         by the operator (tmnxSLAProfSchedOvrRowStatus). Rows can only be
         created for existing schedulers defined in
         TIMETRA-QOS-MIB::tVirtualSchedulerTable."
    INDEX { tmnxSLAProfName,
            tmnxSLAProfSchedOvrDirection,
            tSchedulerPolicyName,
            IMPLIED tVirtualSchedulerName }
    ::= { tmnxSLAProfSchedOverrideTable 1 }

TmnxSLAProfSchedOverrideEntry ::=
    SEQUENCE {
        tmnxSLAProfSchedOvrDirection      TmnxSubDirection,
        tmnxSLAProfSchedOvrRowStatus      RowStatus,
        tmnxSLAProfSchedOvrLastChange     TimeStamp,
        tmnxSLAProfSchedOvrSummedCIR      TruthValue,
        tmnxSLAProfSchedOvrPIRHi          Unsigned32,
        tmnxSLAProfSchedOvrPIRLo          Unsigned32,
        tmnxSLAProfSchedOvrCIRHi          Unsigned32,
        tmnxSLAProfSchedOvrCIRLo          Unsigned32
    }

tmnxSLAProfSchedOvrDirection OBJECT-TYPE
    SYNTAX      TmnxSubDirection
    MAX-ACCESS  not-accessible
    STATUS      current
    DESCRIPTION
        "The value of tmnxSLAProfSchedOvrDirection indicates whether this row
         specifies ingress or egress scheduler override parameters."
    ::= { tmnxSLAProfSchedOverrideEntry 1 }

tmnxSLAProfSchedOvrRowStatus OBJECT-TYPE
    SYNTAX      RowStatus
    MAX-ACCESS  read-create
    STATUS      current
    DESCRIPTION
        "The value of tmnxSLAProfSchedOvrRowStatus controls the creation and
         deletion of rows in this table."
    ::= { tmnxSLAProfSchedOverrideEntry 2 }

tmnxSLAProfSchedOvrLastChange OBJECT-TYPE
    SYNTAX      TimeStamp
    MAX-ACCESS  read-only
    STATUS      current
    DESCRIPTION
        "The value of tmnxSLAProfSchedOvrLastChange indicates the sysUpTime
         at the time of the most recent management-initiated change to this
         table row."
    ::= { tmnxSLAProfSchedOverrideEntry 3 }

tmnxSLAProfSchedOvrSummedCIR OBJECT-TYPE
    SYNTAX      TruthValue
    MAX-ACCESS  read-create
    STATUS      current
    DESCRIPTION
        "The value of tmnxSLAProfSchedOvrSummedCIR specifies if the CIR should
         be used as the summed CIR values of the children schedulers or queues.
         If set to 'true', the applicable scheduler CIR (tmnxSLAProfSchedOvrCIR)
         loses its meaning."
    DEFVAL { true }
    ::= { tmnxSLAProfSchedOverrideEntry 4 }

tmnxSLAProfSchedOvrPIRHi OBJECT-TYPE
    SYNTAX      Unsigned32 (0 | 4294967295)
    UNITS       "kbps"
    MAX-ACCESS  read-create
    STATUS      current
    DESCRIPTION 
        "The value of tmnxSLAProfSchedOvrPIRHi indicates upper 32 bits of the
         pir-rate allowed for this scheduler.    

         This value should always be set along with tmnxSLAProfSchedOvrPIRLo,
         otherwise an 'inconsistentValue' error is returned. This object is
         mandatory at creation time.

         When the value of tmnxSLAProfSchedOvrPIRHi along with the value of
         tmnxSLAProfSchedOvrPIRLo is set to 4294967295 (0xFFFFFFFF), rate for 
         this scheduler indicates maximum rate."
    DEFVAL { 4294967295 }
    ::= { tmnxSLAProfSchedOverrideEntry 5 }
    
tmnxSLAProfSchedOvrPIRLo OBJECT-TYPE
    SYNTAX      Unsigned32 (1..3200000000 | 4294967295)
    UNITS       "kbps"
    MAX-ACCESS  read-create
    STATUS      current
    DESCRIPTION 
        "The value of tmnxSLAProfSchedOvrPIRLo indicates lower 32 bits of the
         pir-rate allowed for this scheduler.    

         This value should always be set along with tmnxSLAProfSchedOvrPIRHi,
         otherwise an 'inconsistentValue' error is returned. This object is
         mandatory at creation time.

         When the value of tmnxSLAProfSchedOvrPIRHi along with the value of
         tmnxSLAProfSchedOvrPIRLo is set to 4294967295 (0xFFFFFFFF), rate for 
         this scheduler indicates maximum rate."
    DEFVAL { 4294967295 }
    ::= { tmnxSLAProfSchedOverrideEntry 6 }

tmnxSLAProfSchedOvrCIRHi OBJECT-TYPE
    SYNTAX      Unsigned32 (0 | 4294967295)
    UNITS       "kbps"
    MAX-ACCESS  read-create
    STATUS      current
    DESCRIPTION 
        "The value of tmnxSLAProfSchedOvrCIRHi indicates upper 32 bits of the
         cir-rate allowed for this scheduler.    

         This value should always be set along with tmnxSLAProfSchedOvrCIRLo,
         otherwise an 'inconsistentValue' error is returned. This object is
         mandatory at creation time.

         When the value of tmnxSLAProfSchedOvrCIRHi along with the value of
         tmnxSLAProfSchedOvrCIRLo is set to 4294967295 (0xFFFFFFFF), rate for 
         this scheduler indicates maximum rate."
    DEFVAL { 4294967295 }
    ::= { tmnxSLAProfSchedOverrideEntry 7 }

tmnxSLAProfSchedOvrCIRLo OBJECT-TYPE
    SYNTAX      Unsigned32 (0..3200000000 | 4294967295)
    UNITS       "kbps"
    MAX-ACCESS  read-create
    STATUS      current
    DESCRIPTION 
        "The value of tmnxSLAProfSchedOvrCIRLo indicates lower 32 bits of the
         cir-rate allowed for this scheduler.    

         This value should always be set along with tmnxSLAProfSchedOvrPIRHi,
         otherwise an 'inconsistentValue' error is returned. This object is
         mandatory at creation time.

         When the value of tmnxSLAProfSchedOvrCIRHi along with the value of
         tmnxSLAProfSchedOvrCIRLo is set to 4294967295 (0xFFFFFFFF), rate for 
         this scheduler indicates maximum rate."
    DEFVAL { 4294967295 }
    ::= { tmnxSLAProfSchedOverrideEntry 8 }
    
-- ----------------------------------------
-- tmnxSPIEgrQosSchedStatsTable
-- ----------------------------------------
tmnxSPIEgrQosSchedStatsTable OBJECT-TYPE
    SYNTAX      SEQUENCE OF TmnxSPIEgrQosSchedStatsEntry
    MAX-ACCESS  not-accessible
    STATUS      current
    DESCRIPTION
        "The tmnxSPIEgrQosSchedStatsTable contains egress QoS scheduler
         statistics about SLA profile instances.

         In the descriptions below 'Pchip' refers to the Nokia SROS 
         series Packet Processing chip, while 'Qchip' refers to the 
         Nokia SROS series QoS Queueing Engine chip."
    ::= { tmnxSubMgmtObjects 115 }

tmnxSPIEgrQosSchedStatsEntry OBJECT-TYPE
    SYNTAX      TmnxSPIEgrQosSchedStatsEntry
    MAX-ACCESS  not-accessible
    STATUS      current
    DESCRIPTION
        "Each row entry contains egress statistics about a particular
         SLA profile instance QoS scheduler."
    INDEX { tmnxSubInfoSubIdent,
            sapPortId,
            sapEncapValue,
            tmnxSLAProfName,
            IMPLIED tmnxSPIEgrQosSchedStatsName }
    ::= { tmnxSPIEgrQosSchedStatsTable 1 }

TmnxSPIEgrQosSchedStatsEntry ::=
    SEQUENCE {
        tmnxSPIEgrQosSchedStatsName      TNamedItem,
        tmnxSPIEgrQosSchedStatsFwdPkts   Counter64,
        tmnxSPIEgrQosSchedStatsFwdOctets Counter64
    }

tmnxSPIEgrQosSchedStatsName OBJECT-TYPE
    SYNTAX      TNamedItem
    MAX-ACCESS  not-accessible
    STATUS      current
    DESCRIPTION
        "The value of tmnxSPIEgrQosSchedStatsName specifies the egress QoS
         scheduler of this SLA profile instance."
    ::= { tmnxSPIEgrQosSchedStatsEntry 1 }

tmnxSPIEgrQosSchedStatsFwdPkts OBJECT-TYPE
    SYNTAX      Counter64
    MAX-ACCESS  read-only
    STATUS      current
    DESCRIPTION
        "The value of tmnxSPIEgrQosSchedStatsFwdPkts indicates the number of
         forwarded packets by the egress Qchip, as determined by the SLA 
         profile instance egress scheduler policy."
    ::= { tmnxSPIEgrQosSchedStatsEntry 2 }

tmnxSPIEgrQosSchedStatsFwdOctets OBJECT-TYPE
    SYNTAX      Counter64
    MAX-ACCESS  read-only
    STATUS      current
    DESCRIPTION
        "The value of tmnxSPIEgrQosSchedStatsFwdOctets indicates the number of
         forwarded octets by the egress Qchip, as determined by the SLA
         profile instance egress scheduler policy."
    ::= { tmnxSPIEgrQosSchedStatsEntry 3 }
    
--
-- System configuration objects
--

tmnxSubSysNextHopLimit  OBJECT-TYPE
    SYNTAX      Unsigned32 ( 0..16383 )
    MAX-ACCESS  read-write
    STATUS      obsolete
    DESCRIPTION
        "The value of tmnxSubSysNextHopLimit specifies
         the maximum number of IP next-hop entries available
         for subscriber management host's managed routes."
    DEFVAL { 16383 }    
    ::= { tmnxSubSysObjs 1 }

tmnxSubSysNextHopUsageHigh  OBJECT-TYPE
    SYNTAX      TruthValue
    MAX-ACCESS  read-only
    STATUS      obsolete
    DESCRIPTION
        "The value of tmnxSubSysNextHopUsageHigh indicates
         if the IP next-hop usage is near the limit specified
         with the value of tmnxSubSysNextHopLimit."
    ::= { tmnxSubSysObjs 2 }

--
--      The Subscriber System Chassis Table
--

tmnxSubSysChassTable   OBJECT-TYPE
    SYNTAX      SEQUENCE OF TmnxSubSysChassEntry
    MAX-ACCESS  not-accessible
    STATUS      current
    DESCRIPTION
       "The tmnxSubSysChassTable contains status information about
        the subscriber management function at the system level that
        is associated with hardware chassis resources.

        Entries in this table are created and destroyed by the system."
    ::= { tmnxSubSysObjs 3 }

tmnxSubSysChassEntry   OBJECT-TYPE
    SYNTAX      TmnxSubSysChassEntry
    MAX-ACCESS  not-accessible
    STATUS      current
    DESCRIPTION
       "Each conceptual row represents subscriber management information
        of a chassis."
    INDEX { tmnxChassisIndex }
    ::= { tmnxSubSysChassTable 1 }

TmnxSubSysChassEntry ::= 
    SEQUENCE {
        tmnxSubSysChassMemoryUsageHigh   TruthValue              
    }
        
tmnxSubSysChassMemoryUsageHigh OBJECT-TYPE
    SYNTAX          TruthValue
    MAX-ACCESS      read-only
    STATUS          current
    DESCRIPTION     "The value of tmnxSubSysChassMemoryUsageHigh indicates 
                     that the memory usage of the subscriber management function
                     on this chassis is near the limit."
    ::= { tmnxSubSysChassEntry 1 }

--
--      The data triggered subscriber host statistics object group
--
tmnxSubDtStatsObjs  OBJECT IDENTIFIER ::= { tmnxSubSysObjs 4 }

tmnxSubDtStatsPacketsReceived OBJECT-TYPE
    SYNTAX          Counter64
    MAX-ACCESS      read-only
    STATUS          current
    DESCRIPTION     "The value of tmnxSubDtStatsPacketsReceived indicates 
                     the number of data packets received that may trigger
                     creation of data-triggered subscriber hosts on this system."
    ::= { tmnxSubDtStatsObjs 1 }

tmnxSubDtStatsPacketsDropped OBJECT-TYPE
    SYNTAX          Counter64
    MAX-ACCESS      read-only
    STATUS          current
    DESCRIPTION     "The value of tmnxSubDtStatsPacketsDropped indicates 
                     the number of data packets dropped that could have triggered
                     creation of data-triggered subscriber hosts on this system."
    ::= { tmnxSubDtStatsObjs 2 }
    
tmnxSubDtStatsPacketsInQ OBJECT-TYPE
    SYNTAX          Gauge32
    MAX-ACCESS      read-only
    STATUS          current
    DESCRIPTION     "The value of tmnxSubDtStatsPacketsInQ indicates 
                     the number of data packets currently in the waiting queue
                     that may trigger creation of data-triggered subcsriber hosts on this system."
    ::= { tmnxSubDtStatsObjs 3 }
    
tmnxSubDtStatsPacketsInQPeak OBJECT-TYPE
    SYNTAX          Gauge32
    MAX-ACCESS      read-only
    STATUS          current
    DESCRIPTION     "The value of tmnxSubDtStatsPacketsInQPeak indicates 
                     the maximum value of the tmnxSubDtStatsPacketsInQ object
                     since the start-up of this system or the last time that the value of
                     tmnxSubDtStatsPacketsInQ was reset."
    ::= { tmnxSubDtStatsObjs 4 }
    
-- ----------------------------------------
-- Subscribers with virtual subnetting
-- ----------------------------------------
tmnxSubVSubnetTable OBJECT-TYPE
    SYNTAX      SEQUENCE OF TmnxSubVSubnetEntry
    MAX-ACCESS  not-accessible
    STATUS      current
    DESCRIPTION
        "The tmnxSubVSubnetTable contains information about
         subscribers associated with virtual subnets.
         
         Virtual subnetting is enabled per interface by the object
         TIMETRA-VRTR-MIB::vRtrIfDHCPVirtualSubnet.

         Conceptual rows in this table are created and destroyed
         automatically by the system."
    ::= { tmnxSubMgmtObjects 116 }

tmnxSubVSubnetEntry OBJECT-TYPE
    SYNTAX      TmnxSubVSubnetEntry
    MAX-ACCESS  not-accessible
    STATUS      current
    DESCRIPTION
        "Each conceptual row contains information about virtual subnetting
         of a particular subscriber."
    INDEX {  svcId,
             IMPLIED tmnxSubInfoSubIdent
          }
    ::= { tmnxSubVSubnetTable 1 }

TmnxSubVSubnetEntry ::=
    SEQUENCE {
        tmnxSubVSubnetDefRtrAddrType InetAddressType,
        tmnxSubVSubnetDefRtrAddr     InetAddress,
        tmnxSubVSubnetPrefixLength   InetAddressPrefixLength, 
        tmnxSubVSubnetSapPortId      TmnxPortID,
        tmnxSubVSubnetSapEncapValue  TmnxEncapVal
    }

tmnxSubVSubnetDefRtrAddrType OBJECT-TYPE
    SYNTAX      InetAddressType
    MAX-ACCESS  read-only
    STATUS      current
    DESCRIPTION 
        "The value of tmnxSubVSubnetDefRtrAddrType indicates
         the address type of tmnxSubVSubnetDefRtrAddr."
    ::= { tmnxSubVSubnetEntry 1 }

tmnxSubVSubnetDefRtrAddr OBJECT-TYPE
    SYNTAX      InetAddress (SIZE(4|16))
    MAX-ACCESS  read-only
    STATUS      current
    DESCRIPTION 
        "The value of tmnxSubVSubnetDefRtrAddr indicates
         the IP address of the default router associated
         with this subnet.
         
         The values of tmnxSubVSubnetDefRtrAddr and tmnxSubVSubnetPrefixLength
         indicate the subnet associated with this subscriber."
    ::= { tmnxSubVSubnetEntry 2 }

tmnxSubVSubnetPrefixLength OBJECT-TYPE
    SYNTAX      InetAddressPrefixLength (1..128)
    MAX-ACCESS  read-only
    STATUS      current
    DESCRIPTION 
        "The value of tmnxSubVSubnetPrefixLength indicates
         the prefix length of the subnet."
    ::= { tmnxSubVSubnetEntry 3 }

tmnxSubVSubnetSapPortId OBJECT-TYPE
    SYNTAX      TmnxPortID
    MAX-ACCESS  read-only
    STATUS      current
    DESCRIPTION 
       "The values of the objects tmnxSubVSubnetSapPortId and
        tmnxSubVSubnetSapEncapValue indicate the SAP
        associated with this subscriber."
    ::= { tmnxSubVSubnetEntry 5 }

tmnxSubVSubnetSapEncapValue OBJECT-TYPE
    SYNTAX      TmnxEncapVal
    MAX-ACCESS  read-only
    STATUS      current
    DESCRIPTION 
       "The values of the objects tmnxSubVSubnetSapPortId and
        tmnxSubVSubnetSapEncapValue indicate the SAP
        associated with this subscriber."
    ::= { tmnxSubVSubnetEntry 6 }


-- ----------------------------------------
-- tmnxSubSlaacModifyTable
-- ----------------------------------------
tmnxSubSlaacModifyTable OBJECT-TYPE
    SYNTAX      SEQUENCE OF TmnxSubSlaacModifyEntry
    MAX-ACCESS  not-accessible
    STATUS      current
    DESCRIPTION
        "The tmnxSubSlaacModifyTable augments the tmnxSubSlaacTable.
         The table allows the operator to modify SLAAC host attributes."
    ::= { tmnxSubMgmtObjects 117 }

tmnxSubSlaacModifyEntry OBJECT-TYPE
    SYNTAX      TmnxSubSlaacModifyEntry
    MAX-ACCESS  not-accessible
    STATUS      current
    DESCRIPTION
        "Each row entry contains parameters that allow to modify a SLAAC host."
    AUGMENTS { tmnxSubSlaacEntry }
    ::= { tmnxSubSlaacModifyTable 1 }

TmnxSubSlaacModifyEntry ::=
    SEQUENCE {
        tmnxSubSlaacEvaluate             TruthValue,
        tmnxSubSlaacModifySubscrIdent    DisplayString,
        tmnxSubSlaacModifySubProfString  DisplayString,
        tmnxSubSlaacModifySlaProfString  DisplayString,
        tmnxSubSlaacModifyAppProfString  DisplayString,
        tmnxSubSlaacModifyInterDestId    DisplayString,
        tmnxSubSlaacModifyAncpString     TmnxAncpStringOrZero
    }

tmnxSubSlaacEvaluate OBJECT-TYPE
    SYNTAX      TruthValue
    MAX-ACCESS  read-write
    STATUS      current
    DESCRIPTION
        "The value of tmnxSubSlaacEvaluate allows to
         cause a re-evaluation of the specified SLAAC host.

         When this object is set to 'true', the system will perform
         a re-evaluation of the SLAAC host.

         GETs and GETNEXTs on this variable return false.

         It is not possible to simultaneously request for a
         SLAAC host re-evaluation, and modify any of the
         host values."
    DEFVAL      { false }
    ::= { tmnxSubSlaacModifyEntry 1 }

tmnxSubSlaacModifySubscrIdent OBJECT-TYPE
    SYNTAX      DisplayString
    MAX-ACCESS  read-write
    STATUS      current
    DESCRIPTION
        "The value of tmnxSubSlaacModifySubscrIdent allows to specify a new
         subscriber name for this host.

         When a SET of this object is done with a non empty string,
         the system will attempt to assign a new subscriber name.

         A SET with an empty string has no effect on the system (NOOP).

         GETs and GETNEXTs on this variable return an empty string."
    DEFVAL { ''H }
    ::= { tmnxSubSlaacModifyEntry 2 }

tmnxSubSlaacModifySubProfString OBJECT-TYPE
    SYNTAX      DisplayString
    MAX-ACCESS  read-write
    STATUS      current
    DESCRIPTION
        "The value of tmnxSubSlaacModifySubProfString allows to specify a new
         subscriber profile string for this host.

         When a SET of this object is done with a non empty string,
         the system will attempt to assign a new subscriber profile string.

         A SET with an empty string has no effect on the system (NOOP).

         GETs and GETNEXTs on this variable return an empty string."
    DEFVAL { ''H }
    ::= { tmnxSubSlaacModifyEntry 3 }

tmnxSubSlaacModifySlaProfString OBJECT-TYPE
    SYNTAX      DisplayString
    MAX-ACCESS  read-write
    STATUS      current
    DESCRIPTION
        "The value of tmnxSubSlaacModifySlaProfString allows to specify a new
         sla profile string for this host.

         When a SET of this object is done with a non empty string,
         the system will attempt to assign a new sla profile string.

         A SET with an empty string has no effect on the system (NOOP).

         GETs and GETNEXTs on this variable return an empty string."
    DEFVAL { ''H }
    ::= { tmnxSubSlaacModifyEntry 4 }

tmnxSubSlaacModifyAppProfString OBJECT-TYPE
    SYNTAX      DisplayString
    MAX-ACCESS  read-write
    STATUS      current
    DESCRIPTION
        "The value of tmnxSubSlaacModifyAppProfString allows to specify a new
         application profile string for this host.

         When a SET of this object is done with a non empty string,
         the system will attempt to assign a new application profile string.

         A SET with an empty string has no effect on the system (NOOP).

         GETs and GETNEXTs on this variable return an empty string."
    DEFVAL { ''H }
    ::= { tmnxSubSlaacModifyEntry 5 }

tmnxSubSlaacModifyInterDestId OBJECT-TYPE
    SYNTAX      DisplayString
    MAX-ACCESS  read-write
    STATUS      current
    DESCRIPTION
        "The value of tmnxSubSlaacModifyInterDestId allows to specify a new
         intermediate destination id for this host.

         When a SET of this object is done with a non empty string,
         the system will attempt to assign a new intermediate destination id.

         A SET with an empty string has no effect on the system (NOOP).

         GETs and GETNEXTs on this variable return an empty string."
    DEFVAL { ''H }
    ::= { tmnxSubSlaacModifyEntry 6 }

tmnxSubSlaacModifyAncpString OBJECT-TYPE
    SYNTAX      TmnxAncpStringOrZero
    MAX-ACCESS  read-write
    STATUS      current
    DESCRIPTION
        "The value of tmnxSubSlaacModifyAncpString allows to specify a new
         ANCP-string for this host.

         When a SET of this object is done with a non empty string,
         the system will attempt to assign a new ANCP-string.

         A SET with an empty string has no effect on the system (NOOP).

         GETs and GETNEXTs on this variable return an empty string."
    DEFVAL { ''H }
    ::= { tmnxSubSlaacModifyEntry 7 }

-- ------------------------------------------------
-- tmnxSubV6GrpIfNDTable
-- ------------------------------------------------

tmnxSubV6GrpIfNDTableLastChange OBJECT-TYPE
    SYNTAX      TimeStamp
    MAX-ACCESS  read-only
    STATUS      current
    DESCRIPTION
      "The value of tmnxSubV6GrpIfNDTableLastChange indicates the sysUpTime
       at the time of the last modification of tmnxSubV6GrpIfNDTable.

       If no changes were made to the entry since the last
       re-initialization of the local network management subsystem,
       then this object contains a zero value."
    ::= { tmnxSubMgmtObjects 119 }

tmnxSubV6GrpIfNDTable OBJECT-TYPE
    SYNTAX      SEQUENCE OF TmnxSubV6GrpIfNDEntry
    MAX-ACCESS  not-accessible
    STATUS      current
    DESCRIPTION
      "A table configuring Neighbor Discovery in IPv6.

       Applies to IES and VPRN Group Interfaces.

       A row is automatically created in tmnxSubV6GrpIfNDTable for each entry in
       iesIfTable where the value of the object iesIfType equals 'group (3)'."
    ::= { tmnxSubMgmtObjects 120 }

tmnxSubV6GrpIfNDEntry OBJECT-TYPE
    SYNTAX      TmnxSubV6GrpIfNDEntry
    MAX-ACCESS  not-accessible
    STATUS      current
    DESCRIPTION
      "Information about the Neighbor Discovery configuration in IPv6 for a
      particular IES or VPRN Group Interface."
    INDEX { svcId,
            iesIfIndex }
    ::= { tmnxSubV6GrpIfNDTable 1 }

TmnxSubV6GrpIfNDEntry ::= SEQUENCE
{
    tmnxSubV6GrpIfNDLastChanged        TimeStamp,
    tmnxSubV6GrpIfNDNeighborLimit      Unsigned32,
    tmnxSubV6GrpIfNDNeighborDadSnoop   TruthValue
}

tmnxSubV6GrpIfNDLastChanged OBJECT-TYPE
    SYNTAX      TimeStamp
    MAX-ACCESS  read-only
    STATUS      current
    DESCRIPTION
        "The value of tmnxSubV6GrpIfNDLastChanged indicates the sysUpTime at
         the time of the most recent management-initiated change to this
         Entry."
    ::= { tmnxSubV6GrpIfNDEntry 1 }

tmnxSubV6GrpIfNDNeighborLimit OBJECT-TYPE
    SYNTAX      Unsigned32 (1..8)
    MAX-ACCESS  read-write
    STATUS      current
    DESCRIPTION
        "The value of tmnxSubV6GrpIfNDNeighborLimit specifies the maximum 
         amount of neighbors learned for a single host by doing neighbor
         discovery.

         If ip addresses are learned once this limit has been reached, the
         oldest learned ip address will be overwritten."
    DEFVAL { 1 }
    ::= { tmnxSubV6GrpIfNDEntry 2 }

tmnxSubV6GrpIfNDNeighborDadSnoop OBJECT-TYPE
    SYNTAX      TruthValue
    MAX-ACCESS  read-write
    STATUS      current
    DESCRIPTION
        "The value of tmnxSubV6GrpIfNDNeighborDadSnoop specifies whether
         duplicate address detection packets will be snooped to populate new
         neighbors."
    DEFVAL { false }
    ::= { tmnxSubV6GrpIfNDEntry 3 }

-- ------------------------------------------------
-- tmnxSubSlaacOvrTable
-- ------------------------------------------------

tmnxSubSlaacOvrTable   OBJECT-TYPE
    SYNTAX      SEQUENCE OF TmnxSubSlaacOvrEntry
    MAX-ACCESS  not-accessible
    STATUS      current
    DESCRIPTION
       "The tmnxSubSlaacOvrTable contains QoS (Quality of Service) overrides
        for stateless address autoconfiguration (SLAAC) hosts.

        Entries in this table are created and destroyed by the system.

        This table is a sparse augment of the tmnxSubSlaacTable: entries
        are created only for SLAAC hosts for which QoS overrides information
        is available."
    ::= { tmnxSubMgmtObjects 121 }

tmnxSubSlaacOvrEntry   OBJECT-TYPE
    SYNTAX      TmnxSubSlaacOvrEntry
    MAX-ACCESS  not-accessible
    STATUS      current
    DESCRIPTION
       "Each conceptual row represents QoS overrides information
        of a SLAAC host."
    INDEX { svcId,
            tmnxSubSlaacPfxType,
            tmnxSubSlaacPfx,
            tmnxSubSlaacMacAddr,
            tmnxSubSlaacOvrDirection,
            tmnxSubSlaacOvrType,
            tmnxSubSlaacOvrTypeId,
            tmnxSubSlaacOvrTypeName
        }
    ::= { tmnxSubSlaacOvrTable 1 }

TmnxSubSlaacOvrEntry ::=
    SEQUENCE {
        tmnxSubSlaacOvrDirection        TDirectionIngEgr,
        tmnxSubSlaacOvrType             TQosOverrideType,
        tmnxSubSlaacOvrTypeId           Integer32,
        tmnxSubSlaacOvrTypeName         TNamedItemOrEmpty,
        tmnxSubSlaacOvrPIR              TQosQueuePIRRateOverride,
        tmnxSubSlaacOvrCIR              TQosQueueCIRRateOverride,
        tmnxSubSlaacOvrCBS              TBurstSizeBytesOvr,
        tmnxSubSlaacOvrMBS              TBurstSizeBytesOvr,
        tmnxSubSlaacOvrWrrWeight        THsmdaWrrWeightOverride,
        tmnxSubSlaacOvrSummedCIR        TruthValue
    }

tmnxSubSlaacOvrDirection OBJECT-TYPE
    SYNTAX          TDirectionIngEgr
    MAX-ACCESS      not-accessible
    STATUS          current
    DESCRIPTION     "The value of tmnxSubSlaacOvrDirection indicates if
                     this row specifies ingress or egress qos override
                     parameters."
    ::= { tmnxSubSlaacOvrEntry 1 }

tmnxSubSlaacOvrType OBJECT-TYPE
    SYNTAX          TQosOverrideType
    MAX-ACCESS      not-accessible
    STATUS          current
    DESCRIPTION     "The value of tmnxSubSlaacOvrType indicates what field
                     has been overridden by this row."
    ::= { tmnxSubSlaacOvrEntry 2 }

tmnxSubSlaacOvrTypeId OBJECT-TYPE
    SYNTAX          Integer32
    MAX-ACCESS      not-accessible
    STATUS          current
    DESCRIPTION     "The value of tmnxSubSlaacOvrTypeId indicates the ID of
                     the queue/policer that has been overridden by this row.

                     If the value of tmnxSubSlaacOvrType is not 'queue (1)'
                     or 'policer (2)', this field must be set to zero (0)."
    ::= { tmnxSubSlaacOvrEntry 3 }

tmnxSubSlaacOvrTypeName OBJECT-TYPE
    SYNTAX          TNamedItemOrEmpty
    MAX-ACCESS      not-accessible
    STATUS          current
    DESCRIPTION     "The value of tmnxSubSlaacOvrTypeName indicates the
                     name of the scheduler/arbiter that has been overridden by
                     this row.

                     If the value of tmnxSubSlaacOvrType is not
                     'arbiter (4)' or 'scheduler (5)', this field must be set to
                     zero (0)."
    ::= { tmnxSubSlaacOvrEntry 4 }

tmnxSubSlaacOvrPIR OBJECT-TYPE
    SYNTAX          TQosQueuePIRRateOverride
    MAX-ACCESS      read-only
    STATUS          current
    DESCRIPTION     "The value of tmnxSubSlaacOvrPIR indicates the PIR rate
                     in kbps allowed for the object overridden by this row."
    ::= { tmnxSubSlaacOvrEntry 5 }

tmnxSubSlaacOvrCIR OBJECT-TYPE
    SYNTAX          TQosQueueCIRRateOverride
    MAX-ACCESS      read-only
    STATUS          current
    DESCRIPTION     "The value of tmnxSubSlaacOvrCIR indicates the CIR rate
                     in kbps allowed for the object overridden by this row."
    ::= { tmnxSubSlaacOvrEntry 6 }

tmnxSubSlaacOvrCBS OBJECT-TYPE
    SYNTAX          TBurstSizeBytesOvr
    MAX-ACCESS      read-only
    STATUS          current
    DESCRIPTION     "The value of tmnxSubSlaacOvrCBS indicates the amount of
                     reserved buffer space (in bytes) for the object
                     overridden by this row."
    ::= { tmnxSubSlaacOvrEntry 7 }

tmnxSubSlaacOvrMBS OBJECT-TYPE
    SYNTAX          TBurstSizeBytesOvr
    MAX-ACCESS      read-only
    STATUS          current
    DESCRIPTION     "The value of tmnxSubSlaacOvrMBS indicates the maximum
                     amount of reserved buffer space (in bytes) for the object
                     overridden by this row."
    ::= { tmnxSubSlaacOvrEntry 8 }

tmnxSubSlaacOvrWrrWeight OBJECT-TYPE
    SYNTAX          THsmdaWrrWeightOverride
    MAX-ACCESS      read-only
    STATUS          current
    DESCRIPTION
    "The value of tmnxSubSlaacOvrWrrWeight specifies the weight of this queue
     for the HSMDA scheduler.

     The weight determines how much bandwidth this queue gets out of the
     total rate for the scheduling class.

     The value of tmnxSubSlaacOvrWrrWeight is only relevant if the value of
     tmnxSubSlaacOvrType is equal to 'queue', and if the queue specified in
     tmnxSubSlaacOvrTypeId is referenced in the value of
     TIMETRA-QOS-MIB::tHsmdaWrrPolicyIncludeQueues of the Weighted Round Robin
     policy associated with this PPP session."
    ::= { tmnxSubSlaacOvrEntry 9 }

tmnxSubSlaacOvrSummedCIR OBJECT-TYPE
    SYNTAX      TruthValue
    MAX-ACCESS  read-only
    STATUS      current
    DESCRIPTION
        "The value of tmnxSubSlaacOvrSummedCIR indicates if the CIR should
         be used as the summed CIR values of the children schedulers or queues.
         If set to 'true', the applicable scheduler CIR (tmnxSubSlaacOvrCIR)
         loses its meaning."
    ::= { tmnxSubSlaacOvrEntry 10 }

-- ------------------------------------------------
--  The Subscriber SLAAC Host Address Table
-- ------------------------------------------------

tmnxSubSlaacAddressTable   OBJECT-TYPE
    SYNTAX      SEQUENCE OF TmnxSubSlaacAddressEntry
    MAX-ACCESS  not-accessible
    STATUS      current
    DESCRIPTION
       "The tmnxSubSlaacAddressTable has an entry for each
        address assigned to a stateless address autoconfiguration (SLAAC) host."
    ::= { tmnxSubMgmtObjects 122 }

tmnxSubSlaacAddressEntry   OBJECT-TYPE
    SYNTAX      TmnxSubSlaacAddressEntry
    MAX-ACCESS  not-accessible
    STATUS      current
    DESCRIPTION
       "Each conceptual row represents an address assigned to a slaac host.

        Entries in this table are created and destroyed by the system."
    INDEX       { svcId,
                  tmnxSubSlaacPfxType,
                  tmnxSubSlaacPfx,
                  tmnxSubSlaacMacAddr,
                  tmnxSubSlaacAddressType,
                  tmnxSubSlaacAddress }
    ::= { tmnxSubSlaacAddressTable 1 }

TmnxSubSlaacAddressEntry ::=
    SEQUENCE {
        tmnxSubSlaacAddressType          InetAddressType,
        tmnxSubSlaacAddress              InetAddress,
        tmnxSubSlaacAddrShcvOperState    ServShcvOperState,
        tmnxSubSlaacAddrShcvChecks       Unsigned32,
        tmnxSubSlaacAddrShcvReplies      Unsigned32,
        tmnxSubSlaacAddrShcvReplyTime    TimeStamp
    }

tmnxSubSlaacAddressType OBJECT-TYPE
    SYNTAX          InetAddressType
    MAX-ACCESS      not-accessible
    STATUS          current
    DESCRIPTION     "The value of tmnxSubSlaacAddressType indicates the
                     address type of tmnxSubSlaacAddress."
    ::= { tmnxSubSlaacAddressEntry 1 }

tmnxSubSlaacAddress OBJECT-TYPE
    SYNTAX          InetAddress (SIZE (0|16))
    MAX-ACCESS      not-accessible
    STATUS          current
    DESCRIPTION     "The value of tmnxSubSlaacAddress indicates an IPv6
                     address in use by the SLAAC host."
    ::= { tmnxSubSlaacAddressEntry 2 }

tmnxSubSlaacAddrShcvOperState OBJECT-TYPE
    SYNTAX          ServShcvOperState
    MAX-ACCESS      read-only
    STATUS          current
    DESCRIPTION     "The value of tmnxSubSlaacAddrShcvOperState indicates the
                     state of the subscriber host connectivity check for
                     this SLAAC host address."
    ::= { tmnxSubSlaacAddressEntry 3 }

tmnxSubSlaacAddrShcvChecks OBJECT-TYPE
    SYNTAX          Unsigned32
    MAX-ACCESS      read-only
    STATUS          current
    DESCRIPTION     "The value of tmnxSubSlaacAddrShcvChecks indicates the
                     number of host connectivity check requests for
                     this SLAAC host address."
    ::= { tmnxSubSlaacAddressEntry 4 }

tmnxSubSlaacAddrShcvReplies OBJECT-TYPE
    SYNTAX          Unsigned32
    MAX-ACCESS      read-only
    STATUS          current
    DESCRIPTION     "The value of tmnxSubSlaacAddrShcvReplies indicates the
                     number of host connectivity replies for
                     this SLAAC host address."
    ::= { tmnxSubSlaacAddressEntry 5 }

tmnxSubSlaacAddrShcvReplyTime OBJECT-TYPE
    SYNTAX          TimeStamp
    MAX-ACCESS      read-only
    STATUS          current
    DESCRIPTION     "The value of tmnxSubSlaacAddrShcvReplyTime indicates the
                     time of the last successful host connectivity check for
                     this SLAAC host address."
    ::= { tmnxSubSlaacAddressEntry 6 }

-- --------------------------------------------------------
-- tmnxSubProfLagTable
-- --------------------------------------------------------
--  Augmentation of the tmnxSLAProfileTable
--  The use of the AUGMENTS clause implies a one-to-one dependent relationship
--  between the base table, tmnxSubProfileTable, and the augmenting table,
--  tmnxSubProfLagTable. This in effect extends the tmnxSubProfileTable
--  with additional columns. Creation (or deletion) of a row in the
--  tmnxSubProfileTable results in the same fate for the row in the
--  tmnxSubProfLagTable.

tmnxSubProfLagTableLastChange OBJECT-TYPE
    SYNTAX      TimeStamp
    MAX-ACCESS  read-only
    STATUS      current
    DESCRIPTION
      "The value of tmnxSubProfLagTableLastChange indicates the sysUpTime
       at the time of the last modification of tmnxSubProfLagTable.

       If no changes were made to the entry since the last
       re-initialization of the local network management subsystem,
       then this object contains a zero value."
    ::= { tmnxSubMgmtObjects 123 }


tmnxSubProfLagTable OBJECT-TYPE
    SYNTAX      SEQUENCE OF TmnxSubProfLagEntry
    MAX-ACCESS  not-accessible
    STATUS      current
    DESCRIPTION
        "The tmnxSubProfLagTable contains objects to configure 
         behavior related to Link Aggregation Groups (LAG) for
         the subscribers associated with this profile."
    ::= { tmnxSubMgmtObjects 124 }

tmnxSubProfLagEntry OBJECT-TYPE
    SYNTAX      TmnxSubProfLagEntry
    MAX-ACCESS  not-accessible
    STATUS      current
    DESCRIPTION
        "Each conceptual row represents configuration of a particular
         subscriber profile.
         
         Entries in this table are created and destroyed automatically
         by the system."
    AUGMENTS { tmnxSubProfileEntry }
    ::= { tmnxSubProfLagTable 1 }

TmnxSubProfLagEntry ::=
    SEQUENCE {
        tmnxSubProfLagLastChanged        TimeStamp,
        tmnxSubProfLagPlhClass           TmnxLagPerLinkHashClass,
        tmnxSubProfLagPlhWeight          TmnxLagPerLinkHashWeight
    }

tmnxSubProfLagLastChanged  OBJECT-TYPE
    SYNTAX      TimeStamp
    MAX-ACCESS  read-only
    STATUS      current
    DESCRIPTION
        "The value of tmnxSubProfLagLastChanged indicates the sysUpTime
         at the time of the last modification of this entry."
    ::= { tmnxSubProfLagEntry 1 }

tmnxSubProfLagPlhClass  OBJECT-TYPE
    SYNTAX      TmnxLagPerLinkHashClass
    MAX-ACCESS  read-create
    STATUS      current
    DESCRIPTION
        "The value of tmnxSubProfLagPlhClass specifies the class to be used
         to select a LAG link.

         The value of this object is only applicable when the subscriber
         uses a SAP on a LAG where the value of the object TIMETRA-LAG-MIB::tLagPerLinkHashWeighted
         is equal to 'true'."
    DEFVAL { 1 }
    ::= { tmnxSubProfLagEntry 2 }

tmnxSubProfLagPlhWeight  OBJECT-TYPE
    SYNTAX      TmnxLagPerLinkHashWeight
    MAX-ACCESS  read-create
    STATUS      current
    DESCRIPTION
        "The value of tmnxSubProfLagPlhWeight specifies the weight to be
         associated with this SAP when selecting a LAG link.

         The value of this object is only applicable when the subscriber
         uses a SAP on a LAG where the value of the object TIMETRA-LAG-MIB::tLagPerLinkHashWeighted
         is equal to 'true'."
    DEFVAL { 1 }
    ::= { tmnxSubProfLagEntry 3 }


--
--  The Subscriber SLAAC BGP Host Table
--

tmnxSubSlaacBgpTable   OBJECT-TYPE
    SYNTAX      SEQUENCE OF TmnxSubSlaacBgpEntry
    MAX-ACCESS  not-accessible
    STATUS      current
    DESCRIPTION
        "The tmnxSubSlaacBgpTable augments the tmnxSubSlaacTable.
         This table contains the parameters used for BGP."
    ::= { tmnxSubMgmtObjects 125 }

tmnxSubSlaacBgpEntry   OBJECT-TYPE
    SYNTAX      TmnxSubSlaacBgpEntry
    MAX-ACCESS  not-accessible
    STATUS      current
    DESCRIPTION
        "Each row entry contains parameters used for BGP."
    AUGMENTS        { tmnxSubSlaacEntry }
    ::= { tmnxSubSlaacBgpTable 1 }

TmnxSubSlaacBgpEntry ::=
    SEQUENCE {
        tmnxSubSlaacBgpPrngPlcyName      TNamedItemOrEmpty,
        tmnxSubSlaacBgpAuthKeyChain      TNamedItemOrEmpty,
        tmnxSubSlaacBgpMD5AuthKey        OCTET STRING,
        tmnxSubSlaacBgpImportPolicy      TPolicyStatementNameOrEmpty,
        tmnxSubSlaacBgpExportPolicy      TPolicyStatementNameOrEmpty,
        tmnxSubSlaacBgpPeerAS            InetAutonomousSystemNumber,
        tmnxSubSlaacBgpPeeringStatus     BgpPeeringStatus
    }

tmnxSubSlaacBgpPrngPlcyName OBJECT-TYPE
    SYNTAX          TNamedItemOrEmpty
    MAX-ACCESS      read-only
    STATUS          current
    DESCRIPTION
        "The value of tmnxSubSlaacBgpPrngPlcyName indicates the peering
         policy which is used to set up the BGP peer for this lease state."
    ::= { tmnxSubSlaacBgpEntry 1 }

tmnxSubSlaacBgpAuthKeyChain OBJECT-TYPE
    SYNTAX          TNamedItemOrEmpty
    MAX-ACCESS      read-only
    STATUS          current
    DESCRIPTION
        "The value of tmnxSubSlaacBgpAuthKeyChain indicates the
         keychain which is used to sign and/or authenticate  the BGP
         protocol stream."
    ::= { tmnxSubSlaacBgpEntry 2 }

tmnxSubSlaacBgpMD5AuthKey OBJECT-TYPE
    SYNTAX          OCTET STRING (SIZE(0..255))
    MAX-ACCESS      read-only
    STATUS          current
    DESCRIPTION     
        "The value of tmnxSubSlaacBgpMD5AuthKey indicates 
         the authentication key used between BGP
         peers neighbors before establishing sessions. Authentication
         is done using the MD-5 message based digest protocol."
    ::= { tmnxSubSlaacBgpEntry 3 }

tmnxSubSlaacBgpImportPolicy OBJECT-TYPE
    SYNTAX          TPolicyStatementNameOrEmpty
    MAX-ACCESS      read-only
    STATUS          current
    DESCRIPTION     
        "The value of tmnxSubSlaacBgpImportPolicy indicates 
         the import policy."
    ::= { tmnxSubSlaacBgpEntry 4 }

tmnxSubSlaacBgpExportPolicy OBJECT-TYPE
    SYNTAX          TPolicyStatementNameOrEmpty
    MAX-ACCESS      read-only
    STATUS          current
    DESCRIPTION     
        "The value of tmnxSubSlaacBgpExportPolicy indicates 
         the export policy."
    ::= { tmnxSubSlaacBgpEntry 5 }

tmnxSubSlaacBgpPeerAS OBJECT-TYPE
    SYNTAX          InetAutonomousSystemNumber
    MAX-ACCESS      read-only
    STATUS          current
    DESCRIPTION     
        "The value of tmnxSubSlaacBgpPeerAS indicates the Autonomous System
         number for the remote peer."
    ::= { tmnxSubSlaacBgpEntry 6 }

tmnxSubSlaacBgpPeeringStatus OBJECT-TYPE
    SYNTAX          BgpPeeringStatus
    MAX-ACCESS      read-only
    STATUS          current
    DESCRIPTION
        "The value of tmnxSubSlaacBgpPeeringStatus indicates
         the status of the BGP peering session."
    ::= { tmnxSubSlaacBgpEntry 7 }

--
--  The Subscriber PCC rule table
--

tmnxSubPccRuleTable   OBJECT-TYPE
    SYNTAX      SEQUENCE OF TmnxSubPccRuleEntry
    MAX-ACCESS  not-accessible
    STATUS      current
    DESCRIPTION
        "The tmnxSubPccRuleTable contains read-only info
         on the PCC-rules currently active in the system."
    ::= { tmnxSubMgmtObjects 126 }

tmnxSubPccRuleEntry   OBJECT-TYPE
    SYNTAX      TmnxSubPccRuleEntry
    MAX-ACCESS  not-accessible
    STATUS      current
    DESCRIPTION
        "Each row (entry) contains info of a particular PCC-rule"
    INDEX       { tmnxSubPccRuleName,
                  tmnxSubPccRuleKey }
    ::= { tmnxSubPccRuleTable 1 }

TmnxSubPccRuleEntry ::=
    SEQUENCE {
        tmnxSubPccRuleName               TmnxPccRuleName,
        tmnxSubPccRuleKey                Unsigned32,
        tmnxSubPCCRuleDirection          TDirectionIngEgr,
        tmnxSubPccRuleForwardAction      INTEGER,
        tmnxSubPccRuleQosAction          BITS,
        tmnxSubPccRuleRateLimPirUps      THPolPIRRateOverride,
        tmnxSubPccRuleRateLimPirDwns     THPolPIRRateOverride,
        tmnxSubPccRuleRateLimCirUps      THPolCIRRateOverride,
        tmnxSubPccRuleRateLimCirDwns     THPolCIRRateOverride,
        tmnxSubPccRuleMonitoringKey      TmnxPccRuleMonitorKey,
        tmnxSubPccRuleSetFC              TFCType,
        tmnxSubPccRuleRedirectRouterV4   TmnxServId,
        tmnxSubPccRuleRedirectRouterV6   TmnxServId,
        tmnxSubPccRuleRedirIpv4Addr      InetAddressIPv4,
        tmnxSubPccRuleRedirIpv6Addr      InetAddressIPv6,
        tmnxSubPccRuleRedirUrl           TmnxHttpRedirectUrl,
        tmnxSubPccRuleNbrFlows           INTEGER
    }

tmnxSubPccRuleName OBJECT-TYPE
    SYNTAX      TmnxPccRuleName
    MAX-ACCESS  not-accessible
    STATUS      current
    DESCRIPTION
        "The value of TmnxPccRuleName indicates the PCC rule name.
         The name of a PCC rule must however not be unique in the system."
    ::= { tmnxSubPccRuleEntry 1 }

tmnxSubPccRuleKey OBJECT-TYPE
    SYNTAX      Unsigned32 (1..'ffffffff'h)
    MAX-ACCESS  not-accessible
    STATUS      current
    DESCRIPTION
        "The value of tmnxSubPccRuleKey indicates a system wide unique
         identifier assigned by the system to each PCC-rule."
    ::= { tmnxSubPccRuleEntry 2 }

tmnxSubPCCRuleDirection OBJECT-TYPE
    SYNTAX      TDirectionIngEgr
    MAX-ACCESS  read-only
    STATUS      current
    DESCRIPTION
        "The value of tmnxSubPCCRuleDirection indicates the flow direction
         on which the PCC-rule acts."
    ::= { tmnxSubPccRuleEntry 3 }

tmnxSubPccRuleForwardAction OBJECT-TYPE
    SYNTAX INTEGER {
              none     (0),
              forward  (1),
              drop     (2),
              redirUrl (3)
           }
    MAX-ACCESS  read-only
    STATUS      current
    DESCRIPTION
        "The value of tmnxSubPccRuleForwardAction indicates the 
         the forwarding action of the PCC-rule."
    ::= { tmnxSubPccRuleEntry 4 }

tmnxSubPccRuleQosAction OBJECT-TYPE
     SYNTAX BITS {
              rateLimit (0),
              fcRemark  (1),
              monitor   (2)
           }
    MAX-ACCESS  read-only
    STATUS      current
    DESCRIPTION
        "The value of tmnxSubPccRuleQosAction indicates the 
         Qos action of the PCC-rule."
    ::= { tmnxSubPccRuleEntry 5 }


tmnxSubPccRuleRateLimPirUps OBJECT-TYPE
    SYNTAX      THPolPIRRateOverride
    MAX-ACCESS  read-only
    STATUS      current
    DESCRIPTION
        "The value of tmnxSubPccRuleRateLimPirUps indicates the PIR
         that will be applied to all upstream data flows that pertain
         to this PCC-rule.
         This value is only taken into account if the bit 'rateLimit'
         is set in the object tmnxSubPccRuleQosAction." 
    ::= { tmnxSubPccRuleEntry 6 }

tmnxSubPccRuleRateLimPirDwns OBJECT-TYPE
    SYNTAX      THPolPIRRateOverride
    MAX-ACCESS  read-only
    STATUS      current
    DESCRIPTION
        "The value of tmnxSubPccRuleRateLimPirDwns indicates the PIR
         that will be applied to all downstream data flows that pertain
         to this PCC-rule.
         This value is only taken into account if the bit 'rateLimit'
         is set in the object tmnxSubPccRuleQosAction." 
    ::= { tmnxSubPccRuleEntry 7 }

tmnxSubPccRuleRateLimCirUps OBJECT-TYPE
    SYNTAX      THPolCIRRateOverride
    MAX-ACCESS  read-only
    STATUS      current
    DESCRIPTION
        "The value of tmnxSubPccRuleRateLimCirUps indicates the CIR
         that will be applied to all upstream data flows that pertain
         to this PCC-rule.
         This value is only taken into account if the bit 'rateLimit'
         is set in the object tmnxSubPccRuleQosAction." 
    ::= { tmnxSubPccRuleEntry 8 }

tmnxSubPccRuleRateLimCirDwns OBJECT-TYPE
    SYNTAX      THPolCIRRateOverride
    MAX-ACCESS  read-only
    STATUS      current
    DESCRIPTION
        "The value of tmnxSubPccRuleRateLimCirDwns indicates the CIR
         that will be applied to all downstream data flows that pertain
         to this PCC-rule.
         This value is only taken into account if the bit 'rateLimit'
         is set in the object tmnxSubPccRuleQosAction." 
    ::= { tmnxSubPccRuleEntry 9 }

tmnxSubPccRuleMonitoringKey OBJECT-TYPE
    SYNTAX      TmnxPccRuleMonitorKey
    MAX-ACCESS  read-only
    STATUS      current
    DESCRIPTION
        "If non NULL, the value of tmnxSubPccRuleMonitoringKey indicates
         the monitoring key defined in this PCC-rule.
         This value is only taken into account if the bit 'monitor'
         is set in the object tmnxSubPccRuleQosAction." 
    ::= { tmnxSubPccRuleEntry 10 }

tmnxSubPccRuleSetFC OBJECT-TYPE
    SYNTAX      TFCType
    MAX-ACCESS  read-only
    STATUS      current
    DESCRIPTION
        "The value of tmnxSubPccRuleSetFC indicates the forwarding class (FC)
         that will be assigned to all data flows that pertain
         to this PCC-rule.
         This value is only taken into account if the bit 'fcRemark'
         is set in the object tmnxSubPccRuleQosAction." 
    ::= { tmnxSubPccRuleEntry 11 }

tmnxSubPccRuleRedirectRouterV4 OBJECT-TYPE
    SYNTAX      TmnxServId
    MAX-ACCESS  read-only
    STATUS      current
    DESCRIPTION
        "The value of tmnxSubPccRuleRedirectRouterV4 indicates 
         the service Id into which all IPv4 data flows that pertain
         to this PCC-rule must be routed.
         A value of all zero's indicate that no redirection service 
         is present.
         This value is only taken into account if the object
         tmnxSubPccRuleForwardAction is set to forward."
    ::= { tmnxSubPccRuleEntry 12 }

tmnxSubPccRuleRedirectRouterV6 OBJECT-TYPE
    SYNTAX      TmnxServId
    MAX-ACCESS  read-only
    STATUS      current
    DESCRIPTION
        "The value of tmnxSubPccRuleRedirectRouterV6 indicates 
         the service Id into which all IPv6 data flows that pertain
         to this PCC-rule must be routed.
         A value of all zero's indicate that no redirection service 
         is present.
         This value is only taken into account if the object
         tmnxSubPccRuleForwardAction is set to forward."

    ::= { tmnxSubPccRuleEntry 13 }

tmnxSubPccRuleRedirIpv4Addr OBJECT-TYPE
    SYNTAX      InetAddressIPv4
    MAX-ACCESS  read-only
    STATUS      current
    DESCRIPTION
        "The value of tmnxSubPccRuleRedirIpv4Addr indicates 
         the IPv4 address to which all IPv4 data flows that pertain
         to this PCC-rule must be redirected.
         A value of all zero's indicate that no redirection address 
         is present.
         This value is only taken into account if the object
         tmnxSubPccRuleForwardAction is set to forward."
    ::= { tmnxSubPccRuleEntry 14 }

tmnxSubPccRuleRedirIpv6Addr OBJECT-TYPE
    SYNTAX      InetAddressIPv6
    MAX-ACCESS  read-only
    STATUS      current
    DESCRIPTION
        "The value of tmnxSubPccRuleRedirIpv6Addr indicates 
         the IPv6 address to which all IPv6 data flows that pertain
         to this PCC-rule must be redirected.
         A value of all zero's indicate that no redirection address 
         is present.
         This value is only taken into account if the object
         tmnxSubPccRuleForwardAction is set to forward."
    ::= { tmnxSubPccRuleEntry 15 }

tmnxSubPccRuleRedirUrl OBJECT-TYPE
    SYNTAX      TmnxHttpRedirectUrl
    MAX-ACCESS  read-only
    STATUS      current
    DESCRIPTION
        "If non NULL, the value of tmnxSubPccRuleRedirUrl indicates
         the URL to which all data flows that pertain
         to this PCC-rule must be redirected.
         This value is only taken into account if the object
         tmnxSubPccRuleForwardAction is set to redirUrl."
    ::= { tmnxSubPccRuleEntry 16 }

tmnxSubPccRuleNbrFlows OBJECT-TYPE
    SYNTAX      INTEGER
    MAX-ACCESS  read-only
    STATUS      current
    DESCRIPTION
        "The value of tmnxSubPccRuleRedirUrl indicates
        how many flow rules are defined in this PCC-rule."
    ::= { tmnxSubPccRuleEntry 17 }
     
--
--  The Subscriber PCC rule flow table
--

tmnxSubPccRuleFlowTable   OBJECT-TYPE
    SYNTAX      SEQUENCE OF TmnxSubPccRuleFlowEntry
    MAX-ACCESS  not-accessible
    STATUS      current
    DESCRIPTION
        "The tmnxSubPccRuleFlowTable contains read-only info
         on the flows defined in the PCC-rules currently active
         in the system."
    ::= { tmnxSubMgmtObjects 127 }

tmnxSubPccRuleFlowEntry   OBJECT-TYPE
    SYNTAX      TmnxSubPccRuleFlowEntry
    MAX-ACCESS  not-accessible
    STATUS      current
    DESCRIPTION
        "Each row (entry) contains info of a particular flow of
         a particular PCC-rule"
    INDEX       { tmnxSubPccRuleName,
                  tmnxSubPccRuleKey,
                  tmnxSubPCCRuleFlowId }
    ::= { tmnxSubPccRuleFlowTable 1 }

TmnxSubPccRuleFlowEntry ::=
    SEQUENCE {
        tmnxSubPCCRuleFlowId             Unsigned32,
        tmnxSubPCCRuleFlowDirection      TDirectionIngEgr,
        tmnxSubPCCRuleFlowSrcAddrType    InetAddressType,
        tmnxSubPCCRuleFlowSrcAddr        InetAddress,
        tmnxSubPCCRuleFlowSrcPfxLen      InetAddressPrefixLength,
        tmnxSubPCCRuleFlowSrcPortLow     TTcpUdpPort,
        tmnxSubPCCRuleFlowSrcPortHigh    TTcpUdpPort,
        tmnxSubPCCRuleFlowDstAddrType    InetAddressType,
        tmnxSubPCCRuleFlowDstAddr        InetAddress,
        tmnxSubPCCRuleFlowDstPfxLen      InetAddressPrefixLength,
        tmnxSubPCCRuleFlowDstPortLow     TTcpUdpPort,
        tmnxSubPCCRuleFlowDstPortHigh    TTcpUdpPort,
        tmnxSubPCCRuleFlowProtNxtHdr     TIpProtocol,
        tmnxSubPCCRuleFlowDSCP           TDSCPNameOrEmpty
    }

tmnxSubPCCRuleFlowId OBJECT-TYPE
    SYNTAX      Unsigned32 (1..'ffffffff'h)
    MAX-ACCESS  not-accessible
    STATUS      current
    DESCRIPTION
        "The value of tmnxSubPCCRuleFlowId indicates the ordered 
         precedence number of this flow in the given PCC-rule."
    ::= { tmnxSubPccRuleFlowEntry 1 }

tmnxSubPCCRuleFlowDirection OBJECT-TYPE
    SYNTAX      TDirectionIngEgr
    MAX-ACCESS  read-only
    STATUS      current
    DESCRIPTION
        "The value of tmnxSubPCCRuleFlowDirection indicates the flow
         direction."
    ::= { tmnxSubPccRuleFlowEntry 2 }

tmnxSubPCCRuleFlowSrcAddrType OBJECT-TYPE
    SYNTAX      InetAddressType
    MAX-ACCESS  read-only
    STATUS      current
    DESCRIPTION
        "The value of tmnxSubPCCRuleFlowSrcAddrType indicates the
         address type of tmnxSubPCCRuleFlowSrcAddr."
    ::= { tmnxSubPccRuleFlowEntry 3 }

tmnxSubPCCRuleFlowSrcAddr OBJECT-TYPE
    SYNTAX      InetAddress
    MAX-ACCESS  read-only
    STATUS      current
    DESCRIPTION
        "The value of tmnxSubPCCRuleFlowSrcAddr indicates, together
         with tmnxSubPCCRuleFlowSrcPfxLen the source IP address of 
         the flow."
    ::= { tmnxSubPccRuleFlowEntry 4 }

tmnxSubPCCRuleFlowSrcPfxLen OBJECT-TYPE
    SYNTAX      InetAddressPrefixLength
    MAX-ACCESS  read-only
    STATUS      current
    DESCRIPTION
        "The value of tmnxSubPCCRuleFlowSrcPfxLen indicates 
         the prefix length of tmnxSubPCCRuleFlowSrcAddr."
    ::= { tmnxSubPccRuleFlowEntry 5 }

tmnxSubPCCRuleFlowSrcPortLow OBJECT-TYPE
    SYNTAX     TTcpUdpPort
    MAX-ACCESS read-only
    STATUS     current
    DESCRIPTION
        "The value of tmnxSubPCCRuleFlowSrcPortLow specifies the lower value 
         of the source TCP/UDP port range of the flow."
    ::= { tmnxSubPccRuleFlowEntry 6 }

tmnxSubPCCRuleFlowSrcPortHigh OBJECT-TYPE
    SYNTAX     TTcpUdpPort
    MAX-ACCESS read-only
    STATUS     current
    DESCRIPTION
        "The value of tmnxSubPCCRuleFlowSrcPortHigh specifies the upper value 
         of the source TCP/UDP port range of the flow."
    ::= { tmnxSubPccRuleFlowEntry 7 }

tmnxSubPCCRuleFlowDstAddrType OBJECT-TYPE
    SYNTAX      InetAddressType
    MAX-ACCESS  read-only
    STATUS      current
    DESCRIPTION
        "The value of tmnxSubPCCRuleFlowDstAddrType indicates the
         address type of tmnxSubPCCRuleFlowDstAddr."
    ::= { tmnxSubPccRuleFlowEntry 8 }
         
tmnxSubPCCRuleFlowDstAddr OBJECT-TYPE
    SYNTAX      InetAddress        
    MAX-ACCESS  read-only
    STATUS      current
    DESCRIPTION
        "The value of tmnxSubPCCRuleFlowDstAddr indicates, together
         with tmnxSubPCCRuleFlowDstPfxLen the source IP address of 
         the flow."
    ::= { tmnxSubPccRuleFlowEntry 9 }

tmnxSubPCCRuleFlowDstPfxLen OBJECT-TYPE
    SYNTAX      InetAddressPrefixLength
    MAX-ACCESS  read-only
    STATUS      current
    DESCRIPTION
        "The value of tmnxSubPCCRuleFlowDstPfxLen indicates 
         the prefix length of tmnxSubPCCRuleFlowDstAddr."
    ::= { tmnxSubPccRuleFlowEntry 10 }

tmnxSubPCCRuleFlowDstPortLow OBJECT-TYPE
    SYNTAX     TTcpUdpPort
    MAX-ACCESS read-only
    STATUS     current
    DESCRIPTION
        "The value of tmnxSubPCCRuleFlowDstPortLow specifies the lower value 
         of the destination TCP/UDP port range of the flow."
    ::= { tmnxSubPccRuleFlowEntry 11 }

tmnxSubPCCRuleFlowDstPortHigh OBJECT-TYPE
    SYNTAX     TTcpUdpPort
    MAX-ACCESS read-only
    STATUS     current
    DESCRIPTION
        "The value of tmnxSubPCCRuleFlowDstPortHigh specifies the upper value 
         of the destination TCP/UDP port range of the flow."
    ::= { tmnxSubPccRuleFlowEntry 12 }

tmnxSubPCCRuleFlowProtNxtHdr  OBJECT-TYPE
    SYNTAX      TIpProtocol
    MAX-ACCESS  read-only
    STATUS      current
    DESCRIPTION
        "The value of tmnxSubPCCRuleFlowProtNxtHdr specifies
         for IPv4 MAF the IP protocol field, and for IPv6 the next header
         type to be used in the match criteria for this flow.
         Some well-know protocol numbers are TCP (6), and UDP (7).
         The value of -1 is used to indicate that this object is not
         initialized.
         The value of -2 is used to indicate udp/tcp protocol matching."
    ::= { tmnxSubPccRuleFlowEntry 13 }

tmnxSubPCCRuleFlowDSCP  OBJECT-TYPE
    SYNTAX      TDSCPNameOrEmpty
    MAX-ACCESS  read-only
    STATUS      current
    DESCRIPTION
        "The value of tmnxSubPCCRuleFlowDSCP specifies the DSCP to be
         matched for this flow."
    ::= { tmnxSubPccRuleFlowEntry 14 }

--
--  The Subscriber PCC rule flow table
--
tmnxSubHostPccRuleInfoTable OBJECT-TYPE
    SYNTAX      SEQUENCE OF TmnxSubHostPccRuleInfoEntry
    MAX-ACCESS  not-accessible
    STATUS      current
    DESCRIPTION
        "The tmnxSubHostPccRuleInfoTable shows all PCC rules in use by
         each subscriber host present in the system."
    ::= { tmnxSubMgmtObjects 128 }

tmnxSubHostPccRuleInfoEntry OBJECT-TYPE
    SYNTAX      TmnxSubHostPccRuleInfoEntry
    MAX-ACCESS  not-accessible
    STATUS      current
    DESCRIPTION
        "Each row entry contains PCC rule information about a particular
         PCC rule used by a particular subscriber host available in the system."
    INDEX { svcId,
            sapPortId,
            sapEncapValue,
            tmnxSubHostInfoV2IpAddressType,
            tmnxSubHostInfoV2IpAddress,
            tmnxSubHostInfoV2MacAddress,
            tmnxSubHostInfoV2PppoeSessionId,
            tmnxSubHostPCCRuleIndex}
    ::= { tmnxSubHostPccRuleInfoTable 1 }

TmnxSubHostPccRuleInfoEntry ::=
    SEQUENCE {
        tmnxSubHostPCCRuleIndex          Unsigned32,
        tmnxSubHostPCCRulePrecedence     Unsigned32,
        tmnxSubHostPCCRuleName           TmnxPccRuleName,
        tmnxSubHostPCCRuleKey            Unsigned32
    }

tmnxSubHostPCCRuleIndex OBJECT-TYPE
    SYNTAX      Unsigned32
    MAX-ACCESS  not-accessible
    STATUS      current
    DESCRIPTION
        "The value of tmnxSubHostPCCRuleIndex indicates the PCC rule 
         index for the given host. The Pcc rules are applied in order
         of this index."
    ::= { tmnxSubHostPccRuleInfoEntry 1 }

tmnxSubHostPCCRulePrecedence OBJECT-TYPE
    SYNTAX      Unsigned32
    MAX-ACCESS  read-only
    STATUS      current
    DESCRIPTION
        "The value of tmnxSubHostPCCRulePrecedence indicates the PCC rule 
         precedence for the given host.
         The different pcc-rules for a host are applied in order of increasing
         precedence, i.e. the lowest precedence is the first pcc-rule applied."
    ::= { tmnxSubHostPccRuleInfoEntry 2 }


tmnxSubHostPCCRuleName OBJECT-TYPE
    SYNTAX      TmnxPccRuleName
    MAX-ACCESS  read-only
    STATUS      current
    DESCRIPTION
        "The value of tmnxSubHostPCCRuleName indicates the PCC rule name.
         The name of a PCC rule must not be unique in the system, but for
         a given host a pcc-rule-name can occur only once."
    ::= { tmnxSubHostPccRuleInfoEntry 3 }

tmnxSubHostPCCRuleKey OBJECT-TYPE
    SYNTAX      Unsigned32
    MAX-ACCESS  read-only
    STATUS      current
    DESCRIPTION
        "The value of tmnxSubHostPCCRuleKey indicates a system wide unique
         identifier assigned by the system to each PCC-rule.
         A value 0 (zero) indicates that no id has been assigned to the Rule."
    ::= { tmnxSubHostPccRuleInfoEntry 4 }


-- --------------------------------------------------------
-- tmnxSubIpoePlcyTable
-- --------------------------------------------------------
tmnxSubIpoePlcyTableLastChanged  OBJECT-TYPE
    SYNTAX      TimeStamp
    MAX-ACCESS  read-only
    STATUS      current
    DESCRIPTION
        "The value of tmnxSubIpoePlcyTableLastChanged indicates the 
         sysUpTime at the time of the most recent change to the
         tmnxSubIpoePlcyTable."
    ::= { tmnxSubIpoeObjs 1 }
    
tmnxSubIpoePlcyTable             OBJECT-TYPE
    SYNTAX      SEQUENCE OF TmnxSubIpoePlcyEntry
    MAX-ACCESS  not-accessible
    STATUS      current
    DESCRIPTION
        "The table tmnxSubIpoePlcyTable contains the information pertaining to
         configure an IPoE session policy in the system."
    ::= { tmnxSubIpoeObjs 2 }

tmnxSubIpoePlcyEntry             OBJECT-TYPE
    SYNTAX      TmnxSubIpoePlcyEntry
    MAX-ACCESS  not-accessible
    STATUS      current
    DESCRIPTION
        "Each row entry represents a IPoE session policy configured in
         the system.

         Rows in table tmnxSubIpoePlcyTable are created and destroyed by 
         SNMP SET operations on the object tmnxSubIpoePlcyRowStatus."
    INDEX { IMPLIED tmnxSubIpoePlcyName }
    ::= { tmnxSubIpoePlcyTable 1 }

TmnxSubIpoePlcyEntry ::=
    SEQUENCE {
        tmnxSubIpoePlcyName              TNamedItem,
        tmnxSubIpoePlcyLastChanged       TimeStamp,
        tmnxSubIpoePlcyRowStatus         RowStatus,
        tmnxSubIpoePlcyDescription       TItemDescription,
        tmnxSubIpoePlcySessionKey        BITS,
        tmnxSubIpoePlcySessionTimeout    Unsigned32
    }
    
tmnxSubIpoePlcyName              OBJECT-TYPE
    SYNTAX      TNamedItem
    MAX-ACCESS  not-accessible
    STATUS      current
    DESCRIPTION
        "The value of tmnxSubIpoePlcyName specifies the name of the IPoE
         policy."
    ::= { tmnxSubIpoePlcyEntry 1 }

tmnxSubIpoePlcyLastChanged       OBJECT-TYPE
    SYNTAX      TimeStamp
    MAX-ACCESS  read-only
    STATUS      current
    DESCRIPTION
        "The value of tmnxSubIpoePlcyLastChanged indicates the sysUpTime at
         the time of the last modification of this entry."
    ::= { tmnxSubIpoePlcyEntry 2 }
    
tmnxSubIpoePlcyRowStatus         OBJECT-TYPE
    SYNTAX      RowStatus
    MAX-ACCESS  read-create
    STATUS      current
    DESCRIPTION
        "The value of tmnxSubIpoePlcyRowStatus controls the creation and
         deletion of rows in this table."
    ::= { tmnxSubIpoePlcyEntry 3 }

tmnxSubIpoePlcyDescription       OBJECT-TYPE
    SYNTAX      TItemDescription
    MAX-ACCESS  read-create
    STATUS      current
    DESCRIPTION
        "The value of tmnxSubIpoePlcyDescription specifies the user provided
         description of this IPoE policy."
    DEFVAL { "" }
    ::= { tmnxSubIpoePlcyEntry 4 }

tmnxSubIpoePlcySessionKey        OBJECT-TYPE
    SYNTAX BITS {
        sap    (0),
        mac    (1),
        cid    (2),
        rid    (3)
    }
    MAX-ACCESS  read-create
    STATUS      current
    DESCRIPTION
        "The value of tmnxSubIpoePlcySessionKey specifies the 
         session key to be used for this IPoE session to group 
         subscriber hosts."
    DEFVAL {{sap, mac}}
    ::= { tmnxSubIpoePlcyEntry 5 }
            
tmnxSubIpoePlcySessionTimeout    OBJECT-TYPE
    SYNTAX      Unsigned32 (0|1..31104000)
    UNITS       "seconds"
    MAX-ACCESS  read-create
    STATUS      current
    DESCRIPTION
        "The value of tmnxSubIpoePlcySessionTimeout specifies 
         the session timeout period to be used for this IPoE session.
         The value '0' has the meaning of 'unlimited'"
    DEFVAL { 0 }
    ::= { tmnxSubIpoePlcyEntry 6 }

--
--      The Subscriber IPoE Session Table
--

tmnxSubIpoeTable   OBJECT-TYPE
    SYNTAX      SEQUENCE OF TmnxSubIpoeEntry
    MAX-ACCESS  not-accessible
    STATUS      current
    DESCRIPTION
       "The tmnxSubIpoeTable has an entry for each subscriber IPoE Session."
    ::= { tmnxSubIpoeObjs 3 }

tmnxSubIpoeEntry   OBJECT-TYPE
    SYNTAX      TmnxSubIpoeEntry
    MAX-ACCESS  not-accessible
    STATUS      current
    DESCRIPTION
       "Each conceptual row represents a subscriber IPoE Session.

        Entries in this table are created and destroyed by the system."
    INDEX { tmnxSubIpoeIndex }
    ::= { tmnxSubIpoeTable 1 }

TmnxSubIpoeEntry ::= 
    SEQUENCE {
        tmnxSubIpoeIndex                  Unsigned32     
      , tmnxSubIpoeCircuitId              OCTET STRING
      , tmnxSubIpoeRemoteId               OCTET STRING      
      , tmnxSubIpoeGrpIf                  InterfaceIndexOrZero
      , tmnxSubIpoeSubIf                  InterfaceIndexOrZero        
      , tmnxSubIpoeUpTime                 TimeTicks
      , tmnxSubIpoeSessionTimeLeft        Unsigned32
      , tmnxSubIpoeLastAuthTime           TimeStamp
      , tmnxSubIpoeMinAuthIntervalLeft    Unsigned32
      , tmnxSubIpoePersistenceKey         Unsigned32
      , tmnxSubIpoeSubIdent               TmnxSubIdentStringOrEmpty       
      , tmnxSubIpoeSubProfString          TmnxSubProfileStringOrEmpty
      , tmnxSubIpoeSlaProfString          TmnxSlaProfileStringOrEmpty       
      , tmnxSubIpoeAncpString             TmnxAncpStringOrZero
      , tmnxSubIpoeInterDestId            TmnxSubMgtIntDestIdOrEmpty
      , tmnxSubIpoeAppProfString          TmnxAppProfileStringOrEmpty
      , tmnxSubIpoeCategoryMapName        TNamedItemOrEmpty
      , tmnxSubIpoeAcctSessionId          TmnxSubAcctSessionId
      , tmnxSubIpoeSapSessionIndex        Unsigned32        
      , tmnxSubIpoeIpAddrType             InetAddressType
      , tmnxSubIpoeIpAddr                 InetAddress
      , tmnxSubIpoeIpAddrPrefixLength     InetAddressPrefixLength
      , tmnxSubIpoeOriginIp               DhcpLseStateInfoOrigin       
      , tmnxSubIpoePrimaryDnsType         InetAddressType
      , tmnxSubIpoePrimaryDns             InetAddress
      , tmnxSubIpoeSecondaryDnsType       InetAddressType
      , tmnxSubIpoeSecondaryDns           InetAddress
      , tmnxSubIpoePrimaryNbnsType        InetAddressType
      , tmnxSubIpoePrimaryNbns            InetAddress
      , tmnxSubIpoeSecondaryNbnsType      InetAddressType
      , tmnxSubIpoeSecondaryNbns          InetAddress
      , tmnxSubIpoeAddressPool            DisplayString
      , tmnxSubIpoeIpv6PrefixType         InetAddressType
      , tmnxSubIpoeIpv6Prefix             InetAddress
      , tmnxSubIpoeIpv6PrefixLen          InetAddressPrefixLength
      , tmnxSubIpoeIpv6PrefixOrigin       DhcpLseStateInfoOrigin
      , tmnxSubIpoeIpv6PrefixPool         TNamedItemOrEmpty
      , tmnxSubIpoeIpv6DelPfxType         InetAddressType
      , tmnxSubIpoeIpv6DelPfx             InetAddress
      , tmnxSubIpoeIpv6DelPfxLen          InetAddressPrefixLength
      , tmnxSubIpoeIpv6DelPfxOrigin       DhcpLseStateInfoOrigin
      , tmnxSubIpoeIpv6DelPfxPool         TNamedItemOrEmpty
      , tmnxSubIpoeIpv6AddrType           InetAddressType
      , tmnxSubIpoeIpv6Addr               InetAddress
      , tmnxSubIpoeIpv6AddrOrigin         DhcpLseStateInfoOrigin
      , tmnxSubIpoeIpv6AddrPool           TNamedItemOrEmpty
      , tmnxSubIpoeIpv6Dns1Type           InetAddressType
      , tmnxSubIpoeIpv6Dns1               InetAddress
      , tmnxSubIpoeIpv6Dns2Type           InetAddressType
      , tmnxSubIpoeIpv6Dns2               InetAddress        
      , tmnxSubIpoeSessionTimeout         Unsigned32
      , tmnxSubIpoeRadiusClassAttr        OCTET STRING
      , tmnxSubIpoeRadiusUserName         DisplayString
      , tmnxSubIpoeRetailerSvcId          TmnxServId
      , tmnxSubIpoeRetailerIf             InterfaceIndexOrZero
      , tmnxSubIpoeTerminationType        TmnxSubTerminationType
    }
                
tmnxSubIpoeIndex OBJECT-TYPE
    SYNTAX      Unsigned32
    MAX-ACCESS  not-accessible
    STATUS      current
    DESCRIPTION
       "The value of the object tmnxSubIpoeIndex indicates the local  
        identifier of the session."
    ::= { tmnxSubIpoeEntry 1 }

tmnxSubIpoeCircuitId OBJECT-TYPE
    SYNTAX      OCTET STRING (SIZE (0..256))
    MAX-ACCESS  read-only
    STATUS      current
    DESCRIPTION
        "The value of tmnxSubIpoeCircuitId indicates the value of the
         circuit-id sub-option."
    ::= { tmnxSubIpoeEntry 2 }

tmnxSubIpoeRemoteId OBJECT-TYPE
    SYNTAX      OCTET STRING (SIZE (0..256))
    MAX-ACCESS  read-only
    STATUS      current
    DESCRIPTION
        "The value of tmnxSubIpoeRemoteId indicates the value of the
         remote-id sub-option."
    ::= { tmnxSubIpoeEntry 3 }
    
tmnxSubIpoeGrpIf OBJECT-TYPE
    SYNTAX      InterfaceIndexOrZero
    MAX-ACCESS  read-only
    STATUS      current
    DESCRIPTION
        "The value of tmnxSubIpoeGrpIf indicates the interface index
         of the group-interface ."
    ::= { tmnxSubIpoeEntry 4 }
    
tmnxSubIpoeSubIf OBJECT-TYPE
    SYNTAX      InterfaceIndexOrZero
    MAX-ACCESS  read-only
    STATUS      current
    DESCRIPTION
        "The value of tmnxSubIpoeSubIf indicates the interface index
         of the subscriber-interface to which this session belongs."
    ::= { tmnxSubIpoeEntry 5 }

tmnxSubIpoeUpTime OBJECT-TYPE
    SYNTAX      TimeTicks
    MAX-ACCESS  read-only
    STATUS      current
    DESCRIPTION
        "The value of tmnxSubIpoeUpTime indicates how long (in hundredths
         of a second) that the session already exists in this table."
    ::= { tmnxSubIpoeEntry 6 }

tmnxSubIpoeSessionTimeLeft OBJECT-TYPE
    SYNTAX      Unsigned32
    UNITS       "seconds"
    MAX-ACCESS  read-only
    STATUS      current
    DESCRIPTION
        "The value of tmnxSubIpoeSessionTimeLeft indicates the session
         time left when a session timeout is active for this session.
         A value of 0 indicates no session timeout is active."
    ::= { tmnxSubIpoeEntry 7 }

tmnxSubIpoeLastAuthTime OBJECT-TYPE
    SYNTAX      TimeStamp
    MAX-ACCESS  read-only
    STATUS      current
    DESCRIPTION
        "The value of tmnxSubIpoeLastAuthTime indicates the sysUpTime 
         at the time of the last authentication for this session."
    ::= { tmnxSubIpoeEntry 8 }

tmnxSubIpoeMinAuthIntervalLeft OBJECT-TYPE
    SYNTAX      Unsigned32
    UNITS       "seconds"
    MAX-ACCESS  read-only
    STATUS      current
    DESCRIPTION
        "The value of tmnxSubIpoeMinAuthIntervalLeft indicates the 
         authentication time left when a minimum authentication interval is
         active for this session.
         A value of 0 indicates no minimum authentication interval is active."
    ::= { tmnxSubIpoeEntry 9 }
    
tmnxSubIpoePersistenceKey  OBJECT-TYPE
    SYNTAX      Unsigned32
    MAX-ACCESS  read-only
    STATUS      current
    DESCRIPTION
        "The value of tmnxSubIpoePersistenceKey indicates a key
         value that can be used to track this session in the
         persistence file."
    ::= { tmnxSubIpoeEntry 10 }

tmnxSubIpoeSubIdent OBJECT-TYPE
    SYNTAX      TmnxSubIdentStringOrEmpty
    MAX-ACCESS  read-only
    STATUS      current
    DESCRIPTION
        "The value of tmnxSubIpoeSubIdent indicates the subscriber
         applicable for this session."
    ::= { tmnxSubIpoeEntry 11 }

tmnxSubIpoeSubProfString OBJECT-TYPE
    SYNTAX      TmnxSubProfileStringOrEmpty
    MAX-ACCESS  read-only
    STATUS      current
    DESCRIPTION
        "The value of tmnxSubIpoeSubProfString indicates the subscriber
         profile string applicable for this session."
    ::= { tmnxSubIpoeEntry 12 }

tmnxSubIpoeSlaProfString OBJECT-TYPE
    SYNTAX      TmnxSlaProfileStringOrEmpty
    MAX-ACCESS  read-only
    STATUS      current
    DESCRIPTION
        "The value of tmnxSubIpoeSlaProfString indicates the SLA profile
         string applicable for this session."
    ::= { tmnxSubIpoeEntry 13 }

tmnxSubIpoeAncpString OBJECT-TYPE
    SYNTAX      TmnxAncpStringOrZero
    MAX-ACCESS  read-only
    STATUS      current
    DESCRIPTION
        "The value of tmnxSubIpoeAncpString indicates the ANCP string
         applicable for this session."
    ::= { tmnxSubIpoeEntry 14 }

tmnxSubIpoeInterDestId OBJECT-TYPE
    SYNTAX      TmnxSubMgtIntDestIdOrEmpty
    MAX-ACCESS  read-only
    STATUS      current
    DESCRIPTION
        "The value of tmnxSubIpoeInterDestId indicates the intermediate
         destination identifier applicable for this session."
    ::= { tmnxSubIpoeEntry 15 }

tmnxSubIpoeAppProfString OBJECT-TYPE
    SYNTAX      TmnxAppProfileStringOrEmpty
    MAX-ACCESS  read-only
    STATUS      current
    DESCRIPTION
        "The value of tmnxSubIpoeAppProfString indicates the application
         profile string applicable for this session."
    ::= { tmnxSubIpoeEntry 16 }

tmnxSubIpoeCategoryMapName OBJECT-TYPE
    SYNTAX      TNamedItemOrEmpty
    MAX-ACCESS  read-only
    STATUS      current
    DESCRIPTION
        "The value of tmnxSubIpoeCategoryMapName indicates the
         category map name applicable for this session."
    ::= { tmnxSubIpoeEntry 17 }

tmnxSubIpoeAcctSessionId OBJECT-TYPE
    SYNTAX      TmnxSubAcctSessionId
    MAX-ACCESS  read-only
    STATUS      current
    DESCRIPTION     
        "The value of tmnxSubIpoeAcctSessionId indicates
         the accounting session id of the IPoE session."
    ::= { tmnxSubIpoeEntry 18 }

tmnxSubIpoeSapSessionIndex OBJECT-TYPE
    SYNTAX      Unsigned32
    MAX-ACCESS  read-only
    STATUS      current
    DESCRIPTION     
        "The value of tmnxSubIpoeSapSessionIndex indicates the 
         sap session index of the IPoE session."
    ::= { tmnxSubIpoeEntry 19 }
    
tmnxSubIpoeIpAddrType OBJECT-TYPE
    SYNTAX      InetAddressType
    MAX-ACCESS  read-only
    STATUS      current
    DESCRIPTION
        "The value of tmnxSubIpoeIpAddrType indicates the address type of
         tmnxSubIpoeIpAddr."
    ::= { tmnxSubIpoeEntry 20 }

tmnxSubIpoeIpAddr OBJECT-TYPE
    SYNTAX      InetAddress (SIZE (0|4))
    MAX-ACCESS  read-only
    STATUS      current
    DESCRIPTION
        "The value of tmnxSubIpoeIpAddr indicates the IP address of the
         session.

         The value of tmnxSubIpoeOriginIp indicates from what source this
         IP address was received."
    ::= { tmnxSubIpoeEntry 21 }

tmnxSubIpoeIpAddrPrefixLength OBJECT-TYPE
    SYNTAX      InetAddressPrefixLength
    MAX-ACCESS  read-only
    STATUS      current
    DESCRIPTION
        "The value of tmnxSubIpoeIpAddrPrefixLength indicates 
         the prefix length of tmnxSubIpoeIpAddr."
    ::= { tmnxSubIpoeEntry 22 }

tmnxSubIpoeOriginIp OBJECT-TYPE
    SYNTAX      DhcpLseStateInfoOrigin
    MAX-ACCESS  read-only
    STATUS      current
    DESCRIPTION
        "The value of tmnxSubIpoeOriginIp indicates which source
         provided the IP address."
    ::= { tmnxSubIpoeEntry 23 }

tmnxSubIpoePrimaryDnsType OBJECT-TYPE
    SYNTAX      InetAddressType
    MAX-ACCESS  read-only
    STATUS      current
    DESCRIPTION
        "The value of tmnxSubIpoePrimaryDnsType indicates the address
         type of tmnxSubIpoePrimaryDns."
    ::= { tmnxSubIpoeEntry 24 }

tmnxSubIpoePrimaryDns OBJECT-TYPE
    SYNTAX      InetAddress (SIZE (0|4))
    MAX-ACCESS  read-only
    STATUS      current
    DESCRIPTION
        "The value of tmnxSubIpoePrimaryDns indicates the primary DNS
         server.

         The value of this object is ''H when not applicable."
    ::= { tmnxSubIpoeEntry 25 }

tmnxSubIpoeSecondaryDnsType OBJECT-TYPE
    SYNTAX      InetAddressType
    MAX-ACCESS  read-only
    STATUS      current
    DESCRIPTION
        "The value of tmnxSubIpoeSecondaryDnsType indicates the address
         type of tmnxSubIpoeSecondaryDns."
    ::= { tmnxSubIpoeEntry 26 }

tmnxSubIpoeSecondaryDns OBJECT-TYPE
    SYNTAX      InetAddress (SIZE (0|4))
    MAX-ACCESS  read-only
    STATUS      current
    DESCRIPTION
        "The value of tmnxSubIpoeSecondaryDns indicates the secondary DNS
         server.

         The value of this object is ''H when not applicable."
    ::= { tmnxSubIpoeEntry 27 }

tmnxSubIpoePrimaryNbnsType OBJECT-TYPE
    SYNTAX      InetAddressType
    MAX-ACCESS  read-only
    STATUS      current
    DESCRIPTION
        "The value of tmnxSubIpoePrimaryNbnsType indicates the address
         type of tmnxSubIpoePrimaryNbns."
    ::= { tmnxSubIpoeEntry 28 }

tmnxSubIpoePrimaryNbns OBJECT-TYPE
    SYNTAX      InetAddress (SIZE (0|4))
    MAX-ACCESS  read-only
    STATUS      current
    DESCRIPTION
        "The value of tmnxSubIpoePrimaryNbns indicates the primary NBNS
         server.

         The value of this object is ''H when not applicable."
    ::= { tmnxSubIpoeEntry 29 }

tmnxSubIpoeSecondaryNbnsType OBJECT-TYPE
    SYNTAX      InetAddressType
    MAX-ACCESS  read-only
    STATUS      current
    DESCRIPTION
        "The value of tmnxSubIpoeSecondaryNbnsType indicates the address
         type of tmnxSubIpoeSecondaryNbns."
    ::= { tmnxSubIpoeEntry 30 }

tmnxSubIpoeSecondaryNbns OBJECT-TYPE
    SYNTAX      InetAddress (SIZE(0|4))
    MAX-ACCESS  read-only
    STATUS      current
    DESCRIPTION
        "The value of tmnxSubIpoeSecondaryNbns indicates the secondary
         NBNS server.

         The value of this object is ''H when not applicable."
    ::= { tmnxSubIpoeEntry 31 }

tmnxSubIpoeAddressPool OBJECT-TYPE
    SYNTAX      DisplayString (SIZE (0..255))
    MAX-ACCESS  read-only
    STATUS      current
    DESCRIPTION
        "The value of tmnxSubIpoeAddressPool indicates the IP address pool
         which is used to search for an IP address for this session."
    ::= { tmnxSubIpoeEntry 32 }   

tmnxSubIpoeIpv6PrefixType OBJECT-TYPE
    SYNTAX      InetAddressType
    MAX-ACCESS  read-only
    STATUS      current
    DESCRIPTION
        "The value of tmnxSubIpoeIpv6PrefixType indicates the address
         type of tmnxSubIpoeIpv6Prefix."
    ::= { tmnxSubIpoeEntry 33 }

tmnxSubIpoeIpv6Prefix OBJECT-TYPE
    SYNTAX      InetAddress (SIZE (0|16))
    MAX-ACCESS  read-only
    STATUS      current
    DESCRIPTION
        "The value of tmnxSubPppIpv6Prefix indicates the IPv6 prefix.

         The value of this object is ''H when not applicable."
    ::= { tmnxSubIpoeEntry 34 }
    
tmnxSubIpoeIpv6PrefixLen OBJECT-TYPE
    SYNTAX      InetAddressPrefixLength (0..128)
    MAX-ACCESS  read-only
    STATUS      current
    DESCRIPTION 
        "The value of tmnxSubIpoeIpv6PrefixLen indicates
         the length of tmnxSubIpoeIpv6Prefix."
    ::= { tmnxSubIpoeEntry 35 }  
    
tmnxSubIpoeIpv6PrefixOrigin OBJECT-TYPE
    SYNTAX      DhcpLseStateInfoOrigin
    MAX-ACCESS  read-only
    STATUS      current
    DESCRIPTION 
        "The value of tmnxSubIpoeIpv6PrefixOrigin indicates
         the origin of tmnxSubIpoeIpv6Prefix."
    ::= { tmnxSubIpoeEntry 36 }

tmnxSubIpoeIpv6PrefixPool OBJECT-TYPE
    SYNTAX      TNamedItemOrEmpty
    MAX-ACCESS  read-only
    STATUS      current
    DESCRIPTION 
        "The value of tmnxSubIpoeIpv6PrefixPool indicates
         the DHCP server pool from which the SLAAC prefix,
         indicated by tmnxSubIpoeIpv6Prefix, is allocated."
    ::= { tmnxSubIpoeEntry 37 }  

tmnxSubIpoeIpv6DelPfxType OBJECT-TYPE
    SYNTAX      InetAddressType
    MAX-ACCESS  read-only
    STATUS      current
    DESCRIPTION
        "The value of tmnxSubIpoeIpv6DelPfxType indicates the address
         type of tmnxSubIpoeIpv6DelPfx."
    ::= { tmnxSubIpoeEntry 38 }

tmnxSubIpoeIpv6DelPfx OBJECT-TYPE
    SYNTAX      InetAddress (SIZE (0|16))
    MAX-ACCESS  read-only
    STATUS      current
    DESCRIPTION
        "The value of tmnxSubIpoeIpv6DelPfx indicates the IPv6
         Delegated Prefix.

         The value of this object is ''H when not applicable."
    ::= { tmnxSubIpoeEntry 39 }

tmnxSubIpoeIpv6DelPfxLen OBJECT-TYPE
    SYNTAX      InetAddressPrefixLength (0..128)
    MAX-ACCESS  read-only
    STATUS      current
    DESCRIPTION 
        "The value of tmnxSubIpoeIpv6DelPfxLen indicates
         the length of tmnxSubIpoeIpv6DelPfx."
    ::= { tmnxSubIpoeEntry 40 }

tmnxSubIpoeIpv6DelPfxOrigin OBJECT-TYPE
    SYNTAX      DhcpLseStateInfoOrigin
    MAX-ACCESS  read-only
    STATUS      current
    DESCRIPTION 
        "The value of tmnxSubIpoeIpv6DelPfxOrigin indicates
         the origin of tmnxSubIpoeIpv6DelPfx and tmnxSubIpoeIpv6DelPfxLen."
    ::= { tmnxSubIpoeEntry 41 }
  
tmnxSubIpoeIpv6DelPfxPool OBJECT-TYPE
    SYNTAX      TNamedItemOrEmpty
    MAX-ACCESS  read-only
    STATUS      current
    DESCRIPTION 
        "The value of tmnxSubIpoeIpv6DelPfxPool indicates
         the DHCP server pool from which the delegated prefix,
         indicated by tmnxSubIpoeIpv6DelPfx, is allocated."
    ::= { tmnxSubIpoeEntry 42 }

tmnxSubIpoeIpv6AddrType OBJECT-TYPE
    SYNTAX      InetAddressType
    MAX-ACCESS  read-only
    STATUS      current
    DESCRIPTION
        "The value of tmnxSubIpoeIpv6AddrType indicates the address
         type of tmnxSubIpoeIpv6Addr."
    ::= { tmnxSubIpoeEntry 43 }

tmnxSubIpoeIpv6Addr OBJECT-TYPE
    SYNTAX      InetAddress (SIZE (0|16))
    MAX-ACCESS  read-only
    STATUS      current
    DESCRIPTION
        "The value of tmnxSubIpoeIpv6Addr indicates the IPv6
         address.

         The value of this object is ''H when not applicable."
    ::= { tmnxSubIpoeEntry 44 }

tmnxSubIpoeIpv6AddrOrigin OBJECT-TYPE
    SYNTAX      DhcpLseStateInfoOrigin
    MAX-ACCESS  read-only
    STATUS      current
    DESCRIPTION 
        "The value of tmnxSubIpoeIpv6AddrOrigin indicates
         the origin of tmnxSubIpoeIpv6Addr."
    ::= { tmnxSubIpoeEntry 45 }

tmnxSubIpoeIpv6AddrPool OBJECT-TYPE
    SYNTAX      TNamedItemOrEmpty
    MAX-ACCESS  read-only
    STATUS      current
    DESCRIPTION 
        "The value of tmnxSubIpoeIpv6AddrPool indicates
         the DHCP server pool from which the address,
         indicated by tmnxSubIpoeIpv6Addr, is allocated."
    ::= { tmnxSubIpoeEntry 46 }

tmnxSubIpoeIpv6Dns1Type OBJECT-TYPE
    SYNTAX      InetAddressType
    MAX-ACCESS  read-only
    STATUS      current
    DESCRIPTION
        "The value of tmnxSubIpoeIpv6Dns1Type indicates the address
         type of tmnxSubIpoeIpv6Dns1."
    ::= { tmnxSubIpoeEntry 47 }

tmnxSubIpoeIpv6Dns1 OBJECT-TYPE
    SYNTAX      InetAddress (SIZE (0|16))
    MAX-ACCESS  read-only
    STATUS      current
    DESCRIPTION
        "The value of tmnxSubIpoeIpv6Dns1 indicates the primary DNS
         server."
    ::= { tmnxSubIpoeEntry 48 }

tmnxSubIpoeIpv6Dns2Type OBJECT-TYPE
    SYNTAX      InetAddressType
    MAX-ACCESS  read-only
    STATUS      current
    DESCRIPTION
        "The value of tmnxSubIpoeIpv6Dns2Type indicates the address
         type of tmnxSubIpoeIpv6Dns2."
    ::= { tmnxSubIpoeEntry 49 }

tmnxSubIpoeIpv6Dns2 OBJECT-TYPE
    SYNTAX      InetAddress (SIZE (0|16))
    MAX-ACCESS  read-only
    STATUS      current
    DESCRIPTION
        "The value of tmnxSubIpoeIpv6Dns2 indicates the secondary DNS
         server."
    ::= { tmnxSubIpoeEntry 50 }

tmnxSubIpoeSessionTimeout OBJECT-TYPE
    SYNTAX      Unsigned32 (0..65535)
    UNITS       "seconds"
    MAX-ACCESS  read-only
    STATUS      current
    DESCRIPTION
        "The value of tmnxSubIpoeSessionTimeout indicates the session
         timeout received from the Radius server (if applicable)."
    ::= { tmnxSubIpoeEntry 51 }

tmnxSubIpoeRadiusClassAttr OBJECT-TYPE
    SYNTAX      OCTET STRING (SIZE (0..253))
    MAX-ACCESS  read-only
    STATUS      current
    DESCRIPTION
        "The value of tmnxSubIpoeRadiusClassAttr indicates the Class
         attribute returned by the RADIUS server in an Access-Accept message.
         
         If no RADIUS authentication is performed for this session, or RADIUS
         did not return this attribute, the value of this object is empty."
    ::= { tmnxSubIpoeEntry 52 }

tmnxSubIpoeRadiusUserName OBJECT-TYPE
    SYNTAX      DisplayString (SIZE (0..253))
    MAX-ACCESS  read-only
    STATUS      current
    DESCRIPTION
        "The value of tmnxSubIpoeRadiusUserName indicates the User-Name
         attribute returned by the RADIUS server in an Access-Accept message.

         If RADIUS did not return this attribute, the value of this object
         is equal to the User-Name attribute sent in the original
         Access-Request message.
         
         If no RADIUS authentication is performed for this session, the value
         of this object is empty."
    ::= { tmnxSubIpoeEntry 53 }

tmnxSubIpoeRetailerSvcId OBJECT-TYPE
    SYNTAX      TmnxServId
    MAX-ACCESS  read-only
    STATUS      current
    DESCRIPTION
        "The value of tmnxSubIpoeRetailerSvcId indicates the service ID of
         the retailer service to which this session belongs."
    ::= { tmnxSubIpoeEntry 54 }

tmnxSubIpoeRetailerIf OBJECT-TYPE
    SYNTAX      InterfaceIndexOrZero
    MAX-ACCESS  read-only
    STATUS      current
    DESCRIPTION
        "The value of tmnxSubIpoeRetailerIf indicates the interface index
         of the retailer interface to which this session belongs."
    ::= { tmnxSubIpoeEntry 55 }

tmnxSubIpoeTerminationType OBJECT-TYPE
    SYNTAX      TmnxSubTerminationType
    MAX-ACCESS  read-only
    STATUS      current
    DESCRIPTION
        "The value of tmnxSubIpoeTerminationType indicates the termination type
         of this session."
    ::= { tmnxSubIpoeEntry 56 }

--
--      The Subscriber IPoE Session Table
--

tmnxSubIpoeSessionTable   OBJECT-TYPE
    SYNTAX      SEQUENCE OF TmnxSubIpoeSessionEntry
    MAX-ACCESS  not-accessible
    STATUS      current
    DESCRIPTION
       "The tmnxSubIpoeSessionTable represents the subscriber IPoE sessions
        ordered by service, SAP and MAC address."
    ::= { tmnxSubIpoeObjs 4 }

tmnxSubIpoeSessionEntry   OBJECT-TYPE
    SYNTAX      TmnxSubIpoeSessionEntry
    MAX-ACCESS  not-accessible
    STATUS      current
    DESCRIPTION
       "Each conceptual row represents an association between a subscriber
        IPoE session and a service, SAP and MAC address.

        Entries in this table are created and destroyed by the system."
    INDEX { svcId,
            sapPortId,
            sapEncapValue,
            tmnxSubIpoeSessionMacAddress,
            tmnxSubIpoeIndex
          }
    ::= { tmnxSubIpoeSessionTable 1 }

TmnxSubIpoeSessionEntry ::= 
    SEQUENCE {
        tmnxSubIpoeSessionMacAddress      MacAddress,
        tmnxSubIpoeSessionTimeStamp       TimeStamp    
    }
        
tmnxSubIpoeSessionMacAddress OBJECT-TYPE
    SYNTAX      MacAddress 
    MAX-ACCESS  not-accessible
    STATUS      current
    DESCRIPTION     
        "The value of tmnxSubIpoeSessionMacAddress specifies the MAC address
        to which this session belongs."
    ::= { tmnxSubIpoeSessionEntry 1 }

tmnxSubIpoeSessionTimeStamp OBJECT-TYPE
    SYNTAX      TimeStamp
    MAX-ACCESS  read-only
    STATUS      current
    DESCRIPTION 
        "The value of tmnxSubIpoeSessionTimeStamp indicates
         the time that this association was made."
    ::= { tmnxSubIpoeSessionEntry 2 }  

-- 
-- tmnxSubIpoeModTable
-- 

--  Augmentation of the tmnxSubIpoeTable
--  Use of AUGMENTS clause implies a one-to-one dependent relationship
--  between the base table, tmnxSubIpoeTable, and the augmenting table,
--  tmnxSubIpoeModTable. This in effect extends the tmnxSubIpoeTable
--  with additional columns. Creation (or deletion) of a row in the
--  tmnxSubIpoeTable results in the same fate for the row in the
--  tmnxSubIpoeModTable.

tmnxSubIpoeModTable OBJECT-TYPE
    SYNTAX      SEQUENCE OF TmnxSubIpoeModEntry
    MAX-ACCESS  not-accessible
    STATUS      current
    DESCRIPTION
        "The tmnxSubIpoeModTable augments the tmnxSubIpoeTable.
         The table allows the operator to modify attributes 
         of the Subscriber IPoE Session."
    ::= { tmnxSubIpoeObjs 5 }

tmnxSubIpoeModEntry OBJECT-TYPE
    SYNTAX      TmnxSubIpoeModEntry
    MAX-ACCESS  not-accessible
    STATUS      current
    DESCRIPTION
        "Each row entry contains parameters that allow to modify a
         subscriber IPoE session's attributes."
    AUGMENTS { tmnxSubIpoeEntry }
    ::= { tmnxSubIpoeModTable 1 }

TmnxSubIpoeModEntry ::=
    SEQUENCE {
        tmnxSubIpoeModSubIdent            TmnxSubIdentStringOrEmpty,
        tmnxSubIpoeModSubProfStr          TmnxSubProfileStringOrEmpty,
        tmnxSubIpoeModSlaProfStr          TmnxSlaProfileStringOrEmpty,
        tmnxSubIpoeModAncpStr             TmnxAncpStringOrZero,
        tmnxSubIpoeModInterDestId         TmnxSubMgtIntDestIdOrEmpty,
        tmnxSubIpoeModAppProfStr          TmnxAppProfileStringOrEmpty,
        tmnxSubIpoeModEvaluateState       TruthValue
    }

tmnxSubIpoeModSubIdent OBJECT-TYPE
    SYNTAX      TmnxSubIdentStringOrEmpty
    MAX-ACCESS  read-write
    STATUS      current
    DESCRIPTION
        "The value of tmnxSubIpoeModSubIdent allows to specify a new
         subscriber name for this session.

         When a SET of this object is done with a non empty string, the system
         will attempt to assign a new subscriber name.

         A SET with an empty string has no effect on the system. (NOOP).

         GETs and GETNEXTs on this variable return an empty string."
    DEFVAL { "" }
    ::= { tmnxSubIpoeModEntry 1 }

tmnxSubIpoeModSubProfStr OBJECT-TYPE
    SYNTAX      TmnxSubProfileStringOrEmpty
    MAX-ACCESS  read-write
    STATUS      current
    DESCRIPTION
        "The value of tmnxSubIpoeModSubProfStr allows to specify a new
         subscriber profile string for this session.

         When a SET of this object is done with a non empty string, the system
         will attempt to assign a new subscriber profile string.

         A SET with an empty string has no effect on the system. (NOOP).

         GETs and GETNEXTs on this variable return an empty string."
    DEFVAL { "" }
    ::= { tmnxSubIpoeModEntry 2 }

tmnxSubIpoeModSlaProfStr OBJECT-TYPE
    SYNTAX      TmnxSlaProfileStringOrEmpty
    MAX-ACCESS  read-write
    STATUS      current
    DESCRIPTION
        "The value of tmnxSubIpoeModSlaProfStr allows to specify a new
         SLA profile string for this session.

         When a SET of this object is done with a non empty string, the system
         will attempt to assign a new SLA profile string.

         A SET with an empty string has no effect on the system. (NOOP).

         GETs and GETNEXTs on this variable return an empty string."
    DEFVAL { "" }
    ::= { tmnxSubIpoeModEntry 3 }

tmnxSubIpoeModAncpStr OBJECT-TYPE
    SYNTAX      TmnxAncpStringOrZero
    MAX-ACCESS  read-write
    STATUS      current
    DESCRIPTION
        "The value of tmnxSubIpoeModAncpStr allows to specify a new
         ANCP-string for this session.

         When a SET of this object is done with a non empty string, the system
         will attempt to assign a new ANCP-string.

         A SET with an empty string has no effect on the system. (NOOP).

         GETs and GETNEXTs on this variable return an empty string."
    DEFVAL { "" }
    ::= { tmnxSubIpoeModEntry 4 }

tmnxSubIpoeModInterDestId OBJECT-TYPE
    SYNTAX      TmnxSubMgtIntDestIdOrEmpty
    MAX-ACCESS  read-write
    STATUS      current
    DESCRIPTION
        "The value of tmnxSubIpoeModInterDestId allows to specify a new
         intermediate destination id for this session.

         When a SET of this object is done with a non empty string, the system
         will attempt to assign a new intermediate destination id.

         A SET with an empty string has no effect on the system. (NOOP).

         GETs and GETNEXTs on this variable return an empty string."
    DEFVAL { "" }
    ::= { tmnxSubIpoeModEntry 5 }

tmnxSubIpoeModAppProfStr OBJECT-TYPE
    SYNTAX      TmnxAppProfileStringOrEmpty
    MAX-ACCESS  read-write
    STATUS      current
    DESCRIPTION
        "The value of tmnxSubIpoeModAppProfStr specifies a new
         application profile string for this session.

         When a SET of this object is done with a non empty string, the system
         will attempt to assign a new application profile string.

         A SET with an empty string has no effect on the system. (NOOP).

         GETs and GETNEXTs on this variable return an empty string."
    DEFVAL { "" }
    ::= { tmnxSubIpoeModEntry 6 }

tmnxSubIpoeModEvaluateState OBJECT-TYPE
    SYNTAX      TruthValue
    MAX-ACCESS  read-write
    STATUS      current
    DESCRIPTION
        "The value of tmnxSubIpoeModEvaluateState allows to cause a
         re-evaluation of the specified session.

         When this object is set to 'true', the system will perform a
         re-evaluation of the session.

         GETs and GETNEXTs on this variable return false.

         It is not possible to simultaneously request for a session
         re-evaluation, and modify any of the strings."
    DEFVAL { false }
    ::= { tmnxSubIpoeModEntry 7 }
      

--
--      The Subscriber IPoE Session BGP Peering Table
--

--  Augmentation of the tmnxSubIpoeTable
--  Use of AUGMENTS clause implies a one-to-one dependent relationship
--  between the base table, tmnxSubIpoeTable, and the augmenting table,
--  tmnxSubIpoeBgpTable. This in effect extends the tmnxSubIpoeTable
--  with additional columns. Creation (or deletion) of a row in the
--  tmnxSubIpoeTable results in the same fate for the row in the
--  tmnxSubIpoeBgpTable.

tmnxSubIpoeBgpTable OBJECT-TYPE
    SYNTAX          SEQUENCE OF TmnxSubIpoeBgpEntry
    MAX-ACCESS      not-accessible
    STATUS          current
    DESCRIPTION     
        "The tmnxSubIpoeBgpTable augments the tmnxSubIpoeTable."
    ::= { tmnxSubIpoeObjs 6 }

tmnxSubIpoeBgpEntry OBJECT-TYPE
    SYNTAX          TmnxSubIpoeBgpEntry
    MAX-ACCESS      not-accessible
    STATUS          current
    DESCRIPTION     
        "Each conceptual row contains BGP peering information about a
         Subscriber IPoE session."
    AUGMENTS { tmnxSubIpoeEntry }
    ::= { tmnxSubIpoeBgpTable 1 }

TmnxSubIpoeBgpEntry ::=
    SEQUENCE {
        tmnxSubIpoeBgpPrngPlcyName   TNamedItemOrEmpty,
        tmnxSubIpoeBgpAuthKeyChain   TNamedItemOrEmpty,
        tmnxSubIpoeBgpMD5AuthKey     OCTET STRING,
        tmnxSubIpoeBgpImportPolicy   TPolicyStatementNameOrEmpty,
        tmnxSubIpoeBgpExportPolicy   TPolicyStatementNameOrEmpty,
        tmnxSubIpoeBgpPeerAS         InetAutonomousSystemNumber,
        tmnxSubIpoeBgpPeeringStatus  BgpPeeringStatus
    }

tmnxSubIpoeBgpPrngPlcyName OBJECT-TYPE
    SYNTAX          TNamedItemOrEmpty
    MAX-ACCESS      read-only
    STATUS          current
    DESCRIPTION
        "The value of tmnxSubIpoeBgpPrngPlcyName indicates the
         peering policy which is used to set up the BGP peer for this
         session."
    ::= { tmnxSubIpoeBgpEntry 1 }

tmnxSubIpoeBgpAuthKeyChain OBJECT-TYPE
    SYNTAX          TNamedItemOrEmpty
    MAX-ACCESS      read-only
    STATUS          current
    DESCRIPTION
        "The value of tmnxSubIpoeBgpAuthKeyChain indicates the
         keychain which is used to sign and/or authenticate the BGP
         protocol stream."
    ::= { tmnxSubIpoeBgpEntry 2 }

tmnxSubIpoeBgpMD5AuthKey OBJECT-TYPE
    SYNTAX          OCTET STRING (SIZE(0..255))
    MAX-ACCESS      read-only
    STATUS          current
    DESCRIPTION     
        "The value of tmnxSubIpoeBgpMD5AuthKey indicates the 
         authentication key used between BGP peers neighbors before
         establishing sessions. Authentication is done using the
         MD-5 message based digest protocol."
    ::= { tmnxSubIpoeBgpEntry 3 }

tmnxSubIpoeBgpImportPolicy OBJECT-TYPE
    SYNTAX          TPolicyStatementNameOrEmpty
    MAX-ACCESS      read-only
    STATUS          current
    DESCRIPTION     
        "The value of tmnxSubIpoeBgpImportPolicy indicates 
         the import policy."
    ::= { tmnxSubIpoeBgpEntry 4 }

tmnxSubIpoeBgpExportPolicy OBJECT-TYPE
    SYNTAX          TPolicyStatementNameOrEmpty
    MAX-ACCESS      read-only
    STATUS          current
    DESCRIPTION     
        "The value of tmnxSubIpoeBgpExportPolicy indicates 
         the export policy."
    ::= { tmnxSubIpoeBgpEntry 5 }

tmnxSubIpoeBgpPeerAS OBJECT-TYPE
    SYNTAX          InetAutonomousSystemNumber
    MAX-ACCESS      read-only
    STATUS          current
    DESCRIPTION     
        "The value of tmnxSubIpoeBgpPeerAS indicates the Autonomous System
         number for the remote peer."
    ::= { tmnxSubIpoeBgpEntry 6 }

tmnxSubIpoeBgpPeeringStatus OBJECT-TYPE
    SYNTAX          BgpPeeringStatus
    MAX-ACCESS      read-only
    STATUS          current
    DESCRIPTION
        "The value of tmnxSubIpoeBgpPeeringStatus indicates
         the status of the BGP peering session."
    ::= { tmnxSubIpoeBgpEntry 7 }

--
--      The Subscriber IPoE Session Overrides Table
--

tmnxSubIpoeOvrTable   OBJECT-TYPE
    SYNTAX      SEQUENCE OF TmnxSubIpoeOvrEntry
    MAX-ACCESS  not-accessible
    STATUS      current
    DESCRIPTION
       "The tmnxSubIpoeOvrTable contains QoS (Quality of Service) overrides for 
        Subscriber IPoE Sessions.

        Entries in this table are created and destroyed by the system."
        ::= { tmnxSubIpoeObjs 7 }

tmnxSubIpoeOvrEntry   OBJECT-TYPE
    SYNTAX      TmnxSubIpoeOvrEntry
    MAX-ACCESS  not-accessible
    STATUS      current
    DESCRIPTION
       "Each conceptual row represents QoS overrides information
        of a Subscriber IPoE Session."
    INDEX { tmnxSubIpoeIndex,
            tmnxSubIpoeOvrDirection,
            tmnxSubIpoeOvrType,
            tmnxSubIpoeOvrTypeId,
            tmnxSubIpoeOvrTypeName }
    ::= { tmnxSubIpoeOvrTable 1 }

TmnxSubIpoeOvrEntry ::= 
    SEQUENCE {
        tmnxSubIpoeOvrDirection         TDirectionIngEgr,
        tmnxSubIpoeOvrType              TQosOverrideType,
        tmnxSubIpoeOvrTypeId            Integer32,
        tmnxSubIpoeOvrTypeName          TNamedItemOrEmpty,
        tmnxSubIpoeOvrCBS               TBurstSizeBytesOvr,
        tmnxSubIpoeOvrMBS               TBurstSizeBytesOvr,
        tmnxSubIpoeOvrWrrWeight         THsmdaWrrWeightOverride,
        tmnxSubIpoeOvrPIRHi             Unsigned32,
        tmnxSubIpoeOvrPIRLo             Unsigned32,
        tmnxSubIpoeOvrCIRHi             Unsigned32,
        tmnxSubIpoeOvrCIRLo             Unsigned32,
        tmnxSubIpoeOvrSummedCIR         TruthValue
    }
        
tmnxSubIpoeOvrDirection OBJECT-TYPE
    SYNTAX          TDirectionIngEgr
    MAX-ACCESS      not-accessible
    STATUS          current
    DESCRIPTION
        "The value of tmnxSubIpoeOvrDirection indicates if
         this row specifies ingress or egress qos override 
         parameters."
    ::= { tmnxSubIpoeOvrEntry 1 }

tmnxSubIpoeOvrType OBJECT-TYPE
    SYNTAX          TQosOverrideType
    MAX-ACCESS      not-accessible
    STATUS          current
    DESCRIPTION
        "The value of tmnxSubIpoeOvrType indicates what field
         has been overridden by this row."
    ::= { tmnxSubIpoeOvrEntry 2 }

tmnxSubIpoeOvrTypeId OBJECT-TYPE
    SYNTAX          Integer32
    MAX-ACCESS      not-accessible
    STATUS          current
    DESCRIPTION
        "The value of tmnxSubIpoeOvrTypeId indicates the ID of
         the queue/policer that has been overridden by this row.
       
         If the value of tmnxSubIpoeOvrType is not 'queue (1)'
         or 'policer (2)', this field must be set to zero (0)."
    ::= { tmnxSubIpoeOvrEntry 3 }

tmnxSubIpoeOvrTypeName OBJECT-TYPE
    SYNTAX          TNamedItemOrEmpty
    MAX-ACCESS      not-accessible
    STATUS          current
    DESCRIPTION
        "The value of tmnxSubIpoeOvrTypeName indicates the
         name of the scheduler/arbiter that has been overridden by
         this row.

         If the value of tmnxSubIpoeOvrType is not 
         'arbiter (4)' or 'scheduler (5)', this field must be set to
         zero (0)."
    ::= { tmnxSubIpoeOvrEntry 4 }

tmnxSubIpoeOvrCBS OBJECT-TYPE
    SYNTAX          TBurstSizeBytesOvr
    MAX-ACCESS      read-only
    STATUS          current
    DESCRIPTION
        "The value of tmnxSubIpoeOvrCBS indicates the amount of
         reserved buffer space (in bytes) for the object
         overridden by this row."
    ::= { tmnxSubIpoeOvrEntry 5 }

tmnxSubIpoeOvrMBS OBJECT-TYPE
    SYNTAX          TBurstSizeBytesOvr
    MAX-ACCESS      read-only
    STATUS          current
    DESCRIPTION
        "The value of tmnxSubIpoeOvrMBS indicates the maximum
         amount of reserved buffer space (in bytes) for the object
         overridden by this row."
    ::= { tmnxSubIpoeOvrEntry 6 }

tmnxSubIpoeOvrWrrWeight OBJECT-TYPE
    SYNTAX          THsmdaWrrWeightOverride
    MAX-ACCESS      read-only
    STATUS          current
    DESCRIPTION     
        "The value of tmnxSubIpoeOvrWrrWeight specifies the weight of this 
         queue for the HSMDA scheduler.
     
         The weight determines how much bandwidth this queue gets out of the 
         total rate for the scheduling class.
     
         The value of tmnxSubIpoeOvrWrrWeight is only relevant if the value of
         tmnxSubIpoeOvrType is equal to 'queue', and if the queue specified in
         tmnxSubIpoeOvrTypeId is referenced in the value of 
         TIMETRA-QOS-MIB::tHsmdaWrrPolicyIncludeQueues of the Weighted Round
         Robin policy associated wit this IPoE session."
    ::= { tmnxSubIpoeOvrEntry 7 }

tmnxSubIpoeOvrPIRHi OBJECT-TYPE
    SYNTAX       Unsigned32 (0 | 4294967295)
    UNITS        "kbps"
    MAX-ACCESS   read-only
    STATUS       current
    DESCRIPTION
        "The value of tmnxSubIpoeOvrPIRHi indicates upper 32 bits of the PIR rate
         allowed for the object overwritten by this row.    

         When the value of tmnxSubIpoeOvrPIRHi along with the value of 
         tmnxSubIpoeOvrPIRLo is equal to 4294967295 (0xFFFFFFFF), rate for this
         scheduler indicates maximum rate.

         The value of tmnxSubIpoeOvrPIRHi equal to 4294967295 (0xFFFFFFFF) and 
         the value of tmnxSubIpoeOvrPIRLo equal to 4294967294 (0xFFFFFFFE) 
         indicates no overrides."
    ::= { tmnxSubIpoeOvrEntry 8 }

tmnxSubIpoeOvrPIRLo OBJECT-TYPE
    SYNTAX       Unsigned32 (1..3200000000 | 4294967294 | 4294967295)
    UNITS        "kbps"
    MAX-ACCESS   read-only
    STATUS       current
    DESCRIPTION
        "The value of tmnxSubIpoeOvrPIRHi indicates lower 32 bits of the PIR rate
         allowed for the object overwritten by this row.    
    
         When the value of tmnxSubIpoeOvrPIRHi along with the value of 
         tmnxSubIpoeOvrPIRLo is equal to 4294967295 (0xFFFFFFFF), rate for
         this scheduler indicates maximum rate.
    
         The value of tmnxSubIpoeOvrPIRHi equal to 4294967295 (0xFFFFFFFF) and 
         the value of tmnxSubIpoeOvrPIRLo equal to 4294967294 (0xFFFFFFFE) 
         indicates no overrides."
    ::= { tmnxSubIpoeOvrEntry 9 }

tmnxSubIpoeOvrCIRHi OBJECT-TYPE
    SYNTAX       Unsigned32 (0 | 4294967295)
    UNITS        "kbps"
    MAX-ACCESS   read-only
    STATUS       current
    DESCRIPTION
        "The value of tmnxSubIpoeOvrCIRHi indicates upper 32 bits of the CIR rate
         allowed for the object overwritten by this row.    

         When the value of tmnxSubIpoeOvrCIRHi along with the value of 
         tmnxSubIpoeOvrCIRLo is equal to 4294967295 (0xFFFFFFFF), rate for
         this scheduler indicates maximum rate.

         The value of tmnxSubIpoeOvrCIRHi equal to 4294967295 (0xFFFFFFFF) and 
         the value of tmnxSubIpoeOvrCIRLo equal to 4294967294 (0xFFFFFFFE) 
         indicates no overrides."
    ::= { tmnxSubIpoeOvrEntry 10 }

tmnxSubIpoeOvrCIRLo OBJECT-TYPE
    SYNTAX       Unsigned32 (0..3200000000 | 4294967294 | 4294967295)
    UNITS        "kbps"
    MAX-ACCESS   read-only
    STATUS       current
    DESCRIPTION
        "The value of tmnxSubIpoeOvrCIRHi indicates lower 32 bits of the CIR rate
         allowed for the object overwritten by this row.    
    
         When the value of tmnxSubIpoeOvrCIRHi along with the value of 
         tmnxSubIpoeOvrCIRLo is equal to 4294967295 (0xFFFFFFFF), rate for
         this scheduler indicates maximum rate.
    
         The value of tmnxSubIpoeOvrCIRHi equal to 4294967295 (0xFFFFFFFF) and 
         the value of tmnxSubIpoeOvrCIRLo equal to 4294967294 (0xFFFFFFFE) 
         indicates no overrides."
    ::= { tmnxSubIpoeOvrEntry 11 }

tmnxSubIpoeOvrSummedCIR OBJECT-TYPE
    SYNTAX      TruthValue
    MAX-ACCESS  read-only
    STATUS      current
    DESCRIPTION
        "The value of tmnxSubIpoeOvrSummedCIR specifies if the CIR should
         be used as the summed CIR values of the children schedulers or queues.
         If set to 'true', the applicable scheduler CIR (tmnxSubIpoeOvrCIRHi and
         tmnxSubIpoeOvrCIRLo) loses its meaning.

         The value of tmnxSubIpoeOvrCIRHi equal to 4294967295 (0xFFFFFFFF) and 
         the value of tmnxSubIpoeOvrCIRLo equal to 4294967294 (0xFFFFFFFE) 
         indicates no overrides."
    ::= { tmnxSubIpoeOvrEntry 12 }


--
--      The Subscriber IPoE Session Managed Route Table
--

tmnxSubIpoeMRtTable   OBJECT-TYPE
    SYNTAX      SEQUENCE OF TmnxSubIpoeMRtEntry
    MAX-ACCESS  not-accessible
    STATUS      current
    DESCRIPTION
       "The tmnxSubIpoeMRtTable contains managed routes  
        for Subscriber IPoE Sessions.

        Entries in this table are created and destroyed by the system."
    ::= { tmnxSubIpoeObjs 8 }

tmnxSubIpoeMRtEntry   OBJECT-TYPE
    SYNTAX      TmnxSubIpoeMRtEntry
    MAX-ACCESS  not-accessible
    STATUS      current
    DESCRIPTION
       "Each conceptual row represents a managed route
        of a Subscriber IPoE Session."
    INDEX { tmnxSubIpoeIndex,
            tmnxSubIpoeMRtAddrType,
            tmnxSubIpoeMRtAddr,
            tmnxSubIpoeMRtPrefixLen }
    ::= { tmnxSubIpoeMRtTable 1 }

TmnxSubIpoeMRtEntry ::= 
    SEQUENCE {
        tmnxSubIpoeMRtAddrType          InetAddressType,
        tmnxSubIpoeMRtAddr              InetAddress,
        tmnxSubIpoeMRtPrefixLen         InetAddressPrefixLength,
        tmnxSubIpoeMRtStatus            TmnxManagedRouteStatus,
        tmnxSubIpoeMRtMetric            TmnxRadiusFramedRouteMetric,
        tmnxSubIpoeMRtPreference        TmnxRadiusFramedRoutePreference,
        tmnxSubIpoeMRtTag               TmnxRadiusFramedRouteTag             
    }
        
tmnxSubIpoeMRtAddrType OBJECT-TYPE
    SYNTAX          InetAddressType
    MAX-ACCESS      not-accessible
    STATUS          current
    DESCRIPTION
        "The value of tmnxSubIpoeMRtAddrType indicates
         the address type of tmnxSubIpoeMRtAddr."
    ::= { tmnxSubIpoeMRtEntry 1 }

tmnxSubIpoeMRtAddr OBJECT-TYPE
    SYNTAX          InetAddress (SIZE(4|16))
    MAX-ACCESS      not-accessible
    STATUS          current
    DESCRIPTION
        "The value of tmnxSubIpoeMRtAddr indicates
         the IP address of the managed route."
    ::= { tmnxSubIpoeMRtEntry 2 }

tmnxSubIpoeMRtPrefixLen OBJECT-TYPE
    SYNTAX          InetAddressPrefixLength
    MAX-ACCESS      not-accessible
    STATUS          current
    DESCRIPTION
        "The value of tmnxSubIpoeMRtPrefixLen indicates
         the prefix length of the subnet associated with
         tmnxSubIpoeMRtAddr."
    ::= { tmnxSubIpoeMRtEntry 3 }

tmnxSubIpoeMRtStatus OBJECT-TYPE
    SYNTAX          TmnxManagedRouteStatus
    MAX-ACCESS      read-only
    STATUS          current
    DESCRIPTION
        "The value of tmnxSubIpoeMRtStatus indicates
         the state of this managed route."
    ::= { tmnxSubIpoeMRtEntry 4 }

tmnxSubIpoeMRtMetric OBJECT-TYPE
    SYNTAX          TmnxRadiusFramedRouteMetric
    MAX-ACCESS      read-only
    STATUS          current
    DESCRIPTION
        "The value of tmnxSubIpoeMRtMetric indicates
         the metric of this managed route as specified
         in the RADIUS option 22 Framed-Route or 
         option 99 Framed-IPv6-Route."
    ::= { tmnxSubIpoeMRtEntry 5 }

tmnxSubIpoeMRtPreference OBJECT-TYPE
    SYNTAX          TmnxRadiusFramedRoutePreference
    MAX-ACCESS      read-only
    STATUS          current
    DESCRIPTION
        "The value of tmnxSubIpoeMRtPreference indicates
         the preference of this managed route as specified
         in the RADIUS option 22 Framed-Route or 
         option 99 Framed-IPv6-Route."
    ::= { tmnxSubIpoeMRtEntry 6 }

tmnxSubIpoeMRtTag OBJECT-TYPE
    SYNTAX          TmnxRadiusFramedRouteTag
    MAX-ACCESS      read-only
    STATUS          current
    DESCRIPTION
        "The value of tmnxSubIpoeMRtTag indicates
         the tag of this managed route as specified
         in the RADIUS option 22 Framed-Route or 
         option 99 Framed-IPv6-Route."
    ::= { tmnxSubIpoeMRtEntry 7 }

--
--      The Subscriber IPoE Session BGP IPv6 Peering Table
--
tmnxSubIpoeBgpIpv6Table OBJECT-TYPE
    SYNTAX          SEQUENCE OF TmnxSubIpoeBgpIpv6Entry
    MAX-ACCESS      not-accessible
    STATUS          current
    DESCRIPTION      
        "The tmnxSubIpoeBgpIpv6Table augments the tmnxSubIpoeTable."
    ::= { tmnxSubIpoeObjs 9 }

tmnxSubIpoeBgpIpv6Entry OBJECT-TYPE
    SYNTAX          TmnxSubIpoeBgpIpv6Entry
    MAX-ACCESS      not-accessible
    STATUS          current
    DESCRIPTION     
        "Each conceptual row contains BGP IPv6 peering information about a
         Subscriber IPoE session."
    AUGMENTS { tmnxSubIpoeEntry }
    ::= { tmnxSubIpoeBgpIpv6Table 1 }

TmnxSubIpoeBgpIpv6Entry ::=
    SEQUENCE {
        tmnxSubIpoeBgpIpv6PrngPlcyName   TNamedItemOrEmpty,
        tmnxSubIpoeBgpIpv6AuthKeyChain   TNamedItemOrEmpty,
        tmnxSubIpoeBgpIpv6MD5AuthKey     OCTET STRING,
        tmnxSubIpoeBgpIpv6ImportPolicy   TPolicyStatementNameOrEmpty,
        tmnxSubIpoeBgpIpv6ExportPolicy   TPolicyStatementNameOrEmpty,
        tmnxSubIpoeBgpIpv6PeerAS         InetAutonomousSystemNumber
    }

tmnxSubIpoeBgpIpv6PrngPlcyName OBJECT-TYPE
    SYNTAX          TNamedItemOrEmpty
    MAX-ACCESS      read-only
    STATUS          current
    DESCRIPTION
        "The value of the object tmnxSubIpoeBgpIpv6PrngPlcyName indicates
         the peering policy which is used to set up the BGP IPv6 peer for
         this session."
    ::= { tmnxSubIpoeBgpIpv6Entry 1 }

tmnxSubIpoeBgpIpv6AuthKeyChain OBJECT-TYPE
    SYNTAX          TNamedItemOrEmpty
    MAX-ACCESS      read-only
    STATUS          current
    DESCRIPTION
        "The value of the object tmnxSubIpoeBgpIpv6AuthKeyChain indicates 
         the keychain which is used to sign and/or authenticate the 
         BGP IPv6 protocol stream."
    ::= { tmnxSubIpoeBgpIpv6Entry 2 }

tmnxSubIpoeBgpIpv6MD5AuthKey OBJECT-TYPE
    SYNTAX          OCTET STRING (SIZE(0..255))
    MAX-ACCESS      read-only
    STATUS          current
    DESCRIPTION     
        "The value of the object tmnxSubIpoeBgpIpv6MD5AuthKey indicates  
         the authentication key used between BGP IPv6 peers neighbors 
         before establishing sessions. 
         Authentication is done using the MD-5 message based digest
         protocol."
    ::= { tmnxSubIpoeBgpIpv6Entry 3 }

tmnxSubIpoeBgpIpv6ImportPolicy OBJECT-TYPE
    SYNTAX          TPolicyStatementNameOrEmpty
    MAX-ACCESS      read-only
    STATUS          current
    DESCRIPTION     
        "The value of the object tmnxSubIpoeBgpIpv6ImportPolicy indicates 
         the IPv6 import policy."
    ::= { tmnxSubIpoeBgpIpv6Entry 4 }

tmnxSubIpoeBgpIpv6ExportPolicy OBJECT-TYPE
    SYNTAX          TPolicyStatementNameOrEmpty
    MAX-ACCESS      read-only
    STATUS          current
    DESCRIPTION     
        "The value of the object tmnxSubIpoeBgpIpv6ExportPolicy indicates  
         the IPv6 export policy."
    ::= { tmnxSubIpoeBgpIpv6Entry 5 }

tmnxSubIpoeBgpIpv6PeerAS OBJECT-TYPE
    SYNTAX          InetAutonomousSystemNumber
    MAX-ACCESS      read-only
    STATUS          current
    DESCRIPTION     
        "The value of the object tmnxSubIpoeBgpIpv6PeerAS indicates the 
         Autonomous System number for the remote IPv6 peer."
    ::= { tmnxSubIpoeBgpIpv6Entry 6 }

--  tmnxSubIpoeRipTable
--
--  Augmentation of the tmnxSubIpoeTable
--  Use of AUGMENTS clause implies a one-to-one dependent relationship
--  between the base table, tmnxSubIpoeTable, and the augmenting table,
--  tmnxSubIpoeRipTable. This in effect extends the tmnxSubIpoeTable
--  with additional columns. Creation (or deletion) of a row in the
--  tmnxSubIpoeTable results in the same fate for the row in the
--  tmnxSubIpoeRipTable.


tmnxSubIpoeRipTable OBJECT-TYPE
    SYNTAX          SEQUENCE OF TmnxSubIpoeRipEntry
    MAX-ACCESS      not-accessible
    STATUS          current
    DESCRIPTION     
        "The tmnxSubIpoeRipTable augments the tmnxSubIpoeTable."
    ::= { tmnxSubIpoeObjs 10 }

tmnxSubIpoeRipEntry OBJECT-TYPE
    SYNTAX          TmnxSubIpoeRipEntry
    MAX-ACCESS      not-accessible
    STATUS          current
    DESCRIPTION     
        "Each conceptual row contains RIP Listener information about a
         Subscriber IPoE session."
    AUGMENTS { tmnxSubIpoeEntry }
    ::= { tmnxSubIpoeRipTable 1 }

TmnxSubIpoeRipEntry ::=
    SEQUENCE {
        tmnxSubIpoeRipPlcyName        TNamedItemOrEmpty,
        tmnxSubIpoeRipListenerStatus  TmnxRipListenerStatus
    }

tmnxSubIpoeRipPlcyName OBJECT-TYPE
    SYNTAX          TNamedItemOrEmpty
    MAX-ACCESS      read-only
    STATUS          current
    DESCRIPTION
        "The value of tmnxSubIpoeRipPlcyName indicates the
         RIP policy which is used to set up the RIP listener for this
         session."
    ::= { tmnxSubIpoeRipEntry 1 }

tmnxSubIpoeRipListenerStatus OBJECT-TYPE
    SYNTAX          TmnxRipListenerStatus
    MAX-ACCESS      read-only
    STATUS          current
    DESCRIPTION
        "The value of tmnxSubIpoeRipListenerStatus indicates
         the status of the RIP listener."
    ::= { tmnxSubIpoeRipEntry 2 }
    
    
--
-- The Subscriber RIP/RIP-NG Policy Table
--

tmnxSubRipPlcyTableLastChanged   OBJECT-TYPE
    SYNTAX      TimeStamp
    MAX-ACCESS  read-only
    STATUS      current
    DESCRIPTION
        "The value of tmnxSubRipPlcyTableLastChanged indicates the 
         sysUpTime at the time of the most recent change to the
         tmnxSubRipPlcyTable."
    ::= { tmnxSubRipObjs 1 }
    
tmnxSubRipPlcyTable              OBJECT-TYPE
    SYNTAX      SEQUENCE OF TmnxSubRipPlcyEntry
    MAX-ACCESS  not-accessible
    STATUS      current
    DESCRIPTION
        "The table tmnxSubRipPlcyTable contains the information pertaining to
         configure an RIP/RIP-NG policy in the system."
    ::= { tmnxSubRipObjs 2 }

tmnxSubRipPlcyEntry              OBJECT-TYPE
    SYNTAX      TmnxSubRipPlcyEntry
    MAX-ACCESS  not-accessible
    STATUS      current
    DESCRIPTION
        "Each row entry represents a RIP/RIP-NG policy configured in
         the system.

         Rows in table tmnxSubRipPlcyTable are created and destroyed by 
         SNMP SET operations on the object tmnxSubRipPlcyRowStatus."
    INDEX { IMPLIED tmnxSubRipPlcyName }
    ::= { tmnxSubRipPlcyTable 1 }

TmnxSubRipPlcyEntry ::= SEQUENCE {
        tmnxSubRipPlcyName               TNamedItem,
        tmnxSubRipPlcyLastChanged        TimeStamp,
        tmnxSubRipPlcyRowStatus          RowStatus,
        tmnxSubRipPlcyDescription        TItemDescription,
        tmnxSubRipPlcyAuthType           TmnxRipNgAuthType,
        tmnxSubRipPlcyAuthKey            TmnxRipNgAuthKey
    }

tmnxSubRipPlcyName               OBJECT-TYPE
    SYNTAX      TNamedItem
    MAX-ACCESS  not-accessible
    STATUS      current
    DESCRIPTION
        "The value of tmnxSubRipPlcyName specifies the name of the
         RIP/RIP-NG policy."
    ::= { tmnxSubRipPlcyEntry 1 }

tmnxSubRipPlcyLastChanged         OBJECT-TYPE
    SYNTAX      TimeStamp
    MAX-ACCESS  read-only
    STATUS      current
    DESCRIPTION
        "The value of tmnxSubRipPlcyLastChanged indicates the sysUpTime at
         the time of the last modification of this entry."
    ::= { tmnxSubRipPlcyEntry 2 }
    
tmnxSubRipPlcyRowStatus           OBJECT-TYPE
    SYNTAX      RowStatus
    MAX-ACCESS  read-create
    STATUS      current
    DESCRIPTION
        "The value of tmnxSubRipPlcyRowStatus controls the creation and
         deletion of rows in this table."
    ::= { tmnxSubRipPlcyEntry 3 }

tmnxSubRipPlcyDescription         OBJECT-TYPE
    SYNTAX      TItemDescription
    MAX-ACCESS  read-create
    STATUS      current
    DESCRIPTION
        "The value of tmnxSubRipPlcyDescription specifies the user provided
         description of this IPoE policy."
    DEFVAL { "" }
    ::= { tmnxSubRipPlcyEntry 4 }

tmnxSubRipPlcyAuthType           OBJECT-TYPE
    SYNTAX      TmnxRipNgAuthType
    MAX-ACCESS  read-create
    STATUS      current
    DESCRIPTION
       "The value of tmnxSubRipPlcyAuthType specifies the type of 
        authentication to be used."
    DEFVAL { noAuthentication }
    ::= { tmnxSubRipPlcyEntry 5 }

tmnxSubRipPlcyAuthKey            OBJECT-TYPE
    SYNTAX      TmnxRipNgAuthKey
    MAX-ACCESS  read-create
    STATUS      current
    DESCRIPTION
        "The value of tmnxSubRipPlcyAuthKey specifies the 
         authentication key that should be used when tmnxSubRipPlcyAuthType
         has a value other than noAuthentication(1);        
         modifying the value of tmnxSubRipPlcyAuthType does not modify
         the tmnxSubRipPlcyAuthKey value.
         
         If a string shorter than 16 octets is supplied, it will be
         left-justified and padded to 16 octets, on the right, with
         nulls (0x00).

         Reading this object always results in an  OCTET STRING of
         length zero; authentication may not be bypassed by reading
         the MIB object."
    DEFVAL { ''h }
    ::= { tmnxSubRipPlcyEntry 6 }

--  tmnxSubPppRipTable
--
--  Augmentation of the tmnxSubPppTable
--  Use of AUGMENTS clause implies a one-to-one dependent relationship
--  between the base table, tmnxSubPppTable, and the augmenting table,
--  tmnxSubPppRipTable. This in effect extends the tmnxSubPppTable
--  with additional columns. Creation (or deletion) of a row in the
--  tmnxSubPppTable results in the same fate for the row in the
--  tmnxSubPppRipTable.


tmnxSubPppRipTable OBJECT-TYPE
    SYNTAX          SEQUENCE OF TmnxSubPppRipEntry
    MAX-ACCESS      not-accessible
    STATUS          current
    DESCRIPTION     
        "The tmnxSubPppRipTable augments the tmnxSubPppTable."
    ::= { tmnxSubPppObjs 12 }

tmnxSubPppRipEntry OBJECT-TYPE
    SYNTAX          TmnxSubPppRipEntry
    MAX-ACCESS      not-accessible
    STATUS          current
    DESCRIPTION     
        "Each conceptual row contains RIP Listener information about a
         Subscriber PPP session."
    AUGMENTS { tmnxSubPppEntry }
    ::= { tmnxSubPppRipTable 1 }

TmnxSubPppRipEntry ::=
    SEQUENCE {
        tmnxSubPppRipPlcyName        TNamedItemOrEmpty,
        tmnxSubPppRipListenerStatus  TmnxRipListenerStatus
    }

tmnxSubPppRipPlcyName OBJECT-TYPE
    SYNTAX          TNamedItemOrEmpty
    MAX-ACCESS      read-only
    STATUS          current
    DESCRIPTION
        "The value of tmnxSubPppRipPlcyName indicates the
         RIP policy which is used to set up the RIP listener for this
         session."
    ::= { tmnxSubPppRipEntry 1 }

tmnxSubPppRipListenerStatus OBJECT-TYPE
    SYNTAX          TmnxRipListenerStatus
    MAX-ACCESS      read-only
    STATUS          current
    DESCRIPTION
        "The value of tmnxSubPppRipListenerStatus indicates
         the status of the RIP listener."
    ::= { tmnxSubPppRipEntry 2 }
    

--
--      The Subscriber PPP Session BGP IPv6 Peering Table
--
tmnxSubPppBgpIpv6Table OBJECT-TYPE
    SYNTAX          SEQUENCE OF TmnxSubPppBgpIpv6Entry
    MAX-ACCESS      not-accessible
    STATUS          current
    DESCRIPTION      
        "The tmnxSubPppBgpIpv6Table augments the tmnxSubPppTable."
    ::= { tmnxSubPppObjs 13 }

tmnxSubPppBgpIpv6Entry OBJECT-TYPE
    SYNTAX          TmnxSubPppBgpIpv6Entry
    MAX-ACCESS      not-accessible
    STATUS          current
    DESCRIPTION     
        "Each conceptual row contains BGP IPv6 peering information about a
         Subscriber PPP session."
    AUGMENTS { tmnxSubPppEntry }
    ::= { tmnxSubPppBgpIpv6Table 1 }

TmnxSubPppBgpIpv6Entry ::=
    SEQUENCE {
        tmnxSubPppBgpIpv6PrngPlcyName    TNamedItemOrEmpty,
        tmnxSubPppBgpIpv6AuthKeyChain    TNamedItemOrEmpty,
        tmnxSubPppBgpIpv6MD5AuthKey      OCTET STRING,
        tmnxSubPppBgpIpv6ImportPolicy    TPolicyStatementNameOrEmpty,
        tmnxSubPppBgpIpv6ExportPolicy    TPolicyStatementNameOrEmpty,
        tmnxSubPppBgpIpv6PeerAS          InetAutonomousSystemNumber
    }

tmnxSubPppBgpIpv6PrngPlcyName OBJECT-TYPE
    SYNTAX          TNamedItemOrEmpty
    MAX-ACCESS      read-only
    STATUS          current
    DESCRIPTION
        "The value of tmnxSubPppBgpIpv6PrngPlcyName indicates the peering
         policy which is used to set up the BGP IPv6 peer for this session."
    ::= { tmnxSubPppBgpIpv6Entry 1 }

tmnxSubPppBgpIpv6AuthKeyChain OBJECT-TYPE
    SYNTAX          TNamedItemOrEmpty
    MAX-ACCESS      read-only
    STATUS          current
    DESCRIPTION
        "The value of tmnxSubPppBgpIpv6AuthKeyChain indicates the
         keychain which is used to sign and/or authenticate the BGP IPv6
         protocol stream."
    ::= { tmnxSubPppBgpIpv6Entry 2 }

tmnxSubPppBgpIpv6MD5AuthKey OBJECT-TYPE
    SYNTAX          OCTET STRING (SIZE(0..255))
    MAX-ACCESS      read-only
    STATUS          current
    DESCRIPTION     
        "The value of tmnxSubPppBgpIpv6MD5AuthKey indicates the 
         authentication key used between BGP IPv6 peers neighbors before
         establishing sessions. Authentication is done using the
         MD-5 message based digest protocol."
    ::= { tmnxSubPppBgpIpv6Entry 3 }

tmnxSubPppBgpIpv6ImportPolicy OBJECT-TYPE
    SYNTAX          TPolicyStatementNameOrEmpty
    MAX-ACCESS      read-only
    STATUS          current
    DESCRIPTION     
        "The value of tmnxSubPppBgpIpv6ImportPolicy indicates the
         IPv6 import policy."
    ::= { tmnxSubPppBgpIpv6Entry 4 }

tmnxSubPppBgpIpv6ExportPolicy OBJECT-TYPE
    SYNTAX          TPolicyStatementNameOrEmpty
    MAX-ACCESS      read-only
    STATUS          current
    DESCRIPTION     
        "The value of tmnxSubPppBgpIpv6ExportPolicy indicates the 
         IPv6 export policy."
    ::= { tmnxSubPppBgpIpv6Entry 5 }

tmnxSubPppBgpIpv6PeerAS OBJECT-TYPE
    SYNTAX          InetAutonomousSystemNumber
    MAX-ACCESS      read-only
    STATUS          current
    DESCRIPTION     
        "The value of tmnxSubPppBgpIpv6PeerAS indicates the Autonomous
         System number for the remote IPv6 peer."
    ::= { tmnxSubPppBgpIpv6Entry 6 }

--
--  The Subscriber PIM Policy Table
--

tmnxSubPimPlcyTableLastChanged  OBJECT-TYPE
    SYNTAX      TimeStamp
    MAX-ACCESS  read-only
    STATUS      current
    DESCRIPTION
        "The value of tmnxSubPimPlcyTableLastChanged indicates the 
         sysUpTime at the time of the most recent change to the
         tmnxSubPimPlcyTable."
    ::= { tmnxSubPimObjs 1 }
    
tmnxSubPimPlcyTable OBJECT-TYPE
    SYNTAX     SEQUENCE OF TmnxSubPimPlcyEntry
    MAX-ACCESS not-accessible
    STATUS     current
    DESCRIPTION
        "The tmnxSubPimPlcyTable contains objects to configure
         the Protocol Independent Multicast (PIM) policies used
         for subscriber hosts.
         
         Conceptual rows in this table can be created and destroyed
         by SNMP operations on the object tmnxSubPimPlcyRowStatus."
    ::= { tmnxSubPimObjs 2 }

tmnxSubPimPlcyEntry OBJECT-TYPE
    SYNTAX     TmnxSubPimPlcyEntry
    MAX-ACCESS not-accessible
    STATUS     current
    DESCRIPTION
        "Each conceptual row in the tmnxSubPimPlcyTable represents a 
         subscriber host PIM policy."
    INDEX { IMPLIED tmnxSubPimPlcyName }
    ::= { tmnxSubPimPlcyTable 1 }

TmnxSubPimPlcyEntry ::= SEQUENCE {
    tmnxSubPimPlcyName               TNamedItem,
    tmnxSubPimPlcyRowStatus          RowStatus,
    tmnxSubPimPlcyLastChanged        TimeStamp,
    tmnxSubPimPlcyDescription        TItemDescription
}

tmnxSubPimPlcyName       OBJECT-TYPE
    SYNTAX      TNamedItem
    MAX-ACCESS  not-accessible
    STATUS      current
    DESCRIPTION
        "The value of tmnxSubPimPlcyName specifies the name of the host PIM policy."
    ::= { tmnxSubPimPlcyEntry 1 }

tmnxSubPimPlcyRowStatus OBJECT-TYPE
    SYNTAX     RowStatus
    MAX-ACCESS read-create
    STATUS     current
    DESCRIPTION
        "The value of tmnxSubPimPlcyRowStatus controls the creation and
         deletion of rows in the table."
    ::= { tmnxSubPimPlcyEntry 2 }

tmnxSubPimPlcyLastChanged       OBJECT-TYPE
    SYNTAX      TimeStamp
    MAX-ACCESS  read-only
    STATUS      current
    DESCRIPTION
        "The value of tmnxSubPimPlcyLastChanged indicates the sysUpTime at
         the time of the last modification of this entry."
    ::= { tmnxSubPimPlcyEntry 3 }
    
tmnxSubPimPlcyDescription OBJECT-TYPE
    SYNTAX      TItemDescription
    MAX-ACCESS  read-create
    STATUS      current
    DESCRIPTION
        "The value of tmnxSubPimPlcyDescription specifies the user provided
         description of this subscriber host PIM policy."
    DEFVAL { ''H }
    ::= { tmnxSubPimPlcyEntry 4 }

--
-- The Subscriber Host Connectivity Verification policy table
--

tmnxSubShcvPlcyTableLastChanged  OBJECT-TYPE
    SYNTAX      TimeStamp
    MAX-ACCESS  read-only
    STATUS      current
    DESCRIPTION
        "The value of tmnxSubShcvPlcyTableLastChanged indicates the 
         sysUpTime at the time of the most recent change to the
         tmnxSubShcvPlcyTable."
    ::= { tmnxSubShcvObjs 1 }
    
tmnxSubShcvPlcyTable             OBJECT-TYPE
    SYNTAX      SEQUENCE OF TmnxSubShcvPlcyEntry
    MAX-ACCESS  not-accessible
    STATUS      current
    DESCRIPTION
        "The table tmnxSubShcvPlcyTable contains the 
        Subscriber Host Connectivity Verification (SHCV) policies."
    ::= { tmnxSubShcvObjs 2 }

tmnxSubShcvPlcyEntry             OBJECT-TYPE
    SYNTAX      TmnxSubShcvPlcyEntry
    MAX-ACCESS  not-accessible
    STATUS      current
    DESCRIPTION
        "Each conceptual row represents an SHCV policy.

         Conceptual rows are created and destroyed by 
         SNMP SET operations on the object tmnxSubShcvPlcyRowStatus."
    INDEX { IMPLIED tmnxSubShcvPlcyName }
    ::= { tmnxSubShcvPlcyTable 1 }

TmnxSubShcvPlcyEntry ::=
    SEQUENCE {
        tmnxSubShcvPlcyName              TNamedItem,
        tmnxSubShcvPlcyLastChanged       TimeStamp,
        tmnxSubShcvPlcyRowStatus         RowStatus,
        tmnxSubShcvPlcyDescription       TItemDescription,
        tmnxSubShcvPlcyPeriodAdminState  TmnxEnabledDisabled,
        tmnxSubShcvPlcyPeriodAction      TmnxSubShcvAction,
        tmnxSubShcvPlcyPeriodInterval    Unsigned32,
        tmnxSubShcvPlcyPeriodRetryCount  TmnxSubShcvRetryCount,
        tmnxSubShcvPlcyPeriodRetryTo     TmnxSubShcvRetryTimeout,
        tmnxSubShcvPlcyVplsSrcIp4AddrTyp InetAddressType,
        tmnxSubShcvPlcyVplsSrcIp4Addr    InetAddress,
        tmnxSubShcvPlcyVplsSrcMacAddress MacAddress,
        tmnxSubShcvPlcyL3SrcIpOrigin     TmnxSubShcvSrcIpOrigin         
    }
    
tmnxSubShcvPlcyName              OBJECT-TYPE
    SYNTAX      TNamedItem
    MAX-ACCESS  not-accessible
    STATUS      current
    DESCRIPTION
        "The value of tmnxSubShcvPlcyName specifies
        the name of the SHCV policy."
    ::= { tmnxSubShcvPlcyEntry 1 }

tmnxSubShcvPlcyLastChanged       OBJECT-TYPE
    SYNTAX      TimeStamp
    MAX-ACCESS  read-only
    STATUS      current
    DESCRIPTION
        "The value of tmnxSubShcvPlcyLastChanged indicates the sysUpTime at
         the time of the last modification of this entry."
    ::= { tmnxSubShcvPlcyEntry 2 }
    
tmnxSubShcvPlcyRowStatus         OBJECT-TYPE
    SYNTAX      RowStatus
    MAX-ACCESS  read-create
    STATUS      current
    DESCRIPTION
        "The value of tmnxSubShcvPlcyRowStatus controls the creation and
         deletion of rows in this table."
    ::= { tmnxSubShcvPlcyEntry 3 }

tmnxSubShcvPlcyDescription       OBJECT-TYPE
    SYNTAX      TItemDescription
    MAX-ACCESS  read-create
    STATUS      current
    DESCRIPTION
        "The value of tmnxSubShcvPlcyDescription specifies the user provided
         description of this SHCV policy."
    DEFVAL { "" }
    ::= { tmnxSubShcvPlcyEntry 4 }

tmnxSubShcvPlcyPeriodAdminState       OBJECT-TYPE
    SYNTAX      TmnxEnabledDisabled
    MAX-ACCESS  read-create
    STATUS      current
    DESCRIPTION
        "The value of tmnxSubShcvPlcyPeriodAdminState specifies
         the administrative state of the periodic connectivity
         verification."
    DEFVAL { enabled }
    ::= { tmnxSubShcvPlcyEntry 5 }

tmnxSubShcvPlcyPeriodAction       OBJECT-TYPE
    SYNTAX      TmnxSubShcvAction
    MAX-ACCESS  read-create
    STATUS      current
    DESCRIPTION
        "The value of tmnxSubShcvPlcyPeriodAction specifies
         the action to take when the periodic connectivity verification
         failed."
    DEFVAL { alarm }
    ::= { tmnxSubShcvPlcyEntry 6 }

tmnxSubShcvPlcyPeriodInterval       OBJECT-TYPE
    SYNTAX      Unsigned32 (1..6000)
    UNITS       "minutes"
    MAX-ACCESS  read-create
    STATUS      current
    DESCRIPTION
        "The value of tmnxSubShcvPlcyPeriodInterval specifies
         the interval between periodic connectivity checks."
    DEFVAL { 30 }
    ::= { tmnxSubShcvPlcyEntry 7 }

tmnxSubShcvPlcyPeriodRetryCount       OBJECT-TYPE
    SYNTAX      TmnxSubShcvRetryCount
    MAX-ACCESS  read-create
    STATUS      current
    DESCRIPTION
        "The value of tmnxSubShcvPlcyPeriodRetryCount specifies
         the number of retransmissions in periodic connectivity
         verification.
         
         A value 'n' specifies that, for any given host,
         at most (n+1) probes are done each interval, 
         and (n+1) missed replies are considered as a connectivity 
         failure."
    DEFVAL { 2 }
    ::= { tmnxSubShcvPlcyEntry 8 }

tmnxSubShcvPlcyPeriodRetryTo       OBJECT-TYPE
    SYNTAX      TmnxSubShcvRetryTimeout
    UNITS       "seconds"
    MAX-ACCESS  read-create
    STATUS      current
    DESCRIPTION
        "The value of tmnxSubShcvPlcyPeriodRetryTo specifies
         the timeout before a retransmission in periodic
         connectivity verification."
    DEFVAL { 10 }
    ::= { tmnxSubShcvPlcyEntry 9 }

tmnxSubShcvPlcyVplsSrcIp4AddrTyp OBJECT-TYPE
    SYNTAX      InetAddressType
    MAX-ACCESS  read-create
    STATUS      current
    DESCRIPTION 
        "The value of tmnxSubShcvPlcyVplsSrcIp4AddrTyp specifies
         the address type of tmnxSubShcvPlcyVplsSrcIp4Addr.
         
         The value 'unknown' means that no value is configured for
         tmnxSubShcvPlcyVplsSrcIp4Addr."
    DEFVAL { unknown }
    ::= { tmnxSubShcvPlcyEntry 10 }

tmnxSubShcvPlcyVplsSrcIp4Addr OBJECT-TYPE
    SYNTAX      InetAddress (SIZE(0|4))
    MAX-ACCESS  read-create
    STATUS      current
    DESCRIPTION 
        "The value of tmnxSubShcvPlcyVplsSrcIp4Addr specifies
         the IPv4 address to be used as source address
         for connectivity verification in a VPLS service."
    DEFVAL { ''H }
    ::= { tmnxSubShcvPlcyEntry 11 }
    
tmnxSubShcvPlcyVplsSrcMacAddress OBJECT-TYPE
    SYNTAX      MacAddress
    MAX-ACCESS  read-create
    STATUS      current
    DESCRIPTION 
        "The value of tmnxSubShcvPlcyVplsSrcMacAddress specifies
         the MAC address to be used as source address
         for connectivity verification in a VPLS service.
         
         The value all zeroes means that no MAC address is configured."
    DEFVAL { '000000000000'H }
    ::= { tmnxSubShcvPlcyEntry 12 }
    
tmnxSubShcvPlcyL3SrcIpOrigin OBJECT-TYPE
    SYNTAX      TmnxSubShcvSrcIpOrigin
    MAX-ACCESS  read-create
    STATUS      current
    DESCRIPTION 
        "The value of tmnxSubShcvPlcyL3SrcIpOrigin specifies
         the origin of the source IP address used for
         connectivity verification in an IES or VPRN service."
    DEFVAL { interface }
    ::= { tmnxSubShcvPlcyEntry 13 }

--
--      The Subscriber Host Connectivity Verification Trigger table
--

tmnxSubShcvTrigTableLastChanged  OBJECT-TYPE
    SYNTAX      TimeStamp
    MAX-ACCESS  read-only
    STATUS      current
    DESCRIPTION
        "The value of tmnxSubShcvTrigTableLastChanged indicates the 
         sysUpTime at the time of the most recent change to the
         tmnxSubShcvTrigTable."
    ::= { tmnxSubShcvObjs 3 }
    
tmnxSubShcvTrigTable             OBJECT-TYPE
    SYNTAX      SEQUENCE OF TmnxSubShcvTrigEntry
    MAX-ACCESS  not-accessible
    STATUS      current
    DESCRIPTION
        "The table tmnxSubShcvTrigTable contains the 
        Subscriber Host Connectivity Verification (SHCV) trigger
        configuration of the SHCV policies."
    ::= { tmnxSubShcvObjs 4 }

tmnxSubShcvTrigEntry             OBJECT-TYPE
    SYNTAX      TmnxSubShcvTrigEntry
    MAX-ACCESS  not-accessible
    STATUS      current
    DESCRIPTION
        "Each conceptual row represents an SHCV trigger associated with
         an SHCV policy.

         Conceptual rows are created and destroyed automatically 
         by the system while rows in the tmnxSubShcvPlcyTable are
         created and destroyed."
    INDEX { tmnxSubShcvPlcyName, tmnxSubShcvTrigType }
    ::= { tmnxSubShcvTrigTable 1 }

TmnxSubShcvTrigEntry ::=
    SEQUENCE {
        tmnxSubShcvTrigType              INTEGER,
        tmnxSubShcvTrigLastChanged       TimeStamp,
        tmnxSubShcvTrigAdminState        TmnxEnabledDisabled,
        tmnxSubShcvTrigRetryCount        Unsigned32,
        tmnxSubShcvTrigRetryTo           Unsigned32
    }
    
tmnxSubShcvTrigType              OBJECT-TYPE
    SYNTAX      INTEGER {
                    ipConflict (1),
                    hostLimitExceeded (2),
                    inactivity (3),
                    mobility (4),
                    macLearning (5)
                }
    MAX-ACCESS  not-accessible
    STATUS      current
    DESCRIPTION
        "The value of tmnxSubShcvPlcyName specifies
        the type of SHCV trigger configured
        with this conceptual row."
    ::= { tmnxSubShcvTrigEntry 1 }

tmnxSubShcvTrigLastChanged       OBJECT-TYPE
    SYNTAX      TimeStamp
    MAX-ACCESS  read-only
    STATUS      current
    DESCRIPTION
        "The value of tmnxSubShcvTrigLastChanged indicates the sysUpTime at
         the time of the last modification of this entry."
    ::= { tmnxSubShcvTrigEntry 2 }
    
tmnxSubShcvTrigAdminState       OBJECT-TYPE
    SYNTAX      TmnxEnabledDisabled
    MAX-ACCESS  read-create
    STATUS      current
    DESCRIPTION
        "The value of tmnxSubShcvTrigAdminState specifies
         if connectivity verification is activated when this trigger occurs."
    DEFVAL { enabled }
    ::= { tmnxSubShcvTrigEntry 3 }

tmnxSubShcvTrigRetryCount       OBJECT-TYPE
    SYNTAX      Unsigned32 (1..29)
    MAX-ACCESS  read-create
    STATUS      current
    DESCRIPTION
        "The value of tmnxSubShcvTrigRetryCount specifies
         the number of retransmissions in triggered connectivity
         verification.
         
         A value 'n' specifies that, for any given host,
         at most (n+1) probes are done each interval, 
         and (n+1) missed replies are considered as a connectivity 
         failure.

         The default value depends on the trigger type."
    ::= { tmnxSubShcvTrigEntry 4 }

tmnxSubShcvTrigRetryTo       OBJECT-TYPE
    SYNTAX      Unsigned32 (1..60)
    UNITS       "seconds"
    MAX-ACCESS  read-create
    STATUS      current
    DESCRIPTION
        "The value of tmnxSubShcvTrigRetryTo specifies
         the timeout before a retransmission in triggered
         connectivity verification.

         The default value depends on the trigger type."
    ::= { tmnxSubShcvTrigEntry 5 }

----------------------------------------------------------------------------
--  Notifications
----------------------------------------------------------------------------

-- ----------------------------------
--  Subscriber Notification Objects
-- ----------------------------------
tmnxSubIdent OBJECT-TYPE
    SYNTAX      DisplayString
    MAX-ACCESS  accessible-for-notify
    STATUS      current
    DESCRIPTION
        "The value of the object tmnxSubIdent indicates the subscriber
         identification."
    ::= { tmnxSubscriberNotifyObjects 1 }

tmnxOldSubIdent OBJECT-TYPE
    SYNTAX      DisplayString
    MAX-ACCESS  accessible-for-notify
    STATUS      current
    DESCRIPTION
        "The value of the object tmnxOldSubIdent indicates the old subscriber
         identification. The object is used when reporting a subscriber
         rename action."
    ::= { tmnxSubscriberNotifyObjects 2 }

tmnxNewSubIdent OBJECT-TYPE
    SYNTAX      DisplayString
    MAX-ACCESS  accessible-for-notify
    STATUS      current
    DESCRIPTION
        "The value of the object tmnxNewSubIdent indicates the new subscriber
         identification. The object is used when reporting a subscriber
         rename action."
    ::= { tmnxSubscriberNotifyObjects 3 }

tmnxSubAcctPlcyFailureReason OBJECT-TYPE
    SYNTAX      DisplayString
    MAX-ACCESS  accessible-for-notify
    STATUS      current
    DESCRIPTION
        "The value of the object tmnxSubAcctPlcyFailureReason is a printable
         character string which contains information about the reason why the
         tmnxSubAcctPlcyFailure notification was generated."
    ::= { tmnxSubscriberNotifyObjects 4 }

tmnxSubMcsRelatedProblemDescr OBJECT-TYPE
    SYNTAX      DisplayString
    MAX-ACCESS  accessible-for-notify
    STATUS      current
    DESCRIPTION
        "The value of the object tmnxSubMcsRelatedProblemDescr is a printable
         character string which contains information about the reason why the
         tmnxSubMcsRelatedProblem notification was generated."
    ::= { tmnxSubscriberNotifyObjects 5 }

tmnxSubRadiusDisconnectReason OBJECT-TYPE
    SYNTAX      DisplayString
    MAX-ACCESS  accessible-for-notify
    STATUS      current
    DESCRIPTION
        "The value of the object tmnxSubRadiusDisconnectReason indicates the
         reason why the node failed to process a Disconnect request from a
         Radius server."
    ::= { tmnxSubscriberNotifyObjects 6 }

tmnxSubRadiusCoAReason OBJECT-TYPE
    SYNTAX      DisplayString
    MAX-ACCESS  accessible-for-notify
    STATUS      current
    DESCRIPTION
        "The value of the object tmnxSubRadiusCoAReason indicates the reason
         why the node failed to process a Change of Authorization (CoA) request
         from a Radius server."
    ::= { tmnxSubscriberNotifyObjects 7 }

tmnxSubRadiusSubAuthReason OBJECT-TYPE
    SYNTAX      DisplayString
    MAX-ACCESS  accessible-for-notify
    STATUS      current
    DESCRIPTION
        "The value of the object tmnxSubRadiusSubAuthReason is a printable
         character string which contains information about the problem
         that occurred while trying to authenticate the subscriber."
    ::= { tmnxSubscriberNotifyObjects 8 }

tmnxSubNotifSLAProfName OBJECT-TYPE
    SYNTAX      TNamedItem
    MAX-ACCESS  accessible-for-notify
    STATUS      current
    DESCRIPTION
        "The value of tmnxSubNotifSLAProfName indicates 
         the name of an SLA profile."
    ::= { tmnxSubscriberNotifyObjects 9 }

tmnxSubNotifApCMapName OBJECT-TYPE
    SYNTAX      TNamedItem
    MAX-ACCESS  accessible-for-notify
    STATUS      current
    DESCRIPTION
        "The value of tmnxSubNotifApCMapName indicates 
         the name of a Category Map."
    ::= { tmnxSubscriberNotifyObjects 10 }

tmnxSubNotifApCategoryName OBJECT-TYPE
    SYNTAX      TNamedItem
    MAX-ACCESS  accessible-for-notify
    STATUS      current
    DESCRIPTION
        "The value of tmnxSubNotifApCategoryName indicates
         the name of a Category."
    ::= { tmnxSubscriberNotifyObjects 11 }

tmnxSubNotifMacAddr OBJECT-TYPE
    SYNTAX         MacAddress
    MAX-ACCESS     accessible-for-notify
    STATUS         current
    DESCRIPTION    "The value of the object tmnxSubNotifMacAddr indicates 
                    a MAC address."
    ::= { tmnxSubscriberNotifyObjects 12 }

tmnxSubNotifIpAddrType OBJECT-TYPE
    SYNTAX          InetAddressType
    MAX-ACCESS      accessible-for-notify
    STATUS          current
    DESCRIPTION     "The value of tmnxSubNotifIpAddrType indicates 
                     the address type of tmnxSubNotifIpAddr."
    ::= { tmnxSubscriberNotifyObjects 13 }

tmnxSubNotifIpAddr OBJECT-TYPE
    SYNTAX          InetAddress (SIZE(0|4|16))
    MAX-ACCESS      accessible-for-notify
    STATUS          current
    DESCRIPTION     "The value of tmnxSubNotifIpAddr indicates an IP address."
    ::= { tmnxSubscriberNotifyObjects 14 }

tmnxSubAdditionalInfo OBJECT-TYPE
    SYNTAX      DisplayString
    MAX-ACCESS  accessible-for-notify
    STATUS      current
    DESCRIPTION
        "The value of the object tmnxSubAdditionalInfo is a printable
         character string which contains information about the reason why the
         notification was generated."
    ::= { tmnxSubscriberNotifyObjects 15 }
    
tmnxSubNotifPrefixLength OBJECT-TYPE
    SYNTAX      InetAddressPrefixLength
    MAX-ACCESS  accessible-for-notify
    STATUS      current
    DESCRIPTION
        "The value of the object tmnxSubNotifPrefixLength indicates 
         the prefix length of tmnxSubNotifIpAddr."
    ::= { tmnxSubscriberNotifyObjects 16 }

-- ----------------------------------
-- Radius Notify Statistics objects
-- ----------------------------------
tmnxSubRadNotifyStatsReceived OBJECT-TYPE
    SYNTAX      Counter32
    MAX-ACCESS  read-only
    STATUS      current
    DESCRIPTION
        "The value of tmnxSubRadNotifyStatsReceived indicates the number of
         notify Change-of-Authorization requests received."
    ::= { tmnxSubRadNotifyStatsObjects 1 }

tmnxSubRadNotifyStatsAccepted OBJECT-TYPE
    SYNTAX      Counter32
    MAX-ACCESS  read-only
    STATUS      current
    DESCRIPTION
        "The value of tmnxSubRadNotifyStatsAccepted indicates the number of
         notify Change-of-Authorization requests accepted."
    ::= { tmnxSubRadNotifyStatsObjects 2 }

tmnxSubRadNotifyStatsRejected OBJECT-TYPE
    SYNTAX      Counter32
    MAX-ACCESS  read-only
    STATUS      current
    DESCRIPTION
        "The value of tmnxSubRadNotifyStatsRejected indicates the number of
         notify Change-of-Authorization requests rejected."
    ::= { tmnxSubRadNotifyStatsObjects 3 }

tmnxSubRadNotifyStatsBadAuth OBJECT-TYPE
    SYNTAX      Counter32
    MAX-ACCESS  read-only
    STATUS      current
    DESCRIPTION
        "The value of tmnxSubRadNotifyStatsBadAuth indicates the
        number of notify Change-of-Authorization requests rejected because of
        authentication failure."
    ::= { tmnxSubRadNotifyStatsObjects 4 }

tmnxSubRadNotifyStatsNoNotify OBJECT-TYPE
    SYNTAX      Counter32
    MAX-ACCESS  read-only
    STATUS      current
    DESCRIPTION
        "The value of tmnxSubRadNotifyStatsNoNotify indicates the
        number of notify Change-of-Authorization requests rejected due to lack
        of notification process."
    ::= { tmnxSubRadNotifyStatsObjects 5 }

tmnxSubRadNotifyStatsInvalidMsg OBJECT-TYPE
    SYNTAX      Counter32
    MAX-ACCESS  read-only
    STATUS      current
    DESCRIPTION
        "The value of tmnxSubRadNotifyStatsInvalidMsg indicates the
        number of notify Change-of-Authorization requests rejected because of
        decode errors."
    ::= { tmnxSubRadNotifyStatsObjects 6 }


tmnxSubRadNotifyStatsNoResource OBJECT-TYPE
    SYNTAX      Counter32
    MAX-ACCESS  read-only
    STATUS      current
    DESCRIPTION
        "The value of tmnxSubRadNotifyStatsNoResource indicates the
        number of notify Change-of-Authorization requests rejected due to lack
        of resources."
    ::= { tmnxSubRadNotifyStatsObjects 7 }

tmnxSubRadNotifyStatsUnknownHost OBJECT-TYPE
    SYNTAX      Counter32
    MAX-ACCESS  read-only
    STATUS      current
    DESCRIPTION
        "The value of tmnxSubRadNotifyStatsUnknownHost indicates the
        number of notify Change-of-Authorization requests which do not have
        NAS-Port-ID or Framed-IP-Address set or have mismatched subscriber-id."
    ::= { tmnxSubRadNotifyStatsObjects 8 }

-- ------------------------------------------------------
-- Radius Notify Statistics (Disconnect-Messages) objects
-- ------------------------------------------------------
tmnxSubNotifyDisMsgReceived OBJECT-TYPE
    SYNTAX      Counter32
    MAX-ACCESS  read-only
    STATUS      current
    DESCRIPTION
        "The value of tmnxSubNotifyDisMsgReceived indicates the number of
         notify disconnect requests received."
    ::= { tmnxSubRadNotifyStatsObjects 9 }

tmnxSubNotifyDisMsgAccepted OBJECT-TYPE
    SYNTAX      Counter32
    MAX-ACCESS  read-only
    STATUS      current
    DESCRIPTION
        "The value of tmnxSubNotifyDisMsgAccepted indicates the number of
         notify disconnect requests accepted."
    ::= { tmnxSubRadNotifyStatsObjects 10 }

tmnxSubNotifyDisMsgRejected OBJECT-TYPE
    SYNTAX      Counter32
    MAX-ACCESS  read-only
    STATUS      current
    DESCRIPTION
        "The value of tmnxSubNotifyDisMsgRejected indicates the number of
         notify disconnect requests rejected."
    ::= { tmnxSubRadNotifyStatsObjects 11 }

tmnxSubNotifyDisMsgBadAuth OBJECT-TYPE
    SYNTAX      Counter32
    MAX-ACCESS  read-only
    STATUS      current
    DESCRIPTION
        "The value of tmnxSubNotifyDisMsgBadAuth indicates the
        number of notify disconnect requests rejected because of authentication
        failure."
    ::= { tmnxSubRadNotifyStatsObjects 12 }

tmnxSubNotifyDisMsgNoNotify OBJECT-TYPE
    SYNTAX      Counter32
    MAX-ACCESS  read-only
    STATUS      current
    DESCRIPTION
        "The value of tmnxSubNotifyDisMsgNoNotify indicates the
        number of notify disconnect requests rejected due to lack of
        notification process."
    ::= { tmnxSubRadNotifyStatsObjects 13 }

tmnxSubNotifyDisMsgInvalidMsg OBJECT-TYPE
    SYNTAX      Counter32
    MAX-ACCESS  read-only
    STATUS      current
    DESCRIPTION
        "The value of tmnxSubNotifyDisMsgInvalidMsg indicates the
        number of notify disconnect requests rejected because of decode errors."
    ::= { tmnxSubRadNotifyStatsObjects 14 }


tmnxSubNotifyDisMsgNoResource OBJECT-TYPE
    SYNTAX      Counter32
    MAX-ACCESS  read-only
    STATUS      current
    DESCRIPTION
        "The value of tmnxSubNotifyDisMsgNoResource indicates the
        number of notify disconnect requests rejected due to lack of resources."
    ::= { tmnxSubRadNotifyStatsObjects 15 }

tmnxSubNotifyDisMsgUnknownHost OBJECT-TYPE
    SYNTAX      Counter32
    MAX-ACCESS  read-only
    STATUS      current
    DESCRIPTION
        "The value of tmnxSubNotifyDisMsgUnknownHost indicates the
        number of notify disconnect requests which do not have NAS-Port-ID or
        Framed-IP-Address set or have mismatched subscriber-id."
    ::= { tmnxSubRadNotifyStatsObjects 16 }

-- ----------------------------------
--  Subscriber Notifications
-- ----------------------------------
tmnxSubscriberCreated NOTIFICATION-TYPE
    OBJECTS {
        tmnxSubIdent
    }
    STATUS current
    DESCRIPTION
        "The tmnxSubscriberCreated notification is sent when a new subscriber
         is added to the tmnxSubscriberInfoTable."
    ::= { tmnxSubscriberNotifications 1 }

tmnxSubscriberDeleted NOTIFICATION-TYPE
    OBJECTS {
        tmnxSubIdent
    }
    STATUS current
    DESCRIPTION
        "The tmnxSubscriberDeleted notification is sent when a new subscriber
         is removed from the tmnxSubscriberInfoTable."
    ::= { tmnxSubscriberNotifications 2 }

tmnxSubscriberRenamed NOTIFICATION-TYPE
    OBJECTS {
        tmnxOldSubIdent,
        tmnxNewSubIdent
    }
    STATUS current
    DESCRIPTION
        "The tmnxSubscriberRenamed notification is sent when an existing
         subscriber is given a new name."
    ::= { tmnxSubscriberNotifications 3 }

tmnxSubAcctPlcyFailure NOTIFICATION-TYPE
    OBJECTS {
        tmnxSubAcctPlcyName,
        tmnxSubAcctPlcyFailureReason
    }
    STATUS current
    DESCRIPTION
        "The tmnxSubAcctPlcyFailure notification is generated when a RADIUS
         accounting request was not sent out successfully to any of the RADIUS
         servers in the indicated accounting policy."
    ::= { tmnxSubscriberNotifications 4 }

tmnxSubMcsRelatedProblem NOTIFICATION-TYPE
    OBJECTS {
        tmnxSubMcsRelatedProblemDescr
    }
    STATUS current
    DESCRIPTION
        "The tmnxSubMcsRelatedProblem notification is generated when a
         subscriber management specific problem occurs during Multi Chassis
         Syncing, e.g. of DHCP lease states. 
         
         The problem is described in the object tmnxSubMcsRelatedProblemDescr."
    ::= { tmnxSubscriberNotifications 5 }

tmnxSubAuthPlcyRadSerOperStatChg NOTIFICATION-TYPE
    OBJECTS {
        tmnxSubAuthPlcyRadServAddrType,
        tmnxSubAuthPlcyRadServAddress,
        tmnxSubAuthPlcyRadServOperState
    }
    STATUS  current
    DESCRIPTION
        "The tmnxSubAuthPlcyRadSerOperStatChg notification is generated
         when the operational status of a Radius server, configured for use
         with DHCP radius authentication, has transitioned either from
         'inService' to 'outOfService' or from 'outOfService' to 'inService'."
    ::= { tmnxSubscriberNotifications  6 }

tmnxSubAcctPlcyRadSerOperStatChg NOTIFICATION-TYPE
    OBJECTS {
        tmnxSubAcctPlcyRadServAddrType,
        tmnxSubAcctPlcyRadServAddr,
        tmnxSubAcctPlcyRadServOperState
    }
    STATUS  current
    DESCRIPTION
        "The tmnxSubAcctPlcyRadSerOperStatChg notification is generated
         when the operational status of a Radius server, configured for use
         with DHCP radius based subscriber accounting, has transitioned
         either from 'inService' to 'outOfService' or from 'outOfService' to
         'inService'."
    ::= { tmnxSubscriberNotifications  7 }

tmnxSubRadSapDisconnectError NOTIFICATION-TYPE
    OBJECTS {
        svcId,
        sapPortId,
        sapEncapValue,
        tmnxSubRadiusDisconnectReason
    }
    STATUS  current
    DESCRIPTION
        "The tmnxSubRadSapDisconnectError notification indicates that the
         system was unable to process a Disconnect request from a Radius
         server."
    ::= { tmnxSubscriberNotifications 8 }

tmnxSubRadSdpBndDisconnectError NOTIFICATION-TYPE
    OBJECTS {
        svcId,
        sdpBindId,
        tmnxSubRadiusDisconnectReason
    }
    STATUS  current
    DESCRIPTION
        "The tmnxSubRadSdpBndDisconnectError notification indicates that the
         system was unable to process a Disconnect request from a Radius
         server."
    ::= { tmnxSubscriberNotifications 9 }

tmnxSubRadSapCoAError NOTIFICATION-TYPE
    OBJECTS {
        svcId,
        sapPortId,
        sapEncapValue,
        tmnxSubRadiusCoAReason
    }
    STATUS  current
    DESCRIPTION
        "The tmnxSubRadSapCoAError notification indicates that the
         system was unable to process a Change of Authorization (CoA) request
         from a Radius server."
    ::= { tmnxSubscriberNotifications 10 }

tmnxSubRadSdpBndCoAError NOTIFICATION-TYPE
    OBJECTS {
        svcId,
        sdpBindId,
        tmnxSubRadiusCoAReason
    }
    STATUS  current
    DESCRIPTION
        "The tmnxSubRadSdpBndCoAError notification indicates that the
         system was unable to process a Change of Authorization (CoA) request
         from a Radius server."
    ::= { tmnxSubscriberNotifications 11 }

tmnxSubRadSapSubAuthError NOTIFICATION-TYPE
    OBJECTS {
        svcId,
        sapPortId,
        sapEncapValue,
        tmnxSubRadiusSubAuthReason
    }
    STATUS  current
    DESCRIPTION
        "The tmnxSubRadSapSubAuthError notification indicates that the
         system encountered a problem while trying to authenticate a
         subscriber."
    ::= { tmnxSubscriberNotifications 12 }

tmnxSubRadSdpBndSubAuthError NOTIFICATION-TYPE
    OBJECTS {
        svcId,
        sdpBindId,
        tmnxSubRadiusSubAuthReason
    }
    STATUS  current
    DESCRIPTION
        "The tmnxSubRadSdpBndSubAuthError notification indicates that the
         system encountered a problem while trying to authenticate a
         subscriber."
    ::= { tmnxSubscriberNotifications 13 }

tmnxSubUserCategoryOutOfCredit NOTIFICATION-TYPE
    OBJECTS {
        tmnxSubIdent,
        svcId,
        sapPortId,
        sapEncapValue,
        tmnxSubNotifSLAProfName,
        tmnxSubNotifApCMapName,
        tmnxSubNotifApCategoryName,
        tmnxSubNotifMacAddr,
        tmnxSubNotifIpAddrType,
        tmnxSubNotifIpAddr
    }
    STATUS  current
    DESCRIPTION
        "The tmnxSubUserCategoryOutOfCredit notification indicates that the
         credit for a user's category has expired."
    ::= { tmnxSubscriberNotifications 14 }

tmnxSubUserCategoryRefreshCredit NOTIFICATION-TYPE
    OBJECTS {
        tmnxSubIdent,
        svcId,
        sapPortId,
        sapEncapValue,
        tmnxSubNotifSLAProfName,
        tmnxSubNotifApCMapName,
        tmnxSubNotifApCategoryName,
        tmnxSubNotifMacAddr,
        tmnxSubNotifIpAddrType,
        tmnxSubNotifIpAddr
    }
    STATUS  current
    DESCRIPTION
        "The tmnxSubUserCategoryRefreshCredit notification is sent to 
         indicates that the credit for a user's category has been
         regreshed."
    ::= { tmnxSubscriberNotifications 15 }

tmnxSubUserCategoryError NOTIFICATION-TYPE
    OBJECTS {
        tmnxSubIdent,
        svcId,
        sapPortId,
        sapEncapValue,
        tmnxSubNotifSLAProfName,
        tmnxSubNotifApCMapName,
        tmnxSubNotifApCategoryName,
        tmnxSubNotifMacAddr,
        tmnxSubNotifIpAddrType,
        tmnxSubNotifIpAddr,
        tmnxSubAdditionalInfo
    }
    STATUS  current
    DESCRIPTION
        "The tmnxSubUserCategoryError notification indicates that the
         credit control application has encountered an error and has taken
         corrective action."
    ::= { tmnxSubscriberNotifications 16 }
    
tmnxSubHostInconsistentAtmTdOvr  NOTIFICATION-TYPE
    OBJECTS {
        tmnxSubHostInfoV2SubIdent,
        tmnxSubAdditionalInfo
    }
    STATUS current
    DESCRIPTION
        "The tmnxSubHostInconsistentAtmTdOvr notification is sent
         when an AAA server (e.g. a RADIUS server) specifies an ATM Traffic
         Descriptor override for a subscriber host while it has already
         specified another one for another host on the same ATM Virtual Circuit.
         
         The specified host will not use this traffic descriptor; it will use
         the same as the other host instead.
         
         The configuration of the AAA server must be made consistent such that
         all subscriber hosts on a given ATM VC have the same ATM traffic
         descriptors."
    ::= { tmnxSubscriberNotifications 20 }

tmnxSubSlaacSetupFailure NOTIFICATION-TYPE
    OBJECTS {
        svcId,
        sapPortId,
        sapEncapValue,
        tmnxSubAdditionalInfo
    }
    STATUS current
    DESCRIPTION
        "The tmnxSubSlaacSetupFailure notification indicates that
         the system could not create or update a SLAAC host in the
         tmnxSubSlaacTable. The problem is described in the
         object tmnxSubAdditionalInfo."
    ::= { tmnxSubscriberNotifications 21 }

tmnxSubHostLcktLimitReached NOTIFICATION-TYPE
    OBJECTS {
        tmnxSubAdditionalInfo
    }
    STATUS current
    DESCRIPTION
        "The tmnxSubHostLcktLimitReached notification indicates that
         the system wide maximum number of lockout hosts is reached."
    ::= { tmnxSubscriberNotifications 22 }

tmnxSubHostLcktSapLimitReached NOTIFICATION-TYPE
    OBJECTS {
        sapHostLockoutPolicy,
        tmnxSubLcktPlcyMaxLcktHosts,
        tmnxSubNotifMacAddr
    }
    STATUS current
    DESCRIPTION
        "The tmnxSubHostLcktSapLimitReached notification indicates that
         the maximum number of lockout hosts on a given SAP is reached."
    ::= { tmnxSubscriberNotifications 23 }

tmnxSubSysNextHopUsageHi NOTIFICATION-TYPE
    OBJECTS {
        tmnxSubSysNextHopUsageHigh
    }
    STATUS obsolete
    DESCRIPTION
        "[CAUSE] The tmnxSubSysNextHopUsageHi notification is sent when 
         the IP next-hop usage by subscriber managed routes 
         reaches its high watermark ('true')
         or when it reaches its low watermark again ('false');
         the watermarks are derived from the limit specified with
         the object tmnxSubSysNextHopLimit.
         
         [EFFECT] There is no immediate effect, but when the usage actually
         hits the limit, new hosts will not get their managed routes
         
         [RECOVERY]"
    ::= { tmnxSubscriberNotifications 24}

tmnxSubSlaacOverride NOTIFICATION-TYPE
    OBJECTS {
        tmnxSubSlaacPfxLen,
        tmnxSubSlaacPortId,
        tmnxSubSlaacEncapValue,
        svcDhcpLeaseCiAddrMaskLen
    }
    STATUS current
    DESCRIPTION
        "[CAUSE] The tmnxSubSlaacOverride notification is sent when
         an IPv6 client requests a DHCPv6 non-temporary address (IA_NA)
         which overrides an existing SLAAC prefix for this client.

         [EFFECT] The SLAAC host is removed from the system.

         [RECOVERY] None"
    ::= { tmnxSubscriberNotifications 25}

tmnxSubSysChassMemoryUsageHi NOTIFICATION-TYPE
    OBJECTS {
        tmnxSubSysChassMemoryUsageHigh
    }
    STATUS current
    DESCRIPTION
        "[CAUSE] The tmnxSubSysChassMemoryUsageHi notification is sent when 
         the memory usage by subscriber management on this system 
         reaches its high watermark ('true') or a chassis
         or when it reaches its low watermark again ('false').
         
         [EFFECT] There is no immediate effect, but when the usage actually
         hits the limit, new hosts will not be created.
         
         [RECOVERY] Either change the network configuration to offload subscribers to
         other systems, or upgrade to a set of newer CPM (system management processor) 
         with more memory."
    ::= { tmnxSubscriberNotifications 26}

tmnxSubVSubnetHostsDeleted NOTIFICATION-TYPE
    OBJECTS {
        tmnxSubVSubnetDefRtrAddrType,
        tmnxSubVSubnetDefRtrAddr,
        tmnxSubVSubnetPrefixLength
    }
    STATUS current
    DESCRIPTION
        "[CAUSE] The tmnxSubVSubnetHostsDeleted notification is sent when
         this system deletes all host contexts of a subscriber
         associated with a virtual subnet because a new default router 
         and/or subnet were assigned.
         
         This is the consequence of a change in the configuration in the
         server that assigns the subnets.

         [EFFECT] The hosts have to transmit DHCP requests if they need
         a connection.

         [RECOVERY] None."
    ::= { tmnxSubscriberNotifications 27}

tmnxSubIpoeInvalidSessionKey NOTIFICATION-TYPE
    OBJECTS {
        svcId,
        sapPortId,
        sapEncapValue,
        tmnxSubNotifMacAddr,
        tmnxSubAdditionalInfo
    }
    STATUS current
    DESCRIPTION
        "The tmnxSubIpoeInvalidSessionKey notification is sent
         when this system fails to create an IPoE session in the 
         tmnxSubIpoeSessionTable due to an invalid session key.
         
         [CAUSE] The IPoE session key is invalid.
         
         [EFFECT] The system can not setup the IPoE session.
         
         [RECOVERY] No recovery is required on this system."
    ::= { tmnxSubscriberNotifications 28 }

tmnxSubIpoeInvalidCidRidChange NOTIFICATION-TYPE
    OBJECTS {
        svcId,
        sapPortId,
        sapEncapValue,
        tmnxSubNotifMacAddr,
        tmnxSubAdditionalInfo
    }
    STATUS current
    DESCRIPTION
        "The tmnxSubIpoeInvalidCidRidChange notification is sent
         when this system fails to create an IPoE session in the 
         tmnxSubIpoeSessionTable due to an invalid CID or RID change.
         
         [CAUSE] The IPoE session CID or RID change is invalid.
         
         [EFFECT] The system can not setup the IPoE session.
         
         [RECOVERY] No recovery is required on this system."
    ::= { tmnxSubscriberNotifications 29 }
   
tmnxSubIpoeSessionLimitReached NOTIFICATION-TYPE
    OBJECTS {
        svcId,
        sapPortId,
        sapEncapValue,
        tmnxSubNotifMacAddr,
        tmnxSubAdditionalInfo
    }
    STATUS current
    DESCRIPTION
        "The tmnxSubIpoeSessionLimitReached notification is sent
         when this system fails to create an IPoE session in the 
         tmnxSubIpoeSessionTable because the IPoE session limit
         is reached.
         
         [CAUSE] The IPoE session limit is reached.
         
         [EFFECT] The system can not setup the IPoE session.
         
         [RECOVERY] No recovery is required on this system."
    ::= { tmnxSubscriberNotifications 30 }

tmnxSubIpoePersistenceRecovery NOTIFICATION-TYPE
    OBJECTS {
        svcId,
        sapPortId,
        sapEncapValue,
        tmnxSubNotifMacAddr,
        tmnxSubAdditionalInfo
    }
    STATUS current
    DESCRIPTION
        "The tmnxSubIpoePersistenceRecovery notification is sent
         when this system fails to create an IPoE session in the 
         tmnxSubIpoeSessionTable because the system is still 
         recovering from persistence.
         
         [CAUSE] The system is still recovering from persistence.
         
         [EFFECT] The system can not setup the IPoE session.
         
         [RECOVERY] No recovery is required on this system."
    ::= { tmnxSubscriberNotifications 31 }

tmnxSubIpoeMigrHostDeleted NOTIFICATION-TYPE
    OBJECTS {
        svcId,
        sapPortId,
        sapEncapValue,
        tmnxSubNotifIpAddrType,
        tmnxSubNotifIpAddr,
        tmnxSubNotifPrefixLength,
        tmnxSubAdditionalInfo
    }
    STATUS current
    DESCRIPTION
        "The tmnxSubIpoeMigrHostDeleted notification is sent
         when this system deletes a host for IPoE session migration.
         
         [CAUSE] The system is performing an IPoE session migration.
         
         [EFFECT] The host will be migrated.
         
         [RECOVERY] No recovery is required on this system."
    ::= { tmnxSubscriberNotifications 33 }

----------------------------------------------------------------------------
--  Conformance Groups
----------------------------------------------------------------------------
----------------------------------------------
--  OBJECT-GROUPS
----------------------------------------------

-- tmnxSubMgmtConfGroup   OBJECT-GROUP
--    ::= { tmnxSubMgmtGroups 1 }

tmnxSubAuthenticationV4v0Group   OBJECT-GROUP
    OBJECTS {
        tmnxSubAuthPlcyRowStatus,
        tmnxSubAuthPlcyLastMgmtChange,
        tmnxSubAuthPlcyDescription,
        tmnxSubAuthPlcyPassword,
        tmnxSubAuthPlcyRadAuthRetries,
        tmnxSubAuthPlcyRadAuthSrceAddr,
        tmnxSubAuthPlcyRadAuthSrceAddrTp,
        tmnxSubAuthPlcyRadAuthTimeout,
        tmnxSubAuthPlcyReAuthenticate,
        tmnxSubAuthPlcyUserNameFormat,

        tmnxSubAuthPlcyRadServRowStatus,
        tmnxSubAuthPlcyRadLastMgmtChange,
        tmnxSubAuthPlcyRadServAddress,
        tmnxSubAuthPlcyRadServAddrType,
        tmnxSubAuthPlcyRadServSecret,
        tmnxSubAuthPlcyRadServAuthPort,

        tmnxSubAuthPlcySuccess,
        tmnxSubAuthPlcyReject,

        tmnxSubAuthPlcyRadSuccess,
        tmnxSubAuthPlcyRadReject,
        tmnxSubAuthPlcyRadTimeout,
        tmnxSubAuthPlcyRadMd5Fail,
        tmnxSubAuthPlcyRadPending
    }
    STATUS      obsolete
    DESCRIPTION
        "The group of objects supporting management of subscriber
         authentication policies on Nokia SROS series systems."
    ::= { tmnxSubMgmtGroups 2 }

tmnxSubMgmtV4v0Group   OBJECT-GROUP
    OBJECTS {
        tmnxSubProfRowStatus,
        tmnxSubProfLastMgmtChange,
        tmnxSubProfDescription,
        tmnxSubProfIngQosSchedPolicy,
        tmnxSubProfEgrQosSchedPolicy,
        tmnxSubProfCollectAcctStats,
        tmnxSubProfAccountingPolicyId,

        tmnxSubProfSchedOvrRowStatus,
        tmnxSubProfSchedOvrLastMgmtChange,
        tmnxSubProfSchedOvrPIR,
        tmnxSubProfSchedOvrCIR,
        tmnxSubProfSchedOvrSummedCIR,

        tmnxSubProfSLAProfMapRowStatus,
        tmnxSubProfSLAProfMapLastMgmtChange,
        tmnxSubProfSLAProfMapSLAProfile,

        tmnxSLAProfRowStatus,
        tmnxSLAProfLastMgmtChange,
        tmnxSLAProfDescription,
        tmnxSLAProfHostLimit,
        tmnxSLAProfRemoveOldest,
        tmnxSLAProfIngQosPolId,
        tmnxSLAProfIngSharedQPolicy,
        tmnxSLAProfIngUseMpointShared,
        tmnxSLAProfIngIPFilterId,
        tmnxSLAProfEgrQosPolId,
        tmnxSLAProfEgrIPFilterId,

        tmnxSLAIngQueueOvrRowStatus,
        tmnxSLAIngQueueOvrLastMgmtChange,
        tmnxSLAIngQueueOvrPIR,
        tmnxSLAIngQueueOvrCIR,
        tmnxSLAIngQueueOvrMBS,
        tmnxSLAIngQueueOvrCBS,
        tmnxSLAIngQueueOvrHiPrioOnly,

        tmnxSLAEgrQueueOvrRowStatus,
        tmnxSLAEgrQueueOvrLastMgmtChange,
        tmnxSLAEgrQueueOvrPIR,
        tmnxSLAEgrQueueOvrCIR,
        tmnxSLAEgrQueueOvrMBS,
        tmnxSLAEgrQueueOvrCBS,
        tmnxSLAEgrQueueOvrHiPrioOnly,

        tmnxSubExplicitMapRowStatus,
        tmnxSubExplicitMapLastMgmtChange,
        tmnxSubExplicitMapSubProfile,
        tmnxSubExplicitMapSLAProfile,
        tmnxSubExplicitMapAlias,

        tmnxSubIPolRowStatus,
        tmnxSubIPolLastMgmtChange,
        tmnxSubIPolDescription,
        tmnxSubIPolScript1URL,
        tmnxSubIPolScript1AdminState,
        tmnxSubIPolScript1OperState,
        tmnxSubIPolScript2URL,
        tmnxSubIPolScript2AdminState,
        tmnxSubIPolScript2OperState,
        tmnxSubIPolScript3URL,
        tmnxSubIPolScript3AdminState,
        tmnxSubIPolScript3OperState,

        tmnxSubIPolSubProfMapRowStatus,
        tmnxSubIPolSubProfMapLastMgmtChange,
        tmnxSubIPolSubProfMapSubProfile,

        tmnxSubIPolSLAProfMapRowStatus,
        tmnxSubIPolSLAProfMapLastMgmtChange,
        tmnxSubIPolSLAProfMapSLAProfile,

        tmnxSubInfoSubProfile,
        tmnxSubInfoModifySubIdent,

        tmnxSubHostInfoSubIdent,
        tmnxSubHostInfoSubProfile,
        tmnxSubHostInfoSLAProfile,
        tmnxSubHostInfoOrigin,

        tmnxSubIngQosSchedStatsFwdPkts,
        tmnxSubIngQosSchedStatsFwdOctets,

        tmnxSubEgrQosSchedStatsFwdPkts,
        tmnxSubEgrQosSchedStatsFwdOctets,

        tmnxSPISubHostMacAddress,
        tmnxSPISubHostOrigin,

        tmnxSPIStatsIngPchipOffHiPrioPkts,
        tmnxSPIStatsIngPchipOffHiPrioOctets,
        tmnxSPIStatsIngPchipOffLoPrioPkts,
        tmnxSPIStatsIngPchipOffLoPrioOctets,
        tmnxSPIStatsIngPchipOffUncolPkts,
        tmnxSPIStatsIngPchipOffUncolOctets,
        tmnxSPIStatsIngQchipDropHiPrioPkts,
        tmnxSPIStatsIngQchipDropHiPrioOctets,
        tmnxSPIStatsIngQchipDropLoPrioPkts,
        tmnxSPIStatsIngQchipDropLoPrioOctets,
        tmnxSPIStatsIngQchipFwdInProfPkts,
        tmnxSPIStatsIngQchipFwdInProfOctets,
        tmnxSPIStatsIngQchipFwdOutProfPkts,
        tmnxSPIStatsIngQchipFwdOutProfOctets,
        tmnxSPIStatsEgrQchipDropInProfPkts,
        tmnxSPIStatsEgrQchipDropInProfOctets,
        tmnxSPIStatsEgrQchipDropOutProfPkts,
        tmnxSPIStatsEgrQchipDropOutProfOctets,
        tmnxSPIStatsEgrQchipFwdInProfPkts,
        tmnxSPIStatsEgrQchipFwdInProfOctets,
        tmnxSPIStatsEgrQchipFwdOutProfPkts,
        tmnxSPIStatsEgrQchipFwdOutProfOctets,

        tmnxSPIIngQStatsOffHiPrioPkts,
        tmnxSPIIngQStatsDropHiPrioPkts,
        tmnxSPIIngQStatsOffLoPrioPkts,
        tmnxSPIIngQStatsDropLoPrioPkts,
        tmnxSPIIngQStatsOffHiPrioOctets,
        tmnxSPIIngQStatsDropHiPrioOctets,
        tmnxSPIIngQStatsOffLoPrioOctets,
        tmnxSPIIngQStatsDropLoPrioOctets,
        tmnxSPIIngQStatsOffUncolPkts,
        tmnxSPIIngQStatsOffUncolOctets,
        tmnxSPIIngQStatsFwdInProfPkts,
        tmnxSPIIngQStatsFwdOutProfPkts,
        tmnxSPIIngQStatsFwdInProfOctets,
        tmnxSPIIngQStatsFwdOutProfOctets,

        tmnxSPIEgrQStatsFwdInProfPkts,
        tmnxSPIEgrQStatsDropInProfPkts,
        tmnxSPIEgrQStatsFwdOutProfPkts,
        tmnxSPIEgrQStatsDropOutProfPkts,
        tmnxSPIEgrQStatsFwdInProfOctets,
        tmnxSPIEgrQStatsDropInProfOctets,
        tmnxSPIEgrQStatsFwdOutProfOctets,
        tmnxSPIEgrQStatsDropOutProfOctets
    }
    STATUS      obsolete
    DESCRIPTION
        "The group of objects supporting management of subscriber profiles on
         Nokia SROS series systems."
    ::= { tmnxSubMgmtGroups 3 }

tmnxSubMgmtV5v0Group   OBJECT-GROUP
    OBJECTS {
        tmnxSubProfRowStatus,
        tmnxSubProfLastMgmtChange,
        tmnxSubProfDescription,
        tmnxSubProfIngQosSchedPolicy,
        tmnxSubProfEgrQosSchedPolicy,
        tmnxSubProfCollectAcctStats,
        tmnxSubProfAccountingPolicyId,
        tmnxSubProfEgrAggRateLimit,
        tmnxSubProfRadiusAcctPolicy,
        tmnxSubProfDuplRadiusAcctPolicy,

        tmnxSubProfSchedOvrRowStatus,
        tmnxSubProfSchedOvrLastMgmtChange,
        tmnxSubProfSchedOvrPIR,
        tmnxSubProfSchedOvrCIR,
        tmnxSubProfSchedOvrSummedCIR,

        tmnxSubProfSLAProfMapRowStatus,
        tmnxSubProfSLAProfMapLastMgmtChange,
        tmnxSubProfSLAProfMapSLAProfile,

        tmnxSLAProfRowStatus,
        tmnxSLAProfLastMgmtChange,
        tmnxSLAProfDescription,
        tmnxSLAProfHostLimit,
        tmnxSLAProfRemoveOldest,
        tmnxSLAProfIngQosPolId,
        tmnxSLAProfIngSharedQPolicy,
        tmnxSLAProfIngUseMpointShared,
        tmnxSLAProfIngIPFilterId,
        tmnxSLAProfEgrQosPolId,
        tmnxSLAProfEgrIPFilterId,

        tmnxSLAIngQueueOvrRowStatus,
        tmnxSLAIngQueueOvrLastMgmtChange,
        tmnxSLAIngQueueOvrPIR,
        tmnxSLAIngQueueOvrCIR,
        tmnxSLAIngQueueOvrMBS,
        tmnxSLAIngQueueOvrCBS,
        tmnxSLAIngQueueOvrHiPrioOnly,

        tmnxSLAEgrQueueOvrRowStatus,
        tmnxSLAEgrQueueOvrLastMgmtChange,
        tmnxSLAEgrQueueOvrPIR,
        tmnxSLAEgrQueueOvrCIR,
        tmnxSLAEgrQueueOvrMBS,
        tmnxSLAEgrQueueOvrCBS,
        tmnxSLAEgrQueueOvrHiPrioOnly,
        tmnxSLAEgrQueueOvrAvgOverhead,

        tmnxSubExplicitMapRowStatus,
        tmnxSubExplicitMapLastMgmtChange,
        tmnxSubExplicitMapSubProfile,
        tmnxSubExplicitMapSLAProfile,
        tmnxSubExplicitMapAlias,

        tmnxSubIPolRowStatus,
        tmnxSubIPolLastMgmtChange,
        tmnxSubIPolDescription,
        tmnxSubIPolScript1URL,
        tmnxSubIPolScript1AdminState,
        tmnxSubIPolScript1OperState,
        tmnxSubIPolScript2URL,
        tmnxSubIPolScript2AdminState,
        tmnxSubIPolScript2OperState,
        tmnxSubIPolScript3URL,
        tmnxSubIPolScript3AdminState,
        tmnxSubIPolScript3OperState,

        tmnxSubIPolSubProfMapRowStatus,
        tmnxSubIPolSubProfMapLastMgmtChange,
        tmnxSubIPolSubProfMapSubProfile,

        tmnxSubIPolSLAProfMapRowStatus,
        tmnxSubIPolSLAProfMapLastMgmtChange,
        tmnxSubIPolSLAProfMapSLAProfile,

        tmnxSubInfoSubProfile,
        tmnxSubInfoSubAncpString,
        tmnxSubInfoNumSubProfileChanges,
        tmnxSubInfoModifySubIdent,

        tmnxSubHostInfoSubIdent,
        tmnxSubHostInfoSubProfile,
        tmnxSubHostInfoSLAProfile,
        tmnxSubHostInfoOrigin,
        tmnxSubHostInfoRetailerSvcId,
        tmnxSubHostInfoRetailerIf,
        tmnxSubHostInfoFwdingState,

        tmnxSubIngQosSchedStatsFwdPkts,
        tmnxSubIngQosSchedStatsFwdOctets,

        tmnxSubEgrQosSchedStatsFwdPkts,
        tmnxSubEgrQosSchedStatsFwdOctets,

        tmnxSPISubHostMacAddress,
        tmnxSPISubHostOrigin,

        tmnxSPIStatsIngPchipOffHiPrioPkts,
        tmnxSPIStatsIngPchipOffHiPrioOctets,
        tmnxSPIStatsIngPchipOffLoPrioPkts,
        tmnxSPIStatsIngPchipOffLoPrioOctets,
        tmnxSPIStatsIngPchipOffUncolPkts,
        tmnxSPIStatsIngPchipOffUncolOctets,
        tmnxSPIStatsIngQchipDropHiPrioPkts,
        tmnxSPIStatsIngQchipDropHiPrioOctets,
        tmnxSPIStatsIngQchipDropLoPrioPkts,
        tmnxSPIStatsIngQchipDropLoPrioOctets,
        tmnxSPIStatsIngQchipFwdInProfPkts,
        tmnxSPIStatsIngQchipFwdInProfOctets,
        tmnxSPIStatsIngQchipFwdOutProfPkts,
        tmnxSPIStatsIngQchipFwdOutProfOctets,
        tmnxSPIStatsEgrQchipDropInProfPkts,
        tmnxSPIStatsEgrQchipDropInProfOctets,
        tmnxSPIStatsEgrQchipDropOutProfPkts,
        tmnxSPIStatsEgrQchipDropOutProfOctets,
        tmnxSPIStatsEgrQchipFwdInProfPkts,
        tmnxSPIStatsEgrQchipFwdInProfOctets,
        tmnxSPIStatsEgrQchipFwdOutProfPkts,
        tmnxSPIStatsEgrQchipFwdOutProfOctets,

        tmnxSPIIngQStatsOffHiPrioPkts,
        tmnxSPIIngQStatsDropHiPrioPkts,
        tmnxSPIIngQStatsOffLoPrioPkts,
        tmnxSPIIngQStatsDropLoPrioPkts,
        tmnxSPIIngQStatsOffHiPrioOctets,
        tmnxSPIIngQStatsDropHiPrioOctets,
        tmnxSPIIngQStatsOffLoPrioOctets,
        tmnxSPIIngQStatsDropLoPrioOctets,
        tmnxSPIIngQStatsOffUncolPkts,
        tmnxSPIIngQStatsOffUncolOctets,
        tmnxSPIIngQStatsFwdInProfPkts,
        tmnxSPIIngQStatsFwdOutProfPkts,
        tmnxSPIIngQStatsFwdInProfOctets,
        tmnxSPIIngQStatsFwdOutProfOctets,

        tmnxSPIEgrQStatsFwdInProfPkts,
        tmnxSPIEgrQStatsDropInProfPkts,
        tmnxSPIEgrQStatsFwdOutProfPkts,
        tmnxSPIEgrQStatsDropOutProfPkts,
        tmnxSPIEgrQStatsFwdInProfOctets,
        tmnxSPIEgrQStatsDropInProfOctets,
        tmnxSPIEgrQStatsFwdOutProfOctets,
        tmnxSPIEgrQStatsDropOutProfOctets
    }
    STATUS      obsolete
    DESCRIPTION
        "The group of objects supporting management of subscriber profiles on
         release 5.0 of the Nokia SROS series systems."
    ::= { tmnxSubMgmtGroups 5 }

tmnxSubAuthentication7450V5v0Group   OBJECT-GROUP
    OBJECTS {
        tmnxSubAuthPlcyRowStatus,
        tmnxSubAuthPlcyLastMgmtChange,
        tmnxSubAuthPlcyDescription,
        tmnxSubAuthPlcyPassword,
        tmnxSubAuthPlcyRadAuthRetries,
        tmnxSubAuthPlcyRadAuthSrceAddr,
        tmnxSubAuthPlcyRadAuthSrceAddrTp,
        tmnxSubAuthPlcyRadAuthTimeout,
        tmnxSubAuthPlcyReAuthenticate,
        tmnxSubAuthPlcyUserNameFormat,
        tmnxSubAuthPlcyRadAuthVRtrID,
        tmnxSubAuthPlcyAcceptAuthChange,
        tmnxSubAuthPlcyInclAttributes,
        tmnxSubAuthPlcyRadAuthAlgorithm,

        tmnxSubAuthPlcyRadServRowStatus,
        tmnxSubAuthPlcyRadLastMgmtChange,
        tmnxSubAuthPlcyRadServAddress,
        tmnxSubAuthPlcyRadServAddrType,
        tmnxSubAuthPlcyRadServSecret,
        tmnxSubAuthPlcyRadServAuthPort,
        tmnxSubAuthPlcyRadServOperState,

        tmnxSubAuthPlcySuccess,
        tmnxSubAuthPlcyReject,

        tmnxSubAuthPlcyRadSuccess,
        tmnxSubAuthPlcyRadReject,
        tmnxSubAuthPlcyRadTimeout,
        tmnxSubAuthPlcyRadMd5Fail,
        tmnxSubAuthPlcyRadPending,
        tmnxSubAuthPlcyRadSendFail
    }
    STATUS      obsolete
    DESCRIPTION
        "The group of objects supporting management of subscriber
         authentication policies on Nokia 7450 SR series systems."
    ::= { tmnxSubMgmtGroups 6 }

tmnxSubAuthentication77x0V5v0Group   OBJECT-GROUP
    OBJECTS {
        tmnxSubAuthPlcyRowStatus,
        tmnxSubAuthPlcyLastMgmtChange,
        tmnxSubAuthPlcyDescription,
        tmnxSubAuthPlcyPassword,
        tmnxSubAuthPlcyRadAuthRetries,
        tmnxSubAuthPlcyRadAuthSrceAddr,
        tmnxSubAuthPlcyRadAuthSrceAddrTp,
        tmnxSubAuthPlcyRadAuthTimeout,
        tmnxSubAuthPlcyReAuthenticate,
        tmnxSubAuthPlcyUserNameFormat,
        tmnxSubAuthPlcyRadAuthVRtrID,
        tmnxSubAuthPlcyAcceptAuthChange,
        tmnxSubAuthPlcyInclAttributes,
        tmnxSubAuthPlcyRadAuthAlgorithm,

        tmnxSubAuthPlcyRadServRowStatus,
        tmnxSubAuthPlcyRadLastMgmtChange,
        tmnxSubAuthPlcyRadServAddress,
        tmnxSubAuthPlcyRadServAddrType,
        tmnxSubAuthPlcyRadServSecret,
        tmnxSubAuthPlcyRadServAuthPort,
        tmnxSubAuthPlcyRadServOperState,

        tmnxSubAuthPlcySuccess,
        tmnxSubAuthPlcyReject,

        tmnxSubAuthPlcyRadSuccess,
        tmnxSubAuthPlcyRadReject,
        tmnxSubAuthPlcyRadTimeout,
        tmnxSubAuthPlcyRadMd5Fail,
        tmnxSubAuthPlcyRadPending,
        tmnxSubAuthPlcyRadSendFail
    }
    STATUS      obsolete
    DESCRIPTION
        "The group of objects supporting management of subscriber
         authentication policies on Nokia 7750 SR and 7710 series systems."
    ::= { tmnxSubMgmtGroups 7 }

tmnxSubAccounting7450V5v0Group   OBJECT-GROUP
    OBJECTS {
        tmnxSubAcctPlcyRowStatus,
        tmnxSubAcctPlcyLastMgmtChange,
        tmnxSubAcctPlcyDescription,
        tmnxSubAcctPlcySessionIdFormat,
        tmnxSubAcctPlcyInclAttributes,
        tmnxSubAcctPlcyUpdateIvl,
        tmnxSubAcctPlcyServVRtrID,
        tmnxSubAcctPlcyServRetry,
        tmnxSubAcctPlcyServSrcAddrTp,
        tmnxSubAcctPlcyServSrcAddr,
        tmnxSubAcctPlcyServTimeout,
        tmnxSubAcctPlcyServAlgorithm,

        tmnxSubAcctPlcyRadServRowStatus,
        tmnxSubAcctPlcyRadServLstMgtChg,
        tmnxSubAcctPlcyRadServAddrType,
        tmnxSubAcctPlcyRadServAddr,
        tmnxSubAcctPlcyRadServSecret,
        tmnxSubAcctPlcyRadServAcctPort,
        tmnxSubAcctPlcyRadServOperState,

        tmnxSubAcctPlcyTxRequests,
        tmnxSubAcctPlcyRxResponses,
        tmnxSubAcctPlcyReqTimeouts,
        tmnxSubAcctPlcySendRetries,
        tmnxSubAcctPlcySendFail,

        tmnxSubAcctPlcyRadTxRequests,
        tmnxSubAcctPlcyRadRxResponses,
        tmnxSubAcctPlcyRadReqTimeouts,
        tmnxSubAcctPlcyRadReqSendFail
    }
    STATUS      obsolete
    DESCRIPTION
        "The group of objects supporting management of subscriber
         accounting policies on Nokia 7450 SR series systems."
    ::= { tmnxSubMgmtGroups 8 }

tmnxSubAccounting77x0V5v0Group   OBJECT-GROUP
    OBJECTS {
        tmnxSubAcctPlcyRowStatus,
        tmnxSubAcctPlcyLastMgmtChange,
        tmnxSubAcctPlcyDescription,
        tmnxSubAcctPlcySessionIdFormat,
        tmnxSubAcctPlcyInclAttributes,
        tmnxSubAcctPlcyUpdateIvl,
        tmnxSubAcctPlcyServVRtrID,
        tmnxSubAcctPlcyServRetry,
        tmnxSubAcctPlcyServSrcAddrTp,
        tmnxSubAcctPlcyServSrcAddr,
        tmnxSubAcctPlcyServTimeout,
        tmnxSubAcctPlcyServAlgorithm,

        tmnxSubAcctPlcyRadServRowStatus,
        tmnxSubAcctPlcyRadServLstMgtChg,
        tmnxSubAcctPlcyRadServAddrType,
        tmnxSubAcctPlcyRadServAddr,
        tmnxSubAcctPlcyRadServSecret,
        tmnxSubAcctPlcyRadServAcctPort,
        tmnxSubAcctPlcyRadServOperState,

        tmnxSubAcctPlcyTxRequests,
        tmnxSubAcctPlcyRxResponses,
        tmnxSubAcctPlcyReqTimeouts,
        tmnxSubAcctPlcySendRetries,
        tmnxSubAcctPlcySendFail,

        tmnxSubAcctPlcyRadTxRequests,
        tmnxSubAcctPlcyRadRxResponses,
        tmnxSubAcctPlcyRadReqTimeouts,
        tmnxSubAcctPlcyRadReqSendFail
    }
    STATUS      obsolete
    DESCRIPTION
        "The group of objects supporting management of subscriber
         accounting policies on Nokia 7750 SR and 7710 series systems."
    ::= { tmnxSubMgmtGroups 9 }

tmnxSubRadNotifStatsGroup   OBJECT-GROUP
    OBJECTS {
        tmnxSubRadNotifyStatsReceived,
        tmnxSubRadNotifyStatsAccepted,
        tmnxSubRadNotifyStatsRejected,
        tmnxSubRadNotifyStatsBadAuth,
        tmnxSubRadNotifyStatsNoNotify,
        tmnxSubRadNotifyStatsInvalidMsg,
        tmnxSubRadNotifyStatsNoResource,
        tmnxSubRadNotifyStatsUnknownHost
    }
    STATUS      obsolete
    DESCRIPTION
        "The group of objects supporting management of change-of-authorization
        notification statistics on Nokia SROS series systems."
    ::= { tmnxSubMgmtGroups 10 }

tmnxSubNotificationObjV5v0Group OBJECT-GROUP
    OBJECTS {
        tmnxSubAcctPlcyName,
        tmnxSubIdent,
        tmnxOldSubIdent,
        tmnxNewSubIdent,
        tmnxSubAcctPlcyFailureReason,
        tmnxSubMcsRelatedProblemDescr
    }
    STATUS      obsolete
    DESCRIPTION
        "The group of objects supporting management of notifications
         on Nokia SROS series systems."
    ::= { tmnxSubMgmtGroups 11 }

tmnxSubAuthenticationV6v0Group   OBJECT-GROUP
    OBJECTS {
        tmnxSubAuthPlcyRowStatus,
        tmnxSubAuthPlcyLastMgmtChange,
        tmnxSubAuthPlcyDescription,
        tmnxSubAuthPlcyPassword,
        tmnxSubAuthPlcyRadAuthRetries,
        tmnxSubAuthPlcyRadAuthSrceAddr,
        tmnxSubAuthPlcyRadAuthSrceAddrTp,
        tmnxSubAuthPlcyRadAuthTimeout,
        tmnxSubAuthPlcyReAuthenticate,
        tmnxSubAuthPlcyUserNameFormat,
        tmnxSubAuthPlcyRadAuthVRtrID,
        tmnxSubAuthPlcyAcceptAuthChange,
        tmnxSubAuthPlcyInclAttributes,
        tmnxSubAuthPlcyRadAuthAlgorithm,
        tmnxSubAuthPlcyPppoeAccessMethod,

        tmnxSubAuthPlcyRadServRowStatus,
        tmnxSubAuthPlcyRadLastMgmtChange,
        tmnxSubAuthPlcyRadServAddress,
        tmnxSubAuthPlcyRadServAddrType,
        tmnxSubAuthPlcyRadServSecret,
        tmnxSubAuthPlcyRadServAuthPort,
        tmnxSubAuthPlcyRadServOperState,

        tmnxSubAuthPlcySuccess,
        tmnxSubAuthPlcyReject,

        tmnxSubAuthPlcyRadSuccess,
        tmnxSubAuthPlcyRadReject,
        tmnxSubAuthPlcyRadTimeout,
        tmnxSubAuthPlcyRadMd5Fail,
        tmnxSubAuthPlcyRadPending,
        tmnxSubAuthPlcyRadSendFail
    }
    STATUS      obsolete
    DESCRIPTION
        "The group of objects supporting management of subscriber
         authentication policies on Nokia SROS series systems."
    ::= { tmnxSubMgmtGroups 12 }

tmnxSubAccountingV6v0Group   OBJECT-GROUP
    OBJECTS {
        tmnxSubAcctPlcyRowStatus,
        tmnxSubAcctPlcyLastMgmtChange,
        tmnxSubAcctPlcyDescription,
        tmnxSubAcctPlcySessionIdFormat,
        tmnxSubAcctPlcyInclAttributes,
        tmnxSubAcctPlcyUpdateIvl,
        tmnxSubAcctPlcyServVRtrID,
        tmnxSubAcctPlcyServRetry,
        tmnxSubAcctPlcyServSrcAddrTp,
        tmnxSubAcctPlcyServSrcAddr,
        tmnxSubAcctPlcyServTimeout,
        tmnxSubAcctPlcyServAlgorithm,

        tmnxSubAcctPlcyRadServRowStatus,
        tmnxSubAcctPlcyRadServLstMgtChg,
        tmnxSubAcctPlcyRadServAddrType,
        tmnxSubAcctPlcyRadServAddr,
        tmnxSubAcctPlcyRadServSecret,
        tmnxSubAcctPlcyRadServAcctPort,
        tmnxSubAcctPlcyRadServOperState,

        tmnxSubAcctPlcyTxRequests,
        tmnxSubAcctPlcyRxResponses,
        tmnxSubAcctPlcyReqTimeouts,
        tmnxSubAcctPlcySendRetries,
        tmnxSubAcctPlcySendFail,

        tmnxSubAcctPlcyRadTxRequests,
        tmnxSubAcctPlcyRadRxResponses,
        tmnxSubAcctPlcyRadReqTimeouts,
        tmnxSubAcctPlcyRadReqSendFail
    }
    STATUS      obsolete
    DESCRIPTION
        "The group of objects supporting management of subscriber
         accounting policies on Nokia SROS series systems."
    ::= { tmnxSubMgmtGroups 13 }

tmnxSubMgmtV6v0Group   OBJECT-GROUP
    OBJECTS {
        tmnxSubProfRowStatus,
        tmnxSubProfLastMgmtChange,
        tmnxSubProfDescription,
        tmnxSubProfIngQosSchedPolicy,
        tmnxSubProfEgrQosSchedPolicy,
        tmnxSubProfCollectAcctStats,
        tmnxSubProfAccountingPolicyId,
        tmnxSubProfEgrAggRateLimit,
        tmnxSubProfRadiusAcctPolicy,
        tmnxSubProfDuplRadiusAcctPolicy,
        tmnxSubProfUseDirectSLAMapAsDef,

        tmnxSubProfSchedOvrRowStatus,
        tmnxSubProfSchedOvrLastMgmtChange,
        tmnxSubProfSchedOvrPIR,
        tmnxSubProfSchedOvrCIR,
        tmnxSubProfSchedOvrSummedCIR,

        tmnxSubProfSLAProfMapRowStatus,
        tmnxSubProfSLAProfMapLastMgmtChange,
        tmnxSubProfSLAProfMapSLAProfile,

        tmnxSLAProfRowStatus,
        tmnxSLAProfLastMgmtChange,
        tmnxSLAProfDescription,
        tmnxSLAProfHostLimit,
        tmnxSLAProfRemoveOldest,
        tmnxSLAProfIngQosPolId,
        tmnxSLAProfIngSharedQPolicy,
        tmnxSLAProfIngUseMpointShared,
        tmnxSLAProfIngIPFilterId,
        tmnxSLAProfEgrQosPolId,
        tmnxSLAProfEgrIPFilterId,

        tmnxSLAIngQueueOvrRowStatus,
        tmnxSLAIngQueueOvrLastMgmtChange,
        tmnxSLAIngQueueOvrPIR,
        tmnxSLAIngQueueOvrCIR,
        tmnxSLAIngQueueOvrMBS,
        tmnxSLAIngQueueOvrCBS,
        tmnxSLAIngQueueOvrHiPrioOnly,

        tmnxSLAEgrQueueOvrRowStatus,
        tmnxSLAEgrQueueOvrLastMgmtChange,
        tmnxSLAEgrQueueOvrPIR,
        tmnxSLAEgrQueueOvrCIR,
        tmnxSLAEgrQueueOvrMBS,
        tmnxSLAEgrQueueOvrCBS,
        tmnxSLAEgrQueueOvrHiPrioOnly,
        tmnxSLAEgrQueueOvrAvgOverhead,

        tmnxSubExplicitMapRowStatus,
        tmnxSubExplicitMapLastMgmtChange,
        tmnxSubExplicitMapSubProfile,
        tmnxSubExplicitMapSLAProfile,
        tmnxSubExplicitMapAlias,

        tmnxSubIPolRowStatus,
        tmnxSubIPolLastMgmtChange,
        tmnxSubIPolDescription,
        tmnxSubIPolScript1URL,
        tmnxSubIPolScript1AdminState,
        tmnxSubIPolScript1OperState,
        tmnxSubIPolScript2URL,
        tmnxSubIPolScript2AdminState,
        tmnxSubIPolScript2OperState,
        tmnxSubIPolScript3URL,
        tmnxSubIPolScript3AdminState,
        tmnxSubIPolScript3OperState,
        tmnxSubIPolUseDirectSubMapAsDef,
        tmnxSubIPolUseDirectSLAMapAsDef,
        tmnxSubIPolStringsFromOption,

        tmnxSubIPolSubProfMapRowStatus,
        tmnxSubIPolSubProfMapLastMgmtChange,
        tmnxSubIPolSubProfMapSubProfile,

        tmnxSubIPolSLAProfMapRowStatus,
        tmnxSubIPolSLAProfMapLastMgmtChange,
        tmnxSubIPolSLAProfMapSLAProfile,

        tmnxSubInfoSubProfile,
        tmnxSubInfoSubAncpString,
        tmnxSubInfoNumSubProfileChanges,
        tmnxSubInfoIntermediateDestId,
        tmnxSubInfoModifySubIdent,

        tmnxSubHostInfoSubIdent,
        tmnxSubHostInfoSubProfile,
        tmnxSubHostInfoSLAProfile,
        tmnxSubHostInfoOrigin,
        tmnxSubHostInfoRetailerSvcId,
        tmnxSubHostInfoRetailerIf,
        tmnxSubHostInfoFwdingState,

        tmnxSubIngQosSchedStatsFwdPkts,
        tmnxSubIngQosSchedStatsFwdOctets,

        tmnxSubEgrQosSchedStatsFwdPkts,
        tmnxSubEgrQosSchedStatsFwdOctets,

        tmnxSPISubHostMacAddress,
        tmnxSPISubHostOrigin,

        tmnxSPIStatsIngPchipOffHiPrioPkts,
        tmnxSPIStatsIngPchipOffHiPrioOctets,
        tmnxSPIStatsIngPchipOffLoPrioPkts,
        tmnxSPIStatsIngPchipOffLoPrioOctets,
        tmnxSPIStatsIngPchipOffUncolPkts,
        tmnxSPIStatsIngPchipOffUncolOctets,
        tmnxSPIStatsIngQchipDropHiPrioPkts,
        tmnxSPIStatsIngQchipDropHiPrioOctets,
        tmnxSPIStatsIngQchipDropLoPrioPkts,
        tmnxSPIStatsIngQchipDropLoPrioOctets,
        tmnxSPIStatsIngQchipFwdInProfPkts,
        tmnxSPIStatsIngQchipFwdInProfOctets,
        tmnxSPIStatsIngQchipFwdOutProfPkts,
        tmnxSPIStatsIngQchipFwdOutProfOctets,
        tmnxSPIStatsEgrQchipDropInProfPkts,
        tmnxSPIStatsEgrQchipDropInProfOctets,
        tmnxSPIStatsEgrQchipDropOutProfPkts,
        tmnxSPIStatsEgrQchipDropOutProfOctets,
        tmnxSPIStatsEgrQchipFwdInProfPkts,
        tmnxSPIStatsEgrQchipFwdInProfOctets,
        tmnxSPIStatsEgrQchipFwdOutProfPkts,
        tmnxSPIStatsEgrQchipFwdOutProfOctets,

        tmnxSPIIngQStatsOffHiPrioPkts,
        tmnxSPIIngQStatsDropHiPrioPkts,
        tmnxSPIIngQStatsOffLoPrioPkts,
        tmnxSPIIngQStatsDropLoPrioPkts,
        tmnxSPIIngQStatsOffHiPrioOctets,
        tmnxSPIIngQStatsDropHiPrioOctets,
        tmnxSPIIngQStatsOffLoPrioOctets,
        tmnxSPIIngQStatsDropLoPrioOctets,
        tmnxSPIIngQStatsOffUncolPkts,
        tmnxSPIIngQStatsOffUncolOctets,
        tmnxSPIIngQStatsFwdInProfPkts,
        tmnxSPIIngQStatsFwdOutProfPkts,
        tmnxSPIIngQStatsFwdInProfOctets,
        tmnxSPIIngQStatsFwdOutProfOctets,

        tmnxSPIEgrQStatsFwdInProfPkts,
        tmnxSPIEgrQStatsDropInProfPkts,
        tmnxSPIEgrQStatsFwdOutProfPkts,
        tmnxSPIEgrQStatsDropOutProfPkts,
        tmnxSPIEgrQStatsFwdInProfOctets,
        tmnxSPIEgrQStatsDropInProfOctets,
        tmnxSPIEgrQStatsFwdOutProfOctets,
        tmnxSPIEgrQStatsDropOutProfOctets
    }
    STATUS      obsolete
    DESCRIPTION
        "The group of objects supporting management of subscriber profiles on
         release 6.0 of the Nokia SROS series systems."
    ::= { tmnxSubMgmtGroups 14 }

tmnxSubFrameBasedAccntV6v0Group OBJECT-GROUP
    OBJECTS {
        tmnxSubProfFrameBasedAccounting
   }
    STATUS      current
    DESCRIPTION
        "The group of subscriber management objects supporting management of
         frame-based queue accounting on Nokia SROS series systems
         release 6.0."
    ::= { tmnxSubMgmtGroups 15 }

tmnxSubBsxObjV6v0Group OBJECT-GROUP
    OBJECTS {
        tmnxSubExplicitMapAppProfile,
        tmnxSubIPolUseDirectAppMapAsDef,
        tmnxSubIPolAppProfMapRowStatus,
        tmnxSubIPolAppProfMapLastMgmtChange,
        tmnxSubIPolAppProfMapAppProfile,
        tmnxSubInfoAppProfile,
        tmnxSubHostInfoAppProfile
    }
    STATUS      obsolete
    DESCRIPTION
        "The group of objects supporting management of BSX (Application
         Assurance) Subscribers on Nokia SROS series systems."
    ::= { tmnxSubMgmtGroups 16 }

tmnxHsmdaSubscriberV6v0Group OBJECT-GROUP
    OBJECTS {
        tmnxSubInfoEgrSecShaper,
        tmnxSubProfIngQosPolId,
        tmnxSubProfEgrQosPolId,
        tmnxSubProfHsmdaIngAggRateLimit,
        tmnxSubProfHsmdaEgrAggRateLimit,
        tmnxSubProfHsmdaIngPackByteOff,
        tmnxSubProfHsmdaEgrPackByteOff,
        tmnxSubHsmdaIngQueueOvrTableLC,
        tmnxSubHsmdaIngQueueOvrRowStat,
        tmnxSubHsmdaIngQueueOvrLastChgd,
        tmnxSubHsmdaIngQueueOvrPIR,
        tmnxSubHsmdaIngQueueOvrCIR,
        tmnxSubHsmdaIngQueueOvrSlpPlcy,
        tmnxSubHsmdaEgrQueueOvrTblLC,
        tmnxSubHsmdaEgrQueueOvrRowStat,
        tmnxSubHsmdaEgrQueueOvrLastChgd,
        tmnxSubHsmdaEgrQueueOvrPIR,
        tmnxSubHsmdaEgrQueueOvrCIR,
        tmnxSubHsmdaEgrQueueOvrSlpPlcy,
        tmnxSubHsmdaStSubPortId,
        tmnxSubHsmdaStIngOffTotalPkt,
        tmnxSubHsmdaStIngOffTotalOct,
        tmnxSubHsmdaStIngFwdInProfPkt,
        tmnxSubHsmdaStIngFwdOutProfPkt,
        tmnxSubHsmdaStIngFwdInProfOct,
        tmnxSubHsmdaStIngFwdOutProfOct,
        tmnxSubHsmdaStIngDropHiPrioPkt,
        tmnxSubHsmdaStIngDropLoPrioPkt,
        tmnxSubHsmdaStIngDropHiPrioOct,
        tmnxSubHsmdaStIngDropLoPrioOct,
        tmnxSubHsmdaStEgrFwdInProfPkt,
        tmnxSubHsmdaStEgrFwdOutProfPkt,
        tmnxSubHsmdaStEgrFwdInProfOct,
        tmnxSubHsmdaStEgrFwdOutProfOct,
        tmnxSubHsmdaStEgrDropInProfPkt,
        tmnxSubHsmdaStEgrDropOutProfPkt,
        tmnxSubHsmdaStEgrDropInProfOct,
        tmnxSubHsmdaStEgrDropOutProfOct,
        tmnxSubIngQStatsSubPortId,
        tmnxSubIngQStatsOffTotalPkts,
        tmnxSubIngQStatsOffTotalOcts,
        tmnxSubIngQStatsFwdInProfPkts,
        tmnxSubIngQStatsFwdOutProfPkts,
        tmnxSubIngQStatsFwdInProfOcts,
        tmnxSubIngQStatsFwdOutProfOcts,
        tmnxSubIngQStatsDropHiPrioPkts,
        tmnxSubIngQStatsDropLoPrioPkts,
        tmnxSubIngQStatsDropHiPrioOcts,
        tmnxSubIngQStatsDropLoPrioOcts,
        tmnxSubEgrQStatsSubPortId,
        tmnxSubEgrQStatsFwdInProfPkts,
        tmnxSubEgrQStatsFwdOutProfPkts,
        tmnxSubEgrQStatsFwdInProfOcts,
        tmnxSubEgrQStatsFwdOutProfOcts,
        tmnxSubEgrQStatsDropInProfPkts,
        tmnxSubEgrQStatsDropOutProfPkts,
        tmnxSubEgrQStatsDropInProfOcts,
        tmnxSubEgrQStatsDropOutProfOcts,
        tmnxSubIngOvrCntrSubPortId,
        tmnxSubIngOvrCntrOffTotalPkts,
        tmnxSubIngOvrCntrOffTotalOcts,
        tmnxSubIngOvrCntrFwdInProfPkts,
        tmnxSubIngOvrCntrFwdOutProfPkts,
        tmnxSubIngOvrCntrFwdInProfOcts,
        tmnxSubIngOvrCntrFwdOutProfOcts,
        tmnxSubIngOvrCntrDropHiPrioPkts,
        tmnxSubIngOvrCntrDropLoPrioPkts,
        tmnxSubIngOvrCntrDropHiPrioOcts,
        tmnxSubIngOvrCntrDropLoPrioOcts,
        tmnxSubEgrOvrCntrSubPortId,
        tmnxSubEgrOvrCntrFwdInProfPkts,
        tmnxSubEgrOvrCntrFwdOutProfPkts,
        tmnxSubEgrOvrCntrFwdInProfOcts,
        tmnxSubEgrOvrCntrFwdOutProfOcts,
        tmnxSubEgrOvrCntrDropInProfPkts,
        tmnxSubEgrOvrCntrDropOutProfPkts,
        tmnxSubEgrOvrCntrDropInProfOcts,
        tmnxSubEgrOvrCntrDropOutProfOcts
    }
    STATUS      obsolete
    DESCRIPTION
        "The group of objects supporting management HSMDA-related of subscriber
         profiles on release 6.0 of the Nokia SROS series systems."
    ::= { tmnxSubMgmtGroups 17 }

tmnxSubNotificationObjV6v0Group OBJECT-GROUP
    OBJECTS {
        tmnxSubAcctPlcyName,
        tmnxSubIdent,
        tmnxOldSubIdent,
        tmnxNewSubIdent,
        tmnxSubAcctPlcyFailureReason,
        tmnxSubMcsRelatedProblemDescr,
        tmnxSubRadiusDisconnectReason,
        tmnxSubRadiusCoAReason,
        tmnxSubRadiusSubAuthReason
    }
    STATUS      obsolete
    DESCRIPTION
        "The group of objects supporting management of notifications
         on Nokia SROS series systems."
    ::= { tmnxSubMgmtGroups 18 }

tmnxSubAccountingV6v1Group   OBJECT-GROUP
    OBJECTS {
        tmnxSubAcctPlcyRowStatus,
        tmnxSubAcctPlcyLastMgmtChange,
        tmnxSubAcctPlcyDescription,
        tmnxSubAcctPlcySessionIdFormat,
        tmnxSubAcctPlcyInclAttributes,
        tmnxSubAcctPlcyUpdateIvl,
        tmnxSubAcctPlcyServVRtrID,
        tmnxSubAcctPlcyServRetry,
        tmnxSubAcctPlcyServSrcAddrTp,
        tmnxSubAcctPlcyServSrcAddr,
        tmnxSubAcctPlcyServTimeout,
        tmnxSubAcctPlcyServAlgorithm,
        tmnxSubAcctPlcyUseStdAcctAttrib,
        tmnxSubAcctPlcyNasPortPfixType,
        tmnxSubAcctPlcyNasPortPfixString,
        tmnxSubAcctPlcyNasPortSfixType,

        tmnxSubAcctPlcyRadServRowStatus,
        tmnxSubAcctPlcyRadServLstMgtChg,
        tmnxSubAcctPlcyRadServAddrType,
        tmnxSubAcctPlcyRadServAddr,
        tmnxSubAcctPlcyRadServSecret,
        tmnxSubAcctPlcyRadServAcctPort,
        tmnxSubAcctPlcyRadServOperState,

        tmnxSubAcctPlcyTxRequests,
        tmnxSubAcctPlcyRxResponses,
        tmnxSubAcctPlcyReqTimeouts,
        tmnxSubAcctPlcySendRetries,
        tmnxSubAcctPlcySendFail,

        tmnxSubAcctPlcyRadTxRequests,
        tmnxSubAcctPlcyRadRxResponses,
        tmnxSubAcctPlcyRadReqTimeouts,
        tmnxSubAcctPlcyRadReqSendFail
    }
    STATUS      obsolete
    DESCRIPTION
        "The group of objects supporting management of subscriber
         accounting policies on Nokia SROS series systems."
    ::= { tmnxSubMgmtGroups 19 }

tmnxSubAuthenticationV6v1Group   OBJECT-GROUP
    OBJECTS {
        tmnxSubAuthPlcyRowStatus,
        tmnxSubAuthPlcyLastMgmtChange,
        tmnxSubAuthPlcyDescription,
        tmnxSubAuthPlcyPassword,
        tmnxSubAuthPlcyRadAuthRetries,
        tmnxSubAuthPlcyRadAuthSrceAddr,
        tmnxSubAuthPlcyRadAuthSrceAddrTp,
        tmnxSubAuthPlcyRadAuthTimeout,
        tmnxSubAuthPlcyReAuthenticate,
        tmnxSubAuthPlcyUserNameFormat,
        tmnxSubAuthPlcyRadAuthVRtrID,
        tmnxSubAuthPlcyAcceptAuthChange,
        tmnxSubAuthPlcyInclAttributes,
        tmnxSubAuthPlcyRadAuthAlgorithm,
        tmnxSubAuthPlcyPppoeAccessMethod,
        tmnxSubAuthPlcyNasPortPfixType,
        tmnxSubAuthPlcyNasPortPfixString,
        tmnxSubAuthPlcyNasPortSfixType,

        tmnxSubAuthPlcyRadServRowStatus,
        tmnxSubAuthPlcyRadLastMgmtChange,
        tmnxSubAuthPlcyRadServAddress,
        tmnxSubAuthPlcyRadServAddrType,
        tmnxSubAuthPlcyRadServSecret,
        tmnxSubAuthPlcyRadServAuthPort,
        tmnxSubAuthPlcyRadServOperState,

        tmnxSubAuthPlcySuccess,
        tmnxSubAuthPlcyReject,

        tmnxSubAuthPlcyRadSuccess,
        tmnxSubAuthPlcyRadReject,
        tmnxSubAuthPlcyRadTimeout,
        tmnxSubAuthPlcyRadMd5Fail,
        tmnxSubAuthPlcyRadPending,
        tmnxSubAuthPlcyRadSendFail
    }
    STATUS      obsolete
    DESCRIPTION
        "The group of objects supporting management of subscriber
         authentication policies on Nokia SROS series systems."
    ::= { tmnxSubMgmtGroups 20 }

tmnxSubRadNotifStatsV6v0Group   OBJECT-GROUP
    OBJECTS {
        tmnxSubRadNotifyStatsReceived,
        tmnxSubRadNotifyStatsAccepted,
        tmnxSubRadNotifyStatsRejected,
        tmnxSubRadNotifyStatsBadAuth,
        tmnxSubRadNotifyStatsNoNotify,
        tmnxSubRadNotifyStatsInvalidMsg,
        tmnxSubRadNotifyStatsNoResource,
        tmnxSubRadNotifyStatsUnknownHost,
        tmnxSubNotifyDisMsgReceived,
        tmnxSubNotifyDisMsgAccepted,
        tmnxSubNotifyDisMsgRejected,
        tmnxSubNotifyDisMsgBadAuth,
        tmnxSubNotifyDisMsgNoNotify,
        tmnxSubNotifyDisMsgInvalidMsg,
        tmnxSubNotifyDisMsgNoResource,
        tmnxSubNotifyDisMsgUnknownHost
    }
    STATUS      current
    DESCRIPTION
        "The group of objects supporting management of change-of-authorization
        notification statistics on Nokia SROS series systems."
    ::= { tmnxSubMgmtGroups 21 }

tmnxSubMgmtV7v0Group   OBJECT-GROUP
    OBJECTS {
        tmnxSubProfRowStatus,
        tmnxSubProfLastMgmtChange,
        tmnxSubProfDescription,
        tmnxSubProfIngQosSchedPolicy,
        tmnxSubProfEgrQosSchedPolicy,
        tmnxSubProfCollectAcctStats,
        tmnxSubProfAccountingPolicyId,
        tmnxSubProfEgrAggRateLimit,
        tmnxSubProfRadiusAcctPolicy,
        tmnxSubProfDuplRadiusAcctPolicy,
        tmnxSubProfUseDirectSLAMapAsDef,

        tmnxSubProfSchedOvrRowStatus,
        tmnxSubProfSchedOvrLastMgmtChange,
        tmnxSubProfSchedOvrPIR,
        tmnxSubProfSchedOvrCIR,
        tmnxSubProfSchedOvrSummedCIR,

        tmnxSubProfSLAProfMapRowStatus,
        tmnxSubProfSLAProfMapLastMgmtChange,
        tmnxSubProfSLAProfMapSLAProfile,

        tmnxSLAProfRowStatus,
        tmnxSLAProfLastMgmtChange,
        tmnxSLAProfDescription,
        tmnxSLAProfHostLimit,
        tmnxSLAProfRemoveOldest,
        tmnxSLAProfIngQosPolId,
        tmnxSLAProfIngSharedQPolicy,
        tmnxSLAProfIngUseMpointShared,
        tmnxSLAProfIngIPFilterId,
        tmnxSLAProfEgrQosPolId,
        tmnxSLAProfEgrIPFilterId,
        tmnxSLAProfReportIngRateType,
        tmnxSLAProfReportIngRateSched,
        tmnxSLAProfReportEgrRateType,
        tmnxSLAProfReportEgrRateSched,
        tmnxSLAProfEgrQosMarkingFromSap,

        tmnxSLAIngQueueOvrRowStatus,
        tmnxSLAIngQueueOvrLastMgmtChange,
        tmnxSLAIngQueueOvrPIR,
        tmnxSLAIngQueueOvrCIR,
        tmnxSLAIngQueueOvrMBS,
        tmnxSLAIngQueueOvrCBS,
        tmnxSLAIngQueueOvrHiPrioOnly,

        tmnxSLAEgrQueueOvrRowStatus,
        tmnxSLAEgrQueueOvrLastMgmtChange,
        tmnxSLAEgrQueueOvrPIR,
        tmnxSLAEgrQueueOvrCIR,
        tmnxSLAEgrQueueOvrMBS,
        tmnxSLAEgrQueueOvrCBS,
        tmnxSLAEgrQueueOvrHiPrioOnly,
        tmnxSLAEgrQueueOvrAvgOverhead,

        tmnxSubExplicitMapRowStatus,
        tmnxSubExplicitMapLastMgmtChange,
        tmnxSubExplicitMapSubProfile,
        tmnxSubExplicitMapSLAProfile,
        tmnxSubExplicitMapAlias,

        tmnxSubIPolRowStatus,
        tmnxSubIPolLastMgmtChange,
        tmnxSubIPolDescription,
        tmnxSubIPolScript1URL,
        tmnxSubIPolScript1AdminState,
        tmnxSubIPolScript1OperState,
        tmnxSubIPolScript2URL,
        tmnxSubIPolScript2AdminState,
        tmnxSubIPolScript2OperState,
        tmnxSubIPolScript3URL,
        tmnxSubIPolScript3AdminState,
        tmnxSubIPolScript3OperState,
        tmnxSubIPolUseDirectSubMapAsDef,
        tmnxSubIPolUseDirectSLAMapAsDef,
        tmnxSubIPolStringsFromOption,

        tmnxSubIPolSubProfMapRowStatus,
        tmnxSubIPolSubProfMapLastMgmtChange,
        tmnxSubIPolSubProfMapSubProfile,

        tmnxSubIPolSLAProfMapRowStatus,
        tmnxSubIPolSLAProfMapLastMgmtChange,
        tmnxSubIPolSLAProfMapSLAProfile,

        tmnxSubInfoSubProfile,
        tmnxSubInfoSubAncpString,
        tmnxSubInfoNumSubProfileChanges,
        tmnxSubInfoIntermediateDestId,
        tmnxSubInfoModifySubIdent,

        tmnxSubIngQosSchedStatsFwdPkts,
        tmnxSubIngQosSchedStatsFwdOctets,

        tmnxSubEgrQosSchedStatsFwdPkts,
        tmnxSubEgrQosSchedStatsFwdOctets,

        tmnxSPIStatsIngPchipOffHiPrioPkts,
        tmnxSPIStatsIngPchipOffHiPrioOctets,
        tmnxSPIStatsIngPchipOffLoPrioPkts,
        tmnxSPIStatsIngPchipOffLoPrioOctets,
        tmnxSPIStatsIngPchipOffUncolPkts,
        tmnxSPIStatsIngPchipOffUncolOctets,
        tmnxSPIStatsIngQchipDropHiPrioPkts,
        tmnxSPIStatsIngQchipDropHiPrioOctets,
        tmnxSPIStatsIngQchipDropLoPrioPkts,
        tmnxSPIStatsIngQchipDropLoPrioOctets,
        tmnxSPIStatsIngQchipFwdInProfPkts,
        tmnxSPIStatsIngQchipFwdInProfOctets,
        tmnxSPIStatsIngQchipFwdOutProfPkts,
        tmnxSPIStatsIngQchipFwdOutProfOctets,
        tmnxSPIStatsEgrQchipDropInProfPkts,
        tmnxSPIStatsEgrQchipDropInProfOctets,
        tmnxSPIStatsEgrQchipDropOutProfPkts,
        tmnxSPIStatsEgrQchipDropOutProfOctets,
        tmnxSPIStatsEgrQchipFwdInProfPkts,
        tmnxSPIStatsEgrQchipFwdInProfOctets,
        tmnxSPIStatsEgrQchipFwdOutProfPkts,
        tmnxSPIStatsEgrQchipFwdOutProfOctets,

        tmnxSPIIngQStatsOffHiPrioPkts,
        tmnxSPIIngQStatsDropHiPrioPkts,
        tmnxSPIIngQStatsOffLoPrioPkts,
        tmnxSPIIngQStatsDropLoPrioPkts,
        tmnxSPIIngQStatsOffHiPrioOctets,
        tmnxSPIIngQStatsDropHiPrioOctets,
        tmnxSPIIngQStatsOffLoPrioOctets,
        tmnxSPIIngQStatsDropLoPrioOctets,
        tmnxSPIIngQStatsOffUncolPkts,
        tmnxSPIIngQStatsOffUncolOctets,
        tmnxSPIIngQStatsFwdInProfPkts,
        tmnxSPIIngQStatsFwdOutProfPkts,
        tmnxSPIIngQStatsFwdInProfOctets,
        tmnxSPIIngQStatsFwdOutProfOctets,

        tmnxSPIEgrQStatsFwdInProfPkts,
        tmnxSPIEgrQStatsDropInProfPkts,
        tmnxSPIEgrQStatsFwdOutProfPkts,
        tmnxSPIEgrQStatsDropOutProfPkts,
        tmnxSPIEgrQStatsFwdInProfOctets,
        tmnxSPIEgrQStatsDropInProfOctets,
        tmnxSPIEgrQStatsFwdOutProfOctets,
        tmnxSPIEgrQStatsDropOutProfOctets,

        tmnxSubHostInfoV2FwdingState,
        tmnxSubHostInfoV2Origin,
        tmnxSubHostInfoV2SubIdent,
        tmnxSubHostInfoV2SubProfile,
        tmnxSubHostInfoV2SLAProfile,
        tmnxSubHostInfoV2RetailerSvcId,
        tmnxSubHostInfoV2RetailerIf,

        tmnxSPISubHostV2Origin,

        tmnxSPIInfoCategoryMapName
    }
    STATUS      obsolete
    DESCRIPTION
        "The group of objects supporting management of subscriber profiles on
         release 7.0 of the Nokia SROS series systems."
    ::= { tmnxSubMgmtGroups 22 }

tmnxSubBsxObjV7v0Group OBJECT-GROUP
    OBJECTS {
        tmnxSubExplicitMapAppProfile,
        tmnxSubIPolUseDirectAppMapAsDef,
        tmnxSubIPolAppProfMapRowStatus,
        tmnxSubIPolAppProfMapLastMgmtChange,
        tmnxSubIPolAppProfMapAppProfile,
        tmnxSubInfoAppProfile,
        tmnxSubHostInfoV2AppProfile
    }
    STATUS      obsolete
    DESCRIPTION
        "The group of objects supporting management of BSX (Application
         Assurance) Subscribers on Nokia SROS series systems."
    ::= { tmnxSubMgmtGroups 23 }

tmnxSubHostTrackingGroup OBJECT-GROUP
    OBJECTS {
        tmnxSubTrkPlcyRowStatus,
        tmnxSubTrkPlcyLastMgmtChange,
        tmnxSubTrkPlcyDescription,
        tmnxSubTrkPlcyEgrRateModType,
        tmnxSubTrkPlcyEgrRateModSched,
        tmnxSubProfHostTrackingPolicy,
        tmnxSubTrkStatusPlcyName,
        tmnxSubTrkStatusEgrRateReduction,
        tmnxSubHostTrkUpTime,
        tmnxSubHostTrkExpiryTime,
        tmnxSubHostTrkBw,
        tmnxSubHostSapTrkUpTime,
        tmnxSubHostSapTrkExpiryTime,
        tmnxSubHostSapTrkBw,
        tmnxSubHostSapTrkSubIdent,
        tmnxSubHostGrpTrkUpTime,
        tmnxSubHostGrpTrkExpiryTime,
        tmnxSubHostGrpTrkSubIdent,
        tmnxSubGrpTrkUpTime,
        tmnxSubGrpTrkExpiryTime,
        tmnxSubGrpTrkBw,
        tmnxSubTrkPlcySubscriberId,
        tmnxSubHostSapTrkStatsVal,
        tmnxSubHostTrkStatsVal
    }
    STATUS      obsolete
    DESCRIPTION
        "The group of subscriber management objects supporting management of
         multicast Host Tracking on Nokia SROS series systems."
    ::= { tmnxSubMgmtGroups 24 }

tmnxSubRadusPlcyCustomRecordV7v0Group OBJECT-GROUP
    OBJECTS {
        tmnxSubApCrLastChanged,
        tmnxSubApCrSignChangeDelta,
        tmnxSubApCrSignChangeQueue,
        tmnxSubApCrSignChangeOCntr,
        tmnxSubApCrSignChangeQICounters,
        tmnxSubApCrSignChangeQECounters,
        tmnxSubApCrSignChangeOICounters,
        tmnxSubApCrSignChangeOECounters,
        tmnxSubApCrQueueRowStatus,
        tmnxSubApCrQueueLastChanged,
        tmnxSubApCrQueueICounters,
        tmnxSubApCrQueueECounters,
        tmnxSubApCrOverrideCntrRowStatus,
        tmnxSubApCrOverrideCntrLastChngd,
        tmnxSubApCrOverrideCntrICounters,
        tmnxSubApCrOverrideCntrECounters,
        tmnxSubApCustRecordLastChnge,
        tmnxSubApCustRecQueueLastChnge,
        tmnxSubApCustRecOvrCtrLastChnge
    }
    STATUS      current
    DESCRIPTION
        "The group of subscriber management objects supporting management of
         custom records for radius accounting on Nokia SROS series systems."
    ::= { tmnxSubMgmtGroups 25 }

tmnxSubCreditControlV7v0Group OBJECT-GROUP
    OBJECTS {
       tmnxSubApCCPlcyTableLastChnge,
       tmnxSubCcPlcyRowStatus,
       tmnxSubCcPlcyLastChngd,
       tmnxSubCcPlcyDescription,
       tmnxSubCcPlcyDiameterPlcy,
       tmnxSubCcPlcyDefaultCategoryMap,
       tmnxSubCcPlcyOutOfCreditAction,
       tmnxSubCcPlcyErrorHandlingAction,

       tmnxSLAProfCreditControlPlcy,

       tmnxSubApCategoryMapTblLstChnge,
       tmnxSubApCMapRowStatus,
       tmnxSubApCMapLastChngd,
       tmnxSubApCMapDescription,
       tmnxSubApCMapCreditType,
       tmnxSubApCMapCreditExhstThrshld,
       tmnxSubApCMapActivityThreshold,

       tmnxSubApCategoryTblLstChnge,
       tmnxSubApCategoryRowStatus,
       tmnxSubApCategoryLastChngd,
       tmnxSubApCategoryDescription,
       tmnxSubApCategoryIngressQueues,
       tmnxSubApCategoryEgressQueues,
       tmnxSubApCategoryUseRatingGroup,
       tmnxSubApCategoryRatingGroup,
       tmnxSubApCategoryCTypeOverride,
       tmnxSubApCategoryDfltCrdtVolume,
       tmnxSubApCategoryDfltCrdtVolUnit,
       tmnxSubApCategoryDfltCrdtTime,
       tmnxSubApCategoryOutOfCrdtAction,
       tmnxSubApCategoryPir,
      
       tmnxSPICatMapName,
       tmnxSPICatCreditControlPlcy,
       tmnxSPICatCrdtVolumeUsed,
       tmnxSPICatCrdtVolumeAvail,
       tmnxSPICatCrdtVolumeThres,
       tmnxSPICatCrdtTimeUsed,
       tmnxSPICatCrdtTimeAvail,
       tmnxSPICatCrdtTimeThres,
       tmnxSPICatCrdtExpired,
       tmnxSPICatCrdtNegotiating,
       tmnxSPICatOutOfCrdtAction,
       tmnxSPICatQuotaHoldingTime,
       tmnxSPICatCrdtReset,
       tmnxSLAProfCatLastMgmtChange,
       tmnxSLAProfCatRowStatus,
       tmnxSLAProfCatTimeout
    }
    STATUS      obsolete
    DESCRIPTION
        "The group of subscriber management objects supporting management of
         the credit control feature on Nokia SROS series systems."
    ::= { tmnxSubMgmtGroups 26 }

tmnxSubAuthenticationV7v0Group   OBJECT-GROUP
    OBJECTS {
        tmnxSubAuthPlcyRowStatus,
        tmnxSubAuthPlcyLastMgmtChange,
        tmnxSubAuthPlcyDescription,
        tmnxSubAuthPlcyPassword,
        tmnxSubAuthPlcyRadAuthRetries,
        tmnxSubAuthPlcyRadAuthSrceAddr,
        tmnxSubAuthPlcyRadAuthSrceAddrTp,
        tmnxSubAuthPlcyRadAuthTimeout,
        tmnxSubAuthPlcyReAuthenticate,
        tmnxSubAuthPlcyUserNameFormat,
        tmnxSubAuthPlcyRadAuthVRtrID,
        tmnxSubAuthPlcyAcceptAuthChange,
        tmnxSubAuthPlcyInclAttributes,
        tmnxSubAuthPlcyRadAuthAlgorithm,
        tmnxSubAuthPlcyPppoeAccessMethod,
        tmnxSubAuthPlcyNasPortPfixType,
        tmnxSubAuthPlcyNasPortPfixString,
        tmnxSubAuthPlcyNasPortSfixType,
        tmnxSubAuthPlcyUserNameAppend,

        tmnxSubAuthPlcyRadServRowStatus,
        tmnxSubAuthPlcyRadLastMgmtChange,
        tmnxSubAuthPlcyRadServAddress,
        tmnxSubAuthPlcyRadServAddrType,
        tmnxSubAuthPlcyRadServSecret,
        tmnxSubAuthPlcyRadServAuthPort,
        tmnxSubAuthPlcyRadServOperState,

        tmnxSubAuthPlcySuccess,
        tmnxSubAuthPlcyReject,

        tmnxSubAuthPlcyRadSuccess,
        tmnxSubAuthPlcyRadReject,
        tmnxSubAuthPlcyRadTimeout,
        tmnxSubAuthPlcyRadMd5Fail,
        tmnxSubAuthPlcyRadPending,
        tmnxSubAuthPlcyRadSendFail
    }
    STATUS      obsolete
    DESCRIPTION
        "The group of objects supporting management of subscriber
         authentication policies on Nokia SROS series systems."
    ::= { tmnxSubMgmtGroups 27 }

tmnxSubAuthenticationV8v0Group   OBJECT-GROUP
    OBJECTS {
        tmnxSubAuthPlcyRowStatus,
        tmnxSubAuthPlcyLastMgmtChange,
        tmnxSubAuthPlcyDescription,
        tmnxSubAuthPlcyPassword,
        tmnxSubAuthPlcyRadAuthRetries,
        tmnxSubAuthPlcyRadAuthSrceAddr,
        tmnxSubAuthPlcyRadAuthSrceAddrTp,
        tmnxSubAuthPlcyRadAuthTimeout,
        tmnxSubAuthPlcyReAuthenticate,
        tmnxSubAuthPlcyUserNameFormat,
        tmnxSubAuthPlcyRadAuthVRtrID,
        tmnxSubAuthPlcyAcceptAuthChange,
        tmnxSubAuthPlcyInclAttributes,
        tmnxSubAuthPlcyRadAuthAlgorithm,
        tmnxSubAuthPlcyPppoeAccessMethod,
        tmnxSubAuthPlcyNasPortPfixType,
        tmnxSubAuthPlcyNasPortPfixString,
        tmnxSubAuthPlcyNasPortSfixType,
        tmnxSubAuthPlcyUserNameAppend,
        tmnxSubAuthPlcyFallbackAction,
        tmnxSubAuthPlcyFallbackUserDb,
        tmnxSubAuthPlcyClngStationIdType,
        tmnxSubAuthPlcyNasPortTypeType,
        tmnxSubAuthPlcyNasPortTypeValue,
        tmnxSubAuthPlcyPppUserNameOp,
        tmnxSubAuthPlcyPppDomain,
        tmnxSubAuthPlcyRadAuthDownTime,

        tmnxSubAuthPlcyRadServRowStatus,
        tmnxSubAuthPlcyRadLastMgmtChange,
        tmnxSubAuthPlcyRadServAddress,
        tmnxSubAuthPlcyRadServAddrType,
        tmnxSubAuthPlcyRadServSecret,
        tmnxSubAuthPlcyRadServAuthPort,
        tmnxSubAuthPlcyRadServOperState,
        tmnxSubAuthPlcyRadServCoAOnly,

        tmnxSubAuthPlcySuccess,
        tmnxSubAuthPlcyReject,
        tmnxSubAuthPlcyFallbackSuccess,
        tmnxSubAuthPlcyFallbackReject,

        tmnxSubAuthPlcyRadSuccess,
        tmnxSubAuthPlcyRadReject,
        tmnxSubAuthPlcyRadTimeout,
        tmnxSubAuthPlcyRadMd5Fail,
        tmnxSubAuthPlcyRadPending,
        tmnxSubAuthPlcyRadSendFail,

        tmnxSubAuthPlcyRadRespAttrSelect,
        tmnxSubRadiusAcceptRowStatus,
        tmnxSubRadiusAcceptLastMgmtCh,
        tmnxSubRadiusAcceptSelective,
        tmnxSubAuthPlcyUserNameOp,    
        tmnxSubAuthPlcyDomain,
        tmnxSubAuthPlcyUserNameMacFormat
    }
    STATUS      obsolete
    DESCRIPTION
        "The group of objects supporting management of subscriber
         authentication policies on Nokia SROS series systems
         in release 8.0."
    ::= { tmnxSubMgmtGroups 31 }

tmnxSubNotificationObjV7v0Group OBJECT-GROUP
    OBJECTS {
        tmnxSubAcctPlcyName,
        tmnxSubIdent,
        tmnxOldSubIdent,
        tmnxNewSubIdent,
        tmnxSubAcctPlcyFailureReason,
        tmnxSubMcsRelatedProblemDescr,
        tmnxSubRadiusDisconnectReason,
        tmnxSubRadiusCoAReason,
        tmnxSubRadiusSubAuthReason,
        tmnxSubNotifSLAProfName,
        tmnxSubNotifApCMapName,
        tmnxSubNotifApCategoryName,
        tmnxSubNotifMacAddr,
        tmnxSubNotifIpAddrType,
        tmnxSubNotifIpAddr,
        tmnxSubAdditionalInfo
    }
    STATUS      current
    DESCRIPTION
        "The group of objects supporting management of notifications
         on Nokia SROS series systems."
    ::= { tmnxSubMgmtGroups 28 }

tmnxSubObsoletedV7v0Group OBJECT-GROUP
    OBJECTS {
        tmnxSPISubHostMacAddress,
        tmnxSPISubHostOrigin,
        tmnxSubHostInfoSubIdent,
        tmnxSubHostInfoSubProfile,
        tmnxSubHostInfoSLAProfile,
        tmnxSubHostInfoOrigin,
        tmnxSubHostInfoRetailerSvcId,
        tmnxSubHostInfoRetailerIf,
        tmnxSubHostInfoFwdingState,
        tmnxSubHostInfoAppProfile
    }
    STATUS      current
    DESCRIPTION
        "The group of obsoleted objects for subscriber management on
         Nokia SROS series systems."
    ::= { tmnxSubMgmtGroups 29 }

tmnxSubObsoletedV8v0Group OBJECT-GROUP
    OBJECTS {
        tmnxSPISubHostMacAddress,
        tmnxSPISubHostOrigin,
        tmnxSubHostInfoSubIdent,
        tmnxSubHostInfoSubProfile,
        tmnxSubHostInfoSLAProfile,
        tmnxSubHostInfoOrigin,
        tmnxSubHostInfoRetailerSvcId,
        tmnxSubHostInfoRetailerIf,
        tmnxSubHostInfoFwdingState,
        tmnxSubHostInfoAppProfile,
        tmnxSLAIngQueueOvrMBS,
        tmnxSLAEgrQueueOvrMBS
    }
    STATUS      current
    DESCRIPTION
        "The group of obsoleted objects for subscriber management on
         Nokia SROS series systems."
    ::= { tmnxSubMgmtGroups 30 }


tmnxCcIpFltrV8v0Group OBJECT-GROUP
    OBJECTS {
        tmnxCcIpFltrRowStatus,
        tmnxCcIpFltrLastChanged,
        tmnxCcIpFltrDescription,
        tmnxCcIpFltrAction,
        tmnxCcIpFltrRedirectURL,
        tmnxCcIpFltrProtocol,
        tmnxCcIpFltrDSCP,
        tmnxCcIpFltrSourceIpAddr,
        tmnxCcIpFltrSourceIpMask,
        tmnxCcIpFltrDestinationIpAddr,
        tmnxCcIpFltrDestinationIpMask,
        tmnxCcIpFltrSourcePortValue1,
        tmnxCcIpFltrSourcePortValue2,
        tmnxCcIpFltrSourcePortOperator,
        tmnxCcIpFltrDestPortValue1,
        tmnxCcIpFltrDestPortValue2,
        tmnxCcIpFltrDestPortOperator,
        tmnxCcIpFltrFragment,
        tmnxCcIpFltrIcmpCode,
        tmnxCcIpFltrIcmpType,
        tmnxCcIpFltrIpOptionValue,
        tmnxCcIpFltrIpOptionMask,
        tmnxCcIpFltrMultipleOption,
        tmnxCcIpFltrOptionPresent,
        tmnxCcIpFltrTcpSyn,
        tmnxCcIpFltrTcpAck,
        tmnxCcIpFltrTableLastChange
    }
    STATUS      current
    DESCRIPTION
        "The group of objects supporting credit-based filtering on 
         Nokia SROS series systems."
    ::= { tmnxSubMgmtGroups 32 }

tmnxCcIpv6FltrV8v0Group OBJECT-GROUP
    OBJECTS {
        tmnxCcIpv6FltrRowStatus,
        tmnxCcIpv6FltrLastChanged,
        tmnxCcIpv6FltrDescription,
        tmnxCcIpv6FltrAction,
        tmnxCcIpv6FltrRedirectURL,
        tmnxCcIpv6FltrNextHeader,
        tmnxCcIpv6FltrDSCP,
        tmnxCcIpv6FltrSourceIpAddr,
        tmnxCcIpv6FltrSourceIpMask,
        tmnxCcIpv6FltrDestinationIpAddr,
        tmnxCcIpv6FltrDestinationIpMask,
        tmnxCcIpv6FltrSourcePortValue1,
        tmnxCcIpv6FltrSourcePortValue2,
        tmnxCcIpv6FltrSourcePortOperator,
        tmnxCcIpv6FltrDestPortValue1,
        tmnxCcIpv6FltrDestPortValue2,
        tmnxCcIpv6FltrDestPortOperator,
        tmnxCcIpv6FltrIcmpCode,
        tmnxCcIpv6FltrIcmpType,
        tmnxCcIpv6FltrTcpSyn,
        tmnxCcIpv6FltrTcpAck,
        tmnxCcIpv6FltrTableLastChange
    }
    STATUS      current
    DESCRIPTION
        "The group of objects supporting credit-based filtering on 
         Nokia SROS series systems."
    ::= { tmnxSubMgmtGroups 33 }

tmnxSubV6GrpIfRAV8v0Group OBJECT-GROUP
    OBJECTS {
        tmnxSubV6GrpIfRATableLastChange,
        tmnxSubV6GrpIfRALastChanged,
        tmnxSubV6GrpIfRAAdminState,
        tmnxSubV6GrpIfRACurHopLimit,
        tmnxSubV6GrpIfRAManagedCfg,
        tmnxSubV6GrpIfRAMaxInterval,
        tmnxSubV6GrpIfRAMinInterval,
        tmnxSubV6GrpIfRALinkMTU,
        tmnxSubV6GrpIfRAOtherCfg,
        tmnxSubV6GrpIfRAPfxOptAutonomous,
        tmnxSubV6GrpIfRAPfxOptPrefLtime,
        tmnxSubV6GrpIfRAPfxOptValidLtime,
        tmnxSubV6GrpIfRAReachableTime,
        tmnxSubV6GrpIfRARetransmitTime,
        tmnxSubV6GrpIfRARouterLifetime
    }
    STATUS      obsolete
    DESCRIPTION
        "Group of objects supporting IPv6 Router Advertisements for Neighbor 
         Discovery for Group Interfaces on Nokia SROS series systems."
    ::= { tmnxSubMgmtGroups 34 }

tmnxSubMgmtIPv6V8v0Group OBJECT-GROUP
    OBJECTS {
        tmnxSLAProfEgrIPv6FilterId,
        tmnxSLAProfIngIPv6FilterId
    }
    STATUS      current
    DESCRIPTION
        "Group of objects supporting IPv6 on Nokia SROS series 
         systems."
    ::= { tmnxSubMgmtGroups 35 }

tmnxSubProfileMssExtensionsGroup OBJECT-GROUP
    OBJECTS {
        tmnxSubProfUseSubscriberMss,
        tmnxSubInfoMssName,
        tmnxSubInfoMssCustId
    }
    STATUS      current
    DESCRIPTION
        "The group of subscriber management objects supporting
         multi-service-site extensions on Nokia SROS series systems."
    ::= { tmnxSubMgmtGroups 36 }

tmnxSubAccountingV8v0Group   OBJECT-GROUP
    OBJECTS {
        tmnxSubAcctPlcyRowStatus,
        tmnxSubAcctPlcyLastMgmtChange,
        tmnxSubAcctPlcyDescription,
        tmnxSubAcctPlcySessionIdFormat,
        tmnxSubAcctPlcyInclAttributes,
        tmnxSubAcctPlcyUpdateIvl,
        tmnxSubAcctPlcyServVRtrID,
        tmnxSubAcctPlcyServRetry,
        tmnxSubAcctPlcyServSrcAddrTp,
        tmnxSubAcctPlcyServSrcAddr,
        tmnxSubAcctPlcyServTimeout,
        tmnxSubAcctPlcyServAlgorithm,
        tmnxSubAcctPlcyUseStdAcctAttrib,
        tmnxSubAcctPlcyNasPortPfixType,
        tmnxSubAcctPlcyNasPortPfixString,
        tmnxSubAcctPlcyNasPortSfixType,
        tmnxSubAcctPlcyNasPortTypeType,
        tmnxSubAcctPlcyNasPortTypeValue,

        tmnxSubAcctPlcyHostAccounting,
        tmnxSubAcctPlcyClngStationIdType,
        tmnxSubAcctPlcyNasPortBitspec,

        tmnxSubAcctPlcyRadServRowStatus,
        tmnxSubAcctPlcyRadServLstMgtChg,
        tmnxSubAcctPlcyRadServAddrType,
        tmnxSubAcctPlcyRadServAddr,
        tmnxSubAcctPlcyRadServSecret,
        tmnxSubAcctPlcyRadServAcctPort,
        tmnxSubAcctPlcyRadServOperState,

        tmnxSubAcctPlcyTxRequests,
        tmnxSubAcctPlcyRxResponses,
        tmnxSubAcctPlcyReqTimeouts,
        tmnxSubAcctPlcySendRetries,
        tmnxSubAcctPlcySendFail,

        tmnxSubAcctPlcyRadTxRequests,
        tmnxSubAcctPlcyRadRxResponses,
        tmnxSubAcctPlcyRadReqTimeouts,
        tmnxSubAcctPlcyRadReqSendFail
    }
    STATUS      obsolete
    DESCRIPTION
        "The group of objects supporting management of subscriber
         accounting policies on Nokia SROS series systems."
    ::= { tmnxSubMgmtGroups 37 }

tmnxSubProfileV8v0Group   OBJECT-GROUP
    OBJECTS {
       tmnxSubProfEgrPolicerPolicy,
       tmnxSubProfIngPolicerPolicy,
       tmnxSubProfIgmpPolicy,
       tmnxSubProfEgrAvgFrameSize,
       tmnxSubProfEgrEncapOffsetMode,
       tmnxSubProfEgrEncapOffset,
       tmnxSubProfSubMcacPolicy
    }
    STATUS      obsolete
    DESCRIPTION
        "The group of objects supporting management of subscriber
         profile feature on Nokia SROS series systems."
    ::= { tmnxSubMgmtGroups 38 }

tmnxSubNatGroup   OBJECT-GROUP
    OBJECTS {
       tmnxSubProfNatPolicy
    }
    STATUS      current
    DESCRIPTION
        "The group of objects supporting management of subscriber
         NAT (Network Address Translation) on Nokia SROS series 
         systems."
    ::= { tmnxSubMgmtGroups 39 }

tmnxSubMgmtV8v0Group   OBJECT-GROUP
    OBJECTS {
        tmnxSubProfRowStatus,
        tmnxSubProfLastMgmtChange,
        tmnxSubProfDescription,
        tmnxSubProfIngQosSchedPolicy,
        tmnxSubProfEgrQosSchedPolicy,
        tmnxSubProfCollectAcctStats,
        tmnxSubProfAccountingPolicyId,
        tmnxSubProfEgrAggRateLimit,
        tmnxSubProfRadiusAcctPolicy,
        tmnxSubProfDuplRadiusAcctPolicy,
        tmnxSubProfUseDirectSLAMapAsDef,

        tmnxSubProfSchedOvrRowStatus,
        tmnxSubProfSchedOvrLastMgmtChange,
        tmnxSubProfSchedOvrPIR,
        tmnxSubProfSchedOvrCIR,
        tmnxSubProfSchedOvrSummedCIR,

        tmnxSubProfSLAProfMapRowStatus,
        tmnxSubProfSLAProfMapLastMgmtChange,
        tmnxSubProfSLAProfMapSLAProfile,

        tmnxSLAProfRowStatus,
        tmnxSLAProfLastMgmtChange,
        tmnxSLAProfDescription,
        tmnxSLAProfHostLimit,
        tmnxSLAProfRemoveOldest,
        tmnxSLAProfIngQosPolId,
        tmnxSLAProfIngSharedQPolicy,
        tmnxSLAProfIngUseMpointShared,
        tmnxSLAProfIngIPFilterId,
        tmnxSLAProfEgrQosPolId,
        tmnxSLAProfEgrIPFilterId,
        tmnxSLAProfReportIngRateType,
        tmnxSLAProfReportIngRateSched,
        tmnxSLAProfReportEgrRateType,
        tmnxSLAProfReportEgrRateSched,
        tmnxSLAProfEgrQosMarkingFromSap,
        tmnxSLAProfEgrSchedulerType,

        tmnxSLAIngQueueOvrRowStatus,
        tmnxSLAIngQueueOvrLastMgmtChange,
        tmnxSLAIngQueueOvrPIR,
        tmnxSLAIngQueueOvrCIR,
        tmnxSLAIngQueueOvrCBS,
        tmnxSLAIngQueueOvrHiPrioOnly,
        tmnxSLAIngQueueOvrMBSBytes,

        tmnxSLAEgrQueueOvrRowStatus,
        tmnxSLAEgrQueueOvrLastMgmtChange,
        tmnxSLAEgrQueueOvrPIR,
        tmnxSLAEgrQueueOvrCIR,
        tmnxSLAEgrQueueOvrCBS,
        tmnxSLAEgrQueueOvrHiPrioOnly,
        tmnxSLAEgrQueueOvrAvgOverhead,
        tmnxSLAEgrQueueOvrMBSBytes,

        tmnxSubExplicitMapRowStatus,
        tmnxSubExplicitMapLastMgmtChange,
        tmnxSubExplicitMapSubProfile,
        tmnxSubExplicitMapSLAProfile,
        tmnxSubExplicitMapAlias,

        tmnxSubIPolRowStatus,
        tmnxSubIPolLastMgmtChange,
        tmnxSubIPolDescription,
        tmnxSubIPolScript1URL,
        tmnxSubIPolScript1AdminState,
        tmnxSubIPolScript1OperState,
        tmnxSubIPolScript2URL,
        tmnxSubIPolScript2AdminState,
        tmnxSubIPolScript2OperState,
        tmnxSubIPolScript3URL,
        tmnxSubIPolScript3AdminState,
        tmnxSubIPolScript3OperState,
        tmnxSubIPolUseDirectSubMapAsDef,
        tmnxSubIPolUseDirectSLAMapAsDef,
        tmnxSubIPolStringsFromOption,

        tmnxSubIPolSubProfMapRowStatus,
        tmnxSubIPolSubProfMapLastMgmtChange,
        tmnxSubIPolSubProfMapSubProfile,

        tmnxSubIPolSLAProfMapRowStatus,
        tmnxSubIPolSLAProfMapLastMgmtChange,
        tmnxSubIPolSLAProfMapSLAProfile,

        tmnxSubInfoSubProfile,
        tmnxSubInfoSubAncpString,
        tmnxSubInfoNumSubProfileChanges,
        tmnxSubInfoIntermediateDestId,
        tmnxSubInfoModifySubIdent,

        tmnxSubIngQosSchedStatsFwdPkts,
        tmnxSubIngQosSchedStatsFwdOctets,

        tmnxSubEgrQosSchedStatsFwdPkts,
        tmnxSubEgrQosSchedStatsFwdOctets,

        tmnxSPIStatsIngPchipOffHiPrioPkts,
        tmnxSPIStatsIngPchipOffHiPrioOctets,
        tmnxSPIStatsIngPchipOffLoPrioPkts,
        tmnxSPIStatsIngPchipOffLoPrioOctets,
        tmnxSPIStatsIngPchipOffUncolPkts,
        tmnxSPIStatsIngPchipOffUncolOctets,
        tmnxSPIStatsIngQchipDropHiPrioPkts,
        tmnxSPIStatsIngQchipDropHiPrioOctets,
        tmnxSPIStatsIngQchipDropLoPrioPkts,
        tmnxSPIStatsIngQchipDropLoPrioOctets,
        tmnxSPIStatsIngQchipFwdInProfPkts,
        tmnxSPIStatsIngQchipFwdInProfOctets,
        tmnxSPIStatsIngQchipFwdOutProfPkts,
        tmnxSPIStatsIngQchipFwdOutProfOctets,
        tmnxSPIStatsEgrQchipDropInProfPkts,
        tmnxSPIStatsEgrQchipDropInProfOctets,
        tmnxSPIStatsEgrQchipDropOutProfPkts,
        tmnxSPIStatsEgrQchipDropOutProfOctets,
        tmnxSPIStatsEgrQchipFwdInProfPkts,
        tmnxSPIStatsEgrQchipFwdInProfOctets,
        tmnxSPIStatsEgrQchipFwdOutProfPkts,
        tmnxSPIStatsEgrQchipFwdOutProfOctets,

        tmnxSPIIngQStatsOffHiPrioPkts,
        tmnxSPIIngQStatsDropHiPrioPkts,
        tmnxSPIIngQStatsOffLoPrioPkts,
        tmnxSPIIngQStatsDropLoPrioPkts,
        tmnxSPIIngQStatsOffHiPrioOctets,
        tmnxSPIIngQStatsDropHiPrioOctets,
        tmnxSPIIngQStatsOffLoPrioOctets,
        tmnxSPIIngQStatsDropLoPrioOctets,
        tmnxSPIIngQStatsOffUncolPkts,
        tmnxSPIIngQStatsOffUncolOctets,
        tmnxSPIIngQStatsFwdInProfPkts,
        tmnxSPIIngQStatsFwdOutProfPkts,
        tmnxSPIIngQStatsFwdInProfOctets,
        tmnxSPIIngQStatsFwdOutProfOctets,

        tmnxSPIEgrQStatsFwdInProfPkts,
        tmnxSPIEgrQStatsDropInProfPkts,
        tmnxSPIEgrQStatsFwdOutProfPkts,
        tmnxSPIEgrQStatsDropOutProfPkts,
        tmnxSPIEgrQStatsFwdInProfOctets,
        tmnxSPIEgrQStatsDropInProfOctets,
        tmnxSPIEgrQStatsFwdOutProfOctets,
        tmnxSPIEgrQStatsDropOutProfOctets,

        tmnxSubHostInfoV2FwdingState,
        tmnxSubHostInfoV2Origin,
        tmnxSubHostInfoV2SubIdent,
        tmnxSubHostInfoV2SubProfile,
        tmnxSubHostInfoV2SLAProfile,
        tmnxSubHostInfoV2RetailerSvcId,
        tmnxSubHostInfoV2RetailerIf,
        tmnxSubHostInfoV2PfxLen,
        tmnxSubHostInfoV2EgrQGrpName,
        tmnxSubHostInfoV2EgrVPortName,
        tmnxSubHostInfoV2AcctSessionId,

        tmnxSPISubHostV2Origin,
        tmnxSPISubHostV2PfxLen,

        tmnxSPIInfoCategoryMapName,
        tmnxSPIInfoDiamSessId,
        
        tmnxSLAIngPlcrOverrideTblLstChng,
        tmnxSLAEgrPlcrOverrideTblLstChng,
        tmnxSLAIngPolicerOvrRowStatus,      
        tmnxSLAIngPolicerOvrLastMgmtChg, 
        tmnxSLAIngPolicerOvrPIR,            
        tmnxSLAIngPolicerOvrCIR,            
        tmnxSLAIngPolicerOvrMBS,            
        tmnxSLAIngPolicerOvrCBS,            
        tmnxSLAIngPolicerOvrPktOffset,      
        tmnxSLAIngPolicerOvrStatMode,        
        tmnxSLAEgrPolicerOvrRowStatus,     
        tmnxSLAEgrPolicerOvrLastMgmtChg,
        tmnxSLAEgrPolicerOvrPIR,           
        tmnxSLAEgrPolicerOvrCIR,           
        tmnxSLAEgrPolicerOvrMBS,           
        tmnxSLAEgrPolicerOvrCBS,           
        tmnxSLAEgrPolicerOvrPktOffset,     
        tmnxSLAEgrPolicerOvrStatMode,
        tmnxSubProfPCtrlOvrRowStatus,  
        tmnxSubProfPCtrlOvrTblLstChng,
        tmnxSubProfPCtrlOvrLastChange, 
        tmnxSubProfPCtrlOvrMaxRate,    
        tmnxSubProfPCtrlOvrMinMBSSep,  
        tmnxSubProfPCtrlLvlOvrTblLstChng,
        tmnxSubProfPCtrlLvlOvrRowStatus,  
        tmnxSubProfPCtrlLvlOvrLastChange, 
        tmnxSubProfPCtrlLvlOvrCumMBS,
        
        tmnxSPIIngPStatsMode,
        tmnxSPIIngPStatsOffHiPrioPkts,
        tmnxSPIIngPStatsOffHiPrioPktsL,
        tmnxSPIIngPStatsOffHiPrioPktsH,
        tmnxSPIIngPStatsDrpHiPrioPkts,
        tmnxSPIIngPStatsDrpHiPrioPktsL,
        tmnxSPIIngPStatsDrpHiPrioPktsH,
        tmnxSPIIngPStatsOffLoPrioPkts,
        tmnxSPIIngPStatsOffLoPrioPktsL,
        tmnxSPIIngPStatsOffLoPrioPktsH,
        tmnxSPIIngPStatsDrpLoPrioPkts,
        tmnxSPIIngPStatsDrpLoPrioPktsL,
        tmnxSPIIngPStatsDrpLoPrioPktsH,
        tmnxSPIIngPStatsOffHiPrioOcts,
        tmnxSPIIngPStatsOffHiPrioOctsL,
        tmnxSPIIngPStatsOffHiPrioOctsH,
        tmnxSPIIngPStatsDrpHiPrioOcts,
        tmnxSPIIngPStatsDrpHiPrioOctsL,
        tmnxSPIIngPStatsDrpHiPrioOctsH,
        tmnxSPIIngPStatsOffLoPrioOcts,
        tmnxSPIIngPStatsOffLoPrioOctsL,
        tmnxSPIIngPStatsOffLoPrioOctsH,
        tmnxSPIIngPStatsDrpLoPrioOcts,
        tmnxSPIIngPStatsDrpLoPrioOctsL,
        tmnxSPIIngPStatsDrpLoPrioOctsH,
        tmnxSPIIngPStatsOffUncolPkts,
        tmnxSPIIngPStatsOffUncolPktsL,
        tmnxSPIIngPStatsOffUncolPktsH,
        tmnxSPIIngPStatsOffUncolOcts,
        tmnxSPIIngPStatsOffUncolOctsL,
        tmnxSPIIngPStatsOffUncolOctsH,
        tmnxSPIIngPStatsFwdInProfPkts,
        tmnxSPIIngPStatsFwdInProfPktsL,
        tmnxSPIIngPStatsFwdInProfPktsH,
        tmnxSPIIngPStatsFwdOutProfPkts,
        tmnxSPIIngPStatsFwdOutProfPktsL,
        tmnxSPIIngPStatsFwdOutProfPktsH,
        tmnxSPIIngPStatsFwdInProfOcts,
        tmnxSPIIngPStatsFwdInProfOctsL,
        tmnxSPIIngPStatsFwdInProfOctsH,
        tmnxSPIIngPStatsFwdOutProfOcts,
        tmnxSPIIngPStatsFwdOutProfOctsL,
        tmnxSPIIngPStatsFwdOutProfOctsH,

        tmnxSPIEgrPStatsMode,
        tmnxSPIEgrPStatsOffInProfPkts,
        tmnxSPIEgrPStatsOffInProfPktsL,
        tmnxSPIEgrPStatsOffInProfPktsH,
        tmnxSPIEgrPStatsFwdInProfPkts,
        tmnxSPIEgrPStatsFwdInProfPktsL,
        tmnxSPIEgrPStatsFwdInProfPktsH,
        tmnxSPIEgrPStatsDrpInProfPkts,
        tmnxSPIEgrPStatsDrpInProfPktsL,
        tmnxSPIEgrPStatsDrpInProfPktsH,
        tmnxSPIEgrPStatsOffOutProfPkts,
        tmnxSPIEgrPStatsOffOutProfPktsL,
        tmnxSPIEgrPStatsOffOutProfPktsH,
        tmnxSPIEgrPStatsFwdOutProfPkts,
        tmnxSPIEgrPStatsFwdOutProfPktsL,
        tmnxSPIEgrPStatsFwdOutProfPktsH,
        tmnxSPIEgrPStatsDrpOutProfPkts,
        tmnxSPIEgrPStatsDrpOutProfPktsL,
        tmnxSPIEgrPStatsDrpOutProfPktsH,
        tmnxSPIEgrPStatsOffInProfOcts,
        tmnxSPIEgrPStatsOffInProfOctsL,
        tmnxSPIEgrPStatsOffInProfOctsH,
        tmnxSPIEgrPStatsFwdInProfOcts,
        tmnxSPIEgrPStatsFwdInProfOctsL,
        tmnxSPIEgrPStatsFwdInProfOctsH,
        tmnxSPIEgrPStatsDrpInProfOcts,
        tmnxSPIEgrPStatsDrpInProfOctsL,
        tmnxSPIEgrPStatsDrpInProfOctsH,
        tmnxSPIEgrPStatsOffOutProfOcts,
        tmnxSPIEgrPStatsOffOutProfOctsL,
        tmnxSPIEgrPStatsOffOutProfOctsH,
        tmnxSPIEgrPStatsFwdOutProfOcts,
        tmnxSPIEgrPStatsFwdOutProfOctsL,
        tmnxSPIEgrPStatsFwdOutProfOctsH,
        tmnxSPIEgrPStatsDrpOutProfOcts,
        tmnxSPIEgrPStatsDrpOutProfOctsL,
        tmnxSPIEgrPStatsDrpOutProfOctsH,
        tmnxSPIEgrPStatsOffUncolPkts,
        tmnxSPIEgrPStatsOffUncolPktsL,
        tmnxSPIEgrPStatsOffUncolPktsH,
        tmnxSPIEgrPStatsOffUncolOcts,
        tmnxSPIEgrPStatsOffUncolOctsL,
        tmnxSPIEgrPStatsOffUncolOctsH,

        tmnxSubIngQosArbitStatsFwdPkts,
        tmnxSubIngQosArbitStatsFwdPktsLo,
        tmnxSubIngQosArbitStatsFwdPktsHi,
        tmnxSubIngQosArbitStatsFwdOcts,
        tmnxSubIngQosArbitStatsFwdOctsLo,
        tmnxSubIngQosArbitStatsFwdOctsHi,
        tmnxSubEgrQosArbitStatsFwdPkts,
        tmnxSubEgrQosArbitStatsFwdPktsLo,
        tmnxSubEgrQosArbitStatsFwdPktsHi,
        tmnxSubEgrQosArbitStatsFwdOcts,
        tmnxSubEgrQosArbitStatsFwdOctsLo,
        tmnxSubEgrQosArbitStatsFwdOctsHi,

        tmnxSubIgmpPlcyRowStatus,
        tmnxSubIgmpPlcyDescription,
        tmnxSubIgmpPlcyImportPolicy,
        tmnxSubIgmpPlcyHostMaxGroups,
        tmnxSubIgmpPlcyAdminVersion,
        tmnxSubIgmpPlcyFastLeave,
        tmnxSubIgmpPlcyRedirectionPolicy,
        tmnxSubIgmpPlcyEgrRateModType,
        tmnxSubIgmpPlcyEgrRateModSched,

        tmnxSubIgmpPlcyStaticRowStatus,

        tmnxSLAProfInstOvrPIR,
        tmnxSLAProfInstOvrCIR,
        tmnxSLAProfInstOvrCBS,
        tmnxSLAProfInstOvrMBS,
        tmnxSubOvrPIR,
        tmnxSubOvrCIR,
        tmnxSubOvrCBS,
        tmnxSubOvrMBS,

        tmnxSubIgmpHostsCreated,
        
        tmnxSubIgmpPlcySubscriberId,
        tmnxSubIgmpStatusPlcyName,
        tmnxSubInfoRadEgrAggRateLimit,
        tmnxSubInfoEgrAggRateLimit,
        
        tmnxSubMcacPlcyRowStatus,
        tmnxSubMcacPlcyDescription,
        tmnxSubMcacPlcyAdminState,
        tmnxSubMcacPlcyUnconstrainedBW,
        tmnxSubMcacPlcyPreRsvdMandBW,
        tmnxSubMcacPlcyLastMgmtChange,
        
        tmnxSubMcacPlcySubscriberId,

        tmnxSubMcacStatusPlcyName,
        tmnxSubMcacStatusinUseMandBw,
        tmnxSubMcacStatusinUseOpnlBw,
        tmnxSubMcacStatusAvailMandBw,
        tmnxSubMcacStatusAvailOpnlBw
        }
    STATUS      obsolete
    DESCRIPTION
        "The group of objects supporting management of subscriber profiles on
         release 8.0 of the Nokia SROS series systems."
    ::= { tmnxSubMgmtGroups 40 }

tmnxSubCreditControlV8v0Group OBJECT-GROUP
    OBJECTS {
       tmnxSubApCCPlcyTableLastChnge,
       tmnxSubCcPlcyRowStatus,
       tmnxSubCcPlcyLastChngd,
       tmnxSubCcPlcyDescription,
       tmnxSubCcPlcyDiameterPlcy,
       tmnxSubCcPlcyDefaultCategoryMap,
       tmnxSubCcPlcyOutOfCreditAction,
       tmnxSubCcPlcyErrorHandlingAction,

       tmnxSLAProfCreditControlPlcy,

       tmnxSubApCategoryMapTblLstChnge,
       tmnxSubApCMapRowStatus,
       tmnxSubApCMapLastChngd,
       tmnxSubApCMapDescription,
       tmnxSubApCMapCreditType,
       tmnxSubApCMapCreditExhstThrshld,
       tmnxSubApCMapActivityThreshold,

       tmnxSubApCategoryTblLstChnge,
       tmnxSubApCategoryRowStatus,
       tmnxSubApCategoryLastChngd,
       tmnxSubApCategoryDescription,
       tmnxSubApCategoryIngressQueues,
       tmnxSubApCategoryEgressQueues,
       tmnxSubApCategoryUseRatingGroup,
       tmnxSubApCategoryRatingGroup,
       tmnxSubApCategoryCTypeOverride,
       tmnxSubApCategoryDfltCrdtVolume,
       tmnxSubApCategoryDfltCrdtVolUnit,
       tmnxSubApCategoryDfltCrdtTime,
       tmnxSubApCategoryOutOfCrdtAction,
       tmnxSubApCategoryPir,
       tmnxSubApCategoryIngressPolicers,
       tmnxSubApCategoryEgressPolicers,
      
       tmnxSPICatMapName,
       tmnxSPICatCreditControlPlcy,
       tmnxSPICatCrdtVolumeUsed,
       tmnxSPICatCrdtVolumeAvail,
       tmnxSPICatCrdtVolumeThres,
       tmnxSPICatCrdtTimeUsed,
       tmnxSPICatCrdtTimeAvail,
       tmnxSPICatCrdtTimeThres,
       tmnxSPICatCrdtExpired,
       tmnxSPICatCrdtNegotiating,
       tmnxSPICatOutOfCrdtAction,
       tmnxSPICatQuotaHoldingTime,
       tmnxSPICatCrdtReset
    }
    STATUS      current
    DESCRIPTION
        "The group of subscriber management objects supporting management of
         the credit control feature on Nokia SROS series systems."
    ::= { tmnxSubMgmtGroups 41 }

tmnxSubMgmtV9v0Group   OBJECT-GROUP
    OBJECTS {
        tmnxSubProfRowStatus,
        tmnxSubProfLastMgmtChange,
        tmnxSubProfDescription,
        tmnxSubProfIngQosSchedPolicy,
        tmnxSubProfEgrQosSchedPolicy,
        tmnxSubProfCollectAcctStats,
        tmnxSubProfAccountingPolicyId,
        tmnxSubProfEgrAggRateLimit,
        tmnxSubProfRadiusAcctPolicy,
        tmnxSubProfDuplRadiusAcctPolicy,
        tmnxSubProfUseDirectSLAMapAsDef,

        tmnxSubProfSchedOvrRowStatus,
        tmnxSubProfSchedOvrLastMgmtChange,
        tmnxSubProfSchedOvrPIR,
        tmnxSubProfSchedOvrCIR,
        tmnxSubProfSchedOvrSummedCIR,

        tmnxSubProfSLAProfMapRowStatus,
        tmnxSubProfSLAProfMapLastMgmtChange,
        tmnxSubProfSLAProfMapSLAProfile,

        tmnxSLAProfRowStatus,
        tmnxSLAProfLastMgmtChange,
        tmnxSLAProfDescription,
        tmnxSLAProfHostLimit,
        tmnxSLAProfRemoveOldest,
        tmnxSLAProfIngQosPolId,
        tmnxSLAProfIngSharedQPolicy,
        tmnxSLAProfIngUseMpointShared,
        tmnxSLAProfIngIPFilterId,
        tmnxSLAProfEgrQosPolId,
        tmnxSLAProfEgrIPFilterId,
        tmnxSLAProfReportIngRateType,
        tmnxSLAProfReportIngRateSched,
        tmnxSLAProfReportEgrRateType,
        tmnxSLAProfReportEgrRateSched,
        tmnxSLAProfEgrQosMarkingFromSap,
        tmnxSLAProfEgrSchedulerType,

        tmnxSLAIngQueueOvrRowStatus,
        tmnxSLAIngQueueOvrLastMgmtChange,
        tmnxSLAIngQueueOvrPIR,
        tmnxSLAIngQueueOvrCIR,
        tmnxSLAIngQueueOvrCBS,
        tmnxSLAIngQueueOvrHiPrioOnly,
        tmnxSLAIngQueueOvrMBSBytes,

        tmnxSLAEgrQueueOvrRowStatus,
        tmnxSLAEgrQueueOvrLastMgmtChange,
        tmnxSLAEgrQueueOvrPIR,
        tmnxSLAEgrQueueOvrCIR,
        tmnxSLAEgrQueueOvrCBS,
        tmnxSLAEgrQueueOvrHiPrioOnly,
        tmnxSLAEgrQueueOvrAvgOverhead,
        tmnxSLAEgrQueueOvrMBSBytes,

        tmnxSubExplicitMapRowStatus,
        tmnxSubExplicitMapLastMgmtChange,
        tmnxSubExplicitMapSubProfile,
        tmnxSubExplicitMapSLAProfile,
        tmnxSubExplicitMapAlias,

        tmnxSubIPolRowStatus,
        tmnxSubIPolLastMgmtChange,
        tmnxSubIPolDescription,
        tmnxSubIPolScript1URL,
        tmnxSubIPolScript1AdminState,
        tmnxSubIPolScript1OperState,
        tmnxSubIPolScript2URL,
        tmnxSubIPolScript2AdminState,
        tmnxSubIPolScript2OperState,
        tmnxSubIPolScript3URL,
        tmnxSubIPolScript3AdminState,
        tmnxSubIPolScript3OperState,
        tmnxSubIPolUseDirectSubMapAsDef,
        tmnxSubIPolUseDirectSLAMapAsDef,
        tmnxSubIPolRejectUnknownStrings,
        tmnxSubIPolStringsFromOption,

        tmnxSubIPolSubProfMapRowStatus,
        tmnxSubIPolSubProfMapLastMgmtChange,
        tmnxSubIPolSubProfMapSubProfile,

        tmnxSubIPolSLAProfMapRowStatus,
        tmnxSubIPolSLAProfMapLastMgmtChange,
        tmnxSubIPolSLAProfMapSLAProfile,

        tmnxSubInfoSubProfile,
        tmnxSubInfoSubAncpString,
        tmnxSubInfoNumSubProfileChanges,
        tmnxSubInfoIntermediateDestId,
        tmnxSubInfoModifySubIdent,

        tmnxSubIngQosSchedStatsFwdPkts,
        tmnxSubIngQosSchedStatsFwdOctets,

        tmnxSubEgrQosSchedStatsFwdPkts,
        tmnxSubEgrQosSchedStatsFwdOctets,

        tmnxSPIStatsIngPchipOffHiPrioPkts,
        tmnxSPIStatsIngPchipOffHiPrioOctets,
        tmnxSPIStatsIngPchipOffLoPrioPkts,
        tmnxSPIStatsIngPchipOffLoPrioOctets,
        tmnxSPIStatsIngPchipOffUncolPkts,
        tmnxSPIStatsIngPchipOffUncolOctets,
        tmnxSPIStatsIngQchipDropHiPrioPkts,
        tmnxSPIStatsIngQchipDropHiPrioOctets,
        tmnxSPIStatsIngQchipDropLoPrioPkts,
        tmnxSPIStatsIngQchipDropLoPrioOctets,
        tmnxSPIStatsIngQchipFwdInProfPkts,
        tmnxSPIStatsIngQchipFwdInProfOctets,
        tmnxSPIStatsIngQchipFwdOutProfPkts,
        tmnxSPIStatsIngQchipFwdOutProfOctets,
        tmnxSPIStatsEgrQchipDropInProfPkts,
        tmnxSPIStatsEgrQchipDropInProfOctets,
        tmnxSPIStatsEgrQchipDropOutProfPkts,
        tmnxSPIStatsEgrQchipDropOutProfOctets,
        tmnxSPIStatsEgrQchipFwdInProfPkts,
        tmnxSPIStatsEgrQchipFwdInProfOctets,
        tmnxSPIStatsEgrQchipFwdOutProfPkts,
        tmnxSPIStatsEgrQchipFwdOutProfOctets,

        tmnxSPIIngQStatsOffHiPrioPkts,
        tmnxSPIIngQStatsDropHiPrioPkts,
        tmnxSPIIngQStatsOffLoPrioPkts,
        tmnxSPIIngQStatsDropLoPrioPkts,
        tmnxSPIIngQStatsOffHiPrioOctets,
        tmnxSPIIngQStatsDropHiPrioOctets,
        tmnxSPIIngQStatsOffLoPrioOctets,
        tmnxSPIIngQStatsDropLoPrioOctets,
        tmnxSPIIngQStatsOffUncolPkts,
        tmnxSPIIngQStatsOffUncolOctets,
        tmnxSPIIngQStatsFwdInProfPkts,
        tmnxSPIIngQStatsFwdOutProfPkts,
        tmnxSPIIngQStatsFwdInProfOctets,
        tmnxSPIIngQStatsFwdOutProfOctets,

        tmnxSPIEgrQStatsFwdInProfPkts,
        tmnxSPIEgrQStatsDropInProfPkts,
        tmnxSPIEgrQStatsFwdOutProfPkts,
        tmnxSPIEgrQStatsDropOutProfPkts,
        tmnxSPIEgrQStatsFwdInProfOctets,
        tmnxSPIEgrQStatsDropInProfOctets,
        tmnxSPIEgrQStatsFwdOutProfOctets,
        tmnxSPIEgrQStatsDropOutProfOctets,

        tmnxSubHostInfoV2FwdingState,
        tmnxSubHostInfoV2Origin,
        tmnxSubHostInfoV2SubIdent,
        tmnxSubHostInfoV2SubProfile,
        tmnxSubHostInfoV2SLAProfile,
        tmnxSubHostInfoV2RetailerSvcId,
        tmnxSubHostInfoV2RetailerIf,
        tmnxSubHostInfoV2PfxLen,
        tmnxSubHostInfoV2EgrQGrpName,
        tmnxSubHostInfoV2EgrVPortName,
        tmnxSubHostInfoV2AcctSessionId,
        tmnxSubHostInfoV2AddressOrigin,
        tmnxSubHostInfoV2PppIndex,
        tmnxSubHostInfoV2AcctMultiSessId,
        tmnxSubHostInfoV2IngFilter, 
        tmnxSubHostInfoV2EgrFilter,        
        
        tmnxSPISubHostV2Origin,
        tmnxSPISubHostV2PfxLen,

        tmnxSPIInfoCategoryMapName,
        tmnxSPIInfoDiamSessId,
        
        tmnxSLAIngPlcrOverrideTblLstChng,
        tmnxSLAEgrPlcrOverrideTblLstChng,
        tmnxSLAIngPolicerOvrRowStatus,      
        tmnxSLAIngPolicerOvrLastMgmtChg, 
        tmnxSLAIngPolicerOvrPIR,            
        tmnxSLAIngPolicerOvrCIR,            
        tmnxSLAIngPolicerOvrMBS,            
        tmnxSLAIngPolicerOvrCBS,            
        tmnxSLAIngPolicerOvrPktOffset,      
        tmnxSLAIngPolicerOvrStatMode,        
        tmnxSLAEgrPolicerOvrRowStatus,     
        tmnxSLAEgrPolicerOvrLastMgmtChg,
        tmnxSLAEgrPolicerOvrPIR,           
        tmnxSLAEgrPolicerOvrCIR,           
        tmnxSLAEgrPolicerOvrMBS,           
        tmnxSLAEgrPolicerOvrCBS,           
        tmnxSLAEgrPolicerOvrPktOffset,     
        tmnxSLAEgrPolicerOvrStatMode,
        tmnxSubProfPCtrlOvrRowStatus,  
        tmnxSubProfPCtrlOvrTblLstChng,
        tmnxSubProfPCtrlOvrLastChange, 
        tmnxSubProfPCtrlOvrMaxRate,    
        tmnxSubProfPCtrlOvrMinMBSSep,  
        tmnxSubProfPCtrlLvlOvrTblLstChng,
        tmnxSubProfPCtrlLvlOvrRowStatus,  
        tmnxSubProfPCtrlLvlOvrLastChange, 
        tmnxSubProfPCtrlLvlOvrCumMBS,
        
        tmnxSPIIngPStatsMode,
        tmnxSPIIngPStatsOffHiPrioPkts,
        tmnxSPIIngPStatsOffHiPrioPktsL,
        tmnxSPIIngPStatsOffHiPrioPktsH,
        tmnxSPIIngPStatsDrpHiPrioPkts,
        tmnxSPIIngPStatsDrpHiPrioPktsL,
        tmnxSPIIngPStatsDrpHiPrioPktsH,
        tmnxSPIIngPStatsOffLoPrioPkts,
        tmnxSPIIngPStatsOffLoPrioPktsL,
        tmnxSPIIngPStatsOffLoPrioPktsH,
        tmnxSPIIngPStatsDrpLoPrioPkts,
        tmnxSPIIngPStatsDrpLoPrioPktsL,
        tmnxSPIIngPStatsDrpLoPrioPktsH,
        tmnxSPIIngPStatsOffHiPrioOcts,
        tmnxSPIIngPStatsOffHiPrioOctsL,
        tmnxSPIIngPStatsOffHiPrioOctsH,
        tmnxSPIIngPStatsDrpHiPrioOcts,
        tmnxSPIIngPStatsDrpHiPrioOctsL,
        tmnxSPIIngPStatsDrpHiPrioOctsH,
        tmnxSPIIngPStatsOffLoPrioOcts,
        tmnxSPIIngPStatsOffLoPrioOctsL,
        tmnxSPIIngPStatsOffLoPrioOctsH,
        tmnxSPIIngPStatsDrpLoPrioOcts,
        tmnxSPIIngPStatsDrpLoPrioOctsL,
        tmnxSPIIngPStatsDrpLoPrioOctsH,
        tmnxSPIIngPStatsOffUncolPkts,
        tmnxSPIIngPStatsOffUncolPktsL,
        tmnxSPIIngPStatsOffUncolPktsH,
        tmnxSPIIngPStatsOffUncolOcts,
        tmnxSPIIngPStatsOffUncolOctsL,
        tmnxSPIIngPStatsOffUncolOctsH,
        tmnxSPIIngPStatsFwdInProfPkts,
        tmnxSPIIngPStatsFwdInProfPktsL,
        tmnxSPIIngPStatsFwdInProfPktsH,
        tmnxSPIIngPStatsFwdOutProfPkts,
        tmnxSPIIngPStatsFwdOutProfPktsL,
        tmnxSPIIngPStatsFwdOutProfPktsH,
        tmnxSPIIngPStatsFwdInProfOcts,
        tmnxSPIIngPStatsFwdInProfOctsL,
        tmnxSPIIngPStatsFwdInProfOctsH,
        tmnxSPIIngPStatsFwdOutProfOcts,
        tmnxSPIIngPStatsFwdOutProfOctsL,
        tmnxSPIIngPStatsFwdOutProfOctsH,
      
        tmnxSPIEgrPStatsMode,
        tmnxSPIEgrPStatsOffInProfPkts,
        tmnxSPIEgrPStatsOffInProfPktsL,
        tmnxSPIEgrPStatsOffInProfPktsH,
        tmnxSPIEgrPStatsFwdInProfPkts,
        tmnxSPIEgrPStatsFwdInProfPktsL,
        tmnxSPIEgrPStatsFwdInProfPktsH,
        tmnxSPIEgrPStatsDrpInProfPkts,
        tmnxSPIEgrPStatsDrpInProfPktsL,
        tmnxSPIEgrPStatsDrpInProfPktsH,
        tmnxSPIEgrPStatsOffOutProfPkts,
        tmnxSPIEgrPStatsOffOutProfPktsL,
        tmnxSPIEgrPStatsOffOutProfPktsH,
        tmnxSPIEgrPStatsFwdOutProfPkts,
        tmnxSPIEgrPStatsFwdOutProfPktsL,
        tmnxSPIEgrPStatsFwdOutProfPktsH,
        tmnxSPIEgrPStatsDrpOutProfPkts,
        tmnxSPIEgrPStatsDrpOutProfPktsL,
        tmnxSPIEgrPStatsDrpOutProfPktsH,
        tmnxSPIEgrPStatsOffInProfOcts,
        tmnxSPIEgrPStatsOffInProfOctsL,
        tmnxSPIEgrPStatsOffInProfOctsH,
        tmnxSPIEgrPStatsFwdInProfOcts,
        tmnxSPIEgrPStatsFwdInProfOctsL,
        tmnxSPIEgrPStatsFwdInProfOctsH,
        tmnxSPIEgrPStatsDrpInProfOcts,
        tmnxSPIEgrPStatsDrpInProfOctsL,
        tmnxSPIEgrPStatsDrpInProfOctsH,
        tmnxSPIEgrPStatsOffOutProfOcts,
        tmnxSPIEgrPStatsOffOutProfOctsL,
        tmnxSPIEgrPStatsOffOutProfOctsH,
        tmnxSPIEgrPStatsFwdOutProfOcts,
        tmnxSPIEgrPStatsFwdOutProfOctsL,
        tmnxSPIEgrPStatsFwdOutProfOctsH,
        tmnxSPIEgrPStatsDrpOutProfOcts,
        tmnxSPIEgrPStatsDrpOutProfOctsL,
        tmnxSPIEgrPStatsDrpOutProfOctsH,
        tmnxSPIEgrPStatsOffUncolPkts,
        tmnxSPIEgrPStatsOffUncolPktsL,
        tmnxSPIEgrPStatsOffUncolPktsH,
        tmnxSPIEgrPStatsOffUncolOcts,
        tmnxSPIEgrPStatsOffUncolOctsL,
        tmnxSPIEgrPStatsOffUncolOctsH,
       
        tmnxSubIngQosArbitStatsFwdPkts,
        tmnxSubIngQosArbitStatsFwdPktsLo,
        tmnxSubIngQosArbitStatsFwdPktsHi,
        tmnxSubIngQosArbitStatsFwdOcts,
        tmnxSubIngQosArbitStatsFwdOctsLo,
        tmnxSubIngQosArbitStatsFwdOctsHi,
        tmnxSubEgrQosArbitStatsFwdPkts,
        tmnxSubEgrQosArbitStatsFwdPktsLo,
        tmnxSubEgrQosArbitStatsFwdPktsHi,
        tmnxSubEgrQosArbitStatsFwdOcts,
        tmnxSubEgrQosArbitStatsFwdOctsLo,
        tmnxSubEgrQosArbitStatsFwdOctsHi,

        tmnxSubIgmpPlcyRowStatus,
        tmnxSubIgmpPlcyDescription,
        tmnxSubIgmpPlcyImportPolicy,
        tmnxSubIgmpPlcyHostMaxGroups,
        tmnxSubIgmpPlcyAdminVersion,
        tmnxSubIgmpPlcyFastLeave,
        tmnxSubIgmpPlcyRedirectionPolicy,
        tmnxSubIgmpPlcyEgrRateModType,
        tmnxSubIgmpPlcyEgrRateModSched,
        tmnxSubIgmpPlcyPerHostReplic,
        tmnxSubIgmpPlcyMcRprtDestName,
        tmnxSubIgmpPlcyMcRprtOptFields,
        tmnxSubIgmpPlcyMcRprtAdminState,

        tmnxSubIgmpPlcyStaticRowStatus,

        tmnxSLAProfInstOvrPIR,
        tmnxSLAProfInstOvrCIR,
        tmnxSLAProfInstOvrCBS,
        tmnxSLAProfInstOvrMBS,
        tmnxSubOvrPIR,
        tmnxSubOvrCIR,
        tmnxSubOvrCBS,
        tmnxSubOvrMBS,

        tmnxSubIgmpHostsCreated,
        
        tmnxSubIgmpPlcySubscriberId,
        tmnxSubIgmpStatusPlcyName,
        tmnxSubInfoRadEgrAggRateLimit,
        tmnxSubInfoEgrAggRateLimit,
        
        tmnxSubMcacPlcyRowStatus,
        tmnxSubMcacPlcyDescription,
        tmnxSubMcacPlcyAdminState,
        tmnxSubMcacPlcyUnconstrainedBW,
        tmnxSubMcacPlcyPreRsvdMandBW,
        tmnxSubMcacPlcyLastMgmtChange,
        
        tmnxSubMcacPlcySubscriberId,

        tmnxSubMcacStatusPlcyName,
        tmnxSubMcacStatusinUseMandBw,
        tmnxSubMcacStatusinUseOpnlBw,
        tmnxSubMcacStatusAvailMandBw,
        tmnxSubMcacStatusAvailOpnlBw,
        tmnxSubFlterProfRowStatus
        }
    STATUS      obsolete
    DESCRIPTION
        "The group of objects supporting management of subscriber profiles on
         release 9.0 of the Nokia SROS series systems."
    ::= { tmnxSubMgmtGroups 42 }

tmnxSubProfileV9v0Group   OBJECT-GROUP
    OBJECTS {
       tmnxSubProfEgrPolicerPolicy,
       tmnxSubProfIngPolicerPolicy,
       tmnxSubProfIgmpPolicy,
       tmnxSubProfEgrAvgFrameSize,
       tmnxSubProfEgrEncapOffsetMode,
       tmnxSubProfEgrEncapOffset,
       tmnxSubProfSubMcacPolicy,
       tmnxSubProfPreference
    }
    STATUS      current
    DESCRIPTION
        "The group of objects supporting management of subscriber
         profile feature on Nokia SROS series systems."
    ::= { tmnxSubMgmtGroups 50 }

tmnxSubPppGroup   OBJECT-GROUP
    OBJECTS {
        tmnxSubPppType,                     
        tmnxSubPppUpTime,                         
        tmnxSubPppDescription,                         
        tmnxSubPppLcpState,
        tmnxSubPppIpcpState,
        tmnxSubPppIpv6cpState,
        tmnxSubPppPppMtu,                         
        tmnxSubPppPppAuthProtocol,                
        tmnxSubPppPppUserName,               
        tmnxSubPppSubIdent,                       
        tmnxSubPppOriginSubIdent,                 
        tmnxSubPppSubProfString,                  
        tmnxSubPppSlaProfString,                  
        tmnxSubPppAncpString,                     
        tmnxSubPppInterDestId,
        tmnxSubPppAppProfString,                  
        tmnxSubPppCategoryMapName,
        tmnxSubPppOriginStrings,                  
        tmnxSubPppIpAddrType,                     
        tmnxSubPppIpAddr,
        tmnxSubPppIpAddrPrefixLength,
        tmnxSubPppOriginIp,                 
        tmnxSubPppPrimaryDnsType,                 
        tmnxSubPppPrimaryDns,                     
        tmnxSubPppSecondaryDnsType,               
        tmnxSubPppSecondaryDns,
        tmnxSubPppOriginDns,
        tmnxSubPppPrimaryNbnsType,                
        tmnxSubPppPrimaryNbns,                    
        tmnxSubPppSecondaryNbnsType,
        tmnxSubPppSecondaryNbns,
        tmnxSubPppOriginNbns,                 
        tmnxSubPppInterfaceId,                    
        tmnxSubPppOriginIpv6cpInfo,               
        tmnxSubPppIpv6Dns1Type,                    
        tmnxSubPppIpv6Dns1,                       
        tmnxSubPppIpv6Dns2Type,
        tmnxSubPppIpv6Dns2,                      
        tmnxSubPppIpv6DelPfxType,
        tmnxSubPppIpv6DelPfxLen,
        tmnxSubPppIpv6DelPfxOrigin,
        tmnxSubPppIpv6DelPfxPool,
        tmnxSubPppIpv6DelPfx,                     
        tmnxSubPppIpv6PrefixType,                 
        tmnxSubPppIpv6PrefixLen,                  
        tmnxSubPppIpv6Prefix,
        tmnxSubPppTerminationType,
        tmnxSubPppRetailerSvcId,
        tmnxSubPppRetailerIf,
        tmnxSubPppLacVrtrId,
        tmnxSubPppLacConnectionId,
        tmnxSubPppSessionTimeout,
        tmnxSubPppCircuitId,
        tmnxSubPppRemoteId,
        tmnxSubPppAddressPool,
        tmnxSubPppRadiusClassAttr,
        tmnxSubPppRadiusUserName,
        tmnxSubPppSvcId,
        tmnxSubPppSubIf,
        tmnxSubPppGrpIf,
        tmnxSubPppPortId,
        tmnxSubPppEncapValue,
        tmnxSubPppStatRxUnknownProto,       
        tmnxSubPppStatRxLcpConfReq,        
        tmnxSubPppStatRxLcpConfAck,        
        tmnxSubPppStatRxLcpConfNak,        
        tmnxSubPppStatRxLcpConfRej,
        tmnxSubPppStatRxLcpTermReq,        
        tmnxSubPppStatRxLcpTermAck,        
        tmnxSubPppStatRxLcpCodeRej,
        tmnxSubPppStatRxLcpEchoReq,
        tmnxSubPppStatRxLcpEchoRep,
        tmnxSubPppStatRxLcpProtRej,
        tmnxSubPppStatRxLcpDiscReq,
        tmnxSubPppStatTxLcpConfReq,
        tmnxSubPppStatTxLcpConfAck,
        tmnxSubPppStatTxLcpConfNak,
        tmnxSubPppStatTxLcpConfRej,
        tmnxSubPppStatTxLcpTermReq,
        tmnxSubPppStatTxLcpTermAck,
        tmnxSubPppStatTxLcpCodeRej,
        tmnxSubPppStatTxLcpEchoReq,
        tmnxSubPppStatTxLcpEchoRep,
        tmnxSubPppStatTxLcpProtRej,
        tmnxSubPppStatTxLcpDiscReq,
        tmnxSubPppStatRxPapAuthReq,
        tmnxSubPppStatTxPapAuthAck,
        tmnxSubPppStatTxPapAuthNak,
        tmnxSubPppStatRxChapResponse,
        tmnxSubPppStatTxChapChallenge,
        tmnxSubPppStatTxChapSuccess,
        tmnxSubPppStatTxChapFailure,
        tmnxSubPppStatRxIpcpConfReq,
        tmnxSubPppStatRxIpcpConfAck,
        tmnxSubPppStatRxIpcpConfNak,
        tmnxSubPppStatRxIpcpConfRej,
        tmnxSubPppStatRxIpcpTermReq,
        tmnxSubPppStatRxIpcpTermAck,
        tmnxSubPppStatRxIpcpCodeRej,
        tmnxSubPppStatTxIpcpConfReq,
        tmnxSubPppStatTxIpcpConfAck,
        tmnxSubPppStatTxIpcpConfNak,
        tmnxSubPppStatTxIpcpConfRej,
        tmnxSubPppStatTxIpcpTermReq,
        tmnxSubPppStatTxIpcpTermAck,
        tmnxSubPppStatTxIpcpCodeRej,
        tmnxSubPppStatRxIpv6cpConfReq,
        tmnxSubPppStatRxIpv6cpConfAck,
        tmnxSubPppStatRxIpv6cpConfNak,
        tmnxSubPppStatRxIpv6cpConfRej,
        tmnxSubPppStatRxIpv6cpTermReq,
        tmnxSubPppStatRxIpv6cpTermAck,
        tmnxSubPppStatRxIpv6cpCodeRej,
        tmnxSubPppStatTxIpv6cpConfReq,
        tmnxSubPppStatTxIpv6cpConfAck,
        tmnxSubPppStatTxIpv6cpConfNak,
        tmnxSubPppStatTxIpv6cpConfRej,
        tmnxSubPppStatTxIpv6cpTermReq,
        tmnxSubPppStatTxIpv6cpTermAck,
        tmnxSubPppStatTxIpv6cpCodeRej,
        tmnxSubPppMRtStatus,
        tmnxSubPppOvrPIR,
        tmnxSubPppOvrCIR,
        tmnxSubPppOvrCBS,
        tmnxSubPppOvrMBS,
        tmnxSubPppAleDatalink,
        tmnxSubPppAleEncaps1, 
        tmnxSubPppAleEncaps2, 
        tmnxSubPppBgpPrngPlcyName, 
        tmnxSubPppBgpAuthKeyChain, 
        tmnxSubPppBgpMD5AuthKey,   
        tmnxSubPppBgpImportPolicy, 
        tmnxSubPppBgpExportPolicy, 
        tmnxSubPppBgpPeerAS,       
        tmnxSubPppBgpPeeringStatus,
        tmnxSubPppModSubIdent,
        tmnxSubPppModSubProfStr,   
        tmnxSubPppModSlaProfStr,   
        tmnxSubPppModAncpStr,      
        tmnxSubPppModInterDestId,  
        tmnxSubPppModAppProfStr,
        tmnxSubPppModEvaluateState,
        tmnxSubPppSessions,
        tmnxSubPppTypeSessions,
        tmnxSubPppUserType,
        tmnxSubPppSvcTypeSessions
    }
    STATUS      obsolete
    DESCRIPTION
        "The group of objects for the
         management of subscriber PPP on Nokia SROS series systems."
    ::= { tmnxSubMgmtGroups 51 }

tmnxSubCreditControlV9v0Group OBJECT-GROUP
    OBJECTS {
       tmnxSLAProfCMapName,
       tmnxSLAProfCatLastMgmtChange,
       tmnxSLAProfCatRowStatus,
       tmnxSLAProfCatTimeout
    }
    STATUS      current
    DESCRIPTION
        "The group of subscriber management objects supporting management of
         the credit control feature on Nokia SROS series systems
         added in release 9.0."
    ::= { tmnxSubMgmtGroups 52 }

tmnxSubHsmdaGroup   OBJECT-GROUP
    OBJECTS {
        tmnxSubHsmdaEgrQosQTableLastCh,
        tmnxSubHsmdaEgrQosQRowStatus,  
        tmnxSubHsmdaEgrQosQLastChgd,     
        tmnxSubHsmdaEgrQosQPIR,              
        tmnxSubHsmdaEgrQosQSlopePlcy,        
        tmnxSubHsmdaEgrQosQWrrWeight,
        tmnxSubHsmdaEgrQosQMBS,
        tmnxSubProfHsmda2IngQosPolId,    
        tmnxSubProfHsmda2EgrQosPolId,    
        tmnxSubProfHsmda2EgrAggRateLimit,
        tmnxSubProfHsmda2EgrQosWrrPolicy,
        tmnxSubProfHsmda2EgrPackByteOff,
        tmnxSubPppOvrWrrWeight,
        tmnxSLAProfInstOvrWrrWeight,
        tmnxSubInfoQos,
        tmnxSubOvrWrrWeight,
        tmnxSubHsmdaStIngOffHiPrioPkt,
        tmnxSubHsmdaStIngOffHiPrioPktLw,
        tmnxSubHsmdaStIngOffHiPrioPktHw,
        tmnxSubHsmdaStIngOffHiPrioOct,
        tmnxSubHsmdaStIngOffHiPrioOctLw,
        tmnxSubHsmdaStIngOffHiPrioOctHw,
        tmnxSubHsmdaStIngOffLoPrioPkt,
        tmnxSubHsmdaStIngOffLoPrioPktLw,
        tmnxSubHsmdaStIngOffLoPrioPktHw,
        tmnxSubHsmdaStIngOffLoPrioOct,
        tmnxSubHsmdaStIngOffLoPrioOctLw,
        tmnxSubHsmdaStIngOffLoPrioOctHw,
        tmnxSubHsmdaStIngOffUncolPkt,
        tmnxSubHsmdaStIngOffUncolPktLw,
        tmnxSubHsmdaStIngOffUncolPktHw,
        tmnxSubHsmdaStIngOffUncolOct,
        tmnxSubHsmdaStIngOffUncolOctLw,
        tmnxSubHsmdaStIngOffUncolOctHw,
        tmnxSubIngQStatsOffHiPrioPkts,
        tmnxSubIngQStatsOffHiPrioPktsLw,
        tmnxSubIngQStatsOffHiPrioPktsHw,
        tmnxSubIngQStatsOffLoPrioPkts,
        tmnxSubIngQStatsOffLoPrioPktsLw,
        tmnxSubIngQStatsOffLoPrioPktsHw,
        tmnxSubIngQStatsOffHiPrioOcts,
        tmnxSubIngQStatsOffHiPrioOctsLw,
        tmnxSubIngQStatsOffHiPrioOctsHw,
        tmnxSubIngQStatsOffLoPrioOcts,
        tmnxSubIngQStatsOffLoPrioOctsLw,
        tmnxSubIngQStatsOffLoPrioOctsHw,
        tmnxSubIngQStatsOffUncolPkts,
        tmnxSubIngQStatsOffUncolPktsLw,
        tmnxSubIngQStatsOffUncolPktsHw,
        tmnxSubIngQStatsOffUncolOcts,
        tmnxSubIngQStatsOffUncolOctsLw,
        tmnxSubIngQStatsOffUncolOctsHw,
        tmnxSubIngPStatsMode,
        tmnxSubIngPStatsOffHiPrioPkts,
        tmnxSubIngPStatsOffHiPrioPktsL,
        tmnxSubIngPStatsOffHiPrioPktsH,
        tmnxSubIngPStatsDrpHiPrioPkts,
        tmnxSubIngPStatsDrpHiPrioPktsL,
        tmnxSubIngPStatsDrpHiPrioPktsH,
        tmnxSubIngPStatsOffLoPrioPkts,
        tmnxSubIngPStatsOffLoPrioPktsL,
        tmnxSubIngPStatsOffLoPrioPktsH,
        tmnxSubIngPStatsDrpLoPrioPkts,
        tmnxSubIngPStatsDrpLoPrioPktsL,
        tmnxSubIngPStatsDrpLoPrioPktsH,
        tmnxSubIngPStatsOffHiPrioOcts,
        tmnxSubIngPStatsOffHiPrioOctsL,
        tmnxSubIngPStatsOffHiPrioOctsH,
        tmnxSubIngPStatsDrpHiPrioOcts,
        tmnxSubIngPStatsDrpHiPrioOctsL,
        tmnxSubIngPStatsDrpHiPrioOctsH,
        tmnxSubIngPStatsOffLoPrioOcts,
        tmnxSubIngPStatsOffLoPrioOctsL,
        tmnxSubIngPStatsOffLoPrioOctsH,
        tmnxSubIngPStatsDrpLoPrioOcts,
        tmnxSubIngPStatsDrpLoPrioOctsL,
        tmnxSubIngPStatsDrpLoPrioOctsH,
        tmnxSubIngPStatsOffUncolPkts,
        tmnxSubIngPStatsOffUncolPktsL,
        tmnxSubIngPStatsOffUncolPktsH,
        tmnxSubIngPStatsOffUncolOcts,
        tmnxSubIngPStatsOffUncolOctsL,
        tmnxSubIngPStatsOffUncolOctsH,
        tmnxSubIngPStatsFwdInProfPkts,
        tmnxSubIngPStatsFwdInProfPktsL,
        tmnxSubIngPStatsFwdInProfPktsH,
        tmnxSubIngPStatsFwdOutProfPkts,
        tmnxSubIngPStatsFwdOutProfPktsL,
        tmnxSubIngPStatsFwdOutProfPktsH,
        tmnxSubIngPStatsFwdInProfOcts,
        tmnxSubIngPStatsFwdInProfOctsL,
        tmnxSubIngPStatsFwdInProfOctsH,
        tmnxSubIngPStatsFwdOutProfOcts,
        tmnxSubIngPStatsFwdOutProfOctsL,
        tmnxSubIngPStatsFwdOutProfOctsH
    }
    STATUS      current
    DESCRIPTION
        "The group of subscriber management objects supporting
         management of HSMDA-2 on Nokia SROS series systems."
    ::= { tmnxSubMgmtGroups 53 }

tmnxSubBsxObjV9v0Group OBJECT-GROUP
    OBJECTS {
        tmnxSubExplicitMapAppProfile,
        tmnxSubIPolUseDirectAppMapAsDef,
        tmnxSubIPolAppProfMapRowStatus,
        tmnxSubIPolAppProfMapLastMgmtChange,
        tmnxSubIPolAppProfMapAppProfile,
        tmnxSubInfoAppProfile,
        tmnxSubHostInfoV2AppProfile,
        tmnxSubIPolUseDirectFltrMapAsDef
    }
    STATUS      current
    DESCRIPTION
        "The group of objects supporting management of BSX (Application
         Assurance) Subscribers on Nokia SROS series systems."
    ::= { tmnxSubMgmtGroups 54 }

tmnxSubHostTrackingV9v0Group OBJECT-GROUP
    OBJECTS {
        tmnxSubTrkPlcyRowStatus,
        tmnxSubTrkPlcyLastMgmtChange,
        tmnxSubTrkPlcyDescription,
        tmnxSubTrkPlcyEgrRateModType,
        tmnxSubTrkPlcyEgrRateModSched,

        tmnxSubTrkPlcyMcRprtDestName,
        tmnxSubTrkPlcyMcRprtOptFields,
        tmnxSubTrkPlcyMcRprtAdminState,
        
        tmnxSubProfHostTrackingPolicy,
        tmnxSubTrkStatusPlcyName,
        tmnxSubTrkStatusEgrRateReduction,
        tmnxSubHostTrkUpTime,
        tmnxSubHostTrkExpiryTime,
        tmnxSubHostTrkBw,
        tmnxSubHostSapTrkUpTime,
        tmnxSubHostSapTrkExpiryTime,
        tmnxSubHostSapTrkBw,
        tmnxSubHostSapTrkSubIdent,
        tmnxSubHostGrpTrkUpTime,
        tmnxSubHostGrpTrkExpiryTime,
        tmnxSubHostGrpTrkSubIdent,
        tmnxSubGrpTrkUpTime,
        tmnxSubGrpTrkExpiryTime,
        tmnxSubGrpTrkBw,
        tmnxSubTrkPlcySubscriberId,
        tmnxSubHostSapTrkStatsVal,
        tmnxSubHostTrkStatsVal,
        
        tmnxSubHostSapTrkMcRDstStatVal
    }
    STATUS      current
    DESCRIPTION
        "The group of subscriber management objects supporting management of
         multicast Host Tracking on Nokia SROS series systems."
    ::= { tmnxSubMgmtGroups 55 }

tmnxSubAleGroup   OBJECT-GROUP
        OBJECTS {
            tmnxSubAleEncapOffset,                     
            tmnxSubAleDatalink                         
                    }
        STATUS      current
        DESCRIPTION
            "The group of objects for the  management of 
             subscriber DSL Access Loop information 
             on Nokia SROS series systems."
        ::= { tmnxSubMgmtGroups 56 }

tmnxSubFlterProfGroup   OBJECT-GROUP
    OBJECTS {
        tmnxSubFlterProfTbleLastMgmtChg,
        tmnxSubFlterProfLastMgmtChange,
        tmnxSubFlterProfDescription,
        tmnxSubFlterProfIngIpFltrId,
        tmnxSubFlterProfEgrIpFltrId,
        tmnxSubFlterProfIngIpv6FltrId,
        tmnxSubFlterProfEgrIpv6FltrId,
        
        tmnxSPFltrProfMapTblLstMgtChg,
        tmnxSPFltrProfMapRowStatus,
        tmnxSPFltrProfMapLstMgmtChg,
        tmnxSPFltrProfMapFltrProfile,
        
        tmnxSubIPolFltrProfMapRowStatus,
        tmnxSubIPolFltrProfMapLastMgmtCh,
        tmnxSubIPolFltrProfMapFltrProf,

        tmnxSubFlterProfTbleLastMgmtChg,
        tmnxSubFlterProfLastMgmtChange,
        tmnxSubFlterProfDescription,
        tmnxSubFlterProfIngIpFltrId,
        tmnxSubFlterProfEgrIpFltrId,
        tmnxSubFlterProfIngIpv6FltrId,
        tmnxSubFlterProfEgrIpv6FltrId,
        
        tmnxSPFltrProfMapTblLstMgtChg,
        tmnxSPFltrProfMapRowStatus,
        tmnxSPFltrProfMapLstMgmtChg,
        tmnxSPFltrProfMapFltrProfile,
        
        tmnxSubIPolFltrProfMapRowStatus,
        tmnxSubIPolFltrProfMapLastMgmtCh,
        tmnxSubIPolFltrProfMapFltrProf,

        tmnxSubProfUseDirectFltrMapAsDef
    }
    STATUS      current
    DESCRIPTION
        "The group of objects for the  management of 
         Filter profiles. 
         on Nokia SROS series systems."
    ::= { tmnxSubMgmtGroups 57 }

tmnxSubAuthenticationV10v0Group   OBJECT-GROUP
    OBJECTS {
        tmnxSubAuthPlcyRadRespAttrSelect,
        tmnxSubAuthPlcyAcceptScriptPlcy,
        tmnxSubAuthPlcyRequestScriptPlcy,
        tmnxSubAuthPlcyCoAScriptPlcy,
        tmnxSubAuthPlcyAcctSessionIdType,
        tmnxSubAuthPlcyRadServPndRqLimit,
        tmnxSubAuthPlcyRadServOutTime,
        tmnxSubAuthPlcyRadServOvrldTime,
        tmnxSubAuthPlcyRadOvrldSendFail,
        tmnxSubAuthPlcySendFail
    }
    STATUS      current
    DESCRIPTION
        "The group of objects supporting management of subscriber
         authentication policies on Nokia SROS series systems
         added in release 10.0."
    ::= { tmnxSubMgmtGroups 58 }

tmnxSubL2tpGroup   OBJECT-GROUP
    OBJECTS {
        tmnxSubPppMlpppRole,
        tmnxSubPppMlpppBundleId,
        tmnxSubPppAleOrigin,
        tmnxSubPppAleLinkRateDown,
        tmnxSubPppAleLinkRateDownOrigin
    }
    STATUS      current
    DESCRIPTION
        "The group of objects for the
         management of L2TP subscribers on Nokia SROS series systems."
    ::= { tmnxSubMgmtGroups 60 }

tmnxSubMgmtV10v0Group   OBJECT-GROUP
    OBJECTS {
        tmnxSubProfRowStatus,
        tmnxSubProfLastMgmtChange,
        tmnxSubProfDescription,
        tmnxSubProfIngQosSchedPolicy,
        tmnxSubProfEgrQosSchedPolicy,
        tmnxSubProfCollectAcctStats,
        tmnxSubProfAccountingPolicyId,
        tmnxSubProfEgrAggRateLimit,
        tmnxSubProfRadiusAcctPolicy,
        tmnxSubProfDuplRadiusAcctPolicy,
        tmnxSubProfUseDirectSLAMapAsDef,

        tmnxSubProfSchedOvrRowStatus,
        tmnxSubProfSchedOvrLastMgmtChange,
        tmnxSubProfSchedOvrPIR,
        tmnxSubProfSchedOvrCIR,
        tmnxSubProfSchedOvrSummedCIR,

        tmnxSubProfSLAProfMapRowStatus,
        tmnxSubProfSLAProfMapLastMgmtChange,
        tmnxSubProfSLAProfMapSLAProfile,

        tmnxSLAProfRowStatus,
        tmnxSLAProfLastMgmtChange,
        tmnxSLAProfDescription,
        tmnxSLAProfHostLimit,
        tmnxSLAProfRemoveOldest,
        tmnxSLAProfIngQosPolId,
        tmnxSLAProfIngSharedQPolicy,
        tmnxSLAProfIngUseMpointShared,
        tmnxSLAProfIngIPFilterId,
        tmnxSLAProfEgrQosPolId,
        tmnxSLAProfEgrIPFilterId,
        tmnxSLAProfReportIngRateType,
        tmnxSLAProfReportIngRateSched,
        tmnxSLAProfReportEgrRateType,
        tmnxSLAProfReportEgrRateSched,
        tmnxSLAProfEgrQosMarkingFromSap,
        tmnxSLAProfEgrSchedulerType,
        tmnxSLAProfOTHttpRdrIpv4FltrId,
        tmnxSLAProfEgrUseIngL2tpDscp,

        tmnxSLAIngQueueOvrRowStatus,
        tmnxSLAIngQueueOvrLastMgmtChange,
        tmnxSLAIngQueueOvrPIR,
        tmnxSLAIngQueueOvrCIR,
        tmnxSLAIngQueueOvrCBS,
        tmnxSLAIngQueueOvrHiPrioOnly,
        tmnxSLAIngQueueOvrMBSBytes,

        tmnxSLAEgrQueueOvrRowStatus,
        tmnxSLAEgrQueueOvrLastMgmtChange,
        tmnxSLAEgrQueueOvrPIR,
        tmnxSLAEgrQueueOvrCIR,
        tmnxSLAEgrQueueOvrCBS,
        tmnxSLAEgrQueueOvrHiPrioOnly,
        tmnxSLAEgrQueueOvrAvgOverhead,
        tmnxSLAEgrQueueOvrMBSBytes,

        tmnxSubExplicitMapRowStatus,
        tmnxSubExplicitMapLastMgmtChange,
        tmnxSubExplicitMapSubProfile,
        tmnxSubExplicitMapSLAProfile,
        tmnxSubExplicitMapAlias,

        tmnxSubIPolRowStatus,
        tmnxSubIPolLastMgmtChange,
        tmnxSubIPolDescription,
        tmnxSubIPolScript1URL,
        tmnxSubIPolScript1AdminState,
        tmnxSubIPolScript1OperState,
        tmnxSubIPolScript2URL,
        tmnxSubIPolScript2AdminState,
        tmnxSubIPolScript2OperState,
        tmnxSubIPolScript3URL,
        tmnxSubIPolScript3AdminState,
        tmnxSubIPolScript3OperState,
        tmnxSubIPolUseDirectSubMapAsDef,
        tmnxSubIPolUseDirectSLAMapAsDef,
        tmnxSubIPolRejectUnknownStrings,
        tmnxSubIPolStringsFromOption,

        tmnxSubIPolSubProfMapRowStatus,
        tmnxSubIPolSubProfMapLastMgmtChange,
        tmnxSubIPolSubProfMapSubProfile,

        tmnxSubIPolSLAProfMapRowStatus,
        tmnxSubIPolSLAProfMapLastMgmtChange,
        tmnxSubIPolSLAProfMapSLAProfile,

        tmnxSubInfoSubProfile,
        tmnxSubInfoSubAncpString,
        tmnxSubInfoNumSubProfileChanges,
        tmnxSubInfoIntermediateDestId,
        tmnxSubInfoModifySubIdent,

        tmnxSubIngQosSchedStatsFwdPkts,
        tmnxSubIngQosSchedStatsFwdOctets,

        tmnxSubEgrQosSchedStatsFwdPkts,
        tmnxSubEgrQosSchedStatsFwdOctets,

        tmnxSPIStatsIngPchipOffHiPrioPkts,
        tmnxSPIStatsIngPchipOffHiPrioOctets,
        tmnxSPIStatsIngPchipOffLoPrioPkts,
        tmnxSPIStatsIngPchipOffLoPrioOctets,
        tmnxSPIStatsIngPchipOffUncolPkts,
        tmnxSPIStatsIngPchipOffUncolOctets,
        tmnxSPIStatsIngQchipDropHiPrioPkts,
        tmnxSPIStatsIngQchipDropHiPrioOctets,
        tmnxSPIStatsIngQchipDropLoPrioPkts,
        tmnxSPIStatsIngQchipDropLoPrioOctets,
        tmnxSPIStatsIngQchipFwdInProfPkts,
        tmnxSPIStatsIngQchipFwdInProfOctets,
        tmnxSPIStatsIngQchipFwdOutProfPkts,
        tmnxSPIStatsIngQchipFwdOutProfOctets,
        tmnxSPIStatsEgrQchipDropInProfPkts,
        tmnxSPIStatsEgrQchipDropInProfOctets,
        tmnxSPIStatsEgrQchipDropOutProfPkts,
        tmnxSPIStatsEgrQchipDropOutProfOctets,
        tmnxSPIStatsEgrQchipFwdInProfPkts,
        tmnxSPIStatsEgrQchipFwdInProfOctets,
        tmnxSPIStatsEgrQchipFwdOutProfPkts,
        tmnxSPIStatsEgrQchipFwdOutProfOctets,

        tmnxSPIIngQStatsOffHiPrioPkts,
        tmnxSPIIngQStatsDropHiPrioPkts,
        tmnxSPIIngQStatsOffLoPrioPkts,
        tmnxSPIIngQStatsDropLoPrioPkts,
        tmnxSPIIngQStatsOffHiPrioOctets,
        tmnxSPIIngQStatsDropHiPrioOctets,
        tmnxSPIIngQStatsOffLoPrioOctets,
        tmnxSPIIngQStatsDropLoPrioOctets,
        tmnxSPIIngQStatsOffUncolPkts,
        tmnxSPIIngQStatsOffUncolOctets,
        tmnxSPIIngQStatsFwdInProfPkts,
        tmnxSPIIngQStatsFwdOutProfPkts,
        tmnxSPIIngQStatsFwdInProfOctets,
        tmnxSPIIngQStatsFwdOutProfOctets,

        tmnxSPIEgrQStatsFwdInProfPkts,
        tmnxSPIEgrQStatsDropInProfPkts,
        tmnxSPIEgrQStatsFwdOutProfPkts,
        tmnxSPIEgrQStatsDropOutProfPkts,
        tmnxSPIEgrQStatsFwdInProfOctets,
        tmnxSPIEgrQStatsDropInProfOctets,
        tmnxSPIEgrQStatsFwdOutProfOctets,
        tmnxSPIEgrQStatsDropOutProfOctets,

        tmnxSubHostInfoV2FwdingState,
        tmnxSubHostInfoV2Origin,
        tmnxSubHostInfoV2SubIdent,
        tmnxSubHostInfoV2SubProfile,
        tmnxSubHostInfoV2SLAProfile,
        tmnxSubHostInfoV2RetailerSvcId,
        tmnxSubHostInfoV2RetailerIf,
        tmnxSubHostInfoV2PfxLen,
        tmnxSubHostInfoV2EgrQGrpName,
        tmnxSubHostInfoV2EgrVPortName,
        tmnxSubHostInfoV2AcctSessionId,
        tmnxSubHostInfoV2AddressOrigin,
        tmnxSubHostInfoV2PppIndex,
        tmnxSubHostInfoV2AcctMultiSessId,
        tmnxSubHostInfoV2IngFilter, 
        tmnxSubHostInfoV2EgrFilter,  
        tmnxSubHostInfoV2OtHttpRdrState,
        tmnxSubHostInfoV2OtHttpRdrFilter,
        tmnxSubHostInfoV2OtHttpRdrSource,
              
        
        tmnxSPISubHostV2Origin,
        tmnxSPISubHostV2PfxLen,

        tmnxSPIInfoCategoryMapName,
        tmnxSPIInfoDiamSessId,
        
        tmnxSLAIngPlcrOverrideTblLstChng,
        tmnxSLAEgrPlcrOverrideTblLstChng,
        tmnxSLAIngPolicerOvrRowStatus,      
        tmnxSLAIngPolicerOvrLastMgmtChg, 
        tmnxSLAIngPolicerOvrPIR,            
        tmnxSLAIngPolicerOvrCIR,            
        tmnxSLAIngPolicerOvrMBS,            
        tmnxSLAIngPolicerOvrCBS,            
        tmnxSLAIngPolicerOvrPktOffset,      
        tmnxSLAIngPolicerOvrStatMode,        
        tmnxSLAEgrPolicerOvrRowStatus,     
        tmnxSLAEgrPolicerOvrLastMgmtChg,
        tmnxSLAEgrPolicerOvrPIR,           
        tmnxSLAEgrPolicerOvrCIR,           
        tmnxSLAEgrPolicerOvrMBS,           
        tmnxSLAEgrPolicerOvrCBS,           
        tmnxSLAEgrPolicerOvrPktOffset,     
        tmnxSLAEgrPolicerOvrStatMode,
        tmnxSubProfPCtrlOvrRowStatus,  
        tmnxSubProfPCtrlOvrTblLstChng,
        tmnxSubProfPCtrlOvrLastChange, 
        tmnxSubProfPCtrlOvrMaxRate,    
        tmnxSubProfPCtrlOvrMinMBSSep,  
        tmnxSubProfPCtrlLvlOvrTblLstChng,
        tmnxSubProfPCtrlLvlOvrRowStatus,  
        tmnxSubProfPCtrlLvlOvrLastChange, 
        tmnxSubProfPCtrlLvlOvrCumMBS,
        
        tmnxSPIIngPStatsMode,
        tmnxSPIIngPStatsOffHiPrioPkts,
        tmnxSPIIngPStatsOffHiPrioPktsL,
        tmnxSPIIngPStatsOffHiPrioPktsH,
        tmnxSPIIngPStatsDrpHiPrioPkts,
        tmnxSPIIngPStatsDrpHiPrioPktsL,
        tmnxSPIIngPStatsDrpHiPrioPktsH,
        tmnxSPIIngPStatsOffLoPrioPkts,
        tmnxSPIIngPStatsOffLoPrioPktsL,
        tmnxSPIIngPStatsOffLoPrioPktsH,
        tmnxSPIIngPStatsDrpLoPrioPkts,
        tmnxSPIIngPStatsDrpLoPrioPktsL,
        tmnxSPIIngPStatsDrpLoPrioPktsH,
        tmnxSPIIngPStatsOffHiPrioOcts,
        tmnxSPIIngPStatsOffHiPrioOctsL,
        tmnxSPIIngPStatsOffHiPrioOctsH,
        tmnxSPIIngPStatsDrpHiPrioOcts,
        tmnxSPIIngPStatsDrpHiPrioOctsL,
        tmnxSPIIngPStatsDrpHiPrioOctsH,
        tmnxSPIIngPStatsOffLoPrioOcts,
        tmnxSPIIngPStatsOffLoPrioOctsL,
        tmnxSPIIngPStatsOffLoPrioOctsH,
        tmnxSPIIngPStatsDrpLoPrioOcts,
        tmnxSPIIngPStatsDrpLoPrioOctsL,
        tmnxSPIIngPStatsDrpLoPrioOctsH,
        tmnxSPIIngPStatsOffUncolPkts,
        tmnxSPIIngPStatsOffUncolPktsL,
        tmnxSPIIngPStatsOffUncolPktsH,
        tmnxSPIIngPStatsOffUncolOcts,
        tmnxSPIIngPStatsOffUncolOctsL,
        tmnxSPIIngPStatsOffUncolOctsH,
        tmnxSPIIngPStatsFwdInProfPkts,
        tmnxSPIIngPStatsFwdInProfPktsL,
        tmnxSPIIngPStatsFwdInProfPktsH,
        tmnxSPIIngPStatsFwdOutProfPkts,
        tmnxSPIIngPStatsFwdOutProfPktsL,
        tmnxSPIIngPStatsFwdOutProfPktsH,
        tmnxSPIIngPStatsFwdInProfOcts,
        tmnxSPIIngPStatsFwdInProfOctsL,
        tmnxSPIIngPStatsFwdInProfOctsH,
        tmnxSPIIngPStatsFwdOutProfOcts,
        tmnxSPIIngPStatsFwdOutProfOctsL,
        tmnxSPIIngPStatsFwdOutProfOctsH,
      
        tmnxSPIEgrPStatsMode,
        tmnxSPIEgrPStatsOffInProfPkts,
        tmnxSPIEgrPStatsOffInProfPktsL,
        tmnxSPIEgrPStatsOffInProfPktsH,
        tmnxSPIEgrPStatsFwdInProfPkts,
        tmnxSPIEgrPStatsFwdInProfPktsL,
        tmnxSPIEgrPStatsFwdInProfPktsH,
        tmnxSPIEgrPStatsDrpInProfPkts,
        tmnxSPIEgrPStatsDrpInProfPktsL,
        tmnxSPIEgrPStatsDrpInProfPktsH,
        tmnxSPIEgrPStatsOffOutProfPkts,
        tmnxSPIEgrPStatsOffOutProfPktsL,
        tmnxSPIEgrPStatsOffOutProfPktsH,
        tmnxSPIEgrPStatsFwdOutProfPkts,
        tmnxSPIEgrPStatsFwdOutProfPktsL,
        tmnxSPIEgrPStatsFwdOutProfPktsH,
        tmnxSPIEgrPStatsDrpOutProfPkts,
        tmnxSPIEgrPStatsDrpOutProfPktsL,
        tmnxSPIEgrPStatsDrpOutProfPktsH,
        tmnxSPIEgrPStatsOffInProfOcts,
        tmnxSPIEgrPStatsOffInProfOctsL,
        tmnxSPIEgrPStatsOffInProfOctsH,
        tmnxSPIEgrPStatsFwdInProfOcts,
        tmnxSPIEgrPStatsFwdInProfOctsL,
        tmnxSPIEgrPStatsFwdInProfOctsH,
        tmnxSPIEgrPStatsDrpInProfOcts,
        tmnxSPIEgrPStatsDrpInProfOctsL,
        tmnxSPIEgrPStatsDrpInProfOctsH,
        tmnxSPIEgrPStatsOffOutProfOcts,
        tmnxSPIEgrPStatsOffOutProfOctsL,
        tmnxSPIEgrPStatsOffOutProfOctsH,
        tmnxSPIEgrPStatsFwdOutProfOcts,
        tmnxSPIEgrPStatsFwdOutProfOctsL,
        tmnxSPIEgrPStatsFwdOutProfOctsH,
        tmnxSPIEgrPStatsDrpOutProfOcts,
        tmnxSPIEgrPStatsDrpOutProfOctsL,
        tmnxSPIEgrPStatsDrpOutProfOctsH,
        tmnxSPIEgrPStatsOffUncolPkts,
        tmnxSPIEgrPStatsOffUncolPktsL,
        tmnxSPIEgrPStatsOffUncolPktsH,
        tmnxSPIEgrPStatsOffUncolOcts,
        tmnxSPIEgrPStatsOffUncolOctsL,
        tmnxSPIEgrPStatsOffUncolOctsH,
       
        tmnxSubIngQosArbitStatsFwdPkts,
        tmnxSubIngQosArbitStatsFwdPktsLo,
        tmnxSubIngQosArbitStatsFwdPktsHi,
        tmnxSubIngQosArbitStatsFwdOcts,
        tmnxSubIngQosArbitStatsFwdOctsLo,
        tmnxSubIngQosArbitStatsFwdOctsHi,
        tmnxSubEgrQosArbitStatsFwdPkts,
        tmnxSubEgrQosArbitStatsFwdPktsLo,
        tmnxSubEgrQosArbitStatsFwdPktsHi,
        tmnxSubEgrQosArbitStatsFwdOcts,
        tmnxSubEgrQosArbitStatsFwdOctsLo,
        tmnxSubEgrQosArbitStatsFwdOctsHi,

        tmnxSubIgmpPlcyRowStatus,
        tmnxSubIgmpPlcyDescription,
        tmnxSubIgmpPlcyImportPolicy,
        tmnxSubIgmpPlcyHostMaxGroups,
        tmnxSubIgmpPlcyAdminVersion,
        tmnxSubIgmpPlcyFastLeave,
        tmnxSubIgmpPlcyRedirectionPolicy,
        tmnxSubIgmpPlcyEgrRateModType,
        tmnxSubIgmpPlcyEgrRateModSched,
        tmnxSubIgmpPlcyPerHostReplic,
        tmnxSubIgmpPlcyMcRprtDestName,
        tmnxSubIgmpPlcyMcRprtOptFields,
        tmnxSubIgmpPlcyMcRprtAdminState,

        tmnxSubIgmpPlcyStaticRowStatus,

        tmnxSLAProfInstOvrPIR,
        tmnxSLAProfInstOvrCIR,
        tmnxSLAProfInstOvrCBS,
        tmnxSLAProfInstOvrMBS,
        tmnxSubOvrPIR,
        tmnxSubOvrCIR,
        tmnxSubOvrCBS,
        tmnxSubOvrMBS,

        tmnxSubIgmpHostsCreated,
        
        tmnxSubIgmpPlcySubscriberId,
        tmnxSubIgmpStatusPlcyName,
        tmnxSubInfoRadEgrAggRateLimit,
        tmnxSubInfoEgrAggRateLimit,
        
        tmnxSubMcacPlcyRowStatus,
        tmnxSubMcacPlcyDescription,
        tmnxSubMcacPlcyAdminState,
        tmnxSubMcacPlcyUnconstrainedBW,
        tmnxSubMcacPlcyPreRsvdMandBW,
        tmnxSubMcacPlcyLastMgmtChange,
        
        tmnxSubMcacPlcySubscriberId,

        tmnxSubMcacStatusPlcyName,
        tmnxSubMcacStatusinUseMandBw,
        tmnxSubMcacStatusinUseOpnlBw,
        tmnxSubMcacStatusAvailMandBw,
        tmnxSubMcacStatusAvailOpnlBw,
        tmnxSubFlterProfRowStatus,
        
        tmnxSubLcktPlcyRowStatus,
        tmnxSubLcktPlcyLastMgmtChange,
        tmnxSubLcktPlcyDescription,
        tmnxSubLcktPlcyLcktTimeMin,
        tmnxSubLcktPlcyLcktTimeMax,
        tmnxSubLcktPlcyLcktResetTime,
        tmnxSubLcktPlcyMaxLcktHosts,
        tmnxSubLcktPlcyHostKey,
        
        tmnxSubIgmpPlcyHostMaxSources
        }
    STATUS      obsolete
    DESCRIPTION
        "The group of objects supporting management of subscriber profiles on
         release 10.0 of the Nokia SROS series systems."
    ::= { tmnxSubMgmtGroups 61 }

tmnxSubAccountingV10v0Group   OBJECT-GROUP
    OBJECTS {
        tmnxSubAcctPlcyRequestScriptPlcy,
        tmnxSubAcctPlcyQueueInstAcct,
        tmnxSubAcctPlcySessionAcct,
        tmnxSubPppAcctSessionId
    }
    STATUS      current
    DESCRIPTION
        "The group of objects supporting management of subscriber
         accounting policies on Nokia SROS series systems
         since release 10.0."
    ::= { tmnxSubMgmtGroups 62 }

tmnxSubCreditControlV10v0Group OBJECT-GROUP
    OBJECTS {
       tmnxSLAProfCatTimeoutAction
    }
    STATUS      current
    DESCRIPTION
        "The group of subscriber management objects supporting management of
         the credit control feature on Nokia SROS series systems
         added in release 10.0."
    ::= { tmnxSubMgmtGroups 63 }

tmnxSubAutoSubIdV10v0Group OBJECT-GROUP
    OBJECTS {
        tmnxSubAutoSubIdIpoeKey1,
        tmnxSubAutoSubIdIpoeKey2,
        tmnxSubAutoSubIdIpoeKey3,
        tmnxSubAutoSubIdIpoeKey4,
        tmnxSubAutoSubIdPppKey1,
        tmnxSubAutoSubIdPppKey2,
        tmnxSubAutoSubIdPppKey3,
        tmnxSubAutoSubIdPppKey4,
        tmnxSubAutoSubIdPppKey5
    }
    STATUS      current
    DESCRIPTION
        "The group of subscriber management objects supporting management of
         the auto-generated subscriber identification feature
         on Nokia SROS series systems since release 10.0."
    ::= { tmnxSubMgmtGroups 64 }

tmnxSubIpoeLinkV10v0Group OBJECT-GROUP
    OBJECTS {
        tmnxSubIpoeLinkLastMgmtChange,
        tmnxSubIpoeLinkTableLastChange,
        tmnxSubIpoeLinkAdminState,
        tmnxSubIpoeLinkShareCircId,
        tmnxSubIpoeLinkGratRtrAdv
    }
    STATUS      current
    DESCRIPTION
        "The group of subscriber management objects supporting management of
         the IPoE host linking feature on Nokia SROS series systems
         since release 10.0."
    ::= { tmnxSubMgmtGroups 65 }

tmnxSubPppV10v0Group OBJECT-GROUP
    OBJECTS {
        tmnxSubPppIpv6AddrType,
        tmnxSubPppIpv6Addr,
        tmnxSubPppIpv6AddrOrigin,
        tmnxSubPppIpv6AddrPool
    }
    STATUS      obsolete
    DESCRIPTION
        "The group of objects for the
         management of subscriber PPP on Nokia SROS series systems
         since release 10.0."
    ::= { tmnxSubMgmtGroups 66 }

tmnxSubSlaacV10v0Group OBJECT-GROUP
    OBJECTS {
        tmnxSubSlaacPfxLen,
        tmnxSubSlaacPortId,
        tmnxSubSlaacEncapValue,
        tmnxSubSlaacPppIndex,
        tmnxSubSlaacPersistKey,
        tmnxSubSlaacInterfaceId,
        tmnxSubSlaacCircuitId,
        tmnxSubSlaacRemoteId,
        tmnxSubSlaacSubscrIdent,
        tmnxSubSlaacSubProfString,
        tmnxSubSlaacSlaProfString,
        tmnxSubSlaacAppProfString,
        tmnxSubSlaacCategoryMapName,
        tmnxSubSlaacAncpString,
        tmnxSubSlaacInterDestId,
        tmnxSubSlaacRadiusClassAttr,
        tmnxSubSlaacShcvOperState,
        tmnxSubSlaacShcvChecks,
        tmnxSubSlaacShcvReplies,
        tmnxSubSlaacShcvReplyTime,
        tmnxSubSlaacPrimaryDnsType,
        tmnxSubSlaacPrimaryDns,
        tmnxSubSlaacSecondaryDnsType,
        tmnxSubSlaacSecondaryDns,
        tmnxSubSlaacCreationTime,
        tmnxSubSlaacOriginSubscrId,
        tmnxSubSlaacOriginStrings,
        tmnxSubSlaacOriginPfxInfo        
    }
    STATUS      obsolete
    DESCRIPTION
        "The group of objects for the management of stateless address
         autoconfiguration hosts on Nokia SROS series systems
         since release 10.0."
    ::= { tmnxSubMgmtGroups 67 }

tmnxSubAuthenticationV11v0Group OBJECT-GROUP
    OBJECTS {
        tmnxSubAuthPlcyNasPortBitspec,
        tmnxSubAuthPlcyRadiusServerPlcy,
        tmnxSubAuthPlcyAcctStopOnFail
    }
   
    STATUS      current
    DESCRIPTION
        "The group of objects supporting management of subscriber
         authentication policies on Nokia SROS series systems
         added in release 11.0."
    ::= { tmnxSubMgmtGroups 68 }


tmnxSubMgmtV11v0Group   OBJECT-GROUP
    OBJECTS {
        tmnxSubMgmtPortSIpcp             ,
        tmnxSubMgmtPortSIpcpPeak         ,
        tmnxSubMgmtPortSL2tpHost         ,
        tmnxSubMgmtPortSL2tpHostPeak     ,
        tmnxSubMgmtPortSDhcp             ,
        tmnxSubMgmtPortSDhcpPeak         ,
        tmnxSubMgmtPortSArp              ,
        tmnxSubMgmtPortSArpPeak          ,
        tmnxSubMgmtPortSStatic           ,
        tmnxSubMgmtPortSStaticPeak       ,
        tmnxSubMgmtPortSNonSub           ,
        tmnxSubMgmtPortSNonSubPeak       ,
        tmnxSubMgmtPortSPppSlaac         ,
        tmnxSubMgmtPortSPppSlaacPeak     ,
        tmnxSubMgmtPortSPppDhcp6Pd       ,
        tmnxSubMgmtPortSPppDhcp6PdPeak   ,
        tmnxSubMgmtPortSPppDhcp6Na       ,
        tmnxSubMgmtPortSPppDhcp6NaPeak   ,
        tmnxSubMgmtPortSIpoeSlaac        ,
        tmnxSubMgmtPortSIpoeSlaacPeak    ,
        tmnxSubMgmtPortSIpoeDhcp6Pd      ,
        tmnxSubMgmtPortSIpoeDhcp6PdPeak  ,
        tmnxSubMgmtPortSIpoeDhcp6Na      ,
        tmnxSubMgmtPortSIpoeDhcp6NaPeak  ,
        tmnxSubMgmtPortSV4               ,
        tmnxSubMgmtPortSV4Peak           ,
        tmnxSubMgmtPortSV6               ,
        tmnxSubMgmtPortSV6Peak           ,
        tmnxSubMgmtPortSPppHosts         ,
        tmnxSubMgmtPortSPppHostsPeak     ,
        tmnxSubMgmtPortSIpoeHosts        ,
        tmnxSubMgmtPortSIpoeHostsPeak    ,
        tmnxSubMgmtPortSTotal            ,
        tmnxSubMgmtPortSTotalPeak        ,
        tmnxSubMgmtPortSPppLclOE         ,
        tmnxSubMgmtPortSPppLclOEPeak     ,
        tmnxSubMgmtPortSPppLclOEOA       ,
        tmnxSubMgmtPortSPppLclOEOAPeak   ,
        tmnxSubMgmtPortSPppLclOA         ,
        tmnxSubMgmtPortSPppLclOAPeak     ,
        tmnxSubMgmtPortSPppLclL2tp       ,
        tmnxSubMgmtPortSPppLclL2tpPeak   ,
        tmnxSubMgmtPortSPppLclTotal      ,
        tmnxSubMgmtPortSPppLclTotalPeak  ,
        tmnxSubMgmtPortSPppLacOE         ,
        tmnxSubMgmtPortSPppLacOEPeak     ,
        tmnxSubMgmtPortSPppLacOEOA       ,
        tmnxSubMgmtPortSPppLacOEOAPeak   ,
        tmnxSubMgmtPortSPppLacOA         ,
        tmnxSubMgmtPortSPppLacOAPeak     ,
        tmnxSubMgmtPortSPppLacL2tp       ,
        tmnxSubMgmtPortSPppLacL2tpPeak   ,
        tmnxSubMgmtPortSPppLacTotal      ,
        tmnxSubMgmtPortSPppLacTotalPeak  ,
        tmnxSubMgmtPortSPppSessIs        ,
        tmnxSubMgmtPortSPppSessIsPeak    ,
        tmnxSubMgmtPortSPppSessTotal     ,
        tmnxSubMgmtPortSPppSessTotalPeak ,
        tmnxSubMgmtPortSSubscribers      ,
        tmnxSubMgmtPortSSubscribersPeak  ,
        
        tmnxSubLcktHostMacAddr           ,
        tmnxSubLcktHostCctId             ,
        tmnxSubLcktHostRemId             ,
        tmnxSubLcktHostResetTimeElapsed  ,
        tmnxSubLcktHostLockTimeCurrent   ,
        tmnxSubLcktHostLockTimeElapsed   ,
        tmnxSubLcktHostLockTimeNext      ,
        tmnxSubLcktHostNumLockouts       ,
        
        tmnxSubIgmpPlcyHostMaxGrpSources ,

        tmnxSubMgmtMdaSIpcp              ,
        tmnxSubMgmtMdaSIpcpPeak          ,
        tmnxSubMgmtMdaSL2tpHost          ,
        tmnxSubMgmtMdaSL2tpHostPeak      ,
        tmnxSubMgmtMdaSDhcp              ,
        tmnxSubMgmtMdaSDhcpPeak          ,
        tmnxSubMgmtMdaSArp               ,
        tmnxSubMgmtMdaSArpPeak           ,
        tmnxSubMgmtMdaSStatic            ,
        tmnxSubMgmtMdaSStaticPeak        ,
        tmnxSubMgmtMdaSNonSub            ,
        tmnxSubMgmtMdaSNonSubPeak        ,
        tmnxSubMgmtMdaSPppSlaac          ,
        tmnxSubMgmtMdaSPppSlaacPeak      ,
        tmnxSubMgmtMdaSPppDhcp6Pd        ,
        tmnxSubMgmtMdaSPppDhcp6PdPeak    ,
        tmnxSubMgmtMdaSPppDhcp6Na        ,
        tmnxSubMgmtMdaSPppDhcp6NaPeak    ,
        tmnxSubMgmtMdaSIpoeSlaac         ,
        tmnxSubMgmtMdaSIpoeSlaacPeak     ,
        tmnxSubMgmtMdaSIpoeDhcp6Pd       ,
        tmnxSubMgmtMdaSIpoeDhcp6PdPeak   ,
        tmnxSubMgmtMdaSIpoeDhcp6Na       ,
        tmnxSubMgmtMdaSIpoeDhcp6NaPeak   ,
        tmnxSubMgmtMdaSV4                ,
        tmnxSubMgmtMdaSV4Peak            ,
        tmnxSubMgmtMdaSV6                ,
        tmnxSubMgmtMdaSV6Peak            ,
        tmnxSubMgmtMdaSPppHosts          ,
        tmnxSubMgmtMdaSPppHostsPeak      ,
        tmnxSubMgmtMdaSIpoeHosts         ,
        tmnxSubMgmtMdaSIpoeHostsPeak     ,
        tmnxSubMgmtMdaSTotal             ,
        tmnxSubMgmtMdaSTotalPeak         ,
        tmnxSubMgmtMdaSPppLclOE          ,
        tmnxSubMgmtMdaSPppLclOEPeak      ,
        tmnxSubMgmtMdaSPppLclOEOA        ,
        tmnxSubMgmtMdaSPppLclOEOAPeak    ,
        tmnxSubMgmtMdaSPppLclOA          ,
        tmnxSubMgmtMdaSPppLclOAPeak      ,
        tmnxSubMgmtMdaSPppLclL2tp        ,
        tmnxSubMgmtMdaSPppLclL2tpPeak    ,
        tmnxSubMgmtMdaSPppLclTotal       ,
        tmnxSubMgmtMdaSPppLclTotalPeak   ,
        tmnxSubMgmtMdaSPppLacOE          ,
        tmnxSubMgmtMdaSPppLacOEPeak      ,
        tmnxSubMgmtMdaSPppLacOEOA        ,
        tmnxSubMgmtMdaSPppLacOEOAPeak    ,
        tmnxSubMgmtMdaSPppLacOA          ,
        tmnxSubMgmtMdaSPppLacOAPeak      ,
        tmnxSubMgmtMdaSPppLacL2tp        ,
        tmnxSubMgmtMdaSPppLacL2tpPeak    ,
        tmnxSubMgmtMdaSPppLacTotal       ,
        tmnxSubMgmtMdaSPppLacTotalPeak   ,
        tmnxSubMgmtMdaSPppSessIs         ,
        tmnxSubMgmtMdaSPppSessIsPeak     ,
        tmnxSubMgmtMdaSPppSessTotal      ,
        tmnxSubMgmtMdaSPppSessTotalPeak  ,
        tmnxSubMgmtMdaSSubscribers       ,
        tmnxSubMgmtMdaSSubscribersPeak   ,

        tmnxSubMgmtSlotSIpcp             ,
        tmnxSubMgmtSlotSIpcpPeak         ,
        tmnxSubMgmtSlotSL2tpHost         ,
        tmnxSubMgmtSlotSL2tpHostPeak     ,
        tmnxSubMgmtSlotSDhcp             ,
        tmnxSubMgmtSlotSDhcpPeak         ,
        tmnxSubMgmtSlotSArp              ,
        tmnxSubMgmtSlotSArpPeak          ,
        tmnxSubMgmtSlotSStatic           ,
        tmnxSubMgmtSlotSStaticPeak       ,
        tmnxSubMgmtSlotSNonSub           ,
        tmnxSubMgmtSlotSNonSubPeak       ,
        tmnxSubMgmtSlotSPppSlaac         ,
        tmnxSubMgmtSlotSPppSlaacPeak     ,
        tmnxSubMgmtSlotSPppDhcp6Pd       ,
        tmnxSubMgmtSlotSPppDhcp6PdPeak   ,
        tmnxSubMgmtSlotSPppDhcp6Na       ,
        tmnxSubMgmtSlotSPppDhcp6NaPeak   ,
        tmnxSubMgmtSlotSIpoeSlaac        ,
        tmnxSubMgmtSlotSIpoeSlaacPeak    ,
        tmnxSubMgmtSlotSIpoeDhcp6Pd      ,
        tmnxSubMgmtSlotSIpoeDhcp6PdPeak  ,
        tmnxSubMgmtSlotSIpoeDhcp6Na      ,
        tmnxSubMgmtSlotSIpoeDhcp6NaPeak  ,
        tmnxSubMgmtSlotSV4               ,
        tmnxSubMgmtSlotSV4Peak           ,
        tmnxSubMgmtSlotSV6               ,
        tmnxSubMgmtSlotSV6Peak           ,
        tmnxSubMgmtSlotSPppHosts         ,
        tmnxSubMgmtSlotSPppHostsPeak     ,
        tmnxSubMgmtSlotSIpoeHosts        ,
        tmnxSubMgmtSlotSIpoeHostsPeak    ,
        tmnxSubMgmtSlotSTotal            ,
        tmnxSubMgmtSlotSTotalPeak        ,
        tmnxSubMgmtSlotSPppLclOE         ,
        tmnxSubMgmtSlotSPppLclOEPeak     ,
        tmnxSubMgmtSlotSPppLclOEOA       ,
        tmnxSubMgmtSlotSPppLclOEOAPeak   ,
        tmnxSubMgmtSlotSPppLclOA         ,
        tmnxSubMgmtSlotSPppLclOAPeak     ,
        tmnxSubMgmtSlotSPppLclL2tp       ,
        tmnxSubMgmtSlotSPppLclL2tpPeak   ,
        tmnxSubMgmtSlotSPppLclTotal      ,
        tmnxSubMgmtSlotSPppLclTotalPeak  ,
        tmnxSubMgmtSlotSPppLacOE         ,
        tmnxSubMgmtSlotSPppLacOEPeak     ,
        tmnxSubMgmtSlotSPppLacOEOA       ,
        tmnxSubMgmtSlotSPppLacOEOAPeak   ,
        tmnxSubMgmtSlotSPppLacOA         ,
        tmnxSubMgmtSlotSPppLacOAPeak     ,
        tmnxSubMgmtSlotSPppLacL2tp       ,
        tmnxSubMgmtSlotSPppLacL2tpPeak   ,
        tmnxSubMgmtSlotSPppLacTotal      ,
        tmnxSubMgmtSlotSPppLacTotalPeak  ,
        tmnxSubMgmtSlotSPppSessIs        ,
        tmnxSubMgmtSlotSPppSessIsPeak    ,
        tmnxSubMgmtSlotSPppSessTotal     ,
        tmnxSubMgmtSlotSPppSessTotalPeak ,
        tmnxSubMgmtSlotSSubscribers      ,
        tmnxSubMgmtSlotSSubscribersPeak  ,

        tmnxSubMgmtSystSIpcp             ,
        tmnxSubMgmtSystSIpcpPeak         ,
        tmnxSubMgmtSystSL2tpHost         ,
        tmnxSubMgmtSystSL2tpHostPeak     ,
        tmnxSubMgmtSystSDhcp             ,
        tmnxSubMgmtSystSDhcpPeak         ,
        tmnxSubMgmtSystSArp              ,
        tmnxSubMgmtSystSArpPeak          ,
        tmnxSubMgmtSystSStatic           ,
        tmnxSubMgmtSystSStaticPeak       ,
        tmnxSubMgmtSystSNonSub           ,
        tmnxSubMgmtSystSNonSubPeak       ,
        tmnxSubMgmtSystSPppSlaac         ,
        tmnxSubMgmtSystSPppSlaacPeak     ,
        tmnxSubMgmtSystSPppDhcp6Pd       ,
        tmnxSubMgmtSystSPppDhcp6PdPeak   ,
        tmnxSubMgmtSystSPppDhcp6Na       ,
        tmnxSubMgmtSystSPppDhcp6NaPeak   ,
        tmnxSubMgmtSystSIpoeSlaac        ,
        tmnxSubMgmtSystSIpoeSlaacPeak    ,
        tmnxSubMgmtSystSIpoeDhcp6Pd      ,
        tmnxSubMgmtSystSIpoeDhcp6PdPeak  ,
        tmnxSubMgmtSystSIpoeDhcp6Na      ,
        tmnxSubMgmtSystSIpoeDhcp6NaPeak  ,
        tmnxSubMgmtSystSV4               ,
        tmnxSubMgmtSystSV4Peak           ,
        tmnxSubMgmtSystSV6               ,
        tmnxSubMgmtSystSV6Peak           ,
        tmnxSubMgmtSystSPppHosts         ,
        tmnxSubMgmtSystSPppHostsPeak     ,
        tmnxSubMgmtSystSIpoeHosts        ,
        tmnxSubMgmtSystSIpoeHostsPeak    ,
        tmnxSubMgmtSystSTotal            ,
        tmnxSubMgmtSystSTotalPeak        ,
        tmnxSubMgmtSystSPppLclOE         ,
        tmnxSubMgmtSystSPppLclOEPeak     ,
        tmnxSubMgmtSystSPppLclOEOA       ,
        tmnxSubMgmtSystSPppLclOEOAPeak   ,
        tmnxSubMgmtSystSPppLclOA         ,
        tmnxSubMgmtSystSPppLclOAPeak     ,
        tmnxSubMgmtSystSPppLclL2tp       ,
        tmnxSubMgmtSystSPppLclL2tpPeak   ,
        tmnxSubMgmtSystSPppLclTotal      ,
        tmnxSubMgmtSystSPppLclTotalPeak  ,
        tmnxSubMgmtSystSPppLacOE         ,
        tmnxSubMgmtSystSPppLacOEPeak     ,
        tmnxSubMgmtSystSPppLacOEOA       ,
        tmnxSubMgmtSystSPppLacOEOAPeak   ,
        tmnxSubMgmtSystSPppLacOA         ,
        tmnxSubMgmtSystSPppLacOAPeak     ,
        tmnxSubMgmtSystSPppLacL2tp       ,
        tmnxSubMgmtSystSPppLacL2tpPeak   ,
        tmnxSubMgmtSystSPppLacTotal      ,
        tmnxSubMgmtSystSPppLacTotalPeak  ,
        tmnxSubMgmtSystSPppSessIs        ,
        tmnxSubMgmtSystSPppSessIsPeak    ,
        tmnxSubMgmtSystSPppSessTotal     ,
        tmnxSubMgmtSystSPppSessTotalPeak ,
        tmnxSubMgmtSystSL2tpTunOrig      ,
        tmnxSubMgmtSystSL2tpTunOrigPeak  ,
        tmnxSubMgmtSystSL2tpTunRecv      ,
        tmnxSubMgmtSystSL2tpTunRecvPeak  ,
        tmnxSubMgmtSystSL2tpTunTotal     ,
        tmnxSubMgmtSystSL2tpTunTotalPeak ,
        tmnxSubMgmtSystSSubscribers      ,
        tmnxSubMgmtSystSSubscribersPeak  ,
        
        tmnxSubMgmtPwPortSIpcp           ,
        tmnxSubMgmtPwPortSIpcpPk         ,
        tmnxSubMgmtPwPortSL2tpHost       ,
        tmnxSubMgmtPwPortSL2tpHostPk     ,
        tmnxSubMgmtPwPortSDhcp           ,
        tmnxSubMgmtPwPortSDhcpPk         ,
        tmnxSubMgmtPwPortSArp            ,
        tmnxSubMgmtPwPortSArpPk          ,
        tmnxSubMgmtPwPortSStatic         ,
        tmnxSubMgmtPwPortSStaticPk       ,
        tmnxSubMgmtPwPortSNonSub         ,
        tmnxSubMgmtPwPortSNonSubPk       ,
        tmnxSubMgmtPwPortSPppSlaac       ,
        tmnxSubMgmtPwPortSPppSlaacPk     ,
        tmnxSubMgmtPwPortSPppDhcp6Pd     ,
        tmnxSubMgmtPwPortSPppDhcp6PdPk   ,
        tmnxSubMgmtPwPortSPppDhcp6Na     ,
        tmnxSubMgmtPwPortSPppDhcp6NaPk   ,
        tmnxSubMgmtPwPortSIpoeSlaac      ,
        tmnxSubMgmtPwPortSIpoeSlaacPk    ,
        tmnxSubMgmtPwPortSIpoeDhcp6Pd    ,
        tmnxSubMgmtPwPortSIpoeDhcp6PdPk  ,
        tmnxSubMgmtPwPortSIpoeDhcp6Na    ,
        tmnxSubMgmtPwPortSIpoeDhcp6NaPk  ,
        tmnxSubMgmtPwPortSV4             ,
        tmnxSubMgmtPwPortSV4Pk           ,
        tmnxSubMgmtPwPortSV6             ,
        tmnxSubMgmtPwPortSV6Pk           ,
        tmnxSubMgmtPwPortSPppHosts       ,
        tmnxSubMgmtPwPortSPppHostsPk     ,
        tmnxSubMgmtPwPortSIpoeHosts      ,
        tmnxSubMgmtPwPortSIpoeHostsPk    ,
        tmnxSubMgmtPwPortSTotal          ,
        tmnxSubMgmtPwPortSTotalPk        ,
        tmnxSubMgmtPwPortSPppLclOE       ,
        tmnxSubMgmtPwPortSPppLclOEPk     ,
        tmnxSubMgmtPwPortSPppLclOEOA     ,
        tmnxSubMgmtPwPortSPppLclOEOAPk   ,
        tmnxSubMgmtPwPortSPppLclOA       ,
        tmnxSubMgmtPwPortSPppLclOAPk     ,
        tmnxSubMgmtPwPortSPppLclL2tp     ,
        tmnxSubMgmtPwPortSPppLclL2tpPk   ,
        tmnxSubMgmtPwPortSPppLclTotal    ,
        tmnxSubMgmtPwPortSPppLclTotalPk  ,
        tmnxSubMgmtPwPortSPppLacOE       ,
        tmnxSubMgmtPwPortSPppLacOEPk     ,
        tmnxSubMgmtPwPortSPppLacOEOA     ,
        tmnxSubMgmtPwPortSPppLacOEOAPk   ,
        tmnxSubMgmtPwPortSPppLacOA       ,
        tmnxSubMgmtPwPortSPppLacOAPk     ,
        tmnxSubMgmtPwPortSPppLacL2tp     ,
        tmnxSubMgmtPwPortSPppLacL2tpPk   ,
        tmnxSubMgmtPwPortSPppLacTotal    ,
        tmnxSubMgmtPwPortSPppLacTotalPk  ,
        tmnxSubMgmtPwPortSPppSessIs      ,
        tmnxSubMgmtPwPortSPppSessIsPk    ,
        tmnxSubMgmtPwPortSPppSessTotal   ,
        tmnxSubMgmtPwPortSPppSessTotalPk ,
        tmnxSubMgmtPwPortSSubscribers    ,
        tmnxSubMgmtPwPortSSubscribersPk  
        }
    STATUS      current
    DESCRIPTION
        "The group of objects supporting management of subscriber profiles on
         release 11.0 of the Nokia SROS series systems."
    ::= { tmnxSubMgmtGroups 69 }

tmnxHsmdaSubscriberV10v0Group OBJECT-GROUP
    OBJECTS {
        tmnxSubInfoEgrSecShaper,
        tmnxSubHsmdaStSubPortId,
        tmnxSubHsmdaStIngOffTotalPkt,
        tmnxSubHsmdaStIngOffTotalOct,
        tmnxSubHsmdaStIngFwdInProfPkt,
        tmnxSubHsmdaStIngFwdOutProfPkt,
        tmnxSubHsmdaStIngFwdInProfOct,
        tmnxSubHsmdaStIngFwdOutProfOct,
        tmnxSubHsmdaStIngDropHiPrioPkt,
        tmnxSubHsmdaStIngDropLoPrioPkt,
        tmnxSubHsmdaStIngDropHiPrioOct,
        tmnxSubHsmdaStIngDropLoPrioOct,
        tmnxSubHsmdaStEgrFwdInProfPkt,
        tmnxSubHsmdaStEgrFwdOutProfPkt,
        tmnxSubHsmdaStEgrFwdInProfOct,
        tmnxSubHsmdaStEgrFwdOutProfOct,
        tmnxSubHsmdaStEgrDropInProfPkt,
        tmnxSubHsmdaStEgrDropOutProfPkt,
        tmnxSubHsmdaStEgrDropInProfOct,
        tmnxSubHsmdaStEgrDropOutProfOct,
        tmnxSubIngQStatsSubPortId,
        tmnxSubIngQStatsOffTotalPkts,
        tmnxSubIngQStatsOffTotalOcts,
        tmnxSubIngQStatsFwdInProfPkts,
        tmnxSubIngQStatsFwdOutProfPkts,
        tmnxSubIngQStatsFwdInProfOcts,
        tmnxSubIngQStatsFwdOutProfOcts,
        tmnxSubIngQStatsDropHiPrioPkts,
        tmnxSubIngQStatsDropLoPrioPkts,
        tmnxSubIngQStatsDropHiPrioOcts,
        tmnxSubIngQStatsDropLoPrioOcts,
        tmnxSubEgrQStatsSubPortId,
        tmnxSubEgrQStatsFwdInProfPkts,
        tmnxSubEgrQStatsFwdOutProfPkts,
        tmnxSubEgrQStatsFwdInProfOcts,
        tmnxSubEgrQStatsFwdOutProfOcts,
        tmnxSubEgrQStatsDropInProfPkts,
        tmnxSubEgrQStatsDropOutProfPkts,
        tmnxSubEgrQStatsDropInProfOcts,
        tmnxSubEgrQStatsDropOutProfOcts,
        tmnxSubEgrOvrCntrSubPortId,
        tmnxSubEgrOvrCntrFwdInProfPkts,
        tmnxSubEgrOvrCntrFwdOutProfPkts,
        tmnxSubEgrOvrCntrFwdInProfOcts,
        tmnxSubEgrOvrCntrFwdOutProfOcts,
        tmnxSubEgrOvrCntrDropInProfPkts,
        tmnxSubEgrOvrCntrDropOutProfPkts,
        tmnxSubEgrOvrCntrDropInProfOcts,
        tmnxSubEgrOvrCntrDropOutProfOcts
    }
    STATUS      current
    DESCRIPTION
        "The group of objects supporting management HSMDA-related of subscriber
         profiles on release 10.0 of the Nokia SROS series systems."
    ::= { tmnxSubMgmtGroups 70 }

tmnxSubObsoletedV10v0Group OBJECT-GROUP
    OBJECTS {
        tmnxSubProfIngQosPolId,
        tmnxSubProfEgrQosPolId,
        tmnxSubProfHsmdaIngAggRateLimit,
        tmnxSubProfHsmdaEgrAggRateLimit,
        tmnxSubProfHsmdaIngPackByteOff,
        tmnxSubProfHsmdaEgrPackByteOff,
        tmnxSubHsmdaIngQueueOvrTableLC,
        tmnxSubHsmdaEgrQueueOvrTblLC,
        tmnxSubHsmdaIngQueueOvrRowStat,
        tmnxSubHsmdaIngQueueOvrLastChgd,
        tmnxSubHsmdaIngQueueOvrPIR,
        tmnxSubHsmdaIngQueueOvrCIR,
        tmnxSubHsmdaIngQueueOvrSlpPlcy,
        tmnxSubHsmdaEgrQueueOvrRowStat,
        tmnxSubHsmdaEgrQueueOvrLastChgd,
        tmnxSubHsmdaEgrQueueOvrPIR,
        tmnxSubHsmdaEgrQueueOvrCIR,
        tmnxSubHsmdaEgrQueueOvrSlpPlcy,
        tmnxSubIngOvrCntrSubPortId,
        tmnxSubIngOvrCntrOffTotalPkts,
        tmnxSubIngOvrCntrOffTotalOcts,
        tmnxSubIngOvrCntrFwdInProfPkts,
        tmnxSubIngOvrCntrFwdOutProfPkts,
        tmnxSubIngOvrCntrFwdInProfOcts,
        tmnxSubIngOvrCntrFwdOutProfOcts,
        tmnxSubIngOvrCntrDropHiPrioPkts,
        tmnxSubIngOvrCntrDropLoPrioPkts,
        tmnxSubIngOvrCntrDropHiPrioOcts,
        tmnxSubIngOvrCntrDropLoPrioOcts
    }   
    STATUS      current
    DESCRIPTION
        "The group of obsoleted objects for subscriber management on
         Nokia SROS series systems in release 10.0."
    ::= { tmnxSubMgmtGroups 71 }

tmnxSubV6GrpIfRAV11v0Group OBJECT-GROUP
    OBJECTS {
        tmnxSubV6GrpIfRATableLastChange,
        tmnxSubV6GrpIfRALastChanged,
        tmnxSubV6GrpIfRAAdminState,
        tmnxSubV6GrpIfRACurHopLimit,
        tmnxSubV6GrpIfRAManagedCfg,
        tmnxSubV6GrpIfRAMaxInterval,
        tmnxSubV6GrpIfRAMinInterval,
        tmnxSubV6GrpIfRALinkMTU,
        tmnxSubV6GrpIfRAOtherCfg,
        tmnxSubV6GrpIfRAPfxOptAutonomous,
        tmnxSubV6GrpIfRAPfxOptPrefLtime,
        tmnxSubV6GrpIfRAPfxOptValidLtime,
        tmnxSubV6GrpIfRAReachableTime,
        tmnxSubV6GrpIfRARetransmitTime,
        tmnxSubV6GrpIfRARouterLifetime,
        tmnxSubV6GrpIfRADnsOptInclDns,
        tmnxSubV6GrpIfRADnsOptRdnssLtime
    }
    STATUS      current
    DESCRIPTION
        "Group of objects supporting IPv6 Router Advertisements for Neighbor 
         Discovery for Group Interfaces on Nokia SROS series systems in
         release 11.0."
    ::= { tmnxSubMgmtGroups 72 }
    
tmnxSubPppV11v0Group   OBJECT-GROUP
    OBJECTS {
        tmnxSubPppType,                     
        tmnxSubPppUpTime,                         
        tmnxSubPppDescription,                         
        tmnxSubPppLcpState,
        tmnxSubPppIpcpState,
        tmnxSubPppIpv6cpState,
        tmnxSubPppPppMtu,                         
        tmnxSubPppPppAuthProtocol,                
        tmnxSubPppPppUserName,               
        tmnxSubPppSubIdent,                       
        tmnxSubPppSubProfString,                  
        tmnxSubPppSlaProfString,                  
        tmnxSubPppAncpString,                     
        tmnxSubPppInterDestId,
        tmnxSubPppAppProfString,                  
        tmnxSubPppCategoryMapName,
        tmnxSubPppIpAddrType,                     
        tmnxSubPppIpAddr,
        tmnxSubPppIpAddrPrefixLength,
        tmnxSubPppOriginIp,                 
        tmnxSubPppPrimaryDnsType,                 
        tmnxSubPppPrimaryDns,                     
        tmnxSubPppSecondaryDnsType,               
        tmnxSubPppSecondaryDns,
        tmnxSubPppOriginDns,
        tmnxSubPppPrimaryNbnsType,                
        tmnxSubPppPrimaryNbns,                    
        tmnxSubPppSecondaryNbnsType,
        tmnxSubPppSecondaryNbns,
        tmnxSubPppOriginNbns,                 
        tmnxSubPppInterfaceId,                    
        tmnxSubPppIpv6Dns1Type,                    
        tmnxSubPppIpv6Dns1,                       
        tmnxSubPppIpv6Dns2Type,
        tmnxSubPppIpv6Dns2,                      
        tmnxSubPppIpv6DelPfxType,
        tmnxSubPppIpv6DelPfxLen,
        tmnxSubPppIpv6DelPfxOrigin,
        tmnxSubPppIpv6DelPfxPool,
        tmnxSubPppIpv6DelPfx,                     
        tmnxSubPppIpv6PrefixType,                 
        tmnxSubPppIpv6PrefixLen,                  
        tmnxSubPppIpv6Prefix,
        tmnxSubPppTerminationType,
        tmnxSubPppRetailerSvcId,
        tmnxSubPppRetailerIf,
        tmnxSubPppLacVrtrId,
        tmnxSubPppLacConnectionId,
        tmnxSubPppSessionTimeout,
        tmnxSubPppCircuitId,
        tmnxSubPppRemoteId,
        tmnxSubPppAddressPool,
        tmnxSubPppRadiusClassAttr,
        tmnxSubPppRadiusUserName,
        tmnxSubPppSvcId,
        tmnxSubPppSubIf,
        tmnxSubPppGrpIf,
        tmnxSubPppPortId,
        tmnxSubPppEncapValue,
        tmnxSubPppStatRxUnknownProto,       
        tmnxSubPppStatRxLcpConfReq,        
        tmnxSubPppStatRxLcpConfAck,        
        tmnxSubPppStatRxLcpConfNak,        
        tmnxSubPppStatRxLcpConfRej,
        tmnxSubPppStatRxLcpTermReq,        
        tmnxSubPppStatRxLcpTermAck,        
        tmnxSubPppStatRxLcpCodeRej,
        tmnxSubPppStatRxLcpEchoReq,
        tmnxSubPppStatRxLcpEchoRep,
        tmnxSubPppStatRxLcpProtRej,
        tmnxSubPppStatRxLcpDiscReq,
        tmnxSubPppStatTxLcpConfReq,
        tmnxSubPppStatTxLcpConfAck,
        tmnxSubPppStatTxLcpConfNak,
        tmnxSubPppStatTxLcpConfRej,
        tmnxSubPppStatTxLcpTermReq,
        tmnxSubPppStatTxLcpTermAck,
        tmnxSubPppStatTxLcpCodeRej,
        tmnxSubPppStatTxLcpEchoReq,
        tmnxSubPppStatTxLcpEchoRep,
        tmnxSubPppStatTxLcpProtRej,
        tmnxSubPppStatTxLcpDiscReq,
        tmnxSubPppStatRxPapAuthReq,
        tmnxSubPppStatTxPapAuthAck,
        tmnxSubPppStatTxPapAuthNak,
        tmnxSubPppStatRxChapResponse,
        tmnxSubPppStatTxChapChallenge,
        tmnxSubPppStatTxChapSuccess,
        tmnxSubPppStatTxChapFailure,
        tmnxSubPppStatRxIpcpConfReq,
        tmnxSubPppStatRxIpcpConfAck,
        tmnxSubPppStatRxIpcpConfNak,
        tmnxSubPppStatRxIpcpConfRej,
        tmnxSubPppStatRxIpcpTermReq,
        tmnxSubPppStatRxIpcpTermAck,
        tmnxSubPppStatRxIpcpCodeRej,
        tmnxSubPppStatTxIpcpConfReq,
        tmnxSubPppStatTxIpcpConfAck,
        tmnxSubPppStatTxIpcpConfNak,
        tmnxSubPppStatTxIpcpConfRej,
        tmnxSubPppStatTxIpcpTermReq,
        tmnxSubPppStatTxIpcpTermAck,
        tmnxSubPppStatTxIpcpCodeRej,
        tmnxSubPppStatRxIpv6cpConfReq,
        tmnxSubPppStatRxIpv6cpConfAck,
        tmnxSubPppStatRxIpv6cpConfNak,
        tmnxSubPppStatRxIpv6cpConfRej,
        tmnxSubPppStatRxIpv6cpTermReq,
        tmnxSubPppStatRxIpv6cpTermAck,
        tmnxSubPppStatRxIpv6cpCodeRej,
        tmnxSubPppStatTxIpv6cpConfReq,
        tmnxSubPppStatTxIpv6cpConfAck,
        tmnxSubPppStatTxIpv6cpConfNak,
        tmnxSubPppStatTxIpv6cpConfRej,
        tmnxSubPppStatTxIpv6cpTermReq,
        tmnxSubPppStatTxIpv6cpTermAck,
        tmnxSubPppStatTxIpv6cpCodeRej,
        tmnxSubPppMRtStatus,
        tmnxSubPppOvrCBS,
        tmnxSubPppOvrMBS,
        tmnxSubPppAleDatalink,
        tmnxSubPppAleEncaps1, 
        tmnxSubPppAleEncaps2, 
        tmnxSubPppBgpPrngPlcyName, 
        tmnxSubPppBgpAuthKeyChain, 
        tmnxSubPppBgpMD5AuthKey,   
        tmnxSubPppBgpImportPolicy, 
        tmnxSubPppBgpExportPolicy, 
        tmnxSubPppBgpPeerAS,       
        tmnxSubPppBgpPeeringStatus,
        tmnxSubPppModSubIdent,
        tmnxSubPppModSubProfStr,   
        tmnxSubPppModSlaProfStr,   
        tmnxSubPppModAncpStr,      
        tmnxSubPppModInterDestId,  
        tmnxSubPppModAppProfStr,
        tmnxSubPppModEvaluateState,
        tmnxSubPppSessions,
        tmnxSubPppTypeSessions,
        tmnxSubPppUserType,
        tmnxSubPppSvcTypeSessions,
        tmnxSubPppIpv6AddrType,
        tmnxSubPppIpv6Addr,
        tmnxSubPppIpv6AddrOrigin,
        tmnxSubPppIpv6AddrPool,
        tmnxSubPppSessionTimeLeft,
        tmnxSubPppLogicalLineId,
        tmnxSubPppIpv6PrefixOrigin,
        tmnxSubPppIpv6PrefixPool
    }
    STATUS      current
    DESCRIPTION
        "The group of objects for the
         management of subscriber PPP on Nokia SROS series systems in
         release 11.0."
    ::= { tmnxSubMgmtGroups 73 }
    
 tmnxSubObsoletedV11v0Group OBJECT-GROUP
    OBJECTS {
        tmnxSubPppOriginSubIdent,
        tmnxSubPppOriginStrings,
        tmnxSubSlaacOriginSubscrId,
        tmnxSubSlaacOriginStrings,
        tmnxSubPppOriginIpv6cpInfo               
    }   
    STATUS      current
    DESCRIPTION
        "The group of obsoleted objects for subscriber management on
         Nokia SROS series systems in release 11.0."
    ::= { tmnxSubMgmtGroups 74 }  
    
 tmnxSubSlaacV11v0Group OBJECT-GROUP
    OBJECTS {
        tmnxSubSlaacPfxLen,
        tmnxSubSlaacPortId,
        tmnxSubSlaacEncapValue,
        tmnxSubSlaacPppIndex,
        tmnxSubSlaacPersistKey,
        tmnxSubSlaacInterfaceId,
        tmnxSubSlaacCircuitId,
        tmnxSubSlaacRemoteId,
        tmnxSubSlaacSubscrIdent,
        tmnxSubSlaacSubProfString,
        tmnxSubSlaacSlaProfString,
        tmnxSubSlaacAppProfString,
        tmnxSubSlaacCategoryMapName,
        tmnxSubSlaacAncpString,
        tmnxSubSlaacInterDestId,
        tmnxSubSlaacRadiusClassAttr,
        tmnxSubSlaacShcvOperState,
        tmnxSubSlaacShcvChecks,
        tmnxSubSlaacShcvReplies,
        tmnxSubSlaacShcvReplyTime,
        tmnxSubSlaacPrimaryDnsType,
        tmnxSubSlaacPrimaryDns,
        tmnxSubSlaacSecondaryDnsType,
        tmnxSubSlaacSecondaryDns,
        tmnxSubSlaacCreationTime,
        tmnxSubSlaacOriginPfxInfo,
        
        tmnxSubSlaacMRtStatus,
        tmnxSubSlaacMRtMetric,
        tmnxSubSlaacMRtPreference,
        tmnxSubSlaacMRtTag,
        tmnxSubPppMRtMetric,
        tmnxSubPppMRtPreference,
        tmnxSubPppMRtTag,
        tmnxSubSlaacPfxPool
    }
    STATUS      current
    DESCRIPTION
        "The group of objects for the management of stateless address
         autoconfiguration hosts on Nokia SROS series systems
         since release 11.0."
    ::= { tmnxSubMgmtGroups 75 } 

tmnxSubHttpRedirectGroup OBJECT-GROUP
    OBJECTS {
        tmnxSubHttpRdrPlcyTableLastCh,
        tmnxSubHttpRdrPlcyRowStatus,
        tmnxSubHttpRdrPlcyLastCh,
        tmnxSubHttpRdrPlcyDescription,
        tmnxSubHttpRdrPlcyUrl,
        tmnxSubHttpRdrPlcyDestPort,
        tmnxSubHttpRdrPlcyPortalHoldTime,
        tmnxSubHttpRdrFwdTableLastCh,
        tmnxSubHttpRdrFwdRowStatus,
        tmnxSubHttpRdrFwdLastCh
     }
    STATUS      current
    DESCRIPTION
        "The group of subscriber management objects supporting
         HTTP redirection on Nokia SROS series systems."
    ::= { tmnxSubMgmtGroups 76 }
    
tmnxSubAccountingV11v0Group OBJECT-GROUP
    OBJECTS {
        tmnxSubAcctPlcyRadiusServerPlcy,
        tmnxSubAcctPlcyUpdateIvlJitter
    }
    STATUS      current
    DESCRIPTION
        "The group of objects supporting management of subscriber
         accounting policies on Nokia SROS series systems
         since release 11.0."
    ::= { tmnxSubMgmtGroups 77 }

tmnxSubServiceGroup OBJECT-GROUP
    OBJECTS {
        tmnxSubSvcName,
        tmnxSubSvcType,
        tmnxSubSvcAcctType,
        tmnxSubSvcAcctUpdateIvl,
        tmnxSubSvcAttrType,
        tmnxSubSvcAttrString,
        tmnxSubSvcAcctSessionId,
        tmnxSubSvcUpTime,
        tmnxSubSvcInPckts,
        tmnxSubSvcInOcts,
        tmnxSubSvcOutPckts,
        tmnxSubSvcOutOcts
    }
    STATUS      current
    DESCRIPTION
        "The group of objects supporting management of subscriber
         services on Nokia SROS series systems
         since release 11.0."
    ::= { tmnxSubMgmtGroups 78 }

tmnxSubSchedulerRateV11v0Group OBJECT-GROUP
    OBJECTS {
        tmnxSubProfSchedOvrPIRHi,
        tmnxSubProfSchedOvrPIRLo,
        tmnxSubProfSchedOvrCIRHi,
        tmnxSubProfSchedOvrCIRLo,
        tmnxSLAProfInstOvrPIRHi,
        tmnxSLAProfInstOvrPIRLo,
        tmnxSLAProfInstOvrCIRHi,
        tmnxSLAProfInstOvrCIRLo,
        tmnxSubOvrPIRHi,
        tmnxSubOvrPIRLo,
        tmnxSubOvrCIRHi,
        tmnxSubOvrCIRLo,
        tmnxSubPppOvrPIRHi,
        tmnxSubPppOvrPIRLo,
        tmnxSubPppOvrCIRHi,
        tmnxSubPppOvrCIRLo
    }
    STATUS      current
    DESCRIPTION
        "The group of objects supporting management of Scheduler policies
         on Nokia SROS series systems release 11.0."
    ::= { tmnxSubMgmtGroups 79 } 

tmnxSubMgmtQosV11v0Group   OBJECT-GROUP
    OBJECTS {
        tmnxSubProfRowStatus,
        tmnxSubProfLastMgmtChange,
        tmnxSubProfDescription,
        tmnxSubProfIngQosSchedPolicy,
        tmnxSubProfEgrQosSchedPolicy,
        tmnxSubProfCollectAcctStats,
        tmnxSubProfAccountingPolicyId,
        tmnxSubProfEgrAggRateLimit,
        tmnxSubProfRadiusAcctPolicy,
        tmnxSubProfDuplRadiusAcctPolicy,
        tmnxSubProfUseDirectSLAMapAsDef,

        tmnxSubProfSchedOvrRowStatus,
        tmnxSubProfSchedOvrLastMgmtChange,
        tmnxSubProfSchedOvrSummedCIR,

        tmnxSubProfSLAProfMapRowStatus,
        tmnxSubProfSLAProfMapLastMgmtChange,
        tmnxSubProfSLAProfMapSLAProfile,

        tmnxSLAProfRowStatus,
        tmnxSLAProfLastMgmtChange,
        tmnxSLAProfDescription,
        tmnxSLAProfHostLimit,
        tmnxSLAProfRemoveOldest,
        tmnxSLAProfIngQosPolId,
        tmnxSLAProfIngSharedQPolicy,
        tmnxSLAProfIngUseMpointShared,
        tmnxSLAProfIngIPFilterId,
        tmnxSLAProfEgrQosPolId,
        tmnxSLAProfEgrIPFilterId,
        tmnxSLAProfReportIngRateType,
        tmnxSLAProfReportIngRateSched,
        tmnxSLAProfReportEgrRateType,
        tmnxSLAProfReportEgrRateSched,
        tmnxSLAProfEgrQosMarkingFromSap,
        tmnxSLAProfEgrSchedulerType,
        tmnxSLAProfOTHttpRdrIpv4FltrId,
        tmnxSLAProfEgrUseIngL2tpDscp,

        tmnxSLAIngQueueOvrRowStatus,
        tmnxSLAIngQueueOvrLastMgmtChange,
        tmnxSLAIngQueueOvrPIR,
        tmnxSLAIngQueueOvrCIR,
        tmnxSLAIngQueueOvrCBS,
        tmnxSLAIngQueueOvrHiPrioOnly,
        tmnxSLAIngQueueOvrMBSBytes,

        tmnxSLAEgrQueueOvrRowStatus,
        tmnxSLAEgrQueueOvrLastMgmtChange,
        tmnxSLAEgrQueueOvrPIR,
        tmnxSLAEgrQueueOvrCIR,
        tmnxSLAEgrQueueOvrCBS,
        tmnxSLAEgrQueueOvrHiPrioOnly,
        tmnxSLAEgrQueueOvrAvgOverhead,
        tmnxSLAEgrQueueOvrMBSBytes,

        tmnxSubExplicitMapRowStatus,
        tmnxSubExplicitMapLastMgmtChange,
        tmnxSubExplicitMapSubProfile,
        tmnxSubExplicitMapSLAProfile,
        tmnxSubExplicitMapAlias,

        tmnxSubIPolRowStatus,
        tmnxSubIPolLastMgmtChange,
        tmnxSubIPolDescription,
        tmnxSubIPolScript1URL,
        tmnxSubIPolScript1AdminState,
        tmnxSubIPolScript1OperState,
        tmnxSubIPolScript2URL,
        tmnxSubIPolScript2AdminState,
        tmnxSubIPolScript2OperState,
        tmnxSubIPolScript3URL,
        tmnxSubIPolScript3AdminState,
        tmnxSubIPolScript3OperState,
        tmnxSubIPolUseDirectSubMapAsDef,
        tmnxSubIPolUseDirectSLAMapAsDef,
        tmnxSubIPolRejectUnknownStrings,
        tmnxSubIPolStringsFromOption,

        tmnxSubIPolSubProfMapRowStatus,
        tmnxSubIPolSubProfMapLastMgmtChange,
        tmnxSubIPolSubProfMapSubProfile,

        tmnxSubIPolSLAProfMapRowStatus,
        tmnxSubIPolSLAProfMapLastMgmtChange,
        tmnxSubIPolSLAProfMapSLAProfile,

        tmnxSubInfoSubProfile,
        tmnxSubInfoSubAncpString,
        tmnxSubInfoNumSubProfileChanges,
        tmnxSubInfoIntermediateDestId,
        tmnxSubInfoModifySubIdent,

        tmnxSubIngQosSchedStatsFwdPkts,
        tmnxSubIngQosSchedStatsFwdOctets,

        tmnxSubEgrQosSchedStatsFwdPkts,
        tmnxSubEgrQosSchedStatsFwdOctets,

        tmnxSPIStatsIngPchipOffHiPrioPkts,
        tmnxSPIStatsIngPchipOffHiPrioOctets,
        tmnxSPIStatsIngPchipOffLoPrioPkts,
        tmnxSPIStatsIngPchipOffLoPrioOctets,
        tmnxSPIStatsIngPchipOffUncolPkts,
        tmnxSPIStatsIngPchipOffUncolOctets,
        tmnxSPIStatsIngQchipDropHiPrioPkts,
        tmnxSPIStatsIngQchipDropHiPrioOctets,
        tmnxSPIStatsIngQchipDropLoPrioPkts,
        tmnxSPIStatsIngQchipDropLoPrioOctets,
        tmnxSPIStatsIngQchipFwdInProfPkts,
        tmnxSPIStatsIngQchipFwdInProfOctets,
        tmnxSPIStatsIngQchipFwdOutProfPkts,
        tmnxSPIStatsIngQchipFwdOutProfOctets,
        tmnxSPIStatsEgrQchipDropInProfPkts,
        tmnxSPIStatsEgrQchipDropInProfOctets,
        tmnxSPIStatsEgrQchipDropOutProfPkts,
        tmnxSPIStatsEgrQchipDropOutProfOctets,
        tmnxSPIStatsEgrQchipFwdInProfPkts,
        tmnxSPIStatsEgrQchipFwdInProfOctets,
        tmnxSPIStatsEgrQchipFwdOutProfPkts,
        tmnxSPIStatsEgrQchipFwdOutProfOctets,

        tmnxSPIIngQStatsOffHiPrioPkts,
        tmnxSPIIngQStatsDropHiPrioPkts,
        tmnxSPIIngQStatsOffLoPrioPkts,
        tmnxSPIIngQStatsDropLoPrioPkts,
        tmnxSPIIngQStatsOffHiPrioOctets,
        tmnxSPIIngQStatsDropHiPrioOctets,
        tmnxSPIIngQStatsOffLoPrioOctets,
        tmnxSPIIngQStatsDropLoPrioOctets,
        tmnxSPIIngQStatsOffUncolPkts,
        tmnxSPIIngQStatsOffUncolOctets,
        tmnxSPIIngQStatsFwdInProfPkts,
        tmnxSPIIngQStatsFwdOutProfPkts,
        tmnxSPIIngQStatsFwdInProfOctets,
        tmnxSPIIngQStatsFwdOutProfOctets,

        tmnxSPIEgrQStatsFwdInProfPkts,
        tmnxSPIEgrQStatsDropInProfPkts,
        tmnxSPIEgrQStatsFwdOutProfPkts,
        tmnxSPIEgrQStatsDropOutProfPkts,
        tmnxSPIEgrQStatsFwdInProfOctets,
        tmnxSPIEgrQStatsDropInProfOctets,
        tmnxSPIEgrQStatsFwdOutProfOctets,
        tmnxSPIEgrQStatsDropOutProfOctets,

        tmnxSubHostInfoV2FwdingState,
        tmnxSubHostInfoV2Origin,
        tmnxSubHostInfoV2SubIdent,
        tmnxSubHostInfoV2SubProfile,
        tmnxSubHostInfoV2SLAProfile,
        tmnxSubHostInfoV2RetailerSvcId,
        tmnxSubHostInfoV2RetailerIf,
        tmnxSubHostInfoV2PfxLen,
        tmnxSubHostInfoV2EgrQGrpName,
        tmnxSubHostInfoV2EgrVPortName,
        tmnxSubHostInfoV2AcctSessionId,
        tmnxSubHostInfoV2AddressOrigin,
        tmnxSubHostInfoV2PppIndex,
        tmnxSubHostInfoV2AcctMultiSessId,
        tmnxSubHostInfoV2IngFilter, 
        tmnxSubHostInfoV2EgrFilter,  
        tmnxSubHostInfoV2OtHttpRdrState,
        tmnxSubHostInfoV2OtHttpRdrFilter,
        tmnxSubHostInfoV2OtHttpRdrSource,
              
        
        tmnxSPISubHostV2Origin,
        tmnxSPISubHostV2PfxLen,

        tmnxSPIInfoCategoryMapName,
        tmnxSPIInfoDiamSessId,
        
        tmnxSLAIngPlcrOverrideTblLstChng,
        tmnxSLAEgrPlcrOverrideTblLstChng,
        tmnxSLAIngPolicerOvrRowStatus,      
        tmnxSLAIngPolicerOvrLastMgmtChg, 
        tmnxSLAIngPolicerOvrPIR,            
        tmnxSLAIngPolicerOvrCIR,            
        tmnxSLAIngPolicerOvrMBS,            
        tmnxSLAIngPolicerOvrCBS,            
        tmnxSLAIngPolicerOvrPktOffset,      
        tmnxSLAIngPolicerOvrStatMode,        
        tmnxSLAEgrPolicerOvrRowStatus,     
        tmnxSLAEgrPolicerOvrLastMgmtChg,
        tmnxSLAEgrPolicerOvrPIR,           
        tmnxSLAEgrPolicerOvrCIR,           
        tmnxSLAEgrPolicerOvrMBS,           
        tmnxSLAEgrPolicerOvrCBS,           
        tmnxSLAEgrPolicerOvrPktOffset,     
        tmnxSLAEgrPolicerOvrStatMode,
        tmnxSubProfPCtrlOvrRowStatus,  
        tmnxSubProfPCtrlOvrTblLstChng,
        tmnxSubProfPCtrlOvrLastChange, 
        tmnxSubProfPCtrlOvrMaxRate,    
        tmnxSubProfPCtrlOvrMinMBSSep,  
        tmnxSubProfPCtrlLvlOvrTblLstChng,
        tmnxSubProfPCtrlLvlOvrRowStatus,  
        tmnxSubProfPCtrlLvlOvrLastChange, 
        tmnxSubProfPCtrlLvlOvrCumMBS,
        
        tmnxSPIIngPStatsMode,
        tmnxSPIIngPStatsOffHiPrioPkts,
        tmnxSPIIngPStatsOffHiPrioPktsL,
        tmnxSPIIngPStatsOffHiPrioPktsH,
        tmnxSPIIngPStatsDrpHiPrioPkts,
        tmnxSPIIngPStatsDrpHiPrioPktsL,
        tmnxSPIIngPStatsDrpHiPrioPktsH,
        tmnxSPIIngPStatsOffLoPrioPkts,
        tmnxSPIIngPStatsOffLoPrioPktsL,
        tmnxSPIIngPStatsOffLoPrioPktsH,
        tmnxSPIIngPStatsDrpLoPrioPkts,
        tmnxSPIIngPStatsDrpLoPrioPktsL,
        tmnxSPIIngPStatsDrpLoPrioPktsH,
        tmnxSPIIngPStatsOffHiPrioOcts,
        tmnxSPIIngPStatsOffHiPrioOctsL,
        tmnxSPIIngPStatsOffHiPrioOctsH,
        tmnxSPIIngPStatsDrpHiPrioOcts,
        tmnxSPIIngPStatsDrpHiPrioOctsL,
        tmnxSPIIngPStatsDrpHiPrioOctsH,
        tmnxSPIIngPStatsOffLoPrioOcts,
        tmnxSPIIngPStatsOffLoPrioOctsL,
        tmnxSPIIngPStatsOffLoPrioOctsH,
        tmnxSPIIngPStatsDrpLoPrioOcts,
        tmnxSPIIngPStatsDrpLoPrioOctsL,
        tmnxSPIIngPStatsDrpLoPrioOctsH,
        tmnxSPIIngPStatsOffUncolPkts,
        tmnxSPIIngPStatsOffUncolPktsL,
        tmnxSPIIngPStatsOffUncolPktsH,
        tmnxSPIIngPStatsOffUncolOcts,
        tmnxSPIIngPStatsOffUncolOctsL,
        tmnxSPIIngPStatsOffUncolOctsH,
        tmnxSPIIngPStatsFwdInProfPkts,
        tmnxSPIIngPStatsFwdInProfPktsL,
        tmnxSPIIngPStatsFwdInProfPktsH,
        tmnxSPIIngPStatsFwdOutProfPkts,
        tmnxSPIIngPStatsFwdOutProfPktsL,
        tmnxSPIIngPStatsFwdOutProfPktsH,
        tmnxSPIIngPStatsFwdInProfOcts,
        tmnxSPIIngPStatsFwdInProfOctsL,
        tmnxSPIIngPStatsFwdInProfOctsH,
        tmnxSPIIngPStatsFwdOutProfOcts,
        tmnxSPIIngPStatsFwdOutProfOctsL,
        tmnxSPIIngPStatsFwdOutProfOctsH,
      
        tmnxSPIEgrPStatsMode,
        tmnxSPIEgrPStatsOffInProfPkts,
        tmnxSPIEgrPStatsOffInProfPktsL,
        tmnxSPIEgrPStatsOffInProfPktsH,
        tmnxSPIEgrPStatsFwdInProfPkts,
        tmnxSPIEgrPStatsFwdInProfPktsL,
        tmnxSPIEgrPStatsFwdInProfPktsH,
        tmnxSPIEgrPStatsDrpInProfPkts,
        tmnxSPIEgrPStatsDrpInProfPktsL,
        tmnxSPIEgrPStatsDrpInProfPktsH,
        tmnxSPIEgrPStatsOffOutProfPkts,
        tmnxSPIEgrPStatsOffOutProfPktsL,
        tmnxSPIEgrPStatsOffOutProfPktsH,
        tmnxSPIEgrPStatsFwdOutProfPkts,
        tmnxSPIEgrPStatsFwdOutProfPktsL,
        tmnxSPIEgrPStatsFwdOutProfPktsH,
        tmnxSPIEgrPStatsDrpOutProfPkts,
        tmnxSPIEgrPStatsDrpOutProfPktsL,
        tmnxSPIEgrPStatsDrpOutProfPktsH,
        tmnxSPIEgrPStatsOffInProfOcts,
        tmnxSPIEgrPStatsOffInProfOctsL,
        tmnxSPIEgrPStatsOffInProfOctsH,
        tmnxSPIEgrPStatsFwdInProfOcts,
        tmnxSPIEgrPStatsFwdInProfOctsL,
        tmnxSPIEgrPStatsFwdInProfOctsH,
        tmnxSPIEgrPStatsDrpInProfOcts,
        tmnxSPIEgrPStatsDrpInProfOctsL,
        tmnxSPIEgrPStatsDrpInProfOctsH,
        tmnxSPIEgrPStatsOffOutProfOcts,
        tmnxSPIEgrPStatsOffOutProfOctsL,
        tmnxSPIEgrPStatsOffOutProfOctsH,
        tmnxSPIEgrPStatsFwdOutProfOcts,
        tmnxSPIEgrPStatsFwdOutProfOctsL,
        tmnxSPIEgrPStatsFwdOutProfOctsH,
        tmnxSPIEgrPStatsDrpOutProfOcts,
        tmnxSPIEgrPStatsDrpOutProfOctsL,
        tmnxSPIEgrPStatsDrpOutProfOctsH,
        tmnxSPIEgrPStatsOffUncolPkts,
        tmnxSPIEgrPStatsOffUncolPktsL,
        tmnxSPIEgrPStatsOffUncolPktsH,
        tmnxSPIEgrPStatsOffUncolOcts,
        tmnxSPIEgrPStatsOffUncolOctsL,
        tmnxSPIEgrPStatsOffUncolOctsH,
       
        tmnxSubIngQosArbitStatsFwdPkts,
        tmnxSubIngQosArbitStatsFwdPktsLo,
        tmnxSubIngQosArbitStatsFwdPktsHi,
        tmnxSubIngQosArbitStatsFwdOcts,
        tmnxSubIngQosArbitStatsFwdOctsLo,
        tmnxSubIngQosArbitStatsFwdOctsHi,
        tmnxSubEgrQosArbitStatsFwdPkts,
        tmnxSubEgrQosArbitStatsFwdPktsLo,
        tmnxSubEgrQosArbitStatsFwdPktsHi,
        tmnxSubEgrQosArbitStatsFwdOcts,
        tmnxSubEgrQosArbitStatsFwdOctsLo,
        tmnxSubEgrQosArbitStatsFwdOctsHi,

        tmnxSubIgmpPlcyRowStatus,
        tmnxSubIgmpPlcyDescription,
        tmnxSubIgmpPlcyImportPolicy,
        tmnxSubIgmpPlcyHostMaxGroups,
        tmnxSubIgmpPlcyAdminVersion,
        tmnxSubIgmpPlcyFastLeave,
        tmnxSubIgmpPlcyRedirectionPolicy,
        tmnxSubIgmpPlcyEgrRateModType,
        tmnxSubIgmpPlcyEgrRateModSched,
        tmnxSubIgmpPlcyPerHostReplic,
        tmnxSubIgmpPlcyMcRprtDestName,
        tmnxSubIgmpPlcyMcRprtOptFields,
        tmnxSubIgmpPlcyMcRprtAdminState,

        tmnxSubIgmpPlcyStaticRowStatus,

        tmnxSLAProfInstOvrCBS,
        tmnxSLAProfInstOvrMBS,
        tmnxSubOvrCBS,
        tmnxSubOvrMBS,

        tmnxSubIgmpHostsCreated,
        
        tmnxSubIgmpPlcySubscriberId,
        tmnxSubIgmpStatusPlcyName,
        tmnxSubInfoRadEgrAggRateLimit,
        tmnxSubInfoEgrAggRateLimit,
        
        tmnxSubMcacPlcyRowStatus,
        tmnxSubMcacPlcyDescription,
        tmnxSubMcacPlcyAdminState,
        tmnxSubMcacPlcyUnconstrainedBW,
        tmnxSubMcacPlcyPreRsvdMandBW,
        tmnxSubMcacPlcyLastMgmtChange,
        
        tmnxSubMcacPlcySubscriberId,

        tmnxSubMcacStatusPlcyName,
        tmnxSubMcacStatusinUseMandBw,
        tmnxSubMcacStatusinUseOpnlBw,
        tmnxSubMcacStatusAvailMandBw,
        tmnxSubMcacStatusAvailOpnlBw,
        tmnxSubFlterProfRowStatus,
        
        tmnxSubLcktPlcyRowStatus,
        tmnxSubLcktPlcyLastMgmtChange,
        tmnxSubLcktPlcyDescription,
        tmnxSubLcktPlcyLcktTimeMin,
        tmnxSubLcktPlcyLcktTimeMax,
        tmnxSubLcktPlcyLcktResetTime,
        tmnxSubLcktPlcyMaxLcktHosts,
        tmnxSubLcktPlcyHostKey,
        
        tmnxSubIgmpPlcyHostMaxSources
        }
    STATUS      current
    DESCRIPTION
        "The group of objects supporting management of subscriber profiles on
         release 11.0 of the Nokia SROS series systems."
    ::= { tmnxSubMgmtGroups 80 }

tmnxSubMgmtObsoletedV11v0Group OBJECT-GROUP
    OBJECTS {     
        tmnxSubProfSchedOvrPIR,
        tmnxSubProfSchedOvrCIR,
        tmnxSLAProfInstOvrPIR,
        tmnxSLAProfInstOvrCIR,
        tmnxSubOvrPIR,
        tmnxSubOvrCIR,
        tmnxSubPppOvrPIR,
        tmnxSubPppOvrCIR
   }
    STATUS      current
    DESCRIPTION
        "The group of objects obsoleted supporting management of subscriber
         profiles on Nokia SROS series systems release 11.0."
    ::= { tmnxSubMgmtGroups 81 }

tmnxSubMgmtObsoletedV12v0Group OBJECT-GROUP
    OBJECTS {
        tmnxSubAuthPlcyRadRespAttrSelect,
        tmnxSubRadiusAcceptRowStatus,
        tmnxSubRadiusAcceptLastMgmtCh,
        tmnxSubRadiusAcceptSelective,
        tmnxSubSysNextHopLimit,
        tmnxSubSysNextHopUsageHigh
   }
    STATUS      current
    DESCRIPTION
        "The group of objects obsoleted supporting management of subscriber
         profiles on Nokia SROS series systems release 12.0."
    ::= { tmnxSubMgmtGroups 82 }

tmnxSubAuthenticationV12v0Group OBJECT-GROUP
    OBJECTS {
        tmnxSubAuthPlcyRowStatus,
        tmnxSubAuthPlcyLastMgmtChange,
        tmnxSubAuthPlcyDescription,
        tmnxSubAuthPlcyPassword,
        tmnxSubAuthPlcyRadAuthRetries,
        tmnxSubAuthPlcyRadAuthSrceAddr,
        tmnxSubAuthPlcyRadAuthSrceAddrTp,
        tmnxSubAuthPlcyRadAuthTimeout,
        tmnxSubAuthPlcyReAuthenticate,
        tmnxSubAuthPlcyUserNameFormat,
        tmnxSubAuthPlcyRadAuthVRtrID,
        tmnxSubAuthPlcyAcceptAuthChange,
        tmnxSubAuthPlcyInclAttributes,
        tmnxSubAuthPlcyRadAuthAlgorithm,
        tmnxSubAuthPlcyPppoeAccessMethod,
        tmnxSubAuthPlcyNasPortPfixType,
        tmnxSubAuthPlcyNasPortPfixString,
        tmnxSubAuthPlcyNasPortSfixType,
        tmnxSubAuthPlcyUserNameAppend,
        tmnxSubAuthPlcyFallbackAction,
        tmnxSubAuthPlcyFallbackUserDb,
        tmnxSubAuthPlcyClngStationIdType,
        tmnxSubAuthPlcyNasPortTypeType,
        tmnxSubAuthPlcyNasPortTypeValue,
        tmnxSubAuthPlcyPppUserNameOp,
        tmnxSubAuthPlcyPppDomain,
        tmnxSubAuthPlcyRadAuthDownTime,

        tmnxSubAuthPlcyRadServRowStatus,
        tmnxSubAuthPlcyRadLastMgmtChange,
        tmnxSubAuthPlcyRadServAddress,
        tmnxSubAuthPlcyRadServAddrType,
        tmnxSubAuthPlcyRadServSecret,
        tmnxSubAuthPlcyRadServAuthPort,
        tmnxSubAuthPlcyRadServOperState,
        tmnxSubAuthPlcyRadServCoAOnly,

        tmnxSubAuthPlcySuccess,
        tmnxSubAuthPlcyReject,
        tmnxSubAuthPlcyFallbackSuccess,
        tmnxSubAuthPlcyFallbackReject,

        tmnxSubAuthPlcyRadSuccess,
        tmnxSubAuthPlcyRadReject,
        tmnxSubAuthPlcyRadTimeout,
        tmnxSubAuthPlcyRadMd5Fail,
        tmnxSubAuthPlcyRadPending,
        tmnxSubAuthPlcyRadSendFail,

        tmnxSubAuthPlcyUserNameOp,    
        tmnxSubAuthPlcyDomain,
        tmnxSubAuthPlcyUserNameMacFormat 
    }
   
    STATUS      current
    DESCRIPTION
        "The group of objects supporting management of subscriber
         authentication policies on Nokia SROS series systems
         added in release 12.0."
    ::= { tmnxSubMgmtGroups 83 }

tmnxSubMgmtV12v0Group   OBJECT-GROUP
    OBJECTS {
        tmnxSubProfMldPolicy            ,
        
        tmnxSubMldPlcyRowStatus         ,
        tmnxSubMldPlcyDescription       ,
        tmnxSubMldPlcyImportPolicy      ,
        tmnxSubMldPlcyHostMaxGroups     ,
        tmnxSubMldPlcyAdminVersion      ,
        tmnxSubMldPlcyFastLeave         ,
        tmnxSubMldPlcyRedirectionPolicy ,    
        tmnxSubMldPlcyEgrRateModType    ,
        tmnxSubMldPlcyEgrRateModSched   ,
        tmnxSubMldPlcyPerHostReplic     ,
        tmnxSubMldPlcyMcRprtDestName    ,
        tmnxSubMldPlcyMcRprtOptFields   ,
        tmnxSubMldPlcyMcRprtAdminState  ,
        tmnxSubMldPlcyHostMaxSources    ,
        tmnxSubMldPlcyHostMaxGrpSources ,
        
        tmnxSubMldPlcyStaticRowStatus   ,
        
        tmnxSubMldHostsCreated          ,
        
        tmnxSubMldPlcySubscriberId      ,
        
        tmnxSubMldStatusPlcyName        ,
        
        tmnxSubHostInfoV2HttpRdrUrlOvrd ,
        tmnxSubProfVolumeStatsType      ,
        tmnxSPISubHostV2Service,
        tmnxSubV6GrpIfRAForceMcast      ,
        tmnxSubSlaacLastRsAuth          ,
        tmnxSubSlaacInactivityTimeExp   ,
        tmnxSubV6GrpIfNDTableLastChange ,
        tmnxSubV6GrpIfNDLastChanged     ,
        tmnxSubV6GrpIfNDNeighborLimit   ,
        tmnxSubV6GrpIfNDNeighborDadSnoop,
        tmnxSubHostInfoV2GtpLclBrkout,
        tmnxSubHostInfoV2DiamSessId,
        tmnxSubV6GrpIfRAPfxOptOnLink,
        tmnxSubSlaacOvrPIR,
        tmnxSubSlaacOvrCIR,
        tmnxSubSlaacOvrCBS,
        tmnxSubSlaacOvrMBS,
        tmnxSubSlaacOvrWrrWeight,
        tmnxSPIIngQStatModeFormat,
        tmnxSPIEgrQStatModeFormat,
        tmnxSubSlaacAddrShcvOperState,
        tmnxSubSlaacAddrShcvChecks,
        tmnxSubSlaacAddrShcvReplies,
        tmnxSubSlaacAddrShcvReplyTime,
        tmnxSubProfLagTableLastChange,
        tmnxSubProfLagLastChanged,
        tmnxSubProfLagPlhClass,
        tmnxSubProfLagPlhWeight
        }
    STATUS      current
    DESCRIPTION
        "The group of objects supporting subscriber management on
         release 12.0 of the Nokia SROS series systems."
    ::= { tmnxSubMgmtGroups 84 }

tmnxSubMgmtQosV12v0Group   OBJECT-GROUP
    OBJECTS {
        tmnxSPIEgrQosSchedStatsFwdPkts,
        tmnxSPIEgrQosSchedStatsFwdOctets,
        tmnxSubPppSapSessionIndex,
        tmnxSLAIngQueueOvrStatMode,
        tmnxSLAEgrQueueOvrStatMode,
        tmnxSubHsmdaEgrQosQStatMode,
        tmnxSubHsmdaIngQosQTableLastCh,
        tmnxSubHsmdaIngQosQRowStatus,
        tmnxSubHsmdaIngQosQLastChgd,
        tmnxSubHsmdaIngQosQStatMode,
        tmnxSubHsmdaIngQosPolTableLastCh,
        tmnxSubHsmdaIngQosPolRowStatus,
        tmnxSubHsmdaIngQosPolLastChgd,
        tmnxSubHsmdaIngQosPolStatMode,
        tmnxSPIStatsIngPchipOffV4Pkts,
        tmnxSPIStatsIngPchipOffV4Octets,
        tmnxSPIStatsIngPchipOffV6Pkts,
        tmnxSPIStatsIngPchipOffV6Octets,
        tmnxSPIStatsIngQchipDropV4Pkts,
        tmnxSPIStatsIngQchipDropV4Octets,
        tmnxSPIStatsIngQchipDropV6Pkts,
        tmnxSPIStatsIngQchipDropV6Octets,
        tmnxSPIStatsIngQchipFwdV4Pkts,
        tmnxSPIStatsIngQchipFwdV4Octets,
        tmnxSPIStatsIngQchipFwdV6Pkts,
        tmnxSPIStatsIngQchipFwdV6Octets,
        tmnxSPIStatsEgrQchipDropV4Pkts,
        tmnxSPIStatsEgrQchipDropV4Octets,
        tmnxSPIStatsEgrQchipDropV6Pkts,
        tmnxSPIStatsEgrQchipDropV6Octets,
        tmnxSPIStatsEgrQchipFwdV4Pkts,
        tmnxSPIStatsEgrQchipFwdV4Octets,
        tmnxSPIStatsEgrQchipFwdV6Pkts,
        tmnxSPIStatsEgrQchipFwdV6Octets
        }
    STATUS      current
    DESCRIPTION
        "The group of objects supporting management of subscriber profiles on
         the Nokia SROS series systems added in release 12.0."
    ::= { tmnxSubMgmtGroups 85 }
    
tmnxSubSchedulerRateV12v0Group OBJECT-GROUP
    OBJECTS {
        tmnxSLAProfSchedOvrRowStatus,
        tmnxSLAProfSchedOvrLastChange,
        tmnxSLAProfSchedOvrSummedCIR,
        tmnxSLAProfSchedOvrPIRHi,
        tmnxSLAProfSchedOvrPIRLo,
        tmnxSLAProfSchedOvrCIRHi,
        tmnxSLAProfSchedOvrCIRLo
    }
    STATUS      current
    DESCRIPTION
        "The group of objects supporting management of Scheduler policies
         on Nokia SROS series systems release 12.0."
    ::= { tmnxSubMgmtGroups 86 }

tmnxSubSysGroup OBJECT-GROUP
    OBJECTS {
        tmnxSubSysChassMemoryUsageHigh
    }
    STATUS      current
    DESCRIPTION
        "The group of objects supporting management at system level
          of subscriber management on Nokia SROS series."
    ::= { tmnxSubMgmtGroups 87 }

tmnxSubHttpRedirectV12v0Group OBJECT-GROUP
    OBJECTS {
        tmnxSubHttpRdrFwdDestIpPfxLen
     }
    STATUS      current
    DESCRIPTION
        "The group of subscriber management objects supporting
         HTTP redirection added in release 12.0
         of Nokia SROS series systems."
    ::= { tmnxSubMgmtGroups 88 }
    
tmnxSubVSubnetV12v0Group OBJECT-GROUP
    OBJECTS {
        tmnxSubVSubnetDefRtrAddrType,
        tmnxSubVSubnetDefRtrAddr,
        tmnxSubVSubnetPrefixLength, 
        tmnxSubVSubnetSapPortId,
        tmnxSubVSubnetSapEncapValue
     }
    STATUS      current
    DESCRIPTION
        "The group of subscriber management objects supporting
         virtual subnetting in release 12.0
         of Nokia SROS series systems."
    ::= { tmnxSubMgmtGroups 89 }
    
tmnxSubSlaacV12v0Group OBJECT-GROUP
    OBJECTS {
        tmnxSubSlaacEvaluate,
        tmnxSubSlaacModifySubscrIdent,
        tmnxSubSlaacModifySubProfString,
        tmnxSubSlaacModifySlaProfString,
        tmnxSubSlaacModifyAppProfString,
        tmnxSubSlaacModifyInterDestId,
        tmnxSubSlaacModifyAncpString
    }
    STATUS      current
    DESCRIPTION
        "The group of new objects for the management of stateless address
         autoconfiguration hosts on Nokia SROS series systems
         introduced in release 12.0."
    ::= { tmnxSubMgmtGroups 90 } 

tmnxSubObsoletedV12v0Group OBJECT-GROUP
    OBJECTS {
        tmnxSubAcctPlcyUseStdAcctAttrib
    }
    STATUS      current
    DESCRIPTION
        "The group of obsoleted objects for subscriber management on
         Nokia SROS series systems."
    ::= { tmnxSubMgmtGroups 91 }

tmnxSubAccountingV12v0Group   OBJECT-GROUP
    OBJECTS {
        tmnxSubAcctPlcyRowStatus,
        tmnxSubAcctPlcyLastMgmtChange,
        tmnxSubAcctPlcyDescription,
        tmnxSubAcctPlcySessionIdFormat,
        tmnxSubAcctPlcyInclAttributes,
        tmnxSubAcctPlcyUpdateIvl,
        tmnxSubAcctPlcyServVRtrID,
        tmnxSubAcctPlcyServRetry,
        tmnxSubAcctPlcyServSrcAddrTp,
        tmnxSubAcctPlcyServSrcAddr,
        tmnxSubAcctPlcyServTimeout,
        tmnxSubAcctPlcyServAlgorithm,
        tmnxSubAcctPlcyNasPortPfixType,
        tmnxSubAcctPlcyNasPortPfixString,
        tmnxSubAcctPlcyNasPortSfixType,
        tmnxSubAcctPlcyNasPortTypeType,
        tmnxSubAcctPlcyNasPortTypeValue,

        tmnxSubAcctPlcyHostAccounting,
        tmnxSubAcctPlcyClngStationIdType,
        tmnxSubAcctPlcyNasPortBitspec,

        tmnxSubAcctPlcyRadServRowStatus,
        tmnxSubAcctPlcyRadServLstMgtChg,
        tmnxSubAcctPlcyRadServAddrType,
        tmnxSubAcctPlcyRadServAddr,
        tmnxSubAcctPlcyRadServSecret,
        tmnxSubAcctPlcyRadServAcctPort,
        tmnxSubAcctPlcyRadServOperState,

        tmnxSubAcctPlcyTxRequests,
        tmnxSubAcctPlcyRxResponses,
        tmnxSubAcctPlcyReqTimeouts,
        tmnxSubAcctPlcySendRetries,
        tmnxSubAcctPlcySendFail,

        tmnxSubAcctPlcyRadTxRequests,
        tmnxSubAcctPlcyRadRxResponses,
        tmnxSubAcctPlcyRadReqTimeouts,
        tmnxSubAcctPlcyRadReqSendFail
    }
    STATUS      current
    DESCRIPTION
        "The group of objects supporting management of subscriber
         accounting policies on Nokia SROS series systems."
    ::= { tmnxSubMgmtGroups 92 }

tmnxSubHsmdaV12v0Group   OBJECT-GROUP
    OBJECTS {
        tmnxSubIngQStatModeFormat,
        tmnxSubEgrQStatModeFormat,
        tmnxSubEgrOvrCntrStatModeFormat,
        tmnxSubHsmdaStIngOffV4Packets,
        tmnxSubHsmdaStIngOffV4Octets,
        tmnxSubHsmdaStIngOffV6Packets,
        tmnxSubHsmdaStIngOffV6Octets,
        tmnxSubHsmdaStIngDropV4Packets,
        tmnxSubHsmdaStIngDropV4Octets,
        tmnxSubHsmdaStIngDropV6Packets,
        tmnxSubHsmdaStIngDropV6Octets,
        tmnxSubHsmdaStIngFwdV4Packets,
        tmnxSubHsmdaStIngFwdV4Octets,
        tmnxSubHsmdaStIngFwdV6Packets,
        tmnxSubHsmdaStIngFwdV6Octets,
        tmnxSubHsmdaStEgrDropV4Packets,
        tmnxSubHsmdaStEgrDropV4Octets,
        tmnxSubHsmdaStEgrDropV6Packets,
        tmnxSubHsmdaStEgrDropV6Octets,
        tmnxSubHsmdaStEgrFwdV4Packets,
        tmnxSubHsmdaStEgrFwdV4Octets,
        tmnxSubHsmdaStEgrFwdV6Packets,
        tmnxSubHsmdaStEgrFwdV6Octets
    }
    STATUS      current
    DESCRIPTION
        "The group of new subscriber management objects supporting
         management of HSMDA-2 on Nokia SROS series systems in
         release 12.0."
    ::= { tmnxSubMgmtGroups 93 }

tmnxSubQosParentLocV12v0Group   OBJECT-GROUP
    OBJECTS {
        tmnxSLAProfEgrQosSchedPolicy
        }
    STATUS      current
    DESCRIPTION
        "The group of objects supporting management of subscriber profiles on
         the Nokia SROS series systems added in release 12.0."
    ::= { tmnxSubMgmtGroups 94 }

tmnxSubIpoeV13v0Group   OBJECT-GROUP
    OBJECTS {
        tmnxSubIpoePlcyTableLastChanged,
        tmnxSubIpoePlcyLastChanged,
        tmnxSubIpoePlcyRowStatus,
        tmnxSubIpoePlcyDescription,
        tmnxSubIpoePlcySessionKey,
        tmnxSubIpoePlcySessionTimeout,
        tmnxSubIpoeRetailerSvcId,
        tmnxSubIpoeRetailerIf,
        tmnxSubIpoeCircuitId,
        tmnxSubIpoeRemoteId,      
        tmnxSubIpoeGrpIf,
        tmnxSubIpoeSubIf,        
        tmnxSubIpoeUpTime,
        tmnxSubIpoeSessionTimeLeft,
        tmnxSubIpoeLastAuthTime,
        tmnxSubIpoeMinAuthIntervalLeft,
        tmnxSubIpoePersistenceKey,
        tmnxSubIpoeSubIdent,       
        tmnxSubIpoeSubProfString,
        tmnxSubIpoeSlaProfString,       
        tmnxSubIpoeAncpString,
        tmnxSubIpoeInterDestId,
        tmnxSubIpoeAppProfString,
        tmnxSubIpoeCategoryMapName,
        tmnxSubIpoeAcctSessionId,
        tmnxSubIpoeSapSessionIndex,        
        tmnxSubIpoeIpAddrType,
        tmnxSubIpoeIpAddr,
        tmnxSubIpoeIpAddrPrefixLength,
        tmnxSubIpoeOriginIp,       
        tmnxSubIpoePrimaryDnsType,
        tmnxSubIpoePrimaryDns,
        tmnxSubIpoeSecondaryDnsType,
        tmnxSubIpoeSecondaryDns,
        tmnxSubIpoePrimaryNbnsType,
        tmnxSubIpoePrimaryNbns,
        tmnxSubIpoeSecondaryNbnsType,
        tmnxSubIpoeSecondaryNbns,
        tmnxSubIpoeAddressPool,
        tmnxSubIpoeIpv6PrefixType,
        tmnxSubIpoeIpv6Prefix,
        tmnxSubIpoeIpv6PrefixLen,
        tmnxSubIpoeIpv6PrefixOrigin,
        tmnxSubIpoeIpv6PrefixPool,
        tmnxSubIpoeIpv6DelPfxType,
        tmnxSubIpoeIpv6DelPfx,
        tmnxSubIpoeIpv6DelPfxLen,
        tmnxSubIpoeIpv6DelPfxOrigin,
        tmnxSubIpoeIpv6DelPfxPool,
        tmnxSubIpoeIpv6AddrType,
        tmnxSubIpoeIpv6Addr,
        tmnxSubIpoeIpv6AddrOrigin,
        tmnxSubIpoeIpv6AddrPool,
        tmnxSubIpoeIpv6Dns1Type,
        tmnxSubIpoeIpv6Dns1,
        tmnxSubIpoeIpv6Dns2Type,
        tmnxSubIpoeIpv6Dns2,        
        tmnxSubIpoeSessionTimeout,
        tmnxSubIpoeRadiusClassAttr,
        tmnxSubIpoeRadiusUserName,
        tmnxSubIpoeSessionTimeStamp,
        tmnxSubHostInfoV2IpoeIndex,
        tmnxSubIpoeModSubIdent,
        tmnxSubIpoeModSubProfStr,
        tmnxSubIpoeModSlaProfStr,
        tmnxSubIpoeModAncpStr,
        tmnxSubIpoeModInterDestId,
        tmnxSubIpoeModAppProfStr,
        tmnxSubIpoeModEvaluateState,
        tmnxSubIpoeBgpPrngPlcyName,
        tmnxSubIpoeBgpAuthKeyChain,
        tmnxSubIpoeBgpMD5AuthKey,
        tmnxSubIpoeBgpImportPolicy,
        tmnxSubIpoeBgpExportPolicy,
        tmnxSubIpoeBgpPeerAS,
        tmnxSubIpoeBgpPeeringStatus,
        tmnxSubIpoeOvrCBS,
        tmnxSubIpoeOvrMBS,
        tmnxSubIpoeOvrWrrWeight,
        tmnxSubIpoeOvrPIRHi,
        tmnxSubIpoeOvrPIRLo,
        tmnxSubIpoeOvrCIRHi,
        tmnxSubIpoeOvrCIRLo,
        tmnxSubIpoeOvrSummedCIR,
        tmnxSubIpoeMRtStatus,
        tmnxSubIpoeMRtMetric,
        tmnxSubIpoeMRtPreference,
        tmnxSubIpoeMRtTag,
        tmnxSubIpoeBgpIpv6PrngPlcyName,
        tmnxSubIpoeBgpIpv6AuthKeyChain,
        tmnxSubIpoeBgpIpv6MD5AuthKey,
        tmnxSubIpoeBgpIpv6ImportPolicy,
        tmnxSubIpoeBgpIpv6ExportPolicy,
        tmnxSubIpoeBgpIpv6PeerAS
      , tmnxSubIpoeTerminationType
        }
    STATUS      current
    DESCRIPTION
        "The group of objects supporting management of subscriber 
         IPoE session policies on the Nokia SROS series
         systems added in release 13.0."
    ::= { tmnxSubMgmtGroups 95 }
    
tmnxSubMgmtV13v0Group   OBJECT-GROUP
    OBJECTS {
        tmnxSLAProfHostLimV4             ,
        tmnxSLAProfHostLimV4Ppp          ,
        tmnxSLAProfHostLimV4Dhcp         ,
        tmnxSLAProfHostLimV4Arp          ,
        tmnxSLAProfHostLimV6             ,
        tmnxSLAProfHostLimV6Wan          ,
        tmnxSLAProfHostLimV6WanPppSlaac  ,
        tmnxSLAProfHostLimV6WanPppDhcp   ,
        tmnxSLAProfHostLimV6WanIpoeSlaac ,
        tmnxSLAProfHostLimV6WanIpoeDhcp  ,
        tmnxSLAProfHostLimV6Pd           ,
        tmnxSLAProfHostLimV6PdPppDhcp    ,
        tmnxSLAProfHostLimV6PdIpoeDhcp   ,
        tmnxSLAProfHostLimLac            ,
        tmnxSubMgmtPortSDhcpBsmAs        ,
        tmnxSubMgmtPortSDhcpBsmAsPeak    , 
        tmnxSubMgmtPortSStaticBsmAs      ,
        tmnxSubMgmtPortSStaticBsmAsPeak  , 
        tmnxSubMgmtPortSDhcpBsm          ,
        tmnxSubMgmtPortSDhcpBsmPeak      , 
        tmnxSubMgmtPortSStaticBsm        ,
        tmnxSubMgmtPortSStaticBsmPeak    , 
        tmnxSubMgmtPortSPppDhcp6Mr       ,
        tmnxSubMgmtPortSPppDhcp6MrPeak   ,
        tmnxSubMgmtPortSIpoeDhcp6Mr      ,
        tmnxSubMgmtPortSIpoeDhcp6MrPeak  ,
        tmnxSubMgmtPortSV6StaticWan      ,
        tmnxSubMgmtPortSV6StaticWanPeak  ,
        tmnxSubMgmtPortSBsmDhcp6Pd       ,
        tmnxSubMgmtPortSBsmDhcp6PdPeak   ,
        tmnxSubMgmtPortSBsmDhcp6Na       ,
        tmnxSubMgmtPortSBsmDhcp6NaPeak   ,
        tmnxSubMgmtPortSTotInternal      ,
        tmnxSubMgmtPortSTotInternalPeak  ,
        tmnxSubMgmtPortSTotDhcp          ,
        tmnxSubMgmtPortSTotDhcpPeak      ,
        tmnxSubMgmtPortSTotDhcpV6        ,
        tmnxSubMgmtPortSTotDhcpV6Peak    ,
        tmnxSubMgmtPortSTotMngdRt        ,
        tmnxSubMgmtPortSTotMngdRtPeak    ,
        tmnxSubMgmtPortSIpoeSesIs        ,
        tmnxSubMgmtPortSIpoeSesIsPeak    ,
        tmnxSubMgmtPortSIpoeSesTotal     ,
        tmnxSubMgmtPortSIpoeSesTotalPeak ,
        tmnxSubMgmtPortSV6StaticPd       ,
        tmnxSubMgmtPortSV6StaticPdPeak   ,
        tmnxSubMgmtMdaSDhcpBsmAs         ,
        tmnxSubMgmtMdaSDhcpBsmAsPeak     ,   
        tmnxSubMgmtMdaSStaticBsmAs       ,
        tmnxSubMgmtMdaSStaticBsmAsPeak   , 
        tmnxSubMgmtMdaSDhcpBsm           ,
        tmnxSubMgmtMdaSDhcpBsmPeak       ,   
        tmnxSubMgmtMdaSStaticBsm         ,
        tmnxSubMgmtMdaSStaticBsmPeak     , 
        tmnxSubMgmtMdaSPppDhcp6Mr        ,
        tmnxSubMgmtMdaSPppDhcp6MrPeak    ,
        tmnxSubMgmtMdaSIpoeDhcp6Mr       ,
        tmnxSubMgmtMdaSIpoeDhcp6MrPeak   ,
        tmnxSubMgmtMdaSV6StaticWan       ,
        tmnxSubMgmtMdaSV6StaticWanPeak   ,
        tmnxSubMgmtMdaSBsmDhcp6Pd        ,
        tmnxSubMgmtMdaSBsmDhcp6PdPeak    ,
        tmnxSubMgmtMdaSBsmDhcp6Na        ,
        tmnxSubMgmtMdaSBsmDhcp6NaPeak    ,
        tmnxSubMgmtMdaSTotInternal       ,
        tmnxSubMgmtMdaSTotInternalPeak   ,
        tmnxSubMgmtMdaSTotDhcp           ,
        tmnxSubMgmtMdaSTotDhcpPeak       ,
        tmnxSubMgmtMdaSTotDhcpV6         ,
        tmnxSubMgmtMdaSTotDhcpV6Peak     ,
        tmnxSubMgmtMdaSTotMngdRt         ,
        tmnxSubMgmtMdaSTotMngdRtPeak     ,
        tmnxSubMgmtMdaSIpoeSesIs         ,
        tmnxSubMgmtMdaSIpoeSesIsPeak     ,
        tmnxSubMgmtMdaSIpoeSesTotal      ,
        tmnxSubMgmtMdaSIpoeSesTotalPeak  ,
        tmnxSubMgmtMdaSV6StaticPd        ,
        tmnxSubMgmtMdaSV6StaticPdPeak    ,
        tmnxSubMgmtSlotSDhcpBsmAs        ,
        tmnxSubMgmtSlotSDhcpBsmAsPeak    ,   
        tmnxSubMgmtSlotSStaticBsmAs      ,
        tmnxSubMgmtSlotSStaticBsmAsPeak  , 
        tmnxSubMgmtSlotSDhcpBsm          ,
        tmnxSubMgmtSlotSDhcpBsmPeak      ,   
        tmnxSubMgmtSlotSStaticBsm        ,
        tmnxSubMgmtSlotSStaticBsmPeak    , 
        tmnxSubMgmtSlotSPppDhcp6Mr       ,
        tmnxSubMgmtSlotSPppDhcp6MrPeak   ,
        tmnxSubMgmtSlotSIpoeDhcp6Mr      ,
        tmnxSubMgmtSlotSIpoeDhcp6MrPeak  ,
        tmnxSubMgmtSlotSV6StaticWan      ,
        tmnxSubMgmtSlotSV6StaticWanPeak  ,
        tmnxSubMgmtSlotSBsmDhcp6Pd       ,
        tmnxSubMgmtSlotSBsmDhcp6PdPeak   ,
        tmnxSubMgmtSlotSBsmDhcp6Na       ,
        tmnxSubMgmtSlotSBsmDhcp6NaPeak   ,
        tmnxSubMgmtSlotSTotInternal      ,
        tmnxSubMgmtSlotSTotInternalPeak  ,
        tmnxSubMgmtSlotSTotDhcp          ,
        tmnxSubMgmtSlotSTotDhcpPeak      ,
        tmnxSubMgmtSlotSTotDhcpV6        ,
        tmnxSubMgmtSlotSTotDhcpV6Peak    ,
        tmnxSubMgmtSlotSTotMngdRt        ,
        tmnxSubMgmtSlotSTotMngdRtPeak    ,
        tmnxSubMgmtSlotSIpoeSesIs        ,
        tmnxSubMgmtSlotSIpoeSesIsPeak    ,
        tmnxSubMgmtSlotSIpoeSesTotal     ,
        tmnxSubMgmtSlotSIpoeSesTotalPeak ,
        tmnxSubMgmtSlotSV6StaticPd       ,
        tmnxSubMgmtSlotSV6StaticPdPeak   ,
        tmnxSubMgmtSystSDhcpBsmAs        ,
        tmnxSubMgmtSystSDhcpBsmAsPeak    ,
        tmnxSubMgmtSystSStaticBsmAs      ,
        tmnxSubMgmtSystSStaticBsmAsPeak  , 
        tmnxSubMgmtSystSDhcpBsm          ,
        tmnxSubMgmtSystSDhcpBsmPeak      ,
        tmnxSubMgmtSystSStaticBsm        ,
        tmnxSubMgmtSystSStaticBsmPeak    , 
        tmnxSubMgmtSystSPppDhcp6Mr       ,
        tmnxSubMgmtSystSPppDhcp6MrPeak   ,
        tmnxSubMgmtSystSIpoeDhcp6Mr      ,
        tmnxSubMgmtSystSIpoeDhcp6MrPeak  ,
        tmnxSubMgmtSystSV6StaticWan      ,
        tmnxSubMgmtSystSV6StaticWanPeak  ,
        tmnxSubMgmtSystSBsmDhcp6Pd       ,
        tmnxSubMgmtSystSBsmDhcp6PdPeak   ,
        tmnxSubMgmtSystSBsmDhcp6Na       ,
        tmnxSubMgmtSystSBsmDhcp6NaPeak   ,
        tmnxSubMgmtSystSTotInternal      ,
        tmnxSubMgmtSystSTotInternalPeak  ,
        tmnxSubMgmtSystSTotDhcp          ,
        tmnxSubMgmtSystSTotDhcpPeak      ,
        tmnxSubMgmtSystSTotDhcpV6        ,
        tmnxSubMgmtSystSTotDhcpV6Peak    ,
        tmnxSubMgmtSystSTotMngdRt        ,
        tmnxSubMgmtSystSTotMngdRtPeak    ,
        tmnxSubMgmtSystSIpoeSesIs        ,
        tmnxSubMgmtSystSIpoeSesIsPeak    ,
        tmnxSubMgmtSystSIpoeSesTotal     ,
        tmnxSubMgmtSystSIpoeSesTotalPeak ,
        tmnxSubMgmtSystSHostsScale       ,
        tmnxSubMgmtSystSHostsScalePeak   ,
        tmnxSubMgmtSystSV6StaticPd       ,
        tmnxSubMgmtSystSV6StaticPdPeak   ,
        tmnxSubMgmtPwPortSDhcpBsmAs      ,
        tmnxSubMgmtPwPortSDhcpBsmAsPk    , 
        tmnxSubMgmtPwPortSStaticBsmAs    ,
        tmnxSubMgmtPwPortSStaticBsmAsPk  ,
        tmnxSubMgmtPwPortSDhcpBsm        ,
        tmnxSubMgmtPwPortSDhcpBsmPk      , 
        tmnxSubMgmtPwPortSStaticBsm      ,
        tmnxSubMgmtPwPortSStaticBsmPk    ,
        tmnxSubMgmtPwPortSPppDhcp6Mr     ,
        tmnxSubMgmtPwPortSPppDhcp6MrPk   ,
        tmnxSubMgmtPwPortSIpoeDhcp6Mr    ,
        tmnxSubMgmtPwPortSIpoeDhcp6MrPk  ,
        tmnxSubMgmtPwPortSV6StaticWan    ,
        tmnxSubMgmtPwPortSV6StaticWanPk  ,
        tmnxSubMgmtPwPortSBsmDhcp6Pd     ,
        tmnxSubMgmtPwPortSBsmDhcp6PdPk   ,
        tmnxSubMgmtPwPortSBsmDhcp6Na     ,
        tmnxSubMgmtPwPortSBsmDhcp6NaPk   ,
        tmnxSubMgmtPwPortSTotInternal    ,
        tmnxSubMgmtPwPortSTotInternalPk  ,
        tmnxSubMgmtPwPortSTotDhcp        ,
        tmnxSubMgmtPwPortSTotDhcpPk      ,
        tmnxSubMgmtPwPortSTotDhcpV6      ,
        tmnxSubMgmtPwPortSTotDhcpV6Pk    ,
        tmnxSubMgmtPwPortSTotMngdRt      ,
        tmnxSubMgmtPwPortSTotMngdRtPk    ,
        tmnxSubMgmtPwPortSIpoeSesIs      ,
        tmnxSubMgmtPwPortSIpoeSesIsPk    ,
        tmnxSubMgmtPwPortSIpoeSesTotal   ,
        tmnxSubMgmtPwPortSIpoeSesTotalPk ,
        tmnxSubMgmtPwPortSV6StaticPd     ,
        tmnxSubMgmtPwPortSV6StaticPdPk   ,
        tmnxSubProfPimPolicy,
        tmnxSubIgmpPlcyPerHostMcastMac,
        tmnxSubMldPlcyPerHostMcastMac
        }
    STATUS      current
    DESCRIPTION
        "The group of objects supporting subscriber management on
         release 13.0 of the Nokia SROS series systems."
    ::= { tmnxSubMgmtGroups 96 }

tmnxSubRipV13v0Group    OBJECT-GROUP
    OBJECTS {  
        tmnxSubRipPlcyTableLastChanged,
        tmnxSubRipPlcyLastChanged,
        tmnxSubRipPlcyRowStatus,
        tmnxSubRipPlcyDescription,
        tmnxSubRipPlcyAuthType,
        tmnxSubRipPlcyAuthKey,
        tmnxSubPppRipPlcyName,
        tmnxSubPppRipListenerStatus,
        tmnxSubIpoeRipPlcyName,
        tmnxSubIpoeRipListenerStatus
            }
    STATUS        current
    DESCRIPTION
        "The group of objects supporting management of subscriber 
         RIP/RIP-NG policies on the Nokia SROS series
         systems added in release 13.0."
    ::= { tmnxSubMgmtGroups 97 }
    
tmnxSubPimGroup    OBJECT-GROUP
    OBJECTS {
        tmnxSubPimPlcyTableLastChanged,
        tmnxSubPimPlcyRowStatus,
        tmnxSubPimPlcyLastChanged,
        tmnxSubPimPlcyDescription
    }
    STATUS        current
    DESCRIPTION
        "The group of objects supporting management of subscriber 
         PIM policies on the Nokia SROS series."
    ::= { tmnxSubMgmtGroups 98 }
    
tmnxSubSlaacV13v0Group OBJECT-GROUP
    OBJECTS {
      tmnxSubSlaacRetailerSvcId
    , tmnxSubSlaacRetailerIf
    , tmnxSubSlaacTerminationType
    , tmnxSubSlaacBgpPrngPlcyName
    , tmnxSubSlaacBgpAuthKeyChain
    , tmnxSubSlaacBgpMD5AuthKey  
    , tmnxSubSlaacBgpImportPolicy
    , tmnxSubSlaacBgpExportPolicy
    , tmnxSubSlaacBgpPeerAS      
    , tmnxSubSlaacBgpPeeringStatus     
    , tmnxSubSlaacIpoeSessionHost
    , tmnxSubSlaacPppSessionHost
    }
    STATUS      current
    DESCRIPTION
        "The group of objects for the management of stateless address
         autoconfiguration hosts on Nokia SROS series systems
         since release 13.0."
    ::= { tmnxSubMgmtGroups 100 } 
    
tmnxSubPppV13v0Group   OBJECT-GROUP
    OBJECTS {
        tmnxSubPppBgpIpv6PrngPlcyName,                     
        tmnxSubPppBgpIpv6AuthKeyChain,                         
        tmnxSubPppBgpIpv6MD5AuthKey,                         
        tmnxSubPppBgpIpv6ImportPolicy,
        tmnxSubPppBgpIpv6ExportPolicy,
        tmnxSubPppBgpIpv6PeerAS
    }
    STATUS      current
    DESCRIPTION
        "The group of objects for the management of subscriber PPP on 
         Nokia SROS series systems in release 13.0."
    ::= { tmnxSubMgmtGroups 101 }

tmnxSubShcvGroup    OBJECT-GROUP
    OBJECTS {
        tmnxSubShcvPlcyTableLastChanged,
        tmnxSubShcvPlcyRowStatus,
        tmnxSubShcvPlcyLastChanged,
        tmnxSubShcvPlcyDescription,
        tmnxSubShcvPlcyPeriodAdminState,
        tmnxSubShcvPlcyPeriodAction,
        tmnxSubShcvPlcyPeriodInterval,
        tmnxSubShcvPlcyPeriodRetryCount,
        tmnxSubShcvPlcyPeriodRetryTo,
        tmnxSubShcvPlcyVplsSrcIp4AddrTyp,
        tmnxSubShcvPlcyVplsSrcIp4Addr,
        tmnxSubShcvPlcyVplsSrcMacAddress,
        tmnxSubShcvPlcyL3SrcIpOrigin,
        tmnxSubShcvTrigTableLastChanged,
        tmnxSubShcvTrigLastChanged,
        tmnxSubShcvPlcyDescription,
        tmnxSubShcvTrigAdminState,
        tmnxSubShcvTrigRetryCount,
        tmnxSubShcvTrigRetryTo        
    }
    STATUS        current
    DESCRIPTION
        "The group of objects supporting management of subscriber 
         Subscriber Host Connectivity Verification (SHCV) policies
         on the Nokia SROS series."
    ::= { tmnxSubMgmtGroups 102 }
    
tmnxSubPppDfGroup OBJECT-GROUP
    OBJECTS {
        tmnxSubPppIgnoringDfBit
    }
    STATUS      current
    DESCRIPTION
        "The group of objects supporting Don't Fragment behavior control
         for PPPoE hosts on Nokia SROS series systems."
    ::= { tmnxSubMgmtGroups 103 }
  

tmnxSubPccRuleEntryV13v0Group OBJECT-GROUP
    OBJECTS {
        tmnxSubPCCRuleDirection       ,
        tmnxSubPccRuleRateLimPirUps   ,
        tmnxSubPccRuleRateLimPirDwns  ,
        tmnxSubPccRuleRateLimCirUps   ,
        tmnxSubPccRuleRateLimCirDwns  ,
        tmnxSubPccRuleMonitoringKey   ,
        tmnxSubPccRuleForwardAction   ,
        tmnxSubPccRuleQosAction       ,
        tmnxSubPccRuleSetFC           ,
        tmnxSubPccRuleRedirectRouterV4,
        tmnxSubPccRuleRedirectRouterV6,
        tmnxSubPccRuleRedirIpv4Addr   ,
        tmnxSubPccRuleRedirIpv6Addr   ,
        tmnxSubPccRuleRedirUrl        ,
        tmnxSubPccRuleNbrFlows        ,
        tmnxSubPCCRuleFlowDirection   ,
        tmnxSubPCCRuleFlowSrcAddrType ,
        tmnxSubPCCRuleFlowSrcAddr     ,
        tmnxSubPCCRuleFlowSrcPfxLen   ,
        tmnxSubPCCRuleFlowSrcPortLow  ,
        tmnxSubPCCRuleFlowSrcPortHigh ,
        tmnxSubPCCRuleFlowDstAddrType ,
        tmnxSubPCCRuleFlowDstAddr     ,
        tmnxSubPCCRuleFlowDstPfxLen   ,
        tmnxSubPCCRuleFlowDstPortLow  ,
        tmnxSubPCCRuleFlowDstPortHigh ,
        tmnxSubPCCRuleFlowProtNxtHdr  ,      
        tmnxSubPCCRuleFlowDSCP        ,
        tmnxSPIInfoIngQosPolIdOvr     , 
        tmnxSPIInfoEgrQosPolIdOvr     ,
        tmnxSubHostPCCRulePrecedence  ,
        tmnxSubHostPCCRuleName        ,
        tmnxSubHostPCCRuleKey        
    }
    STATUS      current
    DESCRIPTION
        "The group of objects supporting management of PCC chraging rules
         on Nokia SROS series systems."
    ::= { tmnxSubMgmtGroups 105 }
tmnxSubDataTriggerGroup    OBJECT-GROUP
    OBJECTS {
        tmnxSubDtStatsPacketsReceived,
        tmnxSubDtStatsPacketsDropped,
        tmnxSubDtStatsPacketsInQ,
        tmnxSubDtStatsPacketsInQPeak
    }
    STATUS        current
    DESCRIPTION
        "The group of objects supporting management of
         data-triggered subscriber hosts and MAC learning
         on the Nokia SROS series."
    ::= { tmnxSubMgmtGroups 106 }
    

tmnxSubNotificationObjV13v0Group OBJECT-GROUP
    OBJECTS {
        tmnxSubNotifPrefixLength
    }
    STATUS      current
    DESCRIPTION
        "The group of objects supporting management of notifications
         on Nokia SROS series systems added in release 13.0."
    ::= { tmnxSubMgmtGroups 109 }

tmnxSubSchedulerRateV13v0Group OBJECT-GROUP
    OBJECTS {
        tmnxSubOvrSummedCIR,
        tmnxSubPppOvrSummedCIR,
        tmnxSLAProfInstOvrSummedCIR,
        tmnxSubSlaacOvrSummedCIR
    }
    STATUS      current
    DESCRIPTION
        "The group of objects supporting management of scheduler policies
         on Nokia SROS series systems added in release 13.0."
    ::= { tmnxSubMgmtGroups 111 } 

tmnxSubCcLongCatMapNameGroup OBJECT-GROUP
    OBJECTS {
       tmnxSPICatAlias
    }
    STATUS      current
    DESCRIPTION
        "The group of subscriber management objects supporting
         long names for the credit control categories
         on Nokia SROS series systems."
    ::= { tmnxSubMgmtGroups 112 }

----------------------------------------------
--  NOTIFICATION-GROUPS
----------------------------------------------
tmnxSubMgmtV4v0NotifGroup NOTIFICATION-GROUP
    NOTIFICATIONS {
        tmnxSubscriberCreated,
        tmnxSubscriberDeleted,
        tmnxSubscriberRenamed
    }
    STATUS      obsolete
    DESCRIPTION
        "The group of objects supporting traps for management of subscriber
         management on Nokia SROS series systems."
    ::= { tmnxSubMgmtNotifGroup 1 }

tmnxSubMgmtV5v0NotifGroup NOTIFICATION-GROUP
    NOTIFICATIONS {
        tmnxSubscriberCreated,
        tmnxSubscriberDeleted,
        tmnxSubscriberRenamed,
        tmnxSubAcctPlcyFailure,
        tmnxSubMcsRelatedProblem,
        tmnxSubAuthPlcyRadSerOperStatChg,
        tmnxSubAcctPlcyRadSerOperStatChg
    }
    STATUS      obsolete
    DESCRIPTION
        "The group of objects supporting traps for management of subscriber
         management on Nokia SROS series systems."
    ::= { tmnxSubMgmtNotifGroup 2 }

tmnxSubMgmtV6v0NotifGroup NOTIFICATION-GROUP
    NOTIFICATIONS {
        tmnxSubscriberCreated,
        tmnxSubscriberDeleted,
        tmnxSubscriberRenamed,
        tmnxSubAcctPlcyFailure,
        tmnxSubMcsRelatedProblem,
        tmnxSubAuthPlcyRadSerOperStatChg,
        tmnxSubAcctPlcyRadSerOperStatChg,
        tmnxSubRadSapDisconnectError,
        tmnxSubRadSdpBndDisconnectError,
        tmnxSubRadSapCoAError,
        tmnxSubRadSdpBndCoAError,
        tmnxSubRadSapSubAuthError,
        tmnxSubRadSdpBndSubAuthError
    }
    STATUS      obsolete
    DESCRIPTION
        "The group of objects supporting traps for management of subscriber
         management on Nokia SROS series systems."
    ::= { tmnxSubMgmtNotifGroup 3 }

tmnxSubMgmtV7v0NotifGroup NOTIFICATION-GROUP
    NOTIFICATIONS {
        tmnxSubscriberCreated,
        tmnxSubscriberDeleted,
        tmnxSubscriberRenamed,
        tmnxSubAcctPlcyFailure,
        tmnxSubMcsRelatedProblem,
        tmnxSubAuthPlcyRadSerOperStatChg,
        tmnxSubAcctPlcyRadSerOperStatChg,
        tmnxSubRadSapDisconnectError,
        tmnxSubRadSdpBndDisconnectError,
        tmnxSubRadSapCoAError,
        tmnxSubRadSdpBndCoAError,
        tmnxSubRadSapSubAuthError,
        tmnxSubRadSdpBndSubAuthError,
        tmnxSubUserCategoryOutOfCredit,
        tmnxSubUserCategoryRefreshCredit,
        tmnxSubUserCategoryError
    }
    STATUS      current
    DESCRIPTION
        "The group of objects supporting traps for management of subscriber
         management on Nokia SROS series systems."
    ::= { tmnxSubMgmtNotifGroup 4 }
    
tmnxSubMgmtV9v0NotifGroup NOTIFICATION-GROUP
    NOTIFICATIONS {
        tmnxSubHostInconsistentAtmTdOvr
    }
    STATUS      current
    DESCRIPTION
        "The group of notifications that were added in release 9.0
         on Nokia SROS series systems."
    ::= { tmnxSubMgmtNotifGroup 5 }

tmnxSubMgmtV10v0NotifGroup NOTIFICATION-GROUP
    NOTIFICATIONS {
        tmnxSubSlaacSetupFailure,
        tmnxSubHostLcktLimitReached,
        tmnxSubHostLcktSapLimitReached
    }
    STATUS      current
    DESCRIPTION
        "The group of notifications that were added in release 10.0
         on Nokia SROS series systems."
    ::= { tmnxSubMgmtNotifGroup 6 }

tmnxSubMgmtV12v0NotifGroup NOTIFICATION-GROUP
    NOTIFICATIONS {
        tmnxSubSlaacOverride,
        tmnxSubSysChassMemoryUsageHi,
        tmnxSubVSubnetHostsDeleted
    }                                                      
    STATUS      current
    DESCRIPTION
        "The group of notifications that were added in release 12.0
         on Nokia SROS series systems."
    ::= { tmnxSubMgmtNotifGroup 7 }

tmnxSubMgmtObsoletedNotifGroup NOTIFICATION-GROUP
    NOTIFICATIONS {
        tmnxSubSysNextHopUsageHi
    }
    STATUS      current
    DESCRIPTION
        "The group of obsoleted subscriber management notifications
         on Nokia SROS series systems."
    ::= { tmnxSubMgmtNotifGroup 8 }
    

tmnxSubMgmtIpoeNotifGroup NOTIFICATION-GROUP
    NOTIFICATIONS {
        tmnxSubIpoeInvalidSessionKey,
        tmnxSubIpoeInvalidCidRidChange,
        tmnxSubIpoeSessionLimitReached,
        tmnxSubIpoePersistenceRecovery
    }                                                      
    STATUS      current
    DESCRIPTION
        "The group of subscriber management notifications generated by
         the IPoE sessions feature on Nokia SROS series systems."
    ::= { tmnxSubMgmtNotifGroup 9 }

tmnxSubMgmtV13v0NotifGroup NOTIFICATION-GROUP
    NOTIFICATIONS {
        tmnxSubIpoeMigrHostDeleted
    }                                                      
    STATUS      current
    DESCRIPTION
        "The group of notifications that were added in release 13.0
         on Nokia SROS series systems."
    ::= { tmnxSubMgmtNotifGroup 10 }
----------------------------------------------------------------------------
--  Compliance Info
----------------------------------------------------------------------------
tmnxSubMgmtV4v0MIBCompliance MODULE-COMPLIANCE
    STATUS  obsolete
    DESCRIPTION
            "The compliance statement for TIMETRA-SUBSCRIBER-MGMT-MIB."
    MODULE  -- this module
        MANDATORY-GROUPS {
            tmnxSubAuthenticationV4v0Group,
            tmnxSubMgmtV4v0Group,
            tmnxSubMgmtV4v0NotifGroup
        }
    ::= { tmnxSubMgmtCompliances 1 }

tmnxSubMgmt7450V5v0MIBCompliance MODULE-COMPLIANCE
    STATUS  obsolete
    DESCRIPTION
            "The compliance statement for TIMETRA-SUBSCRIBER-MGMT-MIB
            on Nokia 7450 ESS series systems release R5.0."
    MODULE  -- this module
        MANDATORY-GROUPS {
            tmnxSubAuthentication7450V5v0Group,
            tmnxSubAccounting7450V5v0Group,
            tmnxSubMgmtV5v0Group,
            tmnxSubMgmtV6v0NotifGroup,
            tmnxSubRadNotifStatsGroup,
            tmnxSubNotificationObjV5v0Group
        }
    ::= { tmnxSubMgmtCompliances 2 }

tmnxSubMgmt77x0V5v0MIBCompliance MODULE-COMPLIANCE
    STATUS  obsolete
    DESCRIPTION
            "The compliance statement for TIMETRA-SUBSCRIBER-MGMT-MIB
            on Nokia 7750 SR and 7710 series systems release R5.0."
    MODULE  -- this module
        MANDATORY-GROUPS {
            tmnxSubAuthentication77x0V5v0Group,
            tmnxSubAccounting77x0V5v0Group,
            tmnxSubMgmtV5v0Group,
            tmnxSubMgmtV5v0NotifGroup,
            tmnxSubRadNotifStatsGroup,
            tmnxSubNotificationObjV5v0Group
        }
    ::= { tmnxSubMgmtCompliances 3 }

tmnxSubMgmt7450V6v0MIBCompliance MODULE-COMPLIANCE
    STATUS  obsolete
    DESCRIPTION
            "The compliance statement for TIMETRA-SUBSCRIBER-MGMT-MIB
            on Nokia 7450 ESS series systems release R6.0."
    MODULE  -- this module
        MANDATORY-GROUPS {
            tmnxSubAuthenticationV6v0Group,
            tmnxSubAccountingV6v0Group,
            tmnxSubMgmtV6v0Group,
            tmnxSubMgmtV6v0NotifGroup,
            tmnxSubRadNotifStatsV6v0Group,
            tmnxSubFrameBasedAccntV6v0Group,
            tmnxHsmdaSubscriberV6v0Group,
            tmnxSubBsxObjV6v0Group,
            tmnxSubNotificationObjV6v0Group
        }
    ::= { tmnxSubMgmtCompliances 4 }

tmnxSubMgmt7750V6v0MIBCompliance MODULE-COMPLIANCE
    STATUS  obsolete
    DESCRIPTION
            "The compliance statement for TIMETRA-SUBSCRIBER-MGMT-MIB
            on Nokia 7750 SR series systems release R6.0."
    MODULE  -- this module
        MANDATORY-GROUPS {
            tmnxSubAuthenticationV6v0Group,
            tmnxSubAccountingV6v0Group,
            tmnxSubMgmtV6v0Group,
            tmnxSubMgmtV6v0NotifGroup,
            tmnxSubRadNotifStatsV6v0Group,
            tmnxSubFrameBasedAccntV6v0Group,
            tmnxHsmdaSubscriberV6v0Group,
            tmnxSubBsxObjV6v0Group,
            tmnxSubNotificationObjV6v0Group
        }
    ::= { tmnxSubMgmtCompliances 5 }

tmnxSubMgmt7710V6v0MIBCompliance MODULE-COMPLIANCE
    STATUS  obsolete
    DESCRIPTION
            "The compliance statement for TIMETRA-SUBSCRIBER-MGMT-MIB
            on Nokia 7710 SR series systems release R6.0."
    MODULE  -- this module
        MANDATORY-GROUPS {
            tmnxSubAuthenticationV6v0Group,
            tmnxSubAccountingV6v0Group,
            tmnxSubMgmtV6v0Group,
            tmnxSubMgmtV6v0NotifGroup,
            tmnxSubRadNotifStatsV6v0Group,
            tmnxSubFrameBasedAccntV6v0Group,
            -- tmnxHsmdaSubscriberV6v0Group
            -- tmnxSubBsxObjV6v0Group       no Application Assurance on 7710
            tmnxSubNotificationObjV6v0Group
        }
    ::= { tmnxSubMgmtCompliances 6 }

tmnxSubMgmt7450V6v1MIBCompliance MODULE-COMPLIANCE
    STATUS  obsolete
    DESCRIPTION
            "The compliance statement for TIMETRA-SUBSCRIBER-MGMT-MIB
            on Nokia 7450 ESS series systems release R6.1."
    MODULE  -- this module
        MANDATORY-GROUPS {
            tmnxSubAuthenticationV6v1Group,
            tmnxSubAccountingV6v1Group,
            tmnxSubMgmtV6v0Group,
            tmnxSubMgmtV6v0NotifGroup,
            tmnxSubRadNotifStatsV6v0Group,
            tmnxSubFrameBasedAccntV6v0Group,
            tmnxHsmdaSubscriberV6v0Group,
            tmnxSubBsxObjV6v0Group
        }
    ::= { tmnxSubMgmtCompliances 7 }

tmnxSubMgmt7750V6v1MIBCompliance MODULE-COMPLIANCE
    STATUS  obsolete
    DESCRIPTION
            "The compliance statement for TIMETRA-SUBSCRIBER-MGMT-MIB
            on Nokia 7750 SR series systems release R6.1."
    MODULE  -- this module
        MANDATORY-GROUPS {
            tmnxSubAuthenticationV6v1Group,
            tmnxSubAccountingV6v1Group,
            tmnxSubMgmtV6v0Group,
            tmnxSubMgmtV6v0NotifGroup,
            tmnxSubRadNotifStatsV6v0Group,
            tmnxSubFrameBasedAccntV6v0Group,
            tmnxHsmdaSubscriberV6v0Group,
            tmnxSubBsxObjV6v0Group
        }
    ::= { tmnxSubMgmtCompliances 8 }

tmnxSubMgmt7710V6v1MIBCompliance MODULE-COMPLIANCE
    STATUS  obsolete
    DESCRIPTION
            "The compliance statement for TIMETRA-SUBSCRIBER-MGMT-MIB
            on Nokia 7710 SR series systems release R6.1."
    MODULE  -- this module
        MANDATORY-GROUPS {
            tmnxSubAuthenticationV6v1Group,
            tmnxSubAccountingV6v1Group,
            tmnxSubMgmtV6v0Group,
            tmnxSubMgmtV6v0NotifGroup,
            tmnxSubRadNotifStatsV6v0Group,
            tmnxSubFrameBasedAccntV6v0Group
            -- tmnxHsmdaSubscriberV6v0Group
            -- tmnxSubBsxObjV6v0Group       no Application Assurance on 7710
        }
    ::= { tmnxSubMgmtCompliances 9 }

tmnxSubMgmt7450V7v0MIBCompliance MODULE-COMPLIANCE
    STATUS  obsolete
    DESCRIPTION
            "The compliance statement for TIMETRA-SUBSCRIBER-MGMT-MIB
            on Nokia 7450 ESS series systems release R7.0."
    MODULE  -- this module
        MANDATORY-GROUPS {
            tmnxSubAuthenticationV7v0Group,
            tmnxSubAccountingV6v1Group,
            tmnxSubMgmtV7v0Group,
            tmnxSubMgmtV7v0NotifGroup,
            tmnxSubRadNotifStatsV6v0Group,
            tmnxSubFrameBasedAccntV6v0Group,
            tmnxHsmdaSubscriberV6v0Group,
            tmnxSubBsxObjV7v0Group,
            tmnxSubHostTrackingGroup,
            tmnxSubRadusPlcyCustomRecordV7v0Group,
            tmnxSubCreditControlV7v0Group
        }
    ::= { tmnxSubMgmtCompliances 10 }

tmnxSubMgmt7750V7v0MIBCompliance MODULE-COMPLIANCE
    STATUS  obsolete
    DESCRIPTION
            "The compliance statement for TIMETRA-SUBSCRIBER-MGMT-MIB
            on Nokia 7750 SR series systems release R7.0."
    MODULE  -- this module
        MANDATORY-GROUPS {
            tmnxSubAuthenticationV7v0Group,
            tmnxSubAccountingV6v1Group,
            tmnxSubMgmtV7v0Group,
            tmnxSubMgmtV7v0NotifGroup,
            tmnxSubRadNotifStatsV6v0Group,
            tmnxSubFrameBasedAccntV6v0Group,
            tmnxHsmdaSubscriberV6v0Group,
            tmnxSubBsxObjV7v0Group,
            tmnxSubHostTrackingGroup,
            tmnxSubRadusPlcyCustomRecordV7v0Group,
            tmnxSubCreditControlV7v0Group
        }
    ::= { tmnxSubMgmtCompliances 11 }

tmnxSubMgmt7710V7v0MIBCompliance MODULE-COMPLIANCE
    STATUS  obsolete
    DESCRIPTION
            "The compliance statement for TIMETRA-SUBSCRIBER-MGMT-MIB
            on Nokia 7710 SR series systems release R7.0."
    MODULE  -- this module
        MANDATORY-GROUPS {
            tmnxSubAuthenticationV7v0Group,
            tmnxSubAccountingV6v1Group,
            tmnxSubMgmtV7v0Group,
            tmnxSubMgmtV7v0NotifGroup,
            tmnxSubRadNotifStatsV6v0Group,
            tmnxSubFrameBasedAccntV6v0Group,
            -- tmnxHsmdaSubscriberV6v0Group
            -- tmnxSubBsxObjV7v0Group       no Application Assurance on 7710
            tmnxSubHostTrackingGroup,
            tmnxSubRadusPlcyCustomRecordV7v0Group,
            tmnxSubCreditControlV7v0Group
        }
    ::= { tmnxSubMgmtCompliances 12 }

tmnxSubMgmt7450V8v0MIBCompliance MODULE-COMPLIANCE
    STATUS  obsolete
    DESCRIPTION
            "The compliance statement for TIMETRA-SUBSCRIBER-MGMT-MIB
            on Nokia 7450 ESS series systems release 8.0."
    MODULE  -- this module
        MANDATORY-GROUPS {
            tmnxSubAuthenticationV8v0Group,
            tmnxSubAccountingV8v0Group,
            tmnxSubMgmtV8v0Group,
            tmnxSubMgmtV7v0NotifGroup,
            tmnxSubRadNotifStatsV6v0Group,
            tmnxSubFrameBasedAccntV6v0Group,
            tmnxHsmdaSubscriberV6v0Group,
            tmnxSubBsxObjV7v0Group,
            tmnxSubHostTrackingGroup,
            tmnxSubRadusPlcyCustomRecordV7v0Group,
            tmnxSubCreditControlV8v0Group,
            tmnxCcIpFltrV8v0Group,
            -- tmnxCcIpv6FltrV8v0Group,    ipv6 is not supported on 7450
            tmnxSubV6GrpIfRAV8v0Group,
            tmnxSubMgmtIPv6V8v0Group,
            tmnxSubProfileMssExtensionsGroup,
            tmnxSubProfileV8v0Group
        }
    ::= { tmnxSubMgmtCompliances 13 }

tmnxSubMgmt7750V8v0MIBCompliance MODULE-COMPLIANCE
    STATUS  obsolete
    DESCRIPTION
            "The compliance statement for TIMETRA-SUBSCRIBER-MGMT-MIB
            on Nokia 7750 SR series systems release 8.0."
    MODULE  -- this module
        MANDATORY-GROUPS {
            tmnxSubAuthenticationV8v0Group,
            tmnxSubAccountingV8v0Group,
            tmnxSubMgmtV8v0Group,
            tmnxSubMgmtV7v0NotifGroup,
            tmnxSubRadNotifStatsV6v0Group,
            tmnxSubFrameBasedAccntV6v0Group,
            tmnxHsmdaSubscriberV6v0Group,
            tmnxSubBsxObjV7v0Group,
            tmnxSubHostTrackingGroup,
            tmnxSubRadusPlcyCustomRecordV7v0Group,
            tmnxSubCreditControlV8v0Group,
            tmnxCcIpFltrV8v0Group,
            tmnxCcIpv6FltrV8v0Group,
            tmnxSubV6GrpIfRAV8v0Group,
            tmnxSubMgmtIPv6V8v0Group,
            tmnxSubProfileMssExtensionsGroup,
            tmnxSubProfileV8v0Group,
            tmnxSubNatGroup
        }
    ::= { tmnxSubMgmtCompliances 14 }

tmnxSubMgmt7710V8v0MIBCompliance MODULE-COMPLIANCE
    STATUS  obsolete
    DESCRIPTION
            "The compliance statement for TIMETRA-SUBSCRIBER-MGMT-MIB
            on Nokia 7710 SR series systems release 8.0."
    MODULE  -- this module
        MANDATORY-GROUPS {
            tmnxSubAuthenticationV8v0Group,
            tmnxSubAccountingV8v0Group,
            tmnxSubMgmtV8v0Group,
            tmnxSubMgmtV7v0NotifGroup,
            tmnxSubRadNotifStatsV6v0Group,
            tmnxSubFrameBasedAccntV6v0Group,
            -- tmnxHsmdaSubscriberV6v0Group
            -- tmnxSubBsxObjV7v0Group       no Application Assurance on 7710
            tmnxSubHostTrackingGroup,
            tmnxSubRadusPlcyCustomRecordV7v0Group,
            tmnxSubCreditControlV8v0Group,
            tmnxCcIpFltrV8v0Group,
            tmnxCcIpv6FltrV8v0Group,
            tmnxSubV6GrpIfRAV8v0Group,
            tmnxSubMgmtIPv6V8v0Group,
            tmnxSubProfileMssExtensionsGroup,
            tmnxSubProfileV8v0Group,
            tmnxSubNatGroup
        }
    ::= { tmnxSubMgmtCompliances 15 }

tmnxSubMgmt7450V9v0MIBCompliance MODULE-COMPLIANCE
    STATUS  obsolete
    DESCRIPTION
            "The compliance statement for TIMETRA-SUBSCRIBER-MGMT-MIB
            on Nokia 7450 ESS series systems release 9.0."
    MODULE  -- this module
        MANDATORY-GROUPS {
            tmnxSubAuthenticationV8v0Group,
            tmnxSubAccountingV8v0Group,
            tmnxSubMgmtV9v0Group,
            tmnxSubMgmtV7v0NotifGroup,
            tmnxSubMgmtV9v0NotifGroup,
            tmnxSubRadNotifStatsV6v0Group,
            tmnxSubFrameBasedAccntV6v0Group,
            tmnxHsmdaSubscriberV6v0Group,
            tmnxSubBsxObjV9v0Group,
            tmnxSubHostTrackingV9v0Group,
            tmnxSubRadusPlcyCustomRecordV7v0Group,
            tmnxSubCreditControlV8v0Group,
            tmnxCcIpFltrV8v0Group,
            -- tmnxCcIpv6FltrV8v0Group,    ipv6 is not supported on 7450
            tmnxSubV6GrpIfRAV8v0Group,
            tmnxSubMgmtIPv6V8v0Group,
            tmnxSubProfileMssExtensionsGroup,
            tmnxSubCreditControlV9v0Group,                 
            tmnxSubPppGroup,
            tmnxSubProfileV9v0Group
        }
    ::= { tmnxSubMgmtCompliances 16 }

tmnxSubMgmt7750V9v0MIBCompliance MODULE-COMPLIANCE
    STATUS  obsolete
    DESCRIPTION
            "The compliance statement for TIMETRA-SUBSCRIBER-MGMT-MIB
            on Nokia 7750 SR series systems release 9.0."
    MODULE  -- this module
        MANDATORY-GROUPS {
            tmnxSubAuthenticationV8v0Group,
            tmnxSubAccountingV8v0Group,
            tmnxSubMgmtV9v0Group,
            tmnxSubMgmtV7v0NotifGroup,
            tmnxSubMgmtV9v0NotifGroup,
            tmnxSubRadNotifStatsV6v0Group,
            tmnxSubFrameBasedAccntV6v0Group,
            tmnxHsmdaSubscriberV6v0Group,
            tmnxSubBsxObjV9v0Group,
            tmnxSubHostTrackingV9v0Group,
            tmnxSubRadusPlcyCustomRecordV7v0Group,
            tmnxSubCreditControlV8v0Group,
            tmnxCcIpFltrV8v0Group,
            tmnxCcIpv6FltrV8v0Group,
            tmnxSubV6GrpIfRAV8v0Group,
            tmnxSubMgmtIPv6V8v0Group,
            tmnxSubProfileMssExtensionsGroup,
            tmnxSubCreditControlV9v0Group,                 
            tmnxSubPppGroup,
            tmnxSubProfileV9v0Group,
            tmnxSubNatGroup
        }
    ::= { tmnxSubMgmtCompliances 17 }

tmnxSubMgmt7710V9v0MIBCompliance MODULE-COMPLIANCE
    STATUS  obsolete
    DESCRIPTION
            "The compliance statement for TIMETRA-SUBSCRIBER-MGMT-MIB
            on Nokia 7710 SR series systems release 9.0."
    MODULE  -- this module
        MANDATORY-GROUPS {
            tmnxSubAuthenticationV8v0Group,
            tmnxSubAccountingV8v0Group,
            tmnxSubMgmtV9v0Group,
            tmnxSubMgmtV7v0NotifGroup,
            tmnxSubMgmtV9v0NotifGroup,
            tmnxSubRadNotifStatsV6v0Group,
            tmnxSubFrameBasedAccntV6v0Group,
            -- tmnxHsmdaSubscriberV6v0Group
            -- tmnxSubBsxObjV9v0Group       no Application Assurance on 7710
            tmnxSubHostTrackingV9v0Group,
            tmnxSubRadusPlcyCustomRecordV7v0Group,
            tmnxSubCreditControlV8v0Group,
            tmnxCcIpFltrV8v0Group,
            tmnxCcIpv6FltrV8v0Group,
            tmnxSubV6GrpIfRAV8v0Group,
            tmnxSubMgmtIPv6V8v0Group,
            tmnxSubProfileMssExtensionsGroup,
            tmnxSubCreditControlV9v0Group,                 
            tmnxSubPppGroup,
            tmnxSubProfileV9v0Group,
            tmnxSubNatGroup
        }
    ::= { tmnxSubMgmtCompliances 18 }

tmnxSubMgmtHsmdaCompliance MODULE-COMPLIANCE
    STATUS  obsolete
    DESCRIPTION
        "The compliance statement for management of 
         HSMDA-2 for subscriber management
         on Nokia SROS series systems."
    MODULE  -- this module
        MANDATORY-GROUPS {
             tmnxSubHsmdaGroup,
             tmnxSubAleGroup
        }
    ::= { tmnxSubMgmtCompliances 19 }

tmnxSubFlterProfCompliance MODULE-COMPLIANCE
    STATUS  current
    DESCRIPTION
        "The compliance statement for management of 
         Filter profiles in  subscriber management
         on Nokia SROS series systems."
    MODULE  -- this module
        MANDATORY-GROUPS {
             tmnxSubFlterProfGroup
        }
    ::= { tmnxSubMgmtCompliances 20 }

tmnxSubMgmt7x50V10v0Compliance MODULE-COMPLIANCE
    STATUS  obsolete
    DESCRIPTION
            "The compliance statement for TIMETRA-SUBSCRIBER-MGMT-MIB
            on Nokia 7x50 SR series systems release 10.0."
    MODULE  -- this module
        MANDATORY-GROUPS {
            tmnxSubAuthenticationV8v0Group,
            tmnxSubAuthenticationV10v0Group,
            tmnxSubAccountingV8v0Group,
            tmnxSubAccountingV10v0Group,
            tmnxSubMgmtV10v0Group,
            tmnxSubMgmtV7v0NotifGroup,
            tmnxSubMgmtV9v0NotifGroup,
            tmnxSubMgmtV10v0NotifGroup,
            tmnxSubRadNotifStatsV6v0Group,
            tmnxSubFrameBasedAccntV6v0Group,
            tmnxHsmdaSubscriberV6v0Group,
            tmnxSubBsxObjV9v0Group,
            tmnxSubHostTrackingV9v0Group,
            tmnxSubRadusPlcyCustomRecordV7v0Group,
            tmnxSubCreditControlV8v0Group,
            tmnxCcIpFltrV8v0Group,
            tmnxCcIpv6FltrV8v0Group,
            tmnxSubV6GrpIfRAV8v0Group,
            tmnxSubMgmtIPv6V8v0Group,
            tmnxSubProfileMssExtensionsGroup,
            tmnxSubCreditControlV9v0Group,                 
            tmnxSubCreditControlV10v0Group,
            tmnxSubAutoSubIdV10v0Group,
            tmnxSubIpoeLinkV10v0Group,
            tmnxSubPppGroup,
            tmnxSubPppV10v0Group,
            tmnxSubSlaacV10v0Group,
            tmnxSubProfileV9v0Group,
            tmnxSubNatGroup,
            tmnxSubL2tpGroup
        }
    ::= { tmnxSubMgmtCompliances 21 }

tmnxSubMgmt7710V10v0Compliance MODULE-COMPLIANCE
    STATUS  obsolete
    DESCRIPTION
            "The compliance statement for TIMETRA-SUBSCRIBER-MGMT-MIB
            on Nokia 7710 SR series systems release 10.0."
    MODULE  -- this module
        MANDATORY-GROUPS {
            tmnxSubAuthenticationV8v0Group,
            tmnxSubAuthenticationV10v0Group,
            tmnxSubAccountingV8v0Group,
            tmnxSubAccountingV10v0Group,
            tmnxSubMgmtV10v0Group,
            tmnxSubMgmtV7v0NotifGroup,
            tmnxSubMgmtV9v0NotifGroup,
            tmnxSubMgmtV10v0NotifGroup,
            tmnxSubRadNotifStatsV6v0Group,
            tmnxSubFrameBasedAccntV6v0Group,
            -- tmnxHsmdaSubscriberV6v0Group
            -- tmnxSubBsxObjV9v0Group       no Application Assurance on 7710
            tmnxSubHostTrackingV9v0Group,
            tmnxSubRadusPlcyCustomRecordV7v0Group,
            tmnxSubCreditControlV8v0Group,
            tmnxCcIpFltrV8v0Group,
            tmnxCcIpv6FltrV8v0Group,
            tmnxSubV6GrpIfRAV8v0Group,
            tmnxSubMgmtIPv6V8v0Group,
            tmnxSubProfileMssExtensionsGroup,
            tmnxSubCreditControlV9v0Group,                 
            tmnxSubCreditControlV10v0Group,
            tmnxSubAutoSubIdV10v0Group,
            tmnxSubIpoeLinkV10v0Group,
            tmnxSubPppGroup,
            tmnxSubPppV10v0Group,
            tmnxSubSlaacV10v0Group,
            tmnxSubProfileV9v0Group,
            tmnxSubNatGroup
        }
    ::= { tmnxSubMgmtCompliances 22 }

tmnxSubMgmtSROSV11v0Compliance MODULE-COMPLIANCE
    STATUS  obsolete
    DESCRIPTION
            "The compliance statement for TIMETRA-SUBSCRIBER-MGMT-MIB
            on Nokia SROS systems release 11.0."
    MODULE  -- this module
        MANDATORY-GROUPS {
            tmnxSubAuthenticationV8v0Group,
            tmnxSubAuthenticationV10v0Group,
            tmnxSubAuthenticationV11v0Group,
            tmnxSubAccountingV8v0Group,
            tmnxSubAccountingV10v0Group,
            tmnxSubAccountingV11v0Group,
            tmnxSubMgmtV7v0NotifGroup,
            tmnxSubMgmtV9v0NotifGroup,
            tmnxSubMgmtV10v0NotifGroup,
            tmnxSubRadNotifStatsV6v0Group,
            tmnxSubFrameBasedAccntV6v0Group,
            tmnxHsmdaSubscriberV10v0Group,
            tmnxSubBsxObjV9v0Group,
            tmnxSubHostTrackingV9v0Group,
            tmnxSubRadusPlcyCustomRecordV7v0Group,
            tmnxSubCreditControlV8v0Group,
            tmnxCcIpFltrV8v0Group,
            tmnxCcIpv6FltrV8v0Group,
            tmnxSubV6GrpIfRAV11v0Group,
            tmnxSubMgmtIPv6V8v0Group,
            tmnxSubProfileMssExtensionsGroup,
            tmnxSubCreditControlV9v0Group,                 
            tmnxSubCreditControlV10v0Group,
            tmnxSubAutoSubIdV10v0Group,
            tmnxSubIpoeLinkV10v0Group,
            tmnxSubPppV11v0Group,
            tmnxSubSlaacV11v0Group,
            tmnxSubProfileV9v0Group,
            tmnxSubNatGroup,
            tmnxSubL2tpGroup,
            tmnxSubMgmtV11v0Group,
            tmnxSubHttpRedirectGroup,
            tmnxSubServiceGroup,
            tmnxSubSchedulerRateV11v0Group,
            tmnxSubMgmtQosV11v0Group
        }
    ::= { tmnxSubMgmtCompliances 23 }

tmnxSubMgmtSROSV12v0Compliance MODULE-COMPLIANCE
    STATUS  obsolete
    DESCRIPTION
            "The compliance statement for TIMETRA-SUBSCRIBER-MGMT-MIB
            on Nokia SROS systems release 12.0."
    MODULE  -- this module
        MANDATORY-GROUPS {
            tmnxSubAuthenticationV10v0Group,
            tmnxSubAuthenticationV11v0Group,
            tmnxSubAuthenticationV12v0Group,
            tmnxSubAccountingV10v0Group,
            tmnxSubAccountingV11v0Group,
            tmnxSubAccountingV12v0Group,
            tmnxSubMgmtV7v0NotifGroup,
            tmnxSubMgmtV9v0NotifGroup,
            tmnxSubMgmtV10v0NotifGroup,
            tmnxSubMgmtV12v0NotifGroup,
            tmnxSubMgmtObsoletedNotifGroup,
            tmnxSubRadNotifStatsV6v0Group,
            tmnxSubFrameBasedAccntV6v0Group,
            tmnxHsmdaSubscriberV10v0Group,
            tmnxSubBsxObjV9v0Group,
            tmnxSubHostTrackingV9v0Group,
            tmnxSubRadusPlcyCustomRecordV7v0Group,
            tmnxSubCreditControlV8v0Group,
            tmnxCcIpFltrV8v0Group,
            tmnxCcIpv6FltrV8v0Group,
            tmnxSubV6GrpIfRAV11v0Group,
            tmnxSubMgmtIPv6V8v0Group,
            tmnxSubProfileMssExtensionsGroup,
            tmnxSubCreditControlV9v0Group,
            tmnxSubCreditControlV10v0Group,
            tmnxSubAutoSubIdV10v0Group,
            tmnxSubIpoeLinkV10v0Group,
            tmnxSubPppV11v0Group,
            tmnxSubSlaacV11v0Group,
            tmnxSubProfileV9v0Group,
            tmnxSubNatGroup,
            tmnxSubL2tpGroup,
            tmnxSubMgmtV11v0Group,
            tmnxSubMgmtV12v0Group,
            tmnxSubHttpRedirectGroup,
            tmnxSubHttpRedirectV12v0Group,
            tmnxSubVSubnetV12v0Group,
            tmnxSubSysGroup,
            tmnxSubServiceGroup,
            tmnxSubSchedulerRateV11v0Group,
            tmnxSubSchedulerRateV12v0Group,
            tmnxSubMgmtQosV11v0Group,
            tmnxSubMgmtQosV12v0Group,
            tmnxSubSlaacV12v0Group,
            tmnxSubQosParentLocV12v0Group
        }
    ::= { tmnxSubMgmtCompliances 24 }

tmnxSubMgmtHsmdaV12v0Compliance MODULE-COMPLIANCE
    STATUS  current
    DESCRIPTION
        "The compliance statement for management of 
         HSMDA-2 for subscriber management
         on Nokia SROS series systems release 12.0."
    MODULE  -- this module
        MANDATORY-GROUPS {
             tmnxSubHsmdaGroup,
             tmnxSubAleGroup,
             tmnxSubHsmdaV12v0Group
        }
    ::= { tmnxSubMgmtCompliances 25 }

    
tmnxSubMgmtSROSV13v0Compliance MODULE-COMPLIANCE
    STATUS  current
    DESCRIPTION
            "The compliance statement for TIMETRA-SUBSCRIBER-MGMT-MIB
            on Nokia SROS systems release 13.0."
    MODULE  -- this module
        MANDATORY-GROUPS {
            tmnxSubAuthenticationV10v0Group,
            tmnxSubAuthenticationV11v0Group,
            tmnxSubAuthenticationV12v0Group,
            tmnxSubAccountingV10v0Group,
            tmnxSubAccountingV11v0Group,
            tmnxSubAccountingV12v0Group,
            tmnxSubMgmtV7v0NotifGroup,
            tmnxSubMgmtV9v0NotifGroup,
            tmnxSubMgmtV10v0NotifGroup,
            tmnxSubMgmtV12v0NotifGroup,
            tmnxSubMgmtV13v0NotifGroup,
            tmnxSubMgmtObsoletedNotifGroup,
            tmnxSubMgmtIpoeNotifGroup,
            tmnxSubRadNotifStatsV6v0Group,
            tmnxSubFrameBasedAccntV6v0Group,
            tmnxHsmdaSubscriberV10v0Group,
            tmnxSubBsxObjV9v0Group,
            tmnxSubHostTrackingV9v0Group,
            tmnxSubRadusPlcyCustomRecordV7v0Group,
            tmnxSubCreditControlV8v0Group,
            tmnxCcIpFltrV8v0Group,
            tmnxCcIpv6FltrV8v0Group,
            tmnxSubV6GrpIfRAV11v0Group,
            tmnxSubMgmtIPv6V8v0Group,
            tmnxSubProfileMssExtensionsGroup,
            tmnxSubCreditControlV9v0Group,
            tmnxSubCreditControlV10v0Group,
            tmnxSubAutoSubIdV10v0Group,
            tmnxSubIpoeLinkV10v0Group,
            tmnxSubPppV11v0Group,
            tmnxSubPppV13v0Group,
            tmnxSubSlaacV11v0Group,
            tmnxSubSlaacV12v0Group,
            tmnxSubSlaacV13v0Group,
            tmnxSubProfileV9v0Group,
            tmnxSubNatGroup,
            tmnxSubL2tpGroup,
            tmnxSubMgmtV11v0Group,
            tmnxSubMgmtV12v0Group,
            tmnxSubMgmtV13v0Group,
            tmnxSubHttpRedirectGroup,
            tmnxSubHttpRedirectV12v0Group,
            tmnxSubVSubnetV12v0Group,
            tmnxSubSysGroup,
            tmnxSubServiceGroup,
            tmnxSubSchedulerRateV11v0Group,
            tmnxSubSchedulerRateV12v0Group,
            tmnxSubSchedulerRateV13v0Group,
            tmnxSubMgmtQosV11v0Group,
            tmnxSubMgmtQosV12v0Group,
            tmnxSubQosParentLocV12v0Group,
            tmnxSubIpoeV13v0Group,
            tmnxSubRipV13v0Group,
            tmnxSubCcLongCatMapNameGroup,
            tmnxSubPimGroup,
            tmnxSubShcvGroup,
            tmnxSubPppDfGroup,
            tmnxSubPccRuleEntryV13v0Group,
            tmnxSubDataTriggerGroup
        }
    ::= { tmnxSubMgmtCompliances 26 }
    
END
