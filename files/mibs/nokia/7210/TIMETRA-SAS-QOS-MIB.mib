TIMETRA-SAS-QOS-MIB DEFINITIONS ::= BEGIN

IMPORTS
    MODULE-IDENTITY, OBJECT-TYPE,
    Unsigned32, IpAddress, Integer32, Counter64
                                                     FROM SNMPv2-SMI
    MODULE-COMPLIANCE, OBJECT-GROUP
                                                     FROM SNMPv2-CONF
    TEXTUAL-CONVENTION, RowStatus,
    MacAddress, TruthValue, 
    StorageType, TimeStamp
                                                     FROM SNMPv2-TC
    timetraSASObjs, timetraSASNotifyPrefix, 
    timetraSASConfs, timetraSASModules               FROM TIMETRA-SAS-GLOBAL-MIB
    Dot1PPriority, IpAddressPrefixLength,
    ServiceAccessPoint,TItemDescription,
    TNamedItem, TNamedItemOrEmpty,
    TDSCPValue,  TDSCPName, TDSCPNameOrEmpty,
    TIpProtocol, TTcpUdpPort, TDSCPValueOrNone,
    TTcpUdpPortOperator, TFrameType, TFCName,
    TLspExpValue, TQueueId, TIngressQueueId,
    TEgressQueueId, TPortSchedulerPIR, 
    TPortSchedulerCIR, TIngressMeterId, TFCType,
    TSapIngressMeterId, TNetworkIngressMeterId,
    TMplsLspExpProfMapID, TPIRRatePercent, TDEValue,
    TBWRateType                                      FROM TIMETRA-TC-MIB

    AtmServiceCategory, AtmTrafficDescrParamIndex
                                                     FROM ATM-TC-MIB
    InetAddressIPv6, InetAddressPrefixLength
                                                     FROM INET-ADDRESS-MIB
    svcId 
                                                     FROM TIMETRA-SERV-MIB    
    sapPortId, sapEncapValue
                                                     FROM TIMETRA-SAP-MIB
    tSapIngressIndex, tNetworkPolicyIndex,
    tSlopePolicyEntry, tPortSchedulerPlcyEntry,        
    tSapIngressFCEntry, tSlopePolicy, tNetworkQueuePolicyEntry, 
    tSapIngressEntry, tNetworkPolicyEntry, tSapEgressEntry,
    tNetworkQueueEntry, tSapEgressQueueEntry,
    tSapIngressQueueEntry, tSapIngressMacCriteriaEntry,
    tSapIngressIPCriteriaEntry,tSapIngressIPv6CriteriaEntry,
    tNetworkEgressFCEntry                          FROM TIMETRA-QOS-MIB
    ;

timetraSASQosMIBModule   MODULE-IDENTITY
        LAST-UPDATED    "0701010000Z"
        ORGANIZATION    "Nokia"
        CONTACT-INFO
            "Nokia 7x50 Support
             Web: http://www.nokia.com"
        DESCRIPTION
            "This document is the SNMP MIB module to manage and provision
             Quality of Service features on Nokia 7x50 systems.

             Copyright 2003-2014 Nokia. All rights reserved.
             Reproduction of this document is authorized on the condition that
             the foregoing copyright notice is included.

             This SNMP MIB module (Specification) embodies Nokia's
             proprietary intellectual property.  Nokia retains
             all title and ownership in the Specification, including any
             revisions.

             Nokia grants all interested parties a non-exclusive
             license to use and distribute an unmodified copy of this
             Specification in connection with management of Nokia
             products, and without fee, provided this copyright notice and
             license appear on all copies.

             This Specification is supplied 'as is', and Nokia
             makes no warranty, either express or implied, as to the use,
             operation, condition, or performance of the Specification."

--
--  Revision History
--
        REVISION        "0801090000Z"
        DESCRIPTION     "Rev 1.0                09 Jan 2008 00:00
                This is the 1.0 release of the TIMETRA-SAS-GLOBAL-MIB."
        ::= { timetraSASModules 5 }


tSASQosObjects                    OBJECT IDENTIFIER ::= { timetraSASObjs 1 }
tmnxSASQosConformance             OBJECT IDENTIFIER ::= { timetraSASConfs 1 }

tAccessEgressObjects           OBJECT IDENTIFIER ::= { tSASQosObjects 1 }
tSASSapIngressObjects          OBJECT IDENTIFIER ::= { tSASQosObjects 2 }
tSASNetworkIngressObjects      OBJECT IDENTIFIER ::= { tSASQosObjects 3 }
tSASSlopeObjects               OBJECT IDENTIFIER ::= { tSASQosObjects 4 }
tSasSchedulerObjects           OBJECT IDENTIFIER ::= { tSASQosObjects 5 }
tQosFrameBasedAccntObjects     OBJECT IDENTIFIER ::= { tSASQosObjects 6 }
tSASNetworkObjects             OBJECT IDENTIFIER ::= { tSASQosObjects 7 }
tSASQueueMgmtObjects           OBJECT IDENTIFIER ::= { tSASQosObjects 8 }
tSASSapEgressObjects           OBJECT IDENTIFIER ::= { tSASQosObjects 9 }
tMplsQosObjects                OBJECT IDENTIFIER ::= { tSASQosObjects 10 }
tSASGeneralQosObjects          OBJECT IDENTIFIER ::= { tSASQosObjects 21 }
--
-- TEXTUAL-CONVENTIONs for Nokia 7x50 SR series QoS Elements
--
TPolicyID ::= TEXTUAL-CONVENTION
    STATUS       current
    DESCRIPTION
        "the identification number of a policy."
    SYNTAX Unsigned32 (0..65535)

TSapIngressPolicyID ::= TEXTUAL-CONVENTION
    STATUS       current
    DESCRIPTION
        "the identification number of a SAP ingress policy."
    SYNTAX TPolicyID

TSapEgressPolicyID ::= TEXTUAL-CONVENTION
    STATUS       current
    DESCRIPTION
        "the identification number of a SAP egress policy."
    SYNTAX TPolicyID (1..65535)

TAccessEgressPolicyID ::= TEXTUAL-CONVENTION
    STATUS       current
    DESCRIPTION
        "the identification number of a Access egress policy."
    SYNTAX TPolicyID (1..65535)


TNetworkPolicyID ::= TEXTUAL-CONVENTION
    STATUS       current
    DESCRIPTION
        "the identification number of a network policy."
    SYNTAX TPolicyID (1..65535)

TRemarkPolicyID ::= TEXTUAL-CONVENTION
    STATUS       current
    DESCRIPTION
        "the identification number of a Remark policy."
    SYNTAX TPolicyID (1..65535)

TClassificationPolicyID ::= TEXTUAL-CONVENTION
    STATUS       current
    DESCRIPTION
        "the identification number of a Classification policy."
    SYNTAX TPolicyID (1..65535)

TItemScope ::= TEXTUAL-CONVENTION
    STATUS       current
    DESCRIPTION
        "This textual-convention determines some aspects of an item's
        behavior regarding creation and use, unused entry garbage collection,
        and automated promulgation by Element Management System to
        other systems in the service domain.

        TItemScope applies to SAP-ingress, SAP-egress, and Network policies,
        and to IP filters and MAC filters.

        exclusive:

            When the scope of an item is defined as exclusive, the item can
            only be applied once, for example to a single SAP.  Attempting
            to assign the policy to a second SAP is not allowed and will
            result in an error.  If the item is removed from the exclusive
            SAP, it will become available for assignment to another
            exclusive SAP.

            A non-applied exclusive scope policy is a candidate to be removed
            from the system by a TBD garbage collection command.

            The system default policies cannot be put into the exclusive scope.
            An error will be generated if scope exclusive is executed in
            any policies with a policy-id equal to 1.

        template:

            When the scope of an item is defined as template, the item can be
            applied any number of times.  Policies with template scope
            will not be considered for deletion by a TBD garbage collection
            command; all items of scope 'template' must be deleted explicitly.

            The system default policies will always be scope template.
            An error will occur if a policy-id 1 is attempted to be
            set to scope exclusive."
    SYNTAX INTEGER { exclusive(1), template(2) }

TItemMatch  ::= TEXTUAL-CONVENTION
    STATUS       current
    DESCRIPTION
        "when set to off, the item is not matched.
         when set to false, packets without the item match the filter.
         when set to true, packets with the item match the filter."
    SYNTAX INTEGER { off(1), false(2), true(3) }

TPriority ::= TEXTUAL-CONVENTION
    STATUS       current
    DESCRIPTION
        "the priority to apply to a packet"
    SYNTAX INTEGER { low(1), high(2) }

TPriorityOrDefault ::= TEXTUAL-CONVENTION
    STATUS       current
    DESCRIPTION
        "the priority to apply to a packet.
         when set to default(3), the priority from the default-action is used."
    SYNTAX INTEGER { low(1), high(2), default(3) }

TProfile ::= TEXTUAL-CONVENTION
    STATUS       current
    DESCRIPTION
        "the profile marking of a packet at the ingress."
    SYNTAX INTEGER { in(1), out(2) }

TProfileOrDei ::= TEXTUAL-CONVENTION
    STATUS       current
    DESCRIPTION
        "the profile marking of a packet at the ingress."
    SYNTAX INTEGER { in(1), out(2), use-dei(13) }

TProfileOrDeiOrNone ::= TEXTUAL-CONVENTION
    STATUS       current
    DESCRIPTION
        "the profile marking of a packet at the ingress."
    SYNTAX INTEGER { in(1), out(2), use-dei(13), none(0) }

TProfileOrNone ::= TEXTUAL-CONVENTION
    STATUS       current
    DESCRIPTION
        "Profile marking of a packet."
    SYNTAX INTEGER { none (0), in(1), out(2) }

TAdaptationRule ::= TEXTUAL-CONVENTION
    STATUS       current
    DESCRIPTION
        "The adaptation rule to be applied to calcluate the operational values
         for the specified entity."
    SYNTAX       INTEGER {
                     max    (1),
                     min    (2),
                     closest(3)
                 }

TRemarkType ::=  TEXTUAL-CONVENTION
    STATUS       current
    DESCRIPTION
        "The remarking to be used."
    SYNTAX       INTEGER {
                     none       (1),
                     dscp       (2),
                     precedence (3)
                 }

TPrecValue ::= TEXTUAL-CONVENTION
    STATUS       current
    DESCRIPTION
        "The precedence bits as used in the IPv4 header. This constitutes of
         3 bits and hence can hold the values from 0 to 7."
    SYNTAX       INTEGER (0..7)

TPrecValueOrNone ::= TEXTUAL-CONVENTION
    STATUS       current
    DESCRIPTION
        "The precedence bits as used in the IPv4 header. This constitutes of
         3 bits and hence can hold the values from 0 to 7. The value '-1'
         specifies that the precedence value is undefined/unused."
    SYNTAX      INTEGER (-1 | 0..7)

TIngressCIRRate ::= TEXTUAL-CONVENTION
    STATUS       current
    DESCRIPTION
        "The rate to be used in kbps. The value -1 means maximum rate."
    SYNTAX       INTEGER (-1 | 0..20000000)

TIngressPIRRate ::= TEXTUAL-CONVENTION
    STATUS      current
    DESCRIPTION
        "The rate to be used in kbps. The value -1 means maximum rate."
    SYNTAX      INTEGER (-1 | 0..20000000)

TCIRRate ::= TEXTUAL-CONVENTION
    STATUS       current
    DESCRIPTION
        "The rate to be used in kbps. The value -1 means maximum rate."
    SYNTAX       INTEGER (-1 | 0..100000000)

TPIRRate ::= TEXTUAL-CONVENTION
    STATUS      current
    DESCRIPTION
        "The rate to be used in kbps. The value -1 means maximum rate."
    SYNTAX      INTEGER (-1 | 1..100000000)

TPIRRateOrZero ::= TEXTUAL-CONVENTION
    STATUS      current
    DESCRIPTION
        "The rate to be used in kbps. The value -1 means maximum rate. The
         value 0 means undefined rate."
    SYNTAX      INTEGER (-1 | 0..100000000)

TIngressBurstSize ::= TEXTUAL-CONVENTION
    STATUS       current
    DESCRIPTION
        "The amount of buffer space (in Kbits) assigned to a meter.
         The value -1 means default value" 
    SYNTAX       INTEGER (-1 | 4..2146959)

TIngressBurstSizeBytes ::= TEXTUAL-CONVENTION
    STATUS       current
    DESCRIPTION
        "The amount of buffer space (in bytes) assigned to a meter.
         The value -1 means default value" 
    SYNTAX       INTEGER (-1 | 512..274810752)

TIngressBurstSizeKBytes ::= TEXTUAL-CONVENTION
    STATUS       current
    DESCRIPTION
        "The amount of buffer space (in kilo bytes) assigned to a meter.
         The value -1 means default value" 
    SYNTAX       INTEGER (-1 | 1..268369)

TBurstSize ::= TEXTUAL-CONVENTION
    STATUS       current
    DESCRIPTION
        "The amount of buffer space (in kbytes) assigned to a queue.
         The value -1 means that the actual value is derived from the
         corresponding buffer policy's default value."
    SYNTAX       INTEGER (-1 | 0..131072)

TBurstPercent ::= TEXTUAL-CONVENTION
    STATUS       current
    DESCRIPTION
        "The percentage of buffer space assigned to a queue that is
         reserved for some purpose."
    SYNTAX       INTEGER (0..100)

TBurstHundredthsOfPercent ::= TEXTUAL-CONVENTION
    STATUS      current
    DESCRIPTION
        "The percentage of buffer space assigned to a queue that is
         reserved for some purpose, defined to two decimal places."
    SYNTAX      Integer32 (0..10000)

TBurstPercentOrDefault ::= TEXTUAL-CONVENTION
    STATUS       current
    DESCRIPTION
        "The percentage of buffer space assigned to a queue that is
         reserved for some purpose.
         The value -1 means that the actual value is derived from the
         corresponding buffer policy's default value."
    SYNTAX       INTEGER (-1 | 0..100)

TRatePercent ::= TEXTUAL-CONVENTION
    STATUS       current
    DESCRIPTION
        "The percentage of maximum rate allowed."
    SYNTAX       INTEGER (0..100)

TLevel ::= TEXTUAL-CONVENTION
    STATUS       current
    DESCRIPTION
        "The level of the specified entity while feeding into the parent."
    SYNTAX      INTEGER (1..8)

TLevelOrDefault ::= TEXTUAL-CONVENTION
    STATUS       current
    DESCRIPTION
        "The level of the specified entity while feeding into the parent.
         The value 0 is used to denote a default value."
    SYNTAX       INTEGER (0|1..8)

TWeight ::= TEXTUAL-CONVENTION
    STATUS       current
    DESCRIPTION
        "The weight of the specified entity while feeding into the parent."
    SYNTAX       INTEGER (0..100)

TQWeight ::= TEXTUAL-CONVENTION
    STATUS       current
    DESCRIPTION
        "The Queue weight of the specified entity."
    SYNTAX       INTEGER (0 |1..100)


TMeterMode ::= TEXTUAL-CONVENTION
    STATUS       current
    DESCRIPTION
        "Meter mode"
    SYNTAX       INTEGER {
                     priority(1),
                     profile (2)
                 }
                 
TPlcyMode ::= TEXTUAL-CONVENTION
    STATUS       current
    DESCRIPTION
        "Policy mode "
    SYNTAX       INTEGER {
                     strict (0),
                     roundRobin (1),
                     weightedRoundRobin (2),
                     weightedDeficitRoundRobin (3)
                 }
    
TMeterRateMode ::= TEXTUAL-CONVENTION
    STATUS       current
    DESCRIPTION
        "Meter Rate mode.The mode can be configured as Two Rate Three Color 
        Marker (trTCM) or Single Rate Three Color Marker (srTCM). 
        The mode command can be executed at anytime."
    SYNTAX       INTEGER {
                     trtcm (1),
                     srtcm (2),
                     trtcm1 (3),
                     trtcm2 (4)
                 }

TPlcyQuanta ::= TEXTUAL-CONVENTION
    STATUS       current
    DESCRIPTION
        "Policy Quata"
    SYNTAX       INTEGER 
    
TQueueMode ::= TEXTUAL-CONVENTION
    STATUS       current
    DESCRIPTION
        "The mode in which the queue is operating.

         If the queue is operating in the 'priority' mode, it is
         capable of handling traffic differently with two distinct
         priorities. These priorities are assigned by the stages
         preceding the queueing framework in the system.

         When the queue is operating in the 'profile' mode, in other
         words the color aware mode, the queue tries to provide the
         appropriate bandwidth to the packets with different profiles.

         The profiles are assigned according to the configuration of the
         forwarding class or the sub-forwarding class.

         In 'priority' mode, the queue does not have the functionality
         to support the profiled traffic and in such cases the queue
         will have a degraded performance. However, the converse is not
         valid and a queue in 'profile' mode should be capable of
         supporting the different priorities of traffic."
    SYNTAX       INTEGER {
                     priority(1),
                     profile (2)
                 }

TEntryIndicator ::= TEXTUAL-CONVENTION
    STATUS       current
    DESCRIPTION
        "Uniquely identifies an entry in a policy or filter table. The
         value 0 is not a valid entry-id. When used as insertion point
         the value 0 indicates that entries must be inserted at the very
         beginning, i.e.before the first entry defined."
    SYNTAX Unsigned32 (0..65535)

TEntryId ::= TEXTUAL-CONVENTION
    STATUS       current
    DESCRIPTION
        "uniquely identifies an entry in a policy or filter table.
         to facilitate insertion of entries in the tables, we recommend
         assigning entry IDs by 10s:  10, 20, 30, etc. "
    SYNTAX TEntryIndicator (1..65535)

TMatchCriteria ::= TEXTUAL-CONVENTION
    STATUS       current
    DESCRIPTION
        "determines whether the entry matches traffic using IP match
         entries or MAC match entries."
    SYNTAX  INTEGER { ip(1), mac(2), none(3), dscp(4), dot1p(5), prec(6) }

TAtmTdpDescrType ::= TEXTUAL-CONVENTION
    STATUS       current
    DESCRIPTION
        "The TAtmTdpDescrType is an enumerated integer whose value
         indicates the types of cell loss priority to be used in
         conjunction with traffic parameters.

        The following values are outlined:
          Integer Value               Interpretation
          -------------               ------------------------
          clp0And1pcr                 PCR applies to CLP 0 and
                                      CLP 1 cell flows
          clp0And1pcrPlusClp0And1scr  PCR applies to CLP 0 and
                                      CLP 1 cell flows.
                                      SCR applies to CLP 0 and
                                      CLP 1 cell flows.
          clp0And1pcrPlusClp0scr      PCR applies to CLP 0 and
                                      CLP 1 cell flows.
                                      SCR applies to CLP 0 cell flows.
          clp0And1pcrPlusClp0scrTag   PCR applies to CLP 0 and
                                      CLP 1 cell flows.
                                      SCR applies to CLP 0 cell flows. "
    SYNTAX INTEGER {
               clp0And1pcr(0),
               clp0And1pcrPlusClp0And1scr(1),
               clp0And1pcrPlusClp0scr(2),
               clp0And1pcrPlusClp0scrTag(3)
           }

TSlopeDropRate ::= TEXTUAL-CONVENTION
    STATUS       current
    DESCRIPTION
        "The slope drop rate. 
         Mapping of drop-rate values in percentage:
                       0 - 100% cliff drop
                       1 - 6.25%
                       2 - 3.125%
                       3 - 1.5625%
                       4 - 0.78125%
                       5 - 0.390625%
                       6 - 0.1953125%
                       7 - 0.09765625%
       "
    SYNTAX INTEGER (0..7) 

TSlopeThreshold ::= TEXTUAL-CONVENTION
    STATUS       current
    DESCRIPTION
        "The percentage of the shared buffer"
    SYNTAX INTEGER (0..100)

TMaxProbability ::= TEXTUAL-CONVENTION
    STATUS       current
    DESCRIPTION
        "The slope between the Start Average and Max Average"
    SYNTAX Unsigned32 (0..10|25|50|75|100)

TNetworkPolicyType ::= TEXTUAL-CONVENTION
    STATUS       current
    DESCRIPTION
        "Network policy type"
    SYNTAX INTEGER { ipInterface(1), port(2) }
    
TDot1PLspExpValue ::= TEXTUAL-CONVENTION
    STATUS          current
    DESCRIPTION
        "MPLS Experimental bits or 802.1p priority. This type is used when
        these are shared.  -1 means not set."
    REFERENCE ""
    SYNTAX      INTEGER (-1 | 0..7)

TMplsLspExpProfileValue ::= TEXTUAL-CONVENTION
    STATUS          current
    DESCRIPTION
        "MPLS Experimental bits.   -1 means not set."
    REFERENCE ""
    SYNTAX      INTEGER (-1 | 0..7)

--
-- mib objects
--

tMplsLspExpProfMapTable OBJECT-TYPE
    SYNTAX       SEQUENCE OF TMplsLspExpProfMapEntry
    MAX-ACCESS   not-accessible
    STATUS       current
    DESCRIPTION
        "Information about all MPLS LSP EXP Profiles."
    ::= { tMplsQosObjects 1 }

tMplsLspExpProfMapEntry OBJECT-TYPE
    SYNTAX       TMplsLspExpProfMapEntry
    MAX-ACCESS   not-accessible
    STATUS       current
    DESCRIPTION
        "Information about one MPLS LSP EXP Profile"
    INDEX { tMplsLspExpProfMapIndex }
    ::= { tMplsLspExpProfMapTable 1 }

TMplsLspExpProfMapEntry ::= SEQUENCE
    {
        tMplsLspExpProfMapIndex           TMplsLspExpProfMapID,    
        tMplsLspExpProfMapRowStatus       RowStatus,
        tMplsLspExpProfMapDescription     TItemDescription,        
        tMplsLspExpProfMapLastChanged     TimeStamp        
    }

tMplsLspExpProfMapIndex OBJECT-TYPE
    SYNTAX       TMplsLspExpProfMapID
    MAX-ACCESS   not-accessible
    STATUS       current
    DESCRIPTION
        "The tMplsLspExpProfMapIndex is used as index for the table."
    ::= { tMplsLspExpProfMapEntry 1 }

tMplsLspExpProfMapRowStatus OBJECT-TYPE
    SYNTAX       RowStatus
    MAX-ACCESS   read-create
    STATUS       current
    DESCRIPTION
        "Row Status of this profile entry."
    ::= { tMplsLspExpProfMapEntry 2 }

tMplsLspExpProfMapDescription OBJECT-TYPE
    SYNTAX       TItemDescription
    MAX-ACCESS   read-create
    STATUS       current
    DESCRIPTION
        "User-provided description of the policy."
    DEFVAL { ''H }
    ::= { tMplsLspExpProfMapEntry 3 }
    
tMplsLspExpProfMapLastChanged OBJECT-TYPE
    SYNTAX       TimeStamp
    MAX-ACCESS   read-only
    STATUS       current
    DESCRIPTION
        "timestamp of last change to this row in tMplsLspExpProfMapTable."
    ::= { tMplsLspExpProfMapEntry 4 }    

--

tMplsLspExpProfileTable OBJECT-TYPE
    SYNTAX       SEQUENCE OF TMplsLspExpProfileEntry
    MAX-ACCESS   not-accessible
    STATUS       current
    DESCRIPTION  "  "
    ::= { tMplsQosObjects 4 }

tMplsLspExpProfileEntry OBJECT-TYPE
    SYNTAX       TMplsLspExpProfileEntry
    MAX-ACCESS   not-accessible
    STATUS       current
    DESCRIPTION
        "Information about MPLS LSP EXP mapping."
    INDEX { tMplsLspExpProfMapIndex, tMplsLspExpProfileBits }
    ::= { tMplsLspExpProfileTable 1 }

TMplsLspExpProfileEntry ::= SEQUENCE
    {
        tMplsLspExpProfileBits            TMplsLspExpProfileValue,
        tMplsLspExpProfileRowStatus       RowStatus,        
        tMplsLspExpProfile                TProfile,
        tMplsLspExpProfileLastChanged     TimeStamp
    }
    
tMplsLspExpProfileBits OBJECT-TYPE
    SYNTAX       TMplsLspExpProfileValue
    MAX-ACCESS   not-accessible
    STATUS       current
    DESCRIPTION
        "The MPLS Exp value to use for MPLS traffic."
    DEFVAL { -1 }
    ::= { tMplsLspExpProfileEntry 1 }

tMplsLspExpProfileRowStatus OBJECT-TYPE
    SYNTAX       RowStatus
    MAX-ACCESS   read-create
    STATUS       current
    DESCRIPTION
        "Row Status of this profile entry."
    ::= { tMplsLspExpProfileEntry 2 }
    
tMplsLspExpProfile OBJECT-TYPE
    SYNTAX       TProfile
    MAX-ACCESS   read-create
    STATUS       current
    DESCRIPTION
        "tMplsLspExpProfile specifies the profile to be used for this 
        EXP value as indicated by tMplsLspExpProfileBits."
    DEFVAL { out }
    ::= { tMplsLspExpProfileEntry 3 }
    
tMplsLspExpProfileLastChanged OBJECT-TYPE
    SYNTAX       TimeStamp
    MAX-ACCESS   read-only
    STATUS       current
    DESCRIPTION
        "timestamp of last change to this row in tMplsLspExpProfileTable."
    ::= { tMplsLspExpProfileEntry 4 }    

-- 

tGlobalMplsLspExpProfile OBJECT-TYPE
    SYNTAX       TMplsLspExpProfMapID
    MAX-ACCESS   read-create
    STATUS       current
    DESCRIPTION
        "tGlobalMplsLspExpProfile is used by the LDP packets when the ip 
        interface is configured in color aware mode. When the ip interface
        is configured in color blind mode, tGlobalMplsLspExpProfile is not
        applied to LDP packets received on that ip interface"
    DEFVAL { 1 }
    ::= { tMplsQosObjects 3 }

tLdpLocalFcEnableAdminStatus OBJECT-TYPE
    SYNTAX       TruthValue
    MAX-ACCESS   read-create
    STATUS       current
    DESCRIPTION
        "When tLdpLocalFcEnableAdminStatus is not set, the behavior is like 
        SAS release 3.0 here the profile policy will be attached to one qos 
        policy. tLdpLocalFcEnableAdminStatus when set to true the system 
        opertation status .'tLdpLocalFcEnableOperStatus' will also become 'true',
        
        When tLdpLocalFcEnableAdminStatus is set then more than one profile 
        policy can be attached to network policy
        
        When tLdpLocalFcEnableAdminStatus is reset to 'false', the system  oper 
        'tLdpLocalFcEnableOperStatus' status would continue to be true until the 
        system is reset.tLdpLocalFcEnableAdminStatus will take effect when the 
        system is reset, 
        "
    DEFVAL { false }
    ::= { tMplsQosObjects 5 }

tLdpLocalFcEnableOperStatus OBJECT-TYPE
    SYNTAX       TruthValue
    MAX-ACCESS   read-only
    STATUS       current
    DESCRIPTION
        "Operational status of how ldp local fc is configured.
        
        After the system init, reseting tLdpLocalFcEnableAdminStatus to false
        from 'true' take effect when the system is reset"
    ::= { tMplsQosObjects 6 }
    
--
-- access-egress policy table
--
tAccessEgressTable OBJECT-TYPE
    SYNTAX       SEQUENCE OF TAccessEgressEntry
    MAX-ACCESS   not-accessible
    STATUS       current
    DESCRIPTION
        "Information about all Access-egress policies."
    ::= { tAccessEgressObjects 1 }

tAccessEgressEntry OBJECT-TYPE
    SYNTAX       TAccessEgressEntry
    MAX-ACCESS   not-accessible
    STATUS       current
    DESCRIPTION
        "Access Egress QoS information for a particular port"
    INDEX { tAccessEgressIndex }
    ::= { tAccessEgressTable 1 }

TAccessEgressEntry ::= SEQUENCE
    {
        tAccessEgressIndex                  TAccessEgressPolicyID, 
        tAccessEgressRowStatus              RowStatus,
        tAccessEgressScope                  TItemScope,
        tAccessEgressDescription            TItemDescription,
        tAccessEgressLastChanged            TimeStamp,
        tAccessEgressRemark                 TruthValue,
        tAccessEgressRemarkPolicyId         TRemarkPolicyID,
        tAccessEgressRemarkType             INTEGER,
        tAccessEgressMPQueuesAggAdminPIR    TPIRRate,
        tAccessEgressMPQueuesAggAdminCIR    TCIRRate,
        tAccessEgressMPQueuesAggOperPIR     TPIRRate,
        tAccessEgressMPQueuesAggOperCIR     TCIRRate
    }

tAccessEgressIndex OBJECT-TYPE
    SYNTAX       TAccessEgressPolicyID
    MAX-ACCESS   not-accessible
    STATUS       current
    DESCRIPTION
        "the sap-egress policy ID is used as index for the table."
    ::= { tAccessEgressEntry 1 }

tAccessEgressRowStatus OBJECT-TYPE
    SYNTAX       RowStatus
    MAX-ACCESS   read-create
    STATUS       current
    DESCRIPTION
        "Row Status of this policy's entry."
    ::= { tAccessEgressEntry 2 }

tAccessEgressScope OBJECT-TYPE
    SYNTAX       TItemScope
    MAX-ACCESS   read-create
    STATUS       current
    DESCRIPTION
        "scope of the sap-egress policy."
    DEFVAL { template }
    ::= { tAccessEgressEntry 3 }

tAccessEgressDescription OBJECT-TYPE
    SYNTAX       TItemDescription
    MAX-ACCESS   read-create
    STATUS       current
    DESCRIPTION
        "user-supplied description of this sap-egress policy."
    DEFVAL { ''H }
    ::= { tAccessEgressEntry 4 }

tAccessEgressLastChanged OBJECT-TYPE
    SYNTAX       TimeStamp
    MAX-ACCESS   read-only
    STATUS       current
    DESCRIPTION
        "timestamp of last change to this row in tAccessEgressTable."
    ::= { tAccessEgressEntry 5 }

tAccessEgressRemark OBJECT-TYPE
    SYNTAX       TruthValue
    MAX-ACCESS   read-create
    STATUS       current
    DESCRIPTION
        "This object specifies if the system
         will remark the egress packets or not. DEf val is
         TRUE for STU and FALSE for MTU"
    DEFVAL { false }
::= { tAccessEgressEntry 6 }

tAccessEgressRemarkPolicyId OBJECT-TYPE
    SYNTAX       TRemarkPolicyID
    MAX-ACCESS   read-create
    STATUS       current
    DESCRIPTION
        "Remark Policy Id that be used when remarking is enabled."
    DEFVAL { 1 }
    ::= { tAccessEgressEntry 7 }

tAccessEgressRemarkType OBJECT-TYPE
    SYNTAX       INTEGER {
                     use-dot1p  (1),
                     use-dscp   (2),
                     all        (3)
                 }
    MAX-ACCESS   read-create
    STATUS       current
    DESCRIPTION
        "This object specifies system remark type, tAccessEgressRemark
        will be set to true and tAccessEgressRemarkType will specify the
        remark type."
    ::= { tAccessEgressEntry 8 }

tAccessEgressMPQueuesAggAdminPIR OBJECT-TYPE
    SYNTAX       TPIRRate
    MAX-ACCESS   read-create
    STATUS       current
    DESCRIPTION
        "The administrative PIR specified by the user."
    DEFVAL { -1 }
    ::= { tAccessEgressEntry 9 }

tAccessEgressMPQueuesAggAdminCIR OBJECT-TYPE
    SYNTAX       TCIRRate
    MAX-ACCESS   read-create
    STATUS       current
    DESCRIPTION
        "The administrative CIR specified by the user."
    DEFVAL { 0 }
    ::= { tAccessEgressEntry 10 }

tAccessEgressMPQueuesAggOperPIR OBJECT-TYPE
    SYNTAX       TPIRRate
    MAX-ACCESS   read-only
    STATUS       current
    DESCRIPTION
        "The administrative PIR specified by the user."
    ::= { tAccessEgressEntry 11 }

tAccessEgressMPQueuesAggOperCIR OBJECT-TYPE
    SYNTAX       TCIRRate
    MAX-ACCESS   read-only
    STATUS       current
    DESCRIPTION
        "The operational value derived by computing the CIR value from
         the administrative CIR and PIR values and their corresponding
         adaptation rules."
    ::= { tAccessEgressEntry 12 }

--
-- access-egress policy queue table
--

tAccessEgressQueueTable OBJECT-TYPE
    SYNTAX       SEQUENCE OF TAccessEgressQueueEntry
    MAX-ACCESS   not-accessible
    STATUS       current
    DESCRIPTION  "information about all access-egress policies' queues."
    ::= {  tAccessEgressObjects 2 }

tAccessEgressQueueEntry OBJECT-TYPE
    SYNTAX       TAccessEgressQueueEntry
    MAX-ACCESS   not-accessible
    STATUS       current
    DESCRIPTION
        "Information about a particular sap-egress queue.
         Entries are created/deleted by user.
         There is no StorageType object, entries have a presumed
         StorageType of nonVolatile."
    INDEX { tAccessEgressIndex, tAccessEgressQueueIndex }
    ::= { tAccessEgressQueueTable 1 }

TAccessEgressQueueEntry ::= SEQUENCE
    {
        tAccessEgressQueueIndex             TEgressQueueId,
        tAccessEgressQueueRowStatus         RowStatus,
        tAccessEgressQueueCBS               TBurstSize,
        tAccessEgressQueueMBS               TBurstSize,
        tAccessEgressQueuePIRAdaptation     TAdaptationRule,
        tAccessEgressQueueCIRAdaptation     TAdaptationRule,
        tAccessEgressQueueAdminPIR          TPIRRate,
        tAccessEgressQueueAdminCIR          TCIRRate,
        tAccessEgressQueueOperPIR           TPIRRate,
        tAccessEgressQueueOperCIR           TCIRRate,
        tAccessEgressQueueLastChanged       TimeStamp,
        tAccessEgressQueuePolicyName        TNamedItem,
        tAccessEgressQueuePolicyQueueMode   INTEGER,
        tAccessEgressQueuePolicyWeight      INTEGER,
        tAccessEgressQueueAdminPIRPercent   Unsigned32,
        tAccessEgressQueueAdminCIRPercent   Unsigned32,
        tAccessEgressQueueRateType          TBWRateType
    }

tAccessEgressQueueIndex OBJECT-TYPE
    SYNTAX       TEgressQueueId (1..8)
    MAX-ACCESS   not-accessible
    STATUS       current
    DESCRIPTION
        "the number of a queue.  zero is not allowed.
         for sap-egress, only three queues are allowed,
         so the queue index range is restricted."
    ::= { tAccessEgressQueueEntry 1 }

tAccessEgressQueueRowStatus OBJECT-TYPE
    SYNTAX       RowStatus
    MAX-ACCESS   read-create
    STATUS       current
    DESCRIPTION
        "Row Status of the entry."
    ::= { tAccessEgressQueueEntry 2 }

tAccessEgressQueueCBS OBJECT-TYPE
    SYNTAX       TBurstSize
    MAX-ACCESS   read-create
    STATUS       current
    DESCRIPTION
        "The amount of reserved buffer space (in kilo bytes) for the queue."
    DEFVAL { -1 }
    ::= { tAccessEgressQueueEntry 3 }

tAccessEgressQueueMBS OBJECT-TYPE
    SYNTAX       TBurstSize
    MAX-ACCESS   read-create
    STATUS       current
    DESCRIPTION
        "The maximum amount of buffer space (in kilo bytes) allowed for the
        queue."
    DEFVAL { -1 }
    ::= { tAccessEgressQueueEntry 4 }

tAccessEgressQueuePIRAdaptation OBJECT-TYPE
    SYNTAX       TAdaptationRule
    MAX-ACCESS   read-create
    STATUS       current
    DESCRIPTION
        "The adaptation rule to be used while computing the operational PIR
         value. The adaptation rule specifies the rules to compute the
         operational values while maintaining minimum offset."
    DEFVAL { closest }
    ::= { tAccessEgressQueueEntry 5 }

tAccessEgressQueueCIRAdaptation OBJECT-TYPE
    SYNTAX       TAdaptationRule
    MAX-ACCESS   read-create
    STATUS       current
    DESCRIPTION
        "The adaptation rule to be used while computing the operational CIR
         value. The adaptation rule specifies the rules to compute the
         operational values while maintaining minimum offset."
    DEFVAL { closest }
    ::= { tAccessEgressQueueEntry 6 }

tAccessEgressQueueAdminPIR OBJECT-TYPE
    SYNTAX       TPIRRate
    MAX-ACCESS   read-create
    STATUS       current
    DESCRIPTION
        "The administrative PIR specified by the user."
    DEFVAL { -1 }
    ::= { tAccessEgressQueueEntry 7 }

tAccessEgressQueueAdminCIR OBJECT-TYPE
    SYNTAX       TCIRRate
    MAX-ACCESS   read-create
    STATUS       current
    DESCRIPTION
        "The administrative CIR specified by the user."
    DEFVAL { 0 }
    ::= { tAccessEgressQueueEntry 8 }

tAccessEgressQueueOperPIR OBJECT-TYPE
    SYNTAX       TPIRRate
    MAX-ACCESS   read-only
    STATUS       current
    DESCRIPTION
        "The administrative PIR specified by the user."
    ::= { tAccessEgressQueueEntry 9 }

tAccessEgressQueueOperCIR OBJECT-TYPE
    SYNTAX       TCIRRate
    MAX-ACCESS   read-only
    STATUS       current
    DESCRIPTION
        "The operational value derived by computing the CIR value from
         the administrative CIR and PIR values and their corresponding
         adaptation rules."
    ::= { tAccessEgressQueueEntry 10 }

tAccessEgressQueueLastChanged OBJECT-TYPE
    SYNTAX       TimeStamp
    MAX-ACCESS   read-only
    STATUS       current
    DESCRIPTION
        "timestamp of last change to this row in tAccessEgressQueueTable."
    ::= { tAccessEgressQueueEntry 11 }

tAccessEgressQueuePolicyName  OBJECT-TYPE
    SYNTAX       TNamedItem 
    MAX-ACCESS   read-create
    STATUS       current
    DESCRIPTION
        "SapEgressQueuePolicyName determines the queue management policy
        attached to this SAP Egress queue."
    DEFVAL { "default" }
    ::= { tAccessEgressQueueEntry 12 }

tAccessEgressQueuePolicyQueueMode OBJECT-TYPE
    SYNTAX       INTEGER {
                     strict-ef   (1),
                     strict      (2),
                     weighted    (3)
                 }
    MAX-ACCESS   read-create
    STATUS       current
    DESCRIPTION
        "tAccessEgressQueuePolicyQueueMode specifies this policies mode. It has
    to be set when the policy is created."
    DEFVAL { weighted }
    ::= { tAccessEgressQueueEntry 13 }

tAccessEgressQueuePolicyWeight OBJECT-TYPE
    SYNTAX       INTEGER (1..15)
    MAX-ACCESS   read-create
    STATUS       current
    DESCRIPTION
        "tAccessEgressQueuePolicyWeight specifies this policies weight. It is
    applicable only if queue mode is weighted."
    DEFVAL { 1 }    
    ::= { tAccessEgressQueueEntry 14 }

tAccessEgressQueueAdminPIRPercent OBJECT-TYPE
    SYNTAX       Unsigned32 (1..100)
    UNITS        "hundredths of a percent"
    MAX-ACCESS   read-create
    STATUS       current
    DESCRIPTION
        "The administrative PIR percentage, in hundredths of a percent.
         An 'inconsistentValue' error is returned if 
         tAccessEgressQueueAdminPIRPercent is set to non-default value when the 
         object tAccessEgressQueueRateType is set to 'kbps'."
    DEFVAL { 100 }
    ::= { tAccessEgressQueueEntry 15 }

tAccessEgressQueueAdminCIRPercent OBJECT-TYPE
    SYNTAX       Unsigned32 (0..100)
    UNITS        "hundredths of a percent"
    MAX-ACCESS   read-create
    STATUS       current
    DESCRIPTION
        "The administrative CIR percentage, in hundredths of a percent.
         An 'inconsistentValue' error is returned if 
         tAccessEgressQueueAdminCIRPercent is set to non-default value when the
         object tAccessEgressQueueRateType is set to 'kbps'."
    DEFVAL { 0 }
    ::= { tAccessEgressQueueEntry 16 }

tAccessEgressQueueRateType OBJECT-TYPE
    SYNTAX       TBWRateType
    MAX-ACCESS   read-create
    STATUS       current
    DESCRIPTION
        "The value of tAccessEgressQueueRateType specifies the type of Egress 
         Queue rate.

         When the value of the object is set to 'kbps', the ingresss queue rates
         are specified in kbps. The objects  tAccessEgressQueueAdminCIRPercent and
         tAccessEgressQueueAdminPIRPercent will be set to their default values.

         When the value of the object is set to either 'percentOfPortLimit' or
         'percentOfLocalLimit', the egress queue rates are specified in 
         percentage. The objects tAccessEgressQueueAdminCIR and 
         tAccessEgressQueueAdminPIR will be set to their default values."
    DEFVAL { kbps }
    ::= { tAccessEgressQueueEntry 17 }


--
-- access-egress policy fc table
--

tAccessEgressFCTable OBJECT-TYPE
    SYNTAX       SEQUENCE OF TAccessEgressFCEntry
    MAX-ACCESS   not-accessible
    STATUS       current
    DESCRIPTION  "  "
    ::= { tAccessEgressObjects 3 }  

tAccessEgressFCEntry OBJECT-TYPE
    SYNTAX       TAccessEgressFCEntry
    MAX-ACCESS   not-accessible
    STATUS       current
    DESCRIPTION
        "Information about a particular access-egress policy's
         forwarding class mappings to queues and dot1p values.
         Entries are created/deleted by user.
         There is no StorageType object, entries have a presumed
         StorageType of nonVolatile.
        "
    INDEX { tAccessEgressIndex, tAccessEgressFCName }
    ::= { tAccessEgressFCTable 1 }

TAccessEgressFCEntry ::= SEQUENCE
    {
        tAccessEgressFCName                TFCName,
        tAccessEgressFCRowStatus           RowStatus,
        tAccessEgressFCQueue               TEgressQueueId,
        tAccessEgressFCDot1PInProfile      Dot1PPriority,
        tAccessEgressFCDot1POutProfile     Dot1PPriority,
        tAccessEgressFCLastChanged         TimeStamp,
        tAccessEgressFCDscpInProfile       TDSCPNameOrEmpty,
        tAccessEgressFCDscpOutProfile      TDSCPNameOrEmpty,
        tAccessEgressFCDot1PProfile        Dot1PPriority,
        tAccessEgressFCForceDEValue        TDEValue,
        tAccessEgressFCDEMark              TruthValue
    }

tAccessEgressFCName OBJECT-TYPE
    SYNTAX       TFCName
    MAX-ACCESS   not-accessible
    STATUS       current
    DESCRIPTION
        "forwarding class name."
    ::= { tAccessEgressFCEntry 1 }

tAccessEgressFCRowStatus OBJECT-TYPE
    SYNTAX       RowStatus
    MAX-ACCESS   read-create
    STATUS       current
    DESCRIPTION
        "Row Status."
    ::= { tAccessEgressFCEntry 2 }

tAccessEgressFCQueue OBJECT-TYPE
    SYNTAX       TEgressQueueId
    MAX-ACCESS   read-create
    STATUS       current
    DESCRIPTION
        "The queue to use for packets in this forwarding class.
         No FC can map to the same queue being used by 'premium' class.
         You must specify a valid queue-id before setting the row status
         to active."
    ::= { tAccessEgressFCEntry 3 }

tAccessEgressFCDot1PInProfile OBJECT-TYPE
    SYNTAX       Dot1PPriority
    MAX-ACCESS   read-create
    STATUS       current
    DESCRIPTION
        "the Dot1p to use for in-profile traffic."
    DEFVAL { -1 }
    ::= { tAccessEgressFCEntry 4 }

tAccessEgressFCDot1POutProfile OBJECT-TYPE
    SYNTAX       Dot1PPriority
    MAX-ACCESS   read-create
    STATUS       current
    DESCRIPTION
        "the Dot1p to use for in-profile traffic."
    DEFVAL { -1 }
    ::= { tAccessEgressFCEntry 5 }

tAccessEgressFCLastChanged OBJECT-TYPE
    SYNTAX       TimeStamp
    MAX-ACCESS   read-only
    STATUS       current
    DESCRIPTION
        "timestamp of last change to this row in tAccessEgressFCTable."
    ::= { tAccessEgressFCEntry 6 }

tAccessEgressFCDscpInProfile OBJECT-TYPE
    SYNTAX       TDSCPNameOrEmpty
    MAX-ACCESS   read-create
    STATUS       current
    DESCRIPTION
        "The DSCP to use for in-profile traffic."
    DEFVAL { ''H }
    ::= { tAccessEgressFCEntry 7 }

tAccessEgressFCDscpOutProfile OBJECT-TYPE
    SYNTAX       TDSCPNameOrEmpty
    MAX-ACCESS   read-create
    STATUS       current
    DESCRIPTION
        "The DSCP to use for out-profile traffic."
    DEFVAL { ''H }
    ::= { tAccessEgressFCEntry 8 }

tAccessEgressFCDot1PProfile OBJECT-TYPE
    SYNTAX       Dot1PPriority
    MAX-ACCESS   read-create
    STATUS       current
    DESCRIPTION
        "the Dot1p to use for profile traffic."
    DEFVAL { -1 }
    ::= { tAccessEgressFCEntry 9 }

tAccessEgressFCForceDEValue OBJECT-TYPE
    SYNTAX       TDEValue
    MAX-ACCESS   read-create
    STATUS       current
    DESCRIPTION
        "The value of tAccessEgressFCForceDEValue specifies the DE value to set
        for Access egress packets in this forwarding class regardless of
        profile status of the frames.

       An inconsistentValue error is returned if this object is set to any value
       other than '-1', when tAccessEgressFCDEMark object is set to
       'false'."
    DEFVAL { -1 }
    ::= { tAccessEgressFCEntry 10 }
    
tAccessEgressFCDEMark OBJECT-TYPE
    SYNTAX       TruthValue
    MAX-ACCESS   read-create
    STATUS       current
    DESCRIPTION
       "The value of tAccessEgressFCDEMark specifies whether to set DE value
       in the frames of this forwarding class.

       An inconsistentValue error is returned if this object is set to 'false'
       when tAccessEgressFCForceDEValue object is not set to '-1'."
    DEFVAL { false }
    ::= { tAccessEgressFCEntry 11 }

--
-- Access egress multipoint queue table
--
tAccessEgressMPQueueTable OBJECT-TYPE
    SYNTAX       SEQUENCE OF TAccessEgressMPQueueEntry
    MAX-ACCESS   not-accessible
    STATUS       current
    DESCRIPTION  "information about all access-egress policies' queues."
    ::= {  tAccessEgressObjects 4 }

tAccessEgressMPQueueEntry OBJECT-TYPE
    SYNTAX       TAccessEgressMPQueueEntry
    MAX-ACCESS   not-accessible
    STATUS       current
    DESCRIPTION
        "Information about a particular sap-egress queue.
         Entries are created/deleted by user.
         There is no StorageType object, entries have a presumed
         StorageType of nonVolatile."
    INDEX { tAccessEgressIndex, tAccessEgressMPQueueIndex }
    ::= { tAccessEgressMPQueueTable 1 }

TAccessEgressMPQueueEntry ::= SEQUENCE
    {
        tAccessEgressMPQueueIndex             TEgressQueueId,
        tAccessEgressMPQueueRowStatus         RowStatus,
        tAccessEgressMPQueueCBS               TBurstSize,
        tAccessEgressMPQueueMBS               TBurstSize,
        tAccessEgressMPQueuePIRAdaptation     TAdaptationRule,
        tAccessEgressMPQueueCIRAdaptation     TAdaptationRule,
        tAccessEgressMPQueueAdminPIR          TPIRRate,
        tAccessEgressMPQueueAdminCIR          TCIRRate,
        tAccessEgressMPQueueOperPIR           TPIRRate,
        tAccessEgressMPQueueOperCIR           TCIRRate,
        tAccessEgressMPQueueLastChanged       TimeStamp,
        tAccessEgressMPQueuePolicyName        TNamedItem,
        tAccessEgressMPQueuePolicyQueueMode   INTEGER,
        tAccessEgressMPQueuePolicyWeight      INTEGER
    }

tAccessEgressMPQueueIndex OBJECT-TYPE
    SYNTAX       TEgressQueueId (1..8)
    MAX-ACCESS   not-accessible
    STATUS       current
    DESCRIPTION
        "the number of a queue.  zero is not allowed.
         for sap-egress, only three queues are allowed,
         so the queue index range is restricted."
    ::= { tAccessEgressMPQueueEntry 1 }

tAccessEgressMPQueueRowStatus OBJECT-TYPE
    SYNTAX       RowStatus
    MAX-ACCESS   read-create
    STATUS       current
    DESCRIPTION
        "Row Status of the entry."
    ::= { tAccessEgressMPQueueEntry 2 }

tAccessEgressMPQueueCBS OBJECT-TYPE
    SYNTAX       TBurstSize
    MAX-ACCESS   read-create
    STATUS       current
    DESCRIPTION
        "The amount of reserved buffer space (in kilo bytes) for the queue."
    DEFVAL { -1 }
    ::= { tAccessEgressMPQueueEntry 3 }

tAccessEgressMPQueueMBS OBJECT-TYPE
    SYNTAX       TBurstSize
    MAX-ACCESS   read-create
    STATUS       current
    DESCRIPTION
        "The maximum amount of buffer space (in kilo bytes) allowed for the
        queue."
    DEFVAL { -1 }
    ::= { tAccessEgressMPQueueEntry 4 }

tAccessEgressMPQueuePIRAdaptation OBJECT-TYPE
    SYNTAX       TAdaptationRule
    MAX-ACCESS   read-create
    STATUS       current
    DESCRIPTION
        "The adaptation rule to be used while computing the operational PIR
         value. The adaptation rule specifies the rules to compute the
         operational values while maintaining minimum offset."
    DEFVAL { closest }
    ::= { tAccessEgressMPQueueEntry 5 }

tAccessEgressMPQueueCIRAdaptation OBJECT-TYPE
    SYNTAX       TAdaptationRule
    MAX-ACCESS   read-create
    STATUS       current
    DESCRIPTION
        "The adaptation rule to be used while computing the operational CIR
         value. The adaptation rule specifies the rules to compute the
         operational values while maintaining minimum offset."
    DEFVAL { closest }
    ::= { tAccessEgressMPQueueEntry 6 }

tAccessEgressMPQueueAdminPIR OBJECT-TYPE
    SYNTAX       TPIRRate
    MAX-ACCESS   read-create
    STATUS       current
    DESCRIPTION
        "The administrative PIR specified by the user."
    DEFVAL { -1 }
    ::= { tAccessEgressMPQueueEntry 7 }

tAccessEgressMPQueueAdminCIR OBJECT-TYPE
    SYNTAX       TCIRRate
    MAX-ACCESS   read-create
    STATUS       current
    DESCRIPTION
        "The administrative CIR specified by the user."
    DEFVAL { 0 }
    ::= { tAccessEgressMPQueueEntry 8 }

tAccessEgressMPQueueOperPIR OBJECT-TYPE
    SYNTAX       TPIRRate
    MAX-ACCESS   read-only
    STATUS       current
    DESCRIPTION
        "The administrative PIR specified by the user."
    ::= { tAccessEgressMPQueueEntry 9 }

tAccessEgressMPQueueOperCIR OBJECT-TYPE
    SYNTAX       TCIRRate
    MAX-ACCESS   read-only
    STATUS       current
    DESCRIPTION
        "The operational value derived by computing the CIR value from
         the administrative CIR and PIR values and their corresponding
         adaptation rules."
    ::= { tAccessEgressMPQueueEntry 10 }

tAccessEgressMPQueueLastChanged OBJECT-TYPE
    SYNTAX       TimeStamp
    MAX-ACCESS   read-only
    STATUS       current
    DESCRIPTION
        "timestamp of last change to this row in tAccessEgressMPQueueTable."
    ::= { tAccessEgressMPQueueEntry 11 }

tAccessEgressMPQueuePolicyName  OBJECT-TYPE
    SYNTAX       TNamedItem 
    MAX-ACCESS   read-create
    STATUS       current
    DESCRIPTION
        "SapEgressMPQueuePolicyName determines the queue management policy
        attached to this SAP Egress queue."
    DEFVAL { "default" }
    ::= { tAccessEgressMPQueueEntry 12 }

tAccessEgressMPQueuePolicyQueueMode OBJECT-TYPE
    SYNTAX       INTEGER {
                     strict-ef   (1),
                     strict      (2),
                     weighted    (3)
                 }
    MAX-ACCESS   read-create
    STATUS       current
    DESCRIPTION
        "tAccessEgressMPQueuePolicyQueueMode specifies this policies mode. It has
    to be set when the policy is created."
    DEFVAL { weighted }
    ::= { tAccessEgressMPQueueEntry 13 }

tAccessEgressMPQueuePolicyWeight OBJECT-TYPE
    SYNTAX       INTEGER (1..15)
    MAX-ACCESS   read-create
    STATUS       current
    DESCRIPTION
        "tAccessEgressMPQueuePolicyWeight specifies this policies weight. It is
    applicable only if queue mode is weighted."
    DEFVAL { 1 }    
    ::= { tAccessEgressMPQueueEntry 14 }


--
-- sap-ingress meter table
--
tSapIngressMeterTable OBJECT-TYPE
    SYNTAX       SEQUENCE OF TSapIngressMeterEntry
    MAX-ACCESS   not-accessible
    STATUS       current
    DESCRIPTION
        "Information about all sap-ingress policies' Meters."
    ::= { tSASSapIngressObjects 1 }  
    
tSapIngressMeterEntry OBJECT-TYPE
    SYNTAX       TSapIngressMeterEntry
    MAX-ACCESS   not-accessible
    STATUS       current
    DESCRIPTION
        "Information about a particular meter for a sap-ingress policy.
         Meter (1) is the used as a default for unicast and meter (11) is
         used as a default for multicast. Both these are created by the
         agent and can be edited but not removed from the system.
         Other entries are created by user."
    INDEX { tSapIngressIndex, tSapIngressMeter }
    ::= { tSapIngressMeterTable 1 }

TSapIngressMeterEntry ::= SEQUENCE
    {
        tSapIngressMeter                 TSapIngressMeterId, 
        tSapIngressMeterRowStatus        RowStatus,
        tSapIngressMeterMCast            TruthValue,
        tSapIngressMeterCBS              TIngressBurstSize,
        tSapIngressMeterMBS              TIngressBurstSize,
        tSapIngressMeterPIRAdaptation    TAdaptationRule,
        tSapIngressMeterCIRAdaptation    TAdaptationRule,
        tSapIngressMeterAdminPIR         TIngressPIRRate,
        tSapIngressMeterAdminCIR         TIngressCIRRate,
        tSapIngressMeterOperPIR          TPIRRate,
        tSapIngressMeterOperCIR          TCIRRate,
        tSapIngressMeterLastChanged      TimeStamp,
        tSapIngressMeterMode             TMeterMode,
        tSapIngressMeterRateMode         TMeterRateMode,
        tSapIngressMeterAdminCBS         TIngressBurstSize,
        tSapIngressMeterAdminMBS         TIngressBurstSize,
        tSapIngressMeterOperCBS          TIngressBurstSize,
        tSapIngressMeterOperMBS          TIngressBurstSize,
        tSapIngressMeterProfileMode      TruthValue,
        tSapIngressMeterColorMode        INTEGER,
        tSapIngressMeterAdminCBSType     INTEGER,
        tSapIngressMeterAdminCBSBytes    TIngressBurstSizeBytes,
        tSapIngressMeterAdminCBSKBytes   TIngressBurstSizeKBytes,
        tSapIngressMeterAdminMBSType     INTEGER,
        tSapIngressMeterAdminMBSBytes    TIngressBurstSizeBytes,
        tSapIngressMeterAdminMBSKBytes   TIngressBurstSizeKBytes,
        tSapIngressMeterOperCBSBytes     TIngressBurstSizeBytes,
        tSapIngressMeterOperCBSKBytes    TIngressBurstSizeKBytes,
        tSapIngressMeterOperMBSBytes     TIngressBurstSizeBytes,
        tSapIngressMeterOperMBSKBytes    TIngressBurstSizeKBytes
    }


tSapIngressMeter OBJECT-TYPE
    SYNTAX       TSapIngressMeterId 
    MAX-ACCESS   not-accessible
    STATUS       current
    DESCRIPTION
        "The Meter ID is used as the secondary index to the table entry."
    ::= { tSapIngressMeterEntry 1 }

tSapIngressMeterRowStatus OBJECT-TYPE
    SYNTAX       RowStatus
    MAX-ACCESS   read-create
    STATUS       current
    DESCRIPTION
        "Row Status of the entry. This allows creation/deletion of rows in this
         table."
    ::= { tSapIngressMeterEntry 2 }

tSapIngressMeterMCast OBJECT-TYPE
    SYNTAX       TruthValue
    MAX-ACCESS   read-create
    STATUS       current
    DESCRIPTION
        "This object specifies if this is a multicast meter or not."
    DEFVAL { false }
    ::= { tSapIngressMeterEntry 8 }

tSapIngressMeterCBS OBJECT-TYPE
    SYNTAX       TIngressBurstSize 
    MAX-ACCESS   read-create
    STATUS       obsolete
    DESCRIPTION
        "The amount of committed burst size (in kilo bits) for the meter."
    DEFVAL { -1 }
    ::= { tSapIngressMeterEntry 10 }

tSapIngressMeterMBS OBJECT-TYPE
    SYNTAX       TIngressBurstSize
    MAX-ACCESS   read-create
    STATUS       obsolete
    DESCRIPTION
        "The maximum amount of burst size (in kilo bits) allowed for the
         meter."
    DEFVAL { -1 }
    ::= { tSapIngressMeterEntry 11 }

tSapIngressMeterCIRAdaptation OBJECT-TYPE
    SYNTAX       TAdaptationRule
    MAX-ACCESS   read-create
    STATUS       current
    DESCRIPTION
        "The adaptation rule to be used while computing the operational CIR
         value. The adaptation rule specifies the rules to compute the
         operational values while maintaining minimum offset."
    DEFVAL { closest }
    ::= { tSapIngressMeterEntry 14 }

tSapIngressMeterPIRAdaptation OBJECT-TYPE
    SYNTAX       TAdaptationRule
    MAX-ACCESS   read-create
    STATUS       current
    DESCRIPTION
        "The adaptation rule to be used while computing the operational PIR
         value. The adaptation rule specifies the rules to compute the
         operational values while maintaining minimum offset."
    DEFVAL { closest }
    ::= { tSapIngressMeterEntry 13 }


tSapIngressMeterAdminPIR OBJECT-TYPE
    SYNTAX       TIngressPIRRate
    MAX-ACCESS   read-create
    STATUS       current
    DESCRIPTION
        "The administrative PIR specified by the user."
    DEFVAL { -1 }
    ::= { tSapIngressMeterEntry 15 }

tSapIngressMeterAdminCIR OBJECT-TYPE
    SYNTAX       TIngressCIRRate
    MAX-ACCESS   read-create
    STATUS       current
    DESCRIPTION
        "The administrative CIR specified by the user."
    DEFVAL { 0 }
    ::= { tSapIngressMeterEntry 16 }

tSapIngressMeterOperPIR OBJECT-TYPE
    SYNTAX       TPIRRate
    MAX-ACCESS   read-only
    STATUS       current
    DESCRIPTION
        "The operational value derived by computing the PIR value from
         the administrative PIR value and their corresponding
         adaptation rules."
    ::= { tSapIngressMeterEntry 17 }

tSapIngressMeterOperCIR OBJECT-TYPE
    SYNTAX       TCIRRate
    MAX-ACCESS   read-only
    STATUS       current
    DESCRIPTION
        "The operational value derived by computing the CIR value from
         the administrative CIR value and their corresponding
         adaptation rules."
    ::= { tSapIngressMeterEntry 18 }

tSapIngressMeterLastChanged OBJECT-TYPE
    SYNTAX       TimeStamp
    MAX-ACCESS   read-only
    STATUS       current
    DESCRIPTION
        "Timestamp of last change to this row in tSapIngressMeterTable."
    ::= { tSapIngressMeterEntry 19 }

tSapIngressMeterMode OBJECT-TYPE
    SYNTAX       TMeterMode
    MAX-ACCESS   read-create
    STATUS       current
    DESCRIPTION
        "This object is not used on SAS platform currently"
    DEFVAL { priority }
    ::= { tSapIngressMeterEntry 21 }

tSapIngressMeterRateMode OBJECT-TYPE
    SYNTAX       TMeterRateMode
    MAX-ACCESS   read-create
    STATUS       current
    DESCRIPTION
        "Sap Ingress Meter Rate mode.The mode can be configured as 
         Two Rate Three Color Marker (trTCM) or Single Rate Three Color 
         Marker (srTCM). The mode command can be executed at anytime."
    DEFVAL { trtcm1 }
    ::= { tSapIngressMeterEntry 22 }         


tSapIngressMeterAdminCBS OBJECT-TYPE
    SYNTAX       TIngressBurstSize
    MAX-ACCESS   read-create
    STATUS       current
    DESCRIPTION
        "The administrative CBS specified by the user. The amount of 
        committed burst size (in kilo bits) for the meter."
    DEFVAL { -1 }
    ::= { tSapIngressMeterEntry 23 }

tSapIngressMeterAdminMBS OBJECT-TYPE
    SYNTAX       TIngressBurstSize
    MAX-ACCESS   read-create
    STATUS       current
    DESCRIPTION
        "The administrative MBS specified by the user. The maximum amount 
        of burst size (in kilo bits) allowed for the meter."
    DEFVAL { -1 }
    ::= { tSapIngressMeterEntry 24 }

tSapIngressMeterOperCBS OBJECT-TYPE
    SYNTAX       TIngressBurstSize 
    MAX-ACCESS   read-only
    STATUS       current
    DESCRIPTION
        "The operational value derived by computing the CBS value from
         the administrative CBS value"
    ::= { tSapIngressMeterEntry 25 }

tSapIngressMeterOperMBS OBJECT-TYPE
    SYNTAX       TIngressBurstSize
    MAX-ACCESS   read-only
    STATUS       current
    DESCRIPTION
        "The operational value derived by computing the MBS value from
         the administrative MBS value"
    ::= { tSapIngressMeterEntry 26 }

tSapIngressMeterProfileMode OBJECT-TYPE
    SYNTAX       TruthValue
    MAX-ACCESS   read-create
    STATUS       current
    DESCRIPTION
        "The value of this object specifies whether 
        the meter mode is color aware or color blind"
    DEFVAL { false }
    ::= { tSapIngressMeterEntry 27 }

tSapIngressMeterColorMode OBJECT-TYPE
    SYNTAX       INTEGER {
                     color-aware  (1),
                     color-blind  (2)
                 }
    MAX-ACCESS   read-create
    STATUS       current
    DESCRIPTION
        "Set meter color mode"
    DEFVAL { color-blind }
    ::= { tSapIngressMeterEntry 28 }

tSapIngressMeterAdminCBSType OBJECT-TYPE
    SYNTAX       INTEGER {
                    kbits   (1),
                    bytes   (2),
                    kbytes  (3)
                 }
    MAX-ACCESS   read-create
    STATUS       current
    DESCRIPTION
        "The type for administrative CBS specified by the user. The amount of 
        committed burst size (in kilo bits/bytes/kbytes) for the meter."
    DEFVAL { kbits }
    ::= { tSapIngressMeterEntry 29 }

tSapIngressMeterAdminCBSBytes OBJECT-TYPE
    SYNTAX       TIngressBurstSizeBytes
    MAX-ACCESS   read-create
    STATUS       current
    DESCRIPTION
        "The administrative CBS specified by the user. The amount of 
        committed burst size (in bytes) for the meter."
    DEFVAL { -1 }
    ::= { tSapIngressMeterEntry 30 }

tSapIngressMeterAdminCBSKBytes OBJECT-TYPE
    SYNTAX       TIngressBurstSizeKBytes
    MAX-ACCESS   read-create
    STATUS       current
    DESCRIPTION
        "The administrative CBS specified by the user. The amount of 
        committed burst size (in kilo bytes) for the meter."
    DEFVAL { -1 }
    ::= { tSapIngressMeterEntry 31 }

tSapIngressMeterAdminMBSType OBJECT-TYPE
    SYNTAX       INTEGER {
                    kbits   (1),
                    bytes   (2),
                    kbytes  (3)
                 }
    MAX-ACCESS   read-create
    STATUS       current
    DESCRIPTION
        "The type for administrative MBS specified by the user. The amount of 
        committed burst size (in kilo bits/bytes/kbytes) for the meter."
    DEFVAL { kbits }
    ::= { tSapIngressMeterEntry 32 }

tSapIngressMeterAdminMBSBytes OBJECT-TYPE
    SYNTAX       TIngressBurstSizeBytes
    MAX-ACCESS   read-create
    STATUS       current
    DESCRIPTION
        "The administrative MBS specified by the user. The amount of 
        committed burst size (in bytes) for the meter."
    DEFVAL { -1 }
    ::= { tSapIngressMeterEntry 33 }

tSapIngressMeterAdminMBSKBytes OBJECT-TYPE
    SYNTAX       TIngressBurstSizeKBytes
    MAX-ACCESS   read-create
    STATUS       current
    DESCRIPTION
        "The administrative MBS specified by the user. The amount of 
        committed burst size (in kilo bytes) for the meter."
    DEFVAL { -1 }
    ::= { tSapIngressMeterEntry 34 }

tSapIngressMeterOperCBSBytes OBJECT-TYPE
    SYNTAX       TIngressBurstSizeBytes 
    MAX-ACCESS   read-only
    STATUS       current
    DESCRIPTION
        "The operational value derived by computing the CBS value from
         the administrative CBS value"
    ::= { tSapIngressMeterEntry 35 }

tSapIngressMeterOperCBSKBytes OBJECT-TYPE
    SYNTAX       TIngressBurstSizeKBytes
    MAX-ACCESS   read-only
    STATUS       current
    DESCRIPTION
        "The operational value derived by computing the CBS value from
         the administrative CBS value"
    ::= { tSapIngressMeterEntry 36 }

tSapIngressMeterOperMBSBytes OBJECT-TYPE
    SYNTAX       TIngressBurstSizeBytes 
    MAX-ACCESS   read-only
    STATUS       current
    DESCRIPTION
        "The operational value derived by computing the MBS value from
         the administrative MBS value"
    ::= { tSapIngressMeterEntry 37 }

tSapIngressMeterOperMBSKBytes OBJECT-TYPE
    SYNTAX       TIngressBurstSizeKBytes
    MAX-ACCESS   read-only
    STATUS       current
    DESCRIPTION
        "The operational value derived by computing the MBS value from
         the administrative MBS value"
    ::= { tSapIngressMeterEntry 38 }

---

tNetworkIngressFCExtnTable OBJECT-TYPE
    SYNTAX       SEQUENCE OF TNetworkIngressFCExtnEntry
    MAX-ACCESS   not-accessible
    STATUS       current
    DESCRIPTION
        "This table maintains the mapping of a particular
         forwarding class traffic into the specified meter."
    ::= { tSASNetworkIngressObjects 1 }

tNetworkIngressFCExtnEntry OBJECT-TYPE
    SYNTAX       TNetworkIngressFCExtnEntry
    MAX-ACCESS   not-accessible
    STATUS       current
    DESCRIPTION
        "Information about a particular network-ingress policy's
         forwarding class mappings to meter.

         Entries are created and deleted by user. They have
         a presumed StorageType of nonVolatile."
    INDEX { tNetworkPolicyIndex, tNetworkIngressFCExtnName }
    ::= { tNetworkIngressFCExtnTable 1 }

TNetworkIngressFCExtnEntry ::= SEQUENCE
    {
        tNetworkIngressFCExtnName           TNamedItem,
        tNetworkIngressFCExtnRowStatus      RowStatus,
        tNetworkIngressFCExtnMeter          TNetworkIngressMeterId,
        tNetworkIngressFCExtnMCastMeter     TNetworkIngressMeterId,
        tNetworkIngressFCExtnLastChanged    TimeStamp,
        tNetworkIngressFCExtnQueue          TQueueId,
        tNetworkIngressFCExtnUseDei         TruthValue,
        tNetworkIngressFCExtnMCQueue        TQueueId
    }
    
tNetworkIngressFCExtnName OBJECT-TYPE
    SYNTAX       TNamedItem
    MAX-ACCESS   not-accessible
    STATUS       current
    DESCRIPTION
        "tNetworkIngressFCExtnName specifies the forwarding class 
        for which this mapping is defined."
    ::= { tNetworkIngressFCExtnEntry 1 }

tNetworkIngressFCExtnRowStatus OBJECT-TYPE
    SYNTAX       RowStatus
    MAX-ACCESS   read-create
    STATUS       current
    DESCRIPTION
        "Row Status for this Entry."
    ::= { tNetworkIngressFCExtnEntry 2 }

tNetworkIngressFCExtnMeter OBJECT-TYPE
    SYNTAX       TNetworkIngressMeterId
    MAX-ACCESS   read-create
    STATUS       current
    DESCRIPTION
        "The specific meter to be used for packets in this forwarding class.
         A value of zero implies that the default meters should be used."
    ::= { tNetworkIngressFCExtnEntry 3 }

tNetworkIngressFCExtnMCastMeter OBJECT-TYPE
    SYNTAX       TNetworkIngressMeterId
    MAX-ACCESS   read-create
    STATUS       current
    DESCRIPTION
        "The specific multicast meter to be used for packets in this forwarding
         class. The meter is used only for specific entities and will be
         ignored wherever it is irrelevant.

         A value of zero implies that the default meters should be used."
    ::= { tNetworkIngressFCExtnEntry 4 }

tNetworkIngressFCExtnLastChanged OBJECT-TYPE
    SYNTAX       TimeStamp
    MAX-ACCESS   read-only
    STATUS       current
    DESCRIPTION
        "tNetworkIngressFCExtnLastChanged indicates the value of sysUpTime
         when the forwarding class entry was last modified."
    ::= { tNetworkIngressFCExtnEntry 5 }

tNetworkIngressFCExtnQueue OBJECT-TYPE
    SYNTAX       TQueueId
    MAX-ACCESS   read-create
    STATUS       current
    DESCRIPTION
        "The specific queue to be used for packets in this forwarding class

         A value of zero implies that the default queue should be used."
    ::= { tNetworkIngressFCExtnEntry 6 }

tNetworkIngressFCExtnUseDei OBJECT-TYPE
    SYNTAX       TruthValue
    MAX-ACCESS   read-create
    STATUS       current
    DESCRIPTION
         "Enables/Disables Drop Eligible bit"
    DEFVAL { false }
    ::= { tNetworkIngressFCExtnEntry 7 }

tNetworkIngressFCExtnMCQueue OBJECT-TYPE
    SYNTAX       TQueueId
    MAX-ACCESS   read-create
    STATUS       current
    DESCRIPTION
        "The specific mc-queue to be used for packets in this forwarding class

         A value of zero implies that the default queue should be used."
    ::= { tNetworkIngressFCExtnEntry 8 }


tNetworkIngressMeterTable OBJECT-TYPE
    SYNTAX       SEQUENCE OF TNetworkIngressMeterEntry
    MAX-ACCESS   not-accessible
    STATUS       current
    DESCRIPTION
        "information about all network policies' meters."
    ::= { tSASNetworkIngressObjects 2 }  
    
tNetworkIngressMeterEntry OBJECT-TYPE
    SYNTAX       TNetworkIngressMeterEntry
    MAX-ACCESS   not-accessible
    STATUS       current
    DESCRIPTION
        "Information about a particular meter for a network policy.
         Meter (1) is the used as a default for unicast and meter (9) is
         used as a default for multicast. Both these are created by the
         agent and can be edited but not removed from the system.
         Other entries are created by user."
    INDEX { tNetworkPolicyIndex, tNetworkIngressMeterIndex }
    ::= { tNetworkIngressMeterTable 1 }

TNetworkIngressMeterEntry ::= SEQUENCE
    {
         tNetworkIngressMeterIndex             TNetworkIngressMeterId,
         tNetworkIngressMeterRowStatus         RowStatus,
         tNetworkIngressMeterCBS               TIngressBurstSize,
         tNetworkIngressMeterMBS               TIngressBurstSize,
         tNetworkIngressMeterCIRAdaptation     TAdaptationRule,
         tNetworkIngressMeterPIRAdaptation     TAdaptationRule,
         tNetworkIngressMeterAdminPIR          TIngressPIRRate,
         tNetworkIngressMeterAdminCIR          TIngressCIRRate,
         tNetworkIngressMeterOperPIR           TPIRRate,
         tNetworkIngressMeterOperCIR           TCIRRate,
         tNetworkIngressMeterLastChanged       TimeStamp,
         tNetworkIngressMeterMode              TMeterMode,
         tNetworkIngressMeterMCast             TruthValue,
         tNetworkIngressMeterRateMode          TMeterRateMode,
         tNetworkIngressMeterAdminCBS          TIngressBurstSize,
         tNetworkIngressMeterAdminMBS          TIngressBurstSize,
         tNetworkIngressMeterOperCBS           TIngressBurstSize,
         tNetworkIngressMeterOperMBS           TIngressBurstSize,
         tNetworkIngressMeterAdminCBSType      INTEGER,
         tNetworkIngressMeterAdminCBSBytes     TIngressBurstSizeBytes,
         tNetworkIngressMeterAdminCBSKBytes    TIngressBurstSizeKBytes,
         tNetworkIngressMeterAdminMBSType      INTEGER,
         tNetworkIngressMeterAdminMBSBytes     TIngressBurstSizeBytes,
         tNetworkIngressMeterAdminMBSKBytes    TIngressBurstSizeKBytes,
         tNetworkIngressMeterOperCBSBytes      TIngressBurstSizeBytes,
         tNetworkIngressMeterOperCBSKBytes     TIngressBurstSizeKBytes,
         tNetworkIngressMeterOperMBSBytes      TIngressBurstSizeBytes,
         tNetworkIngressMeterOperMBSKBytes     TIngressBurstSizeKBytes
    }

tNetworkIngressMeterIndex OBJECT-TYPE
    SYNTAX       TNetworkIngressMeterId
    MAX-ACCESS   not-accessible
    STATUS       current
    DESCRIPTION
        "The Meter ID is used as the secondary index to the table entry."
    ::= { tNetworkIngressMeterEntry 1 }

tNetworkIngressMeterRowStatus OBJECT-TYPE
    SYNTAX       RowStatus
    MAX-ACCESS   read-create
    STATUS       current
    DESCRIPTION
        "Row Status of the entry. This allows creation/deletion of rows in this
         table."
    ::= { tNetworkIngressMeterEntry 2 }

tNetworkIngressMeterCBS OBJECT-TYPE
    SYNTAX       TIngressBurstSize 
    MAX-ACCESS   read-create
    STATUS       obsolete
    DESCRIPTION
        "The amount of committed burst size (in kilo bits) for the meter."
    DEFVAL { -1 }
    ::= { tNetworkIngressMeterEntry 3 }

tNetworkIngressMeterMBS OBJECT-TYPE
    SYNTAX       TIngressBurstSize
    MAX-ACCESS   read-create
    STATUS       obsolete
    DESCRIPTION
        "The maximum amount of burst size (in kilo bits) allowed for the
         meter."
    DEFVAL { -1 }
    ::= { tNetworkIngressMeterEntry 4 }

tNetworkIngressMeterCIRAdaptation OBJECT-TYPE
    SYNTAX       TAdaptationRule
    MAX-ACCESS   read-create
    STATUS       current
    DESCRIPTION
        "The adaptation rule to be used while computing the operational CIR
         value. The adaptation rule specifies the rules to compute the
         operational values while maintaining minimum offset."
    DEFVAL { closest }
    ::= { tNetworkIngressMeterEntry 5 }

tNetworkIngressMeterPIRAdaptation OBJECT-TYPE
    SYNTAX       TAdaptationRule
    MAX-ACCESS   read-create
    STATUS       current
    DESCRIPTION
        "The adaptation rule to be used while computing the operational PIR
         value. The adaptation rule specifies the rules to compute the
         operational values while maintaining minimum offset."
    DEFVAL { closest }
    ::= { tNetworkIngressMeterEntry 6 }


tNetworkIngressMeterAdminPIR OBJECT-TYPE
    SYNTAX       TIngressPIRRate
    MAX-ACCESS   read-create
    STATUS       current
    DESCRIPTION
        "The administrative PIR specified by the user."
    DEFVAL { -1 }
    ::= { tNetworkIngressMeterEntry 7 }

tNetworkIngressMeterAdminCIR OBJECT-TYPE
    SYNTAX       TIngressCIRRate
    MAX-ACCESS   read-create
    STATUS       current
    DESCRIPTION
        "The administrative CIR specified by the user."
    DEFVAL { 0 }
    ::= { tNetworkIngressMeterEntry 8 }

tNetworkIngressMeterOperPIR OBJECT-TYPE
    SYNTAX       TPIRRate
    MAX-ACCESS   read-only
    STATUS       current
    DESCRIPTION
        "The operational value derived by computing the PIR value from
         the administrative PIR value and their corresponding
         adaptation rules."
    ::= { tNetworkIngressMeterEntry 9 }

tNetworkIngressMeterOperCIR OBJECT-TYPE
    SYNTAX       TCIRRate
    MAX-ACCESS   read-only
    STATUS       current
    DESCRIPTION
        "The operational value derived by computing the CIR value from
         the administrative CIR value and their corresponding
         adaptation rules."
    ::= { tNetworkIngressMeterEntry 10 }

tNetworkIngressMeterLastChanged OBJECT-TYPE
    SYNTAX       TimeStamp
    MAX-ACCESS   read-only
    STATUS       current
    DESCRIPTION
        "Timestamp of last change to this row."
    ::= { tNetworkIngressMeterEntry 11 }

tNetworkIngressMeterMode OBJECT-TYPE
    SYNTAX       TMeterMode
    MAX-ACCESS   read-create
    STATUS       current
    DESCRIPTION
        "Network Ingress Meter Mode"
    DEFVAL { priority }
    ::= { tNetworkIngressMeterEntry 12 }

tNetworkIngressMeterMCast OBJECT-TYPE
    SYNTAX       TruthValue
    MAX-ACCESS   read-create
    STATUS       current
    DESCRIPTION
        "This object specifies if this is a multicast meter or not."
    DEFVAL { false }
    ::= { tNetworkIngressMeterEntry 13 }

tNetworkIngressMeterRateMode OBJECT-TYPE
    SYNTAX       TMeterRateMode
    MAX-ACCESS   read-create
    STATUS       current
    DESCRIPTION
        " Network Ingress Meter Rate mode.The mode can be configured 
        as Two Rate Three Color Marker (trTCM) or Single Rate Three 
        Color Marker (srTCM).  The mode command can be executed at 
        anytime."
    DEFVAL { trtcm1 }
    ::= { tNetworkIngressMeterEntry 14 }        

tNetworkIngressMeterAdminCBS OBJECT-TYPE
    SYNTAX       TIngressBurstSize 
    MAX-ACCESS   read-create
    STATUS       current
    DESCRIPTION
        "The administrative CBS specified by the user. The amount of 
        committed burst size (in kilo bits) for the meter."
    DEFVAL { -1 }
    ::= { tNetworkIngressMeterEntry 15 }

tNetworkIngressMeterAdminMBS OBJECT-TYPE
    SYNTAX       TIngressBurstSize
    MAX-ACCESS   read-create
    STATUS       current
    DESCRIPTION
        "The administrative MBS specified by the user. The maximum amount 
        of burst size (in kilo bits) allowed for the meter."
    DEFVAL { -1 }
    ::= { tNetworkIngressMeterEntry 16 }

tNetworkIngressMeterOperCBS OBJECT-TYPE
    SYNTAX       TIngressBurstSize 
    MAX-ACCESS   read-only
    STATUS       current
    DESCRIPTION
        "The operational value derived by computing the CBS value from
         the administrative CBS value"
    ::= { tNetworkIngressMeterEntry 17 }

tNetworkIngressMeterOperMBS OBJECT-TYPE
    SYNTAX       TIngressBurstSize
    MAX-ACCESS   read-only
    STATUS       current
    DESCRIPTION
        "The operational value derived by computing the MBS value from
         the administrative MBS value"
    ::= { tNetworkIngressMeterEntry 26 }


tNetworkIngressMeterAdminCBSType OBJECT-TYPE
    SYNTAX       INTEGER {
                    kbits   (1),
                    bytes   (2),
                    kbytes  (3)
                 }
    MAX-ACCESS   read-create
    STATUS       current
    DESCRIPTION
        "The type for administrative CBS specified by the user. The amount of 
        committed burst size (in kilo bits/bytes/kbytes) for the meter."
    DEFVAL { kbits }
    ::= { tNetworkIngressMeterEntry 27 }

tNetworkIngressMeterAdminCBSBytes OBJECT-TYPE
    SYNTAX       TIngressBurstSizeBytes
    MAX-ACCESS   read-create
    STATUS       current
    DESCRIPTION
        "The administrative CBS specified by the user. The amount of 
        committed burst size (in bytes) for the meter."
    DEFVAL { -1 }
    ::= { tNetworkIngressMeterEntry 28 }

tNetworkIngressMeterAdminCBSKBytes OBJECT-TYPE
    SYNTAX       TIngressBurstSizeKBytes
    MAX-ACCESS   read-create
    STATUS       current
    DESCRIPTION
        "The administrative CBS specified by the user. The amount of 
        committed burst size (in kilo bytes) for the meter."
    DEFVAL { -1 }
    ::= { tNetworkIngressMeterEntry 29 }

tNetworkIngressMeterAdminMBSType OBJECT-TYPE
    SYNTAX       INTEGER {
                    kbits   (1),
                    bytes   (2),
                    kbytes  (3)
                 }
    MAX-ACCESS   read-create
    STATUS       current
    DESCRIPTION
        "The type for administrative MBS specified by the user. The amount of 
        committed burst size (in kilo bits/bytes/kbytes) for the meter."
    DEFVAL { kbits }
    ::= { tNetworkIngressMeterEntry 30 }

tNetworkIngressMeterAdminMBSBytes OBJECT-TYPE
    SYNTAX       TIngressBurstSizeBytes
    MAX-ACCESS   read-create
    STATUS       current
    DESCRIPTION
        "The administrative MBS specified by the user. The amount of 
        committed burst size (in bytes) for the meter."
    DEFVAL { -1 }
    ::= { tNetworkIngressMeterEntry 31 }

tNetworkIngressMeterAdminMBSKBytes OBJECT-TYPE
    SYNTAX       TIngressBurstSizeKBytes
    MAX-ACCESS   read-create
    STATUS       current
    DESCRIPTION
        "The administrative MBS specified by the user. The amount of 
        committed burst size (in kilo bytes) for the meter."
    DEFVAL { -1 }
    ::= { tNetworkIngressMeterEntry 32 }

tNetworkIngressMeterOperCBSBytes OBJECT-TYPE
    SYNTAX       TIngressBurstSizeBytes 
    MAX-ACCESS   read-only
    STATUS       current
    DESCRIPTION
        "The operational value derived by computing the CBS value from
         the administrative CBS value"
    ::= { tNetworkIngressMeterEntry 33 }

tNetworkIngressMeterOperCBSKBytes OBJECT-TYPE
    SYNTAX       TIngressBurstSizeKBytes
    MAX-ACCESS   read-only
    STATUS       current
    DESCRIPTION
        "The operational value derived by computing the CBS value from
         the administrative CBS value"
    ::= { tNetworkIngressMeterEntry 34 }

tNetworkIngressMeterOperMBSBytes OBJECT-TYPE
    SYNTAX       TIngressBurstSizeBytes 
    MAX-ACCESS   read-only
    STATUS       current
    DESCRIPTION
        "The operational value derived by computing the MBS value from
         the administrative MBS value"
    ::= { tNetworkIngressMeterEntry 35 }

tNetworkIngressMeterOperMBSKBytes OBJECT-TYPE
    SYNTAX       TIngressBurstSizeKBytes
    MAX-ACCESS   read-only
    STATUS       current
    DESCRIPTION
        "The operational value derived by computing the MBS value from
         the administrative MBS value"
    ::= { tNetworkIngressMeterEntry 36 }

--
-- network policy ingress queue table
--

tNetworkIngressQueueTable OBJECT-TYPE
    SYNTAX       SEQUENCE OF TNetworkIngressQueueEntry
    MAX-ACCESS   not-accessible
    STATUS       current
    DESCRIPTION  ""
    ::= { tSASNetworkIngressObjects 3 }

tNetworkIngressQueueEntry OBJECT-TYPE
    SYNTAX       TNetworkIngressQueueEntry
    MAX-ACCESS   not-accessible
    STATUS       current
    DESCRIPTION  ""
    INDEX { tNetworkPolicyIndex, tNetworkIngressQueue }
    ::= { tNetworkIngressQueueTable 1 }

TNetworkIngressQueueEntry ::= SEQUENCE
    {
        tNetworkIngressQueue                 TQueueId,
        tNetworkIngressQueueRowStatus        RowStatus,
        tNetworkIngressQueuePoolName         TNamedItemOrEmpty,
        tNetworkIngressQueueParent           TNamedItemOrEmpty,
        tNetworkIngressQueueLevel            TLevel,
        tNetworkIngressQueueWeight           TWeight,
        tNetworkIngressQueueCIRLevel         TLevelOrDefault,
        tNetworkIngressQueueCIRWeight        TWeight,
        tNetworkIngressQueueMCast            TruthValue,
        tNetworkIngressQueueExpedite         INTEGER,
        tNetworkIngressQueueCIR              TRatePercent,
        tNetworkIngressQueuePIR              TPIRRatePercent,
        tNetworkIngressQueueCBS              Integer32,
        tNetworkIngressQueueMBS              Integer32,
        tNetworkIngressQueueHiPrioOnly       TBurstPercentOrDefault,
        tNetworkIngressQueueLastChanged      TimeStamp,
        tNetworkIngressQueueUsePortParent    TruthValue,
        tNetworkIngressQueuePortLvl          TLevel,
        tNetworkIngressQueuePortWght         TWeight,
        tNetworkIngressQueuePortCIRLvl       TLevelOrDefault,
        tNetworkIngressQueuePortCIRWght      TWeight,
        tNetworkIngressQueuePortAvgOverhead  Unsigned32,
        tNetworkIngressQueueCIRAdaptation    TAdaptationRule,
        tNetworkIngressQueuePIRAdaptation    TAdaptationRule,
        tNetworkIngressQueuePolicyName       TNamedItemOrEmpty
    }

tNetworkIngressQueue OBJECT-TYPE
    SYNTAX       TQueueId (1..8)
    MAX-ACCESS   not-accessible
    STATUS       current
    DESCRIPTION
        "The queue ID is used as the secondary index to the table entry."
    ::= { tNetworkIngressQueueEntry 1 }

tNetworkIngressQueueRowStatus OBJECT-TYPE
    SYNTAX       RowStatus
    MAX-ACCESS   read-create
    STATUS       current
    DESCRIPTION
        "Row Status of the entry. This allows creation/deletion of rows in this
         table."
    ::= { tNetworkIngressQueueEntry 2 }

tNetworkIngressQueuePoolName OBJECT-TYPE
    SYNTAX       TNamedItemOrEmpty
    MAX-ACCESS   read-create
    STATUS       current
    DESCRIPTION
        "The tNetworkIngressQueuePoolName specifies the pool that is associated
         with this network queue. If tNetworkIngressQueuePoolName is empty, no pool
         has been associated with the queue."
    DEFVAL { ''H }
    ::= { tNetworkIngressQueueEntry 3 }

tNetworkIngressQueueParent OBJECT-TYPE
    SYNTAX       TNamedItemOrEmpty
    MAX-ACCESS   read-create
    STATUS       current
    DESCRIPTION
        "The scheduler to which this queue would be feeding to."
    DEFVAL { ''H }
    ::= { tNetworkIngressQueueEntry 4 }

tNetworkIngressQueueLevel OBJECT-TYPE
    SYNTAX       TLevel
    MAX-ACCESS   read-create
    STATUS       current
    DESCRIPTION
        "This specifies the level of priority while feeding to the parent."
    DEFVAL { 1 }
    ::= { tNetworkIngressQueueEntry 5 }

tNetworkIngressQueueWeight OBJECT-TYPE
    SYNTAX       TWeight
    MAX-ACCESS   read-create
    STATUS       current
    DESCRIPTION
        "The weight that needs to be used by the scheduler to which this queue
         would be feeding to."
    DEFVAL { 1 }
    ::= { tNetworkIngressQueueEntry 6 }

tNetworkIngressQueueCIRLevel OBJECT-TYPE
    SYNTAX       TLevelOrDefault
    MAX-ACCESS   read-create
    STATUS       current
    DESCRIPTION
        "This specifies the level of priority while feeding to the parent.
         The level '0' means treat all offered load for this queue as for
         the above CIR traffic."
    DEFVAL { 0 }
    ::= { tNetworkIngressQueueEntry 7 }

tNetworkIngressQueueCIRWeight OBJECT-TYPE
    SYNTAX       TWeight
    MAX-ACCESS   read-create
    STATUS       current
    DESCRIPTION
        "The weight that needs to be used until the committed rate by the
         scheduler to which this queue would be feeding to."
    DEFVAL { 1 }
    ::= { tNetworkIngressQueueEntry 8 }

tNetworkIngressQueueMCast OBJECT-TYPE
    SYNTAX       TruthValue
    MAX-ACCESS   read-create
    STATUS       current
    DESCRIPTION
        "This object specifies if this is a multicast queue or not."
    DEFVAL { false }
    ::= { tNetworkIngressQueueEntry 9 }

tNetworkIngressQueueExpedite OBJECT-TYPE
    SYNTAX       INTEGER {
                     expedited     (1),
                     auto-expedited(2),
                     non-expedited (3)
                 }
    MAX-ACCESS   read-create
    STATUS       current
    DESCRIPTION
        "tNetworkIngressQueueExpedite specifies the priority that this queue should
         be assigned by the hardware level schedulers.

         The value 'auto-expedited' implies that this attribute should be
         dynamically updated by looking at the forwarding classes mapping
         into this queue. In such a case the queue is treated as
         'non-expedited' if there is even a single non-expedited forwarding
         class using this queue.

         This attribute is associated with the queue at the time of creation
         and cannot be modified thereafter."
    DEFVAL { auto-expedited }
    ::= { tNetworkIngressQueueEntry 10 }

tNetworkIngressQueueCIR OBJECT-TYPE
    SYNTAX       TRatePercent
    MAX-ACCESS   read-create
    STATUS       current
    DESCRIPTION
        "The percentage of max rate allowed."
    DEFVAL { 0 }
    ::= { tNetworkIngressQueueEntry 11 }

tNetworkIngressQueuePIR OBJECT-TYPE
    SYNTAX       TPIRRatePercent
    MAX-ACCESS   read-create
    STATUS       current
    DESCRIPTION
        "The percentage of max rate allowed."
    DEFVAL { 100 }
    ::= { tNetworkIngressQueueEntry 12 }

tNetworkIngressQueueCBS OBJECT-TYPE
    SYNTAX       Integer32 (0..10240)
    MAX-ACCESS   read-create
    STATUS       current
    DESCRIPTION
        "The absolute value (Kilo bytes) of reserved buffer space for the queue" 
    DEFVAL { 50 }
    ::= { tNetworkIngressQueueEntry 13 }

tNetworkIngressQueueMBS OBJECT-TYPE
    SYNTAX       Integer32 (0..12800)
    MAX-ACCESS   read-create
    STATUS       current
    DESCRIPTION
        "The absolute value (Kilo bytes) of reserved buffer space for the queue" 
    DEFVAL { 200 }
    ::= { tNetworkIngressQueueEntry 14 }

tNetworkIngressQueueHiPrioOnly OBJECT-TYPE
    SYNTAX       TBurstPercentOrDefault
    MAX-ACCESS   read-create
    STATUS       current
    DESCRIPTION
        "The percentage of buffer space for the queue, used
         exclusively by high priority packets."
    DEFVAL { -1 }
    ::= { tNetworkIngressQueueEntry 15 }

tNetworkIngressQueueLastChanged OBJECT-TYPE
    SYNTAX       TimeStamp
    MAX-ACCESS   read-only
    STATUS       current
    DESCRIPTION
        "The value of the object tNetworkIngressQueueLastChanged indicates the 
         timestamp of last change to this row in tNetworkIngressQueueTable."
    ::= { tNetworkIngressQueueEntry 16 }

tNetworkIngressQueueUsePortParent  OBJECT-TYPE
    SYNTAX      TruthValue
    MAX-ACCESS  read-create
    STATUS      current
    DESCRIPTION
        "The value of the object tNetworkIngressQueueUsePortParent specifies
         whether this queue is parented by a port-level scheduler. When
         the value is 'true', this network queue is parented by a 
         port-level scheduler."
    DEFVAL      { false }
    ::= { tNetworkIngressQueueEntry 17 }

tNetworkIngressQueuePortLvl        OBJECT-TYPE
    SYNTAX       TLevel
    MAX-ACCESS  read-create
    STATUS      current
    DESCRIPTION
        "The value of the object tNetworkIngressQueuePortLvl specifies the
         port priority this queue will use to receive bandwidth from
         the port-level scheduler for its above-cir offered load."
    DEFVAL      { 1 }
    ::= { tNetworkIngressQueueEntry 18 }

tNetworkIngressQueuePortWght       OBJECT-TYPE
    SYNTAX      TWeight
    MAX-ACCESS  read-create
    STATUS      current
    DESCRIPTION
        "The value of the object tNetworkIngressQueuePortWght specifies the
         weight this queue will use to receive bandwidth from the
         port-level scheduler for its above-cir offered load."
    DEFVAL      { 1 }
    ::= { tNetworkIngressQueueEntry 19 }

tNetworkIngressQueuePortCIRLvl        OBJECT-TYPE
    SYNTAX      TLevelOrDefault
    MAX-ACCESS  read-create
    STATUS      current
    DESCRIPTION
        "The value of the object tNetworkIngressQueuePortCIRLvl specifies the
         port priority this queue will use to receive bandwidth from
         the port-level scheduler for its within-cir offered load."
    DEFVAL      { 0 }
    ::= { tNetworkIngressQueueEntry 20 }

tNetworkIngressQueuePortCIRWght       OBJECT-TYPE
    SYNTAX      TWeight
    MAX-ACCESS  read-create
    STATUS      current
    DESCRIPTION
        "The value of the object tNetworkIngressQueuePortCIRWght specifies the
         weight this queue will use to receive bandwidth from the
         port-level scheduler for its within-cir offered load."
    DEFVAL      { 0 }
    ::= { tNetworkIngressQueueEntry 21 }

tNetworkIngressQueuePortAvgOverhead    OBJECT-TYPE
    SYNTAX      Unsigned32 (0..10000)
    UNITS       "Hundredths of a percent"
    MAX-ACCESS  read-create
    STATUS      current
    DESCRIPTION
        "The value of tNetworkIngressQueuePortAvgOverhead specifies the 
         encapsulation overhead, in hundredths of a percent,  used to 
         translate packet-based rate to frame-based rate and vice versa."
    DEFVAL      { 0 }
    ::= { tNetworkIngressQueueEntry 22 }

tNetworkIngressQueueCIRAdaptation       OBJECT-TYPE
    SYNTAX      TAdaptationRule
    MAX-ACCESS  read-create
    STATUS      current
    DESCRIPTION
        "The value of tNetworkIngressQueueCIRAdaptation specifies the adaptation rule
         to be used while computing the operational CIR value. The adaptation
         rule specifies the rules to compute the operational value while
         maintaining the minimum offset."
    DEFVAL      { closest }
    ::= { tNetworkIngressQueueEntry 23 }

tNetworkIngressQueuePIRAdaptation       OBJECT-TYPE
    SYNTAX      TAdaptationRule
    MAX-ACCESS  read-create
    STATUS      current
    DESCRIPTION
        "The value of tNetworkIngressQueuePIRAdaptation specifies the adaptation rule
         to be used while computing the operational PIR value. The adaptation
         rule specifies the rules to compute the operational value while
         maintaining the minimum offset."
    DEFVAL      { closest }
    ::= { tNetworkIngressQueueEntry 24 }

tNetworkIngressQueuePolicyName OBJECT-TYPE
    SYNTAX       TNamedItemOrEmpty
    MAX-ACCESS   read-create
    STATUS       current
    DESCRIPTION
        "The tNetworkIngressQueuePolicyName specifies the pool that is associated
         with this network queue. If tNetworkIngressQueuePolicyName is empty, no pool
         has been associated with the queue."
    DEFVAL { ''H }
    ::= { tNetworkIngressQueueEntry 25 }



tSasSlopePolicyExtnTable OBJECT-TYPE
    SYNTAX       SEQUENCE OF TSasSlopePolicyExtnEntry
    MAX-ACCESS   not-accessible
    STATUS       current
    DESCRIPTION
        "Slope Policy Table. Additions for sas platform"
    ::= { tSASSlopeObjects 1 }

tSasSlopePolicyExtnEntry OBJECT-TYPE
    SYNTAX       TSasSlopePolicyExtnEntry
    MAX-ACCESS   not-accessible
    STATUS       current
    DESCRIPTION
        "Slope Policy Entry additions for sas platform."
    AUGMENTS    { tSlopePolicyEntry }
    ::= { tSasSlopePolicyExtnTable 1 }

TSasSlopePolicyExtnEntry ::= SEQUENCE
    {
        tSlopeHiQueue1DropRate TSlopeDropRate,
        tSlopeHiQueue2DropRate TSlopeDropRate,
        tSlopeHiQueue3DropRate TSlopeDropRate,
        tSlopeHiQueue4DropRate TSlopeDropRate,
        tSlopeHiQueue5DropRate TSlopeDropRate,
        tSlopeHiQueue6DropRate TSlopeDropRate,
        tSlopeHiQueue7DropRate TSlopeDropRate,
        tSlopeHiQueue8DropRate TSlopeDropRate,
        tSlopeLoQueue1DropRate TSlopeDropRate,
        tSlopeLoQueue2DropRate TSlopeDropRate,
        tSlopeLoQueue3DropRate TSlopeDropRate,
        tSlopeLoQueue4DropRate TSlopeDropRate,
        tSlopeLoQueue5DropRate TSlopeDropRate,
        tSlopeLoQueue6DropRate TSlopeDropRate,
        tSlopeLoQueue7DropRate TSlopeDropRate,
        tSlopeLoQueue8DropRate TSlopeDropRate,
        tSlopeHiStartThreshold TSlopeThreshold,
        tSlopeLoStartThreshold TSlopeThreshold,
        tSlopeHiRingAdminStatus     INTEGER,
        tSlopeHiRingStartAverage    Unsigned32,
        tSlopeHiRingMaxAverage      Unsigned32,
        tSlopeHiRingMaxProbability  Unsigned32,
        tSlopeLoRingAdminStatus     INTEGER,
        tSlopeLoRingStartAverage    Unsigned32,
        tSlopeLoRingMaxAverage      Unsigned32,
        tSlopeLoRingMaxProbability  Unsigned32     
    }

tSlopeHiQueue1DropRate OBJECT-TYPE
    SYNTAX       TSlopeDropRate
    MAX-ACCESS   read-create
    STATUS       current
    DESCRIPTION
        "High Queue Drop Rate"
    DEFVAL { 1 }
    ::= { tSasSlopePolicyExtnEntry 1 }

tSlopeHiQueue2DropRate OBJECT-TYPE
    SYNTAX       TSlopeDropRate
    MAX-ACCESS   read-create
    STATUS       current
    DESCRIPTION
        "High Queue Drop Rate"
    DEFVAL { 1 }
    ::= { tSasSlopePolicyExtnEntry 2 }

tSlopeHiQueue3DropRate OBJECT-TYPE
    SYNTAX       TSlopeDropRate
    MAX-ACCESS   read-create
    STATUS       current
    DESCRIPTION
        "High Queue Drop Rate"
    DEFVAL { 1 }
    ::= { tSasSlopePolicyExtnEntry 3 }

tSlopeHiQueue4DropRate OBJECT-TYPE
    SYNTAX       TSlopeDropRate
    MAX-ACCESS   read-create
    STATUS       current
    DESCRIPTION
        "High Queue Drop Rate"
    DEFVAL { 1 }
    ::= { tSasSlopePolicyExtnEntry 4 }

tSlopeHiQueue5DropRate OBJECT-TYPE
    SYNTAX       TSlopeDropRate
    MAX-ACCESS   read-create
    STATUS       current
    DESCRIPTION
        "High Queue Drop Rate"
    DEFVAL { 1 }
    ::= { tSasSlopePolicyExtnEntry 5 }

tSlopeHiQueue6DropRate OBJECT-TYPE
    SYNTAX       TSlopeDropRate
    MAX-ACCESS   read-create
    STATUS       current
    DESCRIPTION
        "High Queue Drop Rate"
    DEFVAL { 1 }
    ::= { tSasSlopePolicyExtnEntry 6 }

tSlopeHiQueue7DropRate OBJECT-TYPE
    SYNTAX       TSlopeDropRate
    MAX-ACCESS   read-create
    STATUS       current
    DESCRIPTION
        "High Queue Drop Rate"
    DEFVAL { 1 }
    ::= { tSasSlopePolicyExtnEntry 7 }

tSlopeHiQueue8DropRate OBJECT-TYPE
    SYNTAX       TSlopeDropRate
    MAX-ACCESS   read-create
    STATUS       current
    DESCRIPTION
        "High Queue Drop Rate"
    DEFVAL { 1 }
    ::= { tSasSlopePolicyExtnEntry 8 }

tSlopeLoQueue1DropRate OBJECT-TYPE
    SYNTAX       TSlopeDropRate
    MAX-ACCESS   read-create
    STATUS       current
    DESCRIPTION
        "Low Queue Drop Rate"
    DEFVAL { 0 }
    ::= { tSasSlopePolicyExtnEntry 9 }

tSlopeLoQueue2DropRate OBJECT-TYPE
    SYNTAX       TSlopeDropRate
    MAX-ACCESS   read-create
    STATUS       current
    DESCRIPTION
        "Low Queue Drop Rate"
    DEFVAL { 0 }
    ::= { tSasSlopePolicyExtnEntry 10 }

tSlopeLoQueue3DropRate OBJECT-TYPE
    SYNTAX       TSlopeDropRate
    MAX-ACCESS   read-create
    STATUS       current
    DESCRIPTION
        "Low Queue Drop Rate"
    DEFVAL { 0 }
    ::= { tSasSlopePolicyExtnEntry 11 }

tSlopeLoQueue4DropRate OBJECT-TYPE
    SYNTAX       TSlopeDropRate
    MAX-ACCESS   read-create
    STATUS       current
    DESCRIPTION
        "Low Queue Drop Rate"
    DEFVAL { 0 }
    ::= { tSasSlopePolicyExtnEntry 12 }

tSlopeLoQueue5DropRate OBJECT-TYPE
    SYNTAX       TSlopeDropRate
    MAX-ACCESS   read-create
    STATUS       current
    DESCRIPTION
        "Low Queue Drop Rate"
    DEFVAL { 0 }
    ::= { tSasSlopePolicyExtnEntry 13 }

tSlopeLoQueue6DropRate OBJECT-TYPE
    SYNTAX       TSlopeDropRate
    MAX-ACCESS   read-create
    STATUS       current
    DESCRIPTION
        "Low Queue Drop Rate"
    DEFVAL { 0 }
    ::= { tSasSlopePolicyExtnEntry 14 }

tSlopeLoQueue7DropRate OBJECT-TYPE
    SYNTAX       TSlopeDropRate
    MAX-ACCESS   read-create
    STATUS       current
    DESCRIPTION
        "Low Queue Drop Rate"
    DEFVAL { 0 }
    ::= { tSasSlopePolicyExtnEntry 15 }

tSlopeLoQueue8DropRate OBJECT-TYPE
    SYNTAX       TSlopeDropRate
    MAX-ACCESS   read-create
    STATUS       current
    DESCRIPTION
        "Low Queue Drop Rate"
    DEFVAL { 0 }
    ::= { tSasSlopePolicyExtnEntry 16 }

tSlopeHiStartThreshold OBJECT-TYPE
    SYNTAX       TSlopeThreshold
    MAX-ACCESS   read-create
    STATUS       current
    DESCRIPTION
        "High slope Start Threshold.This object implies that once the 
        shared buffer utilization reaches the start-threshold 
        level then high-priority packets egressing out from 
        a particular queue would be dropped at configured drop 
        rate."
    DEFVAL { 75 }
    ::= { tSasSlopePolicyExtnEntry 17 }

tSlopeLoStartThreshold OBJECT-TYPE
    SYNTAX       TSlopeThreshold
    MAX-ACCESS   read-create
    STATUS       current
    DESCRIPTION
        "Low slope Start Threshold.This implies that once the 
        shared buffer utilization reaches the start-threshold 
        level then low-priority packets egressing out from a 
        particular queue would be dropped at configured drop 
        rate."
    DEFVAL { 50 }
    ::= { tSasSlopePolicyExtnEntry 18 }

tSlopeHiRingAdminStatus OBJECT-TYPE
    SYNTAX       INTEGER {
                     up  (1),
                     down(2)
                 }
    MAX-ACCESS   read-create
    STATUS       current
    DESCRIPTION
        "tSlopeHiRingAdminStatus specifies the admin state for the high priority RED
         slope ring. If the tSlopeHiRingAdminStatus is set to 'down', the RED slope is
         inactive."
    DEFVAL { down }
    ::= {  tSasSlopePolicyExtnEntry 19 }

tSlopeHiRingStartAverage OBJECT-TYPE
    SYNTAX       Unsigned32 (0..100)
    MAX-ACCESS   read-create
    STATUS       current
    DESCRIPTION
        "The percentage of the buffer utilized after which the drop probability
         starts to rise above 0."
    DEFVAL { 70 }
    ::= { tSasSlopePolicyExtnEntry 20 }

tSlopeHiRingMaxAverage OBJECT-TYPE
    SYNTAX       Unsigned32 (0..100)
    MAX-ACCESS   read-create
    STATUS       current
    DESCRIPTION
        "The percentage of the buffer utilized after which the drop probability
         is 100 percent. This implies that all packets beyond this point will be
         dropped."
    DEFVAL { 90 }
    ::= {  tSasSlopePolicyExtnEntry 21 }

tSlopeHiRingMaxProbability OBJECT-TYPE
    SYNTAX       Unsigned32 (0..100)
    MAX-ACCESS   read-create
    STATUS       current
    DESCRIPTION
        "The drop probability increases steadily from 0 at the
         tSlopeHiStartAverage upto the tSlopeHiMaxProbability at the
         tSlopeHiMaxAverage."
    DEFVAL { 80 }
    ::= {  tSasSlopePolicyExtnEntry 22}

tSlopeLoRingAdminStatus OBJECT-TYPE
    SYNTAX       INTEGER {
                     up(1),
                     down(2)
                 }
    MAX-ACCESS   read-create
    STATUS       current
    DESCRIPTION
        "tSlopeLoAdminStatus specifies the admin state for the high priority RED
        slope. If the tSlopeLoAdminStatus is set to 'down', the RED slope is
        inactive."
    DEFVAL { down }
    ::= { tSasSlopePolicyExtnEntry 23 }

tSlopeLoRingStartAverage OBJECT-TYPE
    SYNTAX       Unsigned32 (0..100)
    MAX-ACCESS   read-create
    STATUS       current
    DESCRIPTION
        "The percentage of the buffer utilized after which the drop probability
        starts to rise above 0."
    DEFVAL { 50 }
    ::= { tSasSlopePolicyExtnEntry  24 }

tSlopeLoRingMaxAverage OBJECT-TYPE
    SYNTAX       Unsigned32 (0..100)
    MAX-ACCESS   read-create
    STATUS       current
    DESCRIPTION
        "The percentage of the buffer utilized after which the drop probability
        is 100 percent. This implies that all packets beyond this point will be
        dropped."
    DEFVAL { 75 }
    ::= { tSasSlopePolicyExtnEntry 25 }

tSlopeLoRingMaxProbability OBJECT-TYPE
    SYNTAX       Unsigned32 (0..100)
    MAX-ACCESS   read-create
    STATUS       current
    DESCRIPTION
        "The drop probability increases steadily from 0 at the
        tSlopeLoStartAverage upto the tSlopeLoMaxProbability at the
        tSlopeLoMaxAverage."
    DEFVAL { 80 }
    ::= { tSasSlopePolicyExtnEntry  26}    

tSlopePolicyQueueTable OBJECT-TYPE
    SYNTAX       SEQUENCE OF TQueueSlopePolicyEntry
    MAX-ACCESS   not-accessible
    STATUS       current
    DESCRIPTION
        "Slope Policy Per Queue Per Port additions for SAS-M platform.
        In SAS-M there are three slopes associated with a queue.
        One slope for Tcp Green packets, one for Tcp Yellow packets
        and one for Non Tcp Packets(both green and yellow packets).
        Each slope in turn can have four parameters defining its 
        behavior"
    ::= { tSASSlopeObjects 2 }

tSlopePolicyQueueEntry OBJECT-TYPE
    SYNTAX       TQueueSlopePolicyEntry
    MAX-ACCESS   not-accessible
    STATUS       current
    DESCRIPTION
        ""
    INDEX    { tSlopePolicy,  tSlopePolicyQueueId }
    ::= { tSlopePolicyQueueTable 1 }

TQueueSlopePolicyEntry ::= SEQUENCE
    {
        tSlopePolicyQueueId                    TQueueId,
        tSlopePolicyQueueRowStatus             RowStatus,
        tSlopePolicyQueueLastChanged           TimeStamp,
        tSlopePolicyQueueHiAdminStatus         INTEGER,
        tSlopePolicyQueueHiStartAverage        Unsigned32,
        tSlopePolicyQueueHiMaxAverage          Unsigned32,
        tSlopePolicyQueueHiMaxProbability      TMaxProbability,        
        tSlopePolicyQueueLoAdminStatus         INTEGER,
        tSlopePolicyQueueLoStartAverage        Unsigned32,
        tSlopePolicyQueueLoMaxAverage          Unsigned32,
        tSlopePolicyQueueLoMaxProbability      TMaxProbability,
        tSlopePolicyQueueNonTcpAdminStatus     INTEGER,
        tSlopePolicyQueueNonTcpStartAverage    Unsigned32,
        tSlopePolicyQueueNonTcpMaxAverage      Unsigned32,
        tSlopePolicyQueueNonTcpMaxProbability  TMaxProbability,        
        tSlopePolicyQueueTimeAvgFactor         Unsigned32
    }        

tSlopePolicyQueueId OBJECT-TYPE
    SYNTAX       TQueueId (1..8)
    MAX-ACCESS   not-accessible
    STATUS       current
    DESCRIPTION
        "Queue for which slope policy is being defined"
    ::= { tSlopePolicyQueueEntry 1 }


tSlopePolicyQueueRowStatus OBJECT-TYPE
    SYNTAX       RowStatus
    MAX-ACCESS   read-create
    STATUS       current
    DESCRIPTION
        "Row Status of the entry. This allows creation/deletion of rows in this
         table."
    ::= { tSlopePolicyQueueEntry 2 }

tSlopePolicyQueueLastChanged OBJECT-TYPE
    SYNTAX       TimeStamp
    MAX-ACCESS   read-only
    STATUS       current
    DESCRIPTION
        "Timestamp of last change to this row."
    ::= { tSlopePolicyQueueEntry 3 }
    
tSlopePolicyQueueHiAdminStatus OBJECT-TYPE
    SYNTAX       INTEGER {
                     up  (1),
                     down(2)
                 }
    MAX-ACCESS   read-create
    STATUS       current
    DESCRIPTION
        "tSlopePolicyQueueHiAdminStatus specifies the admin state for the queue's
 high profile (Tcp Green Packets )slope. If the tSlopePolicyQueueHiAdminStatus
 is set to 'down',the slope is inactive."
    DEFVAL { down }    
    ::= { tSlopePolicyQueueEntry 4 }

tSlopePolicyQueueHiStartAverage OBJECT-TYPE
    SYNTAX       Unsigned32 (0..100)
    MAX-ACCESS   read-create
    STATUS       current
    DESCRIPTION
        "The percentage of the buffer utilized after which the drop probability
        starts to rise above 0."
    DEFVAL { 70 }
    ::= { tSlopePolicyQueueEntry 5 }

tSlopePolicyQueueHiMaxAverage OBJECT-TYPE
    SYNTAX       Unsigned32 (0..100)
    MAX-ACCESS   read-create
    STATUS       current
    DESCRIPTION
        "The percentage of the buffer utilized after which the drop probability
 is 100 percent. This implies that all packets beyond this point will be
        dropped."
    DEFVAL { 90 }
    ::= { tSlopePolicyQueueEntry 6 }

tSlopePolicyQueueHiMaxProbability OBJECT-TYPE
    SYNTAX       TMaxProbability
    MAX-ACCESS   read-create
    STATUS       current
    DESCRIPTION
        "High Profile Max Probability.Defines the slope between the
        Start Average and Max Average"
    DEFVAL { 75 }
    ::= { tSlopePolicyQueueEntry 7 }    

tSlopePolicyQueueLoAdminStatus OBJECT-TYPE
    SYNTAX       INTEGER {
                     up  (1),
                     down(2)
                 }
    MAX-ACCESS   read-create
    STATUS       current
    DESCRIPTION
        "tSlopePolicyQueueLoAdminStatus specifies the admin state for the queue's
        low profile (Tcp Yellow Packets )slope. If the tSlopePolicyQueueLoAdminStatus
 is set to 'down',the slope is inactive."
    DEFVAL { down }
    ::= { tSlopePolicyQueueEntry 8 }

tSlopePolicyQueueLoStartAverage OBJECT-TYPE
    SYNTAX       Unsigned32 (0..100)
    MAX-ACCESS   read-create
    STATUS       current
    DESCRIPTION
        "The percentage of the buffer utilized after which the drop probability
        starts to rise above 0."
    DEFVAL { 50 }
    ::= { tSlopePolicyQueueEntry 9 }

tSlopePolicyQueueLoMaxAverage OBJECT-TYPE
    SYNTAX       Unsigned32 (0..100)
    MAX-ACCESS   read-create
    STATUS       current
    DESCRIPTION
        "The percentage of the buffer utilized after which the drop probability
 is 100 percent. This implies that all packets beyond this point will be
        dropped."
    DEFVAL { 75 }
    ::= { tSlopePolicyQueueEntry 10 }    

tSlopePolicyQueueLoMaxProbability OBJECT-TYPE
    SYNTAX       TMaxProbability
    MAX-ACCESS   read-create
    STATUS       current
    DESCRIPTION
        "Low Profile Max Probability.Defines the slope between the
        Start Average and Max Average"
    DEFVAL { 75 }
    ::= { tSlopePolicyQueueEntry 11 }    

tSlopePolicyQueueNonTcpAdminStatus OBJECT-TYPE
    SYNTAX       INTEGER {
                     up  (1),
                     down(2)
                 }
    MAX-ACCESS   read-create
    STATUS       current
    DESCRIPTION
        "tSlopePolicyQueueNonTcpAdminStatus specifies the admin state for the queue's
         non tcp profile (Non Tcp Packets )slope. If the tSlopePolicyQueueNonTcpAdminStatus
 is set to 'down',the slope is inactive."
    DEFVAL { down }
    ::= { tSlopePolicyQueueEntry 12 }

tSlopePolicyQueueNonTcpStartAverage OBJECT-TYPE
    SYNTAX       Unsigned32 (0..100)
    MAX-ACCESS   read-create
    STATUS       current
    DESCRIPTION
        "The percentage of the buffer utilized after which the drop probability
        starts to rise above 0."
    DEFVAL { 50 }
    ::= { tSlopePolicyQueueEntry 13 }

tSlopePolicyQueueNonTcpMaxAverage OBJECT-TYPE
    SYNTAX       Unsigned32 (0..100)
    MAX-ACCESS   read-create
    STATUS       current
    DESCRIPTION
        "The percentage of the buffer utilized after which the drop probability
         is 100 percent. This implies that all packets beyond this point will be
        dropped."
    DEFVAL { 75 }
    ::= { tSlopePolicyQueueEntry 14 }    

tSlopePolicyQueueNonTcpMaxProbability OBJECT-TYPE
    SYNTAX       TMaxProbability
    MAX-ACCESS   read-create
    STATUS       current
    DESCRIPTION
        "Non Tcp Profile Max Probability.Defines the slope between the
        Start Average and Max Average"
    DEFVAL { 75 }
    ::= { tSlopePolicyQueueEntry 15 }    

tSlopePolicyQueueTimeAvgFactor OBJECT-TYPE
    SYNTAX       Unsigned32 (0..15)
    MAX-ACCESS   read-create
    STATUS       current
    DESCRIPTION
        "The time average factor describes the weighting between the previous
 shared buffer average utilization result and the new shared buffer
        utilization in determining the new shared buffer average utilization."
    DEFVAL { 7 }
    ::= { tSlopePolicyQueueEntry 16 }    

tSasSapIngressFCTable OBJECT-TYPE
    SYNTAX       SEQUENCE OF TSasSapIngressFCEntry
    MAX-ACCESS   not-accessible
    STATUS       current
    DESCRIPTION
        "This table maintains the mapping of a particular
         forwarding class traffic into the specified meter."
    ::= { tSASSapIngressObjects 2 }

tSasSapIngressFCEntry OBJECT-TYPE
    SYNTAX       TSasSapIngressFCEntry
    MAX-ACCESS   not-accessible
    STATUS       current
    DESCRIPTION
        "Information about a particular sap-ingress policy's
         forwarding class mappings to meters."
    AUGMENTS    { tSapIngressFCEntry }
    ::= { tSasSapIngressFCTable 1 }

TSasSapIngressFCEntry ::= SEQUENCE
    {
        tSapIngressFCMeter          TSapIngressMeterId,
        tSapIngressFCMCastMeter     TSapIngressMeterId,
        tSapIngressFCBCastMeter     TSapIngressMeterId,
        tSapIngressFCUnknownMeter   TSapIngressMeterId,
        tSapIngressFCUseDei         TruthValue
    }    

tSapIngressFCMeter OBJECT-TYPE
    SYNTAX       TSapIngressMeterId
    MAX-ACCESS   read-create
    STATUS       current
    DESCRIPTION
        "The specific meter to be used for packets in this forwarding class.
         A value of zero implies that the default meter should be used."
    ::= { tSasSapIngressFCEntry 1 }


tSapIngressFCMCastMeter OBJECT-TYPE
    SYNTAX       TSapIngressMeterId
    MAX-ACCESS   read-create
    STATUS       current
    DESCRIPTION
        "The specific multicast meter to be used for packets in this forwarding
         class. The meter is used only for specific entities and will be
         ignored wherever it is irrelevant.

         A value of zero implies that the default meters should be used."
    ::= { tSasSapIngressFCEntry 2 }

tSapIngressFCBCastMeter OBJECT-TYPE
    SYNTAX       TSapIngressMeterId
    MAX-ACCESS   read-create
    STATUS       current
    DESCRIPTION
        "The specific broadcast meter to be used for packets in this forwarding
         class. The meter is used only for specific entities and will be
         ignored wherever it is irrelevant.

         A value of zero implies that the default meters should be used."
    ::= { tSasSapIngressFCEntry 3 }

tSapIngressFCUnknownMeter OBJECT-TYPE
    SYNTAX       TSapIngressMeterId
    MAX-ACCESS   read-create
    STATUS       current
    DESCRIPTION
        "The specific unknown destination meter to be used for packets in this
         forwarding class. The meter is used only for specific entities and
         will be ignored wherever it is irrelevant.

         A value of zero implies that the default meters should be used."
    ::= { tSasSapIngressFCEntry 4 }

tSapIngressFCUseDei OBJECT-TYPE
    SYNTAX       TruthValue
    MAX-ACCESS   read-create
    STATUS       current
    DESCRIPTION
         "Enables/Disables Drop Eligible bit"
    DEFVAL { false }
    ::= { tSasSapIngressFCEntry 5 }


tSasPortSchedulerPlcyTable       OBJECT-TYPE
    SYNTAX      SEQUENCE OF TSasPortSchedulerPlcyEntry
    MAX-ACCESS  not-accessible
    STATUS      current
    DESCRIPTION
        "The tSasPortSchedulerPlcyTable has an entry for each port scheduler
         configured on this system."
    ::= { tSasSchedulerObjects 1 }

tSasPortSchedulerPlcyEntry       OBJECT-TYPE
    SYNTAX      TSasPortSchedulerPlcyEntry
    MAX-ACCESS  not-accessible
    STATUS      current
    DESCRIPTION
        "Each row represents a particular port scheduler. Entries are created
         and deleted by the user."
    AUGMENTS   { tPortSchedulerPlcyEntry }
    ::= { tSasPortSchedulerPlcyTable 1 }

TSasPortSchedulerPlcyEntry ::= SEQUENCE
    {
        tPortSchedulerPlcyMode                  TPlcyMode,
        tPortSchedulerPlcyQuanta                TPlcyQuanta,
        tPortSchedulerPlcyQueue1Weight          TQWeight,
        tPortSchedulerPlcyQueue2Weight          TQWeight,
        tPortSchedulerPlcyQueue3Weight          TQWeight,
        tPortSchedulerPlcyQueue4Weight          TQWeight,
        tPortSchedulerPlcyQueue5Weight          TQWeight,
        tPortSchedulerPlcyQueue6Weight          TQWeight,
        tPortSchedulerPlcyQueue7Weight          TQWeight,
        tPortSchedulerPlcyQueue8Weight          TQWeight        
     }

tPortSchedulerPlcyMode        OBJECT-TYPE
    SYNTAX      TPlcyMode
    MAX-ACCESS  read-create
    STATUS      current
    DESCRIPTION
        "Port Scheduler Policy Mode"
    DEFVAL      { strict }
    ::= { tSasPortSchedulerPlcyEntry 1 }
    
tPortSchedulerPlcyQuanta        OBJECT-TYPE
    SYNTAX      TPlcyQuanta
    MAX-ACCESS  read-create
    STATUS      current
    DESCRIPTION
        "Port Scheduler Policy Quanta"
    DEFVAL      { 0 }
    ::= { tSasPortSchedulerPlcyEntry 2 } 

tPortSchedulerPlcyQueue1Weight         OBJECT-TYPE
    SYNTAX      TQWeight
    MAX-ACCESS  read-create
    STATUS      current
    DESCRIPTION
        "Port Scheduler Policy Queue 1 Weight"
    DEFVAL      { 1 }
    ::= { tSasPortSchedulerPlcyEntry 3 }               


tPortSchedulerPlcyQueue2Weight         OBJECT-TYPE
    SYNTAX      TQWeight
    MAX-ACCESS  read-create
    STATUS      current
    DESCRIPTION
        "Port Scheduler Policy Queue 2 Weight"
    DEFVAL      { 1 }
    ::= { tSasPortSchedulerPlcyEntry 4 }               


tPortSchedulerPlcyQueue3Weight         OBJECT-TYPE
    SYNTAX      TQWeight
    MAX-ACCESS  read-create
    STATUS      current
    DESCRIPTION
        "Port Scheduler Policy Queue 3 Weight"
    DEFVAL      { 1 }
    ::= { tSasPortSchedulerPlcyEntry 5 }               


tPortSchedulerPlcyQueue4Weight         OBJECT-TYPE
    SYNTAX      TQWeight
    MAX-ACCESS  read-create
    STATUS      current
    DESCRIPTION
        "Port Scheduler Policy Queue 4 Weight"
    DEFVAL      { 1 }
    ::= { tSasPortSchedulerPlcyEntry 6 }               


tPortSchedulerPlcyQueue5Weight         OBJECT-TYPE
    SYNTAX      TQWeight
    MAX-ACCESS  read-create
    STATUS      current
    DESCRIPTION
        "Port Scheduler Policy Queue 5 Weight"
    DEFVAL      { 1 }
    ::= { tSasPortSchedulerPlcyEntry 7 }               


tPortSchedulerPlcyQueue6Weight         OBJECT-TYPE
    SYNTAX      TQWeight
    MAX-ACCESS  read-create
    STATUS      current
    DESCRIPTION
        "Port Scheduler Policy Queue 6 Weight"
    DEFVAL      { 1 }
    ::= { tSasPortSchedulerPlcyEntry 8 }               


tPortSchedulerPlcyQueue7Weight         OBJECT-TYPE
    SYNTAX      TQWeight
    MAX-ACCESS  read-create
    STATUS      current
    DESCRIPTION
        "Port Scheduler Policy Queue 7 Weight"
    DEFVAL      { 1 }
    ::= { tSasPortSchedulerPlcyEntry 9 }               


tPortSchedulerPlcyQueue8Weight         OBJECT-TYPE
    SYNTAX      TQWeight
    MAX-ACCESS  read-create
    STATUS      current
    DESCRIPTION
        "Port Scheduler Policy Queue 8 Weight"
    DEFVAL      { 1 }
    ::= { tSasPortSchedulerPlcyEntry 10 }               


-- ----------------------------------------
-- Ingress QoS Meter SAP Statistics Table
-- ----------------------------------------
sapIngQosMeterStatsTable OBJECT-TYPE
    SYNTAX          SEQUENCE OF SapIngQosMeterStatsEntry
    MAX-ACCESS      not-accessible
    STATUS          current
    DESCRIPTION     "A table that contains ingress QoS meter SAP
                     statistics."
    ::= { tSASSapIngressObjects 3 }

sapIngQosMeterStatsEntry OBJECT-TYPE
    SYNTAX          SapIngQosMeterStatsEntry
    MAX-ACCESS      not-accessible
    STATUS          current
    DESCRIPTION     "Ingress statistics about a specific SAP's
                     QoS meter."
    INDEX           { svcId, sapPortId, sapEncapValue, sapIngQosMeterId }
    ::= { sapIngQosMeterStatsTable 1 }

SapIngQosMeterStatsEntry ::=
    SEQUENCE {
        sapIngQosMeterId                           TSapIngressMeterId,
        sapIngQosMeterStatsForwardedInProfPackets  Counter64,
        sapIngQosMeterStatsForwardedOutProfPackets Counter64,
        sapIngQosMeterStatsForwardedInProfOctets   Counter64,
        sapIngQosMeterStatsForwardedOutProfOctets  Counter64,
        sapIngQosMeterStatsForwardedPackets        Counter64,
        sapIngQosMeterStatsForwardedOctets         Counter64,
        sapIngQosMeterStatsDroppedPackets          Counter64,
        sapIngQosMeterStatsDroppedOctets           Counter64
    }

sapIngQosMeterId OBJECT-TYPE
    SYNTAX          TSapIngressMeterId
    MAX-ACCESS      read-only
    STATUS          current
    DESCRIPTION     "The index of the ingress QoS meter of
                     this SAP."
    ::= { sapIngQosMeterStatsEntry 1 }

sapIngQosMeterStatsForwardedInProfPackets OBJECT-TYPE
    SYNTAX          Counter64
    MAX-ACCESS      read-only
    STATUS          current
    DESCRIPTION     "The number of in-profile packets
                     (rate below CIR) forwarded by the
                     ingress Qchip."
    ::= { sapIngQosMeterStatsEntry 10 }

sapIngQosMeterStatsForwardedOutProfPackets OBJECT-TYPE
    SYNTAX          Counter64
    MAX-ACCESS      read-only
    STATUS          current
    DESCRIPTION     "The number of out-of-profile packets
                     (rate above CIR) forwarded by the
                     ingress Qchip."
    ::= { sapIngQosMeterStatsEntry 11 }

sapIngQosMeterStatsForwardedInProfOctets OBJECT-TYPE
    SYNTAX          Counter64
    MAX-ACCESS      read-only
    STATUS          current
    DESCRIPTION     "The number of in-profile octets
                     (rate below CIR) forwarded by the
                     ingress Qchip."
    ::= { sapIngQosMeterStatsEntry 12 }

sapIngQosMeterStatsForwardedOutProfOctets OBJECT-TYPE
    SYNTAX          Counter64
    MAX-ACCESS      read-only
    STATUS          current
    DESCRIPTION     "The number of out-of-profile octets
                     (rate above CIR) forwarded by the
                     ingress Qchip."
    ::= { sapIngQosMeterStatsEntry 13 }

sapIngQosMeterStatsForwardedPackets OBJECT-TYPE
    SYNTAX          Counter64
    MAX-ACCESS      read-only
    STATUS          current
    DESCRIPTION     "The number of packets forwarded by the
                     ingress Qchip."
    ::= { sapIngQosMeterStatsEntry 14 }

sapIngQosMeterStatsForwardedOctets OBJECT-TYPE
    SYNTAX          Counter64
    MAX-ACCESS      read-only
    STATUS          current
    DESCRIPTION     "The number of octets forwarded 
                    by the ingress Qchip."
    ::= { sapIngQosMeterStatsEntry 15 }

sapIngQosMeterStatsDroppedPackets OBJECT-TYPE
    SYNTAX          Counter64
    MAX-ACCESS      read-only
    STATUS          current
    DESCRIPTION     "The number of packets dropped by the
                     ingress Qchip."
    ::= { sapIngQosMeterStatsEntry 16 }

sapIngQosMeterStatsDroppedOctets OBJECT-TYPE
    SYNTAX          Counter64
    MAX-ACCESS      read-only
    STATUS          current
    DESCRIPTION     "The number of  octets dropped by the
                     ingress Qchip."
    ::= { sapIngQosMeterStatsEntry 17 }


tQosIngressFrameBasedAccnt OBJECT-TYPE
    SYNTAX      TruthValue
    MAX-ACCESS  read-create
    STATUS      current
    DESCRIPTION
        "This object is used to enable frame based accounting for all
         the ingress meters in use by the system. When this is enabled
         the ingress meters account for the IFG (12 bytes) + SFD (8 bytes)
         overhead associated with Ethernet frame."
    DEFVAL { false }
    ::= { tQosFrameBasedAccntObjects 1 }

tQosEgressFrameBasedAccnt OBJECT-TYPE
    SYNTAX      TruthValue
    MAX-ACCESS  read-create
    STATUS      current
    DESCRIPTION
        "This object is used to enable frame based accounting for all
         the egress queue shapers and the port egress rate shaper in
         use by the system. When this is enabled the shapers account for
         the IFG (12 bytes) + SFD (8 bytes) overhead associated with
         Ethernet frame."
    DEFVAL { false }
    ::= { tQosFrameBasedAccntObjects 2 }

tSapIngressExtnTable OBJECT-TYPE
    SYNTAX          SEQUENCE OF TSapIngressExtnEntry
    MAX-ACCESS      not-accessible
    STATUS          current
    DESCRIPTION     ""
    ::= { tSASSapIngressObjects 4 }

tSapIngressExtnEntry OBJECT-TYPE
    SYNTAX          TSapIngressExtnEntry
    MAX-ACCESS      not-accessible
    STATUS          current
    DESCRIPTION     ""
    AUGMENTS   { tSapIngressEntry }
    ::= { tSapIngressExtnTable 1 }

TSapIngressExtnEntry ::=
    SEQUENCE {
        tSapIngressNumQosClassifiers              Unsigned32,
        tSapIngressQosClassifiersUsed             Unsigned32,
        tSapIngressQosMetersUsed                  Unsigned32,
        tSapIngressQosClassifiersRequiredInVpls   Unsigned32,
        tSapIngressQosClassifiersRequiredInEpipe  Unsigned32,        
        tSapIngressQosMetersRequiredInVpls        Unsigned32,        
        tSapIngressQosMetersRequiredInEpipe       Unsigned32,
        tSapIngressIPCriteriaMatch                INTEGER,
        tSapIngressMacCriteriaMatch               INTEGER,
        tSapIngressDefaultFCProfile               TProfileOrDeiOrNone,
        tSapIngressIPv6CriteriaEnable             TruthValue,
        tSapIngressIPv6CriteriaMatch              INTEGER,
        tSapIngressIPMacMatch                     INTEGER,
        tSapIngressQosClassifiersRequiredInIes    Unsigned32,
        tSapIngressQosMetersRequiredInIes         Unsigned32,
        tSapIngressQosDot1PClassificationPolicy   Unsigned32,
        tSapIngressQosDscpClassificationPolicy    Unsigned32,
        tSapIngressQosInnerDot1PMatch             TruthValue,
        tSapIngressQosMplsLspExpClassificationPolicy   Unsigned32
    }

tSapIngressNumQosClassifiers OBJECT-TYPE
    SYNTAX Unsigned32 (2..256) 
    MAX-ACCESS read-create
    STATUS current
    DESCRIPTION    
        "The number of ingress QoS classifiers to be allocated 
        to the SAP on which this policy is applied. The number 
        of QoS classifiers required by a SAP ingress QoS policy 
        should be less than or equal to its tSapIngressNumQosClassifiers. 
        The number of Meters required by a SAP ingress QoS policy 
        should be less than or equal to half the number of 
        tSapIngressNumQosClassifiers."
    DEFVAL { 2 }
    ::= { tSapIngressExtnEntry 1 }

tSapIngressQosClassifiersUsed OBJECT-TYPE
    SYNTAX Unsigned32 
    MAX-ACCESS read-only
    STATUS obsolete
    DESCRIPTION 
        "This value indicates the number of ingress QoS classifiers 
        required when this policy is applied on a SAP. This value is 
        calculated based on the number of classifiers required for a 
        VPLS SAP."
    ::= { tSapIngressExtnEntry 2 }

tSapIngressQosMetersUsed OBJECT-TYPE
    SYNTAX Unsigned32 
    MAX-ACCESS read-only
    STATUS obsolete
    DESCRIPTION 
        "This value indicates the number of ingress QoS meters required 
        when this policy is applied on a SAP.  This value is calculated 
        based on the number of meters required for a VPLS SAP."
    ::= { tSapIngressExtnEntry 3 }

tSapIngressQosClassifiersRequiredInVpls OBJECT-TYPE
    SYNTAX Unsigned32 
    MAX-ACCESS read-only
    STATUS current
    DESCRIPTION 
        "This value indicates the number of ingress QoS classifiers 
        required when this policy is applied on a SAP. This value is 
        calculated based on the number of classifiers required for a 
        VPLS SAP."
    ::= { tSapIngressExtnEntry 4 }

tSapIngressQosClassifiersRequiredInEpipe OBJECT-TYPE
    SYNTAX Unsigned32 
    MAX-ACCESS read-only
    STATUS current
    DESCRIPTION 
        "This value indicates the number of ingress QoS classifiers 
        required when this policy is applied on a SAP. This value is 
        calculated based on the number of classifiers required for a 
        EPIPE SAP."
    ::= { tSapIngressExtnEntry 5 }

tSapIngressQosMetersRequiredInVpls OBJECT-TYPE
    SYNTAX Unsigned32 
    MAX-ACCESS read-only
    STATUS current
    DESCRIPTION 
        "This value indicates the number of ingress QoS meters required 
        when this policy is applied on a SAP.  This value is calculated 
        based on the number of meters required for a VPLS SAP."
    ::= { tSapIngressExtnEntry 6 }

tSapIngressQosMetersRequiredInEpipe OBJECT-TYPE
    SYNTAX Unsigned32 
    MAX-ACCESS read-only
    STATUS current
    DESCRIPTION 
        "This value indicates the number of ingress QoS meters required 
        when this policy is applied on a SAP.  This value is calculated 
        based on the number of meters required for a EPIPE SAP."
    ::= { tSapIngressExtnEntry 7 }

tSapIngressIPCriteriaMatch OBJECT-TYPE
    SYNTAX       INTEGER {
                     any  (1),
                     dscp-only(2)
                 }
    MAX-ACCESS   read-create
    STATUS       current
    DESCRIPTION
        "This object specifies the basic match criteria as 'any' or 'dscp-only'
        based on ip. The default value is 'dscp-only' "
    DEFVAL { dscp-only }    
    ::= { tSapIngressExtnEntry 8 }    

tSapIngressMacCriteriaMatch OBJECT-TYPE
    SYNTAX       INTEGER {
                     any  (1),
                     dot1p-only(2)
                 }
    MAX-ACCESS   read-create
    STATUS       current
    DESCRIPTION
         "This object specifies the basic match criteria as 'any' or 'dot1p-only'
        based on Mac Address. The default value is 'any' "
    DEFVAL { any }    
    ::= { tSapIngressExtnEntry 9 }      

tSapIngressDefaultFCProfile OBJECT-TYPE
    SYNTAX       TProfileOrDeiOrNone
    MAX-ACCESS   read-create
    STATUS       current
    DESCRIPTION
        "tSapIngressDefaultFCProfile specifies the profile  for 
        the default fc"
    DEFVAL { out }
    ::= { tSapIngressExtnEntry 10 }

tSapIngressIPv6CriteriaEnable OBJECT-TYPE
    SYNTAX       TruthValue
    MAX-ACCESS   read-create
    STATUS       current
    DESCRIPTION
        "tSapIngressIPv6CriteriaEnable is a boolean  
        flag which allows/disallows configuring match criteria 
        based on ipv6 address"
    DEFVAL { false }
    ::= { tSapIngressExtnEntry 11 }

tSapIngressIPv6CriteriaMatch OBJECT-TYPE
    SYNTAX       INTEGER {
                     any  (1),
                     dscp-only(2)
                 }
    MAX-ACCESS   read-create
    STATUS       current
    DESCRIPTION
        "This object specifies the basic match criteria as 'any' or 'dscp-only'
        based on ipv6. The default value is 'dscp-only' "
    DEFVAL { dscp-only }    
    ::= { tSapIngressExtnEntry 12 }        

tSapIngressIPMacMatch OBJECT-TYPE
    SYNTAX       INTEGER {
                     none      (0),
                     ip-first  (1),
                     mac-first (2)
                 }
    MAX-ACCESS   read-create
    STATUS       current
    DESCRIPTION
        "This object specifies the basic match criteria whether to match
        ip or mac criteria first"
    DEFVAL { none }    
    ::= { tSapIngressExtnEntry 13 }   

tSapIngressQosClassifiersRequiredInIes OBJECT-TYPE
    SYNTAX Unsigned32 
    MAX-ACCESS read-only
    STATUS current
    DESCRIPTION 
        "This value indicates the number of ingress QoS classifiers 
        required when this policy is applied on a SAP. This value is 
        calculated based on the number of classifiers required for a 
        IES SAP."
    ::= { tSapIngressExtnEntry 14 }

tSapIngressQosMetersRequiredInIes OBJECT-TYPE
    SYNTAX Unsigned32 
    MAX-ACCESS read-only
    STATUS current
    DESCRIPTION 
        "This value indicates the number of ingress QoS classifiers 
        required when this policy is applied on a SAP. This value is 
        calculated based on the number of classifiers required for a 
        IES SAP."
    ::= { tSapIngressExtnEntry 15 }
    
tSapIngressQosDot1PClassificationPolicy OBJECT-TYPE
    SYNTAX Unsigned32 (0..65535) 
    MAX-ACCESS read-create
    STATUS current
    DESCRIPTION 
        "This variable is used to apply Dot1P Classification policy"
    DEFVAL { 0 }    
    ::= { tSapIngressExtnEntry 16 }
    
tSapIngressQosDscpClassificationPolicy OBJECT-TYPE
    SYNTAX Unsigned32 (0..65535) 
    MAX-ACCESS read-create
    STATUS current
    DESCRIPTION 
        "This variable is used to apply Dscp Classification policy"
    DEFVAL { 0 }    
    ::= { tSapIngressExtnEntry 17 }
    
tSapIngressQosInnerDot1PMatch OBJECT-TYPE
    SYNTAX TruthValue
    MAX-ACCESS read-create
    STATUS current
    DESCRIPTION 
        "This variable is used to enable inner dot1p match criteria"
    DEFVAL { false }    
    ::= { tSapIngressExtnEntry 18 }
    
tSapIngressQosMplsLspExpClassificationPolicy OBJECT-TYPE
    SYNTAX Unsigned32 (0..65535) 
    MAX-ACCESS read-create
    STATUS current
    DESCRIPTION 
        "This variable is used to apply MplsLspExp Classification policy"
    DEFVAL { 0 }    
    ::= { tSapIngressExtnEntry 19 }
    
tNetworkPolicyExtnTable OBJECT-TYPE
    SYNTAX          SEQUENCE OF TNetworkPolicyExtnEntry
    MAX-ACCESS      not-accessible
    STATUS          current
    DESCRIPTION     
        "Extension table to tNetworkPolicyTable"
    ::= { tSASNetworkObjects 1 }

tNetworkPolicyExtnEntry OBJECT-TYPE
    SYNTAX          TNetworkPolicyExtnEntry
    MAX-ACCESS      not-accessible
    STATUS          current
    DESCRIPTION     ""
    AUGMENTS   { tNetworkPolicyEntry }
    ::= { tNetworkPolicyExtnTable 1 }

TNetworkPolicyExtnEntry ::=
    SEQUENCE {
        tNetworkPolicyType                TNetworkPolicyType,
        tNetworkPolicyRemarkPolicyId      TRemarkPolicyID,
        tNetworkIngressMeterColorMode     INTEGER,
        tNetworkIngressMplsLspExpProfile  TMplsLspExpProfMapID,
        tNetworkEgressRemarkType           INTEGER,
        tNetworkIngressQosDot1PClassificationPolicy Unsigned32,
        tNetworkIngressQosDscpClassificationPolicy  Unsigned32,
        tNetworkIngressQosMplsLspExpClassificationPolicy Unsigned32
    }

tNetworkPolicyType  OBJECT-TYPE
    SYNTAX       TNetworkPolicyType 
    MAX-ACCESS   read-create
    STATUS       current
    DESCRIPTION
        "Network policy Type determines the point of attachment of the   
         network qos policy. Network policy with 'ipInterface' type can be         
         attached to ip interface and 'port' type can be attached to 
         physical port"
    DEFVAL { ipInterface }
    ::= { tNetworkPolicyExtnEntry 1 }

tNetworkPolicyRemarkPolicyId OBJECT-TYPE
    SYNTAX       TRemarkPolicyID
    MAX-ACCESS   read-create
    STATUS       current
    DESCRIPTION
        "Remark Policy Id that be used."
    DEFVAL { 2 }
    ::= { tNetworkPolicyExtnEntry 2 }

tNetworkIngressMeterColorMode OBJECT-TYPE
    SYNTAX       INTEGER {
                     color-aware  (1),
                     color-blind  (2)
                 }
    MAX-ACCESS   read-create
    STATUS       current
    DESCRIPTION
        "tNetworkIngressMeterColorMode indicates whether the ip interface is
        color-aware or color-blind. By default every ip interface is color-aware" 
    DEFVAL { color-aware }
    ::= { tNetworkPolicyExtnEntry 3 }  

tNetworkIngressMplsLspExpProfile  OBJECT-TYPE
    SYNTAX      TMplsLspExpProfMapID
    MAX-ACCESS  read-create
    STATUS      current
    DESCRIPTION
        "tNetworkIngressMplsLspExpProfile attaches the MPLS LSP EXP Profile to 
        this network policy."
    DEFVAL { 1 }
    ::= { tNetworkPolicyExtnEntry 4 }  

tNetworkEgressRemarkType OBJECT-TYPE
    SYNTAX       INTEGER {
                     use-dot1p  (1),
                     use-dscp   (2),
                     all        (3)
                 }
    MAX-ACCESS   read-create
    STATUS       current
    DESCRIPTION
        "This object specifies system remark type, tNetworkPolicyEgressRemark
        will be set to true and tNetworkEgressRemarkType will specify the
        remark type."
    ::= { tNetworkPolicyExtnEntry 5 }
    
tNetworkIngressQosDot1PClassificationPolicy  OBJECT-TYPE
    SYNTAX      Unsigned32 (0..65535)
    MAX-ACCESS  read-create
    STATUS      current
    DESCRIPTION
        "This variable is used to apply Dot1P Classification policy"
    DEFVAL { 0 }
    ::= { tNetworkPolicyExtnEntry 6 }  

tNetworkIngressQosDscpClassificationPolicy  OBJECT-TYPE
    SYNTAX      Unsigned32 (0..65535)
    MAX-ACCESS  read-create
    STATUS      current
    DESCRIPTION
        "This variable is used to apply Dscp Classification policy"
    DEFVAL { 0 }
    ::= { tNetworkPolicyExtnEntry 7 }  

tNetworkIngressQosMplsLspExpClassificationPolicy  OBJECT-TYPE
    SYNTAX      Unsigned32 (0..65535)
    MAX-ACCESS  read-create
    STATUS      current
    DESCRIPTION
        "This variable is used to apply MplsLspExp Classification policy"
    DEFVAL { 0 }
    ::= { tNetworkPolicyExtnEntry 8 }  


--
tNetworkQueueExtnTable OBJECT-TYPE
    SYNTAX          SEQUENCE OF TNetworkQueueExtnEntry
    MAX-ACCESS      not-accessible
    STATUS          current
    DESCRIPTION     
        "Extension table to tNetworkQueueTable"
    ::= { tSASNetworkObjects 2 }

tNetworkQueueExtnEntry OBJECT-TYPE
    SYNTAX          TNetworkQueueExtnEntry
    MAX-ACCESS      not-accessible
    STATUS          current
    DESCRIPTION     ""
    AUGMENTS   { tNetworkQueueEntry }
    ::= { tNetworkQueueExtnTable 1 }

TNetworkQueueExtnEntry ::=
    SEQUENCE {
        tNetworkQueuePolicyName        TNamedItem,
        tNetworkQueuePolicyQueueMode   INTEGER,
        tNetworkQueuePolicyWeight      INTEGER,
        tNetworkQueuePolicyCBSAbsolute TBurstSize,
        tNetworkQueuePolicyMBSAbsolute TBurstSize
    }

tNetworkQueuePolicyName  OBJECT-TYPE
    SYNTAX       TNamedItem 
    MAX-ACCESS   read-create
    STATUS       current
    DESCRIPTION
        "NetworkQueuePolicyName determines the queue management policy
        attached to this network queue."
    DEFVAL { "default" }
    ::= { tNetworkQueueExtnEntry 1 }

tNetworkQueuePolicyQueueMode OBJECT-TYPE
    SYNTAX       INTEGER {
                     strict-ef   (1),
                     strict      (2),
                     weighted    (3)
                 }
    MAX-ACCESS   read-create
    STATUS       current
    DESCRIPTION
        "tNetworkQueuePolicyQueueMode specifies this policies mode. It has
    to be set when the policy is created."
    DEFVAL { weighted }
    ::= { tNetworkQueueExtnEntry 2 }

tNetworkQueuePolicyWeight OBJECT-TYPE
    SYNTAX       INTEGER (1..15)
    MAX-ACCESS   read-create
    STATUS       current
    DESCRIPTION
        "tNetworkQueuePolicyWeight specifies this policies weight. It is
    applicable only if queue mode is weighted."
    DEFVAL { 1 }    
    ::= { tNetworkQueueExtnEntry 3 }

tNetworkQueuePolicyCBSAbsolute OBJECT-TYPE
    SYNTAX       TBurstSize
    MAX-ACCESS   read-create
    STATUS       current
    DESCRIPTION
        "The absolute value (Kilo bytes) of reserved buffer space for the queue" 
    DEFVAL { 50 }
    ::= { tNetworkQueueExtnEntry 4 }

tNetworkQueuePolicyMBSAbsolute OBJECT-TYPE
    SYNTAX       TBurstSize
    MAX-ACCESS   read-create
    STATUS       current
    DESCRIPTION
        "The absolute value (Kilo bytes) of reserved buffer space for the queue" 
    DEFVAL { 200 }
    ::= { tNetworkQueueExtnEntry 5 }

--

tNetworkEgressFCExtnTable OBJECT-TYPE
    SYNTAX       SEQUENCE OF TNetworkEgressFCExtnEntry
    MAX-ACCESS   not-accessible
    STATUS       current
    DESCRIPTION
        "Information about all network policies' egress FC traffic disposition,
        this table extends the capabilities available in tNetworkEgressFCTable"
    ::= { tSASNetworkObjects 3 }

tNetworkEgressFCExtnEntry OBJECT-TYPE
    SYNTAX       TNetworkEgressFCExtnEntry
    MAX-ACCESS   not-accessible
    STATUS       current
    DESCRIPTION
        "Information about a particular network policy's egress
         per-forwarding-class traffic disposition.

         Entries are created/deleted as an action of creating/deleting
         a row in the tNetworkPolicyTable.

         There is no StorageType object, entries have a presumed
         StorageType of nonVolatile."
    AUGMENTS { tNetworkEgressFCEntry }
    ::= { tNetworkEgressFCExtnTable 1 }

TNetworkEgressFCExtnEntry ::= SEQUENCE
    {
        tNetworkEgressFCDot1pProfile    Dot1PPriority
    }

tNetworkEgressFCDot1pProfile OBJECT-TYPE
    SYNTAX       Dot1PPriority
    MAX-ACCESS   read-write
    STATUS       current
    DESCRIPTION
        "the Dot1p to use for in-profile traffic."
    ::= { tNetworkEgressFCExtnEntry 1 }

--

tQueueMgmtPolicyTable OBJECT-TYPE
    SYNTAX       SEQUENCE OF TQueueMgmtPolicyEntry
    MAX-ACCESS   not-accessible
    STATUS       current
    DESCRIPTION
        "Queue Management Policy definition for 7210-X platform."
    ::= { tSASQueueMgmtObjects 1 }

tQueueMgmtPolicyEntry OBJECT-TYPE
    SYNTAX       TQueueMgmtPolicyEntry
    MAX-ACCESS   not-accessible
    STATUS       current
    DESCRIPTION
        ""
    INDEX    { tQueueMgmtPolicyName }
    ::= { tQueueMgmtPolicyTable 1 }

TQueueMgmtPolicyEntry ::= SEQUENCE
    {
        tQueueMgmtPolicyName                  TNamedItem,
        tQueueMgmtPolicyRowStatus             RowStatus,
        tQueueMgmtPolicyLastChanged           TimeStamp,
        tQueueMgmtPolicyDescription           TItemDescription,
        tQueueMgmtPolicyHiAdminStatus         INTEGER,
        tQueueMgmtPolicyHiStartAverage        Unsigned32,
        tQueueMgmtPolicyHiMaxAverage          Unsigned32,
        tQueueMgmtPolicyHiMaxProbability      Unsigned32,        
        tQueueMgmtPolicyLoAdminStatus         INTEGER,
        tQueueMgmtPolicyLoStartAverage        Unsigned32,
        tQueueMgmtPolicyLoMaxAverage          Unsigned32,
        tQueueMgmtPolicyLoMaxProbability      Unsigned32,
        tQueueMgmtPolicyCBS                   INTEGER,
        tQueueMgmtPolicyMBS                   INTEGER,
        tQueueMgmtPolicyTimeAvgFactor         Unsigned32,
        tQueueMgmtPolicyScope                 TItemScope
    }        

tQueueMgmtPolicyName OBJECT-TYPE
    SYNTAX       TNamedItem
    MAX-ACCESS   not-accessible
    STATUS       current
    DESCRIPTION
        "The value of tQueueMgmtPolicyName specifies the name of the Queue 
         Management policy."
    ::= { tQueueMgmtPolicyEntry 1 }

tQueueMgmtPolicyRowStatus OBJECT-TYPE
    SYNTAX       RowStatus
    MAX-ACCESS   read-create
    STATUS       current
    DESCRIPTION
        "Row Status of the entry. This allows creation/deletion of rows in this
         table."
    ::= { tQueueMgmtPolicyEntry 2 }

tQueueMgmtPolicyLastChanged OBJECT-TYPE
    SYNTAX       TimeStamp
    MAX-ACCESS   read-only
    STATUS       current
    DESCRIPTION
        "Timestamp of last change to this row."
    ::= { tQueueMgmtPolicyEntry 3 }
    
tQueueMgmtPolicyDescription OBJECT-TYPE
    SYNTAX       TItemDescription
    MAX-ACCESS   read-create
    STATUS       current
    DESCRIPTION
        "User-provided description of the policy."
    DEFVAL { ''H }
    ::= { tQueueMgmtPolicyEntry 4 }

tQueueMgmtPolicyHiAdminStatus OBJECT-TYPE
    SYNTAX       INTEGER {
                     up  (1),
                     down(2)
                 }
    MAX-ACCESS   read-create
    STATUS       current
    DESCRIPTION
        "tQueueMgmtPolicyHiAdminStatus specifies the admin state for the queue's
 high profile (Green Packets) slope. If the tQueueMgmtPolicyHiAdminStatus
 is set to 'down',the slope is inactive."
    DEFVAL { down }    
    ::= { tQueueMgmtPolicyEntry 5 }

tQueueMgmtPolicyHiStartAverage OBJECT-TYPE
    SYNTAX       Unsigned32 (0..100)
    MAX-ACCESS   read-create
    STATUS       current
    DESCRIPTION
        "The percentage of the buffer utilized after which the drop probability
        starts to rise above 0."
    DEFVAL { 70 }
    ::= { tQueueMgmtPolicyEntry 6 }

tQueueMgmtPolicyHiMaxAverage OBJECT-TYPE
    SYNTAX       Unsigned32 (0..100)
    MAX-ACCESS   read-create
    STATUS       current
    DESCRIPTION
        "The percentage of the buffer utilized after which the drop probability
 is 100 percent. This implies that all packets beyond this point will be
        dropped."
    DEFVAL { 90 }
    ::= { tQueueMgmtPolicyEntry 7 }

tQueueMgmtPolicyHiMaxProbability OBJECT-TYPE
    SYNTAX       Unsigned32 (1..99)
    MAX-ACCESS   read-create
    STATUS       current
    DESCRIPTION
        "High Profile Max Probability.Defines the slope between the
        Start Average and Max Average"
    DEFVAL { 75 }
    ::= { tQueueMgmtPolicyEntry 8 }    

tQueueMgmtPolicyLoAdminStatus OBJECT-TYPE
    SYNTAX       INTEGER {
                     up  (1),
                     down(2)
                 }
    MAX-ACCESS   read-create
    STATUS       current
    DESCRIPTION
        "tQueueMgmtPolicyLoAdminStatus specifies the admin state for the queue's
        low profile (Yellow Packets) slope. If the tQueueMgmtPolicyLoAdminStatus
 is set to 'down',the slope is inactive."
    DEFVAL { down }
    ::= { tQueueMgmtPolicyEntry 9 }

tQueueMgmtPolicyLoStartAverage OBJECT-TYPE
    SYNTAX       Unsigned32 (0..100)
    MAX-ACCESS   read-create
    STATUS       current
    DESCRIPTION
        "The percentage of the buffer utilized after which the drop probability
        starts to rise above 0."
    DEFVAL { 50 }
    ::= { tQueueMgmtPolicyEntry 10 }

tQueueMgmtPolicyLoMaxAverage OBJECT-TYPE
    SYNTAX       Unsigned32 (0..100)
    MAX-ACCESS   read-create
    STATUS       current
    DESCRIPTION
        "The percentage of the buffer utilized after which the drop probability
 is 100 percent. This implies that all packets beyond this point will be
        dropped."
    DEFVAL { 75 }
    ::= { tQueueMgmtPolicyEntry 11 }    

tQueueMgmtPolicyLoMaxProbability OBJECT-TYPE
    SYNTAX       Unsigned32 (1..99)
    MAX-ACCESS   read-create
    STATUS       current
    DESCRIPTION
        "Low Profile Max Probability.Defines the slope between the
        Start Average and Max Average"
    DEFVAL { 75 }
    ::= { tQueueMgmtPolicyEntry 12 }    

tQueueMgmtPolicyCBS OBJECT-TYPE
    SYNTAX       INTEGER (-1 | 0..800000)
    MAX-ACCESS   read-create
    STATUS       current
    DESCRIPTION
        "The amount of reserved buffer space (in kilo bytes) for the queue."
    DEFVAL { -1 }
    ::= { tQueueMgmtPolicyEntry 13 }

tQueueMgmtPolicyMBS OBJECT-TYPE
    SYNTAX       INTEGER (-1 | 1..800000)
    MAX-ACCESS   read-create
    STATUS       current
    DESCRIPTION
        "The maximum amount of buffer space (in kilo bytes) allowed for the
        queue."
    DEFVAL { -1 }
    ::= { tQueueMgmtPolicyEntry 14 }

tQueueMgmtPolicyTimeAvgFactor OBJECT-TYPE
    SYNTAX       Unsigned32 (0..15)
    MAX-ACCESS   read-create
    STATUS       current
    DESCRIPTION
        "The time average factor describes the weighting between the previous
 shared buffer average utilization result and the new shared buffer
        utilization in determining the new shared buffer average utilization."
    DEFVAL { 7 }
    ::= { tQueueMgmtPolicyEntry 15 }    

tQueueMgmtPolicyScope OBJECT-TYPE
    SYNTAX       TItemScope
    MAX-ACCESS   read-create
    STATUS       current
    DESCRIPTION
        "Scope of the queue management policy."
    DEFVAL { template }
    ::= { tQueueMgmtPolicyEntry 16 }

tSapEgressExtnTable OBJECT-TYPE
    SYNTAX          SEQUENCE OF TSapEgressExtnEntry
    MAX-ACCESS      not-accessible
    STATUS          current
    DESCRIPTION     
        "Extension table to tSapEgressTable"
    ::= { tSASSapEgressObjects 1 }

tSapEgressExtnEntry OBJECT-TYPE
    SYNTAX          TSapEgressExtnEntry
    MAX-ACCESS      not-accessible
    STATUS          current
    DESCRIPTION     ""
    AUGMENTS   { tSapEgressEntry }
    ::= { tSapEgressExtnTable 1 }

TSapEgressExtnEntry ::=
    SEQUENCE {
        tSapEgressRemark             TruthValue,
        tSapEgressRemarkPolicyId     TRemarkPolicyID
    }

tSapEgressRemark OBJECT-TYPE
    SYNTAX       TruthValue
    MAX-ACCESS   read-create
    STATUS       current
    DESCRIPTION
        "This object specifies if the system
         will remark the egress packets on SAP or not."
    DEFVAL { false }
::= { tSapEgressExtnEntry 1 }

tSapEgressRemarkPolicyId OBJECT-TYPE
    SYNTAX       TRemarkPolicyID
    MAX-ACCESS   read-create
    STATUS       current
    DESCRIPTION
        "Remark Policy Id that be used.  The default value is the default
        dot1p-dscp policy."
    DEFVAL { 1 }
    ::= { tSapEgressExtnEntry 2 }

tSapEgressQueueExtnTable OBJECT-TYPE
    SYNTAX          SEQUENCE OF TSapEgressQueueExtnEntry
    MAX-ACCESS      not-accessible
    STATUS          current
    DESCRIPTION     
        "Extension table to tSapEgressQueueTable"
    ::= { tSASSapEgressObjects 2 }

tSapEgressQueueExtnEntry OBJECT-TYPE
    SYNTAX          TSapEgressQueueExtnEntry
    MAX-ACCESS      not-accessible
    STATUS          current
    DESCRIPTION     ""
    AUGMENTS   { tSapEgressQueueEntry }
    ::= { tSapEgressQueueExtnTable 1 }

TSapEgressQueueExtnEntry ::=
    SEQUENCE {
        tSapEgressQueuePolicyName           TNamedItem,
        tSapEgressQueuePolicyQueueMode   INTEGER,
        tSapEgressQueuePolicyWeight      INTEGER,
        tSapEgressQueueMBSAbsolute       INTEGER
    }

tSapEgressQueuePolicyName  OBJECT-TYPE
    SYNTAX       TNamedItem 
    MAX-ACCESS   read-create
    STATUS       current
    DESCRIPTION
        "SapEgressQueuePolicyName determines the queue management policy
        attached to this SAP Egress queue."
    DEFVAL { "default" }
    ::= { tSapEgressQueueExtnEntry 1 }

tSapEgressQueuePolicyQueueMode OBJECT-TYPE
    SYNTAX       INTEGER {
                     strict-ef   (1),
                     strict      (2),
                     weighted    (3)
                 }
    MAX-ACCESS   read-create
    STATUS       current
    DESCRIPTION
        "tSapEgressQueuePolicyQueueMode specifies this policies mode. It has
    to be set when the policy is created."
    DEFVAL { weighted }
    ::= { tSapEgressQueueExtnEntry 2 }

tSapEgressQueuePolicyWeight OBJECT-TYPE
    SYNTAX       INTEGER (1..15)
    MAX-ACCESS   read-create
    STATUS       current
    DESCRIPTION
        "tSapEgressQueuePolicyWeight specifies this policies weight. It is
    applicable only if queue mode is weighted."
    DEFVAL { 1 }    
    ::= { tSapEgressQueueExtnEntry 3 }

tSapEgressQueueMBSAbsolute OBJECT-TYPE
    SYNTAX       INTEGER (-1 | 0..12800)
    MAX-ACCESS   read-create
    STATUS       current
    DESCRIPTION
        "The maximum amount of buffer space (in kilo bytes) allowed for the
        queue.

        This object has been replaced with tSapEgressQueueMBSAbsolute object."
    DEFVAL { -1 }
    ::= { tSapEgressQueueExtnEntry 4 }

--
-- remark policy table
--

tSASRemarkPolicyTable OBJECT-TYPE
    SYNTAX       SEQUENCE OF TSASRemarkPolicyEntry
    MAX-ACCESS   not-accessible
    STATUS       current
    DESCRIPTION  "  "
    ::= { tSASGeneralQosObjects 1 }  

tSASRemarkPolicyEntry OBJECT-TYPE
    SYNTAX       TSASRemarkPolicyEntry
    MAX-ACCESS   not-accessible
    STATUS       current
    DESCRIPTION
        "Information about a particular remarking policy's
         forwarding class mappings to dot1p / dscp / exp 
         values.
         Entries are created/deleted by user."
    INDEX { tSASRemarkPolicyId }
    ::= { tSASRemarkPolicyTable 1 }

TSASRemarkPolicyEntry ::= SEQUENCE
    {
        tSASRemarkPolicyId                TRemarkPolicyID,
        tSASRemarkPolicyRowStatus         RowStatus,
        tSASRemarkPolicyDescription       TItemDescription,
        tSASRemarkPolicyType              INTEGER,
        tSASRemarkPolicyLastChanged       TimeStamp
    }

tSASRemarkPolicyId OBJECT-TYPE
    SYNTAX       TRemarkPolicyID
    MAX-ACCESS   not-accessible
    STATUS       current
    DESCRIPTION
        "The remark policy ID is used as index for the table."
    ::= { tSASRemarkPolicyEntry 1 }

tSASRemarkPolicyRowStatus OBJECT-TYPE
    SYNTAX       RowStatus
    MAX-ACCESS   read-create
    STATUS       current
    DESCRIPTION
        "Row Status."
    ::= { tSASRemarkPolicyEntry 2 }

tSASRemarkPolicyDescription OBJECT-TYPE
    SYNTAX       TItemDescription
    MAX-ACCESS   read-create
    STATUS       current
    DESCRIPTION
        "User-provided description of the policy."
    DEFVAL { ''H }
    ::= { tSASRemarkPolicyEntry 3 }

tSASRemarkPolicyType OBJECT-TYPE
    SYNTAX       INTEGER {
                     dot1p                (1),
                     dscp                 (2),
                     lsp-exp              (3),
                     dot1p-dscp           (4),
                     dot1p-lsp-exp-shared (5),
                     dot1p-lsp-exp        (6),
                     dscp-lsp-exp         (7),
                     dot1p-lsp-exp-dscp   (8)

                 }
    MAX-ACCESS   read-create
    STATUS       current
    DESCRIPTION
        "The remarking type of this policy.  This specifies which
         of the fields will be remarked."
    DEFVAL { dot1p-lsp-exp-shared }
    ::= { tSASRemarkPolicyEntry 4 }

tSASRemarkPolicyLastChanged OBJECT-TYPE
    SYNTAX       TimeStamp
    MAX-ACCESS   read-only
    STATUS       current
    DESCRIPTION
        "Timestamp of last change to this row in tSASRemarkPolicyTable."
    ::= { tSASRemarkPolicyEntry 5 }

--
-- remark policy FC table
--

tSASRemarkPolicyFCTable OBJECT-TYPE
    SYNTAX       SEQUENCE OF TSASRemarkPolicyFCEntry
    MAX-ACCESS   not-accessible
    STATUS       current
    DESCRIPTION  "  "
    ::= { tSASGeneralQosObjects 2 }  

tSASRemarkPolicyFCEntry OBJECT-TYPE
    SYNTAX       TSASRemarkPolicyFCEntry
    MAX-ACCESS   not-accessible
    STATUS       current
    DESCRIPTION
        "Information about a particular queue in a remarking policy's
         forwarding class mappings to dot1p / dscp / exp 
         values.
         Entries are created/deleted whenever a policy is created/deleted."
    INDEX { tSASRemarkPolicyId, tSASRemarkPolicyFCName }
    ::= { tSASRemarkPolicyFCTable 1 }

TSASRemarkPolicyFCEntry ::= SEQUENCE
    {
        tSASRemarkPolicyFCName                 TFCName,
        tSASRemarkPolicyDot1PInProfile         Dot1PPriority,
        tSASRemarkPolicyDot1POutProfile        Dot1PPriority,
        tSASRemarkPolicyDSCPInProfile          TDSCPNameOrEmpty,
        tSASRemarkPolicyDSCPOutProfile         TDSCPNameOrEmpty,
        tSASRemarkPolicyLspExpInProfile        TLspExpValue,
        tSASRemarkPolicyLspExpOutProfile       TLspExpValue,
        tSASRemarkPolicyDot1PLspExpInProfile   TDot1PLspExpValue,
        tSASRemarkPolicyDot1PLspExpOutProfile  TDot1PLspExpValue,
        tSASRemarkPolicyDot1PProfile           Dot1PPriority,
        tSASRemarkPolicyForceDEValue           TDEValue,
        tSASRemarkPolicyFCDEMark               TruthValue,
        tSASRemarkPolicyDot1PInner                  Dot1PPriority,
        tSASRemarkPolicyDot1PInnerInProfile         Dot1PPriority,
        tSASRemarkPolicyDot1PInnerOutProfile        Dot1PPriority,
        tSASRemarkPolicyDot1POuter                  Dot1PPriority,
        tSASRemarkPolicyDot1POuterInProfile         Dot1PPriority,
        tSASRemarkPolicyDot1POuterOutProfile        Dot1PPriority
    }

tSASRemarkPolicyFCName OBJECT-TYPE
    SYNTAX       TFCName
    MAX-ACCESS   not-accessible
    STATUS       current
    DESCRIPTION
        "The FC Class Name."
    ::= { tSASRemarkPolicyFCEntry 1 }

tSASRemarkPolicyDot1PInProfile OBJECT-TYPE
    SYNTAX       Dot1PPriority
    MAX-ACCESS   read-write
    STATUS       current
    DESCRIPTION
        "The Dot1p to use for in-profile traffic.  This field is valid
         only for the following remarking types:
              dot1p
              dot1p-dscp"
    DEFVAL { -1 }
    ::= { tSASRemarkPolicyFCEntry 2 }

tSASRemarkPolicyDot1POutProfile OBJECT-TYPE
    SYNTAX       Dot1PPriority
    MAX-ACCESS   read-write
    STATUS       current
    DESCRIPTION
        "The Dot1p to use for out-of-profile traffic.  This field is valid
         only for the following remarking types:
              dot1p
              dot1p-dscp"
    DEFVAL { -1 }
    ::= { tSASRemarkPolicyFCEntry 3 }

tSASRemarkPolicyDSCPInProfile OBJECT-TYPE
    SYNTAX       TDSCPNameOrEmpty
    MAX-ACCESS   read-write
    STATUS       current
    DESCRIPTION
        "The DSCP to use for in-profile traffic.  This field is valid
         only for remarking type of dscp and dot1p-dscp."
    DEFVAL { ''H }
    ::= { tSASRemarkPolicyFCEntry 4 }

tSASRemarkPolicyDSCPOutProfile OBJECT-TYPE
    SYNTAX       TDSCPNameOrEmpty
    MAX-ACCESS   read-write
    STATUS       current
    DESCRIPTION
        "The DSCP to use for out-of-profile traffic.  This field is valid
         only for remarking type of dscp and dot1p-dscp."
    DEFVAL { ''H }
    ::= { tSASRemarkPolicyFCEntry 5 }

tSASRemarkPolicyLspExpInProfile OBJECT-TYPE
    SYNTAX       TLspExpValue
    MAX-ACCESS   read-write
    STATUS       current
    DESCRIPTION
        "The lsp-exp value to use for in-profile traffic.  This field is 
         valid only for remarking type of lsp-exp."
    DEFVAL { -1 }
    ::= { tSASRemarkPolicyFCEntry 6 }

tSASRemarkPolicyLspExpOutProfile OBJECT-TYPE
    SYNTAX       TLspExpValue
    MAX-ACCESS   read-write
    STATUS       current
    DESCRIPTION
        "The lsp-exp value to use for out-of-profile traffic.  This field is 
         valid only for remarking type of lsp-exp."
    DEFVAL { -1 }
    ::= { tSASRemarkPolicyFCEntry 7 }

tSASRemarkPolicyDot1PLspExpInProfile OBJECT-TYPE
    SYNTAX       TDot1PLspExpValue
    MAX-ACCESS   read-write
    STATUS       current
    DESCRIPTION
        "The Dot1p / MPLS Exp value to use for in-profile traffic.  
         This field is valid only for remarking type of dot1p-lsp-exp-shared."
    DEFVAL { -1 }
    ::= { tSASRemarkPolicyFCEntry 8 }

tSASRemarkPolicyDot1PLspExpOutProfile OBJECT-TYPE
    SYNTAX       TDot1PLspExpValue
    MAX-ACCESS   read-write
    STATUS       current
    DESCRIPTION
        "The Dot1p / MPLS Exp value to use for out-profile traffic.  
         This field is valid only for remarking type of dot1p-lsp-exp-shared."
    DEFVAL { -1 }
    ::= { tSASRemarkPolicyFCEntry 9 }

tSASRemarkPolicyDot1PProfile OBJECT-TYPE
    SYNTAX       Dot1PPriority
    MAX-ACCESS   read-write
    STATUS       current
    DESCRIPTION
        "The Dot1p to use for profile traffic. "
    DEFVAL { -1 }
    ::= { tSASRemarkPolicyFCEntry 10 }

tSASRemarkPolicyForceDEValue OBJECT-TYPE
    SYNTAX       TDEValue
    MAX-ACCESS   read-write
    STATUS       current
    DESCRIPTION
        "The value of tSASRemarkPolicyForceDEValue specifies the DE value to set
        for remark packets in this forwarding class regardless of
        profile status of the frames.

       An inconsistentValue error is returned if this object is set to any value
       other than '-1', when tSASRemarkFCDEMark object is set to
       'false'."
    DEFVAL { -1 }
    ::= { tSASRemarkPolicyFCEntry 11 }

tSASRemarkPolicyFCDEMark OBJECT-TYPE
    SYNTAX       TruthValue
    MAX-ACCESS   read-write
    STATUS       current
    DESCRIPTION
       "The value of tSASRemarkPolicyFCDEMark specifies whether to set DE value
       in the frames of this forwarding class.

       An inconsistentValue error is returned if this object is set to 'false'
       when tSASRemarkPolicyFCForceDEValue object is not set to '-1'."
    DEFVAL { false }
    ::= { tSASRemarkPolicyFCEntry 12 }

tSASRemarkPolicyDot1PInner OBJECT-TYPE
    SYNTAX       Dot1PPriority
    MAX-ACCESS   read-write
    STATUS       current
    DESCRIPTION
        "The Dot1p to use for in-profile/out-profile traffic.  This field is valid
         only for the following remarking types:
              dot1p
              dot1p-dscp"
    DEFVAL { -1 }
    ::= { tSASRemarkPolicyFCEntry 13 }

tSASRemarkPolicyDot1PInnerInProfile OBJECT-TYPE
    SYNTAX       Dot1PPriority
    MAX-ACCESS   read-write
    STATUS       current
    DESCRIPTION
        "The Dot1p to use for in-profile traffic.  This field is valid
         only for the following remarking types:
              dot1p
              dot1p-dscp"
    DEFVAL { -1 }
    ::= { tSASRemarkPolicyFCEntry 14 }

tSASRemarkPolicyDot1PInnerOutProfile OBJECT-TYPE
    SYNTAX       Dot1PPriority
    MAX-ACCESS   read-write
    STATUS       current
    DESCRIPTION
        "The Dot1p to use for out-profile traffic.  This field is valid
         only for the following remarking types:
              dot1p
              dot1p-dscp"
    DEFVAL { -1 }
    ::= { tSASRemarkPolicyFCEntry 15 }

tSASRemarkPolicyDot1POuter OBJECT-TYPE
    SYNTAX       Dot1PPriority
    MAX-ACCESS   read-write
    STATUS       current
    DESCRIPTION
        "The Dot1p to use for in-profile/out-profile traffic.  This field is valid
         only for the following remarking types:
              dot1p
              dot1p-dscp"
    DEFVAL { -1 }
    ::= { tSASRemarkPolicyFCEntry 16 }

tSASRemarkPolicyDot1POuterInProfile OBJECT-TYPE
    SYNTAX       Dot1PPriority
    MAX-ACCESS   read-write
    STATUS       current
    DESCRIPTION
        "The Dot1p to use for in-profile traffic.  This field is valid
         only for the following remarking types:
              dot1p
              dot1p-dscp"
    DEFVAL { -1 }
    ::= { tSASRemarkPolicyFCEntry 17 }

tSASRemarkPolicyDot1POuterOutProfile OBJECT-TYPE
    SYNTAX       Dot1PPriority
    MAX-ACCESS   read-write
    STATUS       current
    DESCRIPTION
        "The Dot1p to use for out-profile traffic.  This field is valid
         only for the following remarking types:
              dot1p
              dot1p-dscp"
    DEFVAL { -1 }
    ::= { tSASRemarkPolicyFCEntry 18 }

--
-- QoS Dot1P Classification policy table
--

tSASDot1PClassificationPolicyTable OBJECT-TYPE
    SYNTAX       SEQUENCE OF TSASDot1PClassificationPolicyEntry
    MAX-ACCESS   not-accessible
    STATUS       current
    DESCRIPTION  "  "
    ::= { tSASGeneralQosObjects 3 }  

tSASDot1PClassificationPolicyEntry OBJECT-TYPE
    SYNTAX       TSASDot1PClassificationPolicyEntry
    MAX-ACCESS   not-accessible
    STATUS       current
    DESCRIPTION
        "Information about a particular dot1p classification policy's
         forwarding class mappings to dot1p / dscp / exp 
         values.
         Entries are created/deleted by user."
    INDEX { tSASDot1PClassificationPolicyId }
    ::= { tSASDot1PClassificationPolicyTable 1 }

TSASDot1PClassificationPolicyEntry ::= SEQUENCE
    {
        tSASDot1PClassificationPolicyId                TClassificationPolicyID,
        tSASDot1PClassificationPolicyRowStatus         RowStatus,
        tSASDot1PClassificationPolicyDescription       TItemDescription,
        tSASDot1PClassificationPolicyLastChanged       TimeStamp
    }

tSASDot1PClassificationPolicyId OBJECT-TYPE
    SYNTAX       TClassificationPolicyID
    MAX-ACCESS   not-accessible
    STATUS       current
    DESCRIPTION
        "The Dot1P classification policy ID is used as index for the table."
    ::= { tSASDot1PClassificationPolicyEntry 1 }

tSASDot1PClassificationPolicyRowStatus OBJECT-TYPE
    SYNTAX       RowStatus
    MAX-ACCESS   read-create
    STATUS       current
    DESCRIPTION
        "Row Status."
    ::= { tSASDot1PClassificationPolicyEntry 2 }

tSASDot1PClassificationPolicyDescription OBJECT-TYPE
    SYNTAX       TItemDescription
    MAX-ACCESS   read-create
    STATUS       current
    DESCRIPTION
        "User-provided description of the policy."
    DEFVAL { ''H }
    ::= { tSASDot1PClassificationPolicyEntry 3 }

tSASDot1PClassificationPolicyLastChanged OBJECT-TYPE
    SYNTAX       TimeStamp
    MAX-ACCESS   read-only
    STATUS       current
    DESCRIPTION
        "timestamp of last change to this row in tSASDot1PClassificationPolicyTable."
    ::= { tSASDot1PClassificationPolicyEntry 4 }


--
-- Dot1P Classification dot1p table
--

tSASDot1PClassificationDot1PTable OBJECT-TYPE
    SYNTAX       SEQUENCE OF TSASDot1PClassificationDot1PEntry
    MAX-ACCESS   not-accessible
    STATUS       current
    DESCRIPTION
        "a list of all dot1p entries for all dot1p-classification policies."
    ::= { tSASGeneralQosObjects 4 }  

tSASDot1PClassificationDot1PEntry OBJECT-TYPE
    SYNTAX       TSASDot1PClassificationDot1PEntry
    MAX-ACCESS   not-accessible
    STATUS       current
    DESCRIPTION
        "Information about a particular dot1p match for a dot1p-classification policy.
         Entries are created by user.

         There is no StorageType object, entries have a presumed
         StorageType of nonVolatile.
        "
    INDEX { tSASDot1PClassificationPolicyId, tSASDot1PClassificationDot1PValue }
    ::= { tSASDot1PClassificationDot1PTable 1 }

TSASDot1PClassificationDot1PEntry ::= SEQUENCE
    {
        tSASDot1PClassificationDot1PValue               Dot1PPriority,
        tSASDot1PClassificationDot1PRowStatus           RowStatus,
        tSASDot1PClassificationDot1PFC                  TNamedItemOrEmpty,
        tSASDot1PClassificationDot1PProfile             TProfileOrNone,
        tSASDot1PClassificationDot1PLastChanged         TimeStamp
    }

tSASDot1PClassificationDot1PValue OBJECT-TYPE
    SYNTAX       Dot1PPriority (0..7)
    MAX-ACCESS   not-accessible
    STATUS       current
    DESCRIPTION
        "dot1p value to match in the packet.  this value is
        also used as an index so that for any dot1p value there
        is only one possible disposition queue and priority.
        "
    ::= { tSASDot1PClassificationDot1PEntry 1 }

tSASDot1PClassificationDot1PRowStatus OBJECT-TYPE
    SYNTAX       RowStatus
    MAX-ACCESS   read-create
    STATUS       current
    DESCRIPTION
        "Row Status for this dot1p-classification policy's dot1p entry."
    ::= { tSASDot1PClassificationDot1PEntry 2 }

tSASDot1PClassificationDot1PFC OBJECT-TYPE
    SYNTAX       TNamedItemOrEmpty
    MAX-ACCESS   read-create
    STATUS       current
    DESCRIPTION
        "tSASDot1PClassificationDot1PFC specifies the forwarding class or the sub
         forwarding class to be used to classify all the traffic that
         matches the specific Dot1p i.e. tSASDot1PClassificationDot1PValue.

         Specification of a sub forwarding class is also allowed. The
         format of a sub forwarding class is the concatenation of the
         base forwarding class and a sub class identifier in the form

             base-fc-name[.sub-fc-name]

         To reference a sub forwarding class, the mapping of the sub
         forwarding class should be existing in this QoS policy.

         Unless tSASDot1PClassificationDot1PFC is specified explicitly, this match
         will be ignored for classification purposes."
    DEFVAL { ''H }
    ::= { tSASDot1PClassificationDot1PEntry 3 }

tSASDot1PClassificationDot1PProfile  OBJECT-TYPE
    SYNTAX       TProfileOrNone
    MAX-ACCESS   read-create
    STATUS       current
    DESCRIPTION
        "priority to use for packets that match the dot1p value
        tSASDot1PClassificationDot1PValue."
    DEFVAL { none }
    ::= { tSASDot1PClassificationDot1PEntry 4 }

tSASDot1PClassificationDot1PLastChanged OBJECT-TYPE
    SYNTAX       TimeStamp
    MAX-ACCESS   read-only
    STATUS       current
    DESCRIPTION
        "timestamp of last change to this row in tSASDot1PClassificationDot1PTable."
    ::= { tSASDot1PClassificationDot1PEntry 5 }

--
-- QoS Dscp Classification policy table
--

tSASDscpClassificationPolicyTable OBJECT-TYPE
    SYNTAX       SEQUENCE OF TSASDscpClassificationPolicyEntry
    MAX-ACCESS   not-accessible
    STATUS       current
    DESCRIPTION  "  "
    ::= { tSASGeneralQosObjects 5 }  

tSASDscpClassificationPolicyEntry OBJECT-TYPE
    SYNTAX       TSASDscpClassificationPolicyEntry
    MAX-ACCESS   not-accessible
    STATUS       current
    DESCRIPTION
        "Information about a particular dscp classification policy's
         forwarding class mappings to dot1p / dscp / exp 
         values.
         Entries are created/deleted by user."
    INDEX { tSASDscpClassificationPolicyId }
    ::= { tSASDscpClassificationPolicyTable 1 }

TSASDscpClassificationPolicyEntry ::= SEQUENCE
    {
        tSASDscpClassificationPolicyId                TClassificationPolicyID,
        tSASDscpClassificationPolicyRowStatus         RowStatus,
        tSASDscpClassificationPolicyDescription       TItemDescription,
        tSASDscpClassificationPolicyLastChanged       TimeStamp
    }

tSASDscpClassificationPolicyId OBJECT-TYPE
    SYNTAX       TClassificationPolicyID
    MAX-ACCESS   not-accessible
    STATUS       current
    DESCRIPTION
        "The Dscp classification policy ID is used as index for the table."
    ::= { tSASDscpClassificationPolicyEntry 1 }

tSASDscpClassificationPolicyRowStatus OBJECT-TYPE
    SYNTAX       RowStatus
    MAX-ACCESS   read-create
    STATUS       current
    DESCRIPTION
        "Row Status."
    ::= { tSASDscpClassificationPolicyEntry 2 }

tSASDscpClassificationPolicyDescription OBJECT-TYPE
    SYNTAX       TItemDescription
    MAX-ACCESS   read-create
    STATUS       current
    DESCRIPTION
        "User-provided description of the policy."
    DEFVAL { ''H }
    ::= { tSASDscpClassificationPolicyEntry 3 }

tSASDscpClassificationPolicyLastChanged OBJECT-TYPE
    SYNTAX       TimeStamp
    MAX-ACCESS   read-only
    STATUS       current
    DESCRIPTION
        "timestamp of last change to this row in tSASDscpClassificationPolicyTable."
    ::= { tSASDscpClassificationPolicyEntry 4 }


--
-- Dscp Classification Policy dscp table
--

tSASDscpClassificationDscpTable OBJECT-TYPE
    SYNTAX       SEQUENCE OF TSASDscpClassificationDscpEntry
    MAX-ACCESS   not-accessible
    STATUS       current
    DESCRIPTION
        "a list of all dscp entries for all dscp-classification policies."
    ::= { tSASGeneralQosObjects 6 }  

tSASDscpClassificationDscpEntry OBJECT-TYPE
    SYNTAX       TSASDscpClassificationDscpEntry
    MAX-ACCESS   not-accessible
    STATUS       current
    DESCRIPTION
        "Information about a particular dscp match for a dscp-classification policy.
         Entries are created by user.

         There is no StorageType object, entries have a presumed
         StorageType of nonVolatile.
        "
    INDEX { tSASDscpClassificationPolicyId, tSASDscpClassificationDscpName }
    ::= { tSASDscpClassificationDscpTable 1 }

TSASDscpClassificationDscpEntry ::= SEQUENCE
    {
        tSASDscpClassificationDscpName                TDSCPName,
        tSASDscpClassificationDscpRowStatus           RowStatus,
        tSASDscpClassificationDscpFC                  TNamedItemOrEmpty,
        tSASDscpClassificationDscpProfile             TProfileOrNone,
        tSASDscpClassificationDscpLastChanged         TimeStamp
    }

tSASDscpClassificationDscpName OBJECT-TYPE
    SYNTAX       TDSCPName
    MAX-ACCESS   not-accessible
    STATUS       current
    DESCRIPTION
        " 
        "
    ::= { tSASDscpClassificationDscpEntry 1 }

tSASDscpClassificationDscpRowStatus OBJECT-TYPE
    SYNTAX       RowStatus
    MAX-ACCESS   read-create
    STATUS       current
    DESCRIPTION
        "Row Status for this dscp-classification policy's dscp entry."
    ::= { tSASDscpClassificationDscpEntry 2 }

tSASDscpClassificationDscpFC OBJECT-TYPE
    SYNTAX       TNamedItemOrEmpty
    MAX-ACCESS   read-create
    STATUS       current
    DESCRIPTION
        "tSASDscpClassificationDscpFC specifies the forwarding class or the sub
         forwarding class to be used to classify all the traffic that
         matches the specific Dot1p i.e. tSASDscpClassificationDscpValue.

         Specification of a sub forwarding class is also allowed. The
         format of a sub forwarding class is the concatenation of the
         base forwarding class and a sub class identifier in the form

             base-fc-name[.sub-fc-name]

         To reference a sub forwarding class, the mapping of the sub
         forwarding class should be existing in this QoS policy.

         Unless tSASDscpClassificationDscpFC is specified explicitly, this match
         will be ignored for classification purposes."
    DEFVAL { ''H }
    ::= { tSASDscpClassificationDscpEntry 3 }

tSASDscpClassificationDscpProfile  OBJECT-TYPE
    SYNTAX       TProfileOrNone
    MAX-ACCESS   read-create
    STATUS       current
    DESCRIPTION
        "priority to use for packets that match the dscp value
        tSASDscpClassificationDscpValue."
    DEFVAL { none }
    ::= { tSASDscpClassificationDscpEntry 4 }

tSASDscpClassificationDscpLastChanged OBJECT-TYPE
    SYNTAX       TimeStamp
    MAX-ACCESS   read-only
    STATUS       current
    DESCRIPTION
        "timestamp of last change to this row in tSASDscpClassificationDscpTable."
    ::= { tSASDscpClassificationDscpEntry 5 }


--
-- QoS MplsLspExp Classification policy table
--

tSASMplsLspExpClassificationPolicyTable OBJECT-TYPE
    SYNTAX       SEQUENCE OF TSASMplsLspExpClassificationPolicyEntry
    MAX-ACCESS   not-accessible
    STATUS       current
    DESCRIPTION  "  "
    ::= { tSASGeneralQosObjects 7 }  

tSASMplsLspExpClassificationPolicyEntry OBJECT-TYPE
    SYNTAX       TSASMplsLspExpClassificationPolicyEntry
    MAX-ACCESS   not-accessible
    STATUS       current
    DESCRIPTION
        "Information about a particular mpls-lsp-exp classification policy's
         forwarding class mappings to mpls-lsp-exp / dscp / exp 
         values.
         Entries are created/deleted by user."
    INDEX { tSASMplsLspExpClassificationPolicyId }
    ::= { tSASMplsLspExpClassificationPolicyTable 1 }

TSASMplsLspExpClassificationPolicyEntry ::= SEQUENCE
    {
        tSASMplsLspExpClassificationPolicyId                TClassificationPolicyID,
        tSASMplsLspExpClassificationPolicyRowStatus         RowStatus,
        tSASMplsLspExpClassificationPolicyDescription       TItemDescription,
        tSASMplsLspExpClassificationPolicyLastChanged       TimeStamp
    }

tSASMplsLspExpClassificationPolicyId OBJECT-TYPE
    SYNTAX       TClassificationPolicyID
    MAX-ACCESS   not-accessible
    STATUS       current
    DESCRIPTION
        "The MplsLspExp classification policy ID is used as index for the table."
    ::= { tSASMplsLspExpClassificationPolicyEntry 1 }

tSASMplsLspExpClassificationPolicyRowStatus OBJECT-TYPE
    SYNTAX       RowStatus
    MAX-ACCESS   read-create
    STATUS       current
    DESCRIPTION
        "Row Status."
    ::= { tSASMplsLspExpClassificationPolicyEntry 2 }

tSASMplsLspExpClassificationPolicyDescription OBJECT-TYPE
    SYNTAX       TItemDescription
    MAX-ACCESS   read-create
    STATUS       current
    DESCRIPTION
        "User-provided description of the policy."
    DEFVAL { ''H }
    ::= { tSASMplsLspExpClassificationPolicyEntry 3 }

tSASMplsLspExpClassificationPolicyLastChanged OBJECT-TYPE
    SYNTAX       TimeStamp
    MAX-ACCESS   read-only
    STATUS       current
    DESCRIPTION
        "timestamp of last change to this row in tSASMplsLspExpClassificationPolicyTable."
    ::= { tSASMplsLspExpClassificationPolicyEntry 4 }


--
-- MplsLspExp Classification Lsp Exp table
--

tSASMplsLspExpClassificationLspExpTable OBJECT-TYPE
    SYNTAX       SEQUENCE OF TSASMplsLspExpClassificationLspExpEntry
    MAX-ACCESS   not-accessible
    STATUS       current
    DESCRIPTION
        "a list of all mpls-lsp-exp entries for all mpls-lsp-exp-classification policies."
    ::= { tSASGeneralQosObjects 8 }  

tSASMplsLspExpClassificationLspExpEntry OBJECT-TYPE
    SYNTAX       TSASMplsLspExpClassificationLspExpEntry
    MAX-ACCESS   not-accessible
    STATUS       current
    DESCRIPTION
        "Information about a particular mpls-lsp-exp match for a mpls-lsp-exp-classification policy.
         Entries are created by user.

         There is no StorageType object, entries have a presumed
         StorageType of nonVolatile.
        "
    INDEX { tSASMplsLspExpClassificationPolicyId, tSASMplsLspExpClassificationLspExpValue }
    ::= { tSASMplsLspExpClassificationLspExpTable 1 }

TSASMplsLspExpClassificationLspExpEntry ::= SEQUENCE
    {
        tSASMplsLspExpClassificationLspExpValue               TMplsLspExpProfileValue,
        tSASMplsLspExpClassificationLspExpRowStatus           RowStatus,
        tSASMplsLspExpClassificationLspExpFC                  TNamedItemOrEmpty,
        tSASMplsLspExpClassificationLspExpProfile             TProfileOrNone,
        tSASMplsLspExpClassificationLspExpLastChanged         TimeStamp
    }

tSASMplsLspExpClassificationLspExpValue OBJECT-TYPE
    SYNTAX       TMplsLspExpProfileValue (0..7)
    MAX-ACCESS   not-accessible
    STATUS       current
    DESCRIPTION
        "mpls-lsp-exp value to match in the packet.  this value is
        also used as an index so that for any mpls-lsp-exp value there
        is only one possible disposition queue and priority.
        "
    ::= { tSASMplsLspExpClassificationLspExpEntry 1 }

tSASMplsLspExpClassificationLspExpRowStatus OBJECT-TYPE
    SYNTAX       RowStatus
    MAX-ACCESS   read-create
    STATUS       current
    DESCRIPTION
        "Row Status for this mpls-lsp-exp-classification policy's mpls-lsp-exp entry."
    ::= { tSASMplsLspExpClassificationLspExpEntry 2 }

tSASMplsLspExpClassificationLspExpFC OBJECT-TYPE
    SYNTAX       TNamedItemOrEmpty
    MAX-ACCESS   read-create
    STATUS       current
    DESCRIPTION
        "tSASMplsLspExpClassificationLspExpFC specifies the forwarding class or the sub
         forwarding class to be used to classify all the traffic that
         matches the specific MplsLspExp i.e. tSASMplsLspExpClassificationLspExpValue.

         Specification of a sub forwarding class is also allowed. The
         format of a sub forwarding class is the concatenation of the
         base forwarding class and a sub class identifier in the form

             base-fc-name[.sub-fc-name]

         To reference a sub forwarding class, the mapping of the sub
         forwarding class should be existing in this QoS policy.

         Unless tSASMplsLspExpClassificationLspExpFC is specified explicitly, this match
         will be ignored for classification purposes."
    DEFVAL { ''H }
    ::= { tSASMplsLspExpClassificationLspExpEntry 3 }

tSASMplsLspExpClassificationLspExpProfile  OBJECT-TYPE
    SYNTAX       TProfileOrNone
    MAX-ACCESS   read-create
    STATUS       current
    DESCRIPTION
        "priority to use for packets that match the mpls-lsp-exp value
        tSASMplsLspExpClassificationLspExpValue."
    DEFVAL { none }
    ::= { tSASMplsLspExpClassificationLspExpEntry 4 }

tSASMplsLspExpClassificationLspExpLastChanged OBJECT-TYPE
    SYNTAX       TimeStamp
    MAX-ACCESS   read-only
    STATUS       current
    DESCRIPTION
        "timestamp of last change to this row in tSASMplsLspExpClassificationLspExpTable."
    ::= { tSASMplsLspExpClassificationLspExpEntry 5 }


tSapIngressQueueExtnTable OBJECT-TYPE
    SYNTAX          SEQUENCE OF TSapIngressQueueExtnEntry
    MAX-ACCESS      not-accessible
    STATUS          current
    DESCRIPTION     
        "Extension table to tSapIngressQueueTable"
    ::= { tSASSapIngressObjects 5 }

tSapIngressQueueExtnEntry OBJECT-TYPE
    SYNTAX          TSapIngressQueueExtnEntry
    MAX-ACCESS      not-accessible
    STATUS          current
    DESCRIPTION     ""
    AUGMENTS   { tSapIngressQueueEntry }
    ::= { tSapIngressQueueExtnTable 1 }

TSapIngressQueueExtnEntry ::=
    SEQUENCE {
        tSapIngressQueuePolicyName          TNamedItem,
        tSapIngressQueueMBSAbsolute         INTEGER
    }

tSapIngressQueuePolicyName  OBJECT-TYPE
    SYNTAX       TNamedItem 
    MAX-ACCESS   read-create
    STATUS       current
    DESCRIPTION
        "SapIngressQueuePolicyName determines the queue management policy
        attached to this SAP Ingress queue."
    DEFVAL { "default" }
    ::= { tSapIngressQueueExtnEntry 1 }

tSapIngressQueueMBSAbsolute OBJECT-TYPE
    SYNTAX       INTEGER (-1 | 0..12800)
    MAX-ACCESS   read-create
    STATUS       current
    DESCRIPTION
        "The maximum amount of buffer space (in kilo bytes) allowed for the
         queue.

         This object has been replaced with tSapIngressQueueMBSBytes object."
    DEFVAL { -1 }
    ::= { tSapIngressQueueExtnEntry 2 }

---

tSapIngressIPCriteriaExtnTable OBJECT-TYPE
    SYNTAX       SEQUENCE OF TSapIngressIPCriteriaExtnEntry
    MAX-ACCESS   not-accessible
    STATUS       current
    DESCRIPTION
        "information about sap-ingress policies extenstion to
        tSapIngressIPCriteriaEntry"
    ::= { tSASSapIngressObjects 6 }

tSapIngressIPCriteriaExtnEntry OBJECT-TYPE
    SYNTAX       TSapIngressIPCriteriaExtnEntry
    MAX-ACCESS   not-accessible
    STATUS       current
    DESCRIPTION
        "Information about a particular ip-criteria entry for a sap-ingress
         policy. This is an extenstion to tSapIngressIPCriteriaEntry.
        "
    AUGMENTS { tSapIngressIPCriteriaEntry }
    ::= { tSapIngressIPCriteriaExtnTable 1 }

TSapIngressIPCriteriaExtnEntry ::= SEQUENCE
    {
        tSapIngressIPCriteriaActionProfile      TProfileOrDeiOrNone,
        tSapIngressIPCriteriaDSCPVal            TDSCPValueOrNone,
        tSapIngressIPCriteriaDSCPMask           TDSCPValueOrNone
    }
    
tSapIngressIPCriteriaActionProfile OBJECT-TYPE
    SYNTAX       TProfileOrDeiOrNone
    MAX-ACCESS   read-create
    STATUS       current
    DESCRIPTION
        "tSapIngressIPCriteriaActionProfile specifies the profile of the
         traffic that matches the specific IP criteria.

         The value none indicates that the profile is derived
         from ingress classification and profiling functions."
    DEFVAL { none }
    ::= { tSapIngressIPCriteriaExtnEntry 1 }    

tSapIngressIPCriteriaDSCPVal OBJECT-TYPE
    SYNTAX       TDSCPValueOrNone
    MAX-ACCESS   read-create
    STATUS       current
    DESCRIPTION
        "tSapIngressIPCriteriaDSCPVal specifies the dscp value of the
         traffic that matches the specific IP criteria."
    DEFVAL { -1 }
    ::= { tSapIngressIPCriteriaExtnEntry 33 }    

tSapIngressIPCriteriaDSCPMask OBJECT-TYPE
    SYNTAX       TDSCPValueOrNone
    MAX-ACCESS   read-create
    STATUS       current
    DESCRIPTION
        "tSapIngressIPCriteriaDSCPMask specifies the dscp mask of the
         traffic that matches the specific IP criteria."
    DEFVAL { 0 }
    ::= { tSapIngressIPCriteriaExtnEntry 34 }    

---

tSapIngressMacCriteriaExtnTable OBJECT-TYPE
    SYNTAX       SEQUENCE OF TSapIngressMacCriteriaExtnEntry
    MAX-ACCESS   not-accessible
    STATUS       current
    DESCRIPTION
        "Information about mac-criteria entries. 
        Extenstion to tSapIngressMacCriteriaEntry"
    ::= { tSASSapIngressObjects 7 }

tSapIngressMacCriteriaExtnEntry OBJECT-TYPE
    SYNTAX       TSapIngressMacCriteriaExtnEntry
    MAX-ACCESS   not-accessible
    STATUS       current
    DESCRIPTION
        "Information about a particular mac-criteria entry
         for a sap-ingress policy.
         Entries are created by user.
         Entries are deleted by user.
         There is no StorageType object, entries have a presumed
         StorageType of nonVolatile."
    AUGMENTS { tSapIngressMacCriteriaEntry }
    ::= { tSapIngressMacCriteriaExtnTable 1 }

TSapIngressMacCriteriaExtnEntry ::= SEQUENCE
    {
        tSapIngressMacCriteriaActionProfile      TProfileOrDeiOrNone,
        tSapIngressMacCriteriaInnerDot1PValue    Dot1PPriority,
        tSapIngressMacCriteriaInnerDot1PMask     Dot1PPriority,
        tSapIngressMacCriteriaOuterDot1PValue    Dot1PPriority,
        tSapIngressMacCriteriaOuterDot1PMask     Dot1PPriority
    }
    
tSapIngressMacCriteriaActionProfile OBJECT-TYPE
    SYNTAX       TProfileOrDeiOrNone
    MAX-ACCESS   read-create
    STATUS       current
    DESCRIPTION
        "tSapIngressMacCriteriaActionProfile specifies the profile of the
         traffic that matches the specific MAC criteria.

         The value none indicates that the profile is derived
         from ingress classification and profiling functions."
    DEFVAL { none }
    ::= { tSapIngressMacCriteriaExtnEntry 1 }    

tSapIngressMacCriteriaInnerDot1PValue OBJECT-TYPE
    SYNTAX       Dot1PPriority
    MAX-ACCESS   read-create
    STATUS       current
    DESCRIPTION ""
    DEFVAL { -1 }
    ::= { tSapIngressMacCriteriaExtnEntry 2 }

tSapIngressMacCriteriaInnerDot1PMask OBJECT-TYPE
    SYNTAX       Dot1PPriority (0..7)
    MAX-ACCESS   read-create
    STATUS       current
    DESCRIPTION ""
    DEFVAL { 0 }
    ::= { tSapIngressMacCriteriaExtnEntry 3 }

tSapIngressMacCriteriaOuterDot1PValue OBJECT-TYPE
    SYNTAX       Dot1PPriority
    MAX-ACCESS   read-create
    STATUS       current
    DESCRIPTION ""
    DEFVAL { -1 }
    ::= { tSapIngressMacCriteriaExtnEntry 4 }

tSapIngressMacCriteriaOuterDot1PMask OBJECT-TYPE
    SYNTAX       Dot1PPriority (0..7)
    MAX-ACCESS   read-create
    STATUS       current
    DESCRIPTION ""
    DEFVAL { 0 }
    ::= { tSapIngressMacCriteriaExtnEntry 5 }

---

tSapIngressIPv6CriteriaExtnTable OBJECT-TYPE
    SYNTAX       SEQUENCE OF TSapIngressIPv6CriteriaExtnEntry
    MAX-ACCESS   not-accessible
    STATUS       current
    DESCRIPTION
        "information about sap-ingress policies extenstion to
        tSapIngressIPv6CriteriaEntry"
    ::= { tSASSapIngressObjects 8 }

tSapIngressIPv6CriteriaExtnEntry OBJECT-TYPE
    SYNTAX       TSapIngressIPv6CriteriaExtnEntry
    MAX-ACCESS   not-accessible
    STATUS       current
    DESCRIPTION
        "Information about a particular ip-criteria entry for a sap-ingress
         policy. This is an extenstion to tSapIngressIPv6CriteriaEntry.
        "
    AUGMENTS { tSapIngressIPv6CriteriaEntry }
    ::= { tSapIngressIPv6CriteriaExtnTable 1 }

TSapIngressIPv6CriteriaExtnEntry ::= SEQUENCE
    {
        tSapIngressIPv6CriteriaActionProfile      TProfileOrDeiOrNone,
        tSapIngressIPv6CriteriaDSCPVal            TDSCPValueOrNone,
        tSapIngressIPv6CriteriaDSCPMask           TDSCPValueOrNone
    }
    
tSapIngressIPv6CriteriaActionProfile OBJECT-TYPE
    SYNTAX       TProfileOrDeiOrNone
    MAX-ACCESS   read-create
    STATUS       current
    DESCRIPTION
        "tSapIngressIPv6CriteriaActionProfile specifies the profile of the
         traffic that matches the specific IP criteria.

         The value none indicates that the profile is derived
         from ingress classification and profiling functions."
    DEFVAL { none }
    ::= { tSapIngressIPv6CriteriaExtnEntry 1 }
    
tSapIngressIPv6CriteriaDSCPVal OBJECT-TYPE
    SYNTAX       TDSCPValueOrNone
    MAX-ACCESS   read-create
    STATUS       current
    DESCRIPTION
        "tSapIngressIPv6CriteriaDSCPVal specifies the dscp value of the
         traffic that matches the specific IP criteria."
    DEFVAL { -1 }
    ::= { tSapIngressIPv6CriteriaExtnEntry 2 }    

tSapIngressIPv6CriteriaDSCPMask OBJECT-TYPE
    SYNTAX       TDSCPValueOrNone
    MAX-ACCESS   read-create
    STATUS       current
    DESCRIPTION
        "tSapIngressIPv6CriteriaDSCPMask specifies the dscp mask of the
         traffic that matches the specific IP criteria."
    DEFVAL { 0 }
    ::= { tSapIngressIPv6CriteriaExtnEntry 3 }    

--
-- Conformance Information
--

tmnxSASQosCompliances OBJECT IDENTIFIER ::= { tmnxSASQosConformance 1 }
tmnxSASQosGroups      OBJECT IDENTIFIER ::= { tmnxSASQosConformance 2 }

tmnxSASQoSV1v0Group OBJECT-GROUP
    OBJECTS    {
        tAccessEgressRowStatus,
        tAccessEgressScope,
        tAccessEgressDescription,
        tAccessEgressLastChanged,
        tAccessEgressRemark,
        tAccessEgressQueueRowStatus,
        tAccessEgressQueueCBS,
        tAccessEgressQueueMBS,
        tAccessEgressQueuePIRAdaptation,
        tAccessEgressQueueCIRAdaptation,
        tAccessEgressQueueAdminPIR,
        tAccessEgressQueueAdminCIR,
        tAccessEgressQueueOperPIR,
        tAccessEgressQueueOperCIR,
        tAccessEgressQueueLastChanged,
        tAccessEgressFCRowStatus,
        tAccessEgressFCQueue,
        tAccessEgressFCDot1PInProfile,
        tAccessEgressFCDot1POutProfile,
        tAccessEgressFCLastChanged,
        tSapIngressMeterRowStatus,
        tSapIngressMeterMCast,
        tSapIngressMeterAdminCBS,
        tSapIngressMeterAdminMBS,
        tSapIngressMeterOperCBS,
        tSapIngressMeterOperMBS,
        tSapIngressMeterCIRAdaptation,
        tSapIngressMeterPIRAdaptation,
        tSapIngressMeterAdminPIR,
        tSapIngressMeterAdminCIR,
        tSapIngressMeterOperPIR,
        tSapIngressMeterOperCIR,
        tSapIngressMeterLastChanged,
        tSapIngressMeterMode,
        tSapIngressMeterRateMode,
        tNetworkIngressFCExtnRowStatus,
        tNetworkIngressFCExtnMeter,
        tNetworkIngressFCExtnMCastMeter,
        tNetworkIngressFCExtnLastChanged,
        tNetworkIngressMeterRowStatus,
        tNetworkIngressMeterAdminCBS,
        tNetworkIngressMeterAdminMBS,
        tNetworkIngressMeterOperCBS,
        tNetworkIngressMeterOperMBS,        
        tNetworkIngressMeterCIRAdaptation,
        tNetworkIngressMeterPIRAdaptation,
        tNetworkIngressMeterAdminPIR,
        tNetworkIngressMeterAdminCIR,
        tNetworkIngressMeterOperPIR,
        tNetworkIngressMeterOperCIR,
        tNetworkIngressMeterLastChanged,
        tNetworkIngressMeterMode,
        tNetworkIngressMeterMCast,
        tNetworkIngressMeterRateMode,
        tSlopeHiQueue1DropRate,
        tSlopeHiQueue2DropRate,
        tSlopeHiQueue3DropRate,
        tSlopeHiQueue4DropRate,
        tSlopeHiQueue5DropRate,
        tSlopeHiQueue6DropRate,
        tSlopeHiQueue7DropRate,
        tSlopeHiQueue8DropRate,
        tSlopeLoQueue1DropRate,
        tSlopeLoQueue2DropRate,
        tSlopeLoQueue3DropRate,
        tSlopeLoQueue4DropRate,
        tSlopeLoQueue5DropRate,
        tSlopeLoQueue6DropRate,
        tSlopeLoQueue7DropRate,
        tSlopeLoQueue8DropRate,
        tSlopeHiStartThreshold,
        tSlopeLoStartThreshold,
        tPortSchedulerPlcyMode,
        tPortSchedulerPlcyQuanta,
        tPortSchedulerPlcyQueue1Weight,
        tPortSchedulerPlcyQueue2Weight,
        tPortSchedulerPlcyQueue3Weight,
        tPortSchedulerPlcyQueue4Weight,
        tPortSchedulerPlcyQueue5Weight,
        tPortSchedulerPlcyQueue6Weight,
        tPortSchedulerPlcyQueue7Weight,
        tPortSchedulerPlcyQueue8Weight,
        tSapIngressFCMeter,       
        tSapIngressFCMCastMeter,  
        tSapIngressFCBCastMeter,  
        tSapIngressFCUnknownMeter,
        sapIngQosMeterId,                          
        sapIngQosMeterStatsForwardedInProfPackets, 
        sapIngQosMeterStatsForwardedOutProfPackets,
        sapIngQosMeterStatsForwardedInProfOctets,  
        sapIngQosMeterStatsForwardedOutProfOctets,
        tQosIngressFrameBasedAccnt,
        tQosEgressFrameBasedAccnt,
        tSapIngressNumQosClassifiers
} 
       STATUS current
       DESCRIPTION 
           " sas group object definition "
       ::= { tmnxSASQosGroups 1 }


tmnxSASMQoSV1v0Group OBJECT-GROUP
    OBJECTS    {
        tSlopePolicyQueueRowStatus,           
        tSlopePolicyQueueLastChanged,         
        tSlopePolicyQueueHiAdminStatus,       
        tSlopePolicyQueueHiStartAverage,      
        tSlopePolicyQueueHiMaxAverage,        
        tSlopePolicyQueueHiMaxProbability,    
        tSlopePolicyQueueLoAdminStatus,       
        tSlopePolicyQueueLoStartAverage,      
        tSlopePolicyQueueLoMaxAverage,        
        tSlopePolicyQueueLoMaxProbability,    
        tSlopePolicyQueueNonTcpAdminStatus,   
        tSlopePolicyQueueNonTcpStartAverage,  
        tSlopePolicyQueueNonTcpMaxAverage,    
        tSlopePolicyQueueNonTcpMaxProbability,
        tSlopePolicyQueueTimeAvgFactor       
     }
       STATUS current
       DESCRIPTION 
           " SAS M specific group object definition "
       ::= { tmnxSASQosGroups 2 }

tmnxSASQoSV2v0Group OBJECT-GROUP
    OBJECTS    {
        tNetworkQueuePolicyName,
        tNetworkPolicyRemarkPolicyId,
        tNetworkPolicyType,
        tSapEgressQueuePolicyName,
        tSapEgressRemarkPolicyId,
        tSapEgressRemark,
        tAccessEgressRemarkPolicyId,
        tSASRemarkPolicyRowStatus,
        tSASRemarkPolicyDescription,
        tSASRemarkPolicyType,
        tSASRemarkPolicyDot1PInProfile,
        tSASRemarkPolicyDot1POutProfile,
        tSASRemarkPolicyDSCPInProfile,
        tSASRemarkPolicyDSCPOutProfile,
        tSASRemarkPolicyLspExpInProfile,
        tSASRemarkPolicyLspExpOutProfile,
        tSASRemarkPolicyDot1PLspExpInProfile,
        tSASRemarkPolicyDot1PLspExpOutProfile,
        tSASRemarkPolicyLastChanged,
        tQueueMgmtPolicyDescription,
        tQueueMgmtPolicyRowStatus,
        tQueueMgmtPolicyLastChanged,
        tQueueMgmtPolicyHiAdminStatus,
        tQueueMgmtPolicyHiStartAverage,
        tQueueMgmtPolicyHiMaxAverage,
        tQueueMgmtPolicyHiMaxProbability,        
        tQueueMgmtPolicyLoAdminStatus,
        tQueueMgmtPolicyLoStartAverage,
        tQueueMgmtPolicyLoMaxAverage,
        tQueueMgmtPolicyLoMaxProbability,
        tQueueMgmtPolicyCBS,
        tQueueMgmtPolicyMBS,
        tQueueMgmtPolicyTimeAvgFactor,
        tQueueMgmtPolicyScope,
        tAccessEgressRowStatus,
        tAccessEgressScope,
        tAccessEgressDescription,
        tAccessEgressLastChanged,
        tAccessEgressRemark,
        tAccessEgressQueueRowStatus,
        tAccessEgressQueueCBS,
        tAccessEgressQueueMBS,
        tAccessEgressQueuePIRAdaptation,
        tAccessEgressQueueCIRAdaptation,
        tAccessEgressQueueAdminPIR,
        tAccessEgressQueueAdminCIR,
        tAccessEgressQueueOperPIR,
        tAccessEgressQueueOperCIR,
        tAccessEgressQueueLastChanged,
        tAccessEgressFCRowStatus,
        tAccessEgressFCQueue,
        tAccessEgressFCDot1PInProfile,
        tAccessEgressFCDot1POutProfile,
        tAccessEgressFCLastChanged,
        tSapIngressMeterRowStatus,
        tSapIngressMeterMCast,
        tSapIngressMeterAdminCBS,
        tSapIngressMeterAdminMBS,
        tSapIngressMeterOperCBS,
        tSapIngressMeterOperMBS,
        tSapIngressMeterCIRAdaptation,
        tSapIngressMeterPIRAdaptation,
        tSapIngressMeterAdminPIR,
        tSapIngressMeterAdminCIR,
        tSapIngressMeterOperPIR,
        tSapIngressMeterOperCIR,
        tSapIngressMeterLastChanged,
        tSapIngressMeterMode,
        tSapIngressMeterRateMode,
        tNetworkIngressFCExtnRowStatus,
        tNetworkIngressFCExtnMeter,
        tNetworkIngressFCExtnMCastMeter,
        tNetworkIngressFCExtnLastChanged,
        tNetworkIngressMeterRowStatus,
        tNetworkIngressMeterAdminCBS,
        tNetworkIngressMeterAdminMBS,
        tNetworkIngressMeterOperCBS,
        tNetworkIngressMeterOperMBS,        
        tNetworkIngressMeterCIRAdaptation,
        tNetworkIngressMeterPIRAdaptation,
        tNetworkIngressMeterAdminPIR,
        tNetworkIngressMeterAdminCIR,
        tNetworkIngressMeterOperPIR,
        tNetworkIngressMeterOperCIR,
        tNetworkIngressMeterLastChanged,
        tNetworkIngressMeterMode,
        tNetworkIngressMeterMCast,
        tNetworkIngressMeterRateMode,
        tSlopeHiQueue1DropRate,
        tSlopeHiQueue2DropRate,
        tSlopeHiQueue3DropRate,
        tSlopeHiQueue4DropRate,
        tSlopeHiQueue5DropRate,
        tSlopeHiQueue6DropRate,
        tSlopeHiQueue7DropRate,
        tSlopeHiQueue8DropRate,
        tSlopeLoQueue1DropRate,
        tSlopeLoQueue2DropRate,
        tSlopeLoQueue3DropRate,
        tSlopeLoQueue4DropRate,
        tSlopeLoQueue5DropRate,
        tSlopeLoQueue6DropRate,
        tSlopeLoQueue7DropRate,
        tSlopeLoQueue8DropRate,
        tSlopeHiStartThreshold,
        tSlopeLoStartThreshold,
        tPortSchedulerPlcyMode,
        tPortSchedulerPlcyQuanta,
        tPortSchedulerPlcyQueue1Weight,
        tPortSchedulerPlcyQueue2Weight,
        tPortSchedulerPlcyQueue3Weight,
        tPortSchedulerPlcyQueue4Weight,
        tPortSchedulerPlcyQueue5Weight,
        tPortSchedulerPlcyQueue6Weight,
        tPortSchedulerPlcyQueue7Weight,
        tPortSchedulerPlcyQueue8Weight,
        tSapIngressFCMeter,       
        tSapIngressFCMCastMeter,  
        tSapIngressFCBCastMeter,  
        tSapIngressFCUnknownMeter,
        sapIngQosMeterId,                          
        sapIngQosMeterStatsForwardedInProfPackets, 
        sapIngQosMeterStatsForwardedOutProfPackets,
        sapIngQosMeterStatsForwardedInProfOctets,  
        sapIngQosMeterStatsForwardedOutProfOctets,
        tQosIngressFrameBasedAccnt,
        tQosEgressFrameBasedAccnt,
        tSapIngressNumQosClassifiers,
        tSapIngressQosClassifiersRequiredInVpls, 
        tSapIngressQosClassifiersRequiredInEpipe,
        tSapIngressQosMetersRequiredInVpls,
        tSapIngressQosMetersRequiredInEpipe,
        tSapIngressIPCriteriaMatch,
        tSapIngressMacCriteriaMatch,
        tSapIngressIPv6CriteriaEnable,
        tSapIngressIPv6CriteriaMatch,
        tNetworkEgressRemarkType,
        tSapIngressIPMacMatch
} 
       STATUS current
       DESCRIPTION 
           " sas group object definition "
       ::= { tmnxSASQosGroups 3 }

tmnxSASQosObsolete7210V2v0Group OBJECT-GROUP
    OBJECTS 
{
        tNetworkIngressMeterCBS,
        tNetworkIngressMeterMBS,
        tSapIngressMeterCBS,
        tSapIngressMeterMBS,
        tSapIngressQosClassifiersUsed,
        tSapIngressQosMetersUsed
}
    STATUS current
    DESCRIPTION
        "The group of objects which are obsoleted from version 2.0 of
        Nokia 7210 series systems."
    ::= { tmnxSASQosGroups 4}

tmnxSASQos7210V4v0Group OBJECT-GROUP
    OBJECTS 
{
        tGlobalMplsLspExpProfile,
        tLdpLocalFcEnableAdminStatus,
        tLdpLocalFcEnableOperStatus,
        tMplsLspExpProfMapRowStatus,
        tMplsLspExpProfMapDescription,
        tAccessEgressRemarkType,
        tAccessEgressFCDscpInProfile,
        tAccessEgressFCDscpOutProfile,
        tSapIngressQueuePolicyName,
        tSapIngressIPCriteriaActionProfile,
        tSapIngressMacCriteriaActionProfile,
        tSapIngressIPv6CriteriaActionProfile,
        sapIngQosMeterStatsForwardedPackets,
        sapIngQosMeterStatsForwardedOctets,
        sapIngQosMeterStatsDroppedPackets,
        sapIngQosMeterStatsDroppedOctets
}
    STATUS current
    DESCRIPTION
        "The group of objects which are obsoleted from version 4.0 of
        Nokia 7210 series systems."
    ::= { tmnxSASQosGroups 5}

tmnxSASQoSV10v0Group OBJECT-GROUP
    OBJECTS    {
        tSapIngressQosClassifiersRequiredInIes,
        tSapIngressQosMetersRequiredInIes
    }
       STATUS current
       DESCRIPTION 
           " sas group object definition version 7.0"
       ::= { tmnxSASQosGroups 6 }
    
tmnxSASQoSComp7210V1v0  MODULE-COMPLIANCE
    STATUS  current
    DESCRIPTION
            "The compliance statement for revision 1.0 of TIMETRA-SAS-QOS-MIB."
    MODULE  -- this module
        MANDATORY-GROUPS { 
           tmnxSASQoSV1v0Group
        }
    ::= { tmnxSASQosCompliances 1 }

tmnxSASQoSComp7210V2v0  MODULE-COMPLIANCE
    STATUS  current
    DESCRIPTION
            "The compliance statement for revision 2.0 of TIMETRA-SAS-QOS-MIB."
    MODULE  -- this module
        MANDATORY-GROUPS { 
           tmnxSASQoSV2v0Group
        }
    ::= { tmnxSASQosCompliances 2 }

END
