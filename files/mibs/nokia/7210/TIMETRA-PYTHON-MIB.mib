TIMETRA-PYTHON-MIB DEFINITIONS ::= BEGIN

IMPORTS
    Unsigned32, Counter32, Gauge32,
    MODULE-IDENTITY,
    OBJECT-TYPE,
    NOTIFICATION-TYPE
                                                    FROM SNMPv2-SMI


    RowStatus, TEXTUAL-CONVENTION,
    TimeStamp, TimeInterval,
    DisplayString,
    TruthValue
                                                    FROM SNMPv2-TC


    OBJECT-GROUP,
    MODULE-COMPLIANCE,
    NOTIFICATION-GROUP
                                                    FROM SNMPv2-CONF

    InetAddressType, InetAddress
                                                    FROM INET-ADDRESS-MIB
    timetraSRMIBModules, tmnxSRObjs,
    tmnxSRNotifyPrefix, tmnxSRConfs                 FROM TIMETRA-GLOBAL-MIB

    TmnxAdminState, TmnxOperState,
    TNamedItem, TNamedItemOrEmpty,
    TItemDescription,
    TmnxDisplayStringURL,
    TDirectionIngEgr, TmnxActionType
                                                    FROM TIMETRA-TC-MIB
    ;

timetraPythonMIBModule    MODULE-IDENTITY
    LAST-UPDATED    "201401011200Z"
    ORGANIZATION    "Nokia"
    CONTACT-INFO
    "Nokia 7xxx Support
    Web: http://www.nokia.com"
    DESCRIPTION
    "This document is the SNMP MIB module to manage and provision
     Python for the Nokia 7xxx device.

     Copyright 2013-2015 Nokia. All rights reserved.
     Reproduction of this document is authorized on the condition that
     the foregoing copyright notice is included.

     This SNMP MIB module (Specification) embodies Nokia's
     proprietary intellectual property. Nokia retains all title and
     ownership in the Specification, including any revisions.

     Nokia grants all interested parties a non-exclusive
     license to use and distribute an unmodified copy of this
     Specification in connection with management of Nokia products,
     and without fee, provided this copyright notice and license appear
     on all copies.

     This Specification is supplied 'as is', and Nokia
     makes no warranty, either express or implied, as to the use,
     operation, condition, or performance of the Specification."

--
--  Revision History
--
    REVISION        "201501011200Z"
    DESCRIPTION     "Rev 13.0               1 Jan 2015 00:00
                    Release 13.0 version of the TIMETRA-PYTHON-MIB."

    REVISION        "201401011200Z"
    DESCRIPTION     "Rev 0.1                1 Jan 2014 00:00
                    Initial version of the TIMETRA-PYTHON-MIB."

    ::= { timetraSRMIBModules 87 }

-- ----------------------------------------------------------------------------
--  MIB structure
-- ----------------------------------------------------------------------------
tmnxPython                     OBJECT IDENTIFIER ::= { tmnxSRObjs 87 }
    tmnxPythonObjs             OBJECT IDENTIFIER ::= { tmnxPython 1 }
    tmnxPythonNotificationObjs OBJECT IDENTIFIER ::= { tmnxPython 2 }

tmnxPythonNotifyPrefix      OBJECT IDENTIFIER ::= { tmnxSRNotifyPrefix 87 }
    tmnxPythonNotifications OBJECT IDENTIFIER ::= { tmnxPythonNotifyPrefix 0 }

tmnxPythonConformance       OBJECT IDENTIFIER ::= { tmnxSRConfs 87 }
    tmnxPythonCompliances   OBJECT IDENTIFIER ::= { tmnxPythonConformance 1 }
    tmnxPythonGroups        OBJECT IDENTIFIER ::= { tmnxPythonConformance 2 }
    tmnxPythonNotifGroups   OBJECT IDENTIFIER ::= { tmnxPythonConformance 3 }

-- ----------------------------------------------------------------------------
--  Textual Conventions
-- ----------------------------------------------------------------------------

TmnxProtection ::= TEXTUAL-CONVENTION
    STATUS  current
    DESCRIPTION
        "The value of TmnxProtection specifies the method used to
         ensure the integrity and/or the confidentiality of the affected
         file.
    
         A value of 'none (1)' indicates the file is stored in plain-text, 
         without any mechanism in place to ensure the integrity nor
         the confidentiality of the content of the file.

         A value of 'hmacSha256' indicates the first line of the file must 
         include the hash value obtained by hashing the rest of the
         file using the hmac-sha256 hashing algorithm given a specified key."
    SYNTAX INTEGER {
           none        (1),
           hmacSha256  (2)
        }

-- --------------------------------------------------------
-- The Python Script table
-- --------------------------------------------------------

tmnxPythonScriptTableLastCh OBJECT-TYPE
    SYNTAX      TimeStamp
    MAX-ACCESS  read-only
    STATUS      current
    DESCRIPTION
        "The value tmnxPythonScriptTableLastCh indicates the sysUpTime at
         the time of the last modification of an entry in the
         tmnxPythonScriptTable."
    ::= { tmnxPythonObjs 1 }

tmnxPythonScriptTable OBJECT-TYPE
    SYNTAX      SEQUENCE OF TmnxPythonScriptEntry
    MAX-ACCESS  not-accessible
    STATUS      current
    DESCRIPTION
        "The table tmnxPythonScriptTable contains objects to configure
         Python scripts.

         These scripts are grouped in a script policy in the
         tmnxPythonPolicyMessageTable."
    ::= { tmnxPythonObjs 2 }

tmnxPythonScriptEntry OBJECT-TYPE
    SYNTAX      TmnxPythonScriptEntry
    MAX-ACCESS  not-accessible
    STATUS      current
    DESCRIPTION
        "Each row represents a Python script.

         Entries in this table can be created or deleted via SNMP operations."
    INDEX { tmnxPythonScriptName }
    ::= { tmnxPythonScriptTable 1 }

TmnxPythonScriptEntry ::= SEQUENCE {
    tmnxPythonScriptName             TNamedItem,
    tmnxPythonScriptRowStatus        RowStatus,
    tmnxPythonScriptLastChanged      TimeStamp,
    tmnxPythonScriptAdminState       TmnxAdminState,
    tmnxPythonScriptOperState        TmnxOperState,
    tmnxPythonScriptDescription      TItemDescription,
    tmnxPythonScriptOnFail           INTEGER,
    tmnxPythonScriptProtection       TmnxProtection,
    tmnxPythonScriptProtectionKey    DisplayString,
    tmnxPythonScriptPrimaryUrl       TmnxDisplayStringURL,
    tmnxPythonScriptSecondaryUrl     TmnxDisplayStringURL,
    tmnxPythonScriptTertiaryUrl      TmnxDisplayStringURL,
    tmnxPythonScriptActiveUrl        INTEGER,
    tmnxPythonScriptReloadAction     TmnxActionType
}

tmnxPythonScriptName OBJECT-TYPE
    SYNTAX      TNamedItem
    MAX-ACCESS  not-accessible
    STATUS      current
    DESCRIPTION
        "The value of tmnxPythonScriptName specifies the name of this Python
         script policy."
    ::= { tmnxPythonScriptEntry 1 }

tmnxPythonScriptRowStatus OBJECT-TYPE
    SYNTAX      RowStatus
    MAX-ACCESS  read-create
    STATUS      current
    DESCRIPTION
        "The value of tmnxPythonScriptRowStatus controls the creation and
         deletion of rows in the table."
    ::= { tmnxPythonScriptEntry 2 }

tmnxPythonScriptLastChanged OBJECT-TYPE
    SYNTAX      TimeStamp
    MAX-ACCESS  read-only
    STATUS      current
    DESCRIPTION
        "The value tmnxPythonScriptLastChanged indicates the sysUpTime at
         the time of the most recent management-initiated change to this
         Python script policy."
    ::= { tmnxPythonScriptEntry 3 }

tmnxPythonScriptAdminState OBJECT-TYPE
    SYNTAX      TmnxAdminState
    MAX-ACCESS  read-create
    STATUS      current
    DESCRIPTION
        "The value of tmnxPythonScriptAdminState specifies the
         administrative state of the Python script."
    DEFVAL { outOfService }
    ::= { tmnxPythonScriptEntry 4 }

tmnxPythonScriptOperState OBJECT-TYPE
    SYNTAX      TmnxOperState
    MAX-ACCESS  read-only
    STATUS      current
    DESCRIPTION
        "The value of tmnxPythonScriptOperState specifies the
         operational state of the Python script."
    ::= { tmnxPythonScriptEntry 5 }

tmnxPythonScriptDescription OBJECT-TYPE
    SYNTAX      TItemDescription
    MAX-ACCESS  read-create
    STATUS      current
    DESCRIPTION
        "The value of tmnxPythonScriptDescription specifies the description of
         this Python script policy."
    DEFVAL { "" }
    ::= { tmnxPythonScriptEntry 6 }

tmnxPythonScriptOnFail OBJECT-TYPE
    SYNTAX INTEGER {
           passthrough (1),
           drop        (2)
        }
    MAX-ACCESS  read-create
    STATUS      current
    DESCRIPTION
        "The value of tmnxPythonScriptOnFail specifies the action taken
         when Python fails to modify the given message.

         When the value is 'passthrough' the packet will be sent out without
         any modifications.

         When the value is 'drop' the packet will be dropped."
    DEFVAL { drop }
    ::= { tmnxPythonScriptEntry 7 }

tmnxPythonScriptProtection OBJECT-TYPE
    SYNTAX TmnxProtection
    MAX-ACCESS  read-create
    STATUS      current
    DESCRIPTION
        "The value of tmnxPythonScriptProtection specifies the method used to
         ensure the integrity and/or the confidentiality of the content of the
         Python script.

         A value of 'none (1)' indicates the Python script is stored in
         plain-text, without any mechanism in place to ensure the integrity nor
         the confidentiality of the content of the Python script.

         A value of 'hmacSha256' indicates the first line of the Python script
         must consist of the hash value obtained by hashing the rest of the
         Python script using the hmac-sha256 hashing algorithm given the key
         specified in tmnxPythonScriptProtectionKey.

         To set this field you must also set tmnxPythonScriptProtectionKey."
    DEFVAL { none }
    ::= { tmnxPythonScriptEntry 8 }

tmnxPythonScriptProtectionKey OBJECT-TYPE
    SYNTAX DisplayString (SIZE (0..128))
    MAX-ACCESS  read-create
    STATUS      current
    DESCRIPTION
        "The value of tmnxPythonScriptProtectionKey specifies the secret key
         used for the protection mechanism specified in
         tmnxPythonScriptProtection.

         If tmnxPythonScriptProtection is set to 'none (1)' this key must be
         set to the empty string.

         Performing an SNMP GET on this field will always return an empty
         string."
    DEFVAL { ''H }
    ::= { tmnxPythonScriptEntry 9 }

tmnxPythonScriptPrimaryUrl OBJECT-TYPE
    SYNTAX      TmnxDisplayStringURL
    MAX-ACCESS  read-create
    STATUS      current
    DESCRIPTION
        "The value of tmnxPythonScriptPrimaryUrl specifies the URL of the
         primary script to change the Python message."
    DEFVAL { ''H }
    ::= { tmnxPythonScriptEntry 10 }

tmnxPythonScriptSecondaryUrl OBJECT-TYPE
    SYNTAX      TmnxDisplayStringURL
    MAX-ACCESS  read-create
    STATUS      current
    DESCRIPTION
        "The value of tmnxPythonScriptSecondaryUrl specifies the URL of the
         secondary script to change the Python message."
    DEFVAL { ''H }
    ::= { tmnxPythonScriptEntry 11 }

tmnxPythonScriptTertiaryUrl OBJECT-TYPE
    SYNTAX      TmnxDisplayStringURL
    MAX-ACCESS  read-create
    STATUS      current
    DESCRIPTION
        "The value of tmnxPythonScriptTertiaryUrl specifies the URL of the
         tertiary script to change the Python message."
    DEFVAL { ''H }
    ::= { tmnxPythonScriptEntry 12 }

tmnxPythonScriptActiveUrl OBJECT-TYPE
    SYNTAX INTEGER {
           none      (0),
           primary   (1),
           secondary (2),
           tertiary  (3)
        }
    MAX-ACCESS  read-only
    STATUS      current
    DESCRIPTION
        "The value of tmnxPythonScriptActiveUrl indicates from which URL the
         script has been loaded.

         A value of 'primary(1)' indicates the URL in
         tmnxPythonScriptPrimaryUrl has been used.
         A value of 'secondary(2)' indicates the URL in
         tmnxPythonScriptSecondaryUrl has been used.
         A value of 'tertiary(3)' indicates the URL in
         tmnxPythonScriptTertiaryUrl has been used.

         A value of 'none(0)' indicates no script has been loaded."
    ::= { tmnxPythonScriptEntry 13 }

tmnxPythonScriptReloadAction OBJECT-TYPE
    SYNTAX TmnxActionType
    MAX-ACCESS  read-create
    STATUS      current
    DESCRIPTION
        "The value of tmnxPythonScriptReloadAction indicates whether
         to reload the Python script file specified by this Python script.

         When SET to the value of 'doAction' the system will load and parse
         the file specified in the primary, secondary or tertiary url.

         An SNMP GET request on this object should return 'notApplicable'."
    DEFVAL { notApplicable }
    ::= { tmnxPythonScriptEntry 50 }

-- --------------------------------------------------------
-- The Python Policy table
-- --------------------------------------------------------

tmnxPythonPolicyTableLastCh OBJECT-TYPE
    SYNTAX      TimeStamp
    MAX-ACCESS  read-only
    STATUS      current
    DESCRIPTION
        "The value tmnxPythonPolicyTableLastCh indicates the sysUpTime at
         the time of the last modification of an entry in the
         tmnxPythonPolicyTable."
    ::= { tmnxPythonObjs 3 }

tmnxPythonPolicyTable OBJECT-TYPE
    SYNTAX      SEQUENCE OF TmnxPythonPolicyEntry
    MAX-ACCESS  not-accessible
    STATUS      current
    DESCRIPTION
        "The table tmnxPythonPolicyTable contains objects to configure
         Python policies."
    ::= { tmnxPythonObjs 4 }

tmnxPythonPolicyEntry OBJECT-TYPE
    SYNTAX      TmnxPythonPolicyEntry
    MAX-ACCESS  not-accessible
    STATUS      current
    DESCRIPTION
        "Each row represents a Python policy.

         Entries in this table can be created or deleted via SNMP operations."
    INDEX { tmnxPyPlcyName }
    ::= { tmnxPythonPolicyTable 1 }

TmnxPythonPolicyEntry ::= SEQUENCE {
    tmnxPyPlcyName                   TNamedItem,
    tmnxPyPlcyRowStatus              RowStatus,
    tmnxPyPlcyLastChanged            TimeStamp,
    tmnxPyPlcyDescription            TItemDescription
}

tmnxPyPlcyName OBJECT-TYPE
    SYNTAX      TNamedItem
    MAX-ACCESS  not-accessible
    STATUS      current
    DESCRIPTION
        "The value of tmnxPyPlcyName specifies the name of this Python policy."
    ::= { tmnxPythonPolicyEntry 1 }

tmnxPyPlcyRowStatus OBJECT-TYPE
    SYNTAX      RowStatus
    MAX-ACCESS  read-create
    STATUS      current
    DESCRIPTION
        "The value of tmnxPyPlcyRowStatus controls the creation and
         deletion of rows in the table."
    ::= { tmnxPythonPolicyEntry 2 }

tmnxPyPlcyLastChanged OBJECT-TYPE
    SYNTAX      TimeStamp
    MAX-ACCESS  read-only
    STATUS      current
    DESCRIPTION
        "The value tmnxPyPlcyLastChanged indicates the sysUpTime at
         the time of the most recent management-initiated change to this
         Python policy."
    ::= { tmnxPythonPolicyEntry 3 }

tmnxPyPlcyDescription OBJECT-TYPE
    SYNTAX      TItemDescription
    MAX-ACCESS  read-create
    STATUS      current
    DESCRIPTION
        "The value of tmnxPyPlcyDescription specifies the description of
         this Python policy."
    DEFVAL { "" }
    ::= { tmnxPythonPolicyEntry 4 }

-- --------------------------------------------------------
-- The Python Policy Cache table
-- --------------------------------------------------------
--
--      Sparse augment of the TIMETRA-PYTHON-MIB::tmnxPythonPolicyTable

tmnxPythonPolicyCacheTableLastCh OBJECT-TYPE
    SYNTAX      TimeStamp
    MAX-ACCESS  read-only
    STATUS      current
    DESCRIPTION
        "The value tmnxPythonPolicyCacheTableLastCh indicates the sysUpTime at
         the time of the last modification of an entry in the
         tmnxPythonPolicyCacheTable."
    ::= { tmnxPythonObjs 5 }

tmnxPythonPolicyCacheTable OBJECT-TYPE
    SYNTAX      SEQUENCE OF TmnxPythonPolicyCacheEntry
    MAX-ACCESS  not-accessible
    STATUS      current
    DESCRIPTION
        "The table tmnxPythonPolicyCacheTable contains objects to configure
         Python policy caches."
    ::= { tmnxPythonObjs 6 }

tmnxPythonPolicyCacheEntry OBJECT-TYPE
    SYNTAX      TmnxPythonPolicyCacheEntry
    MAX-ACCESS  not-accessible
    STATUS      current
    DESCRIPTION
        "Each row represents the cache of a Python policy.

         Entries in this table can be created or deleted via SNMP operations."
    INDEX { tmnxPyPlcyName }
    ::= { tmnxPythonPolicyCacheTable 1 }

TmnxPythonPolicyCacheEntry ::= SEQUENCE {
    tmnxPyPlcyCacheRowStatus         RowStatus,
    tmnxPyPlcyCacheEntrySize         INTEGER,
    tmnxPyPlcyCacheMaxEntries        INTEGER,
    tmnxPyPlcyCacheMaxLifetime       INTEGER,
    tmnxPyPlcyCacheAdminState        TmnxAdminState,
    tmnxPyPlcyCacheLastChanged       TimeStamp,
    tmnxPyPlcyCachePersistent        TruthValue,
    tmnxPyPlcyCacheMinLifetimeMcs    Unsigned32,
    tmnxPyPlcyCacheMinLifetimeHa     Unsigned32,
    tmnxPyPlcyCacheMinLifetimePers   Unsigned32,
    tmnxPyPlcyCacheNumberOfEntries   Gauge32
}

tmnxPyPlcyCacheRowStatus OBJECT-TYPE
    SYNTAX      RowStatus
    MAX-ACCESS  read-create
    STATUS      current
    DESCRIPTION
        "The value of tmnxPyPlcyCacheRowStatus controls the creation and
         deletion of rows in the table."
    ::= { tmnxPythonPolicyCacheEntry 1 }

tmnxPyPlcyCacheEntrySize OBJECT-TYPE
    SYNTAX      INTEGER (32..2048)
    UNITS       "bytes"
    MAX-ACCESS  read-create
    STATUS      current
    DESCRIPTION
        "The value of tmnxPyPlcyCacheEntrySize specifies the maximum size of the
         data structure that can be stored in a single Python cache entry.

         When requesting to store a data structure the size of the serialized
         object is compared with the value specified in this MIB field.
         If it's larger, the object will not be stored and Python will throw an
         exception."
    DEFVAL { 256 }
    ::= { tmnxPythonPolicyCacheEntry 2 }

tmnxPyPlcyCacheMaxEntries OBJECT-TYPE
    SYNTAX      INTEGER (1..1000000)
    MAX-ACCESS  read-create
    STATUS      current
    DESCRIPTION
        "The value of tmnxPyPlcyCacheMaxEntries specifies the maximum number of
         Python cache entries that can be stored in the cache of this Python
         policy.

         If the limit has been reached, a Python exception will be thrown when
         requested to store another data structure."
    DEFVAL { 128000 }
    ::= { tmnxPythonPolicyCacheEntry 3 }

tmnxPyPlcyCacheMaxLifetime OBJECT-TYPE
    SYNTAX      INTEGER (1..604800)
    UNITS       "seconds"
    MAX-ACCESS  read-create
    STATUS      current
    DESCRIPTION
        "The value of tmnxPyPlcyCacheMaxLifetime specifies the maximum allowed
         lifetime for each entry of the Python cache of this Python policy.

         When adding data to the Python cache the lifetime of the given object
         must always be specified. If the specified lifetime is bigger than the
         value of tmnxPyPlcyCacheMaxLifetime, the value of
         tmnxPyPlcyCacheMaxLifetime will be used instead of the lifetime that
         was specified."
    DEFVAL { 86400 }
    ::= { tmnxPythonPolicyCacheEntry 4 }

tmnxPyPlcyCacheAdminState OBJECT-TYPE
    SYNTAX      TmnxAdminState
    MAX-ACCESS  read-create
    STATUS      current
    DESCRIPTION
        "The value of tmnxPyPlcyCacheAdminState specifies the
         administrative state of the cache of this Python policy."
    DEFVAL { outOfService }
    ::= { tmnxPythonPolicyCacheEntry 5 }

tmnxPyPlcyCacheLastChanged OBJECT-TYPE
    SYNTAX      TimeStamp
    MAX-ACCESS  read-only
    STATUS      current
    DESCRIPTION
        "The value tmnxPyPlcyCacheLastChanged indicates the sysUpTime at
         the time of the most recent management-initiated change to the 
         cache of this Python policy."
    ::= { tmnxPythonPolicyCacheEntry 6 }


tmnxPyPlcyCachePersistent OBJECT-TYPE
    SYNTAX      TruthValue
    MAX-ACCESS  read-create
    STATUS      current
    DESCRIPTION
        "The value of tmnxPyPlcyCachePersistent specifies
         if the cache of this Python policy is persistent."
    DEFVAL { false }
    ::= { tmnxPythonPolicyCacheEntry 10 }

tmnxPyPlcyCacheMinLifetimeMcs OBJECT-TYPE
    SYNTAX      Unsigned32 (0..600)
    UNITS       "seconds"
    MAX-ACCESS  read-create
    STATUS      current
    DESCRIPTION
        "The value of tmnxPyPlcyCacheMinLifetimeMcs specifies the minimum
         value for the remaining lifetime of any cache entry
         to be be synchronized with the peer system using
         Multi-Chassis Redundancy Synchronization."
    DEFVAL { 0 }
    ::= { tmnxPythonPolicyCacheEntry 11 }

tmnxPyPlcyCacheMinLifetimeHa OBJECT-TYPE
    SYNTAX      Unsigned32 (0..600)
    UNITS       "seconds"
    MAX-ACCESS  read-create
    STATUS      current
    DESCRIPTION
        "The value of tmnxPyPlcyCacheMinLifetimeHa specifies the minimum
         value for the remaining lifetime of any cache entry
         to be be synchronized with the standby CPM using High Availability."
    DEFVAL { 0 }
    ::= { tmnxPythonPolicyCacheEntry 12 }

tmnxPyPlcyCacheMinLifetimePers OBJECT-TYPE
    SYNTAX      Unsigned32 (0..1800)
    UNITS       "seconds"
    MAX-ACCESS  read-create
    STATUS      current
    DESCRIPTION
        "The value of tmnxPyPlcyCacheMinLifetimePers specifies the minimum
         value for the remaining lifetime of any cache entry
         to be be written to the system persistence file."
    DEFVAL { 0 }
    ::= { tmnxPythonPolicyCacheEntry 13 }

tmnxPyPlcyCacheNumberOfEntries OBJECT-TYPE
    SYNTAX      Gauge32
    MAX-ACCESS  read-only
    STATUS      current
    DESCRIPTION
        "The value of tmnxPyPlcyCacheNumberOfEntries specifies the current
         number of Python cache entries that are stored in the cache of
         this Python policy."
    ::= { tmnxPythonPolicyCacheEntry 14 }

-- --------------------------------------------------------
-- The Python Policy Message Table
-- --------------------------------------------------------

tmnxPythonPolicyMessageTblLstCh OBJECT-TYPE
    SYNTAX      TimeStamp
    MAX-ACCESS  read-only
    STATUS      current
    DESCRIPTION
        "The value tmnxPythonPolicyMessageTblLstCh indicates the sysUpTime at
         the time of the last modification of an entry in the
         tmnxPythonPolicyMessageTable."
    ::= { tmnxPythonObjs 7 }

tmnxPythonPolicyMessageTable OBJECT-TYPE
    SYNTAX      SEQUENCE OF TmnxPythonPolicyMessageEntry
    MAX-ACCESS  not-accessible
    STATUS      current
    DESCRIPTION
        "The table tmnxPythonPolicyMessageTable specifies when a Python script
         must be invoked."
    ::= { tmnxPythonObjs 8 }

tmnxPythonPolicyMessageEntry OBJECT-TYPE
    SYNTAX      TmnxPythonPolicyMessageEntry
    MAX-ACCESS  not-accessible
    STATUS      current
    DESCRIPTION
        "Each row represents an event that triggers the execution of the
         specified Python script.

         Entries in this table can be created or deleted via SNMP operations."
    INDEX { tmnxPyPlcyName,
            tmnxPyPlcyMessageType,
            tmnxPyPlcyMessageDirection }
    ::= { tmnxPythonPolicyMessageTable 1 }

TmnxPythonPolicyMessageEntry ::= SEQUENCE {
    tmnxPyPlcyMessageType            INTEGER,
    tmnxPyPlcyMessageDirection       TDirectionIngEgr,
    tmnxPyPlcyMessageRowStatus       RowStatus,
    tmnxPyPlcyMessageLastChanged     TimeStamp,
    tmnxPyPlcyMessagePyScript        TNamedItem
}

tmnxPyPlcyMessageType OBJECT-TYPE
    SYNTAX      INTEGER {
               --         RADIUS messages         --
               radiusAccessRequest                (1),
               radiusAccessAccept                 (2),
               radiusAccessReject                 (3),
               radiusAccountingRequest            (4),
               radiusAccountingResponse           (5),
               radiusAccessChallenge              (6),
               radiusDisconnectRequest            (7),
               radiusChangeOfAuthorizationRequest (8),

               --         DHCPv4 messages         --
               dhcpDiscover                       (1001),
               dhcpOffer                          (1002),
               dhcpRequest                        (1003),
               dhcpDecline                        (1004),
               dhcpAck                            (1005),
               dhcpNak                            (1006),
               dhcpRelease                        (1007),
               dhcpInform                         (1008),
               dhcpForceRenew                     (1009),
               dhcpLeaseQuery                     (1010),
               dhcpLeaseUnassigned                (1011),
               dhcpLeaseUnknown                   (1012),
               dhcpLeaseActive                    (1013),

               --         DHCPv6 messages         --
               dhcp6Solicit                       (2001),
               dhcp6Advertise                     (2002),
               dhcp6Request                       (2003),
               dhcp6Confirm                       (2004),
               dhcp6Renew                         (2005),
               dhcp6Rebind                        (2006),
               dhcp6Reply                         (2007),
               dhcp6Release                       (2008),
               dhcp6Decline                       (2009),
               dhcp6Reconfigure                   (2010),
               dhcp6InfoRequest                   (2011),
               dhcp6RelayForward                  (2012),
               dhcp6RelayReply                    (2013),

               --         DIAMETER messages       --
               diameterCCR                        (3001),
               diameterCCA                        (3002),
               diameterRAR                        (3003),
               diameterRAA                        (3004),
               diameterCER                        (3005),
               diameterCEA                        (3006),
               diameterDWR                        (3007),
               diameterDWA                        (3008),
               diameterDPR                        (3009),
               diameterDPA                        (3010),
               diameterASR                        (3011),
               diameterASA                        (3012),
               diameterAAR                        (3013),
               diameterAAA                        (3014)

               --         VSD messages       --

               }
    MAX-ACCESS  not-accessible
    STATUS      current
    DESCRIPTION
        "The value of tmnxPyPlcyMessageType specifies the message type of the
         event."
    ::= { tmnxPythonPolicyMessageEntry 2 }

tmnxPyPlcyMessageDirection OBJECT-TYPE
    SYNTAX      TDirectionIngEgr
    MAX-ACCESS  not-accessible
    STATUS      current
    DESCRIPTION
        "The value of tmnxPyPlcyMessageDirection specifies whether the event is
         incoming or outgoing."
    ::= { tmnxPythonPolicyMessageEntry 3 }

tmnxPyPlcyMessageRowStatus OBJECT-TYPE
    SYNTAX      RowStatus
    MAX-ACCESS  read-create
    STATUS      current
    DESCRIPTION
        "The value of tmnxPyPlcyMessageRowStatus controls the creation and
         deletion of rows in the table."
    ::= { tmnxPythonPolicyMessageEntry 4 }

tmnxPyPlcyMessageLastChanged OBJECT-TYPE
    SYNTAX      TimeStamp
    MAX-ACCESS  read-only
    STATUS      current
    DESCRIPTION
        "The value tmnxPyPlcyMessageLastChanged indicates the sysUpTime at
         the time of the most recent management-initiated change to this
         Python policy protocol."
    ::= { tmnxPythonPolicyMessageEntry 5 }

tmnxPyPlcyMessagePyScript OBJECT-TYPE
    SYNTAX      TNamedItem
    MAX-ACCESS  read-create
    STATUS      current
    DESCRIPTION
        "The value of tmnxPyPlcyMessagePyScript specifies the name of the
         Python script that will be used to handle the message specified by this
         row."
    ::= { tmnxPythonPolicyMessageEntry 6 }

-- --------------------------------------------------------
-- The "Python protect" Group
-- --------------------------------------------------------

--
--      The Python protect file Action
--
-- The tmnxPythonProtectAction object allows to request 
-- the protection of a Python script file.
--
-- Write the file-url of the Python script file in tmnxPythonProtectFileUrl,
-- the destination file-url in the tmnxPythonProtectDestFileUrl and the
-- requested protection type and key in tmnxPythonProtectType and
-- tmnxPythonProtectKey respectively.
-- Writing the value 'doAction (1)' in the object tmnxPythonProtectActionGo
-- triggers a request to perform the specified action.
--
-- If the action could be performed successfully, the value of the object
-- tmnxPythonProtectActionSuccess equals 'true'.
-- If the value of the object equals 'false', 
-- an entry in the TIMETRA-LOG-MIB::tmnxSnmpSetErrsTable is created.

-- If the action could be performed successfully, 
-- the protected script will be written in the file specified in 
-- tmnxPythonProtectDestFileUrl.
--
-- The values of the object tmnxPythonProtectActionSuccess refers to the 
-- last action. The value of tmnxPythonProtectActionTime indicates the 
-- time of the last action.
--
-- To avoid concurrency problems, set the value of tmnxPythonProtectActionGo
-- along with all necessary parameters in a single SNMP set request.

tmnxPythonProtectAction OBJECT IDENTIFIER ::= { tmnxPythonObjs 9 }

tmnxPythonProtectFileUrl OBJECT-TYPE
    SYNTAX      TmnxDisplayStringURL
    MAX-ACCESS  read-write
    STATUS      current
    DESCRIPTION
        "The value of tmnxPythonProtectFileUrl specifies the URL of the
         Python script to protect."
    DEFVAL { ''H }
    ::= { tmnxPythonProtectAction 1 }

tmnxPythonProtectDestFileUrl OBJECT-TYPE
    SYNTAX      TmnxDisplayStringURL
    MAX-ACCESS  read-write
    STATUS      current
    DESCRIPTION
        "The value of tmnxPythonProtectDestFileUrl specifies the URL where the
         protected Python script must be stored."
    DEFVAL { ''H }
    ::= { tmnxPythonProtectAction 2 }

tmnxPythonProtectType OBJECT-TYPE
    SYNTAX TmnxProtection
    MAX-ACCESS  read-write
    STATUS      current
    DESCRIPTION
        "The value of tmnxPythonProtectType specifies the method used to
         ensure the integrity and/or the confidentiality of the content of the
         Python script."
    DEFVAL { none }
    ::= { tmnxPythonProtectAction 3 }

tmnxPythonProtectKey OBJECT-TYPE
    SYNTAX DisplayString (SIZE (0..128))
    MAX-ACCESS  read-write
    STATUS      current
    DESCRIPTION
        "The value of tmnxPythonProtectKey specifies the secret key
         used for the protection mechanism specified in tmnxPythonProtectType."
    DEFVAL { ''H }
    ::= { tmnxPythonProtectAction 4 }

tmnxPythonProtectActionGo OBJECT-TYPE
    SYNTAX      TmnxActionType
    MAX-ACCESS  read-write
    STATUS      current
    DESCRIPTION
        "Setting this object to 'doAction' triggers an attempt to 
         protect the Python script file specified in tmnxPythonProtectFileUrl.

         Reading this object returns the value 'notApplicable'."
    ::= { tmnxPythonProtectAction 5 }

tmnxPythonProtectActionSuccess OBJECT-TYPE
    SYNTAX      TruthValue
    MAX-ACCESS  read-only
    STATUS      current
    DESCRIPTION
        "The value of the object tmnxPythonProtectActionSuccess indicates
         if the last action request was successful.

         If the value of the object equals 'false', a row in the
         TIMETRA-LOG-MIB::tmnxSnmpSetErrsTable is created."
    ::= { tmnxPythonProtectAction 6 }

tmnxPythonProtectActionTime OBJECT-TYPE
    SYNTAX      TimeStamp
    MAX-ACCESS  read-only
    STATUS      current
    DESCRIPTION
        "The value of the object tmnxPythonProtectActionTime indicates
         the value of sysUpTime at the last time that the object 
         tmnxPythonProtectActionSuccess was written by the system."
    ::= { tmnxPythonProtectAction 7 }

-- ----------------------------------------------------------------------------
--  Conformance Groups
-- ----------------------------------------------------------------------------
tmnxPythonGroup OBJECT-GROUP
    OBJECTS {
         tmnxPythonScriptTableLastCh,
         tmnxPythonScriptRowStatus,
         tmnxPythonScriptLastChanged,
         tmnxPythonScriptDescription,
         tmnxPythonScriptOnFail,
         tmnxPythonScriptProtection,
         tmnxPythonScriptProtectionKey,
         tmnxPythonScriptAdminState,
         tmnxPythonScriptOperState,
         tmnxPythonScriptPrimaryUrl,
         tmnxPythonScriptSecondaryUrl,
         tmnxPythonScriptTertiaryUrl,
         tmnxPythonScriptActiveUrl,
         tmnxPythonScriptReloadAction,

         tmnxPythonPolicyTableLastCh,
         tmnxPyPlcyRowStatus,
         tmnxPyPlcyLastChanged,
         tmnxPyPlcyDescription,
         tmnxPythonPolicyCacheTableLastCh,
         tmnxPyPlcyCacheRowStatus,
         tmnxPyPlcyCacheEntrySize,
         tmnxPyPlcyCacheMaxEntries,
         tmnxPyPlcyCacheMaxLifetime,
         tmnxPyPlcyCacheAdminState,
         tmnxPyPlcyCacheLastChanged,               
         tmnxPyPlcyCachePersistent,
         tmnxPyPlcyCacheMinLifetimeMcs,
         tmnxPyPlcyCacheMinLifetimeHa,
         tmnxPyPlcyCacheMinLifetimePers,
         tmnxPyPlcyCacheNumberOfEntries,
         tmnxPythonProtectFileUrl,
         tmnxPythonProtectDestFileUrl,
         tmnxPythonProtectType,
         tmnxPythonProtectKey, 
         tmnxPythonProtectActionGo,
         tmnxPythonProtectActionSuccess,
         tmnxPythonProtectActionTime,

         tmnxPythonPolicyMessageTblLstCh,
         tmnxPyPlcyMessageRowStatus,
         tmnxPyPlcyMessageLastChanged,
         tmnxPyPlcyMessagePyScript
    }
    STATUS       current
    DESCRIPTION
        "The group of objects providing configuration of Python on
         Nokia SROS series systems."
    ::= { tmnxPythonGroups 1 }
    

----------------------------------------------
--  NOTIFICATION-GROUPS
----------------------------------------------

-- ----------------------------------------------------------------------------
--  Conformance information
-- ----------------------------------------------------------------------------
tmnxPythonCompliance MODULE-COMPLIANCE
    STATUS  current
    DESCRIPTION
        "The compliance statement for management of Python on
         Nokia SROS series systems."
    MODULE  -- this module
        MANDATORY-GROUPS {
            tmnxPythonGroup
        }
    ::= { tmnxPythonCompliances 1 }

tmnxPythonV13v0Compliance MODULE-COMPLIANCE
    STATUS  current
    DESCRIPTION
        "The compliance statement for management of Python on
         Nokia SROS series systems."
    MODULE  -- this module
        MANDATORY-GROUPS {
            tmnxPythonGroup
        }
    ::= { tmnxPythonCompliances 2 }

END
