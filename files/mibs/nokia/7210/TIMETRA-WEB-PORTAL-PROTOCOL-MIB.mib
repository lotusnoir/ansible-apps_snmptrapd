TIMETRA-WEB-PORTAL-PROTOCOL-MIB DEFINITIONS ::= BEGIN

IMPORTS
    Unsigned32, Gauge32, Counter32,
    MODULE-IDENTITY,
    OBJECT-TYPE      
                                                                FROM SNMPv2-SMI


    RowStatus, TEXTUAL-CONVENTION, 
    TimeStamp, DisplayString, TruthValue,
    MacAddress
                                                                 FROM SNMPv2-TC


    OBJECT-GROUP, MODULE-COMPLIANCE
                                                               FROM SNMPv2-CONF

    InetAddressType, InetAddress, InetPortNumber
                                                         FROM INET-ADDRESS-MIB
    timetraSRMIBModules, tmnxSRObjs, tmnxSRConfs, 
    tmnxSRNotifyPrefix
                                                        FROM TIMETRA-GLOBAL-MIB

    TItemDescription, TNamedItem, TNamedItemOrEmpty,
    TmnxVRtrID, TmnxVRtrIDOrZero, TmnxServId,
    TmnxAdminState, TmnxEnabledDisabled
                                                            FROM TIMETRA-TC-MIB

    svcId, iesIfIndex                        
                                                          FROM TIMETRA-SERV-MIB
    vRtrID, vRtrIfIndex                                          
                                                          FROM TIMETRA-VRTR-MIB


    ;
timetraWppMIBModule    MODULE-IDENTITY
    LAST-UPDATED    "201401010000Z"
    ORGANIZATION    "Nokia"
    CONTACT-INFO
    "Nokia 7xxx Support
    Web: http://www.nokia.com"
    DESCRIPTION
    "This document is the SNMP MIB module to manage and provision
    the Web Portal Protocol for the Nokia 7xxx device.

    Copyright 2011-2015 Nokia. All rights reserved.
    Reproduction of this document is authorized on the condition that
    the foregoing copyright notice is included.

    This SNMP MIB module (Specification) embodies Nokia's
    proprietary intellectual property. Nokia retains all title and
    ownership in the Specification, including any revisions.

    Nokia grants all interested parties a non-exclusive
    license to use and distribute an unmodified copy of this
    Specification in connection with management of Nokia products,
    and without fee, provided this copyright notice and license appear
    on all copies.

    This Specification is supplied 'as is', and Nokia
    makes no warranty, either express or implied, as to the use,
    operation, condition, or performance of the Specification."

--
--  Revision History
--

    REVISION        "201401010000Z"
    DESCRIPTION     "Rev 12.0                01 Jan 2014 00:00
                     12.0 release of the TIMETRA-WEB-PORTAL-PROTOCOL-MIB.mib."

    REVISION        "201202281200Z"
    DESCRIPTION     "Rev 10.0                28 Feb 2012 12:00
                     10.0 release of the TIMETRA-WEB-PORTAL-PROTOCOL-MIB.mib."

    ::= { timetraSRMIBModules 80 }

-- ----------------------------------------------------------------------------
--  Nokia 7xxx series WPP MIB structure
-- ----------------------------------------------------------------------------
tmnxWpp                      OBJECT IDENTIFIER ::= { tmnxSRObjs 80 }
    tmnxWppObjs              OBJECT IDENTIFIER ::= { tmnxWpp 1 }
    tmnxWppNotificationObjs  OBJECT IDENTIFIER ::= { tmnxWpp 2 }

tmnxWppConformance       OBJECT IDENTIFIER ::= { tmnxSRConfs 80 }
    tmnxWppCompliances   OBJECT IDENTIFIER ::= { tmnxWppConformance 1 }
    tmnxWppGroups        OBJECT IDENTIFIER ::= { tmnxWppConformance 2 }

tmnxWppNotifyPrefix      OBJECT IDENTIFIER ::= { tmnxSRNotifyPrefix 80 }
    tmnxWppNotifications OBJECT IDENTIFIER ::= { tmnxWppNotifyPrefix 0 }

--
-- Subtrees
--
tmnxWppPortalObjs        OBJECT IDENTIFIER ::= { tmnxWppObjs 1 }


-- ----------------------------------------------------------------------------
--  Textual Conventions
-- ----------------------------------------------------------------------------

TmnxWppStatsType ::= TEXTUAL-CONVENTION
    STATUS  current
    DESCRIPTION
       "The TmnxWppStatsType data type is an enumerated integer 
        that describes the values used to identify the WPP statistics."
    SYNTAX  INTEGER {
                event                      (1),
                droppedMsgType             (2),
                acceptedMsgType            (3),
                originalTransmittedMsgType (4),
                retransmittedMsgType       (5),
                forwardedToPeerMsgType     (6),
                receivedFromPeerMsgType    (7)
            }

TmnxWppUserName ::= TEXTUAL-CONVENTION
     STATUS  current
     DESCRIPTION
         "The data type TmnxWppUserName represents the user name
          of a WPP host."
     SYNTAX DisplayString (SIZE (0..253))

-- ----------------------------------------------------------------------------
--
--      The Web Portal Protocol Table
-- 

tmnxWppTable OBJECT-TYPE
    SYNTAX      SEQUENCE OF TmnxWppEntry
    MAX-ACCESS  not-accessible
    STATUS      current
    DESCRIPTION
        "The tmnxWppTable allows configuration of 
         the Web Portal Protocol (WPP) in a virtual router instance."
    ::= { tmnxWppObjs 2 }

tmnxWppEntry OBJECT-TYPE
    SYNTAX      TmnxWppEntry
    MAX-ACCESS  not-accessible
    STATUS      current
    DESCRIPTION
        "Each entry represents the configuration for 
         WPP in a particular virtual router instance.
         
         Entries in this table can be created and deleted via SNMP SET
         operations to tmnxWppRowStatus.
         
         A corresponding row in the TIMETRA-VRTR-MIB::vRtrConfTable must exist
         in order to create a row in this table."
    INDEX { vRtrID }
    ::= { tmnxWppTable 1 }

    TmnxWppEntry ::=
        SEQUENCE {
            tmnxWppRowStatus              RowStatus,
            tmnxWppLastCh                 TimeStamp,
            tmnxWppAdminState             TmnxAdminState
        }

tmnxWppRowStatus OBJECT-TYPE
    SYNTAX      RowStatus
    MAX-ACCESS  read-create
    STATUS      current
    DESCRIPTION
        "The value of tmnxWppRowStatus controls the creation and
         deletion of rows in the table."
    ::= { tmnxWppEntry 1 }

tmnxWppLastCh OBJECT-TYPE
    SYNTAX      TimeStamp
    MAX-ACCESS  read-only
    STATUS      current
    DESCRIPTION
        "The value of tmnxWppLastCh indicates the sysUpTime at
         the time of the most recent management-initiated change to this
         WPP portal."
    ::= { tmnxWppEntry 2 }

tmnxWppAdminState OBJECT-TYPE
    SYNTAX      TmnxAdminState
    MAX-ACCESS  read-create
    STATUS      current
    DESCRIPTION
        "The value of tmnxWppAdminState specifies
         the administrative state of the WPP in this virtual router instance."
    DEFVAL { outOfService }
    ::= { tmnxWppEntry 3 }

--
--      The WPP statistics Table
--

tmnxWppStatsTable   OBJECT-TYPE
    SYNTAX      SEQUENCE OF TmnxWppStatsEntry
    MAX-ACCESS  not-accessible
    STATUS      current
    DESCRIPTION
       "The tmnxWppStatsTable shows WPP statistics."
    ::= { tmnxWppObjs 3 }

tmnxWppStatsEntry   OBJECT-TYPE
    SYNTAX      TmnxWppStatsEntry
    MAX-ACCESS  not-accessible
    STATUS      current
    DESCRIPTION
       "Each conceptual row represents protocol statistics of a specific type.

        Entries in this table are created and destroyed by the system.
         
        Rows are only created where the statistics value is nonzero;
        this allows faster walking through this table; hence, it is recommended
        to perform only get-next-request operations to retrieve information
        from this table."
    INDEX { vRtrID,
            tmnxWppStatsType,
            tmnxWppStatsInstance
          }
    ::= { tmnxWppStatsTable 1 }

TmnxWppStatsEntry ::= 
    SEQUENCE {
        tmnxWppStatsType          TmnxWppStatsType,
        tmnxWppStatsInstance      Unsigned32,
        tmnxWppStatsName          DisplayString,
        tmnxWppStatsVal           Counter32
    }

tmnxWppStatsType OBJECT-TYPE
    SYNTAX      TmnxWppStatsType
    MAX-ACCESS  not-accessible
    STATUS      current
    DESCRIPTION 
       "The value of the object tmnxWppStatsType indicates
        the type of WPP statistics contained in this conceptual row."
    ::= { tmnxWppStatsEntry 1 }

tmnxWppStatsInstance OBJECT-TYPE
    SYNTAX      Unsigned32 (0..40)
    MAX-ACCESS  not-accessible
    STATUS      current
    DESCRIPTION 
       "The value of the object tmnxWppStatsInstance indicates
        the instance identifier of the statistics 
        contained in this conceptual row.
        
        Together with the value of tmnxWppStatsType it indicates
        unambiguously what the value of tmnxWppStatsVal means.
        
        For example: if the value of the object tmnxWppStatsType is equal
        to 'event', the value of tmnxWppStatsInstance indicates 
        the identifier of the type of event that this conceptual row 
        refers to, for example 'noResources', 
        and the value of tmnxWppStatsVal indicates the number
        of times a 'no resources' event occurred for this WPP portal."
    ::= { tmnxWppStatsEntry 2 }

tmnxWppStatsName OBJECT-TYPE
    SYNTAX      DisplayString (SIZE (1..64))
    MAX-ACCESS  read-only
    STATUS      current
    DESCRIPTION 
       "The value of the object tmnxWppStatsType indicates
        the human-readable identifier of the statistics 
        contained in this conceptual row.
        
        In the same example, the value of tmnxWppStatsName is 
        '(SCCRP) Start-Control-Connection-Reply'."
    ::= { tmnxWppStatsEntry 3 }

tmnxWppStatsVal OBJECT-TYPE
    SYNTAX      Counter32
    MAX-ACCESS  read-only
    STATUS      current
    DESCRIPTION 
       "The value of the object tmnxWppStatsType indicates
        the value of the statistics contained in this conceptual row."
    ::= { tmnxWppStatsEntry 4 }

--
--      The WPP Portal Table
--

tmnxWppPortalTable OBJECT-TYPE
    SYNTAX      SEQUENCE OF TmnxWppPortalEntry
    MAX-ACCESS  not-accessible
    STATUS      current
    DESCRIPTION
       "The tmnxWppPortalTable contains objects to configure 
        the WPP portals of this system."
    ::= { tmnxWppPortalObjs 1 }

tmnxWppPortalEntry OBJECT-TYPE
    SYNTAX      TmnxWppPortalEntry
    MAX-ACCESS  not-accessible
    STATUS      current
    DESCRIPTION
        "Each conceptual row represents information about 
         a particular WPP portal.

        Entries in this table can be created or deleted via SNMP operations.
        
        In order to create a conceptual row in this table, a row in the 
        tmnxWppTable with the same value of the object vRtrID must exist."
    INDEX { vRtrID,
            IMPLIED tmnxWppPortalName }
    ::= { tmnxWppPortalTable 1 }

TmnxWppPortalEntry ::= 
    SEQUENCE {
        tmnxWppPortalName           TNamedItem,
        tmnxWppPortalLastCh         TimeStamp,
        tmnxWppPortalRowStatus      RowStatus,
        tmnxWppPortalAddrType       InetAddressType,
        tmnxWppPortalAddr           InetAddress,
        tmnxWppPortalAdminState     TmnxAdminState,
        tmnxWppPortalSecret         DisplayString,
        tmnxWppPortalVersion        Unsigned32,
        tmnxWppPortalRetryInterval       Unsigned32,
        tmnxWppPortalNtfLogoutRetries    Unsigned32,
        tmnxWppPortalAckAuthRetries      Unsigned32
    }

tmnxWppPortalName OBJECT-TYPE
    SYNTAX      TNamedItem
    MAX-ACCESS  not-accessible
    STATUS      current
    DESCRIPTION
        "The value of tmnxWppPortalName specifies
         the name of this WPP portal."
    ::= { tmnxWppPortalEntry 1 }

tmnxWppPortalLastCh OBJECT-TYPE
    SYNTAX      TimeStamp
    MAX-ACCESS  read-only
    STATUS      current
    DESCRIPTION
        "The value of tmnxWppPortalLastCh indicates the sysUpTime at
         the time of the most recent management-initiated change to this
         table row."
    ::= { tmnxWppPortalEntry 2 }

tmnxWppPortalRowStatus OBJECT-TYPE
    SYNTAX      RowStatus
    MAX-ACCESS  read-create
    STATUS      current
    DESCRIPTION
       "The value of tmnxWppPortalRowStatus specifies 
        the row status of this row."
    ::= { tmnxWppPortalEntry 3 }

tmnxWppPortalAddrType OBJECT-TYPE
    SYNTAX      InetAddressType
    MAX-ACCESS  read-create
    STATUS      current
    DESCRIPTION
        "The value of tmnxWppPortalAddrType specifies
         the address type of tmnxWppPortalAddr.
         
         The only value supported is 'ipv4'.
         
         A value for this object must be specified when the row is created."
    ::= { tmnxWppPortalEntry 4 }

tmnxWppPortalAddr OBJECT-TYPE
    SYNTAX      InetAddress (SIZE(4|16))
    MAX-ACCESS  read-create
    STATUS      current
    DESCRIPTION
        "The value of tmnxWppPortalAddr specifies
         the IP address of the WPP portal.
         
         Only IPv4 addresses are supported.
         
         A value for this object must be specified when the row is created."
    ::= { tmnxWppPortalEntry 5 }

tmnxWppPortalAdminState OBJECT-TYPE
    SYNTAX      TmnxAdminState
    MAX-ACCESS  read-create
    STATUS      current
    DESCRIPTION
        "The value of tmnxWppPortalAdminState specifies
         the administrative state of this WPP portal."
    DEFVAL { outOfService }
    ::= { tmnxWppPortalEntry 6 }

tmnxWppPortalSecret  OBJECT-TYPE
    SYNTAX      DisplayString (SIZE (0..64))
    MAX-ACCESS  read-create
    STATUS      current
    DESCRIPTION
        "The value of tmnxWppPortalSecret specifies the 
         secret that is used by WPPv2 to authenticate the
         messages between portal and BRAS.

         A get request on this object always returns an empty string."
    DEFVAL { ''H }
    ::= { tmnxWppPortalEntry 7 }
    
tmnxWppPortalVersion  OBJECT-TYPE
    SYNTAX      Unsigned32 (1|2)
    MAX-ACCESS  read-create
    STATUS      current
    DESCRIPTION
        "The value of tmnxWppPortalVersion specifies the 
         protocol version that is expected by the WPP portal."
    DEFVAL { 1 }
    ::= { tmnxWppPortalEntry 8 } 
    
tmnxWppPortalRetryInterval  OBJECT-TYPE
    SYNTAX      Unsigned32 (10..2000)
    UNITS       "milliseconds"
    MAX-ACCESS  read-create
    STATUS      current
    DESCRIPTION
        "The value of tmnxWppPortalVersion specifies the 
         time interval between two consecutive retransmissions."
    DEFVAL { 2000 }
    ::= { tmnxWppPortalEntry 9 } 
    
tmnxWppPortalNtfLogoutRetries  OBJECT-TYPE
    SYNTAX      Unsigned32 (0..5)
    MAX-ACCESS  read-create
    STATUS      current
    DESCRIPTION
        "The value of tmnxWppPortalNtfLogoutRetries specifies the 
         number of retransmissions of an NTF_LOGOUT message."
    DEFVAL { 5 }
    ::= { tmnxWppPortalEntry 10 } 
    
tmnxWppPortalAckAuthRetries  OBJECT-TYPE
    SYNTAX      Unsigned32 (0..5)
    MAX-ACCESS  read-create
    STATUS      current
    DESCRIPTION
        "The value of tmnxWppPortalVersion specifies the 
         number of retransmissions of an ACK_OUT message."
    DEFVAL { 5 }
    ::= { tmnxWppPortalEntry 11 } 
    
--
--      The WPP Portal status Table
--

tmnxWppPortalStatTable OBJECT-TYPE
    SYNTAX      SEQUENCE OF TmnxWppPortalStatEntry
    MAX-ACCESS  not-accessible
    STATUS      current
    DESCRIPTION
       "The tmnxWppPortalStatTable contains objects to monitor 
        the WPP portals of this system."
    ::= { tmnxWppPortalObjs 2 }

tmnxWppPortalStatEntry OBJECT-TYPE
    SYNTAX      TmnxWppPortalStatEntry
    MAX-ACCESS  not-accessible
    STATUS      current
    DESCRIPTION
        "Each conceptual row represents status information about 
         a particular WPP portal.

        Entries in this table are created and destroyed automatically 
        by the system."
    AUGMENTS { tmnxWppPortalEntry }
    ::= { tmnxWppPortalStatTable 1 }

TmnxWppPortalStatEntry ::= 
    SEQUENCE {
        tmnxWppPortalStateControlledRtr  TmnxVRtrIDOrZero,
        tmnxWppPortalStateNumInterfaces  Gauge32,
        tmnxWppPortalStateTriggeredHosts TmnxEnabledDisabled
    }

tmnxWppPortalStateControlledRtr OBJECT-TYPE
    SYNTAX      TmnxVRtrIDOrZero
    MAX-ACCESS  read-only
    STATUS      current
    DESCRIPTION
        "The value of tmnxWppPortalStateControlledRtr indicates
         the identifier of the virtual router instance 
         being controlled by this portal.
         
         The value zero indicates that this portal is currently not 
         controlling any router instance."
    ::= { tmnxWppPortalStatEntry 1 }

tmnxWppPortalStateNumInterfaces OBJECT-TYPE
    SYNTAX      Gauge32
    MAX-ACCESS  read-only
    STATUS      current
    DESCRIPTION
       "The value of tmnxWppPortalStateNumInterfaces indicates 
        the number of interfaces associated with this portal that are
        administratively enabled."
    ::= { tmnxWppPortalStatEntry 2 }
    
tmnxWppPortalStateTriggeredHosts OBJECT-TYPE
    SYNTAX      TmnxEnabledDisabled
    MAX-ACCESS  read-only
    STATUS      current
    DESCRIPTION
       "The value of tmnxWppPortalStateTriggeredHosts indicates 
        whether triggered hosts are enabled on this portal.
         
        When tmnxWppPortalStateTriggeredHosts is enabled hosts are created
        when a host trigger is received from the WPP portal.
         
        When tmnxWppPortalStateTriggeredHosts is disabled, host triggers 
        are ignored."
    ::= { tmnxWppPortalStatEntry 3 }
--
--      The WPP Portal statistics Table
--

tmnxWppPortalStatsTable   OBJECT-TYPE
    SYNTAX      SEQUENCE OF TmnxWppPortalStatsEntry
    MAX-ACCESS  not-accessible
    STATUS      current
    DESCRIPTION
       "The tmnxWppPortalStatsTable shows protocol statistics information 
        of WPP portals."
    ::= { tmnxWppPortalObjs 3 }

tmnxWppPortalStatsEntry   OBJECT-TYPE
    SYNTAX      TmnxWppPortalStatsEntry
    MAX-ACCESS  not-accessible
    STATUS      current
    DESCRIPTION
       "Each conceptual row represents protocol statistics of a specific type.

        Entries in this table are created and destroyed by the system.
         
        Rows are only created where the statistics value is nonzero;
        this allows faster walking through this table; hence, it is recommended
        to perform only get-next-request operations to retrieve information
        from this table."
    INDEX { vRtrID,
            tmnxWppPortalName,
            tmnxWppPortalStatsType,
            tmnxWppPortalStatsInstance 
          }
    ::= { tmnxWppPortalStatsTable 1 }

TmnxWppPortalStatsEntry ::= 
    SEQUENCE {
        tmnxWppPortalStatsType          TmnxWppStatsType,
        tmnxWppPortalStatsInstance      Unsigned32,
        tmnxWppPortalStatsName          DisplayString,
        tmnxWppPortalStatsVal           Counter32
    }

tmnxWppPortalStatsType OBJECT-TYPE
    SYNTAX      TmnxWppStatsType
    MAX-ACCESS  not-accessible
    STATUS      current
    DESCRIPTION 
       "The value of the object tmnxWppPortalStatsType indicates
        the type of WPP statistics contained in this conceptual row."
    ::= { tmnxWppPortalStatsEntry 1 }

tmnxWppPortalStatsInstance OBJECT-TYPE
    SYNTAX      Unsigned32 (0..40)
    MAX-ACCESS  not-accessible
    STATUS      current
    DESCRIPTION 
       "The value of the object tmnxWppPortalStatsInstance indicates
        the instance identifier of the statistics 
        contained in this conceptual row.
        
        Together with the value of tmnxWppPortalStatsType it indicates
        unambiguously what the value of tmnxWppPortalStatsVal means.
        
        For example: if the value of the object tmnxWppPortalStatsType is equal
        to 'event', the value of tmnxWppPortalStatsInstance indicates 
        the identifier of the type of event that this conceptual row 
        refers to, for example 'noResources', 
        and the value of tmnxWppPortalStatsVal indicates the number
        of times a 'no resources' event occurred for this WPP portal."
    ::= { tmnxWppPortalStatsEntry 2 }

tmnxWppPortalStatsName OBJECT-TYPE
    SYNTAX      DisplayString (SIZE (1..64))
    MAX-ACCESS  read-only
    STATUS      current
    DESCRIPTION 
       "The value of the object tmnxWppPortalStatsType indicates
        the human-readable identifier of the statistics 
        contained in this conceptual row.
        
        In the same example, the value of tmnxWppPortalStatsName is 
        '(SCCRP) Start-Control-Connection-Reply'."
    ::= { tmnxWppPortalStatsEntry 3 }

tmnxWppPortalStatsVal OBJECT-TYPE
    SYNTAX      Counter32
    MAX-ACCESS  read-only
    STATUS      current
    DESCRIPTION 
       "The value of the object tmnxWppPortalStatsType indicates
        the value of the statistics contained in this conceptual row."
    ::= { tmnxWppPortalStatsEntry 4 }

--
--      The WPP Host Table
--

tmnxWppHostTable OBJECT-TYPE
    SYNTAX      SEQUENCE OF TmnxWppHostEntry
    MAX-ACCESS  not-accessible
    STATUS      current
    DESCRIPTION
        "The tmnxWppHostTable contains status information about WPP hosts."
    ::= { tmnxWppPortalObjs 4 }

tmnxWppHostEntry OBJECT-TYPE
    SYNTAX      TmnxWppHostEntry
    MAX-ACCESS  not-accessible
    STATUS      current
    DESCRIPTION
        "Each conceptual row represents information about 
         a particular WPP host.

         Entries in this table are created and destroyed automatically
         by the system."
    INDEX { vRtrID,
            tmnxWppPortalName,
            tmnxWppHostAddrType,
            tmnxWppHostAddr
          }
    ::= { tmnxWppHostTable 1 }

TmnxWppHostEntry ::= 
    SEQUENCE {
        tmnxWppHostAddrType             InetAddressType,
        tmnxWppHostAddr                 InetAddress,
        tmnxWppHostStatus               INTEGER,
        tmnxWppHostSerialNumber         Unsigned32,
        tmnxWppHostRequestId            Unsigned32,
        tmnxWppHostPortalRemotePort     InetPortNumber,
        tmnxWppHostPortalLclIpAddrType  InetAddressType,
        tmnxWppHostPortalLclIpAddr      InetAddress,
        tmnxWppHostUserName             TmnxWppUserName,
        tmnxWppHostService              TmnxServId,
        tmnxWppHostMacAddress           MacAddress,
        tmnxWppHostIsTriggered          TruthValue,
        tmnxWppHostTrackSrrpInst        Unsigned32,
        tmnxWppHostIsMCBackup           TruthValue
    }

tmnxWppHostAddrType OBJECT-TYPE
    SYNTAX      InetAddressType
    MAX-ACCESS  not-accessible
    STATUS      current
    DESCRIPTION
        "The value of tmnxWppHostAddrType specifies
         the address type of tmnxWppHostAddr."
    ::= { tmnxWppHostEntry 1 }

tmnxWppHostAddr OBJECT-TYPE
    SYNTAX      InetAddress (SIZE(4|16))
    MAX-ACCESS  not-accessible
    STATUS      current
    DESCRIPTION
        "The value of tmnxWppHostAddr specifies 
         the IP address of the WPP host."
    ::= { tmnxWppHostEntry 2 }

tmnxWppHostStatus OBJECT-TYPE
    SYNTAX      INTEGER {
                    idle                             (1),
                    challenged                       (2),
                    authenticating                   (3),
                    authenticated                    (4),
                    established                      (5),
                    loggingOut                       (6)
                }
    MAX-ACCESS  read-only
    STATUS      current
    DESCRIPTION
       "The value of tmnxWppHostStatus indicates the
        state of the WPP host."
    ::= { tmnxWppHostEntry 3 }

tmnxWppHostSerialNumber OBJECT-TYPE
    SYNTAX      Unsigned32
    MAX-ACCESS  read-only
    STATUS      current
    DESCRIPTION
       "The value of tmnxWppHostSerialNumber indicates
        the serial number of the WPP host.
        
        The value zero indicates that the serial number is unknown or 
        irrelevant."
    ::= { tmnxWppHostEntry 4 }

tmnxWppHostRequestId OBJECT-TYPE
    SYNTAX      Unsigned32
    MAX-ACCESS  read-only
    STATUS      current
    DESCRIPTION
       "The value of tmnxWppHostRequestId indicates
        the request ID of the WPP host.
        
        The value zero indicates that the request ID is unknown or 
        irrelevant."
    ::= { tmnxWppHostEntry 5 }

tmnxWppHostPortalRemotePort OBJECT-TYPE
    SYNTAX      InetPortNumber
    MAX-ACCESS  read-only
    STATUS      current
    DESCRIPTION 
        "The value of tmnxWppHostPortalRemotePort indicates
         the UDP source port used by the portal while sending WPP protocol
         messages about this host to this system.
         
         The value zero indicates that the port is not yet known."
    ::= { tmnxWppHostEntry 6 }

tmnxWppHostPortalLclIpAddrType OBJECT-TYPE
    SYNTAX      InetAddressType
    MAX-ACCESS  read-only
    STATUS      current
    DESCRIPTION 
        "The value of tmnxWppHostPortalLclIpAddrType indicates
         the address type of tmnxWppHostPortalLclIpAddr."
    ::= { tmnxWppHostEntry 7 }

tmnxWppHostPortalLclIpAddr OBJECT-TYPE
    SYNTAX      InetAddress (SIZE(0|4|16))
    MAX-ACCESS  read-only
    STATUS      current
    DESCRIPTION 
        "The value of tmnxWppHostPortalLclIpAddr indicates
         the destination IP address used by the portal while sending WPP
         protocol messages about this host to this system."
    ::= { tmnxWppHostEntry 8 }

tmnxWppHostUserName OBJECT-TYPE
    SYNTAX      TmnxWppUserName
    MAX-ACCESS  read-only
    STATUS      current
    DESCRIPTION
        "The value of tmnxWppHostUserName indicates the WPP user name
         of this WPP host."
    ::= { tmnxWppHostEntry 9 }

tmnxWppHostService OBJECT-TYPE
    SYNTAX      TmnxServId
    MAX-ACCESS  read-only
    STATUS      current
    DESCRIPTION
        "The value of tmnxWppHostService indicates the service ID of
         the service to which this WPP host belongs."
    ::= { tmnxWppHostEntry 10 }

tmnxWppHostMacAddress OBJECT-TYPE
    SYNTAX      MacAddress
    MAX-ACCESS  read-only
    STATUS      current
    DESCRIPTION 
        "The value of tmnxWppHostMacAddress indicates
         the MAC address of this WPP host."
    ::= { tmnxWppHostEntry 11 }
    
tmnxWppHostIsTriggered OBJECT-TYPE
    SYNTAX      TruthValue
    MAX-ACCESS  read-only
    STATUS      current
    DESCRIPTION 
        "The value of tmnxWppHostIsTriggered indicates
         whether the creation of the host is triggered by the portal.
         
         If the host creation is not triggered by the portal, the 
         tmnxWppHostIsTriggered value is FALSE."
    ::= { tmnxWppHostEntry 12 }       

tmnxWppHostTrackSrrpInst  OBJECT-TYPE
    SYNTAX      Unsigned32
    MAX-ACCESS  read-only
    STATUS      current
    DESCRIPTION
        "The value of tmnxWppHostTrackSrrpInst indicates the SRRP instance 
         whose state is tracked by this WPP host to determine if it is on
         the MCS master or backupo node."
    ::= { tmnxWppHostEntry 13 }
    
tmnxWppHostIsMCBackup  OBJECT-TYPE
    SYNTAX      TruthValue
    MAX-ACCESS  read-only
    STATUS      current
    DESCRIPTION 
        "The value of tmnxWppHostIsMCBackup indicates whether the 
         WPP host is on the MCS backup node or not."
    ::= { tmnxWppHostEntry 14 }
        
--
--      The IES Group Interface WPP Table
--

tmnxWppIfTable OBJECT-TYPE
    SYNTAX      SEQUENCE OF TmnxWppIfEntry
    MAX-ACCESS  not-accessible
    STATUS      current
    DESCRIPTION
       "The tmnxWppIfTable contains objects to configure 
        the WPP for the IES group interfaces of this system."
    ::= { tmnxWppObjs 4 }

tmnxWppIfEntry OBJECT-TYPE
    SYNTAX      TmnxWppIfEntry
    MAX-ACCESS  not-accessible
    STATUS      current
    DESCRIPTION
        "Each conceptual row represents WPP information about 
         a particular IES group interface.

        Entries in this table can be created or deleted via SNMP operations.
        
        In order to create a conceptual row in this table, a row in the 
        TIMETRA-SERV-MIB::iesGrpIfTable with the same index must exist."
    INDEX { svcId, 
            iesIfIndex }
    ::= { tmnxWppIfTable 1 }

TmnxWppIfEntry ::= 
    SEQUENCE {
        tmnxWppIfLastCh                 TimeStamp,
        tmnxWppIfRowStatus              RowStatus,
        tmnxWppIfAdminState             TmnxAdminState,
        tmnxWppIfPortalRouter           TmnxVRtrIDOrZero,
        tmnxWppIfPortalName             TNamedItemOrEmpty,
        tmnxWppIfSubProfile             TNamedItemOrEmpty,
        tmnxWppIfSLAProfile             TNamedItemOrEmpty,
        tmnxWppIfAppProfile             TNamedItemOrEmpty,
        tmnxWppIfRestoreDisconnected    TruthValue
        ,
        tmnxWppIfUserDb                 TNamedItemOrEmpty,
        tmnxWppIfLeaseTime              Unsigned32,
        tmnxWppIfEnableTriggeredHosts   TruthValue
    }

tmnxWppIfLastCh OBJECT-TYPE
    SYNTAX      TimeStamp
    MAX-ACCESS  read-only
    STATUS      current
    DESCRIPTION
        "The value of tmnxWppIfLastCh indicates the sysUpTime at
         the time of the most recent management-initiated change to this
         table row."
    ::= { tmnxWppIfEntry 1 }

tmnxWppIfRowStatus OBJECT-TYPE
    SYNTAX      RowStatus
    MAX-ACCESS  read-create
    STATUS      current
    DESCRIPTION
       "The value of tmnxWppIfRowStatus specifies 
        the row status of this row."
    ::= { tmnxWppIfEntry 2 }

tmnxWppIfAdminState OBJECT-TYPE
    SYNTAX      TmnxAdminState
    MAX-ACCESS  read-create
    STATUS      current
    DESCRIPTION
        "The value of tmnxWppIfAdminState specifies
         the administrative state of the WPP for hosts using
         this IES group interface."
    DEFVAL { outOfService }
    ::= { tmnxWppIfEntry 3 }
    
tmnxWppIfPortalRouter OBJECT-TYPE
    SYNTAX      TmnxVRtrIDOrZero
    MAX-ACCESS  read-create
    STATUS      current
    DESCRIPTION
        "The value of tmnxWppIfPortalName specifies 
         the virtual router instance ID of the WPP portal 
         for the hosts using this IES group interface.
         
         An corresponding row must exist in the TIMETRA-VRTR-MIB::vRtrConfTable.
         
         When that row is removed while the value of tmnxWppIfAdminState is equal to
         outOfService, the system resets the value of this object
         to its default value, zero, and the value of tmnxWppIfPortalName to empty.
         
         A row corresponding to tmnxWppIfPortalRouter and tmnxWppIfPortalName must
         exist in the tmnxWppPortalTable while the value of tmnxWppIfAdminState is
         equal to 'inService'.
         
         The values of the objects tmnxWppIfPortalRouter and tmnxWppIfPortalName must
         be either both equal to their default values (zero/empty) or both not equal
         to their default values."
    DEFVAL { 0 }
    ::= { tmnxWppIfEntry 4 }

tmnxWppIfPortalName OBJECT-TYPE
    SYNTAX      TNamedItemOrEmpty
    MAX-ACCESS  read-create
    STATUS      current
    DESCRIPTION
        "The value of tmnxWppIfPortalName specifies the name of the WPP
         portal for the hosts using this IES group interface.
         
         A row corresponding to tmnxWppIfPortalRouter and tmnxWppIfPortalName must
         exist in the tmnxWppPortalTable while the value of tmnxWppIfAdminState is
         equal to 'inService'.
         
         The values of the objects tmnxWppIfPortalRouter and tmnxWppIfPortalName must
         be either both equal to their default values (zero/empty) or both not equal
         to their default values."
    DEFVAL { ''H }
    ::= { tmnxWppIfEntry 5 }

tmnxWppIfSubProfile OBJECT-TYPE
    SYNTAX      TNamedItemOrEmpty
    MAX-ACCESS  read-create
    STATUS      current
    DESCRIPTION
        "The value of tmnxWppIfSubProfile specifies the initial subscriber
         profile, to be used during the WPP authentication phase of hosts using
         this IES group interface."
    DEFVAL { ''H }
    ::= { tmnxWppIfEntry 6 }

tmnxWppIfSLAProfile OBJECT-TYPE
    SYNTAX      TNamedItemOrEmpty
    MAX-ACCESS  read-create
    STATUS      current
    DESCRIPTION
        "The value of tmnxWppIfSLAProfile specifies the initial SLA
         profile, to be used during the WPP authentication phase of hosts using
         this IES group interface."
    DEFVAL { ''H }
    ::= { tmnxWppIfEntry 7 }

tmnxWppIfAppProfile OBJECT-TYPE
    SYNTAX      TNamedItemOrEmpty
    MAX-ACCESS  read-create
    STATUS      current
    DESCRIPTION
        "The value of tmnxWppIfAppProfile specifies the initial
         application profile, to be used during the WPP authentication phase 
         of hosts using this IES group interface.
    
         The application profile is configured in
         TIMETRA-BSX-NG-MIB.mib::tmnxBsxAppProfTable."
    DEFVAL { ''H }
    ::= { tmnxWppIfEntry 8 }

tmnxWppIfRestoreDisconnected OBJECT-TYPE
    SYNTAX      TruthValue
    MAX-ACCESS  read-create
    STATUS      current
    DESCRIPTION
        "The value of tmnxWppIfRestoreDisconnected specifies
         if the initial profiles must be restored after a host has disconnected."
    DEFVAL { true }
    ::= { tmnxWppIfEntry 9 }

tmnxWppIfUserDb OBJECT-TYPE
    SYNTAX      TNamedItemOrEmpty    
    MAX-ACCESS  read-create
    STATUS      current
    DESCRIPTION
        "The value of tmnxWppIfUserDb specifies the user database that will 
         be used to retrieve the WPP information for the hosts using this 
         IES group interface.
         
         If tmnxWppIfUserDb is configured, the WPP information configured
         on this particular IES group interface is only used in case no 
         corresponding value is returned from LUDB lookup."
    DEFVAL { ''H }
    ::= { tmnxWppIfEntry 10 }
    
tmnxWppIfLeaseTime   OBJECT-TYPE
    SYNTAX      Unsigned32 (10..315446399)
    UNITS       "seconds"
    MAX-ACCESS  read-create
    STATUS      current
    DESCRIPTION
        "The value of the object tmnxWppIfLeaseTime specifies, in seconds, 
         the lease time of hosts using this IES group interface."
    DEFVAL { 600 }
    ::= { tmnxWppIfEntry 11 }
           
tmnxWppIfEnableTriggeredHosts   OBJECT-TYPE
    SYNTAX      TruthValue
    MAX-ACCESS  read-create
    STATUS      current
    DESCRIPTION     
        "The value of the object tmnxWppIfEnableTriggeredHosts specifies 
         whether triggered hosts are enabled on this IES group interface.
         
         When tmnxWppIfEnableTriggeredHosts is set to true hosts are created
         when a host trigger is received from the WPP portal.
         
         When tmnxWppIfEnableTriggeredHosts is set to false, host triggers 
         are ignored.

         The value 'true' is only effective if this interface is associated
         with a port where on one of its SAP's, a row can be created 
         in the TIMETRA-SAP-MIB::sapDefHostTable."
    DEFVAL { false }
    ::= { tmnxWppIfEntry 12 }
        
-- --------------------------------------------------------
-- WPP scalar objects
-- --------------------------------------------------------

tmnxWppTableLastCh OBJECT-TYPE
    SYNTAX      TimeStamp
    MAX-ACCESS  read-only
    STATUS      current
    DESCRIPTION
        "The value of the object tmnxWppTableLastCh indicates
         the value of sysUpTime at the time of the last modification of
         an entry in the tmnxWppTable."
    ::= { tmnxWppObjs 100 }

tmnxWppPortalTableLastCh OBJECT-TYPE
    SYNTAX      TimeStamp
    MAX-ACCESS  read-only
    STATUS      current
    DESCRIPTION
        "The value of the object tmnxWppPortalTableLastCh indicates
         the value of sysUpTime at the time of the last modification of
         an entry in the tmnxWppPortalTable."
    ::= { tmnxWppObjs 101 }
    
tmnxWppIfTableLastCh OBJECT-TYPE
    SYNTAX      TimeStamp
    MAX-ACCESS  read-only
    STATUS      current
    DESCRIPTION
        "The value of the object tmnxWppIfTableLastCh indicates
         the value of sysUpTime at the time of the last modification of
         an entry in the tmnxWppIfTable."
    ::= { tmnxWppObjs 102 }

--  Notification objects

 tmnxWppNotifyDescription  OBJECT-TYPE
    SYNTAX      DisplayString (SIZE(0..255))
    MAX-ACCESS  accessible-for-notify
    STATUS      current
    DESCRIPTION
        "The object tmnxWppNotifyDescription is a printable character 
         string."
    ::= { tmnxWppNotificationObjs 1 }

    
--  Notifications

tmnxWppPortalStatChanged NOTIFICATION-TYPE
    OBJECTS {
        tmnxWppPortalStateControlledRtr,
        tmnxWppPortalStateNumInterfaces
    }
    STATUS current
    DESCRIPTION
        "[CAUSE] The tmnxWppPortalStatChanged notification is sent when 
         the value of one of the objects in the tmnxWppPortalStatTable changes.         
         [EFFECT] No effect on the service.                     
         [RECOVERY] No recovery required."
    ::= { tmnxWppNotifications 1}

tmnxWppHostAuthenticationFailed NOTIFICATION-TYPE
    OBJECTS {
        tmnxWppHostStatus,
        tmnxWppNotifyDescription
    }
    STATUS current
    DESCRIPTION
        "[CAUSE] The tmnxWppHostAuthenticationFailed notification is sent when 
         a WPP host could not be authenticated. 
         
         More detailed information is supplied 
         in the object tmnxWppNotifyDescription.
                 
         [EFFECT] The corresponding row in the tmnxWppHostTable disappears if
         the value of the object tmnxWppIfRestoreDisconnected is 
         equal to 'false'; otherwise, the value of the object tmnxWppHostStatus
         is set to 'idle'.
                              
         [RECOVERY] The recovery action will depend on the exact failure cause,
         as given by the value of tmnxWppNotifyDescription."
    ::= { tmnxWppNotifications 2}
    
tmnxWppPortalUnreachable NOTIFICATION-TYPE
    OBJECTS {
        tmnxWppPortalLastCh,
        tmnxWppNotifyDescription
    }
    STATUS current
    DESCRIPTION
        "[CAUSE] The tmnxWppPortalUnreachable notification is generated when
         WPP protocol messages must be sent out after a node is restarted, but 
         when no route is available yet towards it. This notification is  
         sent every minute as long as the portal is not reachable yet.
         
         [EFFECT] The WPP portal is unreachable and finally the messages will
         be dropped.
         
         [RECOVERY] Initially no recovery is required as it is expected that the
         WPP portal can be unreachable for some time after a node restart. When
         however the problem remains the operator should check the routing table."
    ::= { tmnxWppNotifications 3 }
    
-- ----------------------------------------------------------------------------
--  Conformance Groups
-- ----------------------------------------------------------------------------
tmnxWppGroup   OBJECT-GROUP
    OBJECTS {
        tmnxWppRowStatus,
        tmnxWppLastCh,
        tmnxWppAdminState,
        tmnxWppStatsName,
        tmnxWppStatsVal, 
        tmnxWppPortalLastCh,   
        tmnxWppPortalRowStatus,
        tmnxWppPortalAddrType, 
        tmnxWppPortalAddr,
        tmnxWppPortalAdminState,
        tmnxWppPortalStateControlledRtr,
        tmnxWppPortalStateNumInterfaces,
        tmnxWppPortalStatsName,
        tmnxWppPortalStatsVal, 
        tmnxWppHostStatus,              
        tmnxWppHostSerialNumber,        
        tmnxWppHostRequestId,           
        tmnxWppHostPortalRemotePort,    
        tmnxWppHostPortalLclIpAddrType, 
        tmnxWppHostPortalLclIpAddr,     
        tmnxWppHostUserName,            
        tmnxWppHostService,             
        tmnxWppHostMacAddress,          
        tmnxWppIfLastCh,    
        tmnxWppIfRowStatus,
        tmnxWppIfAdminState,          
        tmnxWppIfPortalRouter,        
        tmnxWppIfPortalName,          
        tmnxWppIfSubProfile,          
        tmnxWppIfSLAProfile,          
        tmnxWppIfAppProfile,          
        tmnxWppIfRestoreDisconnected, 
        tmnxWppTableLastCh,
        tmnxWppPortalTableLastCh,
        tmnxWppIfTableLastCh
    }
    STATUS      current
    DESCRIPTION
        "The group of objects for the
         management of the Web Portal Protocol (WPP)
         on Nokia SROS series systems."
    ::= { tmnxWppGroups 1 }

tmnxWppV12v0Group   OBJECT-GROUP
    OBJECTS {
        tmnxWppPortalSecret,
        tmnxWppPortalVersion,
        tmnxWppIfUserDb,
        tmnxWppIfLeaseTime,
        tmnxWppIfEnableTriggeredHosts,
        tmnxWppHostIsTriggered,
        tmnxWppPortalStateTriggeredHosts,
        tmnxWppHostTrackSrrpInst,
        tmnxWppHostIsMCBackup
    }
    STATUS      current
    DESCRIPTION
        "The group of additional objects for the
         management of the Web Portal Protocol (WPP)
         on Nokia SROS release 12.0 series systems."
    ::= { tmnxWppGroups 2 }
            
tmnxWppNtfLogoutGroup   OBJECT-GROUP
    OBJECTS {
        tmnxWppPortalRetryInterval,
        tmnxWppPortalNtfLogoutRetries,
        tmnxWppPortalAckAuthRetries  
    }
    STATUS      current
    DESCRIPTION
        "The group of additional objects for the
         management of the Web Portal Protocol (WPP)
         on Nokia SROS release 12.0 series systems."
    ::= { tmnxWppGroups 3 }
    
tmnxWppNotifyObjsGroup     OBJECT-GROUP
    OBJECTS {   
        tmnxWppNotifyDescription
    }
    STATUS        current
    DESCRIPTION
        "The group of notification objects supporting NAT notifications
         on Nokia SROS series systems."
    ::= { tmnxWppGroups 99 }

-- ----------------------
-- NOTIFICATION-GROUPS
-- ----------------------

tmnxWppNotifyGroup NOTIFICATION-GROUP
    NOTIFICATIONS {
        tmnxWppPortalStatChanged,
        tmnxWppHostAuthenticationFailed,
        tmnxWppPortalUnreachable
    }
    STATUS      current
    DESCRIPTION
        "The group of notifications supporting WPP
         on Nokia SROS series systems."
    ::= { tmnxWppGroups 100 }
    
-- ----------------------------------------------------------------------------
--  Compliance information
-- ----------------------------------------------------------------------------
tmnxWppCompliance MODULE-COMPLIANCE
    STATUS  obsolete
    DESCRIPTION
        "The compliance statement for management of Web Portal Protocol
         on Nokia 7xxx series systems."
    MODULE  -- this module
        MANDATORY-GROUPS {
            tmnxWppGroup
        }
    ::= { tmnxWppCompliances 1 }

tmnxWppNotifyCompliance MODULE-COMPLIANCE
    STATUS  obsolete
    DESCRIPTION
        "The compliance statement for Web Portal Protocol notifications
         on Nokia SROS series systems."
    MODULE  -- this module
        MANDATORY-GROUPS {
            tmnxWppNotifyGroup
        }
    ::= { tmnxWppCompliances 2 }

tmnxWppV12v0Compliance MODULE-COMPLIANCE
    STATUS  current
    DESCRIPTION
        "The compliance statement for management of Web Portal Protocol
         on Nokia 7xxx series systems in release 12.0."
    MODULE  -- this module
        MANDATORY-GROUPS {
            tmnxWppGroup,
            tmnxWppV12v0Group,
            tmnxWppNtfLogoutGroup,
            tmnxWppNotifyGroup
        }
    ::= { tmnxWppCompliances 3 }

END
